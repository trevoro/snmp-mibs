-- varfix Fri Aug 17 10:36:18 EDT 2001 user: sse
-- File created using agent2concat
-- By: sse
-- Date: Fri Aug 17 10:35:30 EDT 2001


ITOUCHHUB DEFINITIONS ::= BEGIN

--
-- FILE: /users/sse/mibs/src/rfc/rfc1155.smi
--

-- Changes to rfc1155 (SMI):
--      Removed EXPORTS.
--      Added explicit definitions of ccitt, null, iso, org, and dod.
--      Commented out OBJECT-TYPE macro definition (since will use
--        the definition from RFC1212).
--      Commented out definitions of syntax types and replaced
--        with SMIC directives to enable them.



        -- no IMPORTS
IMPORTS
	OBJECT-TYPE, enterprises, TimeTicks, Gauge, Counter, NetworkAddress, IpAddress
		FROM RFC1155-SMI
	TRAP-TYPE
		FROM RFC-1215
;

        -- Define OIDs
--        ccitt        OBJECT IDENTIFIER ::= { 0 }
--        null         OBJECT IDENTIFIER ::= { ccitt 0 }

--        iso          OBJECT IDENTIFIER ::= { 1 }
--        org          OBJECT IDENTIFIER ::= { iso 3 }
--        dod          OBJECT IDENTIFIER ::= { org 6 }
--        internet     OBJECT IDENTIFIER ::= { dod 1 }
--        directory    OBJECT IDENTIFIER ::= { internet 1 }
--        mgmt         OBJECT IDENTIFIER ::= { internet 2 }
--        experimental OBJECT IDENTIFIER ::= { internet 3 }
--        private      OBJECT IDENTIFIER ::= { internet 4 }
--        enterprises  OBJECT IDENTIFIER ::= { private 1 }

        -- Make builtin items known
--        SMI NetworkAddress
--        SMI IpAddress
--        SMI Counter
--        SMI Gauge
--        SMI TimeTicks
--        SMI Opaque


        -- definition of object types

        --    OBJECT-TYPE MACRO ::=
        --    BEGIN
        --        TYPE NOTATION ::= "SYNTAX" type (TYPE ObjectSyntax)
        --                          "ACCESS" Access
        --                          "STATUS" Status
        --        VALUE NOTATION ::= value (VALUE ObjectName)
        --
        --        Access ::= "read-only"
        --                        | "read-write"
        --                        | "write-only"
        --                        | "not-accessible"
        --        Status ::= "mandatory"
        --                        | "optional"
        --                        | "obsolete"
        --    END
        --
        -- names of objects in the MIB
        --
        --       ObjectName ::= OBJECT IDENTIFIER
        --
        -- syntax of objects in the MIB
        --
        --       ObjectSyntax ::=
        --           CHOICE {
        --               simple
        --                   SimpleSyntax,
               -- note that simple SEQUENCEs are not directly
               -- mentioned here to keep things simple (i.e.,
               -- prevent mis-use).  However, application-wide
               -- types which are IMPLICITly encoded simple
               -- SEQUENCEs may appear in the following CHOICE
        --
        --               application-wide
        --                   ApplicationSyntax
        --           }
        --
        --          SimpleSyntax ::=
        --              CHOICE {
        --                  number INTEGER,
        --                  string OCTET STRING,
        --                  object OBJECT IDENTIFIER,
        --                  empty  NULL
        --              }
        --
        --          ApplicationSyntax ::=
        --              CHOICE {
        --                  address NetworkAddress,
        --                  counter Counter,
        --                  gauge Gauge,
        --                  ticks TimeTicks,
        --                  arbitrary Opaque
                  -- other application-wide types, as they are
                  -- defined, will be added here
        --              }
        --
        --
                  -- application-wide types

        --          NetworkAddress ::=
        --              CHOICE {
        --                  internet IpAddress
        --              }
        --
        --          IpAddress ::=
        --              [APPLICATION 0]
        --                  IMPLICIT OCTET STRING (SIZE (4))
        --
        --          Counter ::=
        --              [APPLICATION 1]
        --                  IMPLICIT INTEGER (0..4294967295)
        --
        --          Gauge ::=
        --              [APPLICATION 2]
        --                  IMPLICIT INTEGER (0..4294967295)
        --
        --          TimeTicks ::=
        --              [APPLICATION 3]
        --                  IMPLICIT INTEGER (0..4294967295)
        --
        --          Opaque ::=
        --              [APPLICATION 4]
        --                  IMPLICIT OCTET STRING

--
-- FILE: /users/sse/mibs/src/itouch/it-mib.mib
--

-- $Id: it-mib.mib,v 1.3 2001/05/07 20:48:16 sse Exp $




            iTouch          OBJECT IDENTIFIER ::= { enterprises 33 }
            agent           OBJECT IDENTIFIER ::= { iTouch 8 }

            -- This is a MIB module for all iTouch Communications systems.

            -- Copyright 2000 iTouch Communications, Inc. All Rights Reserved.
            -- Reproduction of this document is authorized on
            -- condition that this copyright notice is included.
            -- This MIB document embodies iTouch Communications, Inc.'s 
            -- proprietary intellectual property.  iTouch Communications, Inc.
            -- retains all title and ownership in this MIB, including any
            -- revisions.
            --
            -- It is iTouch Communications, Inc.'s intent to encourage the
            -- widespread use of this MIB in connection with the management of
            -- iTouch Communications, Inc. products. iTouch Communications,
            -- Inc. grants vendors,end-users, and other interested parties a
            -- non-exclusive license to use this MIB in connection with the
            -- management of iTouch Communications, Inc. products.
            --
            -- This MIB document is supplied "AS IS," and iTouch 
            -- Communications, Inc. makes no warranty, either express or
            -- implied, as to the use operation, condition, or performance of
            -- the MIB.


            -- Textual Conventions

            -- This data type is used throughout the iTouch private MIB
            -- to model an absolute date and time.
            -- In order, the octets contain the following information:
            -- century, year within century (0..99), month (1..12),
            -- day (1..31), hour (0..23), minute (0..59),
            -- second (0..59), hundredth (0..99).  If the century
            -- value is zero, the date and time are unknown, and the
            -- other values are meaningless.

            DateTime ::=
                OCTET STRING (SIZE (8))

            -- This data type is used throughout the iTouch private MIB
            -- to indicate the type of an address stored in a related
            -- octet string.

            AddressType ::=
                INTEGER  { 
                           unknown(1), 
                           other(2), 
                           local(3),
                           ip(4), 
                           ethernet(5) 
                         }

            -- This data type is used throughout the iTouch private MIB
            -- to indicate an address with a type attached.  The type is
            -- the first byte.  The address immediately follows the
            -- type, occupying the appropriate number of bytes, (0..31).
            -- The type values are:
            --     1   unknown
            --     2   other
            --     3   local
            --     4   ip
            --     5   ethernet

            TypedAddress ::=
                OCTET STRING (SIZE (1..32))

            -- This data type is used throughout the iTouch private MIB
            -- to indicate the type of software running on a system. 

            SoftwareType ::=
                INTEGER  { 
                           terminalServer(1), 
                           bridge(3), 
                           repeater(4),
                           bridgeRouter(5), 
                           router(6),
                           bridgeRouterRepeater(7), 
                           switch(8), 
                           oem(9) 
                         }

            -- This data type is used throughout the iTouch private MIB
            -- to indicate the type of a system's main function 
            -- hardware.  


            HardwareType ::=
                INTEGER  { 
                           unknown(1),
                           em1608(29), 
                           ir7520(30), 
                           ir9020(31), 
                           ir7020(32),
                           mxTServJ8(33), 
                           mxTservJ16(34), 
                           mxManF2(35),
                           mx1500(36), 
                           mx1100(37), 
                           mx1800(38),
                           mxNpcP1(39), 
                           mxTsrLJ16(40), 
                           mxTsrvLJ8(41), 
                           mxTsrvMj8(42), 
                           mxTsrvNJ8(43), 
                           mxTsrvOJ8(44),
                           mx1400(45), 
                           mx6510(46),
                           mxRb2(47),  
                           mx1500x8(49), 
                           mx1710(50), 
                           mx2710(51),
                           ts3395(52), 
                           mx1120(53), 
                           mx1520(54),
                           mx1820(55), 
                           mx2220(56), 
                           mx3510(57),
                           mx6625(58), 
                           mx2120(59), 
                           mx6020(60),
                           mx3610(61), 
                           etsmim(62), 
                           mx3010(63),
                           mx6025(64), 
                           lannetTs(65), 
                           fn1500(66),
                           dpXp1(67), 
                           mx3710(68), 
                           mx3210(69),
                           mx6710(70), 
                           mx6220(71),
                           mx1600a(74), 
                           mx1450(75),
                           ts720(76), 
                           so3395aTs(77), 
                           mx1608(78),
                           mx2210a(79), 
                           br401(80), 
                           mx6800a(81),
                           notApplicable(83), 
                           rp210(84),
                           mx6800b(85), 
                           mx1620(86), 
                           mx2240(87),
                           ps3m(88), 
                           lb2Wan(89), 
                           nio1600(90),
                           asy160(91), 
                           mx1640(92), 
                           br220(93),
                           rp211(94), 
                           br221(95), 
                           mx2210b(96),
                           mx1600b(97), 
                           mx1600c(98), 
                           mx800a(99),
                           mx1600d(100), 
                           tokenRing(101), 
                           mx800b(102),
                           br501(103), 
                           br350(105), 
                           br350ExpansionSlot(107),
                           n3000(108), 
                           br402(109), 
                           sw610(110), 
                           sw610S(111), 
                           br501s(112),
                           br501c(113), 
                           br501sc(114),
                           routeRunnerIsdnSt(115), 
                           routeRunner(116),
                           mx1608a(117),  
                           routerRunnerIsdnU(118),
                           mx1608b(119),  
                           mx1604(120),  
                           n3000Ias(123),
                           irMgr0Rdc(124), 
                           ir9040(125),
                           ir7040(126),
                           irMgr0(127),
                           irM800(128),
                           irM700(129),
                           ir8020(130),
                           ir8040(131),
                           ir7004(132),
                           ir7008(133),
                           ir8004(134),
                           ir8008(135),
                           irM900(136),
                           irMGR0AC(137),                       
                           irMGR0AC-IN(138),                       
                           ir9004(139),                       
                           ir9008(140),                       
                           n3000SP(230) 
                         }

            -- This data type is used throughout the iTouch private MIB
            -- to indicate the type of chassis hardware.

            ChassisType ::= 
                 INTEGER { other(1), mx45xx(2), net9000(3), net9000SWITCH(4) }

            -- This data type is used throughout the iTouch private MIB
            -- to indicate the type of I/O hardware.

            IOType ::=
                 INTEGER { 
                           io616(16),
                           dualE175(32), 
                           dualT1(33), 
                           bri8(34), 
                           io351d(35),
                           io352d(36),
                           dualE1120(37), 
                           singleT1(38), 
                           singleE175(39),
                           singleE1120(40),
                           io625(128),
                           io626(129),
                           io601(144), 
                           io602(145), 
                           io603(146),
                           io601A(147), 
                           io602A(148), 
                           io603A(149),
                           io604(150), 
                           io621(155),  
                           io622(156),
                           io623(157),
                           io624(158), 
                           io301x12(160), 
                           io521(174),
                           io522(175), 
                           io512x3(176), 
                           io511x3(177),
                           io520(178),
                           io514(179), 
                           io513(180), 
                           io470x4(182), 
                           io469x2(183),
                           io467x4(184), 
                           io467x2(185), 
                           io468x4(186),
                           io468x2(187), 
                           io466x4(188), 
                           io465x2(189),
                           io464x4(190), 
                           io463x2(191), 
                           io201(192), 
                           io202(193), 
                           io204(194), 
                           io203(195), 
                           io251(196), 
                           io231(197), 
                           io254(198),
                           io206(199), 
                           io253(200), 
                           io256(201), 
                           io201a(202), 
                           io202a(203), 
                           io203a(204), 
                           ioRepeater(207),
                           io205x12(209),
                           io205(210), 
                           io255(214), 
                           io722(224),
                           io721(225), 
                           io411(226), 
                           io724(227),
                           io725(231),
                           io723(232), 
                           io462(233), 
                           io412(234),
                           ioTS16a(235),  
                           ioTS16b(236),  
                           io461(237), 
                           io101(238), 
                           io119(239) 
                         }


            -- Agent Object Identifiers

            -- A iTouch agent identifer has the following fields:
            --
            --     iTouch.agent.software.variant.version
            --
            -- Where:
            --
            --     iTouch.agent   is an ordinary OID prefix.
            --                    Note that iTouch's original form for
            --                    such OID's used the value 1 for agent
            --                    and had no variant or version.  Later
            --                    forms included variant and version in
            --                    an inconsistent manner.
            --
            --     software       a value of the iTouch SoftwareType
            --                    textual convention.
            --
            --     variant        a variant within a software type,
            --                    typically hardware dependent.  If the
            --                    software has no variants, it uses the
            --                    value 1.
            --
            --     version        a version number within the variant,
            --                    increased by one each time that
            --                    variant's agent changes in a way that
            --                    is significant to its MIB
            --                    capabilities description

            -- Terminal Servers

            terminalServer   OBJECT IDENTIFIER ::= { agent 1 }

            --     MAXserver variants, 1M memory
            tsMxCard1M       OBJECT IDENTIFIER ::= { terminalServer 1 }
            tsMxBox1M        OBJECT IDENTIFIER ::= { terminalServer 2 }

            --     MAXserver variants, 1M memory
            tsMxCard         OBJECT IDENTIFIER ::= { terminalServer 3 }
            tsMxBox          OBJECT IDENTIFIER ::= { terminalServer 4 }

            --     Network 9000 variant
            tsN9             OBJECT IDENTIFIER ::= { terminalServer 5 }

            --     Printer controller variant
            tsPrint          OBJECT IDENTIFIER ::= { terminalServer 6 }

            --     X.25 Gateway variant
            tsX25            OBJECT IDENTIFIER ::= { terminalServer 7 }

            --  InReach and Environmental Manager variants. These models
            --  use their hardwareType as the agent variant.
            em1608           OBJECT IDENTIFIER ::= { terminalServer 29 }
            ir7520           OBJECT IDENTIFIER ::= { terminalServer 30 }
            ir9020           OBJECT IDENTIFIER ::= { terminalServer 31 }
            ir7020           OBJECT IDENTIFIER ::= { terminalServer 32 }
            irMgr0Rdc        OBJECT IDENTIFIER ::= { terminalServer 124 }
            ir9040           OBJECT IDENTIFIER ::= { terminalServer 125 }
            ir7040           OBJECT IDENTIFIER ::= { terminalServer 126 }
            irMgr0           OBJECT IDENTIFIER ::= { terminalServer 127 }
            irM800           OBJECT IDENTIFIER ::= { terminalServer 128 }
            irM700           OBJECT IDENTIFIER ::= { terminalServer 129 }
            ir8020           OBJECT IDENTIFIER ::= { terminalServer 130 }
            ir8040           OBJECT IDENTIFIER ::= { terminalServer 131 }
            ir7004           OBJECT IDENTIFIER ::= { terminalServer 132 }
            ir7008           OBJECT IDENTIFIER ::= { terminalServer 133 }
            ir8004           OBJECT IDENTIFIER ::= { terminalServer 134 }
            ir8008           OBJECT IDENTIFIER ::= { terminalServer 135 }
            irM900           OBJECT IDENTIFIER ::= { terminalServer 136 }
            irMGR0AC         OBJECT IDENTIFIER ::= { terminalServer 137 }
            irMGR0AC-IN      OBJECT IDENTIFIER ::= { terminalServer 138 }
            ir9004           OBJECT IDENTIFIER ::= { terminalServer 139 }
            ir9008           OBJECT IDENTIFIER ::= { terminalServer 140 }

            -- Bridges

            bridge                 OBJECT IDENTIFIER ::= { agent 3 }

            -- Repeaters

            repeater               OBJECT IDENTIFIER ::= { agent 4 }

            --     MAXserver variant
            rpMx                   OBJECT IDENTIFIER ::= { repeater 1 }

            --     Network 9000 variant
            rpN9                   OBJECT IDENTIFIER ::= { repeater 2 }

            -- Bridge/Routers

            bridgeRouter           OBJECT IDENTIFIER ::= { agent 5 }

            --     MAXserver variant
            bridgeRouterMx         OBJECT IDENTIFIER ::= { bridgeRouter 1 }

            --     Network 9000 variant
            bridgeRouterN9         OBJECT IDENTIFIER ::= { bridgeRouter 2 }

            -- Network 3000 variant
            bridgeRouterN3         OBJECT IDENTIFIER ::=  { bridgeRouter 3 }

            -- Network 3000 RouteRunner variant
            bridgeRouterN2         OBJECT IDENTIFIER ::=  { bridgeRouter 4 }

            -- EdgeBlaster variant
            bridgeRouterEB         OBJECT IDENTIFIER ::=  { bridgeRouter 5 }

            -- Bridge/Router/Repeaters

            bridgeRouterRepeater   OBJECT IDENTIFIER ::= { agent 7 }

            -- Switches

            switch                 OBJECT IDENTIFIER ::= { agent 8 }

            -- OEM Devices

            oem                    OBJECT IDENTIFIER ::= { agent 9 }

            --     NetVantage variant
            netVantage             OBJECT IDENTIFIER ::= { oem 1 }
            --     NetVantage product variants
            nv8516TT               OBJECT IDENTIFIER ::= { netVantage 1 }
            nv8516FF               OBJECT IDENTIFIER ::= { netVantage 2 }

            -- NBase Devices

            nbase                    OBJECT IDENTIFIER ::= { agent 10 }
            nbaseSwitch              OBJECT IDENTIFIER ::= { nbase 1 }
            nbaseSwitchN9            OBJECT IDENTIFIER ::= { nbaseSwitch 1 }









--
-- FILE: /users/sse/mibs/src/rfc/rfc1212.smi
--

-- changes to rfc1212 (Concise MIB OBJECT-TYPE definition):
--      Removed IMPORTS.
--      Commented out OBJECT-TYPE macro definition and replaced
--        with SMIC directive to enable it.




    -- Make builtin items known
--    SMI OBJECT-TYPE


        --  OBJECT-TYPE MACRO ::=
        --  BEGIN
        --      TYPE NOTATION ::=
                                          -- must conform to
                                          -- RFC1155's ObjectSyntax
        --                        "SYNTAX" type(ObjectSyntax)
        --                        "ACCESS" Access
        --                        "STATUS" Status
        --                        DescrPart
        --                        ReferPart
        --                        IndexPart
        --                        DefValPart
        --      VALUE NOTATION ::= value (VALUE ObjectName)
        --
        --      Access ::= "read-only"
        --                      | "read-write"
        --                      | "write-only"
        --                      | "not-accessible"
        --      Status ::= "mandatory"
        --                      | "optional"
        --                      | "obsolete"
        --                      | "deprecated"
        --
        --      DescrPart ::=
        --                 "DESCRIPTION" value (description DisplayString)
        --                      | empty
        --
        --      ReferPart ::=
        --                 "REFERENCE" value (reference DisplayString)
        --                      | empty
        --
        --      IndexPart ::=
        --                 "INDEX" "{" IndexTypes "}"
        --                      | empty
        --      IndexTypes ::=
        --                 IndexType | IndexTypes "," IndexType
        --      IndexType ::=
                                  -- if indexobject, use the SYNTAX
                                  -- value of the correspondent
                                  -- OBJECT-TYPE invocation
        --                 value (indexobject ObjectName)
                                  -- otherwise use named SMI type
                                  -- must conform to IndexSyntax below
        --                      | type (indextype)
        --
        --      DefValPart ::=
        --                 "DEFVAL" "{" value (defvalue ObjectSyntax) "}"
        --                      | empty
        --  END
        --
        --  IndexSyntax ::=
        --      CHOICE {
        --          number
        --              INTEGER (0..MAX),
        --          string
        --              OCTET STRING,
        --          object
        --              OBJECT IDENTIFIER,
        --          address
        --              NetworkAddress,
        --          ipAddress
        --              IpAddress
        --      }

--
-- FILE: /users/sse/mibs/src/rfc/rfc1213.mib
--

-- Changes to rfc1213 (MIB-II):
--      No changes needed.




          --  This MIB module uses the extended OBJECT-TYPE macro as
          --  defined in [14];


          --  MIB-II (same prefix as MIB-I)

          mib-2      OBJECT IDENTIFIER ::= { mgmt 1 }

          -- textual conventions

          DisplayString ::=
              OCTET STRING
          -- This data type is used to model textual information taken
          -- from the NVT ASCII character set.  By convention, objects
          -- with this syntax are declared as having
          --
          --      SIZE (0..255)

          PhysAddress ::=
              OCTET STRING
          -- This data type is used to model media addresses.  For many
          -- types of media, this will be in a binary representation.
          -- For example, an ethernet address would be represented as
          -- a string of 6 octets.


          -- groups in MIB-II

          system       OBJECT IDENTIFIER ::= { mib-2 1 }

          interfaces   OBJECT IDENTIFIER ::= { mib-2 2 }

          at           OBJECT IDENTIFIER ::= { mib-2 3 }

          ip           OBJECT IDENTIFIER ::= { mib-2 4 }

          icmp         OBJECT IDENTIFIER ::= { mib-2 5 }

          tcp          OBJECT IDENTIFIER ::= { mib-2 6 }

          udp          OBJECT IDENTIFIER ::= { mib-2 7 }

          egp          OBJECT IDENTIFIER ::= { mib-2 8 }

          -- historical (some say hysterical)
          -- cmot      OBJECT IDENTIFIER ::= { mib-2 9 }

          transmission OBJECT IDENTIFIER ::= { mib-2 10 }

          snmp         OBJECT IDENTIFIER ::= { mib-2 11 }


          -- the System group

          -- Implementation of the System group is mandatory for all
          -- systems.  If an agent is not configured to have a value
          -- for any of these variables, a string of length 0 is
          -- returned.

          sysDescr OBJECT-TYPE
              SYNTAX  DisplayString (SIZE (0..255))
              ACCESS  read-only
              STATUS  mandatory
              DESCRIPTION
                      "A textual description of the entity.  This value
                      should include the full name and version
                      identification of the system's hardware type,
                      software operating-system, and networking
                      software.  It is mandatory that this only contain
                      printable ASCII characters."
              ::= { system 1 }

          sysObjectID OBJECT-TYPE
              SYNTAX  OBJECT IDENTIFIER
              ACCESS  read-only
              STATUS  mandatory
              DESCRIPTION
                      "The vendor's authoritative identification of the
                      network management subsystem contained in the
                      entity.  This value is allocated within the SMI
                      enterprises subtree (1.3.6.1.4.1) and provides an
                      easy and unambiguous means for determining `what
                      kind of box' is being managed.  For example, if
                      vendor `Flintstones, Inc.' was assigned the
                      subtree 1.3.6.1.4.1.4242, it could assign the
                      identifier 1.3.6.1.4.1.4242.1.1 to its `Fred
                      Router'."
              ::= { system 2 }

          sysUpTime OBJECT-TYPE
              SYNTAX  TimeTicks
              ACCESS  read-only
              STATUS  mandatory
              DESCRIPTION
                      "The time (in hundredths of a second) since the
                      network management portion of the system was last
                      re-initialized."
              ::= { system 3 }

          sysContact OBJECT-TYPE
              SYNTAX  DisplayString (SIZE (0..255))
              ACCESS  read-write
              STATUS  mandatory
              DESCRIPTION
                      "The textual identification of the contact person
                      for this managed node, together with information
                      on how to contact this person."
              ::= { system 4 }

          sysName OBJECT-TYPE
              SYNTAX  DisplayString (SIZE (0..255))
              ACCESS  read-write
              STATUS  mandatory
              DESCRIPTION
                      "An administratively-assigned name for this
                      managed node.  By convention, this is the node's
                      fully-qualified domain name."
              ::= { system 5 }

          sysLocation OBJECT-TYPE
              SYNTAX  DisplayString (SIZE (0..255))
              ACCESS  read-write
              STATUS  mandatory
              DESCRIPTION
                      "The physical location of this node (e.g.,
                      `telephone closet, 3rd floor')."
              ::= { system 6 }

          sysServices OBJECT-TYPE
              SYNTAX  INTEGER (0..127)
              ACCESS  read-only
              STATUS  mandatory
              DESCRIPTION
                      "A value which indicates the set of services that
                      this entity primarily offers.

                      The value is a sum.  This sum initially takes the
                      value zero, Then, for each layer, L, in the range
                      1 through 7, that this node performs transactions
                      for, 2 raised to (L - 1) is added to the sum.  For
                      example, a node which performs primarily routing
                      functions would have a value of 4 (2^(3-1)).  In
                      contrast, a node which is a host offering
                      application services would have a value of 72
                      (2^(4-1) + 2^(7-1)).  Note that in the context of
                      the Internet suite of protocols, values should be
                      calculated accordingly:

                           layer  functionality
                               1  physical (e.g., repeaters)
                               2  datalink/subnetwork (e.g., bridges)
                               3  internet (e.g., IP gateways)
                               4  end-to-end  (e.g., IP hosts)
                               7  applications (e.g., mail relays)

                      For systems including OSI protocols, layers 5 and
                      6 may also be counted."
              ::= { system 7 }


          -- the Interfaces group

          -- Implementation of the Interfaces group is mandatory for
          -- all systems.

          ifNumber OBJECT-TYPE
              SYNTAX  INTEGER
              ACCESS  read-only
              STATUS  mandatory
              DESCRIPTION
                      "The number of network interfaces (regardless of
                      their current state) present on this system."
              ::= { interfaces 1 }


          -- the Interfaces table

          -- The Interfaces table contains information on the entity's
          -- interfaces.  Each interface is thought of as being
          -- attached to a `subnetwork'.  Note that this term should
          -- not be confused with `subnet' which refers to an
          -- addressing partitioning scheme used in the Internet suite
          -- of protocols.

          ifTable OBJECT-TYPE
              SYNTAX  SEQUENCE OF IfEntry
              ACCESS  not-accessible
              STATUS  mandatory
              DESCRIPTION
                      "A list of interface entries.  The number of
                      entries is given by the value of ifNumber."
              ::= { interfaces 2 }

          ifEntry OBJECT-TYPE
              SYNTAX  IfEntry
              ACCESS  not-accessible
              STATUS  mandatory
              DESCRIPTION
                      "An interface entry containing objects at the
                      subnetwork layer and below for a particular
                      interface."
              INDEX   { ifIndex }
              ::= { ifTable 1 }

          IfEntry ::=
              SEQUENCE {
                  ifIndex
                      INTEGER,
                  ifDescr
                      DisplayString,
                  ifType
                      INTEGER,
                  ifMtu
                      INTEGER,
                  ifSpeed
                      Gauge,
                  ifPhysAddress
                      PhysAddress,
                  ifAdminStatus
                      INTEGER,
                  ifOperStatus
                      INTEGER,
                  ifLastChange
                      TimeTicks,
                  ifInOctets
                      Counter,
                  ifInUcastPkts
                      Counter,
                  ifInNUcastPkts
                      Counter,
                  ifInDiscards
                      Counter,
                  ifInErrors
                      Counter,
                  ifInUnknownProtos
                      Counter,
                  ifOutOctets
                      Counter,
                  ifOutUcastPkts
                      Counter,
                  ifOutNUcastPkts
                      Counter,
                  ifOutDiscards
                      Counter,
                  ifOutErrors
                      Counter,
                  ifOutQLen
                      Gauge,
                  ifSpecific
                      OBJECT IDENTIFIER
              }

          ifIndex OBJECT-TYPE
              SYNTAX  INTEGER
              ACCESS  read-only
              STATUS  mandatory
              DESCRIPTION
                      "A unique value for each interface.  Its value
                      ranges between 1 and the value of ifNumber.  The
                      value for each interface must remain constant at
                      least from one re-initialization of the entity's
                      network management system to the next re-
                      initialization."
              ::= { ifEntry 1 }

          ifDescr OBJECT-TYPE
              SYNTAX  DisplayString (SIZE (0..255))
              ACCESS  read-only
              STATUS  mandatory
              DESCRIPTION
                      "A textual string containing information about the
                      interface.  This string should include the name of
                      the manufacturer, the product name and the version
                      of the hardware interface."
              ::= { ifEntry 2 }

          ifType OBJECT-TYPE
              SYNTAX  INTEGER {
                          other(1),          -- none of the following
                          regular1822(2),
                          hdh1822(3),
                          ddn-x25(4),
                          rfc877-x25(5),
                          ethernet-csmacd(6),
                          iso88023-csmacd(7),
                          iso88024-tokenBus(8),
                          iso88025-tokenRing(9),
                          iso88026-man(10),
                          starLan(11),
                          proteon-10Mbit(12),
                          proteon-80Mbit(13),
                          hyperchannel(14),
                          fddi(15),
                          lapb(16),
                          sdlc(17),
                          ds1(18),           -- T-1
                          e1(19),            -- european equiv. of T-1
                          basicISDN(20),
                          primaryISDN(21),   -- proprietary serial
                          propPointToPointSerial(22),
                          ppp(23),
                          softwareLoopback(24),
                          eon(25),            -- CLNP over IP [11]
                          ethernet-3Mbit(26),
                          nsip(27),           -- XNS over IP
                          slip(28),           -- generic SLIP
                          ultra(29),          -- ULTRA technologies
                          ds3(30),            -- T-3
                          sip(31),            -- SMDS
                          frame-relay(32)
                      }
              ACCESS  read-only
              STATUS  mandatory
              DESCRIPTION
                      "The type of interface, distinguished according to
                      the physical/link protocol(s) immediately `below'
                      the network layer in the protocol stack."
              ::= { ifEntry 3 }

          ifMtu OBJECT-TYPE
              SYNTAX  INTEGER
              ACCESS  read-only
              STATUS  mandatory
              DESCRIPTION
                      "The size of the largest datagram which can be
                      sent/received on the interface, specified in
                      octets.  For interfaces that are used for
                      transmitting network datagrams, this is the size
                      of the largest network datagram that can be sent
                      on the interface."
              ::= { ifEntry 4 }

          ifSpeed OBJECT-TYPE
              SYNTAX  Gauge
              ACCESS  read-only
              STATUS  mandatory
              DESCRIPTION
                      "An estimate of the interface's current bandwidth
                      in bits per second.  For interfaces which do not
                      vary in bandwidth or for those where no accurate
                      estimation can be made, this object should contain
                      the nominal bandwidth."
              ::= { ifEntry 5 }

          ifPhysAddress OBJECT-TYPE
              SYNTAX  PhysAddress
              ACCESS  read-only
              STATUS  mandatory
              DESCRIPTION
                      "The interface's address at the protocol layer
                      immediately `below' the network layer in the
                      protocol stack.  For interfaces which do not have
                      such an address (e.g., a serial line), this object
                      should contain an octet string of zero length."
              ::= { ifEntry 6 }

          ifAdminStatus OBJECT-TYPE
              SYNTAX  INTEGER {
                          up(1),       -- ready to pass packets
                          down(2),
                          testing(3)   -- in some test mode
                      }
              ACCESS  read-write
              STATUS  mandatory
              DESCRIPTION
                      "The desired state of the interface.  The
                      testing(3) state indicates that no operational
                      packets can be passed."
              ::= { ifEntry 7 }

          ifOperStatus OBJECT-TYPE
              SYNTAX  INTEGER {
                          up(1),       -- ready to pass packets
                          down(2),
                          testing(3)   -- in some test mode
                      }
              ACCESS  read-only
              STATUS  mandatory
              DESCRIPTION
                      "The current operational state of the interface.
                      The testing(3) state indicates that no operational
                      packets can be passed."
              ::= { ifEntry 8 }

          ifLastChange OBJECT-TYPE
              SYNTAX  TimeTicks
              ACCESS  read-only
              STATUS  mandatory
              DESCRIPTION
                      "The value of sysUpTime at the time the interface
                      entered its current operational state.  If the
                      current state was entered prior to the last re-
                      initialization of the local network management
                      subsystem, then this object contains a zero
                      value."
              ::= { ifEntry 9 }

          ifInOctets OBJECT-TYPE
              SYNTAX  Counter
              ACCESS  read-only
              STATUS  mandatory
              DESCRIPTION
                      "The total number of octets received on the
                      interface, including framing characters."
              ::= { ifEntry 10 }

          ifInUcastPkts OBJECT-TYPE
              SYNTAX  Counter
              ACCESS  read-only
              STATUS  mandatory
              DESCRIPTION
                      "The number of subnetwork-unicast packets
                      delivered to a higher-layer protocol."
              ::= { ifEntry 11 }

          ifInNUcastPkts OBJECT-TYPE
              SYNTAX  Counter
              ACCESS  read-only
              STATUS  mandatory
              DESCRIPTION
                      "The number of non-unicast (i.e., subnetwork-
                      broadcast or subnetwork-multicast) packets
                      delivered to a higher-layer protocol."
              ::= { ifEntry 12 }

          ifInDiscards OBJECT-TYPE
              SYNTAX  Counter
              ACCESS  read-only
              STATUS  mandatory
              DESCRIPTION
                      "The number of inbound packets which were chosen
                      to be discarded even though no errors had been
                      detected to prevent their being deliverable to a
                      higher-layer protocol.  One possible reason for
                      discarding such a packet could be to free up
                      buffer space."
              ::= { ifEntry 13 }

          ifInErrors OBJECT-TYPE
              SYNTAX  Counter
              ACCESS  read-only
              STATUS  mandatory
              DESCRIPTION
                      "The number of inbound packets that contained
                      errors preventing them from being deliverable to a
                      higher-layer protocol."
              ::= { ifEntry 14 }
          ifInUnknownProtos OBJECT-TYPE
              SYNTAX  Counter
              ACCESS  read-only
              STATUS  mandatory
              DESCRIPTION
                      "The number of packets received via the interface
                      which were discarded because of an unknown or
                      unsupported protocol."
              ::= { ifEntry 15 }

          ifOutOctets OBJECT-TYPE
              SYNTAX  Counter
              ACCESS  read-only
              STATUS  mandatory
              DESCRIPTION
                      "The total number of octets transmitted out of the
                      interface, including framing characters."
              ::= { ifEntry 16 }

          ifOutUcastPkts OBJECT-TYPE
              SYNTAX  Counter
              ACCESS  read-only
              STATUS  mandatory
              DESCRIPTION
                      "The total number of packets that higher-level
                      protocols requested be transmitted to a
                      subnetwork-unicast address, including those that
                      were discarded or not sent."
              ::= { ifEntry 17 }

          ifOutNUcastPkts OBJECT-TYPE
              SYNTAX  Counter
              ACCESS  read-only
              STATUS  mandatory
              DESCRIPTION
                      "The total number of packets that higher-level
                      protocols requested be transmitted to a non-
                      unicast (i.e., a subnetwork-broadcast or
                      subnetwork-multicast) address, including those
                      that were discarded or not sent."
              ::= { ifEntry 18 }

          ifOutDiscards OBJECT-TYPE
              SYNTAX  Counter
              ACCESS  read-only
              STATUS  mandatory
              DESCRIPTION
                      "The number of outbound packets which were chosen
                      to be discarded even though no errors had been
                      detected to prevent their being transmitted.  One
                      possible reason for discarding such a packet could
                      be to free up buffer space."
              ::= { ifEntry 19 }

          ifOutErrors OBJECT-TYPE
              SYNTAX  Counter
              ACCESS  read-only
              STATUS  mandatory
              DESCRIPTION
                      "The number of outbound packets that could not be
                      transmitted because of errors."
              ::= { ifEntry 20 }

          ifOutQLen OBJECT-TYPE
              SYNTAX  Gauge
              ACCESS  read-only
              STATUS  mandatory
              DESCRIPTION
                      "The length of the output packet queue (in
                      packets)."
              ::= { ifEntry 21 }

          ifSpecific OBJECT-TYPE
              SYNTAX  OBJECT IDENTIFIER
              ACCESS  read-only
              STATUS  mandatory
              DESCRIPTION
                      "A reference to MIB definitions specific to the
                      particular media being used to realize the
                      interface.  For example, if the interface is
                      realized by an ethernet, then the value of this
                      object refers to a document defining objects
                      specific to ethernet.  If this information is not
                      present, its value should be set to the OBJECT
                      IDENTIFIER { 0 0 }, which is a syntatically valid
                      object identifier, and any conformant
                      implementation of ASN.1 and BER must be able to
                      generate and recognize this value."
              ::= { ifEntry 22 }


          -- the Address Translation group

          -- Implementation of the Address Translation group is
          -- mandatory for all systems.  Note however that this group
          -- is deprecated by MIB-II. That is, it is being included
          -- solely for compatibility with MIB-I nodes, and will most
          -- likely be excluded from MIB-III nodes.  From MIB-II and
          -- onwards, each network protocol group contains its own
          -- address translation tables.

          -- The Address Translation group contains one table which is
          -- the union across all interfaces of the translation tables
          -- for converting a NetworkAddress (e.g., an IP address) into
          -- a subnetwork-specific address.  For lack of a better term,
          -- this document refers to such a subnetwork-specific address
          -- as a `physical' address.

          -- Examples of such translation tables are: for broadcast
          -- media where ARP is in use, the translation table is
          -- equivalent to the ARP cache; or, on an X.25 network where
          -- non-algorithmic translation to X.121 addresses is
          -- required, the translation table contains the
          -- NetworkAddress to X.121 address equivalences.

          atTable OBJECT-TYPE
              SYNTAX  SEQUENCE OF AtEntry
              ACCESS  not-accessible
              STATUS  deprecated
              DESCRIPTION
                      "The Address Translation tables contain the
                      NetworkAddress to `physical' address equivalences.
                      Some interfaces do not use translation tables for
                      determining address equivalences (e.g., DDN-X.25
                      has an algorithmic method); if all interfaces are
                      of this type, then the Address Translation table
                      is empty, i.e., has zero entries."
              ::= { at 1 }

          atEntry OBJECT-TYPE
              SYNTAX  AtEntry
              ACCESS  not-accessible
              STATUS  deprecated
              DESCRIPTION
                      "Each entry contains one NetworkAddress to
                      `physical' address equivalence."
              INDEX   { atIfIndex,
                        atNetAddress }
              ::= { atTable 1 }

          AtEntry ::=
              SEQUENCE {
                  atIfIndex
                      INTEGER,
                  atPhysAddress
                      PhysAddress,
                  atNetAddress
                      NetworkAddress
              }

          atIfIndex OBJECT-TYPE
              SYNTAX  INTEGER
              ACCESS  read-write
              STATUS  deprecated
              DESCRIPTION
                      "The interface on which this entry's equivalence
                      is effective.  The interface identified by a
                      particular value of this index is the same
                      interface as identified by the same value of
                      ifIndex."
              ::= { atEntry 1 }

          atPhysAddress OBJECT-TYPE
              SYNTAX  PhysAddress
              ACCESS  read-write
              STATUS  deprecated
              DESCRIPTION
                      "The media-dependent `physical' address.

                      Setting this object to a null string (one of zero
                      length) has the effect of invaliding the
                      corresponding entry in the atTable object.  That
                      is, it effectively dissasociates the interface
                      identified with said entry from the mapping
                      identified with said entry.  It is an
                      implementation-specific matter as to whether the
                      agent removes an invalidated entry from the table.
                      Accordingly, management stations must be prepared
                      to receive tabular information from agents that
                      corresponds to entries not currently in use.
                      Proper interpretation of such entries requires
                      examination of the relevant atPhysAddress object."
              ::= { atEntry 2 }

          atNetAddress OBJECT-TYPE
              SYNTAX  NetworkAddress
              ACCESS  read-write
              STATUS  deprecated
              DESCRIPTION
                      "The NetworkAddress (e.g., the IP address)
                      corresponding to the media-dependent `physical'
                      address."
              ::= { atEntry 3 }


          -- the IP group

          -- Implementation of the IP group is mandatory for all
          -- systems.

          ipForwarding OBJECT-TYPE
              SYNTAX  INTEGER {
                          forwarding(1),    -- acting as a gateway
                          not-forwarding(2) -- NOT acting as a gateway
                      }
              ACCESS  read-write
              STATUS  mandatory
              DESCRIPTION
                      "The indication of whether this entity is acting
                      as an IP gateway in respect to the forwarding of
                      datagrams received by, but not addressed to, this
                      entity.  IP gateways forward datagrams.  IP hosts
                      do not (except those source-routed via the host).

                      Note that for some managed nodes, this object may
                      take on only a subset of the values possible.
                      Accordingly, it is appropriate for an agent to
                      return a `badValue' response if a management
                      station attempts to change this object to an
                      inappropriate value."
              ::= { ip 1 }

          ipDefaultTTL OBJECT-TYPE
              SYNTAX  INTEGER
              ACCESS  read-write
              STATUS  mandatory
              DESCRIPTION
                      "The default value inserted into the Time-To-Live
                      field of the IP header of datagrams originated at
                      this entity, whenever a TTL value is not supplied
                      by the transport layer protocol."
              ::= { ip 2 }

          ipInReceives OBJECT-TYPE
              SYNTAX  Counter
              ACCESS  read-only
              STATUS  mandatory
              DESCRIPTION
                      "The total number of input datagrams received from
                      interfaces, including those received in error."
              ::= { ip 3 }

          ipInHdrErrors OBJECT-TYPE
              SYNTAX  Counter
              ACCESS  read-only
              STATUS  mandatory
              DESCRIPTION
                      "The number of input datagrams discarded due to
                      errors in their IP headers, including bad
                      checksums, version number mismatch, other format
                      errors, time-to-live exceeded, errors discovered
                      in processing their IP options, etc."
              ::= { ip 4 }

          ipInAddrErrors OBJECT-TYPE
              SYNTAX  Counter
              ACCESS  read-only
              STATUS  mandatory
              DESCRIPTION
                      "The number of input datagrams discarded because
                      the IP address in their IP header's destination
                      field was not a valid address to be received at
                      this entity.  This count includes invalid
                      addresses (e.g., 0.0.0.0) and addresses of
                      unsupported Classes (e.g., Class E).  For entities
                      which are not IP Gateways and therefore do not
                      forward datagrams, this counter includes datagrams
                      discarded because the destination address was not
                      a local address."
              ::= { ip 5 }

          ipForwDatagrams OBJECT-TYPE
              SYNTAX  Counter
              ACCESS  read-only
              STATUS  mandatory
              DESCRIPTION
                      "The number of input datagrams for which this
                      entity was not their final IP destination, as a
                      result of which an attempt was made to find a
                      route to forward them to that final destination.
                      In entities which do not act as IP Gateways, this
                      counter will include only those packets which were
                      Source-Routed via this entity, and the Source-
                      Route option processing was successful."
              ::= { ip 6 }

          ipInUnknownProtos OBJECT-TYPE
              SYNTAX  Counter
              ACCESS  read-only
              STATUS  mandatory
              DESCRIPTION
                      "The number of locally-addressed datagrams
                      received successfully but discarded because of an
                      unknown or unsupported protocol."
              ::= { ip 7 }

          ipInDiscards OBJECT-TYPE
              SYNTAX  Counter
              ACCESS  read-only
              STATUS  mandatory
              DESCRIPTION
                      "The number of input IP datagrams for which no
                      problems were encountered to prevent their
                      continued processing, but which were discarded
                      (e.g., for lack of buffer space).  Note that this
                      counter does not include any datagrams discarded
                      while awaiting re-assembly."
              ::= { ip 8 }

          ipInDelivers OBJECT-TYPE
              SYNTAX  Counter
              ACCESS  read-only
              STATUS  mandatory
              DESCRIPTION
                      "The total number of input datagrams successfully
                      delivered to IP user-protocols (including ICMP)."
              ::= { ip 9 }

          ipOutRequests OBJECT-TYPE
              SYNTAX  Counter
              ACCESS  read-only
              STATUS  mandatory
              DESCRIPTION
                      "The total number of IP datagrams which local IP
                      user-protocols (including ICMP) supplied to IP in
                      requests for transmission.  Note that this counter
                      does not include any datagrams counted in
                      ipForwDatagrams."
              ::= { ip 10 }

          ipOutDiscards OBJECT-TYPE
              SYNTAX  Counter
              ACCESS  read-only
              STATUS  mandatory
              DESCRIPTION
                      "The number of output IP datagrams for which no
                      problem was encountered to prevent their
                      transmission to their destination, but which were
                      discarded (e.g., for lack of buffer space).  Note
                      that this counter would include datagrams counted
                      in ipForwDatagrams if any such packets met this
                      (discretionary) discard criterion."
              ::= { ip 11 }

          ipOutNoRoutes OBJECT-TYPE
              SYNTAX  Counter
              ACCESS  read-only
              STATUS  mandatory
              DESCRIPTION
                      "The number of IP datagrams discarded because no
                      route could be found to transmit them to their
                      destination.  Note that this counter includes any
                      packets counted in ipForwDatagrams which meet this
                      `no-route' criterion.  Note that this includes any
                      datagarms which a host cannot route because all of
                      its default gateways are down."
              ::= { ip 12 }

          ipReasmTimeout OBJECT-TYPE
              SYNTAX  INTEGER
              ACCESS  read-only
              STATUS  mandatory
              DESCRIPTION
                      "The maximum number of seconds which received
                      fragments are held while they are awaiting
                      reassembly at this entity."
              ::= { ip 13 }

          ipReasmReqds OBJECT-TYPE
              SYNTAX  Counter
              ACCESS  read-only
              STATUS  mandatory
              DESCRIPTION
                      "The number of IP fragments received which needed
                      to be reassembled at this entity."
              ::= { ip 14 }

          ipReasmOKs OBJECT-TYPE
              SYNTAX  Counter
              ACCESS  read-only
              STATUS  mandatory
              DESCRIPTION
                      "The number of IP datagrams successfully re-
                      assembled."
              ::= { ip 15 }

          ipReasmFails OBJECT-TYPE
              SYNTAX  Counter
              ACCESS  read-only
              STATUS  mandatory
              DESCRIPTION
                      "The number of failures detected by the IP re-
                      assembly algorithm (for whatever reason: timed
                      out, errors, etc).  Note that this is not
                      necessarily a count of discarded IP fragments
                      since some algorithms (notably the algorithm in
                      RFC 815) can lose track of the number of fragments
                      by combining them as they are received."
              ::= { ip 16 }

          ipFragOKs OBJECT-TYPE
              SYNTAX  Counter
              ACCESS  read-only
              STATUS  mandatory
              DESCRIPTION
                      "The number of IP datagrams that have been
                      successfully fragmented at this entity."
              ::= { ip 17 }

          ipFragFails OBJECT-TYPE
              SYNTAX  Counter
              ACCESS  read-only
              STATUS  mandatory
              DESCRIPTION
                      "The number of IP datagrams that have been
                      discarded because they needed to be fragmented at
                      this entity but could not be, e.g., because their
                      Don't Fragment flag was set."
              ::= { ip 18 }

          ipFragCreates OBJECT-TYPE
              SYNTAX  Counter
              ACCESS  read-only
              STATUS  mandatory
              DESCRIPTION
                      "The number of IP datagram fragments that have
                      been generated as a result of fragmentation at
                      this entity."
              ::= { ip 19 }

          -- the IP address table

          -- The IP address table contains this entity's IP addressing
          -- information.

          ipAddrTable OBJECT-TYPE
              SYNTAX  SEQUENCE OF IpAddrEntry
              ACCESS  not-accessible
              STATUS  mandatory
              DESCRIPTION
                      "The table of addressing information relevant to
                      this entity's IP addresses."
              ::= { ip 20 }

          ipAddrEntry OBJECT-TYPE
              SYNTAX  IpAddrEntry
              ACCESS  not-accessible
              STATUS  mandatory
              DESCRIPTION
                      "The addressing information for one of this
                      entity's IP addresses."
              INDEX   { ipAdEntAddr }
              ::= { ipAddrTable 1 }

          IpAddrEntry ::=
              SEQUENCE {
                  ipAdEntAddr
                      IpAddress,
                  ipAdEntIfIndex
                      INTEGER,
                  ipAdEntNetMask
                      IpAddress,
                  ipAdEntBcastAddr
                      INTEGER,
                  ipAdEntReasmMaxSize
                      INTEGER (0..65535)
              }

          ipAdEntAddr OBJECT-TYPE
              SYNTAX  IpAddress
              ACCESS  read-only
              STATUS  mandatory
              DESCRIPTION
                      "The IP address to which this entry's addressing
                      information pertains."
              ::= { ipAddrEntry 1 }

          ipAdEntIfIndex OBJECT-TYPE
              SYNTAX  INTEGER
              ACCESS  read-only
              STATUS  mandatory
              DESCRIPTION
                      "The index value which uniquely identifies the
                      interface to which this entry is applicable.  The
                      interface identified by a particular value of this
                      index is the same interface as identified by the
                      same value of ifIndex."
              ::= { ipAddrEntry 2 }

          ipAdEntNetMask OBJECT-TYPE
              SYNTAX  IpAddress
              ACCESS  read-only
              STATUS  mandatory
              DESCRIPTION
                      "The subnet mask associated with the IP address of
                      this entry.  The value of the mask is an IP
                      address with all the network bits set to 1 and all
                      the hosts bits set to 0."
              ::= { ipAddrEntry 3 }

          ipAdEntBcastAddr OBJECT-TYPE
              SYNTAX  INTEGER
              ACCESS  read-only
              STATUS  mandatory
              DESCRIPTION
                      "The value of the least-significant bit in the IP
                      broadcast address used for sending datagrams on
                      the (logical) interface associated with the IP
                      address of this entry.  For example, when the
                      Internet standard all-ones broadcast address is
                      used, the value will be 1.  This value applies to
                      both the subnet and network broadcasts addresses
                      used by the entity on this (logical) interface."
              ::= { ipAddrEntry 4 }

          ipAdEntReasmMaxSize OBJECT-TYPE
              SYNTAX  INTEGER (0..65535)
              ACCESS  read-only
              STATUS  mandatory
              DESCRIPTION
                      "The size of the largest IP datagram which this
                      entity can re-assemble from incoming IP fragmented
                      datagrams received on this interface."
              ::= { ipAddrEntry 5 }

          -- the IP routing table

          -- The IP routing table contains an entry for each route
          -- presently known to this entity.

          ipRouteTable OBJECT-TYPE
              SYNTAX  SEQUENCE OF IpRouteEntry
              ACCESS  not-accessible
              STATUS  mandatory
              DESCRIPTION
                      "This entity's IP Routing table."
              ::= { ip 21 }

          ipRouteEntry OBJECT-TYPE
              SYNTAX  IpRouteEntry
              ACCESS  not-accessible
              STATUS  mandatory
              DESCRIPTION
                      "A route to a particular destination."
              INDEX   { ipRouteDest }
              ::= { ipRouteTable 1 }

          IpRouteEntry ::=
              SEQUENCE {
                  ipRouteDest
                      IpAddress,
                  ipRouteIfIndex
                      INTEGER,
                  ipRouteMetric1
                      INTEGER,
                  ipRouteMetric2
                      INTEGER,
                  ipRouteMetric3
                      INTEGER,
                  ipRouteMetric4
                      INTEGER,
                  ipRouteNextHop
                      IpAddress,
                  ipRouteType
                      INTEGER,
                  ipRouteProto
                      INTEGER,
                  ipRouteAge
                      INTEGER,
                  ipRouteMask
                      IpAddress,
                  ipRouteMetric5
                      INTEGER,
                  ipRouteInfo
                      OBJECT IDENTIFIER
              }

          ipRouteDest OBJECT-TYPE
              SYNTAX  IpAddress
              ACCESS  read-write
              STATUS  mandatory
              DESCRIPTION
                      "The destination IP address of this route.  An
                      entry with a value of 0.0.0.0 is considered a
                      default route.  Multiple routes to a single
                      destination can appear in the table, but access to
                      such multiple entries is dependent on the table-
                      access mechanisms defined by the network
                      management protocol in use."
              ::= { ipRouteEntry 1 }

          ipRouteIfIndex OBJECT-TYPE
              SYNTAX  INTEGER
              ACCESS  read-write
              STATUS  mandatory
              DESCRIPTION
                      "The index value which uniquely identifies the
                      local interface through which the next hop of this
                      route should be reached.  The interface identified
                      by a particular value of this index is the same
                      interface as identified by the same value of
                      ifIndex."
              ::= { ipRouteEntry 2 }

          ipRouteMetric1 OBJECT-TYPE
              SYNTAX  INTEGER
              ACCESS  read-write
              STATUS  mandatory
              DESCRIPTION
                      "The primary routing metric for this route.  The
                      semantics of this metric are determined by the
                      routing-protocol specified in the route's
                      ipRouteProto value.  If this metric is not used,
                      its value should be set to -1."
              ::= { ipRouteEntry 3 }

          ipRouteMetric2 OBJECT-TYPE
              SYNTAX  INTEGER
              ACCESS  read-write
              STATUS  mandatory
              DESCRIPTION
                      "An alternate routing metric for this route.  The
                      semantics of this metric are determined by the
                      routing-protocol specified in the route's
                      ipRouteProto value.  If this metric is not used,
                      its value should be set to -1."
              ::= { ipRouteEntry 4 }

          ipRouteMetric3 OBJECT-TYPE
              SYNTAX  INTEGER
              ACCESS  read-write
              STATUS  mandatory
              DESCRIPTION
                      "An alternate routing metric for this route.  The
                      semantics of this metric are determined by the
                      routing-protocol specified in the route's
                      ipRouteProto value.  If this metric is not used,
                      its value should be set to -1."
              ::= { ipRouteEntry 5 }

          ipRouteMetric4 OBJECT-TYPE
              SYNTAX  INTEGER
              ACCESS  read-write
              STATUS  mandatory
              DESCRIPTION
                      "An alternate routing metric for this route.  The
                      semantics of this metric are determined by the
                      routing-protocol specified in the route's
                      ipRouteProto value.  If this metric is not used,
                      its value should be set to -1."
              ::= { ipRouteEntry 6 }

          ipRouteNextHop OBJECT-TYPE
              SYNTAX  IpAddress
              ACCESS  read-write
              STATUS  mandatory
              DESCRIPTION
                      "The IP address of the next hop of this route.
                      (In the case of a route bound to an interface
                      which is realized via a broadcast media, the value
                      of this field is the agent's IP address on that
                      interface.)"
              ::= { ipRouteEntry 7 }

          ipRouteType OBJECT-TYPE
              SYNTAX  INTEGER {
                          other(1),        -- none of the following

                          invalid(2),      -- an invalidated route
                                           -- route to directly

                          direct(3),       -- connected (sub-)network

                                           -- route to a non-local
                          indirect(4)      -- host/network/sub-network
                      }
              ACCESS  read-write
              STATUS  mandatory
              DESCRIPTION
                      "The type of route.  Note that the values
                      direct(3) and indirect(4) refer to the notion of
                      direct and indirect routing in the IP
                      architecture.

                      Setting this object to the value invalid(2) has
                      the effect of invalidating the corresponding entry
                      in the ipRouteTable object.  That is, it
                      effectively dissasociates the destination
                      identified with said entry from the route
                      identified with said entry.  It is an
                      implementation-specific matter as to whether the
                      agent removes an invalidated entry from the table.
                      Accordingly, management stations must be prepared
                      to receive tabular information from agents that
                      corresponds to entries not currently in use.
                      Proper interpretation of such entries requires
                      examination of the relevant ipRouteType object."
              ::= { ipRouteEntry 8 }

          ipRouteProto OBJECT-TYPE
              SYNTAX  INTEGER {
                          other(1),       -- none of the following

                                          -- non-protocol information,
                                          -- e.g., manually configured
                          local(2),       -- entries

                                          -- set via a network
                          netmgmt(3),     -- management protocol

                                          -- obtained via ICMP,
                          icmp(4),        -- e.g., Redirect

                                          -- the remaining values are
                                          -- all gateway routing
                                          -- protocols
                          egp(5),
                          ggp(6),
                          hello(7),
                          rip(8),
                          is-is(9),
                          es-is(10),
                          ciscoIgrp(11),
                          bbnSpfIgp(12),
                          ospf(13),
                          bgp(14)
                      }
              ACCESS  read-only
              STATUS  mandatory
              DESCRIPTION
                      "The routing mechanism via which this route was
                      learned.  Inclusion of values for gateway routing
                      protocols is not intended to imply that hosts
                      should support those protocols."
              ::= { ipRouteEntry 9 }

          ipRouteAge OBJECT-TYPE
              SYNTAX  INTEGER
              ACCESS  read-write
              STATUS  mandatory
              DESCRIPTION
                      "The number of seconds since this route was last
                      updated or otherwise determined to be correct.
                      Note that no semantics of `too old' can be implied
                      except through knowledge of the routing protocol
                      by which the route was learned."
              ::= { ipRouteEntry 10 }

          ipRouteMask OBJECT-TYPE
              SYNTAX  IpAddress
              ACCESS  read-write
              STATUS  mandatory
              DESCRIPTION
                      "Indicate the mask to be logical-ANDed with the
                      destination address before being compared to the
                      value in the ipRouteDest field.  For those systems
                      that do not support arbitrary subnet masks, an
                      agent constructs the value of the ipRouteMask by
                      determining whether the value of the correspondent
                      ipRouteDest field belong to a class-A, B, or C
                      network, and then using one of:

                           mask           network
                           255.0.0.0      class-A
                           255.255.0.0    class-B
                           255.255.255.0  class-C

                      If the value of the ipRouteDest is 0.0.0.0 (a
                      default route), then the mask value is also
                      0.0.0.0.  It should be noted that all IP routing
                      subsystems implicitly use this mechanism."
              ::= { ipRouteEntry 11 }

          ipRouteMetric5 OBJECT-TYPE
              SYNTAX  INTEGER
              ACCESS  read-write
              STATUS  mandatory
              DESCRIPTION
                      "An alternate routing metric for this route.  The
                      semantics of this metric are determined by the
                      routing-protocol specified in the route's
                      ipRouteProto value.  If this metric is not used,
                      its value should be set to -1."
              ::= { ipRouteEntry 12 }

          ipRouteInfo OBJECT-TYPE
              SYNTAX  OBJECT IDENTIFIER
              ACCESS  read-only
              STATUS  mandatory
              DESCRIPTION
                      "A reference to MIB definitions specific to the
                      particular routing protocol which is responsible
                      for this route, as determined by the value
                      specified in the route's ipRouteProto value.  If
                      this information is not present, its value should
                      be set to the OBJECT IDENTIFIER { 0 0 }, which is
                      a syntatically valid object identifier, and any
                      conformant implementation of ASN.1 and BER must be
                      able to generate and recognize this value."
              ::= { ipRouteEntry 13 }


          -- the IP Address Translation table

          -- The IP address translation table contain the IpAddress to
          -- `physical' address equivalences.  Some interfaces do not
          -- use translation tables for determining address
          -- equivalences (e.g., DDN-X.25 has an algorithmic method);
          -- if all interfaces are of this type, then the Address
          -- Translation table is empty, i.e., has zero entries.

          ipNetToMediaTable OBJECT-TYPE
              SYNTAX  SEQUENCE OF IpNetToMediaEntry
              ACCESS  not-accessible
              STATUS  mandatory
              DESCRIPTION
                      "The IP Address Translation table used for mapping
                      from IP addresses to physical addresses."
              ::= { ip 22 }

          ipNetToMediaEntry OBJECT-TYPE
              SYNTAX  IpNetToMediaEntry
              ACCESS  not-accessible
              STATUS  mandatory
              DESCRIPTION
                      "Each entry contains one IpAddress to `physical'
                      address equivalence."
              INDEX   { ipNetToMediaIfIndex,
                        ipNetToMediaNetAddress }
              ::= { ipNetToMediaTable 1 }

          IpNetToMediaEntry ::=
              SEQUENCE {
                  ipNetToMediaIfIndex
                      INTEGER,
                  ipNetToMediaPhysAddress
                      PhysAddress,
                  ipNetToMediaNetAddress
                      IpAddress,
                  ipNetToMediaType
                      INTEGER
              }

          ipNetToMediaIfIndex OBJECT-TYPE
              SYNTAX  INTEGER
              ACCESS  read-write
              STATUS  mandatory
              DESCRIPTION
                      "The interface on which this entry's equivalence
                      is effective.  The interface identified by a
                      particular value of this index is the same
                      interface as identified by the same value of
                      ifIndex."
              ::= { ipNetToMediaEntry 1 }

          ipNetToMediaPhysAddress OBJECT-TYPE
              SYNTAX  PhysAddress
              ACCESS  read-write
              STATUS  mandatory
              DESCRIPTION
                      "The media-dependent `physical' address."
              ::= { ipNetToMediaEntry 2 }

          ipNetToMediaNetAddress OBJECT-TYPE
              SYNTAX  IpAddress
              ACCESS  read-only
              STATUS  mandatory
              DESCRIPTION
                      "The IpAddress corresponding to the media-
                      dependent `physical' address."
              ::= { ipNetToMediaEntry 3 }

          ipNetToMediaType OBJECT-TYPE
              SYNTAX  INTEGER {
                          other(1),        -- none of the following
                          invalid(2),      -- an invalidated mapping
                          dynamic(3),
                          static(4)
                      }
              ACCESS  read-write
              STATUS  mandatory
              DESCRIPTION
                      "The type of mapping.

                      Setting this object to the value invalid(2) has
                      the effect of invalidating the corresponding entry
                      in the ipNetToMediaTable.  That is, it effectively
                      dissasociates the interface identified with said
                      entry from the mapping identified with said entry.
                      It is an implementation-specific matter as to
                      whether the agent removes an invalidated entry
                      from the table.  Accordingly, management stations
                      must be prepared to receive tabular information
                      from agents that corresponds to entries not
                      currently in use.  Proper interpretation of such
                      entries requires examination of the relevant
                      ipNetToMediaType object."
              ::= { ipNetToMediaEntry 4 }


          -- additional IP objects

          ipRoutingDiscards OBJECT-TYPE
              SYNTAX  Counter
              ACCESS  read-only
              STATUS  mandatory
              DESCRIPTION
                      "The number of routing entries which were chosen
                      to be discarded even though they are valid.  One
                      possible reason for discarding such an entry could
                      be to free-up buffer space for other routing
                      entries."
              ::= { ip 23 }


          -- the ICMP group

          -- Implementation of the ICMP group is mandatory for all
          -- systems.

          icmpInMsgs OBJECT-TYPE
              SYNTAX  Counter
              ACCESS  read-only
              STATUS  mandatory
              DESCRIPTION
                      "The total number of ICMP messages which the
                      entity received.  Note that this counter includes
                      all those counted by icmpInErrors."
              ::= { icmp 1 }

          icmpInErrors OBJECT-TYPE
              SYNTAX  Counter
              ACCESS  read-only
              STATUS  mandatory
              DESCRIPTION
                      "The number of ICMP messages which the entity
                      received but determined as having ICMP-specific
                      errors (bad ICMP checksums, bad length, etc.)."
              ::= { icmp 2 }

          icmpInDestUnreachs OBJECT-TYPE
              SYNTAX  Counter
              ACCESS  read-only
              STATUS  mandatory
              DESCRIPTION
                      "The number of ICMP Destination Unreachable
                      messages received."
              ::= { icmp 3 }

          icmpInTimeExcds OBJECT-TYPE
              SYNTAX  Counter
              ACCESS  read-only
              STATUS  mandatory
              DESCRIPTION
                      "The number of ICMP Time Exceeded messages
                      received."
              ::= { icmp 4 }

          icmpInParmProbs OBJECT-TYPE
              SYNTAX  Counter
              ACCESS  read-only
              STATUS  mandatory
              DESCRIPTION
                      "The number of ICMP Parameter Problem messages
                      received."
              ::= { icmp 5 }

          icmpInSrcQuenchs OBJECT-TYPE
              SYNTAX  Counter
              ACCESS  read-only
              STATUS  mandatory
              DESCRIPTION
                      "The number of ICMP Source Quench messages
                      received."
              ::= { icmp 6 }

          icmpInRedirects OBJECT-TYPE
              SYNTAX  Counter
              ACCESS  read-only
              STATUS  mandatory
              DESCRIPTION
                      "The number of ICMP Redirect messages received."
              ::= { icmp 7 }

          icmpInEchos OBJECT-TYPE
              SYNTAX  Counter
              ACCESS  read-only
              STATUS  mandatory
              DESCRIPTION
                      "The number of ICMP Echo (request) messages
                      received."
              ::= { icmp 8 }

          icmpInEchoReps OBJECT-TYPE
              SYNTAX  Counter
              ACCESS  read-only
              STATUS  mandatory
              DESCRIPTION
                      "The number of ICMP Echo Reply messages received."
              ::= { icmp 9 }

          icmpInTimestamps OBJECT-TYPE
              SYNTAX  Counter
              ACCESS  read-only
              STATUS  mandatory
              DESCRIPTION
                      "The number of ICMP Timestamp (request) messages
                      received."
              ::= { icmp 10 }

          icmpInTimestampReps OBJECT-TYPE
              SYNTAX  Counter
              ACCESS  read-only
              STATUS  mandatory
              DESCRIPTION
                      "The number of ICMP Timestamp Reply messages
                      received."
              ::= { icmp 11 }

          icmpInAddrMasks OBJECT-TYPE
              SYNTAX  Counter
              ACCESS  read-only
              STATUS  mandatory
              DESCRIPTION
                      "The number of ICMP Address Mask Request messages
                      received."
              ::= { icmp 12 }

          icmpInAddrMaskReps OBJECT-TYPE
              SYNTAX  Counter
              ACCESS  read-only
              STATUS  mandatory
              DESCRIPTION
                      "The number of ICMP Address Mask Reply messages
                      received."
              ::= { icmp 13 }

          icmpOutMsgs OBJECT-TYPE
              SYNTAX  Counter
              ACCESS  read-only
              STATUS  mandatory
              DESCRIPTION
                      "The total number of ICMP messages which this
                      entity attempted to send.  Note that this counter
                      includes all those counted by icmpOutErrors."
              ::= { icmp 14 }

          icmpOutErrors OBJECT-TYPE
              SYNTAX  Counter
              ACCESS  read-only
              STATUS  mandatory
              DESCRIPTION
                      "The number of ICMP messages which this entity did
                      not send due to problems discovered within ICMP
                      such as a lack of buffers.  This value should not
                      include errors discovered outside the ICMP layer
                      such as the inability of IP to route the resultant
                      datagram.  In some implementations there may be no
                      types of error which contribute to this counter's
                      value."
              ::= { icmp 15 }

          icmpOutDestUnreachs OBJECT-TYPE
              SYNTAX  Counter
              ACCESS  read-only
              STATUS  mandatory
              DESCRIPTION
                      "The number of ICMP Destination Unreachable
                      messages sent."
              ::= { icmp 16 }

          icmpOutTimeExcds OBJECT-TYPE
              SYNTAX  Counter
              ACCESS  read-only
              STATUS  mandatory
              DESCRIPTION
                      "The number of ICMP Time Exceeded messages sent."
              ::= { icmp 17 }

          icmpOutParmProbs OBJECT-TYPE
              SYNTAX  Counter
              ACCESS  read-only
              STATUS  mandatory
              DESCRIPTION
                      "The number of ICMP Parameter Problem messages
                      sent."
              ::= { icmp 18 }

          icmpOutSrcQuenchs OBJECT-TYPE
              SYNTAX  Counter
              ACCESS  read-only
              STATUS  mandatory
              DESCRIPTION
                      "The number of ICMP Source Quench messages sent."
              ::= { icmp 19 }

          icmpOutRedirects OBJECT-TYPE
              SYNTAX  Counter
              ACCESS  read-only
              STATUS  mandatory
              DESCRIPTION
                      "The number of ICMP Redirect messages sent.  For a
                      host, this object will always be zero, since hosts
                      do not send redirects."
              ::= { icmp 20 }

          icmpOutEchos OBJECT-TYPE
              SYNTAX  Counter
              ACCESS  read-only
              STATUS  mandatory
              DESCRIPTION
                      "The number of ICMP Echo (request) messages sent."
              ::= { icmp 21 }

          icmpOutEchoReps OBJECT-TYPE
              SYNTAX  Counter
              ACCESS  read-only
              STATUS  mandatory
              DESCRIPTION
                      "The number of ICMP Echo Reply messages sent."
              ::= { icmp 22 }

          icmpOutTimestamps OBJECT-TYPE
              SYNTAX  Counter
              ACCESS  read-only
              STATUS  mandatory
              DESCRIPTION
                      "The number of ICMP Timestamp (request) messages
                      sent."
              ::= { icmp 23 }

          icmpOutTimestampReps OBJECT-TYPE
              SYNTAX  Counter
              ACCESS  read-only
              STATUS  mandatory
              DESCRIPTION
                      "The number of ICMP Timestamp Reply messages
                      sent."
              ::= { icmp 24 }

          icmpOutAddrMasks OBJECT-TYPE
              SYNTAX  Counter
              ACCESS  read-only
              STATUS  mandatory
              DESCRIPTION
                      "The number of ICMP Address Mask Request messages
                      sent."
              ::= { icmp 25 }

          icmpOutAddrMaskReps OBJECT-TYPE
              SYNTAX  Counter
              ACCESS  read-only
              STATUS  mandatory
              DESCRIPTION
                      "The number of ICMP Address Mask Reply messages
                      sent."
              ::= { icmp 26 }


          -- the TCP group

          -- Implementation of the TCP group is mandatory for all
          -- systems that implement the TCP.

          -- Note that instances of object types that represent
          -- information about a particular TCP connection are
          -- transient; they persist only as long as the connection
          -- in question.

          tcpRtoAlgorithm OBJECT-TYPE
              SYNTAX  INTEGER {
                          other(1),    -- none of the following

                          constant(2), -- a constant rto
                          rsre(3),     -- MIL-STD-1778, Appendix B
                          vanj(4)      -- Van Jacobson's algorithm [10]
                      }
              ACCESS  read-only
              STATUS  mandatory
              DESCRIPTION
                      "The algorithm used to determine the timeout value
                      used for retransmitting unacknowledged octets."
              ::= { tcp 1 }

          tcpRtoMin OBJECT-TYPE
              SYNTAX  INTEGER
              ACCESS  read-only
              STATUS  mandatory
              DESCRIPTION
                      "The minimum value permitted by a TCP
                      implementation for the retransmission timeout,
                      measured in milliseconds.  More refined semantics
                      for objects of this type depend upon the algorithm
                      used to determine the retransmission timeout.  In
                      particular, when the timeout algorithm is rsre(3),
                      an object of this type has the semantics of the
                      LBOUND quantity described in RFC 793."
              ::= { tcp 2 }


          tcpRtoMax OBJECT-TYPE
              SYNTAX  INTEGER
              ACCESS  read-only
              STATUS  mandatory
              DESCRIPTION
                      "The maximum value permitted by a TCP
                      implementation for the retransmission timeout,
                      measured in milliseconds.  More refined semantics
                      for objects of this type depend upon the algorithm
                      used to determine the retransmission timeout.  In
                      particular, when the timeout algorithm is rsre(3),
                      an object of this type has the semantics of the
                      UBOUND quantity described in RFC 793."
              ::= { tcp 3 }

          tcpMaxConn OBJECT-TYPE
              SYNTAX  INTEGER
              ACCESS  read-only
              STATUS  mandatory
              DESCRIPTION
                      "The limit on the total number of TCP connections
                      the entity can support.  In entities where the
                      maximum number of connections is dynamic, this
                      object should contain the value -1."
              ::= { tcp 4 }

          tcpActiveOpens OBJECT-TYPE
              SYNTAX  Counter
              ACCESS  read-only
              STATUS  mandatory
              DESCRIPTION
                      "The number of times TCP connections have made a
                      direct transition to the SYN-SENT state from the
                      CLOSED state."
              ::= { tcp 5 }

          tcpPassiveOpens OBJECT-TYPE
              SYNTAX  Counter
              ACCESS  read-only
              STATUS  mandatory
              DESCRIPTION
                      "The number of times TCP connections have made a
                      direct transition to the SYN-RCVD state from the
                      LISTEN state."
              ::= { tcp 6 }

          tcpAttemptFails OBJECT-TYPE
              SYNTAX  Counter
              ACCESS  read-only
              STATUS  mandatory
              DESCRIPTION
                      "The number of times TCP connections have made a
                      direct transition to the CLOSED state from either
                      the SYN-SENT state or the SYN-RCVD state, plus the
                      number of times TCP connections have made a direct
                      transition to the LISTEN state from the SYN-RCVD
                      state."
              ::= { tcp 7 }

          tcpEstabResets OBJECT-TYPE
              SYNTAX  Counter
              ACCESS  read-only
              STATUS  mandatory
              DESCRIPTION
                      "The number of times TCP connections have made a
                      direct transition to the CLOSED state from either
                      the ESTABLISHED state or the CLOSE-WAIT state."
              ::= { tcp 8 }

          tcpCurrEstab OBJECT-TYPE
              SYNTAX  Gauge
              ACCESS  read-only
              STATUS  mandatory
              DESCRIPTION
                      "The number of TCP connections for which the
                      current state is either ESTABLISHED or CLOSE-
                      WAIT."
              ::= { tcp 9 }

          tcpInSegs OBJECT-TYPE
              SYNTAX  Counter
              ACCESS  read-only
              STATUS  mandatory
              DESCRIPTION
                      "The total number of segments received, including
                      those received in error.  This count includes
                      segments received on currently established
                      connections."
              ::= { tcp 10 }

          tcpOutSegs OBJECT-TYPE
              SYNTAX  Counter
              ACCESS  read-only
              STATUS  mandatory
              DESCRIPTION
                      "The total number of segments sent, including
                      those on current connections but excluding those
                      containing only retransmitted octets."
              ::= { tcp 11 }

          tcpRetransSegs OBJECT-TYPE
              SYNTAX  Counter
              ACCESS  read-only
              STATUS  mandatory
              DESCRIPTION
                      "The total number of segments retransmitted - that
                      is, the number of TCP segments transmitted
                      containing one or more previously transmitted
                      octets."
              ::= { tcp 12 }


          -- the TCP Connection table

          -- The TCP connection table contains information about this
          -- entity's existing TCP connections.

          tcpConnTable OBJECT-TYPE
              SYNTAX  SEQUENCE OF TcpConnEntry
              ACCESS  not-accessible
              STATUS  mandatory
              DESCRIPTION
                      "A table containing TCP connection-specific
                      information."
              ::= { tcp 13 }

          tcpConnEntry OBJECT-TYPE
              SYNTAX  TcpConnEntry
              ACCESS  not-accessible
              STATUS  mandatory
              DESCRIPTION
                      "Information about a particular current TCP
                      connection.  An object of this type is transient,
                      in that it ceases to exist when (or soon after)
                      the connection makes the transition to the CLOSED
                      state."
              INDEX   { tcpConnLocalAddress,
                        tcpConnLocalPort,
                        tcpConnRemAddress,
                        tcpConnRemPort }
              ::= { tcpConnTable 1 }

          TcpConnEntry ::=
              SEQUENCE {
                  tcpConnState
                      INTEGER,
                  tcpConnLocalAddress
                      IpAddress,
                  tcpConnLocalPort
                      INTEGER (0..65535),
                  tcpConnRemAddress
                      IpAddress,
                  tcpConnRemPort
                      INTEGER (0..65535)
              }

          tcpConnState OBJECT-TYPE
              SYNTAX  INTEGER {
                          closed(1),
                          listen(2),
                          synSent(3),
                          synReceived(4),
                          established(5),
                          finWait1(6),
                          finWait2(7),
                          closeWait(8),
                          lastAck(9),
                          closing(10),
                          timeWait(11),
                          deleteTCB(12)
                      }
              ACCESS  read-write
              STATUS  mandatory
              DESCRIPTION
                      "The state of this TCP connection.

                      The only value which may be set by a management
                      station is deleteTCB(12).  Accordingly, it is
                      appropriate for an agent to return a `badValue'
                      response if a management station attempts to set
                      this object to any other value.

                      If a management station sets this object to the
                      value deleteTCB(12), then this has the effect of
                      deleting the TCB (as defined in RFC 793) of the
                      corresponding connection on the managed node,
                      resulting in immediate termination of the
                      connection.

                      As an implementation-specific option, a RST
                      segment may be sent from the managed node to the
                      other TCP endpoint (note however that RST segments
                      are not sent reliably)."
              ::= { tcpConnEntry 1 }

          tcpConnLocalAddress OBJECT-TYPE
              SYNTAX  IpAddress
              ACCESS  read-only
              STATUS  mandatory
              DESCRIPTION
                      "The local IP address for this TCP connection.  In
                      the case of a connection in the listen state which
                      is willing to accept connections for any IP
                      interface associated with the node, the value
                      0.0.0.0 is used."
              ::= { tcpConnEntry 2 }

          tcpConnLocalPort OBJECT-TYPE
              SYNTAX  INTEGER (0..65535)
              ACCESS  read-only
              STATUS  mandatory
              DESCRIPTION
                      "The local port number for this TCP connection."
              ::= { tcpConnEntry 3 }

          tcpConnRemAddress OBJECT-TYPE
              SYNTAX  IpAddress
              ACCESS  read-only
              STATUS  mandatory
              DESCRIPTION
                      "The remote IP address for this TCP connection."
              ::= { tcpConnEntry 4 }

          tcpConnRemPort OBJECT-TYPE
              SYNTAX  INTEGER (0..65535)
              ACCESS  read-only
              STATUS  mandatory
              DESCRIPTION
                      "The remote port number for this TCP connection."
              ::= { tcpConnEntry 5 }


          -- additional TCP objects

          tcpInErrs OBJECT-TYPE
              SYNTAX  Counter
              ACCESS  read-only
              STATUS  mandatory
              DESCRIPTION
                      "The total number of segments received in error
                      (e.g., bad TCP checksums)."
              ::= { tcp 14 }

          tcpOutRsts OBJECT-TYPE
              SYNTAX  Counter
              ACCESS  read-only
              STATUS  mandatory
              DESCRIPTION
                      "The number of TCP segments sent containing the
                      RST flag."
              ::= { tcp 15 }


          -- the UDP group

          -- Implementation of the UDP group is mandatory for all
          -- systems which implement the UDP.

          udpInDatagrams OBJECT-TYPE
              SYNTAX  Counter
              ACCESS  read-only
              STATUS  mandatory
              DESCRIPTION
                      "The total number of UDP datagrams delivered to
                      UDP users."
              ::= { udp 1 }

          udpNoPorts OBJECT-TYPE
              SYNTAX  Counter
              ACCESS  read-only
              STATUS  mandatory
              DESCRIPTION
                      "The total number of received UDP datagrams for
                      which there was no application at the destination
                      port."
              ::= { udp 2 }

          udpInErrors OBJECT-TYPE
              SYNTAX  Counter
              ACCESS  read-only
              STATUS  mandatory
              DESCRIPTION
                      "The number of received UDP datagrams that could
                      not be delivered for reasons other than the lack
                      of an application at the destination port."
              ::= { udp 3 }

          udpOutDatagrams OBJECT-TYPE
              SYNTAX  Counter
              ACCESS  read-only
              STATUS  mandatory
              DESCRIPTION
                      "The total number of UDP datagrams sent from this
                      entity."
              ::= { udp 4 }


          -- the UDP Listener table

          -- The UDP listener table contains information about this
          -- entity's UDP end-points on which a local application is
          -- currently accepting datagrams.

          udpTable OBJECT-TYPE
              SYNTAX  SEQUENCE OF UdpEntry
              ACCESS  not-accessible
              STATUS  mandatory
              DESCRIPTION
                      "A table containing UDP listener information."
              ::= { udp 5 }

          udpEntry OBJECT-TYPE
              SYNTAX  UdpEntry
              ACCESS  not-accessible
              STATUS  mandatory
              DESCRIPTION
                      "Information about a particular current UDP
                      listener."
              INDEX   { udpLocalAddress, udpLocalPort }
              ::= { udpTable 1 }

          UdpEntry ::=
              SEQUENCE {
                  udpLocalAddress
                      IpAddress,
                  udpLocalPort
                      INTEGER (0..65535)
              }

          udpLocalAddress OBJECT-TYPE
              SYNTAX  IpAddress
              ACCESS  read-only
              STATUS  mandatory
              DESCRIPTION
                      "The local IP address for this UDP listener.  In
                      the case of a UDP listener which is willing to
                      accept datagrams for any IP interface associated
                      with the node, the value 0.0.0.0 is used."
              ::= { udpEntry 1 }

          udpLocalPort OBJECT-TYPE
              SYNTAX  INTEGER (0..65535)
              ACCESS  read-only
              STATUS  mandatory
              DESCRIPTION
                      "The local port number for this UDP listener."
              ::= { udpEntry 2 }


          -- the EGP group

          -- Implementation of the EGP group is mandatory for all
          -- systems which implement the EGP.

          egpInMsgs OBJECT-TYPE
              SYNTAX  Counter
              ACCESS  read-only
              STATUS  mandatory
              DESCRIPTION
                      "The number of EGP messages received without
                      error."
              ::= { egp 1 }

          egpInErrors OBJECT-TYPE
              SYNTAX  Counter
              ACCESS  read-only
              STATUS  mandatory
              DESCRIPTION
                      "The number of EGP messages received that proved
                      to be in error."
              ::= { egp 2 }

          egpOutMsgs OBJECT-TYPE
              SYNTAX  Counter
              ACCESS  read-only
              STATUS  mandatory
              DESCRIPTION
                      "The total number of locally generated EGP
                      messages."
              ::= { egp 3 }

          egpOutErrors OBJECT-TYPE
              SYNTAX  Counter
              ACCESS  read-only
              STATUS  mandatory
              DESCRIPTION
                      "The number of locally generated EGP messages not
                      sent due to resource limitations within an EGP
                      entity."
              ::= { egp 4 }


          -- the EGP Neighbor table

          -- The EGP neighbor table contains information about this
          -- entity's EGP neighbors.

          egpNeighTable OBJECT-TYPE
              SYNTAX  SEQUENCE OF EgpNeighEntry
              ACCESS  not-accessible
              STATUS  mandatory
              DESCRIPTION
                      "The EGP neighbor table."
              ::= { egp 5 }

          egpNeighEntry OBJECT-TYPE
              SYNTAX  EgpNeighEntry
              ACCESS  not-accessible
              STATUS  mandatory
              DESCRIPTION
                      "Information about this entity's relationship with
                      a particular EGP neighbor."
              INDEX   { egpNeighAddr }
              ::= { egpNeighTable 1 }

          EgpNeighEntry ::=
              SEQUENCE {
                  egpNeighState
                      INTEGER,
                  egpNeighAddr
                      IpAddress,
                  egpNeighAs
                      INTEGER,
                  egpNeighInMsgs
                      Counter,
                  egpNeighInErrs
                      Counter,
                  egpNeighOutMsgs
                      Counter,
                  egpNeighOutErrs
                      Counter,
                  egpNeighInErrMsgs
                      Counter,
                  egpNeighOutErrMsgs
                      Counter,
                  egpNeighStateUps
                      Counter,
                  egpNeighStateDowns
                      Counter,
                  egpNeighIntervalHello
                      INTEGER,
                  egpNeighIntervalPoll
                      INTEGER,
                  egpNeighMode
                      INTEGER,
                  egpNeighEventTrigger
                      INTEGER
              }

          egpNeighState OBJECT-TYPE
              SYNTAX  INTEGER {
                          idle(1),
                          acquisition(2),
                          down(3),
                          up(4),
                          cease(5)
                      }
              ACCESS  read-only
              STATUS  mandatory
              DESCRIPTION
                      "The EGP state of the local system with respect to
                      this entry's EGP neighbor.  Each EGP state is
                      represented by a value that is one greater than
                      the numerical value associated with said state in
                      RFC 904."
              ::= { egpNeighEntry 1 }

          egpNeighAddr OBJECT-TYPE
              SYNTAX  IpAddress
              ACCESS  read-only
              STATUS  mandatory
              DESCRIPTION
                      "The IP address of this entry's EGP neighbor."
              ::= { egpNeighEntry 2 }

          egpNeighAs OBJECT-TYPE
              SYNTAX  INTEGER
              ACCESS  read-only
              STATUS  mandatory
              DESCRIPTION
                      "The autonomous system of this EGP peer.  Zero
                      should be specified if the autonomous system
                      number of the neighbor is not yet known."
              ::= { egpNeighEntry 3 }

          egpNeighInMsgs OBJECT-TYPE
              SYNTAX  Counter
              ACCESS  read-only
              STATUS  mandatory
              DESCRIPTION
                      "The number of EGP messages received without error
                      from this EGP peer."
              ::= { egpNeighEntry 4 }

          egpNeighInErrs OBJECT-TYPE
              SYNTAX  Counter
              ACCESS  read-only
              STATUS  mandatory
              DESCRIPTION
                      "The number of EGP messages received from this EGP
                      peer that proved to be in error (e.g., bad EGP
                      checksum)."
              ::= { egpNeighEntry 5 }

          egpNeighOutMsgs OBJECT-TYPE
              SYNTAX  Counter
              ACCESS  read-only
              STATUS  mandatory
              DESCRIPTION
                      "The number of locally generated EGP messages to
                      this EGP peer."
              ::= { egpNeighEntry 6 }

          egpNeighOutErrs OBJECT-TYPE
              SYNTAX  Counter
              ACCESS  read-only
              STATUS  mandatory
              DESCRIPTION
                      "The number of locally generated EGP messages not
                      sent to this EGP peer due to resource limitations
                      within an EGP entity."
              ::= { egpNeighEntry 7 }

          egpNeighInErrMsgs OBJECT-TYPE
              SYNTAX  Counter
              ACCESS  read-only
              STATUS  mandatory
              DESCRIPTION
                      "The number of EGP-defined error messages received
                      from this EGP peer."
              ::= { egpNeighEntry 8 }

          egpNeighOutErrMsgs OBJECT-TYPE
              SYNTAX  Counter
              ACCESS  read-only
              STATUS  mandatory
              DESCRIPTION
                      "The number of EGP-defined error messages sent to
                      this EGP peer."
              ::= { egpNeighEntry 9 }

          egpNeighStateUps OBJECT-TYPE
              SYNTAX  Counter
              ACCESS  read-only
              STATUS  mandatory
              DESCRIPTION
                      "The number of EGP state transitions to the UP
                      state with this EGP peer."
              ::= { egpNeighEntry 10 }

          egpNeighStateDowns OBJECT-TYPE
              SYNTAX  Counter
              ACCESS  read-only
              STATUS  mandatory
              DESCRIPTION
                      "The number of EGP state transitions from the UP
                      state to any other state with this EGP peer."
              ::= { egpNeighEntry 11 }

          egpNeighIntervalHello OBJECT-TYPE
              SYNTAX  INTEGER
              ACCESS  read-only
              STATUS  mandatory
              DESCRIPTION
                      "The interval between EGP Hello command
                      retransmissions (in hundredths of a second).  This
                      represents the t1 timer as defined in RFC 904."
              ::= { egpNeighEntry 12 }

          egpNeighIntervalPoll OBJECT-TYPE
              SYNTAX  INTEGER
              ACCESS  read-only
              STATUS  mandatory
              DESCRIPTION
                      "The interval between EGP poll command
                      retransmissions (in hundredths of a second).  This
                      represents the t3 timer as defined in RFC 904."
              ::= { egpNeighEntry 13 }

          egpNeighMode OBJECT-TYPE
              SYNTAX  INTEGER { active(1), passive(2) }
              ACCESS  read-only
              STATUS  mandatory
              DESCRIPTION
                      "The polling mode of this EGP entity, either
                      passive or active."
              ::= { egpNeighEntry 14 }

          egpNeighEventTrigger OBJECT-TYPE
              SYNTAX  INTEGER { start(1), stop(2) }
              ACCESS  read-write
              STATUS  mandatory
              DESCRIPTION
                      "A control variable used to trigger operator-
                      initiated Start and Stop events.  When read, this
                      variable always returns the most recent value that
                      egpNeighEventTrigger was set to.  If it has not
                      been set since the last initialization of the
                      network management subsystem on the node, it
                      returns a value of `stop'.

                      When set, this variable causes a Start or Stop
                      event on the specified neighbor, as specified on
                      pages 8-10 of RFC 904.  Briefly, a Start event
                      causes an Idle peer to begin neighbor acquisition
                      and a non-Idle peer to reinitiate neighbor
                      acquisition.  A stop event causes a non-Idle peer
                      to return to the Idle state until a Start event
                      occurs, either via egpNeighEventTrigger or
                      otherwise."
              ::= { egpNeighEntry 15 }


          -- additional EGP objects

          egpAs OBJECT-TYPE
              SYNTAX  INTEGER
              ACCESS  read-only
              STATUS  mandatory
              DESCRIPTION
                      "The autonomous system number of this EGP entity."
              ::= { egp 6 }


          -- the Transmission group

          -- Based on the transmission media underlying each interface
          -- on a system, the corresponding portion of the Transmission
          -- group is mandatory for that system.

          -- When Internet-standard definitions for managing
          -- transmission media are defined, the transmission group is
          -- used to provide a prefix for the names of those objects.

          -- Typically, such definitions reside in the experimental
          -- portion of the MIB until they are "proven", then as a
          -- part of the Internet standardization process, the
          -- definitions are accordingly elevated and a new object
          -- identifier, under the transmission group is defined. By
          -- convention, the name assigned is:
          --
          --     type OBJECT IDENTIFIER    ::= { transmission number }
          --
          -- where "type" is the symbolic value used for the media in
          -- the ifType column of the ifTable object, and "number" is
          -- the actual integer value corresponding to the symbol.


          -- the SNMP group

          -- Implementation of the SNMP group is mandatory for all
          -- systems which support an SNMP protocol entity.  Some of
          -- the objects defined below will be zero-valued in those
          -- SNMP implementations that are optimized to support only
          -- those functions specific to either a management agent or
          -- a management station.  In particular, it should be
          -- observed that the objects below refer to an SNMP entity,
          -- and there may be several SNMP entities residing on a
          -- managed node (e.g., if the node is hosting acting as
          -- a management station).

          snmpInPkts OBJECT-TYPE
              SYNTAX  Counter
              ACCESS  read-only
              STATUS  mandatory
              DESCRIPTION
                      "The total number of Messages delivered to the
                      SNMP entity from the transport service."
              ::= { snmp 1 }

          snmpOutPkts OBJECT-TYPE
              SYNTAX  Counter
              ACCESS  read-only
              STATUS  mandatory
              DESCRIPTION
                      "The total number of SNMP Messages which were
                      passed from the SNMP protocol entity to the
                      transport service."
              ::= { snmp 2 }

          snmpInBadVersions OBJECT-TYPE
              SYNTAX  Counter
              ACCESS  read-only
              STATUS  mandatory
              DESCRIPTION
                      "The total number of SNMP Messages which were
                      delivered to the SNMP protocol entity and were for
                      an unsupported SNMP version."
              ::= { snmp 3 }

          snmpInBadCommunityNames OBJECT-TYPE
              SYNTAX  Counter
              ACCESS  read-only
              STATUS  mandatory
              DESCRIPTION
                      "The total number of SNMP Messages delivered to
                      the SNMP protocol entity which used a SNMP
                      community name not known to said entity."
              ::= { snmp 4 }

          snmpInBadCommunityUses OBJECT-TYPE
              SYNTAX  Counter
              ACCESS  read-only
              STATUS  mandatory
              DESCRIPTION
                      "The total number of SNMP Messages delivered to
                      the SNMP protocol entity which represented an SNMP
                      operation which was not allowed by the SNMP
                      community named in the Message."
              ::= { snmp 5 }

          snmpInASNParseErrs OBJECT-TYPE
              SYNTAX  Counter
              ACCESS  read-only
              STATUS  mandatory
              DESCRIPTION
                      "The total number of ASN.1 or BER errors
                      encountered by the SNMP protocol entity when
                      decoding received SNMP Messages."
              ::= { snmp 6 }

          -- { snmp 7 } is not used

          snmpInTooBigs OBJECT-TYPE
              SYNTAX  Counter
              ACCESS  read-only
              STATUS  mandatory
              DESCRIPTION
                      "The total number of SNMP PDUs which were
                      delivered to the SNMP protocol entity and for
                      which the value of the error-status field is
                      `tooBig'."
              ::= { snmp 8 }

          snmpInNoSuchNames OBJECT-TYPE
              SYNTAX  Counter
              ACCESS  read-only
              STATUS  mandatory
              DESCRIPTION
                      "The total number of SNMP PDUs which were
                      delivered to the SNMP protocol entity and for
                      which the value of the error-status field is
                      `noSuchName'."
              ::= { snmp 9 }

          snmpInBadValues OBJECT-TYPE
              SYNTAX  Counter
              ACCESS  read-only
              STATUS  mandatory
              DESCRIPTION
                      "The total number of SNMP PDUs which were
                      delivered to the SNMP protocol entity and for
                      which the value of the error-status field is
                      `badValue'."
              ::= { snmp 10 }

          snmpInReadOnlys OBJECT-TYPE
              SYNTAX  Counter
              ACCESS  read-only
              STATUS  mandatory
              DESCRIPTION
                      "The total number valid SNMP PDUs which were
                      delivered to the SNMP protocol entity and for
                      which the value of the error-status field is
                      `readOnly'.  It should be noted that it is a
                      protocol error to generate an SNMP PDU which
                      contains the value `readOnly' in the error-status
                      field, as such this object is provided as a means
                      of detecting incorrect implementations of the
                      SNMP."
              ::= { snmp 11 }

          snmpInGenErrs OBJECT-TYPE
              SYNTAX  Counter
              ACCESS  read-only
              STATUS  mandatory
              DESCRIPTION
                      "The total number of SNMP PDUs which were
                      delivered to the SNMP protocol entity and for
                      which the value of the error-status field is
                      `genErr'."
              ::= { snmp 12 }

          snmpInTotalReqVars OBJECT-TYPE
              SYNTAX  Counter
              ACCESS  read-only
              STATUS  mandatory
              DESCRIPTION
                      "The total number of MIB objects which have been
                      retrieved successfully by the SNMP protocol entity
                      as the result of receiving valid SNMP Get-Request
                      and Get-Next PDUs."
              ::= { snmp 13 }

          snmpInTotalSetVars OBJECT-TYPE
              SYNTAX  Counter
              ACCESS  read-only
              STATUS  mandatory
              DESCRIPTION
                      "The total number of MIB objects which have been
                      altered successfully by the SNMP protocol entity
                      as the result of receiving valid SNMP Set-Request
                      PDUs."
              ::= { snmp 14 }

          snmpInGetRequests OBJECT-TYPE
              SYNTAX  Counter
              ACCESS  read-only
              STATUS  mandatory
              DESCRIPTION
                      "The total number of SNMP Get-Request PDUs which
                      have been accepted and processed by the SNMP
                      protocol entity."
              ::= { snmp 15 }

          snmpInGetNexts OBJECT-TYPE
              SYNTAX  Counter
              ACCESS  read-only
              STATUS  mandatory
              DESCRIPTION
                      "The total number of SNMP Get-Next PDUs which have
                      been accepted and processed by the SNMP protocol
                      entity."
              ::= { snmp 16 }

          snmpInSetRequests OBJECT-TYPE
              SYNTAX  Counter
              ACCESS  read-only
              STATUS  mandatory
              DESCRIPTION
                      "The total number of SNMP Set-Request PDUs which
                      have been accepted and processed by the SNMP
                      protocol entity."
              ::= { snmp 17 }

          snmpInGetResponses OBJECT-TYPE
              SYNTAX  Counter
              ACCESS  read-only
              STATUS  mandatory
              DESCRIPTION
                      "The total number of SNMP Get-Response PDUs which
                      have been accepted and processed by the SNMP
                      protocol entity."
              ::= { snmp 18 }

          snmpInTraps OBJECT-TYPE
              SYNTAX  Counter
              ACCESS  read-only
              STATUS  mandatory
              DESCRIPTION
                      "The total number of SNMP Trap PDUs which have
                      been accepted and processed by the SNMP protocol
                      entity."
              ::= { snmp 19 }

          snmpOutTooBigs OBJECT-TYPE
              SYNTAX  Counter
              ACCESS  read-only
              STATUS  mandatory
              DESCRIPTION
                      "The total number of SNMP PDUs which were
                      generated by the SNMP protocol entity and for
                      which the value of the error-status field is
                      `tooBig.'"
              ::= { snmp 20 }

          snmpOutNoSuchNames OBJECT-TYPE
              SYNTAX  Counter
              ACCESS  read-only
              STATUS  mandatory
              DESCRIPTION
                      "The total number of SNMP PDUs which were
                      generated by the SNMP protocol entity and for
                      which the value of the error-status is
                      `noSuchName'."
              ::= { snmp 21 }

          snmpOutBadValues OBJECT-TYPE
              SYNTAX  Counter
              ACCESS  read-only
              STATUS  mandatory
              DESCRIPTION
                      "The total number of SNMP PDUs which were
                      generated by the SNMP protocol entity and for
                      which the value of the error-status field is
                      `badValue'."
              ::= { snmp 22 }

          -- { snmp 23 } is not used

          snmpOutGenErrs OBJECT-TYPE
              SYNTAX  Counter
              ACCESS  read-only
              STATUS  mandatory
              DESCRIPTION
                      "The total number of SNMP PDUs which were
                      generated by the SNMP protocol entity and for
                      which the value of the error-status field is
                      `genErr'."
              ::= { snmp 24 }

          snmpOutGetRequests OBJECT-TYPE
              SYNTAX  Counter
              ACCESS  read-only
              STATUS  mandatory
              DESCRIPTION
                      "The total number of SNMP Get-Request PDUs which
                      have been generated by the SNMP protocol entity."
              ::= { snmp 25 }

          snmpOutGetNexts OBJECT-TYPE
              SYNTAX  Counter
              ACCESS  read-only
              STATUS  mandatory
              DESCRIPTION
                      "The total number of SNMP Get-Next PDUs which have
                      been generated by the SNMP protocol entity."
              ::= { snmp 26 }

          snmpOutSetRequests OBJECT-TYPE
              SYNTAX  Counter
              ACCESS  read-only
              STATUS  mandatory
              DESCRIPTION
                      "The total number of SNMP Set-Request PDUs which
                      have been generated by the SNMP protocol entity."
              ::= { snmp 27 }

          snmpOutGetResponses OBJECT-TYPE
              SYNTAX  Counter
              ACCESS  read-only
              STATUS  mandatory
              DESCRIPTION
                      "The total number of SNMP Get-Response PDUs which
                      have been generated by the SNMP protocol entity."
              ::= { snmp 28 }

          snmpOutTraps OBJECT-TYPE
              SYNTAX  Counter
              ACCESS  read-only
              STATUS  mandatory
              DESCRIPTION
                      "The total number of SNMP Trap PDUs which have
                      been generated by the SNMP protocol entity."
              ::= { snmp 29 }

          snmpEnableAuthenTraps OBJECT-TYPE
              SYNTAX  INTEGER { enabled(1), disabled(2) }
              ACCESS  read-write
              STATUS  mandatory
              DESCRIPTION
                      "Indicates whether the SNMP agent process is
                      permitted to generate authentication-failure
                      traps.  The value of this object overrides any
                      configuration information; as such, it provides a
                      means whereby all authentication-failure traps may
                      be disabled.

                      Note that it is strongly recommended that this
                      object be stored in non-volatile memory so that it
                      remains constant between re-initializations of the
                      network management system."
              ::= { snmp 30 }


--
-- FILE: /users/sse/mibs/src/rfc/rfc1215.smi
--

-- Changes for rfc1215 (Concise TRAP):
--      Added MODULE definition.
--      Commented out TRAP-TYPE macro definition and replaced
--        with SMIC directive to enable it.




    -- Make builtin items known

--    SMI TRAP-TYPE

        --  TRAP-TYPE MACRO ::=
        --  BEGIN
        --      TYPE NOTATION ::= "ENTERPRISE" value
        --                            (enterprise OBJECT IDENTIFIER)
        --                        VarPart
        --                        DescrPart
        --                        ReferPart
        --      VALUE NOTATION ::= value (VALUE INTEGER)
        --
        --      VarPart ::=
        --                 "VARIABLES" "{" VarTypes "}"
        --                      | empty
        --      VarTypes ::=
        --                 VarType | VarTypes "," VarType
        --      VarType ::=
        --                 value (vartype ObjectName)
        --
        --      DescrPart ::=
        --                 "DESCRIPTION" value (description DisplayString)
        --                      | empty
        --
        --      ReferPart ::=
        --                 "REFERENCE" value (reference DisplayString)
        --                      | empty
        --
        --  END


--
-- FILE: /users/sse/mibs/src/rfc/rfc1315.mib
--

-- Changes for RFC1315 (Frame Relay MIB)
--      Added IMPORT for Counter.
--      Changed module name from RFC-1155 to RFC1155-SMI.




     --  Frame Relay DTE MIB

     frame-relay     OBJECT IDENTIFIER ::= { transmission 32 }

     --
     --      the range of ifIndex
     --
     Index ::= INTEGER       -- 1..ifNumber

     --
     --      the range of a Data Link Connection Identifier
     --
     DLCI ::= INTEGER        -- 0..DLCINumber


     --  Data Link Connection Management Interface

     --      The variables that configure the DLC Management Interface.

     frDlcmiTable OBJECT-TYPE
         SYNTAX   SEQUENCE OF FrDlcmiEntry
         ACCESS   not-accessible
         STATUS   mandatory
         DESCRIPTION
            "The Parameters for the Data Link Connection Management
            Interface for the frame relay service on this
            interface."
         REFERENCE
            "Draft American National Standard T1.617-1991, Annex D"
         ::= { frame-relay 1 }

         frDlcmiEntry OBJECT-TYPE
             SYNTAX   FrDlcmiEntry
             ACCESS   not-accessible
             STATUS   mandatory
             DESCRIPTION
                "The Parameters for a particular Data Link Con-
                nection Management Interface."
            INDEX { frDlcmiIfIndex }
            ::= { frDlcmiTable 1 }

         FrDlcmiEntry ::=
             SEQUENCE {
                 frDlcmiIfIndex
                     Index,
                 frDlcmiState
                     INTEGER,
                 frDlcmiAddress
                     INTEGER,
                 frDlcmiAddressLen
                     INTEGER,
                 frDlcmiPollingInterval
                     INTEGER,
                 frDlcmiFullEnquiryInterval
                     INTEGER,
                 frDlcmiErrorThreshold
                     INTEGER,
                 frDlcmiMonitoredEvents
                     INTEGER,
                 frDlcmiMaxSupportedVCs
                     INTEGER,
                 frDlcmiMulticast
                     INTEGER
         }



         frDlcmiIfIndex OBJECT-TYPE
             SYNTAX   Index
             ACCESS   read-only
             STATUS   mandatory
             DESCRIPTION
                "The ifIndex value of the  corresponding  ifEn-
                try."
            ::= { frDlcmiEntry 1 }

         frDlcmiState OBJECT-TYPE
             SYNTAX INTEGER {
                 noLmiConfigured (1),
                 lmiRev1         (2),
                 ansiT1-617-D    (3),  -- ANSI T1.617 Annex D
                 ansiT1-617-B    (4)   -- ANSI T1.617 Annex B
             }
             ACCESS   read-write
             STATUS   mandatory
             DESCRIPTION
                "This variable states which Data  Link  Connec-
                tion Management scheme is active (and by impli-
                cation, what DLCI it uses) on the  Frame  Relay
                interface."
            REFERENCE
               "Draft American National Standard T1.617-1991"
           ::= { frDlcmiEntry 2 }



         frDlcmiAddress OBJECT-TYPE
             SYNTAX      INTEGER {
                         q921           (1),  -- 13 bit DLCI
                         q922March90    (2),  -- 11 bit DLCI
                         q922November90 (3),  -- 10 bit DLCI
                         q922           (4)   -- Final Standard
             }
             ACCESS  read-write
             STATUS  mandatory
             DESCRIPTION
                "This variable states which address  format  is
                in use on the Frame Relay interface."
            ::= { frDlcmiEntry 3 }


         frDlcmiAddressLen OBJECT-TYPE
             SYNTAX  INTEGER {
                     two-octets (2),
                     three-octets (3),
                     four-octets (4)
             }
             ACCESS  read-write
             STATUS  mandatory
             DESCRIPTION
                "This variable states which address  length  in
                octets.  In the case of Q922 format, the length
                indicates the entire length of the address  in-
                cluding the control portion."
            ::= { frDlcmiEntry 4 }



         frDlcmiPollingInterval OBJECT-TYPE
             SYNTAX   INTEGER (5..30)
             ACCESS   read-write
             STATUS   mandatory
             DESCRIPTION
                "This is the number of seconds between  succes-
                sive status enquiry messages."
            REFERENCE
               "Draft American National  Standard  T1.617-1991,
               Section D.7 Timer T391."
           DEFVAL { 10 }
           ::= { frDlcmiEntry 5 }


         frDlcmiFullEnquiryInterval OBJECT-TYPE
             SYNTAX   INTEGER (1..255)
             ACCESS   read-write
             STATUS   mandatory
             DESCRIPTION
                "Number of status enquiry intervals  that  pass
                before  issuance  of a full status enquiry mes-
                sage."
            REFERENCE
               "Draft American National  Standard  T1.617-1991,
               Section D.7 Counter N391."
           DEFVAL { 6 }
           ::= { frDlcmiEntry 6 }



         frDlcmiErrorThreshold OBJECT-TYPE
             SYNTAX   INTEGER (1..10)
             ACCESS   read-write
             STATUS   mandatory
             DESCRIPTION
                "This  is  the  maximum  number  of  unanswered
                Status Enquiries the equipment shall accept be-
                fore declaring the interface down."
            REFERENCE
               "Draft American National  Standard  T1.617-1991,
               Section D.5.1 Counter N392."
           DEFVAL { 3 }
           ::= { frDlcmiEntry 7 }


         frDlcmiMonitoredEvents OBJECT-TYPE
             SYNTAX   INTEGER (1..10)
             ACCESS   read-write
             STATUS   mandatory
             DESCRIPTION
                "This is the number of status polling intervals
                over which the error threshold is counted.  For
                example, if within 'MonitoredEvents' number  of
                events  the  station  receives 'ErrorThreshold'
                number of errors, the interface  is  marked  as
                down."
            REFERENCE
               "Draft American National  Standard  T1.617-1991,
               Section D.5.2 Counter N393."
           DEFVAL { 4 }
           ::= { frDlcmiEntry 8 }



         frDlcmiMaxSupportedVCs OBJECT-TYPE
             SYNTAX   INTEGER
             ACCESS   read-write
             STATUS   mandatory
             DESCRIPTION
                "The maximum number of Virtual Circuits allowed
                for  this  interface.   Usually dictated by the
                Frame Relay network.

                In response to a SET, if a value less than zero
                or  higher  than the agent's maximal capability
                is configured, the agent  should  respond  bad-
                Value"
            ::= { frDlcmiEntry 9 }


         frDlcmiMulticast OBJECT-TYPE
             SYNTAX   INTEGER {
                         nonBroadcast (1),
                         broadcast (2)
                         }
             ACCESS   read-write
             STATUS   mandatory
             DESCRIPTION
                "This indicates whether the Frame Relay  inter-
                face is using a multicast service."
            ::= { frDlcmiEntry 10 }


     -- A Frame Relay service is a multiplexing service.  Data
     -- Link Connection Identifiers enumerate virtual circuits
     -- (permanent or dynamic) which are layered onto the underlying
     -- circuit, represented by ifEntry.  Therefore, each of the entries
     -- in the Standard MIB's Interface Table with an IfType of
     -- Frame Relay represents a Q.922 interface.  Zero or more
     -- virtual circuits are layered onto this interface and provide
     -- interconnection with various remote destinations.
     -- Each such virtual circuit is represented by an entry in the
     -- circuit table.

     --   Circuit Table

     -- The table describing the use of the DLCIs attached to
     -- each Frame Relay Interface.

     frCircuitTable OBJECT-TYPE
         SYNTAX   SEQUENCE OF FrCircuitEntry
         ACCESS   not-accessible
         STATUS   mandatory
         DESCRIPTION
            "A table containing information about specific Data
            Link Connection Identifiers and corresponding virtual
            circuits."
         ::= { frame-relay 2 }

         frCircuitEntry OBJECT-TYPE
             SYNTAX   FrCircuitEntry
             ACCESS   not-accessible
             STATUS   mandatory
             DESCRIPTION
                "The information regarding a single  Data  Link
                Connection Identifier."
            INDEX { frCircuitIfIndex, frCircuitDlci }
            ::= { frCircuitTable 1 }


         FrCircuitEntry ::=
             SEQUENCE {
                 frCircuitIfIndex
                     Index,
                 frCircuitDlci
                     DLCI,
                 frCircuitState
                     INTEGER,
                 frCircuitReceivedFECNs
                     Counter,
                 frCircuitReceivedBECNs
                     Counter,
                 frCircuitSentFrames
                     Counter,
                 frCircuitSentOctets
                     Counter,
                 frCircuitReceivedFrames
                     Counter,
                 frCircuitReceivedOctets
                     Counter,
                 frCircuitCreationTime
                     TimeTicks,
                 frCircuitLastTimeChange
                     TimeTicks,
                 frCircuitCommittedBurst
                     INTEGER,
                 frCircuitExcessBurst
                     INTEGER,
                 frCircuitThroughput
                     INTEGER
         }



         frCircuitIfIndex OBJECT-TYPE
             SYNTAX   Index
             ACCESS   read-only
             STATUS   mandatory
             DESCRIPTION
                "The ifIndex Value of the ifEntry this  virtual
                circuit is layered onto."
            ::= { frCircuitEntry 1 }


         frCircuitDlci OBJECT-TYPE
             SYNTAX   DLCI
             ACCESS   read-only
             STATUS   mandatory
             DESCRIPTION
                "The Data Link Connection Identifier  for  this
                virtual circuit."
            REFERENCE
               "Draft American National  Standard  T1.618-1991,
               Section 3.3.6"
           ::= { frCircuitEntry 2 }


         frCircuitState OBJECT-TYPE
             SYNTAX   INTEGER {
                         invalid (1),
                         active (2),
                         inactive (3)
                      }
             ACCESS   read-write
             STATUS   mandatory
             DESCRIPTION
                "Indicates whether the particular virtual  cir-
                cuit  is operational.  In the absence of a Data
                Link Connection Management  Interface,  virtual
                circuit  entries  (rows) may be created by set-
                ting virtual  circuit  state  to  'active',  or
                deleted by changing Circuit state to 'invalid'.
                Whether or not the row actually  disappears  is
                left  to the implementation, so this object may
                actually read as 'invalid' for  some  arbitrary
                length  of  time.   It is also legal to set the
                state of a virtual  circuit  to  'inactive'  to
                temporarily disable a given circuit."
            DEFVAL { active }
            ::= { frCircuitEntry 3 }


         frCircuitReceivedFECNs OBJECT-TYPE
             SYNTAX   Counter
             ACCESS   read-only
             STATUS   mandatory
             DESCRIPTION
                "Number of frames received from the network in-
                dicating  forward  congestion since the virtual
                circuit was created."
            REFERENCE
               "Draft American National  Standard  T1.618-1991,
               Section 3.3.3"
           ::= { frCircuitEntry 4 }



         frCircuitReceivedBECNs OBJECT-TYPE
             SYNTAX   Counter
             ACCESS   read-only
             STATUS   mandatory
             DESCRIPTION
                "Number of frames received from the network in-
                dicating  backward congestion since the virtual
                circuit was created."
            REFERENCE
               "Draft American National  Standard  T1.618-1991,
               Section 3.3.4"
           ::= { frCircuitEntry 5 }



         frCircuitSentFrames OBJECT-TYPE
             SYNTAX   Counter
             ACCESS   read-only
             STATUS   mandatory
             DESCRIPTION
                "The number of frames sent  from  this  virtual
                circuit since it was created."
            ::= { frCircuitEntry 6 }



         frCircuitSentOctets OBJECT-TYPE
             SYNTAX   Counter
             ACCESS   read-only
             STATUS   mandatory
             DESCRIPTION
                "The number of octets sent  from  this  virtual
                circuit since it was created."
            ::= { frCircuitEntry 7 }



         frCircuitReceivedFrames OBJECT-TYPE
             SYNTAX   Counter
             ACCESS   read-only
             STATUS   mandatory
             DESCRIPTION
                "Number of frames received  over  this  virtual
                circuit since it was created."
            ::= { frCircuitEntry 8 }



         frCircuitReceivedOctets OBJECT-TYPE
             SYNTAX   Counter
             ACCESS   read-only
             STATUS   mandatory
             DESCRIPTION
                "Number of octets received  over  this  virtual
                circuit since it was created."
            ::= { frCircuitEntry 9 }


         frCircuitCreationTime OBJECT-TYPE
             SYNTAX   TimeTicks
             ACCESS   read-only
             STATUS   mandatory
             DESCRIPTION
                "The value of sysUpTime when the  virtual  cir-
                cuit was created, whether by the Data Link Con-
                nection Management Interface  or  by  a  SetRe-
                quest."
            ::= { frCircuitEntry 10 }



         frCircuitLastTimeChange OBJECT-TYPE
             SYNTAX   TimeTicks
             ACCESS   read-only
             STATUS   mandatory
             DESCRIPTION
                "The value of sysUpTime when last there  was  a
                change in the virtual circuit state"
            ::= { frCircuitEntry 11 }



         frCircuitCommittedBurst OBJECT-TYPE
             SYNTAX   INTEGER
             ACCESS   read-write
             STATUS   mandatory
             DESCRIPTION
                "This variable indicates the maximum amount  of
                data,  in  bits,  that  the  network  agrees to
                transfer under normal  conditions,  during  the
                measurement interval."
            REFERENCE
               "Draft American National  Standard  T1.617-1991,
               Section 6.5.19"
           DEFVAL   { 0 }  -- the default indicates no commitment
           ::= { frCircuitEntry 12 }



         frCircuitExcessBurst OBJECT-TYPE
             SYNTAX   INTEGER
             ACCESS   read-write
             STATUS   mandatory
             DESCRIPTION
                "This variable indicates the maximum amount  of
                uncommitted data bits that the network will at-
                tempt to deliver over the measurement interval.

                By default, if not configured when creating the
                entry, the Excess Information Burst Size is set
                to the value of ifSpeed."
            REFERENCE
               "Draft American National  Standard  T1.617-1991,
               Section 6.5.19"
                   ::= { frCircuitEntry 13 }



         frCircuitThroughput OBJECT-TYPE
             SYNTAX   INTEGER
             ACCESS   read-write
             STATUS   mandatory
             DESCRIPTION
                "Throughput is the average number of 'Frame Re-
                lay  Information  Field'  bits  transferred per
                second across a user network interface  in  one
                direction, measured over the measurement inter-
                val.

                If the  configured  committed  burst  rate  and
                throughput  are  both non-zero, the measurement
                interval
                T=frCircuitCommittedBurst/frCircuitThroughput.

                If the  configured  committed  burst  rate  and
                throughput  are  both zero, the measurement in-
                terval
                       T=frCircuitExcessBurst/ifSpeed."
            REFERENCE
               "Draft American National  Standard  T1.617-1991,
               Section 6.5.19"
           DEFVAL {0}  -- the default value of Throughput is
                       -- "no commitment".
           ::= { frCircuitEntry 14 }


     --  Error Table

     -- The table describing errors encountered on each Frame
     -- Relay Interface.

     frErrTable OBJECT-TYPE
         SYNTAX   SEQUENCE OF FrErrEntry
         ACCESS   not-accessible
         STATUS   mandatory
         DESCRIPTION
            "A table containing information about Errors on the
            Frame Relay interface."
         ::= { frame-relay 3 }

         frErrEntry OBJECT-TYPE
             SYNTAX   FrErrEntry
             ACCESS   not-accessible
             STATUS   mandatory
             DESCRIPTION
                "The error information for a single frame relay
                interface."
            INDEX { frErrIfIndex }
            ::= { frErrTable 1 }



         FrErrEntry ::=
             SEQUENCE {
                 frErrIfIndex
                     Index,
                 frErrType
                     INTEGER,
                 frErrData
                     OCTET STRING,
                 frErrTime
                     TimeTicks
         }



         frErrIfIndex OBJECT-TYPE
             SYNTAX   Index
             ACCESS   read-only
             STATUS   mandatory
             DESCRIPTION
                "The ifIndex Value of the  corresponding  ifEn-
                try."
            ::= { frErrEntry 1 }



         frErrType OBJECT-TYPE
             SYNTAX   INTEGER {
                         unknownError(1),
                         receiveShort(2),
                         receiveLong(3),
                         illegalDLCI(4),
                         unknownDLCI(5),
                         dlcmiProtoErr(6),
                         dlcmiUnknownIE(7),
                         dlcmiSequenceErr(8),
                         dlcmiUnknownRpt(9),
                         noErrorSinceReset(10)
                      }
             ACCESS   read-only
             STATUS   mandatory
             DESCRIPTION
                "The type of error that was last seen  on  this
                interface."
            ::= { frErrEntry 2 }



         frErrData OBJECT-TYPE
             SYNTAX   OCTET STRING
             ACCESS   read-only
             STATUS   mandatory
             DESCRIPTION
                "An octet string containing as much of the  er-
                ror  packet as possible.  As a minimum, it must
                contain the Q.922 Address or  as  much  as  was
                delivered.   It is desirable to include all in-
                formation up to the PDU."
            ::= { frErrEntry 3 }



         frErrTime OBJECT-TYPE
             SYNTAX   TimeTicks
             ACCESS   read-only
             STATUS   mandatory
             DESCRIPTION
                "The value of sysUpTime at which the error  was
                detected."
            ::= { frErrEntry 4 }


         -- Frame Relay Globals

         frame-relay-globals OBJECT IDENTIFIER ::= { frame-relay 4 }

         frTrapState OBJECT-TYPE
             SYNTAX  INTEGER { enabled(1), disabled(2) }
             ACCESS   read-write
             STATUS   mandatory
             DESCRIPTION
                "This variable  indicates  whether  the  system
                produces the frDLCIStatusChange trap."
            DEFVAL { disabled }
            ::= { frame-relay-globals 1 }


         --  Data Link Connection Management Interface Related Traps

         frDLCIStatusChange TRAP-TYPE
             ENTERPRISE frame-relay
             VARIABLES  { frCircuitIfIndex, frCircuitDlci, frCircuitState }
             DESCRIPTION
                "This trap indicates that the indicated Virtual
                Circuit  has changed state.  It has either been
                created or invalidated, or has toggled  between
                the active and inactive states."
             ::= 1


--
-- FILE: /users/sse/mibs/src/rfc/rfc1271.mib
--

-- Changes for RFC1271 (RMON MIB):
--      Changed RFC1158-MIB to RFC1213-MIB
--      Added import for TimeTicks.
--      Changed syntax of etherStatsStatus from INTEGER to
--          EntryStatus in sequence EtherStatsEntry.
--      Changed syntax of historyControlStatus from INTEGER to
--          EntryStatus in sequence HistoryControlEntry.
--      Changed range of alarmRisingEventIndex in definition
--          of sequence AlarmEntry to match object
--          definition.
--      Changed range of alarmFallingEventIndex in definition
--          of sequence AlarmEntry to match object
--          definition.
--      Changed syntax of alarmStatus from INTEGER to
--          EntryStatus in sequence AlarmEntry.
--      Changed syntax of hostControlStatus from INTEGER to
--          EntryStatus in sequence HostControlEntry.
--      Changed syntax of hostTopNStatus from INTEGER to
--          EntryStatus in sequence HistoryHostTopNControlEntry.
--      Changed syntax of maxtrixControlStatus from INTEGER to
--          EntryStatus in sequence MatrixControlEntry.
--      Changed syntax of filterStatus from INTEGER to
--          EntryStatus in sequence FilterEntry.
--      Changed syntax of channelStatus from INTEGER to
--          EntryStatus in sequence ChannelEntry.
--      Changed syntax of bufferControlStatus from INTEGER to
--          EntryStatus in sequence bufferControlEntry.
--      Changed syntax of eventStatus from INTEGER to
--          EntryStatus in sequence EventEntry.
--      Added import for TRAP-TYPE macro.
--      Added risingAlarm trap definition from RMON draft mib
--          draft-ietf-rmonmib-rmonmib-02.txt
--      Added fallingAlarm trap definition from RMON draft mib
--          draft-ietf-rmonmib-rmonmib-02.txt



          -- RFC1271
          -- November 91


          --  This MIB module uses the extended OBJECT-TYPE macro as
          --  defined in [9].


          --  Remote Network Monitoring MIB

              rmon    OBJECT IDENTIFIER ::= { mib-2 16 }


              -- textual conventions

              OwnerString ::= DisplayString
              -- This data type is used to model an administratively
              -- assigned name of the owner of a resource. This
              -- information is taken from the NVT ASCII character set.
              -- It is suggested that this name contain one or more
              -- of the following:
              -- IP address, management station name, network manager's
              -- name, location, or phone number.
              -- In some cases the agent itself will be the owner of
              -- an entry.  In these cases, this string shall be set
              -- to a string starting with 'monitor'.
              --
              -- SNMP access control is articulated entirely in terms of
              -- the contents of MIB views; access to a particular SNMP
              -- object instance depends only upon its presence or
              -- absence in a particular MIB view and never upon its
              -- value or the value of related object instances. Thus,
              -- objects of this type afford resolution of resource
              -- contention only among cooperating managers; they
              -- realize no access control function with respect
              -- to uncooperative parties.
              --
              -- By convention, objects with this syntax are declared
              -- as having
              --
              --      SIZE (0..127)


              EntryStatus ::= INTEGER
                         { valid(1),
                           createRequest(2),
                           underCreation(3),
                           invalid(4)
                         }

              -- The status of a table entry.
              --
              -- Setting this object to the value invalid(4) has the
              -- effect of invalidating the corresponding entry.
              -- That is, it effectively disassociates the mapping
              -- identified with said entry.
              -- It is an implementation-specific matter as to whether
              -- the agent removes an invalidated entry from the table.
              -- Accordingly, management stations must be prepared to
              -- receive tabular information from agents that corresponds
              -- to entries currently not in use.  Proper
              -- interpretation of such entries requires examination
              -- of the relevant EntryStatus object.
              --
              -- An existing instance of this object cannot be set to
              -- createRequest(2).  This object may only be set to
              -- createRequest(2) when this instance is created.  When
              -- this object is created, the agent may wish to create
              -- supplemental object instances to complete a conceptual
              -- row in this table.  Immediately after completing the
              -- create operation, the agent must set this object to
              -- underCreation(3).
              --
              -- Entries shall exist in the underCreation(3) state until
              -- the management station is finished configuring the
              -- entry and sets this object to valid(1) or aborts,
              -- setting this object to invalid(4).  If the agent
              -- determines that an entry has been in the
              -- underCreation(3) state for an abnormally long time,
              -- it may decide that the management station has
              -- crashed.  If the agent makes this decision,
              -- it may set this object to invalid(4) to reclaim the
              -- entry.  A prudent agent will understand that the
              -- management station may need to wait for human input
              -- and will allow for that possibility in its
              -- determination of this abnormally long period.


              statistics        OBJECT IDENTIFIER ::= { rmon 1 }
              history           OBJECT IDENTIFIER ::= { rmon 2 }
              alarm             OBJECT IDENTIFIER ::= { rmon 3 }
              hosts             OBJECT IDENTIFIER ::= { rmon 4 }
              hostTopN          OBJECT IDENTIFIER ::= { rmon 5 }
              matrix            OBJECT IDENTIFIER ::= { rmon 6 }
              filter            OBJECT IDENTIFIER ::= { rmon 7 }
              capture           OBJECT IDENTIFIER ::= { rmon 8 }
              event             OBJECT IDENTIFIER ::= { rmon 9 }


          -- The Statistics Group
          --
          -- Implementation of the Statistics group is optional.
          --
          -- The statistics group contains statistics measured by the
          -- probe for each monitored interface on this device.  These
          -- statistics take the form of free running counters that
          -- start from zero when a valid entry is created.
          --
          -- This group currently has statistics defined only for
          -- Ethernet interfaces.  Each etherStatsEntry contains
          -- statistics for one Ethernet interface.  The probe must
          -- create one etherStats entry for each monitored Ethernet
          -- interface on the device.

          etherStatsTable OBJECT-TYPE
              SYNTAX SEQUENCE OF EtherStatsEntry
              ACCESS not-accessible
              STATUS mandatory
              DESCRIPTION
                  "A list of Ethernet statistics entries."
              ::= { statistics 1 }

          etherStatsEntry OBJECT-TYPE
              SYNTAX EtherStatsEntry
              ACCESS not-accessible
              STATUS mandatory
              DESCRIPTION
                  "A collection of statistics kept for a particular
                  Ethernet interface."
              INDEX { etherStatsIndex }
              ::= { etherStatsTable 1 }

          EtherStatsEntry ::= SEQUENCE {
              etherStatsIndex                    INTEGER (1..65535),
              etherStatsDataSource               OBJECT IDENTIFIER,
              etherStatsDropEvents               Counter,
              etherStatsOctets                   Counter,
              etherStatsPkts                     Counter,
              etherStatsBroadcastPkts            Counter,
              etherStatsMulticastPkts            Counter,
              etherStatsCRCAlignErrors           Counter,
              etherStatsUndersizePkts            Counter,
              etherStatsOversizePkts             Counter,
              etherStatsFragments                Counter,
              etherStatsJabbers                  Counter,
              etherStatsCollisions               Counter,
              etherStatsPkts64Octets             Counter,
              etherStatsPkts65to127Octets        Counter,
              etherStatsPkts128to255Octets       Counter,
              etherStatsPkts256to511Octets       Counter,
              etherStatsPkts512to1023Octets      Counter,
              etherStatsPkts1024to1518Octets     Counter,
              etherStatsOwner                    OwnerString,
              etherStatsStatus                   EntryStatus
          }

          etherStatsIndex OBJECT-TYPE
              SYNTAX INTEGER (1..65535)
              ACCESS read-only
              STATUS mandatory
              DESCRIPTION
                  "The value of this object uniquely identifies this
                  etherStats entry."
              ::= { etherStatsEntry 1 }

          etherStatsDataSource OBJECT-TYPE
              SYNTAX OBJECT IDENTIFIER
              ACCESS read-write
              STATUS mandatory
              DESCRIPTION
                  "This object identifies the source of the data that
                  this etherStats entry is configured to analyze.  This
                  source can be any ethernet interface on this device.
                  In order to identify a particular interface, this
                  object shall identify the instance of the ifIndex
                  object, defined in [4,6], for the desired interface.
                  For example, if an entry were to receive data from
                  interface #1, this object would be set to ifIndex.1.

                  The statistics in this group reflect all packets
                  on the local network segment attached to the
                  identified interface.

                  This object may not be modified if the associated
                  etherStatsStatus object is equal to valid(1)."
              ::= { etherStatsEntry 2 }

          etherStatsDropEvents OBJECT-TYPE
              SYNTAX Counter
              ACCESS read-only
              STATUS mandatory
              DESCRIPTION
                  "The total number of events in which packets
                  were dropped by the probe due to lack of resources.
                  Note that this number is not necessarily the number of
                  packets dropped; it is just the number of times this
                  condition has been detected."
              ::= { etherStatsEntry 3 }

          etherStatsOctets OBJECT-TYPE
              SYNTAX Counter
              ACCESS read-only
              STATUS mandatory
              DESCRIPTION
                  "The total number of octets of data (including
                  those in bad packets) received on the
                  network (excluding framing bits but including
                  FCS octets)."
              ::= { etherStatsEntry 4 }

          etherStatsPkts OBJECT-TYPE
              SYNTAX Counter
              ACCESS read-only
              STATUS mandatory
              DESCRIPTION
                  "The total number of packets (including error packets)
                  received."
              ::= { etherStatsEntry 5 }

          etherStatsBroadcastPkts OBJECT-TYPE
              SYNTAX Counter
              ACCESS read-only
              STATUS mandatory
              DESCRIPTION
                  "The total number of good packets received that were
                  directed to the broadcast address."
              ::= { etherStatsEntry 6 }

          etherStatsMulticastPkts OBJECT-TYPE
              SYNTAX Counter
              ACCESS read-only
              STATUS mandatory
              DESCRIPTION
                  "The total number of good packets received that were
                  directed to a multicast address.  Note that this
                  number does not include packets directed to the
                  broadcast address."
              ::= { etherStatsEntry 7 }

          etherStatsCRCAlignErrors OBJECT-TYPE
              SYNTAX Counter
              ACCESS read-only
              STATUS mandatory
              DESCRIPTION
                  "The total number of packets received that
                  had a length (excluding framing bits, but
                  including FCS octets) of between 64 and 1518
                  octets, inclusive, but were not an integral number
                  of octets in length or had a bad Frame Check
                  Sequence (FCS)."
              ::= { etherStatsEntry 8 }

          etherStatsUndersizePkts OBJECT-TYPE
              SYNTAX Counter
              ACCESS read-only
              STATUS mandatory
              DESCRIPTION
                  "The total number of packets received that were
                  less than 64 octets long (excluding framing bits,
                  but including FCS octets) and were otherwise well
                  formed."
              ::= { etherStatsEntry 9 }

          etherStatsOversizePkts OBJECT-TYPE
              SYNTAX Counter
              ACCESS read-only
              STATUS mandatory
              DESCRIPTION
                  "The total number of packets received that were
                  longer than 1518 octets (excluding framing bits,
                  but including FCS octets) and were otherwise
                  well formed."
              ::= { etherStatsEntry 10 }

          etherStatsFragments OBJECT-TYPE
              SYNTAX Counter
              ACCESS read-only
              STATUS mandatory
              DESCRIPTION
                  "The total number of packets received that were not an
                  integral number of octets in length or that had a bad
                  Frame Check Sequence (FCS), and were less than 64
                  octets in length (excluding framing bits but
                  including FCS octets)."
              ::= { etherStatsEntry 11 }

          etherStatsJabbers OBJECT-TYPE
              SYNTAX Counter
              ACCESS read-only
              STATUS mandatory
              DESCRIPTION
                  "The total number of packets received that were
                  longer than 1518 octets (excluding framing bits,
                  but including FCS octets), and were not an
                  integral number of octets in length or had
                  a bad Frame Check Sequence (FCS)."
              ::= { etherStatsEntry 12 }

          etherStatsCollisions OBJECT-TYPE
              SYNTAX Counter
              ACCESS read-only
              STATUS mandatory
              DESCRIPTION
                  "The best estimate of the total number of collisions
                  on this Ethernet segment."
              ::= { etherStatsEntry 13 }

          etherStatsPkts64Octets OBJECT-TYPE
              SYNTAX Counter
              ACCESS read-only
              STATUS mandatory
              DESCRIPTION
                  "The total number of packets (including error
                  packets) received that were 64 octets in length
                  (excluding framing bits but including FCS octets)."
              ::= { etherStatsEntry 14 }

          etherStatsPkts65to127Octets OBJECT-TYPE
              SYNTAX Counter
              ACCESS read-only
              STATUS mandatory
              DESCRIPTION
                  "The total number of packets (including error
                  packets) received that were between
                  65 and 127 octets in length inclusive
                  (excluding framing bits but including FCS octets)."
              ::= { etherStatsEntry 15 }

          etherStatsPkts128to255Octets OBJECT-TYPE
              SYNTAX Counter
              ACCESS read-only
              STATUS mandatory
              DESCRIPTION
                  "The total number of packets (including error
                  packets) received that were between
                  128 and 255 octets in length inclusive
                  (excluding framing bits but including FCS octets)."
              ::= { etherStatsEntry 16 }

          etherStatsPkts256to511Octets OBJECT-TYPE
              SYNTAX Counter
              ACCESS read-only
              STATUS mandatory
              DESCRIPTION
                  "The total number of packets (including error
                  packets) received that were between
                  256 and 511 octets in length inclusive
                  (excluding framing bits but including FCS octets)."
              ::= { etherStatsEntry 17 }

          etherStatsPkts512to1023Octets OBJECT-TYPE
              SYNTAX Counter
              ACCESS read-only
              STATUS mandatory
              DESCRIPTION
                  "The total number of packets (including error
                  packets) received that were between
                  512 and 1023 octets in length inclusive
                  (excluding framing bits but including FCS octets)."
              ::= { etherStatsEntry 18 }

          etherStatsPkts1024to1518Octets OBJECT-TYPE
              SYNTAX Counter
              ACCESS read-only
              STATUS mandatory
              DESCRIPTION
                  "The total number of packets (including error
                  packets) received that were between
                  1024 and 1518 octets in length inclusive
                  (excluding framing bits but including FCS octets)."
              ::= { etherStatsEntry 19 }

          etherStatsOwner OBJECT-TYPE
              SYNTAX OwnerString
              ACCESS read-write
              STATUS mandatory
              DESCRIPTION
                  "The entity that configured this entry and is
                  therefore using the resources assigned to it."
              ::= { etherStatsEntry 20 }

          etherStatsStatus OBJECT-TYPE
              SYNTAX EntryStatus
              ACCESS read-write
              STATUS mandatory
              DESCRIPTION
                  "The status of this etherStats entry."
              ::= { etherStatsEntry 21 }


          -- The History Group

          -- Implementation of the History group is optional.
          --
          -- The history group records periodic statistical samples from
          -- a network and stores them for later retrieval.  The
          -- historyControl table stores configuration entries that each
          -- define an interface, polling period, and other parameters.
          -- Once samples are taken, their data is stored in an entry
          -- in a media-specific table.  Each such entry defines one
          -- sample, and is associated with the historyControlEntry that
          -- caused the sample to be taken.  Currently the only media-
          -- specific table defined is the etherHistoryTable, for
          -- Ethernet networks.
          --
          -- If the probe keeps track of the time of day, it should
          -- start the first sample of the history at a time such that
          -- when the next hour of the day begins, a sample is
          -- started at that instant.  This tends to make more
          -- user-friendly reports, and enables comparison of reports
          -- from different probes that have relatively accurate time
          -- of day.
          --
          -- The monitor is encouraged to add two history control entries
          -- per monitored interface upon initialization that describe
          -- a short term and a long term polling period.  Suggested
          -- parameters are 30 seconds for the short term polling
          -- period and 30 minutes for the long term period.












          -- Ether History table




















          -- The Alarm Group

          -- Implementation of the Alarm group is optional.
          --
          -- The Alarm Group requires the implementation of the Event
          -- group.
          --
          -- The Alarm group periodically takes statistical samples from
          -- variables in the probe and compares them to thresholds
          -- that have been configured.  The alarm table stores
          -- configuration entries that each define a variable,
          -- polling period, and threshold parameters.  If a sample is
          -- found to cross the threshold values, an event is
          -- generated.  Only variables that resolve to an ASN.1
          -- primitive type of INTEGER (INTEGER, Counter,
          -- Gauge, or TimeTicks) may be monitored in this way.
          --
          -- This function has a hysteresis mechanism to limit the
          -- generation of events.  This mechanism generates one event
          -- as a threshold is crossed in the appropriate direction.
          -- No more events are generated for that threshold until the
          -- opposite threshold is crossed.
          --
          -- In the case of a sampling a deltaValue, a probe may
          -- implement this mechanism with more precision if it takes
          -- a delta sample twice per period, each time comparing the
          -- sum of the latest two samples to the threshold.  This
          -- allows the detection of threshold crossings
          -- that span the sampling boundary.  Note that this does not
          -- require any special configuration of the threshold value.
          -- It is suggested that probes implement this more precise
          -- algorithm.

          alarmTable OBJECT-TYPE
              SYNTAX SEQUENCE OF AlarmEntry
              ACCESS not-accessible
              STATUS mandatory
              DESCRIPTION
                  "A list of alarm entries."
              ::= { alarm 1 }

          alarmEntry OBJECT-TYPE
              SYNTAX AlarmEntry
              ACCESS not-accessible
              STATUS mandatory
              DESCRIPTION
                  "A list of parameters that set up a periodic checking
                  for alarm conditions."
              INDEX { alarmIndex }
              ::= { alarmTable 1 }

          AlarmEntry ::= SEQUENCE {
              alarmIndex                    INTEGER (1..65535),
              alarmInterval                 INTEGER,
              alarmVariable                 OBJECT IDENTIFIER,
              alarmSampleType               INTEGER,
              alarmValue                    INTEGER,
              alarmStartupAlarm             INTEGER,
              alarmRisingThreshold          INTEGER,
              alarmFallingThreshold         INTEGER,
              alarmRisingEventIndex         INTEGER (0..65535),
              alarmFallingEventIndex        INTEGER (0..65535),
              alarmOwner                    OwnerString,
              alarmStatus                   EntryStatus
          }

          alarmIndex OBJECT-TYPE
              SYNTAX INTEGER (1..65535)
              ACCESS read-only
              STATUS mandatory
              DESCRIPTION
                  "An index that uniquely identifies an entry in the
                  alarm table.  Each such entry defines a
                  diagnostic sample at a particular interval
                  for an object on the device."
              ::= { alarmEntry 1 }

          alarmInterval OBJECT-TYPE
              SYNTAX INTEGER
              ACCESS read-write
              STATUS mandatory
              DESCRIPTION
                  "The interval in seconds over which the data is
                  sampled and compared with the rising and falling
                  thresholds.  When setting this variable, care
                  should be given to ensure that the variable being
                  monitored will not exceed 2^31 - 1 and roll
                  over the alarmValue object during the interval.

                  This object may not be modified if the associated
                  alarmStatus object is equal to valid(1)."
              ::= { alarmEntry 2 }

          alarmVariable OBJECT-TYPE
              SYNTAX OBJECT IDENTIFIER
              ACCESS read-write
              STATUS mandatory
              DESCRIPTION
                  "The object identifier of the particular variable to
                  be sampled.  Only variables that resolve to an ASN.1
                  primitive type of INTEGER (INTEGER, Counter, Gauge,
                  or TimeTicks) may be sampled.

                  Because SNMP access control is articulated entirely
                  in terms of the contents of MIB views, no access
                  control mechanism exists that can restrict the value of
                  this object to identify only those objects that exist
                  in a particular MIB view.  Because there is thus no
                  acceptable means of restricting the read access that
                  could be obtained through the alarm mechanism, the
                  probe must only grant write access to this object in
                  those views that have read access to all objects on
                  the probe.

                  During a set operation, if the supplied variable
                  name is not available in the selected MIB view, a
                  badValue error must be returned.  If at any time
                  the variable name of an established alarmEntry is
                  no longer available in the selected MIB view, the
                  probe must change the status of this alarmEntry
                  to invalid(4).

                  This object may not be modified if the associated
                  alarmStatus object is equal to valid(1)."
              ::= { alarmEntry 3 }

          alarmSampleType OBJECT-TYPE
              SYNTAX INTEGER {
                  absoluteValue(1),
                  deltaValue(2)
              }
              ACCESS read-write
              STATUS mandatory
              DESCRIPTION
                  "The method of sampling the selected variable and
                  calculating the value to be compared against the
                  thresholds.  If the value of this object is
                  absoluteValue(1), the value of the selected variable
                  will be compared directly with the thresholds at the
                  end of the sampling interval.  If the value of this
                  object is deltaValue(2), the value of the selected
                  variable at the last sample will be subtracted from
                  the current value, and the difference compared with
                  the thresholds.

                  This object may not be modified if the associated
                  alarmStatus object is equal to valid(1)."
              ::= { alarmEntry 4 }

          alarmValue OBJECT-TYPE
              SYNTAX INTEGER
              ACCESS read-only
              STATUS mandatory
              DESCRIPTION
                  "The value of the statistic during the last sampling
                  period.  The value during the current sampling period
                  is not made available until the period is completed."
              ::= { alarmEntry 5 }

          alarmStartupAlarm OBJECT-TYPE
              SYNTAX INTEGER {
                  risingAlarm(1),
                  fallingAlarm(2),
                  risingOrFallingAlarm(3)
              }
              ACCESS read-write
              STATUS mandatory
              DESCRIPTION
                  "The alarm that may be sent when this entry is first
                  set to valid.  If the first sample after this entry
                  becomes valid is greater than or equal to the
                  risingThreshold and alarmStartupAlarm is equal to
                  risingAlarm(1) or risingOrFallingAlarm(3), then a
                  single rising alarm will be generated.  If the first
                  sample after this entry becomes valid is less than
                  or equal to the fallingThreshold and
                  alarmStartupAlarm is equal to fallingAlarm(2) or
                  risingOrFallingAlarm(3), then a single falling
                  alarm will be generated.

                  This object may not be modified if the associated
                  alarmStatus object is equal to valid(1)."
              ::= { alarmEntry 6 }

          alarmRisingThreshold OBJECT-TYPE
              SYNTAX INTEGER
              ACCESS read-write
              STATUS mandatory
              DESCRIPTION
                  "A threshold for the sampled statistic.  When the
                  current sampled value is greater than or equal to
                  this threshold, and the value at the last sampling
                  interval was less than this threshold, a single
                  event will be generated.
                  A single event will also be generated if the first
                  sample after this entry becomes valid is greater
                  than or equal to this threshold and the associated
                  alarmStartupAlarm is equal to risingAlarm(1) or
                  risingOrFallingAlarm(3).

                  After a rising event is generated, another such event
                  will not be generated until the sampled value
                  falls below this threshold and reaches the
                  alarmFallingThreshold.

                  This object may not be modified if the associated
                  alarmStatus object is equal to valid(1)."
              ::= { alarmEntry 7 }

          alarmFallingThreshold OBJECT-TYPE
              SYNTAX INTEGER
              ACCESS read-write
              STATUS mandatory
              DESCRIPTION
                  "A threshold for the sampled statistic.  When the
                  current sampled value is less than or equal to
                  this threshold, and the value at the last sampling
                  interval was greater than this threshold, a single
                  event will be generated.
                  A single event will also be generated if the first
                  sample after this entry becomes valid is less than or
                  equal to this threshold and the associated
                  alarmStartupAlarm is equal to fallingAlarm(2) or
                  risingOrFallingAlarm(3).

                  After a falling event is generated, another such event
                  will not be generated until the sampled value
                  rises above this threshold and reaches the
                  alarmRisingThreshold.

                  This object may not be modified if the associated
                  alarmStatus object is equal to valid(1)."
              ::= { alarmEntry 8 }

          alarmRisingEventIndex OBJECT-TYPE
              SYNTAX INTEGER (0..65535)
              ACCESS read-write
              STATUS mandatory
              DESCRIPTION
                  "The index of the eventEntry that is
                  used when a rising threshold is crossed.  The
                  eventEntry identified by a particular value of
                  this index is the same as identified by the same value
                  of the eventIndex object.  If there is no
                  corresponding entry in the eventTable, then
                  no association exists.  In particular, if this value
                  is zero, no associated event will be generated, as
                  zero is not a valid event index.

                  This object may not be modified if the associated
                  alarmStatus object is equal to valid(1)."
              ::= { alarmEntry 9 }

          alarmFallingEventIndex OBJECT-TYPE
              SYNTAX INTEGER (0..65535)
              ACCESS read-write
              STATUS mandatory
              DESCRIPTION
                  "The index of the eventEntry that is
                  used when a falling threshold is crossed.  The
                  eventEntry identified by a particular value of
                  this index is the same as identified by the same value
                  of the eventIndex object.  If there is no
                  corresponding entry in the eventTable, then
                  no association exists.  In particular, if this value
                  is zero, no associated event will be generated, as
                  zero is not a valid event index.

                  This object may not be modified if the associated
                  alarmStatus object is equal to valid(1)."
              ::= { alarmEntry 10 }

          alarmOwner OBJECT-TYPE
              SYNTAX OwnerString
              ACCESS read-write
              STATUS mandatory
              DESCRIPTION
                  "The entity that configured this entry and is
                  therefore using the resources assigned to it."
              ::= { alarmEntry 11 }

          alarmStatus OBJECT-TYPE
              SYNTAX EntryStatus
              ACCESS read-write
              STATUS mandatory
              DESCRIPTION
                  "The status of this alarm entry."
              ::= { alarmEntry 12 }


          -- The Host Group

          -- Implementation of the Host group is optional.
          --
          -- The host group discovers new hosts on the network by
          -- keeping a list of source and destination MAC Addresses seen
          -- in good packets.  For each of these addresses, the host
          -- group keeps a set of statistics.  The hostControlTable
          -- controls which interfaces this function is performed on,
          -- and contains some information about the process.  On
          -- behalf of each hostControlEntry, data is collected on an
          -- interface and placed both the hostTable and the
          -- hostTimeTable.  If the monitoring device finds itself
          -- short of resources, it may delete entries as needed.  It
          -- is suggested that the device delete the least recently
          -- used entries first.

          -- The hostTable contains entries for each address
          -- discovered on a particular interface.  Each entry
          -- contains statistical data about that host.  This table
          -- is indexed by the MAC address of the host, through
          -- which a random access may be achieved.

          -- The hostTimeTable contains data in the same format as the
          -- hostTable, and must contain the same set of hosts, but is
          -- indexed using hostTimeCreationOrder rather than hostAddress.
          -- The hostTimeCreationOrder is an integer which reflects
          -- the relative order in which a particular entry was
          -- discovered and thus inserted into the table.  As this
          -- order, and thus index, is among those entries currently
          -- in the table, the index for a particular entry may change
          -- if an (earlier) entry is deleted.  Thus the association
          -- between hostTimeCreationOrder and hostTimeEntry may be
          -- broken at any time.

          -- The hostTimeTable has two important uses.  The first is the
          -- fast download of this potentially large table.  Because the
          -- index of this table runs from 1 to the size of the table,
          -- inclusive, its values are predictable.  This allows very
          -- efficient packing of variables into SNMP PDU's and allows
          -- a table transfer to have multiple packets outstanding.
          -- These benefits increase transfer rates tremendously.

          -- The second use of the hostTimeTable is the efficient
          -- discovery by the management station of new entries added
          -- to the table.  After the management station has
          -- downloaded the entire table, it knows that new entries
          -- will be added immediately after the end of the current
          -- table.  It can thus detect new entries there
          -- and retrieve them easily.

          -- Because the association between hostTimeCreationOrder and
          -- hostTimeEntry may be broken at any time, the management
          -- station must monitor the related hostControlLastDeleteTime
          -- object.  When the management station thus detects a deletion,
          -- it must assume that any such associations have been broken,
          -- and invalidate any it has stored locally.  This includes
          -- restarting any download of the hostTimeTable that may have
          -- been in progress, as well as rediscovering the end of the
          -- hostTimeTable so that it may detect new entries.  If the
          -- management station does not detect the broken association,
          -- it may continue to refer to a particular host by its
          -- creationOrder while unwittingly retrieving the data
          -- associated with another host entirely.  If this happens
          -- while downloading the host table, the management station
          -- may fail to download all of the entries in the table.

























          -- host Time Table















          -- The Host Top "N" Group

          -- Implementation of the Host Top N group is optional.
          --
          -- The Host Top N group requires the implementation of the
          -- host group.
          --
          -- The Host Top N group is used to prepare reports that
          -- describe the hosts that top a list ordered by one of
          -- their statistics.  The available statistics are samples
          -- of one of their base statistics, over an interval
          -- specified by the management station.  Thus, these
          -- statistics are rate based.  The management
          -- station also selects how many such hosts are reported.

          -- The hostTopNControlTable is used to initiate the generation
          -- of such a report.  The management station may select the
          -- parameters of such a report, such as which interface,
          -- which statistic, how many hosts, and the start and stop
          -- times of the sampling.  When the report is prepared,
          -- entries are created in the hostTopNTable associated with
          -- the relevant hostTopNControlEntry.  These entries are
          -- static for each report after it has been prepared.






















          -- The Matrix Group

          -- Implementation of the Matrix group is optional.
          --
          -- The Matrix group consists of the matrixControlTable,
          -- matrixSDTable and the matrixDSTable.  These tables
          -- store statistics for a particular conversation between
          -- two addresses.  As the device detects a new conversation,
          -- including those to a non-unicast address, it creates a
          -- new entry in both of the matrix tables.
          -- It must only create new entries based on information
          -- received in good packets.  If the monitoring device finds
          -- itself short of resources, it may delete entries as needed.
          -- It is suggested that the device delete the least recently
          -- used entries first.




















          -- Traffic matrix tables from destination to source











          -- The Filter Group

          -- Implementation of the Filter group is optional.
          --
          -- The Filter group allows packets to be captured with an
          -- arbitrary filter expression.  A logical data and
          -- event stream or "channel" is formed by the packets
          -- that match the filter expression.
          --
          -- This filter mechanism allows the creation of an arbitrary
          -- logical expression with which to filter packets.  Each
          -- filter associated with a channel is OR'ed with the others.
          -- Within a filter, any bits checked in the data and status are
          -- AND'ed with respect to other bits in the same filter.  The
          -- NotMask also allows for checking for inequality.  Finally,
          -- the channelAcceptType object allows for inversion of the
          -- whole equation.
          --
          -- The channel can be turned on or off, and can also
          -- generate events when packets pass through it.































          -- The Packet Capture Group

          -- Implementation of the Packet Capture group is optional.
          --
          -- The Packet Capture Group requires implementation of the
          -- Filter Group.
          --
          -- The Packet Capture group allows packets to be captured
          -- upon a filter match.  The bufferControlTable controls
          -- the captured packets output from a channel that is
          -- associated with it.  The captured packets are placed
          -- in entries in the captureBufferTable.  These entries are
          -- associated with the bufferControlEntry on whose behalf they
          -- were stored.




























          -- The Event Group

          -- Implementation of the Event group is optional.
          --
          -- The Event group controls the generation and notification
          -- of events from this device.  Each entry in the eventTable
          -- describes the parameters of the event that can be triggered.
          -- Each event entry is fired by an associated condition located
          -- elsewhere in the MIB.  An event entry may also be associated
          -- with a function elsewhere in the MIB that will be executed
          -- when the event is generated.  For example, a channel may
          -- be turned on or off by the firing of an event.
          --
          -- Each eventEntry may optionally specify that a log entry
          -- be created on its behalf whenever the event occurs.
          -- Each entry may also specify that notification should
          -- occur by way of SNMP trap messages.  In this case, the
          -- community for the trap message is given in the associated
          -- eventCommunity object.  The enterprise and specific trap
          -- fields of the trap are determined by the condition that
          -- triggered the event.  Three traps are defined in a companion
          -- document: risingAlarm, fallingAlarm, and packetMatch.
          -- If the eventTable is triggered by a condition specified
          -- elsewhere, the enterprise and specific trap fields
          -- must be specified for traps generated for that condition.

          eventTable OBJECT-TYPE
              SYNTAX SEQUENCE OF EventEntry
              ACCESS not-accessible
              STATUS mandatory
              DESCRIPTION
                  "A list of events to be generated."
              ::= { event 1 }

          eventEntry OBJECT-TYPE
              SYNTAX EventEntry
              ACCESS not-accessible
              STATUS mandatory
              DESCRIPTION
                  "A set of parameters that describe an event to be
                  generated when certain conditions are met."
              INDEX { eventIndex }
              ::= { eventTable 1 }

          EventEntry ::= SEQUENCE {
              eventIndex          INTEGER (1..65535),
              eventDescription    DisplayString (SIZE (0..127)),
              eventType           INTEGER,
              eventCommunity      OCTET STRING (SIZE (0..127)),
              eventLastTimeSent   TimeTicks,
              eventOwner          OwnerString,
              eventStatus         EntryStatus
          }

          eventIndex OBJECT-TYPE
              SYNTAX INTEGER (1..65535)
              ACCESS read-only
              STATUS mandatory
              DESCRIPTION
                  "An index that uniquely identifies an entry in the
                  event table.  Each such entry defines one event that
                  is to be generated when the appropriate conditions
                  occur."
              ::= { eventEntry 1 }

          eventDescription OBJECT-TYPE
              SYNTAX DisplayString (SIZE (0..127))
              ACCESS read-write
              STATUS mandatory
              DESCRIPTION
                  "A comment describing this event entry."
              ::= { eventEntry 2 }

          eventType OBJECT-TYPE
              SYNTAX INTEGER {
                      none(1),
                      log(2),
                      snmp-trap(3),    -- send an SNMP trap
                      log-and-trap(4)
              }
              ACCESS read-write
              STATUS mandatory
              DESCRIPTION
                  "The type of notification that the probe will make
                  about this event.  In the case of log, an entry is
                  made in the log table for each event.  In the case of
                  snmp-trap, an SNMP trap is sent to one or more
                  management stations."
              ::= { eventEntry 3 }

          eventCommunity OBJECT-TYPE
              SYNTAX OCTET STRING (SIZE (0..127))
              ACCESS read-write
              STATUS mandatory
              DESCRIPTION
                  "If an SNMP trap is to be sent, it will be sent to
                  the SNMP community specified by this octet string.
                  In the future this table will be extended to include
                  the party security mechanism.  This object shall be
                  set to a string of length zero if it is intended that
                  that mechanism be used to specify the destination of
                  the trap."
              ::= { eventEntry 4 }

          eventLastTimeSent OBJECT-TYPE
              SYNTAX TimeTicks
              ACCESS read-only
              STATUS mandatory
              DESCRIPTION
                  "The value of sysUpTime at the time this event
                  entry last generated an event.  If this entry has
                  not generated any events, this value will be
                  zero."
              ::= { eventEntry 5 }

          eventOwner OBJECT-TYPE
              SYNTAX OwnerString
              ACCESS read-write
              STATUS mandatory
              DESCRIPTION
                  "The entity that configured this entry and is therefore
                  using the resources assigned to it.

                  If this object contains a string starting with 'monitor'
                  and has associated entries in the log table, all
                  connected management stations should retrieve those
                  log entries, as they may have significance to all
                  management stations connected to this device"
              ::= { eventEntry 6 }

          eventStatus OBJECT-TYPE
              SYNTAX EntryStatus
              ACCESS read-write
              STATUS mandatory
              DESCRIPTION
                  "The status of this event entry.

                  If this object is not equal to valid(1), all associated
                  log entries shall be deleted by the agent."
              ::= { eventEntry 7 }

          --
          logTable OBJECT-TYPE
              SYNTAX SEQUENCE OF LogEntry
              ACCESS not-accessible
              STATUS mandatory
              DESCRIPTION
                  "A list of events that have been logged."
              ::= { event 2 }

          logEntry OBJECT-TYPE
              SYNTAX LogEntry
              ACCESS not-accessible
              STATUS mandatory
              DESCRIPTION
                  "A set of data describing an event that has been
                  logged."
              INDEX { logEventIndex, logIndex }
              ::= { logTable 1 }

          LogEntry ::= SEQUENCE {
              logEventIndex           INTEGER (1..65535),
              logIndex                INTEGER,
              logTime                 TimeTicks,
              logDescription          DisplayString (SIZE (0..255))
          }

          logEventIndex OBJECT-TYPE
              SYNTAX INTEGER (1..65535)
              ACCESS read-only
              STATUS mandatory
              DESCRIPTION
                  "The event entry that generated this log
                  entry.  The log identified by a particular
                  value of this index is associated with the same
                  eventEntry as identified by the same value
                  of eventIndex."
              ::= { logEntry 1 }

          logIndex OBJECT-TYPE
              SYNTAX INTEGER
              ACCESS read-only
              STATUS mandatory
              DESCRIPTION
                  "An index that uniquely identifies an entry
                  in the log table amongst those generated by the
                  same eventEntries.  These indexes are
                  assigned beginning with 1 and increase by one
                  with each new log entry.  The association
                  between values of logIndex and logEntries
                  is fixed for the lifetime of each logEntry.
                  The agent may choose to delete the oldest
                  instances of logEntry as required because of
                  lack of memory.  It is an implementation-specific
                  matter as to when this deletion may occur."
              ::= { logEntry 2 }

          logTime OBJECT-TYPE
              SYNTAX TimeTicks
              ACCESS read-only
              STATUS mandatory
              DESCRIPTION
                  "The value of sysUpTime when this log entry was
                  created."
              ::= { logEntry 3 }

          logDescription OBJECT-TYPE
              SYNTAX DisplayString (SIZE (0..255))
              ACCESS read-only
              STATUS mandatory
              DESCRIPTION
                  "An implementation dependent description of the
                  event that activated this log entry."
              ::= { logEntry 4 }

          --  These definitions use the TRAP-TYPE macro as defined in [10]

          --  Remote Network Monitoring Traps

          risingAlarm TRAP-TYPE
              ENTERPRISE rmon
              VARIABLES {  alarmIndex, alarmVariable, alarmSampleType,
                          alarmValue, alarmRisingThreshold }
              DESCRIPTION
                  "The SNMP trap that is generated when an alarm
                  entry crosses its rising threshold and generates
                  an event that is configured for sending SNMP
                  traps."
              ::= 1

          fallingAlarm TRAP-TYPE
              ENTERPRISE rmon
              VARIABLES {  alarmIndex, alarmVariable, alarmSampleType,
                          alarmValue, alarmFallingThreshold }
              DESCRIPTION
                  "The SNMP trap that is generated when an alarm
                  entry crosses its falling threshold and generates
                  an event that is configured for sending SNMP
                  traps."
              ::= 2


--
-- FILE: /users/sse/mibs/src/rfc/rfc1493.mib
--



          -- All representations of MAC addresses in this MIB Module
          -- use, as a textual convention (i.e. this convention does
          -- not affect their encoding), the data type:

          MacAddress ::= OCTET STRING (SIZE (6))    -- a 6 octet address
                                                    -- in the
                                                    -- "canonical"
                                                    -- order
          -- defined by IEEE 802.1a, i.e., as if it were transmitted
          -- least significant bit first, even though 802.5 (in
          -- contrast to other n802.x protocols) requires MAC
          -- addresses to be transmitted most significant bit first.
          --
          -- 16-bit addresses, if needed, are represented by setting
          -- their upper 4 octets to all 0's, i.e., AAFF would be
          -- represented as 00000000AAFF.


          -- Similarly, all representations of Bridge-Id in this MIB
          -- Module use, as a textual convention (i.e. this
          -- convention does not affect their encoding), the data
          -- type:

          BridgeId ::= OCTET STRING (SIZE (8))   -- the
                                                 -- Bridge-Identifier
                                                 -- as used in the
                                                 -- Spanning Tree
          -- Protocol to uniquely identify a bridge.  Its first two
          -- octets (in network byte order) contain a priority
          -- value and its last 6 octets contain the MAC address
          -- used to refer to a bridge in a unique fashion
          -- (typically, the numerically smallest MAC address
          -- of all ports on the bridge).
          -- Several objects in this MIB module represent values of
          -- timers used by the Spanning Tree Protocol.  In this
          -- MIB, these timers have values in units of hundreths of
          -- a second (i.e. 1/100 secs).
          -- These timers, when stored in a Spanning Tree Protocol's
          -- BPDU, are in units of 1/256 seconds.  Note, however,
          -- that 802.1D-1990 specifies a settable granularity of
          -- no more than 1 second for these timers.  To avoid
          -- ambiguity, a data type is defined here as a textual
          -- convention and all representation of these timers
          -- in this MIB module are defined using this data type.  An
          -- algorithm is also defined for converting between the
          -- different units, to ensure a timer's value is not
          -- distorted by multiple conversions.
          -- The data type is:

          Timeout ::= INTEGER -- a STP timer in units of 1/100 seconds

          -- To convert a Timeout value into a value in units of
          -- 1/256 seconds, the following algorithm should be used:
          --
          --      b  = floor( (n * 256) / 100)
          --
          -- where:
          --      floor   =  quotient [ignore remainder]
          --      n is the value in 1/100 second units
          --      b is the value in 1/256 second units
          --
          -- To convert the value from 1/256 second units back to
          -- 1/100 seconds, the following algorithm should be used:
          --
          --      n = ceiling( (b * 100) / 256)
          --
          -- where:
          --      ceiling =  quotient [if remainder is 0], or
          --                 quotient + 1 [if remainder is non-zero]
          --      n is the value in 1/100 second units
          --      b is the value in 1/256 second units
          --
          -- Note: it is important that the arithmetic operations are
          -- done in the order specified (i.e., multiply first, divide
          -- second).


             dot1dBridge   OBJECT IDENTIFIER ::= { mib-2 17 }

          -- groups in the Bridge MIB

          dot1dBase     OBJECT IDENTIFIER ::= { dot1dBridge 1 }

          dot1dStp      OBJECT IDENTIFIER ::= { dot1dBridge 2 }

          dot1dSr       OBJECT IDENTIFIER ::= { dot1dBridge 3 }
          -- separately documented

          dot1dTp       OBJECT IDENTIFIER ::= { dot1dBridge 4 }

          dot1dStatic   OBJECT IDENTIFIER ::= { dot1dBridge 5 }


          -- the dot1dBase group

          -- Implementation of the dot1dBase group is mandatory for all
          -- bridges.

          dot1dBaseBridgeAddress OBJECT-TYPE
              SYNTAX  MacAddress
              ACCESS  read-only
              STATUS  mandatory
              DESCRIPTION
                      "The MAC address used by this bridge when it must
                      be referred to in a unique fashion.   It is
                      recommended that this be the numerically smallest
                      MAC address of all ports that belong to this
                      bridge.  However it is only required to be unique.
                      When concatenated with dot1dStpPriority a unique
                      BridgeIdentifier is formed which is used in the
                      Spanning Tree Protocol."
              REFERENCE
                      "IEEE 802.1D-1990: Sections 6.4.1.1.3 and 3.12.5"
              ::= { dot1dBase 1 }

          dot1dBaseNumPorts OBJECT-TYPE
              SYNTAX  INTEGER
              ACCESS  read-only
              STATUS  mandatory
              DESCRIPTION
                      "The number of ports controlled by this bridging
                      entity."
              REFERENCE
                      "IEEE 802.1D-1990: Section 6.4.1.1.3"
              ::= { dot1dBase 2 }

          dot1dBaseType OBJECT-TYPE
              SYNTAX  INTEGER {
                          unknown(1),
                          transparent-only(2),
                          sourceroute-only(3),
                          srt(4)
                      }
              ACCESS  read-only
              STATUS  mandatory
              DESCRIPTION
                      "Indicates what type of bridging this bridge can
                      perform.  If a bridge is actually performing a
                      certain type of bridging this will be indicated by
                      entries in the port table for the given type."
              ::= { dot1dBase 3 }

          -- The Generic Bridge Port Table

          dot1dBasePortTable OBJECT-TYPE
              SYNTAX  SEQUENCE OF Dot1dBasePortEntry
              ACCESS  not-accessible
              STATUS  mandatory
              DESCRIPTION
                      "A table that contains generic information about
                      every port that is associated with this bridge.
                      Transparent, source-route, and srt ports are
                      included."
              ::= { dot1dBase 4 }

          dot1dBasePortEntry OBJECT-TYPE
              SYNTAX  Dot1dBasePortEntry
              ACCESS  not-accessible
              STATUS  mandatory
              DESCRIPTION
                      "A list of information for each port of the
                      bridge."
              REFERENCE
                      "IEEE 802.1D-1990: Section 6.4.2, 6.6.1"
              INDEX  { dot1dBasePort }
              ::= { dot1dBasePortTable 1 }


          Dot1dBasePortEntry ::=
              SEQUENCE {
                  dot1dBasePort
                      INTEGER,
                  dot1dBasePortIfIndex
                      INTEGER,
                  dot1dBasePortCircuit
                      OBJECT IDENTIFIER,
                  dot1dBasePortDelayExceededDiscards
                      Counter,
                  dot1dBasePortMtuExceededDiscards
                      Counter
              }

          dot1dBasePort OBJECT-TYPE
              SYNTAX  INTEGER (1..65535)
              ACCESS  read-only
              STATUS  mandatory
              DESCRIPTION
                      "The port number of the port for which this entry
                      contains bridge management information."
              ::= { dot1dBasePortEntry 1 }

          dot1dBasePortIfIndex OBJECT-TYPE
              SYNTAX  INTEGER
              ACCESS  read-only
              STATUS  mandatory
              DESCRIPTION
                      "The value of the instance of the ifIndex object,
                      defined in MIB-II, for the interface corresponding
                      to this port."
              ::= { dot1dBasePortEntry 2 }

          dot1dBasePortCircuit OBJECT-TYPE
              SYNTAX  OBJECT IDENTIFIER
              ACCESS  read-only
              STATUS  mandatory
              DESCRIPTION
                      "For a port which (potentially) has the same value
                      of dot1dBasePortIfIndex as another port on the
                      same bridge, this object contains the name of an
                      object instance unique to this port.  For example,
                      in the case where multiple ports correspond one-
                      to-one with multiple X.25 virtual circuits, this
                      value might identify an (e.g., the first) object
                      instance associated with the X.25 virtual circuit
                      corresponding to this port.

                      For a port which has a unique value of
                      dot1dBasePortIfIndex, this object can have the
                      value { 0 0 }."
              ::= { dot1dBasePortEntry 3 }

          dot1dBasePortDelayExceededDiscards OBJECT-TYPE
              SYNTAX  Counter
              ACCESS  read-only
              STATUS  mandatory
              DESCRIPTION
                      "The number of frames discarded by this port due
                      to excessive transit delay through the bridge.  It
                      is incremented by both transparent and source
                      route bridges."
              REFERENCE
                       "IEEE 802.1D-1990: Section 6.6.1.1.3"
              ::= { dot1dBasePortEntry 4 }

          dot1dBasePortMtuExceededDiscards OBJECT-TYPE
              SYNTAX  Counter
              ACCESS  read-only
              STATUS  mandatory
              DESCRIPTION
                      "The number of frames discarded by this port due
                      to an excessive size.  It is incremented by both
                      transparent and source route bridges."
              REFERENCE
                      "IEEE 802.1D-1990: Section 6.6.1.1.3"
              ::= { dot1dBasePortEntry 5 }


          -- the dot1dStp group

          -- Implementation of the dot1dStp group is optional.  It is
          -- implemented by those bridges that support the Spanning Tree
          -- Protocol.


          dot1dStpProtocolSpecification OBJECT-TYPE
              SYNTAX  INTEGER {
                          unknown(1),
                          decLb100(2),
                          ieee8021d(3)
                      }
              ACCESS  read-only
              STATUS  mandatory
              DESCRIPTION
                      "An indication of what version of the Spanning
                      Tree Protocol is being run.  The value
                      'decLb100(2)' indicates the DEC LANbridge 100
                      Spanning Tree protocol.  IEEE 802.1d
                      implementations will return 'ieee8021d(3)'.  If
                      future versions of the IEEE Spanning Tree Protocol
                      are released that are incompatible with the
                      current version a new value will be defined."
              ::= { dot1dStp 1 }

          dot1dStpPriority OBJECT-TYPE
              SYNTAX  INTEGER (0..65535)
              ACCESS  read-write
              STATUS  mandatory
              DESCRIPTION
                      "The value of the write-able portion of the Bridge
                      ID, i.e., the first two octets of the (8 octet
                      long) Bridge ID.  The other (last) 6 octets of the
                      Bridge ID are given by the value of
                      dot1dBaseBridgeAddress."
              REFERENCE
                      "IEEE 802.1D-1990: Section 4.5.3.7"
              ::= { dot1dStp 2 }

          dot1dStpTimeSinceTopologyChange OBJECT-TYPE
              SYNTAX  TimeTicks
              ACCESS  read-only
              STATUS  mandatory
              DESCRIPTION
                      "The time (in hundredths of a second) since the
                      last time a topology change was detected by the
                      bridge entity."
              REFERENCE
                      "IEEE 802.1D-1990: Section 6.8.1.1.3"
              ::= { dot1dStp 3 }

          dot1dStpTopChanges OBJECT-TYPE
              SYNTAX  Counter
              ACCESS  read-only
              STATUS  mandatory
              DESCRIPTION
                      "The total number of topology changes detected by
                      this bridge since the management entity was last
                      reset or initialized."
              REFERENCE
                      "IEEE 802.1D-1990: Section 6.8.1.1.3"
              ::= { dot1dStp 4 }

          dot1dStpDesignatedRoot OBJECT-TYPE
              SYNTAX  BridgeId
              ACCESS  read-only
              STATUS  mandatory
              DESCRIPTION
                      "The bridge identifier of the root of the spanning
                      tree as determined by the Spanning Tree Protocol
                      as executed by this node.  This value is used as
                      the Root Identifier parameter in all Configuration
                      Bridge PDUs originated by this node."
              REFERENCE
                      "IEEE 802.1D-1990: Section 4.5.3.1"
              ::= { dot1dStp 5 }

          dot1dStpRootCost OBJECT-TYPE
              SYNTAX  INTEGER
              ACCESS  read-only
              STATUS  mandatory
              DESCRIPTION
                      "The cost of the path to the root as seen from
                      this bridge."
              REFERENCE
                      "IEEE 802.1D-1990: Section 4.5.3.2"
              ::= { dot1dStp 6 }

          dot1dStpRootPort OBJECT-TYPE
              SYNTAX  INTEGER
              ACCESS  read-only
              STATUS  mandatory
              DESCRIPTION
                      "The port number of the port which offers the
                      lowest cost path from this bridge to the root
                      bridge."
              REFERENCE
                      "IEEE 802.1D-1990: Section 4.5.3.3"
              ::= { dot1dStp 7 }

          dot1dStpMaxAge OBJECT-TYPE
              SYNTAX  Timeout
              ACCESS  read-only
              STATUS  mandatory
              DESCRIPTION
                      "The maximum age of Spanning Tree Protocol
                      information learned from the network on any port
                      before it is discarded, in units of hundredths of
                      a second.  This is the actual value that this
                      bridge is currently using."
              REFERENCE
                      "IEEE 802.1D-1990: Section 4.5.3.4"
              ::= { dot1dStp 8 }

          dot1dStpHelloTime OBJECT-TYPE
              SYNTAX  Timeout
              ACCESS  read-only
              STATUS  mandatory
              DESCRIPTION
                      "The amount of time between the transmission of
                      Configuration bridge PDUs by this node on any port
                      when it is the root of the spanning tree or trying
                      to become so, in units of hundredths of a second.
                      This is the actual value that this bridge is
                      currently using."
              REFERENCE
                      "IEEE 802.1D-1990: Section 4.5.3.5"
              ::= { dot1dStp 9 }

          dot1dStpHoldTime OBJECT-TYPE
              SYNTAX  INTEGER
              ACCESS  read-only
              STATUS  mandatory
              DESCRIPTION
                      "This time value determines the interval length
                      during which no more than two Configuration bridge
                      PDUs shall be transmitted by this node, in units
                      of hundredths of a second."
              REFERENCE
                      "IEEE 802.1D-1990: Section 4.5.3.14"
              ::= { dot1dStp 10 }

          dot1dStpForwardDelay OBJECT-TYPE
              SYNTAX  Timeout
              ACCESS  read-only
              STATUS  mandatory
              DESCRIPTION
                      "This time value, measured in units of hundredths
                      of a second, controls how fast a port changes its
                      spanning state when moving towards the Forwarding
                      state.  The value determines how long the port
                      stays in each of the Listening and Learning
                      states, which precede the Forwarding state.  This
                      value is also used, when a topology change has
                      been detected and is underway, to age all dynamic
                      entries in the Forwarding Database.  [Note that
                      this value is the one that this bridge is
                      currently using, in contrast to
                      dot1dStpBridgeForwardDelay which is the value that
                      this bridge and all others would start using
                      if/when this bridge were to become the root.]"
              REFERENCE
                      "IEEE 802.1D-1990: Section 4.5.3.6"
              ::= { dot1dStp 11 }

          dot1dStpBridgeMaxAge OBJECT-TYPE
              SYNTAX  Timeout (600..4000)
              ACCESS  read-write
              STATUS  mandatory
              DESCRIPTION
                      "The value that all bridges use for MaxAge when
                      this bridge is acting as the root.  Note that
                      802.1D-1990 specifies that the range for this
                      parameter is related to the value of
                      dot1dStpBridgeHelloTime. The granularity of this
                      timer is specified by 802.1D-1990 to be 1 second.
                      An agent may return a badValue error if a set is
                      attempted to a value which is not a whole number
                      of seconds."
              REFERENCE
                      "IEEE 802.1D-1990: Section 4.5.3.8"
              ::= { dot1dStp 12 }

          dot1dStpBridgeHelloTime OBJECT-TYPE
              SYNTAX  Timeout (100..1000)
              ACCESS  read-write
              STATUS  mandatory
              DESCRIPTION
                      "The value that all bridges use for HelloTime when
                      this bridge is acting as the root.  The
                      granularity of this timer is specified by 802.1D-
                      1990 to be 1 second.  An agent may return a
                      badValue error if a set is attempted to a value
                      which is not a whole number of seconds."
              REFERENCE
                      "IEEE 802.1D-1990: Section 4.5.3.9"
              ::= { dot1dStp 13 }

          dot1dStpBridgeForwardDelay OBJECT-TYPE
              SYNTAX  Timeout (400..3000)
              ACCESS  read-write
              STATUS  mandatory
              DESCRIPTION
                      "The value that all bridges use for ForwardDelay
                      when this bridge is acting as the root.  Note that
                      802.1D-1990 specifies that the range for this
                      parameter is related to the value of
                      dot1dStpBridgeMaxAge.  The granularity of this
                      timer is specified by 802.1D-1990 to be 1 second.
                      An agent may return a badValue error if a set is
                      attempted to a value which is not a whole number
                      of seconds."
              REFERENCE
                      "IEEE 802.1D-1990: Section 4.5.3.10"
              ::= { dot1dStp 14 }

          -- The Spanning Tree Port Table

          dot1dStpPortTable OBJECT-TYPE
              SYNTAX  SEQUENCE OF Dot1dStpPortEntry
              ACCESS  not-accessible
              STATUS  mandatory
              DESCRIPTION
                      "A table that contains port-specific information
                      for the Spanning Tree Protocol."
              ::= { dot1dStp 15 }

          dot1dStpPortEntry OBJECT-TYPE
              SYNTAX  Dot1dStpPortEntry
              ACCESS  not-accessible
              STATUS  mandatory
              DESCRIPTION
                      "A list of information maintained by every port
                      about the Spanning Tree Protocol state for that
                      port."
              INDEX   { dot1dStpPort }
              ::= { dot1dStpPortTable 1 }

          Dot1dStpPortEntry ::=
              SEQUENCE {
                  dot1dStpPort
                      INTEGER,
                  dot1dStpPortPriority
                      INTEGER,
                  dot1dStpPortState
                      INTEGER,
                  dot1dStpPortEnable
                      INTEGER,
                  dot1dStpPortPathCost
                      INTEGER,
                  dot1dStpPortDesignatedRoot
                      BridgeId,
                  dot1dStpPortDesignatedCost
                      INTEGER,
                  dot1dStpPortDesignatedBridge
                      BridgeId,
                  dot1dStpPortDesignatedPort
                      OCTET STRING,
                  dot1dStpPortForwardTransitions
                      Counter
              }

          dot1dStpPort OBJECT-TYPE
              SYNTAX  INTEGER (1..65535)
              ACCESS  read-only
              STATUS  mandatory
              DESCRIPTION
                      "The port number of the port for which this entry
                      contains Spanning Tree Protocol management
                      information."
              REFERENCE
                      "IEEE 802.1D-1990: Section 6.8.2.1.2"
              ::= { dot1dStpPortEntry 1 }

          dot1dStpPortPriority OBJECT-TYPE
              SYNTAX  INTEGER (0..255)
              ACCESS  read-write
              STATUS  mandatory
              DESCRIPTION
                      "The value of the priority field which is
                      contained in the first (in network byte order)
                      octet of the (2 octet long) Port ID.  The other
                      octet of the Port ID is given by the value of
                      dot1dStpPort."
              REFERENCE
                      "IEEE 802.1D-1990: Section 4.5.5.1"
              ::= { dot1dStpPortEntry 2 }

          dot1dStpPortState OBJECT-TYPE
              SYNTAX  INTEGER {
                          disabled(1),
                          blocking(2),
                          listening(3),
                          learning(4),
                          forwarding(5),
                          broken(6)
                      }
              ACCESS  read-only
              STATUS  mandatory
              DESCRIPTION
                      "The port's current state as defined by
                      application of the Spanning Tree Protocol.  This
                      state controls what action a port takes on
                      reception of a frame.  If the bridge has detected
                      a port that is malfunctioning it will place that
                      port into the broken(6) state.  For ports which
                      are disabled (see dot1dStpPortEnable), this object
                      will have a value of disabled(1)."
              REFERENCE
                      "IEEE 802.1D-1990: Section 4.5.5.2"
              ::= { dot1dStpPortEntry 3 }

          dot1dStpPortEnable OBJECT-TYPE
              SYNTAX  INTEGER {
                          enabled(1),
                          disabled(2)
                      }
              ACCESS  read-write
              STATUS  mandatory
              DESCRIPTION
                      "The enabled/disabled status of the port."
              REFERENCE
                      "IEEE 802.1D-1990: Section 4.5.5.2"
              ::= { dot1dStpPortEntry 4 }

          dot1dStpPortPathCost OBJECT-TYPE
              SYNTAX  INTEGER (1..65535)
              ACCESS  read-write
              STATUS  mandatory
              DESCRIPTION
                      "The contribution of this port to the path cost of
                      paths towards the spanning tree root which include
                      this port.  802.1D-1990 recommends that the
                      default value of this parameter be in inverse
                      proportion to the speed of the attached LAN."
              REFERENCE
                      "IEEE 802.1D-1990: Section 4.5.5.3"
              ::= { dot1dStpPortEntry 5 }

          dot1dStpPortDesignatedRoot OBJECT-TYPE
              SYNTAX  BridgeId
              ACCESS  read-only
              STATUS  mandatory
              DESCRIPTION
                      "The unique Bridge Identifier of the Bridge
                      recorded as the Root in the Configuration BPDUs
                      transmitted by the Designated Bridge for the
                      segment to which the port is attached."
              REFERENCE
                      "IEEE 802.1D-1990: Section 4.5.5.4"
              ::= { dot1dStpPortEntry 6 }

          dot1dStpPortDesignatedCost OBJECT-TYPE
              SYNTAX  INTEGER
              ACCESS  read-only
              STATUS  mandatory
              DESCRIPTION
                      "The path cost of the Designated Port of the
                      segment connected to this port.  This value is
                      compared to the Root Path Cost field in received
                      bridge PDUs."
              REFERENCE
                      "IEEE 802.1D-1990: Section 4.5.5.5"
              ::= { dot1dStpPortEntry 7 }

          dot1dStpPortDesignatedBridge OBJECT-TYPE
              SYNTAX  BridgeId
              ACCESS  read-only
              STATUS  mandatory
              DESCRIPTION
                      "The Bridge Identifier of the bridge which this
                      port considers to be the Designated Bridge for
                      this port's segment."
              REFERENCE
                      "IEEE 802.1D-1990: Section 4.5.5.6"
              ::= { dot1dStpPortEntry 8 }

          dot1dStpPortDesignatedPort OBJECT-TYPE
              SYNTAX  OCTET STRING (SIZE (2))
              ACCESS  read-only
              STATUS  mandatory
              DESCRIPTION
                      "The Port Identifier of the port on the Designated
                      Bridge for this port's segment."
              REFERENCE
                      "IEEE 802.1D-1990: Section 4.5.5.7"
              ::= { dot1dStpPortEntry 9 }

          dot1dStpPortForwardTransitions OBJECT-TYPE
              SYNTAX  Counter
              ACCESS  read-only
              STATUS  mandatory
              DESCRIPTION
                      "The number of times this port has transitioned
                      from the Learning state to the Forwarding state."
              ::= { dot1dStpPortEntry 10 }


          -- the dot1dTp group

          -- Implementation of the dot1dTp group is optional.  It is
          -- implemented by those bridges that support the transparent
          -- bridging mode.  A transparent or SRT bridge will implement
          -- this group.


          dot1dTpLearnedEntryDiscards OBJECT-TYPE
              SYNTAX  Counter
              ACCESS  read-only
              STATUS  mandatory
              DESCRIPTION
                      "The total number of Forwarding Database entries,
                      which have been or would have been learnt, but
                      have been discarded due to a lack of space to
                      store them in the Forwarding Database.  If this
                      counter is increasing, it indicates that the
                      Forwarding Database is regularly becoming full (a
                      condition which has unpleasant performance effects
                      on the subnetwork).  If this counter has a
                      significant value but is not presently increasing,
                      it indicates that the problem has been occurring
                      but is not persistent."
              REFERENCE
                      "IEEE 802.1D-1990: Section 6.7.1.1.3"
              ::= { dot1dTp 1 }

          dot1dTpAgingTime OBJECT-TYPE
              SYNTAX   INTEGER (10..1000000)
              ACCESS   read-write
              STATUS   mandatory
              DESCRIPTION
                      "The timeout period in seconds for aging out
                      dynamically learned forwarding information.
                      802.1D-1990 recommends a default of 300 seconds."
              REFERENCE
                      "IEEE 802.1D-1990: Section 6.7.1.1.3"
              ::= { dot1dTp 2 }


          --  The Forwarding Database for Transparent Bridges

          dot1dTpFdbTable OBJECT-TYPE
              SYNTAX  SEQUENCE OF Dot1dTpFdbEntry
              ACCESS  not-accessible
              STATUS  mandatory
              DESCRIPTION
                      "A table that contains information about unicast
                      entries for which the bridge has forwarding and/or
                      filtering information.  This information is used
                      by the transparent bridging function in
                      determining how to propagate a received frame."
              ::= { dot1dTp 3 }

          dot1dTpFdbEntry OBJECT-TYPE
              SYNTAX  Dot1dTpFdbEntry
              ACCESS  not-accessible
              STATUS  mandatory
              DESCRIPTION
                      "Information about a specific unicast MAC address
                      for which the bridge has some forwarding and/or
                      filtering information."
              INDEX   { dot1dTpFdbAddress }
              ::= { dot1dTpFdbTable 1 }

          Dot1dTpFdbEntry ::=
              SEQUENCE {
                  dot1dTpFdbAddress
                      MacAddress,
                  dot1dTpFdbPort
                      INTEGER,
                  dot1dTpFdbStatus
                      INTEGER
              }

          dot1dTpFdbAddress OBJECT-TYPE
              SYNTAX  MacAddress
              ACCESS  read-only
              STATUS  mandatory
              DESCRIPTION
                      "A unicast MAC address for which the bridge has
                      forwarding and/or filtering information."
              REFERENCE
                      "IEEE 802.1D-1990: Section 3.9.1, 3.9.2"
              ::= { dot1dTpFdbEntry 1 }

          dot1dTpFdbPort OBJECT-TYPE
              SYNTAX  INTEGER
              ACCESS  read-only
              STATUS  mandatory
              DESCRIPTION
                      "Either the value '0', or the port number of the
                      port on which a frame having a source address
                      equal to the value of the corresponding instance
                      of dot1dTpFdbAddress has been seen.  A value of
                      '0' indicates that the port number has not been
                      learned but that the bridge does have some
                      forwarding/filtering information about this
                      address (e.g. in the dot1dStaticTable).
                      Implementors are encouraged to assign the port
                      value to this object whenever it is learned even
                      for addresses for which the corresponding value of
                      dot1dTpFdbStatus is not learned(3)."
              ::= { dot1dTpFdbEntry 2 }

          dot1dTpFdbStatus OBJECT-TYPE
              SYNTAX  INTEGER {
                          other(1),
                          invalid(2),
                          learned(3),
                          self(4),
                          mgmt(5)
                      }
              ACCESS  read-only
              STATUS  mandatory
              DESCRIPTION
                      "The status of this entry.  The meanings of the
                      values are:

                        other(1)   : none of the following.  This would
                                     include the case where some other
                                     MIB object (not the corresponding
                                     instance of dot1dTpFdbPort, nor an
                                     entry in the dot1dStaticTable) is
                                     being used to determine if and how
                                     frames addressed to the value of
                                     the corresponding instance of
                                     dot1dTpFdbAddress are being
                                     forwarded.

                        invalid(2) : this entry is not longer valid
                                     (e.g., it was learned but has since
                                     aged-out), but has not yet been
                                     flushed from the table.

                        learned(3) : the value of the corresponding
                                     instance of dot1dTpFdbPort was
                                     learned, and is being used.

                        self(4)    : the value of the corresponding
                                     instance of dot1dTpFdbAddress
                                     represents one of the bridge's
                                     addresses.  The corresponding
                                     instance of dot1dTpFdbPort
                                     indicates which of the bridge's
                                     ports has this address.

                        mgmt(5)    : the value of the corresponding
                                     instance of dot1dTpFdbAddress is
                                     also the value of an existing
                                     instance of dot1dStaticAddress."
              ::= { dot1dTpFdbEntry 3 }

          --  Port Table for Transparent Bridges

          dot1dTpPortTable OBJECT-TYPE
              SYNTAX  SEQUENCE OF Dot1dTpPortEntry
              ACCESS  not-accessible
              STATUS  mandatory
              DESCRIPTION
                      "A table that contains information about every
                      port that is associated with this transparent
                      bridge."
              ::= { dot1dTp 4 }

          dot1dTpPortEntry OBJECT-TYPE
              SYNTAX  Dot1dTpPortEntry
              ACCESS  not-accessible
              STATUS  mandatory
              DESCRIPTION
                      "A list of information for each port of a
                      transparent bridge."
              INDEX   { dot1dTpPort }
              ::= { dot1dTpPortTable 1 }

          Dot1dTpPortEntry ::=
              SEQUENCE {
                  dot1dTpPort
                      INTEGER,
                  dot1dTpPortMaxInfo
                      INTEGER,
                  dot1dTpPortInFrames
                      Counter,
                  dot1dTpPortOutFrames
                      Counter,
                  dot1dTpPortInDiscards
                      Counter
              }

          dot1dTpPort OBJECT-TYPE
              SYNTAX  INTEGER (1..65535)
              ACCESS  read-only
              STATUS  mandatory
              DESCRIPTION
                      "The port number of the port for which this entry
                      contains Transparent bridging management
                      information."
              ::= { dot1dTpPortEntry 1 }

          -- It would be nice if we could use ifMtu as the size of the
          -- largest INFO field, but we can't because ifMtu is defined
          -- to be the size that the (inter-)network layer can use which
          -- can differ from the MAC layer (especially if several layers
          -- of encapsulation are used).

          dot1dTpPortMaxInfo OBJECT-TYPE
              SYNTAX  INTEGER
              ACCESS  read-only
              STATUS  mandatory
              DESCRIPTION
                      "The maximum size of the INFO (non-MAC) field that
                      this port will receive or transmit."
              ::= { dot1dTpPortEntry 2 }

          dot1dTpPortInFrames OBJECT-TYPE
              SYNTAX  Counter
              ACCESS  read-only
              STATUS  mandatory
              DESCRIPTION
                      "The number of frames that have been received by
                      this port from its segment. Note that a frame
                      received on the interface corresponding to this
                      port is only counted by this object if and only if
                      it is for a protocol being processed by the local
                      bridging function, including bridge management
                      frames."
              REFERENCE
                      "IEEE 802.1D-1990: Section 6.6.1.1.3"
              ::= { dot1dTpPortEntry 3 }

          dot1dTpPortOutFrames OBJECT-TYPE
              SYNTAX  Counter
              ACCESS  read-only
              STATUS  mandatory
              DESCRIPTION
                      "The number of frames that have been transmitted
                      by this port to its segment.  Note that a frame
                      transmitted on the interface corresponding to this
                      port is only counted by this object if and only if
                      it is for a protocol being processed by the local
                      bridging function, including bridge management
                      frames."
              REFERENCE
                      "IEEE 802.1D-1990: Section 6.6.1.1.3"
              ::= { dot1dTpPortEntry 4 }

          dot1dTpPortInDiscards OBJECT-TYPE
              SYNTAX   Counter
              ACCESS   read-only
              STATUS   mandatory
              DESCRIPTION
                      "Count of valid frames received which were
                      discarded (i.e., filtered) by the Forwarding
                      Process."
              REFERENCE
                      "IEEE 802.1D-1990: Section 6.6.1.1.3"
              ::= { dot1dTpPortEntry 5 }


          -- The Static (Destination-Address Filtering) Database

          -- Implementation of this group is optional.


          dot1dStaticTable OBJECT-TYPE
              SYNTAX  SEQUENCE OF Dot1dStaticEntry
              ACCESS  not-accessible
              STATUS  mandatory
              DESCRIPTION
                      "A table containing filtering information
                      configured into the bridge by (local or network)
                      management specifying the set of ports to which
                      frames received from specific ports and containing
                      specific destination addresses are allowed to be
                      forwarded.  The value of zero in this table as the
                      port number from which frames with a specific
                      destination address are received, is used to
                      specify all ports for which there is no specific
                      entry in this table for that particular
                      destination address.  Entries are valid for
                      unicast and for group/broadcast addresses."
              REFERENCE
                      "IEEE 802.1D-1990: Section 6.7.2"
              ::= { dot1dStatic 1 }

          dot1dStaticEntry OBJECT-TYPE
              SYNTAX  Dot1dStaticEntry
              ACCESS  not-accessible
              STATUS  mandatory
              DESCRIPTION
                      "Filtering information configured into the bridge
                      by (local or network) management specifying the
                      set of ports to which frames received from a
                      specific port and containing a specific
                      destination address are allowed to be forwarded."
              REFERENCE
                      "IEEE 802.1D-1990: Section 6.7.2"
              INDEX   { dot1dStaticAddress, dot1dStaticReceivePort }
              ::= { dot1dStaticTable 1 }

          Dot1dStaticEntry ::=
              SEQUENCE {
                  dot1dStaticAddress
                      MacAddress,
                  dot1dStaticReceivePort
                      INTEGER,
                  dot1dStaticAllowedToGoTo
                      OCTET STRING,
                  dot1dStaticStatus
                      INTEGER
              }

          dot1dStaticAddress OBJECT-TYPE
              SYNTAX  MacAddress
              ACCESS  read-write
              STATUS  mandatory
              DESCRIPTION
                      "The destination MAC address in a frame to which
                      this entry's filtering information applies.  This
                      object can take the value of a unicast address, a
                      group address or the broadcast address."
              REFERENCE
                      "IEEE 802.1D-1990: Section 3.9.1, 3.9.2"
              ::= { dot1dStaticEntry 1 }

          dot1dStaticReceivePort OBJECT-TYPE
              SYNTAX  INTEGER
              ACCESS  read-write
              STATUS  mandatory
              DESCRIPTION
                      "Either the value '0', or the port number of the
                      port from which a frame must be received in order
                      for this entry's filtering information to apply.
                      A value of zero indicates that this entry applies
                      on all ports of the bridge for which there is no
                      other applicable entry."
              ::= { dot1dStaticEntry 2 }

          dot1dStaticAllowedToGoTo OBJECT-TYPE
              SYNTAX  OCTET STRING
              ACCESS  read-write
              STATUS  mandatory
              DESCRIPTION
                      "The set of ports to which frames received from a
                      specific port and destined for a specific MAC
                      address, are allowed to be forwarded.  Each octet
                      within the value of this object specifies a set of
                      eight ports, with the first octet specifying ports
                      1 through 8, the second octet specifying ports 9
                      through 16, etc.  Within each octet, the most
                      significant bit represents the lowest numbered
                      port, and the least significant bit represents the
                      highest numbered port.  Thus, each port of the
                      bridge is represented by a single bit within the
                      value of this object.  If that bit has a value of
                      '1' then that port is included in the set of
                      ports; the port is not included if its bit has a
                      value of '0'.  (Note that the setting of the bit
                      corresponding to the port from which a frame is
                      received is irrelevant.)  The default value of
                      this object is a string of ones of appropriate
                      length."
              ::= { dot1dStaticEntry 3 }

          dot1dStaticStatus OBJECT-TYPE
              SYNTAX  INTEGER {
                          other(1),
                          invalid(2),
                          permanent(3),
                          deleteOnReset(4),
                          deleteOnTimeout(5)
                      }
              ACCESS  read-write
              STATUS  mandatory
              DESCRIPTION
                      "This object indicates the status of this entry.
                      The default value is permanent(3).

                           other(1) - this entry is currently in use but
                                the conditions under which it will
                                remain so are different from each of the
                                following values.
                           invalid(2) - writing this value to the object
                                removes the corresponding entry.
                           permanent(3) - this entry is currently in use
                                and will remain so after the next reset
                                of the bridge.
                           deleteOnReset(4) - this entry is currently in
                                use and will remain so until the next
                                reset of the bridge.
                           deleteOnTimeout(5) - this entry is currently
                                in use and will remain so until it is
                                aged out."
              ::= { dot1dStaticEntry 4 }


          -- Traps for use by Bridges

          -- Traps for the Spanning Tree Protocol

          newRoot TRAP-TYPE
              ENTERPRISE  dot1dBridge
              DESCRIPTION
                      "The newRoot trap indicates that the sending agent
                      has become the new root of the Spanning Tree; the
                      trap is sent by a bridge soon after its election
                      as the new root, e.g., upon expiration of the
                      Topology Change Timer immediately subsequent to
                      its election.  Implementation of this trap is
                      optional."
              ::= 1

          topologyChange TRAP-TYPE
              ENTERPRISE  dot1dBridge
              DESCRIPTION
                      "A topologyChange trap is sent by a bridge when
                      any of its configured ports transitions from the
                      Learning state to the Forwarding state, or from
                      the Forwarding state to the Blocking state.  The
                      trap is not sent if a newRoot trap is sent for the
                      same transition.  Implementation of this trap is
                      optional."
              ::= 2


--
-- FILE: /users/sse/mibs/src/rfc/rfc1316.mib
--

-- Changes for RFC1316 (Character MIB)
--      Added IMPORT for mib-2.




            -- this is the MIB module for character stream devices

            char    OBJECT IDENTIFIER ::= { mib-2 19 }

            -- Textual Conventions

                AutonomousType    ::= OBJECT IDENTIFIER

            -- The object identifier is an independently extensible type
            -- identification value.  It may, for example indicate a
            -- particular sub-tree with further MIB definitions, or
            -- define something like a protocol type or type of
            -- hardware.

                InstancePointer   ::= OBJECT IDENTIFIER

            -- The object identifier is a pointer to a specific instance
            -- of a MIB object in this agent's implemented MIB.  By
            -- convention, it is the first object in the conceptual row
            -- for the instance.


            -- the generic Character group

            -- Implementation of this group is mandatory for all
            -- systems that offer character ports

            charNumber OBJECT-TYPE
                SYNTAX INTEGER
                ACCESS read-only
                STATUS mandatory
                DESCRIPTION
                    "The number of entries in charPortTable, regardless
                    of their current state."
                ::= { char 1 }


            -- the Character Port table

            charPortTable OBJECT-TYPE
                SYNTAX SEQUENCE OF CharPortEntry
                ACCESS not-accessible
                STATUS mandatory
                DESCRIPTION
                    "A list of port entries.  The number of entries is
                    given by the value of charNumber."
                ::= { char 2 }

            charPortEntry OBJECT-TYPE
                SYNTAX CharPortEntry
                ACCESS not-accessible
                STATUS mandatory
                DESCRIPTION
                    "Status and parameter values for a character port."
                INDEX { charPortIndex }
                ::= { charPortTable 1 }

            CharPortEntry ::=
                SEQUENCE {
                    charPortIndex
                        INTEGER,
                    charPortName
                        DisplayString,
                    charPortType
                        INTEGER,
                    charPortHardware
                        AutonomousType,
                    charPortReset
                        INTEGER,
                    charPortAdminStatus
                        INTEGER,
                    charPortOperStatus
                        INTEGER,
                    charPortLastChange
                        TimeTicks,
                    charPortInFlowType
                        INTEGER,
                    charPortOutFlowType
                        INTEGER,
                    charPortInFlowState
                        INTEGER,
                    charPortOutFlowState
                        INTEGER,
                    charPortInCharacters
                        Counter,
                    charPortOutCharacters
                        Counter,
                    charPortAdminOrigin
                        INTEGER,
                    charPortSessionMaximum
                        INTEGER,
                    charPortSessionNumber
                        Gauge,
                    charPortSessionIndex
                        INTEGER
                }

            charPortIndex OBJECT-TYPE
                SYNTAX INTEGER
                ACCESS read-only
                STATUS mandatory
                DESCRIPTION
                    "A unique value for each character port.  Its value
                    ranges between 1 and the value of charNumber.  By
                    convention and if possible, hardware port numbers
                    come first, with a simple, direct mapping.  The
                    value for each port must remain constant at least
                    from one re-initialization of the network management
                    agent to the next."
                ::= { charPortEntry 1 }

            charPortName OBJECT-TYPE
                SYNTAX DisplayString (SIZE (0..32))
                ACCESS read-write
                STATUS mandatory
                DESCRIPTION
                    "An administratively assigned name for the port,
                    typically with some local significance."
                ::= { charPortEntry 2 }

            charPortType OBJECT-TYPE
                SYNTAX INTEGER { physical(1), virtual(2) }
                ACCESS read-only
                STATUS mandatory
                DESCRIPTION
                    "The port's type, 'physical' if the port represents
                    an external hardware connector, 'virtual' if it does
                    not."
                ::= { charPortEntry 3 }

            charPortHardware OBJECT-TYPE
                SYNTAX AutonomousType
                ACCESS read-only
                STATUS mandatory
                DESCRIPTION
                    "A reference to hardware MIB definitions specific to
                    a physical port's external connector.  For example,
                    if the connector is RS-232, then the value of this
                    object refers to a MIB sub-tree defining objects
                    specific to RS-232.  If an agent is not configured
                    to have such values, the agent returns the object
                    identifier:

                        nullHardware OBJECT IDENTIFIER ::= { 0 0 }
                    "
                ::= { charPortEntry 4 }

            charPortReset OBJECT-TYPE
                SYNTAX INTEGER { ready(1), execute(2) }
                ACCESS read-write
                STATUS mandatory
                DESCRIPTION
                    "A control to force the port into a clean, initial
                    state, both hardware and software, disconnecting all
                    the port's existing sessions.  In response to a
                    get-request or get-next-request, the agent always
                    returns 'ready' as the value.  Setting the value to
                    'execute' causes a reset."
                ::= { charPortEntry 5 }

            charPortAdminStatus OBJECT-TYPE
                SYNTAX INTEGER { enabled(1), disabled(2), off(3),
                                 maintenance(4) }
                ACCESS read-write
                STATUS mandatory
                DESCRIPTION
                    "The port's desired state, independent of flow
                    control.  'enabled' indicates that the port is
                    allowed to pass characters and form new sessions.
                    'disabled' indicates that the port is allowed to
                    pass characters but not form new sessions.  'off'
                    indicates that the port is not allowed to pass
                    characters or have any sessions. 'maintenance'
                    indicates a maintenance mode, exclusive of normal
                    operation, such as running a test."
                ::= { charPortEntry 6 }

            charPortOperStatus OBJECT-TYPE
                SYNTAX INTEGER { up(1), down(2),
                                 maintenance(3), absent(4), active(5) }
                ACCESS read-only
                STATUS mandatory
                DESCRIPTION
                    "The port's actual, operational state, independent
                    of flow control.  'up' indicates able to function
                    normally.  'down' indicates inability to function
                    for administrative or operational reasons.
                    'maintenance' indicates a maintenance mode,
                    exclusive of normal operation, such as running a
                    test.  'absent' indicates that port hardware is not
                    present.  'active' indicates up with a user present
                    (e.g. logged in)."
                ::= { charPortEntry 7 }

            charPortLastChange OBJECT-TYPE
                SYNTAX TimeTicks
                ACCESS read-only
                STATUS mandatory
                DESCRIPTION
                    "The value of sysUpTime at the time the port entered
                    its current operational state.  If the current state
                    was entered prior to the last reinitialization of
                    the local network management subsystem, then this
                    object contains a zero value."
                ::= { charPortEntry 8 }

            charPortInFlowType OBJECT-TYPE
                SYNTAX INTEGER { none(1), xonXoff(2), hardware(3),
                                 ctsRts(4), dsrDtr(5) }
                ACCESS read-write
                STATUS mandatory
                DESCRIPTION
                    "The port's type of input flow control.  'none'
                    indicates no flow control at this level or below.
                    'xonXoff' indicates software flow control by
                    recognizing XON and XOFF characters.  'hardware'
                    indicates flow control delegated to the lower level,
                    for example a parallel port.

                    'ctsRts' and 'dsrDtr' are specific to RS-232-like
                    ports.  Although not architecturally pure, they are
                    included here for simplicity's sake."
                ::= { charPortEntry 9 }

            charPortOutFlowType OBJECT-TYPE
                SYNTAX INTEGER { none(1), xonXoff(2), hardware(3),
                                 ctsRts(4), dsrDtr(5) }
                ACCESS read-write
                STATUS mandatory
                DESCRIPTION
                    "The port's type of output flow control.  'none'
                    indicates no flow control at this level or below.
                    'xonXoff' indicates software flow control by
                    recognizing XON and XOFF characters.  'hardware'
                    indicates flow control delegated to the lower level,
                    for example a parallel port.

                    'ctsRts' and 'dsrDtr' are specific to RS-232-like
                    ports.  Although not architecturally pure, they are
                    included here for simplicy's sake."
                ::= { charPortEntry 10 }

            charPortInFlowState OBJECT-TYPE
                SYNTAX INTEGER { none(1), unknown(2), stop(3), go(4) }
                ACCESS read-only
                STATUS mandatory
                DESCRIPTION
                    "The current operational state of input flow control
                    on the port.  'none' indicates not applicable.
                    'unknown' indicates this level does not know.
                    'stop' indicates flow not allowed.  'go' indicates
                    flow allowed."
                ::= { charPortEntry 11 }

            charPortOutFlowState OBJECT-TYPE
                SYNTAX INTEGER { none(1), unknown(2), stop(3), go(4) }
                ACCESS read-only
                STATUS mandatory
                DESCRIPTION
                    "The current operational state of output flow
                    control on the port.  'none' indicates not
                    applicable.  'unknown' indicates this level does not
                    know.  'stop' indicates flow not allowed.  'go'
                    indicates flow allowed."
                ::= { charPortEntry 12 }

            charPortInCharacters OBJECT-TYPE
                SYNTAX Counter
                ACCESS read-only
                STATUS mandatory
                DESCRIPTION
                    "Total number of characters detected as input from
                    the port since system re-initialization and while
                    the port operational state was 'up', 'active', or
                    'maintenance', including, for example, framing, flow
                    control (i.e. XON and XOFF), each occurrence of a
                    BREAK condition, locally-processed input, and input
                    sent to all sessions."
                ::= { charPortEntry 13 }

            charPortOutCharacters OBJECT-TYPE
                SYNTAX Counter
                ACCESS read-only
                STATUS mandatory
                DESCRIPTION
                    "Total number of characters detected as output to
                    the port since system re-initialization and while
                    the port operational state was 'up', 'active', or
                    'maintenance', including, for example, framing, flow
                    control (i.e. XON and XOFF), each occurrence of a
                    BREAK condition, locally-created output, and output
                    received from all sessions."
                ::= { charPortEntry 14 }

            charPortAdminOrigin OBJECT-TYPE
                SYNTAX INTEGER { dynamic(1), network(2), local(3),
                                 none(4) }
                ACCESS read-write
                STATUS mandatory
                DESCRIPTION
                    "The administratively allowed origin for
                    establishing session on the port.  'dynamic' allows
                    'network' or 'local' session establishment. 'none'
                    disallows session establishment."
                ::= { charPortEntry 15 }

            charPortSessionMaximum OBJECT-TYPE
                SYNTAX INTEGER
                ACCESS read-write
                STATUS mandatory
                DESCRIPTION
                    "The maximum number of concurrent sessions allowed
                    on the port.  A value of -1 indicates no maximum.
                    Setting the maximum to less than the current number
                    of sessions has unspecified results."
                ::= { charPortEntry 16 }

            charPortSessionNumber OBJECT-TYPE
                SYNTAX Gauge
                ACCESS read-only
                STATUS mandatory
                DESCRIPTION
                    "The number of open sessions on the port that are in
                    the connecting, connected, or disconnecting state."
                ::= { charPortEntry 17 }

            charPortSessionIndex OBJECT-TYPE
                SYNTAX INTEGER
                ACCESS read-only
                STATUS mandatory
                DESCRIPTION
                    "The value of charSessIndex for the port's first or
                    only active session.  If the port has no active
                    session, the agent returns the value zero."
                ::= { charPortEntry 18 }


            -- the Character Session table

            charSessTable OBJECT-TYPE
                SYNTAX SEQUENCE OF CharSessEntry
                ACCESS not-accessible
                STATUS mandatory
                DESCRIPTION
                    "A list of port session entries."
                ::= { char 3 }

            charSessEntry OBJECT-TYPE
                SYNTAX CharSessEntry
                ACCESS not-accessible
                STATUS mandatory
                DESCRIPTION
                    "Status and parameter values for a character port
                    session."
                INDEX { charSessPortIndex, charSessIndex }
                ::= { charSessTable 1 }

            CharSessEntry ::=
                SEQUENCE {
                    charSessPortIndex
                        INTEGER,
                    charSessIndex
                        INTEGER,
                    charSessKill
                        INTEGER,
                    charSessState
                        INTEGER,
                    charSessProtocol
                        AutonomousType,
                    charSessOperOrigin
                        INTEGER,
                    charSessInCharacters
                        Counter,
                    charSessOutCharacters
                        Counter,
                    charSessConnectionId
                        InstancePointer,
                    charSessStartTime
                        TimeTicks
                }

            charSessPortIndex OBJECT-TYPE
                SYNTAX INTEGER
                ACCESS read-only
                STATUS mandatory
                DESCRIPTION
                    "The value of charPortIndex for the port to which
                    this session belongs."
                ::= { charSessEntry 1 }

            charSessIndex OBJECT-TYPE
                SYNTAX INTEGER
                ACCESS read-only
                STATUS mandatory
                DESCRIPTION
                    "The session index in the context of the port, a
                    non-zero positive integer.  Session indexes within a
                    port need not be sequential.  Session indexes may be
                    reused for different ports.  For example, port 1 and
                    port 3 may both have a session 2 at the same time.
                    Session indexes may have any valid integer value,
                    with any meaning convenient to the agent
                    implementation."
                ::= { charSessEntry 2 }

            charSessKill OBJECT-TYPE
                SYNTAX INTEGER { ready(1), execute(2) }
                ACCESS read-write
                STATUS mandatory
                DESCRIPTION
                    "A control to terminate the session.  In response to
                    a get-request or get-next-request, the agent always
                    returns 'ready' as the value.  Setting the value to
                    'execute' causes termination."
                ::= { charSessEntry 3 }

            charSessState OBJECT-TYPE
                SYNTAX INTEGER { connecting(1), connected(2),
                                 disconnecting(3) }
                ACCESS read-only
                STATUS mandatory
                DESCRIPTION
                    "The current operational state of the session,
                    disregarding flow control.  'connected' indicates
                    that character data could flow on the network side
                    of session.  'connecting' indicates moving from
                    nonexistent toward 'connected'.  'disconnecting'
                    indicates moving from 'connected' or 'connecting' to
                    nonexistent."
                ::= { charSessEntry 4 }

            charSessProtocol OBJECT-TYPE
                SYNTAX AutonomousType
                ACCESS read-only
                STATUS mandatory
                DESCRIPTION
                    "The network protocol over which the session is
                    running.  Other OBJECT IDENTIFIER values may be
                    defined elsewhere, in association with specific
                    protocols.  However, this document assigns those of
                    known interest as of this writing."
                ::= { charSessEntry 5 }

            wellKnownProtocols OBJECT IDENTIFIER ::= { char 4 }

            protocolOther  OBJECT IDENTIFIER ::= {wellKnownProtocols 1}
            protocolTelnet OBJECT IDENTIFIER ::= {wellKnownProtocols 2}
            protocolRlogin OBJECT IDENTIFIER ::= {wellKnownProtocols 3}
            protocolLat    OBJECT IDENTIFIER ::= {wellKnownProtocols 4}
            protocolX29    OBJECT IDENTIFIER ::= {wellKnownProtocols 5}
            protocolVtp    OBJECT IDENTIFIER ::= {wellKnownProtocols 6}

            charSessOperOrigin OBJECT-TYPE
                SYNTAX INTEGER { unknown(1), network(2), local(3) }
                ACCESS read-only
                STATUS mandatory
                DESCRIPTION
                    "The session's source of establishment."
                ::= { charSessEntry 6 }

            charSessInCharacters OBJECT-TYPE
                SYNTAX Counter
                ACCESS read-only
                STATUS mandatory
                DESCRIPTION
                    "This session's subset of charPortInCharacters."
                ::= { charSessEntry 7 }

            charSessOutCharacters OBJECT-TYPE
                SYNTAX Counter
                ACCESS read-only
                STATUS mandatory
                DESCRIPTION
                    "This session's subset of charPortOutCharacters."
                ::= { charSessEntry 8 }

            charSessConnectionId OBJECT-TYPE
                SYNTAX InstancePointer
                ACCESS read-only
                STATUS mandatory
                DESCRIPTION
                    "A reference to additional local MIB information.
                    This should be the highest available related MIB,
                    corresponding to charSessProtocol, such as Telnet.
                    For example, the value for a TCP connection (in the
                    absence of a Telnet MIB) is the object identifier of
                    tcpConnState.  If an agent is not configured to have
                    such values, the agent returns the object
                    identifier:

                        nullConnectionId OBJECT IDENTIFIER ::= { 0 0 }
                    "
                ::= { charSessEntry 9 }

            charSessStartTime OBJECT-TYPE
                SYNTAX TimeTicks
                ACCESS read-only
                STATUS mandatory
                DESCRIPTION
                    "The value of sysUpTime in MIB-2 when the session
                    entered connecting state."
                ::= { charSessEntry 10 }


--
-- FILE: /users/sse/mibs/src/rfc/rfc1289.mib
--

-- Changes for RFC1289 (DECnet Phase IV):
--      Inserted space between SYNTAX and INTEGER for
--              phivRouteType.
--      Added phivCircuitIndex to definition of sequences
--          PhivCiruitCountEntry and PhivDDCMPCircuitCountEntry.
--      Added range to phivCircuitCountDataBlocksRecd.
--   Note: these corrections are guesses...
--      Corrected syntax for phivDDCMPCircuitAdjNodeAddr in
--          sequence PhivDDCMPCircuitParametersEntry from
--          INTEGER to PhivAddr.
--      Corrected syntax for phivDDCMPCircuitSelectTimeouts
--          from INTEGER to PhivCounter.
--      Corrected syntax for phivCountersCountSendFailure
--          from INTEGER to PhivCounter.
--      Corrected syntax for phivCountersCountCollDetectFailure
--          from INTEGER to PhivCounter.
--      Corrected syntax for phivCountersCountReceiveFailure
--          from INTEGER to PhivCounter.
--      Corrected syntax for phivCountersCountUnrecFrameDest
--          from INTEGER to PhivCounter.
--      Corrected syntax for phivCountersCountDataOver
--          from INTEGER to PhivCounter.
--      Corrected syntax for phivCountersCountSysBuffUnav
--          from INTEGER to PhivCounter.
--      Corrected syntax for phivCountersCountUsrBuffUnav
--          from INTEGER to PhivCounter.
--      Corrected syntax for phivCircuitCountTermCongLoss
--          by adding range of (0..65535).
--      Question: It seems like all objects that use
--          syntax PhivCounter should have a range specified.



            -- RFC1289
            -- December 91


       -- DECNet Phase-IV MIB

            phiv             OBJECT IDENTIFIER ::= { mib-2 18 }

       -- textual conventions

       PhivAddr ::= OCTET STRING (SIZE (2))
       -- This data type is intended as a short word representation of
       -- standard DECnet Phase IV addresses. DECnet addresses are
       -- hierarchically structured numbers assigned to a particular
       -- DECnet node. The address is structured so that the area
       -- number is contained in the most significant 6 bits of the
       -- first octet.  The next 2 bits of the first octet contain
       -- the first two bits of the host address.  The remainder of
       -- the host address is contained in the second octet.

       PhivCounter ::= INTEGER
       -- This data type has been created for DECnet  counters.  These
       -- counters latch at their maximum specified value until either
       -- the system is restared, or they are reset to zero by the user
       -- or management software.

       -- groups in the decnetiv mib

             phivSystem             OBJECT IDENTIFIER ::= { phiv 1 }
             phivManagement         OBJECT IDENTIFIER ::= { phiv 2 }
             session                OBJECT IDENTIFIER ::= { phiv 3 }
             end                    OBJECT IDENTIFIER ::= { phiv 4 }
             routing                OBJECT IDENTIFIER ::= { phiv 5 }
             circuit                OBJECT IDENTIFIER ::= { phiv 6 }
             ddcmp                  OBJECT IDENTIFIER ::= { phiv 7 }
             control                OBJECT IDENTIFIER ::= { phiv 8 }
             ethernet               OBJECT IDENTIFIER ::= { phiv 9 }
             counters               OBJECT IDENTIFIER ::= { phiv 10 }
             adjacency              OBJECT IDENTIFIER ::= { phiv 11 }
             line                   OBJECT IDENTIFIER ::= { phiv 12 }
             nonBroadcastLine       OBJECT IDENTIFIER ::= { phiv 14 }
             area                   OBJECT IDENTIFIER ::= { phiv 15 }

       -- System Group

       -- The implementation of the System Group is mandatory for
       -- all systems.



       -- Network Management Group

       -- The implementation of the Network Management Group is
       -- mandatory for all systems which contain a DECnet style
       -- management version.



       -- Session Layer Group

       -- The implementation of the Session Layer Group is mandatory for
       -- all systems that implement session layer communications.




       -- End Communication Layer Group

       -- The implementation of the End Communication Layer Group is
       -- mandatory for all systems that implement end layer
       -- communications.

       -- Remote State Table







       -- End System Counter Table


















       -- additional End System objects









       -- Routing Layer Group

       -- The implementation of the Routing Layer Group is mandatory for
       -- all systems that implement level 1 routing layer
       -- communications.






















        -- Level 1 Routing Table








       -- Additional routing parameters



       -- Circuit Group

       -- The implementation of the Circuit Group is mandatory for
       -- all systems.

       -- Circuit Parameters Table


       phivCircuitParametersTable OBJECT-TYPE
           SYNTAX SEQUENCE OF PhivCircuitParametersEntry
           ACCESS not-accessible
           STATUS mandatory
           DESCRIPTION
               "Information about the parameters associated with all
               circuits currently known."
           ::= {circuit 1 }

       phivCircuitParametersEntry OBJECT-TYPE
           SYNTAX PhivCircuitParametersEntry
           ACCESS not-accessible
           STATUS mandatory
           DESCRIPTION
               "Parameters information about all circuits currently
               known."
            INDEX  { phivCircuitIndex }
            ::= { phivCircuitParametersTable 1 }

       PhivCircuitParametersEntry ::=
           SEQUENCE {
               phivCircuitIndex
                   INTEGER,
               phivCircuitLineIndex
                   INTEGER,
               phivCircuitCommonState
                   INTEGER,
               phivCircuitCommonSubState
                   INTEGER,
               phivCircuitCommonName
                   DisplayString,
               phivCircuitExecRecallTimer
                   INTEGER,
               phivCircuitCommonType
                   INTEGER,
               phivCircuitService
                   INTEGER,
               phivCircuitExecCost
                   INTEGER,
               phivCircuitExecHelloTimer
                   INTEGER
           }
        phivCircuitIndex OBJECT-TYPE
           SYNTAX INTEGER
           ACCESS read-only
           STATUS mandatory
           DESCRIPTION
               "A unique index value for each known circuit."
           ::= { phivCircuitParametersEntry 1 }

       phivCircuitLineIndex OBJECT-TYPE
           SYNTAX INTEGER
           ACCESS read-only
           STATUS mandatory
           DESCRIPTION
               "The line on which this circuit is active.  This is
               the same as the IfIndex."
           ::= { phivCircuitParametersEntry 2 }

       phivCircuitCommonState OBJECT-TYPE
           SYNTAX INTEGER {
               on (1),
               off (2),
               service (3),
               cleared (4)
           }
           ACCESS read-write
           STATUS mandatory
           DESCRIPTION
               "This value represents the circuit's Network Management
               operational state. NOTE: These values are incremented
               by one compared to the standard DECnet values in order
               to maintain compliance with RFC 1155."
           ::= { phivCircuitParametersEntry 3 }

       phivCircuitCommonSubState OBJECT-TYPE
           SYNTAX INTEGER {
               starting (1),
               reflecting (2),
               looping (3),
               loading (4),
               dumping (5),
               triggering (6),
               autoservice (7),
               autoloading (8),
               autodumping (9),
               autotriggering (10),
               synchronizing (11),
               failed (12),
               running (13)
           }
           ACCESS read-only
           STATUS mandatory
           DESCRIPTION
               "This value represents the circuit's Network Management
               operational and service substate. NOTE: These values are
               incremented by one compared to the standard DECnet values
               in order to maintain compliance with RFC 1155."
           ::= { phivCircuitParametersEntry 4 }

       phivCircuitCommonName OBJECT-TYPE
           SYNTAX DisplayString ( SIZE (0..16) )
           ACCESS read-only
           STATUS mandatory
           DESCRIPTION
               "The name of the circuit entry in the table, for example,
               SVA-0 or in a level 2 router ASYNC-8 or ETHER-1)."
           ::= { phivCircuitParametersEntry 5 }

       phivCircuitExecRecallTimer OBJECT-TYPE
           SYNTAX INTEGER (0..65535)
           ACCESS read-write
           STATUS mandatory
           DESCRIPTION
               "This parameter represents the minimum number of
               seconds to wait before restarting the circuit.  A
               value of 0 indicates not timer is running."
           ::= { phivCircuitParametersEntry 6 }

       phivCircuitCommonType OBJECT-TYPE
           SYNTAX INTEGER {
               ddcmp-point (1),
               ddcmp-control (2),
               ddcmp-tributary (3),
               x25 (4),
               ddcmp-dmc (5),
               ethernet (6),
               ci (7),
               qp2-dte20 (8),
               bisync (9),
               other (14),
               fddi (15)
           }
           ACCESS read-only
           STATUS mandatory
           DESCRIPTION
               "Represents the type of the circuit. For X.25 circuits,
               the value must be set to X25. For DDCMP and Ethernet
               circuits it is read only and is the same value as the
               protocol of the associated line.
               NOTE: Values 1 - 5 are incremented by one compared to the
               standard DECnet values in order to maintain compliance
               with RFC 1155."
           ::= { phivCircuitParametersEntry 7 }

       phivCircuitService  OBJECT-TYPE
           SYNTAX INTEGER {
               enabled (1),
               disabled (2)
           }
           ACCESS read-write
           STATUS mandatory
           DESCRIPTION
               "This value indicates whether or not Network Management
               allows service operations on a circuit. The values for
               service-control are as follows:

               ENABLED     SERVICE state and/or service functions are
                           allowed.

               DISABLED    SERVICE state and/or service functions are not
                           allowed.

               NOTE: These values are incremented by one compared to the
               standard DECnet values in order to maintain compliance
               with RFC 1155."
           ::= { phivCircuitParametersEntry 8 }

       phivCircuitExecCost OBJECT-TYPE
           SYNTAX INTEGER (1..25)
           ACCESS read-write
           STATUS mandatory
           DESCRIPTION
               "This value represents the routing cost of the circuit.
               Routing sends messages along the path between two nodes
               having the smallest cost."
           ::= { phivCircuitParametersEntry 9 }

       phivCircuitExecHelloTimer OBJECT-TYPE
           SYNTAX INTEGER (1..8191)
           ACCESS read-write
           STATUS mandatory
           DESCRIPTION
               "This value determines the frequency of Routing Hello
               messages sent to the adjacent node on the circuit."
           ::= { phivCircuitParametersEntry 10 }

       -- Circuit Counters Table


       phivCircuitCountTable OBJECT-TYPE
           SYNTAX SEQUENCE OF PhivCircuitCountEntry
           ACCESS not-accessible
           STATUS mandatory
           DESCRIPTION
               "Information about the counters associated with all
               circuits currently known."
           ::= { circuit 2 }

       phivCircuitCountEntry OBJECT-TYPE
           SYNTAX PhivCircuitCountEntry
           ACCESS not-accessible
           STATUS mandatory
           DESCRIPTION
               "Counter information about all circuits currently known"
           INDEX     { phivCircuitIndex }
           ::= { phivCircuitCountTable 1 }

       PhivCircuitCountEntry ::=
           SEQUENCE {
               phivCircuitCountSecLastZeroed
                   PhivCounter (0..65535),
               phivCircuitCountTermPacketsRecd
                   PhivCounter,
               phivCircuitCountOriginPackSent
                   PhivCounter,
               phivCircuitCountTermCongLoss
                   PhivCounter (0..65535),
               phivCircuitCountCorruptLoss
                   PhivCounter (0..255),
               phivCircuitCountTransitPksRecd
                   PhivCounter,
               phivCircuitCountTransitPkSent
                   PhivCounter,
               phivCircuitCountTransitCongestLoss
                   PhivCounter (0..65535),
               phivCircuitCountCircuitDown
                   PhivCounter (0..255),
               phivCircuitCountInitFailure
                   PhivCounter (0..255),
               phivCircuitCountAdjDown
                   PhivCounter,
               phivCircuitCountPeakAdj
                   PhivCounter,
               phivCircuitCountBytesRecd
                   PhivCounter,
               phivCircuitCountBytesSent
                   PhivCounter,
               phivCircuitCountDataBlocksRecd
                   PhivCounter (0..65535),
               phivCircuitCountDataBlocksSent
                   PhivCounter,
               phivCircuitCountUsrBuffUnav
                   PhivCounter (0..65535)
           }
       phivCircuitCountSecLastZeroed  OBJECT-TYPE
           SYNTAX PhivCounter (0..65535)
           ACCESS read-only
           STATUS mandatory
           DESCRIPTION
               "Number of seconds since the circuit counters for this
               circuit were last zeroed."
           ::= { phivCircuitCountEntry 1 }

       phivCircuitCountTermPacketsRecd OBJECT-TYPE
           SYNTAX PhivCounter
           ACCESS read-only
           STATUS mandatory
           DESCRIPTION
               "Number of terminating packets received on this circuit."
           ::= { phivCircuitCountEntry 2 }

       phivCircuitCountOriginPackSent OBJECT-TYPE
           SYNTAX PhivCounter
           ACCESS read-only
           STATUS mandatory
           DESCRIPTION
               "Number of originating packets sent on this circuit."
           ::= { phivCircuitCountEntry 3 }

       phivCircuitCountTermCongLoss OBJECT-TYPE
           SYNTAX PhivCounter (0..65535)
           ACCESS read-only
           STATUS mandatory
           DESCRIPTION
               "Number of terminating congestion losses on this
               circuit."
           ::= { phivCircuitCountEntry 4 }

       phivCircuitCountCorruptLoss OBJECT-TYPE
           SYNTAX PhivCounter (0..255)
           ACCESS read-only
           STATUS mandatory
           DESCRIPTION
               "Number of corruption losses on this circuit."
           ::= { phivCircuitCountEntry 5 }

       phivCircuitCountTransitPksRecd OBJECT-TYPE
           SYNTAX PhivCounter
           ACCESS read-only
           STATUS mandatory
           DESCRIPTION
               "Number of Transit packets received on this circuit."
           ::= { phivCircuitCountEntry 6 }

       phivCircuitCountTransitPkSent OBJECT-TYPE
           SYNTAX PhivCounter
           ACCESS read-only
           STATUS mandatory
           DESCRIPTION
               "Number of transit packets sent on this circuit."
           ::= { phivCircuitCountEntry 7 }

       phivCircuitCountTransitCongestLoss OBJECT-TYPE
           SYNTAX PhivCounter (0..65535)
           ACCESS read-only
           STATUS mandatory
           DESCRIPTION
               "Number of transit congestion losses on this circuit."
           ::= { phivCircuitCountEntry 8 }

       phivCircuitCountCircuitDown OBJECT-TYPE
           SYNTAX PhivCounter (0..255)
           ACCESS read-only
           STATUS mandatory
           DESCRIPTION
               "Number of circuit downs on this circuit."
           ::= { phivCircuitCountEntry 9 }

       phivCircuitCountInitFailure OBJECT-TYPE
           SYNTAX PhivCounter (0..255)
           ACCESS read-only
           STATUS mandatory
           DESCRIPTION
               "Number of Initialization failures on this circuit."
           ::= { phivCircuitCountEntry 10 }

       phivCircuitCountAdjDown OBJECT-TYPE
           SYNTAX PhivCounter
           ACCESS read-only
           STATUS mandatory
           DESCRIPTION
               "This counter indicates the number of adjacency losses
               that result from any of the following:
                    Node listener timeout
                    Invalid data received at node listener
                    Unexpected control (initialization or verification)
                        message received
                    Routing message received with a checksum error
                    Node identification from a routing message or a
                    Hello message that is not the one expected Hello
                    message received indicating that connectivity
                    became one-way
                    Adjacency idled."
           ::= { phivCircuitCountEntry 11 }

       phivCircuitCountPeakAdj OBJECT-TYPE
           SYNTAX PhivCounter
           ACCESS read-only
           STATUS mandatory
           DESCRIPTION
               "This counter indicates the maximum number of nodes
               that are up on the circuit."
           ::= { phivCircuitCountEntry 12 }

       phivCircuitCountBytesRecd OBJECT-TYPE
           SYNTAX PhivCounter
           ACCESS read-only
           STATUS mandatory
           DESCRIPTION
               "Number of bytes received on this circuit."
           ::= { phivCircuitCountEntry 13 }

       phivCircuitCountBytesSent OBJECT-TYPE
           SYNTAX PhivCounter
           ACCESS read-only
           STATUS mandatory
           DESCRIPTION
               "Number of bytes sent on this circuit."
           ::= { phivCircuitCountEntry 14 }

       phivCircuitCountDataBlocksRecd OBJECT-TYPE
           SYNTAX PhivCounter (0..65535)
           ACCESS read-only
           STATUS mandatory
           DESCRIPTION
               "Number of data blocks received on this circuit."
           ::= { phivCircuitCountEntry 15 }

       phivCircuitCountDataBlocksSent OBJECT-TYPE
           SYNTAX PhivCounter
           ACCESS read-only
           STATUS mandatory
           DESCRIPTION
               "Number of data blocks sent on this circuit."
           ::= { phivCircuitCountEntry 16 }

       phivCircuitCountUsrBuffUnav OBJECT-TYPE
           SYNTAX PhivCounter (0..65535)
           ACCESS read-only
           STATUS mandatory
           DESCRIPTION
               "Number of user buffer unavailable errors."
           ::= { phivCircuitCountEntry 17 }

       -- Additional Circuit Parameters

       phivCircuitOrigQueueLimit OBJECT-TYPE
           SYNTAX INTEGER
           ACCESS read-write
           STATUS mandatory
           DESCRIPTION
               "This parameter indicates the maximum number of
               originating packets that may be outstanding on this
               circuit. This does not include route-thru traffic."
           ::= { circuit 3 }

       phivCircuitCountZeroCount OBJECT-TYPE
           SYNTAX INTEGER {
             other (1),
             reset (2)
           }
           ACCESS read-write
           STATUS mandatory
           DESCRIPTION
               "When this value is set to 2, all of the counters in the
               Circuit Counter Table are set to zero."
           ::= { circuit 4 }

       -- DDCMP Circuit Group

       -- The implementation of the DDCMP Circuit Group is mandatory for
       -- all systems which support DDCMP circuits.

       -- DDCMP Parameters Table






       -- DDCMP Circuit Counter Table












       -- DDCMP Line Count Table








       -- DDCMP Multipoint Circuit Control Group

       -- The implementation of the DDCMP Multipoint Circuit Control
       -- Group is mandatory for all systems which support DDCMP
       -- multipoint control circuits.





       -- DDCMP Multipoint Circuit Control Parameters Table















       -- Ethernet Group

       -- The implementation of the Ethernet Group is mandatory
       -- for all systems which support ethernet links.

       -- Ethernet Parameters Table








       -- Counters Group

       -- The implementation of the Counters Group is mandatory for
       -- systems which only support DECnet style locking counters.

       -- Counters Table























       -- Adjacency Group

       -- The implementation of the Adjacency Group is mandatory for all
       -- conformant implementations of this memo.













       -- Line Group

       -- The implementation of the Line Group is mandatory for all
       -- conformant implementations of this memo.














       -- Non Broadcast Line Group

       -- The implementation of the Non Broadcast Line Group is
       -- mandatory for all systems which implement non broadcast
       -- lines.








       -- Area Parameters Group

       -- The implementation of the Area Parameters Group is mandatory
       -- for all systems which implement level 2 routing.









       -- Additional Area Parameters





--
-- FILE: /users/sse/mibs/src/rfc/rfc1253.mib
--

-- Changes to rfc1253 (OSPF MIB):
--      Changed ospfAreaID in index clause for ospfAreaEntry to
--              ospfAreaId.
--      Changed ospfLSACount in definition for sequence OspfAreaEntry
--              to ospfAreaLSACount.
--      Suggestion: the DEFVAL clauses should be removed from
--              the objects that are counters. Some objects that
--              are gauges should probably not have DEFVAL clauses.


     -- RFC1253
     -- August 91


     --  This MIB module uses the extended OBJECT-TYPE macro as
     --  defined in [9].

             ospf OBJECT IDENTIFIER ::= { mib-2 14 }

     --  The Area ID, in OSPF, has the same format as an IP Address,
     --  but has the function of defining a summarization point for
     --  Link State Advertisements

             AreaID ::= IpAddress

     --  The Router ID, in OSPF, has the same format as an IP Address,
     --  but identifies the router independent of its IP Address.

             RouterID ::= IpAddress

     --  The OSPF Metric is defined as an unsigned value in the range

             Metric    ::= INTEGER (1..'FFFF'h)
             BigMetric ::= INTEGER (1..'FFFFFF'h)

     --  Boolean Values

             TruthValue ::= INTEGER { true (1), false (2) }

     --  Status Values

             Status ::= INTEGER { enabled (1), disabled (2) }

     --  Row Creation/Deletion Values

             Validation ::= INTEGER { valid (1), invalid (2) }

     --  Time Durations measured in seconds

             PositiveInteger ::= INTEGER (1..'FFFFFFFF'h)
             HelloRange      ::= INTEGER (1..'FFFF'h)
             UpToMaxAge      ::= INTEGER (1..3600)

     --  The range of ifIndex, i.e. (1..ifNumber)

             InterfaceIndex ::= INTEGER

     --  Potential Priorities for the Designated Router Election

             DesignatedRouterPriority ::= INTEGER (0..'FF'h)

     --  Type of Service is defined as a mapping to the IP Type of
     --  Service Flags as defined in the Router Requirements
     --  Document:
     --
     --      D => Low Delay          R => Reliable Route
     --      T => High Bandwidth

     --  D T R   TOS      D T R   TOS
     --  0 0 0 =>  0      0 0 1 =>  4
     --  0 1 0 =>  8      0 1 1 => 12
     --  1 0 0 => 16      1 0 1 => 20
     --  1 1 0 => 24      1 1 1 => 28

     --  The remaining values are left for future definition.

             TOSType ::= INTEGER (0..31)

     --  OSPF General Variables

     --      These parameters apply globally to the Router's
     --      OSPF Process.

     ospfGeneralGroup OBJECT IDENTIFIER ::= { ospf 1 }












     --      The OSPF Area Data Structure contains information
     --      regarding the various areas. The interfaces and
     --      virtual links are configured as part of these areas.
     --      Area 0.0.0.0, by definition, is the Backbone Area





                     -- none (0),
                     -- simplePassword (1)
                     -- reserved for specification by IANA (> 1)








     --  OSPF Area Default Metric Table

     --      The OSPF Area Default Metric Table describes the metrics
     --      that a default Area Border Router will advertise into a
     --      Stub area.









     --  OSPF Link State Database

     --      The Link State Database contains the Link State
     --      Advertisements from throughout the areas that the
     --      device is attached to.








     --  Note that the OSPF Sequence Number is a 32 bit signed
     --  integer.  It starts with the value '80000001'h,
     --  or -'7FFFFFFF'h, and increments until '7FFFFFFF'h
     --  Thus, a typical sequence number will be very negative.






     --  Address Range Table

     --      The Address Range Table acts as an adjunct to the Area
     --      Table; It describes those Address Range Summaries that
     --      are configured to be propagated from an Area to reduce
     --      the amount of information about it which is known beyond
     --      its borders.









     --  OSPF Host Table

     --      The Host/Metric Table indicates what hosts are directly
     --      attached to the Router, and what metrics and types of
     --      service should be advertised for them.








     --  OSPF Interface Table

     --      The OSPF Interface Table augments the ifTable with OSPF
     --      specific information.





















     --  OSPF Interface Metric Table

     --      The Metric Table describes the metrics to be advertised
     --      for a specified interface at the various types of service.
     --      As such, this table is an adjunct of the OSPF Interface
     --      Table.

     -- Types of service, as defined by RFC 791, have the ability
     -- to request low delay, high bandwidth, or reliable linkage.

     -- For the purposes of this specification, the measure of
     -- bandwidth

     --      Metric = 10^8 / ifSpeed

     -- is the default value.  For multiple link interfaces, note
     -- that ifSpeed is the sum of the individual link speeds.
     -- This yields a number having the following typical values:

     --      Network Type/bit rate   Metric

     --      >= 100 MBPS                 1
     --      Ethernet/802.3             10
     --      E1                         48
     --      T1 (ESF)                   65
     --       64 KBPS                 1562
     --       56 KBPS                 1785
     --       19.2 KBPS               5208
     --        9.6 KBPS              10416

     -- Routes that are not specified use the default (TOS 0) metric










     --  OSPF Virtual Interface Table

     --      The Virtual Interface Table describes the virtual
     --      links that the OSPF Process is configured to
     --      carry on.















     --  OSPF Neighbor Table

     --      The OSPF Neighbor Table describes all neighbors in
     --      the locality of the subject router.














     --  OSPF Virtual Neighbor Table

     --      This table describes all virtual neighbors.
     --      Since Virtual Links are configured in the
     --      virtual interface table, this table is read-only.












--
-- FILE: /users/sse/mibs/src/rfc/rfc1381.mib
--

-- (MNG) IMPORTed PositiveInteger from existing RFC



                          --  LAPB MIB

          lapb    OBJECT IDENTIFIER ::= { transmission 16 }

--          PositiveInteger ::= INTEGER (0..2147483647)

          IfIndexType     ::= INTEGER (1..2147483647)
          -- IfIndexType specifies an index object for a table
          -- with entries that match entries in the MIB-II ifTable.
          -- The value of the index for the table will match the
          -- ifIndex entry for same interface in the ifTable.
          -- The values of this object range from 1 to ifNumber
          -- inclusive.

          -- ###########################################################
          --                      LAPB Admn Table
          -- ###########################################################

          -- Support of the lapbAdmnTable is mandatory for all
          -- agents of systems that implement LAPB.



















          -- ###########################################################
          --                      LAPB operating parameters.
          -- ###########################################################

          -- Support of the lapbOperTable is mandatory for all
          -- agents of systems that implement LAPB.








                  -- See lapbOperTransmitN1FrameSize above










          -- ###########################################################
          --                      LAPB    Flow Table
          -- ###########################################################

          -- Support of the lapbFlowTable is mandatory for all
          -- agents of systems that implement LAPB.







                                  -- initial state or DISC received
                                  -- SABM sent
                                  -- Invalid frame received and
                                  -- FRMR sent
                                  -- DISC sent
                                  -- normal information transfer state
                                  -- SABM(E) sent and UA received, or
                                  -- SABM(E) received and UA sent
                                  -- invalid NS received and REJ sent
                                  -- T1 expired and RR sent
                                  -- RNR sent
                                  -- RNR received
                                  -- RNR received and RNR sent
                                  -- T1 expired, RNR sent
                                  -- T1 expired, RNR received
                                  -- T1 expired, RNR sent,
                                  -- and RNR received
                                  -- REJ sent and RNR received
                                  -- XID frame sent
                                  -- An error state other than
                                  -- a one defined above
                                  --  A state not listed above








          -- ###########################################################
          --                      LAPB    XID Table
          -- ###########################################################

          -- Support for the lapbXidTable is mandatory for all agents
          -- of systems that have a LAPB implementation using XID
          -- negotiation.  Agents of systems without XID negotiation
          -- support should not implement this table.











          -- ###########################################################
          --                      LAPB protocol versions
          -- ###########################################################

          lapbProtocolVersion OBJECT IDENTIFIER
                  ::= { lapb 5 }

          lapbProtocolIso7776v1986 OBJECT IDENTIFIER
                  ::= { lapbProtocolVersion 1 }

          lapbProtocolCcittV1980 OBJECT IDENTIFIER
                  ::= { lapbProtocolVersion 2 }

          lapbProtocolCcittV1984 OBJECT IDENTIFIER
                  ::= { lapbProtocolVersion 3 }

          -- The following describes some of the MIB-II interface
          -- objects and their relationship with the objects in this
          -- MIB extension.

          -- ifDescr:  describes the interface.   It should include
          -- identification information for the physical line and a
          -- description of the network.  For connections to PDNs,
          -- it should name the PDN.

          -- ifMtu: the maximum number of octets an upper layer can
          -- pass to this interface as a single frame.

          -- ifSpeed:


          -- ifAdminStatus:

          -- ifOperStatus:

          -- ifLastChange: the last time the state of the interface
          -- changed.  A reset is considered an instantaneous change to
          -- the ndm state and back to abm or abme.  This will be the
          -- last time that lapbFlowChangeReason and lapbFlowChanges
          -- changed.

          -- ifInOctets: contains the number of octets
          -- received from the peer LAPB including FCS.

          -- ifInUcastPkts: contains the number of I-frames delivered
          -- by this interface to a higher layer interface.

          -- ifInDiscards: contains the number of received
          -- frames discarded because of internal conditions
          -- (such as lack of buffering).

          -- ifInErrors: contains the number of Invalid frames received.
          -- This does not have any relationship with the number REJ,
          -- or RNR frames sent or received.

          -- ifInUnknownProtos: contains the number of frames
          -- that were correct but were dropped because they
          -- were inappropriate for the current state.  This
          -- includes an invalid Poll bit, an unknown address,
          -- or other condition such as an RNR when connection
          -- not established.  This also includes the number of
          -- DISC or other frames that were ignored because the
          -- link was not established and this interface was not
          -- configured to perform link setup on that type frame.

          -- ifOutOctets: number of octets sent to peer including
          -- FCS octets.

          -- ifOutUcastPkts: number of I-frames received from
          -- a higher layer for transmission to peer.

          -- ifOutDiscards: number of frames to be sent that were
          -- dropped due to internal conditions such as buffering etc.

          -- ifOutErrors: number of transmissions that failed
          -- due to errors or were considered invalid by the receiver.
          -- This does not have any relationship with the number REJ,
          -- or RNR frames sent or received.


          -- ifOutQLen: number of frames waiting to be transmitted.

          -- This MIB does not provide any support for:
          --      Multilink procedure (MLP) in ISO 7776 section 6
          --      LLC Pbit timer
          --      LLC REJ timer
          --      LLC Busy State Timer 7.8.1.4

          -- ###########################################################


--
-- FILE: /users/sse/mibs/src/rfc/rfc1382.mib
--



          x25     OBJECT IDENTIFIER ::= { transmission 5 }

          -- Support of the X25 subtree and all subtrees under it
          -- is mandatory for all agents of system that implement X.25.

          X121Address ::= OCTET STRING (SIZE(0..17))
           -- 0 to 17 bytes in length containing the ASCII
           -- characters [0-9], each octet contains one digit
           -- of the address.

          -- ###########################################################
          --            X.25 Administration Table
          -- ###########################################################

          x25AdmnTable OBJECT-TYPE


                  SYNTAX  SEQUENCE OF X25AdmnEntry
                  ACCESS  not-accessible
                  STATUS  mandatory
                  DESCRIPTION
                          "This table contains the administratively
                          set configuration parameters for an X.25
                          Packet Level Entity (PLE).

                         Most of the objects in this table have
                          corresponding objects in the x25OperTable.
                          This table contains the values as last set
                          by the administrator.  The x25OperTable
                          contains the values actually in use by an
                          X.25 PLE.

                          Changing an administrative value may or may
                          not change a current operating value.  The
                          operating value may not change until the
                          interface is restarted.  Some
                          implementations may change the values
                          immediately upon changing the administrative
                          table.  All implementations are required to
                          load the values from the administrative
                          table when initializing a PLE."
                  ::= { x25 1 }

          x25AdmnEntry OBJECT-TYPE
                  SYNTAX  X25AdmnEntry
                  ACCESS  not-accessible
                  STATUS  mandatory
                  DESCRIPTION
                          "Entries of x25AdmnTable."
                  INDEX { x25AdmnIndex }
                  ::= { x25AdmnTable 1 }

          X25AdmnEntry ::= SEQUENCE {
                  x25AdmnIndex
                          IfIndexType,
                  x25AdmnInterfaceMode
                          INTEGER,
                  x25AdmnMaxActiveCircuits
                          INTEGER,
                  x25AdmnPacketSequencing
                          INTEGER,
                  x25AdmnRestartTimer
                          PositiveInteger,
               x25AdmnCallTimer
                          PositiveInteger,


                  x25AdmnResetTimer
                          PositiveInteger,
                  x25AdmnClearTimer
                          PositiveInteger,
                  x25AdmnWindowTimer
                          PositiveInteger,
                  x25AdmnDataRxmtTimer
                          PositiveInteger,
                  x25AdmnInterruptTimer
                          PositiveInteger,
                  x25AdmnRejectTimer
                          PositiveInteger,
                  x25AdmnRegistrationRequestTimer
                          PositiveInteger,
                  x25AdmnMinimumRecallTimer
                          PositiveInteger,
                  x25AdmnRestartCount
                          INTEGER,
                  x25AdmnResetCount
                          INTEGER,
                  x25AdmnClearCount
                          INTEGER,
                  x25AdmnDataRxmtCount
                          INTEGER,
                  x25AdmnRejectCount
                          INTEGER,
                  x25AdmnRegistrationRequestCount
                          INTEGER,
                  x25AdmnNumberPVCs
                          INTEGER,
                  x25AdmnDefCallParamId
                          OBJECT IDENTIFIER,
                  x25AdmnLocalAddress
                          X121Address,
                  x25AdmnProtocolVersionSupported
                          OBJECT IDENTIFIER
                  }

          x25AdmnIndex OBJECT-TYPE
                  SYNTAX  IfIndexType
                  ACCESS  read-only
                  STATUS  mandatory
                  DESCRIPTION
                  "The ifIndex value for the X.25 Interface."
                  ::= { x25AdmnEntry 1 }

          x25AdmnInterfaceMode OBJECT-TYPE
                  SYNTAX  INTEGER {


                                  dte (1),
                                  dce (2),
                                  dxe (3)
                          }
                  ACCESS  read-write
                  STATUS  mandatory
                  DESCRIPTION
                          "Identifies DCE/DTE mode in which the
                          interface operates.  A value of dxe
                          indicates the mode will be determined by XID
                          negotiation."
                  REFERENCE "10733 5.9 interfaceMode"
                  ::= { x25AdmnEntry 2 }

          x25AdmnMaxActiveCircuits        OBJECT-TYPE
                  SYNTAX  INTEGER (0..4096)
                  ACCESS  read-write
                  STATUS  mandatory
                  DESCRIPTION
                          "The maximum number of circuits this PLE can
                          support; including PVCs."
                  REFERENCE "10733 5.9 maxActiveCircuits;
                          See ISO 8208, Section 3.7"
                  ::= { x25AdmnEntry 3 }

          x25AdmnPacketSequencing OBJECT-TYPE
                  SYNTAX  INTEGER {
                                  modulo8 (1),
                                  modulo128 (2)
                          }
                  ACCESS  read-write
                  STATUS  mandatory
                  DESCRIPTION
                          "The modulus of the packet sequence number
                          space."
                  REFERENCE "10733 extendedPacketSequencing;
                          See ISO 8208 Section 7.1.1"
                  ::= { x25AdmnEntry 4 }

          x25AdmnRestartTimer OBJECT-TYPE
               SYNTAX     PositiveInteger
                  ACCESS  read-write
                  STATUS  mandatory
                  DESCRIPTION
                          "The T20 restart timer in milliseconds."
                  REFERENCE "10733 5.9 restartTime
                          See ISO 8208 Section 4.1, table 26"
                  ::= { x25AdmnEntry 5 }


          x25AdmnCallTimer OBJECT-TYPE
                  SYNTAX  PositiveInteger
                  ACCESS  read-write
                  STATUS  mandatory
                  DESCRIPTION
                          "The T21 Call timer in milliseconds."
                  REFERENCE "10733 callTime;
                          See ISO 8208 Section 5.2.1, table 26"
                  ::= { x25AdmnEntry 6 }

          x25AdmnResetTimer OBJECT-TYPE
                  SYNTAX  PositiveInteger
                  ACCESS  read-write
                  STATUS  mandatory
                  DESCRIPTION
                          "The T22 Reset timer in milliseconds."
                  REFERENCE "10733 resetTime;
                          See ISO 8208 Section 8.1, table 26"
                  ::= { x25AdmnEntry 7 }

          x25AdmnClearTimer OBJECT-TYPE
                  SYNTAX  PositiveInteger
                  ACCESS  read-write
                  STATUS  mandatory
                  DESCRIPTION
                          "The T23 Clear timer in milliseconds."
                  REFERENCE "10733 clearTime;
                          See ISO 8208 Section 5.5.1, table 26"
                  ::= { x25AdmnEntry 8 }

          x25AdmnWindowTimer OBJECT-TYPE
                  SYNTAX  PositiveInteger
                  ACCESS  read-write
                  STATUS  mandatory
                  DESCRIPTION
                          "The T24 window status transmission timer in
                          milliseconds.  A value of 2147483647
                          indicates no window timer in use."
                  REFERENCE "10733 5.10.1 windowTime (opt);
                          See ISO 8208 Section 11.2.2, table 26"
                  ::= { x25AdmnEntry 9 }

          x25AdmnDataRxmtTimer OBJECT-TYPE
                  SYNTAX  PositiveInteger
                  ACCESS  read-write
                  STATUS  mandatory
                  DESCRIPTION
                          "The T25 data retransmission timer in


                          milliseconds.  A value of 2147483647
                          indicates no data retransmission timer in
                          use."
                  REFERENCE "10733 5.10.1 dataRetransmissionTime (opt);
                          See ISO 8208 Section 11.2.1, table 26"
                  ::= { x25AdmnEntry 10 }

          x25AdmnInterruptTimer OBJECT-TYPE
                  SYNTAX  PositiveInteger
                  ACCESS  read-write
                  STATUS  mandatory
                  DESCRIPTION
                          "The T26 interrupt timer in milliseconds.  A
                          value of 2147483647 indicates no interrupt
                          timer in use."
                  REFERENCE "10733 interruptTime;
                          See ISO 8208 Section 6.8.1, table 26"
                  ::= { x25AdmnEntry 11 }

          x25AdmnRejectTimer OBJECT-TYPE
                  SYNTAX  PositiveInteger
                  ACCESS  read-write
                  STATUS  mandatory
                  DESCRIPTION
                          "The T27 Reject retransmission timer in
                          milliseconds.  A value of 2147483647
                          indicates no reject timer in use."
                  REFERENCE "10733 5.10.1 dataRejectTime (opt);
                          See ISO 8208 Section 13.4.1, table 26"
                  ::= { x25AdmnEntry 12 }

          x25AdmnRegistrationRequestTimer OBJECT-TYPE
                  SYNTAX  PositiveInteger
                  ACCESS  read-write
                  STATUS  mandatory
                  DESCRIPTION
                          "The T28 registration timer in milliseconds.
                          A value of 2147483647 indicates no
                          registration timer in use."
                  REFERENCE "10733 5.8.1 registrationRequestTime (opt)
                          See ISO 8208    Section 13.1.1.1, table 26"
                  ::= { x25AdmnEntry 13 }

          x25AdmnMinimumRecallTimer OBJECT-TYPE
                  SYNTAX  PositiveInteger
                  ACCESS  read-write
                  STATUS  mandatory
                  DESCRIPTION


                          "Minimum time interval between unsuccessful
                          call attempts in milliseconds."
                  REFERENCE "10733 5.9 minimum RecallTimer"
                  ::= { x25AdmnEntry 14 }

          x25AdmnRestartCount OBJECT-TYPE
                  SYNTAX  INTEGER (0..65535)
                  ACCESS  read-write
                  STATUS  mandatory
                  DESCRIPTION
                          "The R20 restart retransmission count."
                  REFERENCE "10733 5.9 restartCount;
                          See ISO 8208    Section 4.1, table 27"
                  ::= { x25AdmnEntry 15 }

          x25AdmnResetCount OBJECT-TYPE
                  SYNTAX  INTEGER (0..65535)
                  ACCESS  read-write
                  STATUS  mandatory
                  DESCRIPTION
                          "The r22 Reset retransmission count."
                  REFERENCE "10733 resetCount;
                          See section ISO 8208 8.1, table 27"
                  ::= { x25AdmnEntry 16 }

          x25AdmnClearCount OBJECT-TYPE
                  SYNTAX  INTEGER (0..65535)
                  ACCESS  read-write
                  STATUS  mandatory
                  DESCRIPTION
                  "The r23 Clear retransmission count."
                  REFERENCE "10733 clearCount;
                          See ISO 8208 Section 5.5.1, table 27"
                  ::= { x25AdmnEntry 17 }

          x25AdmnDataRxmtCount OBJECT-TYPE
                  SYNTAX  INTEGER (0..65535)
                  ACCESS  read-write
                  STATUS  mandatory
                  DESCRIPTION
                          "The R25 Data retransmission count.  This
                          value is irrelevant if the
                          x25AdmnDataRxmtTimer indicates no timer in
                          use."
                  REFERENCE "10733 5.10.1 dataRetransmissionCount (opt)
                          See ISO 8208 Section 11.2.1, table 27"
                  ::= { x25AdmnEntry 18 }


          x25AdmnRejectCount OBJECT-TYPE
                  SYNTAX  INTEGER (0..65535)
                  ACCESS  read-write
                  STATUS  mandatory
                  DESCRIPTION
                          "The R27 reject retransmission count.  This
                          value is irrelevant if the
                          x25AdmnRejectTimer indicates no timer in
                          use."
                  REFERENCE "10733 5.10.1 dataRejectCount (opt)"
                  ::= { x25AdmnEntry 19 }

          x25AdmnRegistrationRequestCount OBJECT-TYPE
                  SYNTAX  INTEGER (0..65535)
                  ACCESS  read-write
                  STATUS  mandatory
                  DESCRIPTION
                          "The R28 Registration retransmission Count.
                          This value is irrelevant if the
                          x25AdmnRegistrationRequestTimer indicates no
                          timer in use."
                  REFERENCE "10733 5.8.1 registrationRequestCount (opt);
                          See ISO 8208    Section 13.1.1.1, table 27"
                  ::= { x25AdmnEntry 20 }

          x25AdmnNumberPVCs OBJECT-TYPE
                  SYNTAX  INTEGER (0..4096)
                  ACCESS  read-write
                  STATUS  mandatory
                  DESCRIPTION
                          "The number of PVC configured for this PLE.
                          The PVCs use channel numbers from 1 to this
                          number."
                  ::= { x25AdmnEntry 21 }

          x25AdmnDefCallParamId OBJECT-TYPE
                  SYNTAX  OBJECT IDENTIFIER
                  ACCESS  read-write
                  STATUS  mandatory
                  DESCRIPTION
                          "This identifies the instance of the
                          x25CallParmIndex for the entry in the
                          x25CallParmTable which contains the default
                          call parameters for this PLE."
                  ::= { x25AdmnEntry 22 }

          x25AdmnLocalAddress OBJECT-TYPE
                  SYNTAX  X121Address


                  ACCESS  read-write
                  STATUS  mandatory
                  DESCRIPTION
                          "The local address for this PLE subnetwork.
                          A zero length address maybe returned by PLEs
                          that only support PVCs."
                  REFERENCE "10733 5.9 localDTEAddress"
                  ::= { x25AdmnEntry 23 }

          x25AdmnProtocolVersionSupported OBJECT-TYPE
                  SYNTAX  OBJECT IDENTIFIER
                  ACCESS  read-write
                  STATUS  mandatory
                  DESCRIPTION
                          "Identifies the version of the X.25 protocol
                          this interface should support.  Object
                          identifiers for common versions are defined
                          below in the x25ProtocolVersion subtree."
                  REFERENCE "10733 5.9 protocolVersionSupported"
                  ::= { x25AdmnEntry 24 }

          -- ###########################################################
          --            X.25 Operational Table
          -- ###########################################################

          x25OperTable OBJECT-TYPE
                  SYNTAX  SEQUENCE OF X25OperEntry
                  ACCESS  not-accessible
                  STATUS  mandatory
                  DESCRIPTION
                          "The operation parameters in use by the X.25
                          PLE."
                  ::= { x25 2 }

          x25OperEntry OBJECT-TYPE
                  SYNTAX  X25OperEntry
                  ACCESS  not-accessible
                  STATUS  mandatory
                  DESCRIPTION
                          "Entries of x25OperTable."
                  INDEX { x25OperIndex }
                  ::= { x25OperTable 1 }

          X25OperEntry ::= SEQUENCE {
                  x25OperIndex
                          IfIndexType,
                  x25OperInterfaceMode


                          INTEGER,
                  x25OperMaxActiveCircuits
                          INTEGER,
                  x25OperPacketSequencing
                          INTEGER,
                  x25OperRestartTimer
                          PositiveInteger,
                  x25OperCallTimer
                          PositiveInteger,
                  x25OperResetTimer
                          PositiveInteger,
                  x25OperClearTimer
                          PositiveInteger,
                  x25OperWindowTimer
                          PositiveInteger,
                  x25OperDataRxmtTimer
                          PositiveInteger,
                  x25OperInterruptTimer
                          PositiveInteger,
                  x25OperRejectTimer
                          PositiveInteger,
               x25OperRegistrationRequestTimer
                          PositiveInteger,
                  x25OperMinimumRecallTimer
                          PositiveInteger,
                  x25OperRestartCount
                          INTEGER,
                  x25OperResetCount
                          INTEGER,
                  x25OperClearCount
                          INTEGER,
                  x25OperDataRxmtCount
                          INTEGER,
                  x25OperRejectCount
                          INTEGER,
                  x25OperRegistrationRequestCount
                          INTEGER,
                  x25OperNumberPVCs
                          INTEGER,
                  x25OperDefCallParamId
                          OBJECT IDENTIFIER,
                  x25OperLocalAddress
                          X121Address,
                  x25OperDataLinkId
                          OBJECT IDENTIFIER,
                  x25OperProtocolVersionSupported
                          OBJECT IDENTIFIER
                  }


          x25OperIndex OBJECT-TYPE
                  SYNTAX  IfIndexType
                  ACCESS  read-only
                  STATUS  mandatory
                  DESCRIPTION
                          "The ifIndex value for the X.25 interface."
                  ::= { x25OperEntry 1 }

          x25OperInterfaceMode OBJECT-TYPE
                  SYNTAX  INTEGER {
                                  dte (1),
                                  dce (2),
                                  dxe (3)
                          }
                  ACCESS  read-only
                  STATUS  mandatory
                  DESCRIPTION
                  "Identifies DCE/DTE mode in which the
                          interface operates.  A value of dxe
                          indicates the role will be determined by XID
                          negotiation at the Link Layer and that
                          negotiation has not yet taken place."
                  REFERENCE "10733 5.9 interfaceMode"
                  ::= { x25OperEntry 2 }

          x25OperMaxActiveCircuits        OBJECT-TYPE
                  SYNTAX  INTEGER (0..4096)
                  ACCESS  read-only
                  STATUS  mandatory
                  DESCRIPTION
                          "Maximum number of circuits this PLE can
                          support."
                  REFERENCE "10733 5.9 maxActiveCircuits
                          See ISO 8208, Section 3.7"
                  ::= { x25OperEntry 3 }

          x25OperPacketSequencing OBJECT-TYPE
                  SYNTAX  INTEGER {
                                  modulo8 (1),
                                  modulo128 (2)
                          }
                  ACCESS  read-only
                  STATUS  mandatory
                  DESCRIPTION
                          "The modulus of the packet sequence number
                          space."
                  REFERENCE "10733 extendedPacketSequencing;
                          See ISO 8208    Section 7.1.1"


                  ::= { x25OperEntry 4 }

          x25OperRestartTimer OBJECT-TYPE
                  SYNTAX  PositiveInteger
                  ACCESS  read-only
                  STATUS  mandatory
                  DESCRIPTION
                          "The T20 restart timer in milliseconds."
                  REFERENCE "10733 5.9 restartTime;
                          See ISO 8208    Section 4.1, table 26"
                  ::= { x25OperEntry 5 }

          x25OperCallTimer OBJECT-TYPE
                  SYNTAX  PositiveInteger
                  ACCESS  read-only
                  STATUS  mandatory
                  DESCRIPTION
                          "The T21 Call timer in milliseconds."
                  REFERENCE "10733 callTime;
                          See ISO 8208 Section 5.2.1, table 26"
                  ::= { x25OperEntry 6 }

          x25OperResetTimer OBJECT-TYPE
                  SYNTAX  PositiveInteger
                  ACCESS  read-only
                  STATUS  mandatory
                  DESCRIPTION
                          "The T22 Reset timer in milliseconds."
                  REFERENCE "10733 resetTime;
                          See ISO 8208    Section 8.1, table 26"
                  ::= { x25OperEntry 7 }

          x25OperClearTimer OBJECT-TYPE
                  SYNTAX  PositiveInteger
                  ACCESS  read-only
                  STATUS  mandatory
                  DESCRIPTION
                          "The T23 Clear timer in milliseconds."
                  REFERENCE "10733 clearTime;
                          See ISO 8208 Section 5.5.1, table 26"
                  ::= { x25OperEntry 8 }

          x25OperWindowTimer OBJECT-TYPE
                  SYNTAX  PositiveInteger
                  ACCESS  read-only
                  STATUS  mandatory
                  DESCRIPTION
                          "The T24 window status transmission timer


                          milliseconds.  A value of 2147483647
                          indicates no window timer in use."
                  REFERENCE "10733 5.10.1 windowTime (opt);
                          See ISO 8208 Section 11.2.2, table 26"
                  ::= { x25OperEntry 9 }

          x25OperDataRxmtTimer OBJECT-TYPE
                  SYNTAX  PositiveInteger
                  ACCESS  read-only
                  STATUS  mandatory
                  DESCRIPTION
                          "The T25 Data Retransmission timer in
                          milliseconds.  A value of 2147483647
                          indicates no data retransmission timer in
                          use."
                  REFERENCE "10733 5.10.1 dataRetransmissionTime (opt);
                          See ISO 8208 Section 11.2.1, table 26"
                  ::= { x25OperEntry 10 }

          x25OperInterruptTimer OBJECT-TYPE
                  SYNTAX  PositiveInteger
                  ACCESS  read-only
                  STATUS  mandatory
                  DESCRIPTION
                          "The T26 Interrupt timer in milliseconds.  A
                          value of 2147483647 indicates interrupts are
                          not being used."
                  REFERENCE "10733 interruptTime;
                          See ISO 8208 Section 6.8.1, table 26"
                  ::= { x25OperEntry 11 }

          x25OperRejectTimer OBJECT-TYPE
                  SYNTAX  PositiveInteger
                  ACCESS  read-only
                  STATUS  mandatory
                  DESCRIPTION
                          "The T27 Reject retransmission timer in
                          milliseconds.  A value of 2147483647
                          indicates no reject timer in use."
                  REFERENCE "10733 5.10.1 dataRejectTime (opt);
                          See ISO 8208 Section 13.4.1, table 26"
                  ::= { x25OperEntry 12 }

          x25OperRegistrationRequestTimer OBJECT-TYPE
                  SYNTAX  PositiveInteger
                  ACCESS  read-only
                  STATUS  mandatory
                  DESCRIPTION


                          "The T28 registration timer in milliseconds.
                          A value of 2147483647 indicates no
                          registration timer in use."
                  REFERENCE "10733 5.8.1 registrationRequestTime (opt);
                          See ISO 8208    Section 13.1.1.1, table 26"
                  ::= { x25OperEntry 13 }

          x25OperMinimumRecallTimer OBJECT-TYPE
                  SYNTAX  PositiveInteger
                  ACCESS  read-only
                  STATUS  mandatory
                  DESCRIPTION
                          "Minimum time interval between unsuccessful
                          call attempts in milliseconds."
                  REFERENCE "10733 5.9 minimum RecallTimer"
                  ::= { x25OperEntry 14 }

          x25OperRestartCount OBJECT-TYPE
                  SYNTAX  INTEGER (0..65535)
                  ACCESS  read-only
                  STATUS  mandatory
                  DESCRIPTION
                          "The R20 restart retransmission count."
                  REFERENCE "10733 5.9 restartCount
                          See ISO 8208    Section 4.1, table 27"
                  ::= { x25OperEntry 15 }

          x25OperResetCount OBJECT-TYPE
                  SYNTAX  INTEGER (0..65535)
                  ACCESS  read-only
                  STATUS  mandatory
                  DESCRIPTION
                          "The r22 Reset retransmission count."
                  REFERENCE "10733 resetCount;
                          See section ISO 8208 8.1, table 27"
                  ::= { x25OperEntry 16 }

          x25OperClearCount OBJECT-TYPE
                  SYNTAX  INTEGER (0..65535)
                  ACCESS  read-only
                  STATUS  mandatory
                  DESCRIPTION
                          "The r23 Clear retransmission count."
                  REFERENCE "10733 clearCount;
                          See ISO 8208 Section 5.5.1, table 27"
                  ::= { x25OperEntry 17 }

          x25OperDataRxmtCount OBJECT-TYPE


                  SYNTAX  INTEGER (0..65535)
                  ACCESS  read-only
                  STATUS  mandatory
                  DESCRIPTION
                          "The R25 Data retransmission count.  This
                          value is undefined if the
                          x25OperDataRxmtTimer indicates no timer in
                          use."
                  REFERENCE "10733 5.10.1 dataRetransmissionCount (opt);
                          See ISO 8208 Section 11.2.1, table 27"
                  ::= { x25OperEntry 18 }

          x25OperRejectCount OBJECT-TYPE
                  SYNTAX  INTEGER (0..65535)
                  ACCESS  read-only
                  STATUS  mandatory
                  DESCRIPTION
                          "The R27 reject retransmission count.  This
                          value is undefined if the x25OperRejectTimer
                          indicates no timer in use."
                  REFERENCE "10733 5.10.1 dataRejectCount (opt)"
                  ::= { x25OperEntry 19 }

          x25OperRegistrationRequestCount OBJECT-TYPE
                  SYNTAX  INTEGER (0..65535)
                  ACCESS  read-only
                  STATUS  mandatory
                  DESCRIPTION
                          "The R28 Registration retransmission Count.
                          This value is undefined if the
                          x25OperREgistrationRequestTimer indicates no
                          timer in use."
                  REFERENCE "10733 5.8.1 registrationRequestCount (opt);
                          See ISO 8208    Section 13.1.1.1, table 27"
                  ::= { x25OperEntry 20 }

          x25OperNumberPVCs OBJECT-TYPE
                  SYNTAX  INTEGER (0..4096)
                  ACCESS  read-only
                  STATUS  mandatory
                  DESCRIPTION
                          "The number of PVC configured for this PLE.
                          The PVCs use channel numbers from 1 to this
                          number."
                  ::= { x25OperEntry 21 }

          x25OperDefCallParamId OBJECT-TYPE
                  SYNTAX  OBJECT IDENTIFIER


                  ACCESS  read-only
                  STATUS  mandatory
                  DESCRIPTION
                          "This identifies the instance of the
                          x25CallParmIndex for the entry in the
                          x25CallParmTable that contains the default
                          call parameters for this PLE."
                  ::= { x25OperEntry 22 }

          x25OperLocalAddress OBJECT-TYPE
                  SYNTAX  X121Address
                  ACCESS  read-only
                  STATUS  mandatory
                  DESCRIPTION
                          "The local address for this PLE subnetwork.
                          A zero length address maybe returned by PLEs
                          that only support PVCs."
                  REFERENCE "10733 5.9 localDTEAddress"
                  ::= { x25OperEntry 23 }

          x25OperDataLinkId OBJECT-TYPE
                  SYNTAX  OBJECT IDENTIFIER
                  ACCESS  read-only
                  STATUS  mandatory
                  DESCRIPTION
                          "This identifies the instance of the index
                          object in the first table of the most device
                          specific MIB for the interface used by this
                          PLE."
                  ::= { x25OperEntry 24 }

          x25OperProtocolVersionSupported OBJECT-TYPE
                  SYNTAX  OBJECT IDENTIFIER
                  ACCESS  read-only
                  STATUS  mandatory
                  DESCRIPTION
                          "Identifies the version of the X.25 protocol
                          this interface supports.  Object identifiers
                          for common versions are defined below in the
                          x25ProtocolVersion subtree."
                  REFERENCE "10733 5.9 protocolVersionSupported"
                  ::= { x25OperEntry 25 }

          --      MIB-II also provides:

          -- ifDescr:
          -- On an X.25 interface this must include sufficient


          -- information to enable the system's administrator
          -- to determine the appropriate configuration
          -- information on a system having multiple X.25
          -- subnetworks.

          -- ifType: ddn-x25 or rfc877-x25
          --      an interface of type ddn-x25 will use an algorithm to
          --      translate between X.121 address and IP addresses.
          --      An interface of type rfc877-x25 will use a
          --      configuration table to translate between X.121
          --      addresses and IP addresses.

          -- ifMtu: the maximum PDU a higher layer can pass to X.25 or
          -- receive from X.25

          -- ifSpeed:
          -- This will be the value of the local clock for this line.
          -- A value of zero indicates external clocking.

          -- ifAdminStatus:

          -- ifOperStatus

          -- ifLastChange

          -- ###########################################################
          --            X.25 Statistics Table
          -- ###########################################################

          x25StatTable OBJECT-TYPE
                  SYNTAX  SEQUENCE OF X25StatEntry
                  ACCESS  not-accessible
                  STATUS  mandatory
                  DESCRIPTION
                          "Statistics information about this X.25
                          PLE."
                  ::= { x25 3 }

          x25StatEntry OBJECT-TYPE
                  SYNTAX  X25StatEntry
                  ACCESS  not-accessible
                  STATUS  mandatory
                  DESCRIPTION
                           "Entries of the x25StatTable."
                           INDEX { x25StatIndex }
                  ::= { x25StatTable 1 }


          X25StatEntry ::= SEQUENCE {
                  x25StatIndex
                          IfIndexType,
                  x25StatInCalls
                          Counter,
                  x25StatInCallRefusals
                          Counter,
                  x25StatInProviderInitiatedClears
                          Counter,
                  x25StatInRemotelyInitiatedResets
                          Counter,
                  x25StatInProviderInitiatedResets
                          Counter,
                  x25StatInRestarts
                          Counter,
                  x25StatInDataPackets
                          Counter,
                  x25StatInAccusedOfProtocolErrors
                          Counter,
                  x25StatInInterrupts
                          Counter,
                  x25StatOutCallAttempts
                          Counter,
                  x25StatOutCallFailures
                          Counter,
                  x25StatOutInterrupts
                          Counter,
                  x25StatOutDataPackets
                          Counter,
                  x25StatOutgoingCircuits
                          Gauge,
                  x25StatIncomingCircuits
                          Gauge,
                  x25StatTwowayCircuits
                          Gauge,
                  x25StatRestartTimeouts
                          Counter,
                  x25StatCallTimeouts
                          Counter,
                  x25StatResetTimeouts
                          Counter,
                  x25StatClearTimeouts
                          Counter,
                  x25StatDataRxmtTimeouts
                          Counter,
                  x25StatInterruptTimeouts
                          Counter,
                  x25StatRetryCountExceededs


                          Counter,
                  x25StatClearCountExceededs
                          Counter
                  }

          x25StatIndex OBJECT-TYPE
                  SYNTAX  IfIndexType
                  ACCESS  read-only
                  STATUS  mandatory
                  DESCRIPTION
                          "The ifIndex value for the X.25 interface."
                  ::= { x25StatEntry 1 }

          x25StatInCalls OBJECT-TYPE
                  SYNTAX  Counter
                  ACCESS  read-only
                  STATUS  mandatory
                  DESCRIPTION
                          "The number of incoming calls received."
                  ::= { x25StatEntry 2 }

          x25StatInCallRefusals OBJECT-TYPE
                  SYNTAX  Counter
                  ACCESS  read-only
                  STATUS  mandatory
                  DESCRIPTION
                          "The number of incoming calls refused.  This
                          includes calls refused by the PLE and by
                          higher layers.  This also includes calls
                          cleared because of restricted fast select."
                  ::= { x25StatEntry 3 }

          x25StatInProviderInitiatedClears        OBJECT-TYPE
                  SYNTAX  Counter
                  ACCESS  read-only
                  STATUS  mandatory
                  DESCRIPTION
                          "The number of clear requests with a cause
                          code other than DTE initiated."
                          REFERENCE "10733 providerInitiatedDisconnect"
                  ::= { x25StatEntry 4 }

          x25StatInRemotelyInitiatedResets        OBJECT-TYPE
                  SYNTAX  Counter
                  ACCESS  read-only
                  STATUS  mandatory
                  DESCRIPTION
                          "The number of reset requests received with


                          cause code DTE initiated."
                  REFERENCE "10733 remotelyInitiatedResets"
                  ::= { x25StatEntry 5 }

          x25StatInProviderInitiatedResets        OBJECT-TYPE
                  SYNTAX  Counter
                  ACCESS  read-only
                  STATUS  mandatory
                  DESCRIPTION
                          "The number of reset requests received with
                          cause code other than DTE initiated."
                  REFERENCE "10733 ProviderInitiatedResets"
                  ::= { x25StatEntry 6 }

          x25StatInRestarts OBJECT-TYPE
                  SYNTAX  Counter
                  ACCESS  read-only
                  STATUS  mandatory
                  DESCRIPTION
                          "The number of remotely initiated (including
                          provider initiated) restarts experienced by
                          the PLE excluding the restart associated
                          with bringing up the PLE interface.  This
                          only counts restarts received when the PLE
                          already has an established connection with
                          the remove PLE."
                  REFERENCE "10733 5.9 remotelyInitiatedRestarts"
                  ::= { x25StatEntry 7 }

          x25StatInDataPackets    OBJECT-TYPE
                  SYNTAX  Counter
                  ACCESS  read-only
                  STATUS  mandatory
                  DESCRIPTION
                          "The number of data packets received."
                          REFERENCE "10733 5.9 dataPacketsReceived."
                  ::= { x25StatEntry 8 }

          x25StatInAccusedOfProtocolErrors        OBJECT-TYPE
                  SYNTAX  Counter
                  ACCESS  read-only
                  STATUS  mandatory
                  DESCRIPTION
                          "The number of packets received containing a
                          procedure error cause code.  These include
                          clear, reset, restart, or diagnostic
                          packets."
                  REFERENCE "CD 10733 5.9 accusedOfProtocolError"


                  ::= { x25StatEntry 9 }

          x25StatInInterrupts OBJECT-TYPE
                  SYNTAX  Counter
                  ACCESS  read-only
                  STATUS  mandatory
                  DESCRIPTION
                          "The number of interrupt packets received by
                          the PLE or over the PVC/VC."
                  REFERENCE "10733 interruptPacketsReceived"
                  ::= { x25StatEntry 10 }

          x25StatOutCallAttempts OBJECT-TYPE
                  SYNTAX  Counter
                  ACCESS  read-only
                  STATUS  mandatory
                  DESCRIPTION
                          "The number of calls attempted."
                  REFERENCE "10733 5.9 callAttempts"
                  ::= { x25StatEntry 11 }

          x25StatOutCallFailures OBJECT-TYPE
                  SYNTAX  Counter
                  ACCESS  read-only
                  STATUS  mandatory
                  DESCRIPTION
                          "The number of call attempts which failed.
                          This includes calls that were cleared
                          because of restrictive fast select."
                  ::= { x25StatEntry 12 }

          x25StatOutInterrupts    OBJECT-TYPE
                  SYNTAX  Counter
                  ACCESS  read-only
                  STATUS  mandatory
                  DESCRIPTION
                          "The number of interrupt packets send by the
                          PLE or over the PVC/VC."
                  REFERENCE "10733 InterruptPacketsSent"
                  ::= { x25StatEntry 13 }

          x25StatOutDataPackets   OBJECT-TYPE
                  SYNTAX  Counter
                  ACCESS  read-only
                  STATUS  mandatory
                  DESCRIPTION
                          "The number of data packets sent by this
                          PLE."


                  REFERENCE "10733 dataPacketSent"
                  ::= { x25StatEntry 14 }

          x25StatOutgoingCircuits OBJECT-TYPE
                  SYNTAX  Gauge
                  ACCESS  read-only
                  STATUS  mandatory
                  DESCRIPTION
                          "The number of active outgoing circuits.
                          This includes call requests sent but not yet
                          confirmed.  This does not count PVCs."
                  ::= { x25StatEntry 15 }

          x25StatIncomingCircuits OBJECT-TYPE
                  SYNTAX  Gauge
                  ACCESS  read-only
                  STATUS  mandatory
                  DESCRIPTION
                          "The number of active Incoming Circuits.
                          This includes call indications received but
                          not yet acknowledged.  This does not count
                          PVCs."
                  ::= { x25StatEntry 16 }

          x25StatTwowayCircuits   OBJECT-TYPE
                  SYNTAX  Gauge
                  ACCESS  read-only
                  STATUS  mandatory
                  DESCRIPTION
                  "The number of active two-way Circuits.
                          This includes call requests sent but not yet
                          confirmed.  This does not count PVCs."
                  ::= { x25StatEntry 17 }

          x25StatRestartTimeouts OBJECT-TYPE
                  SYNTAX  Counter
                  ACCESS  read-only
                  STATUS  mandatory
                  DESCRIPTION
                          "The number of times the T20 restart timer
                          expired."
                  REFERENCE "10733 5.9 restartTimeouts"
                  ::= { x25StatEntry 18 }

          x25StatCallTimeouts OBJECT-TYPE
                  SYNTAX  Counter
                  ACCESS  read-only
                  STATUS  mandatory


                  DESCRIPTION
                          "The number of times the T21 call timer
                          expired."
                  REFERENCE "10733 5.9 callTimeouts"
                  ::= { x25StatEntry 19 }

          x25StatResetTimeouts    OBJECT-TYPE
                  SYNTAX  Counter
                  ACCESS  read-only
                  STATUS  mandatory
                  DESCRIPTION
                          "The number of times the T22 reset timer
                          expired."
                  REFERENCE "10733 5.9 resetTimeouts"
                  ::= { x25StatEntry 20 }

          x25StatClearTimeouts    OBJECT-TYPE
                  SYNTAX  Counter
                  ACCESS  read-only
                  STATUS  mandatory
                  DESCRIPTION
                          "The number of times the T23 clear timer
                          expired."
                  REFERENCE "10733 5.9 clearTimeouts"
                  ::= { x25StatEntry 21 }

          x25StatDataRxmtTimeouts OBJECT-TYPE
                  SYNTAX  Counter
                  ACCESS  read-only
                  STATUS  mandatory
                  DESCRIPTION
                          "The number of times the T25 data timer
                          expired."
                  REFERENCE "10733 5.9 dataRetransmissionsTimerExpiries"
                  ::= { x25StatEntry 22 }

          x25StatInterruptTimeouts        OBJECT-TYPE
                  SYNTAX  Counter
                  ACCESS  read-only
                  STATUS  mandatory
                  DESCRIPTION
                          "The number of times the T26 interrupt timer
                          expired."
                  REFERENCE "10733 5.9 interruptTimerExpires"
                  ::= { x25StatEntry 23 }

          x25StatRetryCountExceededs OBJECT-TYPE
                  SYNTAX  Counter


                  ACCESS  read-only
                  STATUS  mandatory
                  DESCRIPTION
                          "The number of times a retry counter was
                          exhausted."
                  REFERENCE "10733 5.9 retryCountsExceeded"
                  ::= { x25StatEntry 24 }

          x25StatClearCountExceededs OBJECT-TYPE
                  SYNTAX  Counter
                  ACCESS  read-only
                  STATUS  mandatory
                  DESCRIPTION
                          "The number of times the R23 clear count was
                          exceeded."
                  REFERENCE "10733 5.9 clearCountsExceeded"
                  ::= { x25StatEntry 25 }

          --      MIB-II also contains:

          -- ifInOctets: Number of data octets delivered to upper
          -- layer entities.

          -- ifInUcastPkts: Number of packets with a clear M-bit
          -- delivered to higher layer entities.

          -- ifDiscards: Number of packets dropped for lack of buffering

          -- ifInErrors: Number of packets received containing errors
            -- REFERENCE ProtocolErrorsDetectedLocally

          -- ifInUnknownProtos: Number of packets with unknown circuit
          -- identifier.

          -- ifOutOctets: Number of data octets delivered by
          --      X.25 to upper layers.

          -- ifOutUcastPkts: Number of packets with a clear M-bit
          -- received from higher layer entities.

          -- ###########################################################
          --                    X.25 Channel Table
          -- ###########################################################

          x25ChannelTable OBJECT-TYPE
                  SYNTAX  SEQUENCE OF X25ChannelEntry


                  ACCESS  not-accessible
                  STATUS  mandatory
                  DESCRIPTION
                          "These objects contain information about the
                          channel number configuration in an X.25 PLE.
                          These values are the configured values.
                          changes in these values after the interfaces
                          has started may not be reflected in the
                          operating PLE."
                  REFERENCE "See ISO 8208, Section 3.7"
                  ::= { x25 4 }

          x25ChannelEntry OBJECT-TYPE
                  SYNTAX  X25ChannelEntry
                  ACCESS  not-accessible
                  STATUS  mandatory
                  DESCRIPTION
                          "Entries of x25ChannelTable."
                  REFERENCE "This provides the information available
                          in 10733 logicalChannelAssignments."
                  INDEX { x25ChannelIndex }
                  ::= { x25ChannelTable 1    }

          X25ChannelEntry ::= SEQUENCE {
                  x25ChannelIndex
                          IfIndexType,
                  x25ChannelLIC
                          INTEGER,
                  x25ChannelHIC
                          INTEGER,
                  x25ChannelLTC
                          INTEGER,
                  x25ChannelHTC
                          INTEGER,
                  x25ChannelLOC
                          INTEGER,
                  x25ChannelHOC
                          INTEGER
                  }

          x25ChannelIndex OBJECT-TYPE
                  SYNTAX  IfIndexType
                  ACCESS  read-only
                  STATUS  mandatory
                  DESCRIPTION
                          "The ifIndex value for the X.25 Interface."
                  ::= { x25ChannelEntry 1 }


          x25ChannelLIC OBJECT-TYPE
                  SYNTAX  INTEGER (0..4095)
                  ACCESS  read-write
                  STATUS  mandatory
                  DESCRIPTION
                          "Lowest Incoming channel."
                  ::= { x25ChannelEntry 2 }

          x25ChannelHIC OBJECT-TYPE
                  SYNTAX  INTEGER (0..4095)
                  ACCESS  read-write
                  STATUS  mandatory
                  DESCRIPTION
                          "Highest Incoming channel.  A value of zero
                          indicates no channels in this range."
                  ::= { x25ChannelEntry 3 }

          x25ChannelLTC OBJECT-TYPE
                  SYNTAX  INTEGER (0..4095)
                  ACCESS  read-write
                  STATUS  mandatory
                  DESCRIPTION
                          "Lowest Two-way channel."
                  ::= { x25ChannelEntry 4 }

          x25ChannelHTC OBJECT-TYPE
                  SYNTAX  INTEGER (0..4095)
                  ACCESS  read-write
                  STATUS  mandatory
                  DESCRIPTION
                          "Highest Two-way channel.  A value of zero
                          indicates no channels in this range."
                  ::= { x25ChannelEntry 5 }

          x25ChannelLOC OBJECT-TYPE
                  SYNTAX  INTEGER (0..4095)
                  ACCESS  read-write
                  STATUS  mandatory
                  DESCRIPTION
                          "Lowest outgoing channel."
                  ::= { x25ChannelEntry 6 }

          x25ChannelHOC OBJECT-TYPE
                  SYNTAX  INTEGER (0..4095)
                  ACCESS  read-write
                  STATUS  mandatory
                  DESCRIPTION
                          "Highest outgoing channel.  A value of zero


                          indicates no channels in this range."
                  ::= { x25ChannelEntry 7 }

          -- ###########################################################
          --          X25 Per Circuits Information Table
          -- ###########################################################

          x25CircuitTable OBJECT-TYPE
                  SYNTAX  SEQUENCE OF X25CircuitEntry
                  ACCESS  not-accessible
                  STATUS  mandatory
                  DESCRIPTION
                          "These objects contain general information
                          about a specific circuit of an X.25 PLE."
                  ::= { x25 5 }

          x25CircuitEntry OBJECT-TYPE
                  SYNTAX  X25CircuitEntry
                  ACCESS  not-accessible
                  STATUS  mandatory
                  DESCRIPTION
                          "Entries of x25CircuitTable."
                  INDEX { x25CircuitIndex,
                          x25CircuitChannel }
                  ::= { x25CircuitTable 1 }

          X25CircuitEntry ::= SEQUENCE {
                  x25CircuitIndex
                          IfIndexType,
                  x25CircuitChannel
                          INTEGER,
                  x25CircuitStatus
                          INTEGER,
                  x25CircuitEstablishTime
                          TimeTicks,
                  x25CircuitDirection
                          INTEGER,
                  x25CircuitInOctets
                          Counter,
                  x25CircuitInPdus
                          Counter,
                  x25CircuitInRemotelyInitiatedResets
                          Counter,
                  x25CircuitInProviderInitiatedResets
                          Counter,


                  x25CircuitInInterrupts
                          Counter,
                  x25CircuitOutOctets
                          Counter,
                  x25CircuitOutPdus
                          Counter,
                  x25CircuitOutInterrupts
                          Counter,
                  x25CircuitDataRetransmissionTimeouts
                          Counter,
                  x25CircuitResetTimeouts
                          Counter,
                  x25CircuitInterruptTimeouts
                          Counter,
                  x25CircuitCallParamId
                          OBJECT IDENTIFIER,
                  x25CircuitCalledDteAddress
                          X121Address,
                  x25CircuitCallingDteAddress
                          X121Address,
                  x25CircuitOriginallyCalledAddress
                          X121Address,
                  x25CircuitDescr
                          DisplayString
                  }

          x25CircuitIndex OBJECT-TYPE
                  SYNTAX  IfIndexType
                  ACCESS  read-only
                  STATUS  mandatory
                  DESCRIPTION
                          "The ifIndex value for the X.25 Interface."
                  ::= { x25CircuitEntry 1 }

          x25CircuitChannel OBJECT-TYPE
                  SYNTAX  INTEGER (0..4095)
                  ACCESS  read-only
                  STATUS  mandatory
                  DESCRIPTION
                          "The channel number for this circuit."
                  ::= { x25CircuitEntry 2 }

          x25CircuitStatus OBJECT-TYPE
                  SYNTAX  INTEGER {               -- state table states
                                  invalid (1),
                                  closed (2),             -- (p1)
                                  calling (3),            -- (p2,p3,p5)
                                  open (4),               -- (p4)


                                  clearing (5),           -- (p6,p7)
                                  pvc (6),
                                  pvcResetting (7),
                                  startClear (8),         -- Close cmd
                                  startPvcResetting (9),  -- Reset cmd
                                  other (10)
                          }
                  ACCESS  read-write
                  STATUS  mandatory
                  DESCRIPTION
                          "This object reports the current status of
                          the circuit.

                          An existing instance of this object can only
                          be set to startClear, startPvcResetting, or
                          invalid.  An instance with the value calling
                          or open can only be set to startClear and
                          that action will start clearing the circuit.
                          An instance with the value PVC can only be
                          set to startPvcResetting or invalid and that
                          action resets the PVC or deletes the circuit
                          respectively.  The values startClear or
                          startPvcResetting will never be returned by
                          an agent.  An attempt to set the status of
                          an existing instance to a value other than
                          one of these values will result in an error.

                          A non-existing instance can be set to PVC to
                          create a PVC if the implementation supports
                          dynamic creation of PVCs.  Some
                          implementations may only allow creation and
                          deletion of PVCs if the interface is down.
                          Since the instance identifier will supply
                          the PLE index and the channel number,
                          setting this object alone supplies
                          sufficient information to create the
                          instance.  All the DEFVAL clauses for the
                          other objects of this table are appropriate
                          for creating a PVC; PLEs creating entries
                          for placed or accepted calls will use values
                          appropriate for the call rather than the
                          value of the DEFVAL clause.  Two managers
                          trying to create the same PVC can determine
                          from the return code which manager succeeded
                          and which failed (the failing manager fails
                          because it can not set a value of PVC for an
                          existing object).


                          An entry in the closed or invalid state may
                          be deleted or reused at the agent's
                          convence.  If the entry is kept in the
                          closed state, the values of the parameters
                          associated with the entry must be correct.
                          Closed implies the values in the circuit
                          table are correct.

                          The value of invalid indicates the other
                          values in the table are invalid.  Many
                          agents may never return a value of invalid
                          because they dynamically allocate and free
                          unused table entries.  An agent for a
                          statically configured systems can return
                          invalid to indicate the entry has not yet
                          been used so the counters contain no
                          information."
                  REFERENCE "See ISO 8208,
                                  table 33 for (p) state table"
                  ::= { x25CircuitEntry 3 }

          x25CircuitEstablishTime OBJECT-TYPE
                  SYNTAX  TimeTicks
                  ACCESS  read-only
                  STATUS  mandatory
                  DESCRIPTION
                          "The value of sysUpTime when the channel was
                          associated with this circuit.  For outgoing
                          SVCs, this is the time the first call packet
                          was sent.  For incoming SVCs, this is the
                          time the call indication was received.  For
                          PVCs this is the time the PVC was able to
                          pass data to a higher layer entity without
                          loss of data."
                  ::= { x25CircuitEntry 4 }

          x25CircuitDirection OBJECT-TYPE
                  SYNTAX  INTEGER {
                                  incoming (1),
                                  outgoing (2),
                                  pvc (3)
                          }
                  ACCESS  read-write
                  STATUS  mandatory
                  DESCRIPTION
                          "The direction of the call that established
                          this circuit."
                  REFERENCE "10733 direction"


                  DEFVAL { pvc }
                  ::= { x25CircuitEntry 5 }

                          -- X25 Circuit data flow statistics

          x25CircuitInOctets OBJECT-TYPE
                  SYNTAX  Counter
                  ACCESS  read-only
                  STATUS  mandatory
                  DESCRIPTION
                          "The number of octets of user data delivered
                          to upper layer."
                  REFERENCE "5.11 octetsReceivedCounter"
                  ::= { x25CircuitEntry 6 }

          x25CircuitInPdus OBJECT-TYPE
                  SYNTAX  Counter
                  ACCESS  read-only
                  STATUS  mandatory
                  DESCRIPTION
                          "The number of PDUs received for this
                          circuit."
                  REFERENCE "10733 5.11 dataPacketsReceived"
                  ::= { x25CircuitEntry 7 }

          x25CircuitInRemotelyInitiatedResets OBJECT-TYPE
                  SYNTAX  Counter
                  ACCESS  read-only
                  STATUS  mandatory
                  DESCRIPTION
                          "The number of Resets received for this
                          circuit with cause code of DTE initiated."
                  REFERENCE "10733 remotelyInitiatedResets"
                  ::= { x25CircuitEntry 8 }

          x25CircuitInProviderInitiatedResets OBJECT-TYPE
                  SYNTAX  Counter
                  ACCESS  read-only
                  STATUS  mandatory
                  DESCRIPTION
                          "The number of Resets received for this
                          circuit with cause code other than DTE
                          initiated."
                  REFERENCE "10733 ProviderInitiatedResets"
                  ::= { x25CircuitEntry 9 }

          x25CircuitInInterrupts OBJECT-TYPE
                  SYNTAX  Counter


                  ACCESS  read-only
                  STATUS  mandatory
                  DESCRIPTION
                          "The number of interrupt packets received
                          for this circuit."
                  REFERENCE "10733 interruptPacketsReceived"
                  ::= { x25CircuitEntry 10 }

          x25CircuitOutOctets OBJECT-TYPE
                  SYNTAX  Counter
                  ACCESS  read-only
                  STATUS  mandatory
                  DESCRIPTION
                          "The number of octets of user data sent for
                          this circuit."
                  REFERENCE "10733 5.11 octetsSentCounter"
                  ::= { x25CircuitEntry 11 }

          x25CircuitOutPdus OBJECT-TYPE
                  SYNTAX  Counter
                  ACCESS  read-only
                  STATUS  mandatory
                  DESCRIPTION
                          "The number of PDUs sent for this circuit."
                  REFERENCE "10733 5.11 dataPacketsSent"
                  ::= { x25CircuitEntry 12 }

          x25CircuitOutInterrupts OBJECT-TYPE
                  SYNTAX  Counter
                  ACCESS  read-only
                  STATUS  mandatory
                  DESCRIPTION
                          "The number of interrupt packets sent on
                          this circuit."
                  REFERENCE "10733 interruptPacketsSent"
                  ::= { x25CircuitEntry 13 }

                          -- X25 circuit timer statistics

          x25CircuitDataRetransmissionTimeouts OBJECT-TYPE
                  SYNTAX  Counter
                  ACCESS  read-only
                  STATUS  mandatory
                  DESCRIPTION
                          "The number of times the T25 data
                          retransmission timer expired for this
                          circuit."


                  REFERENCE "10733 5.11 dataRetransmissionTimerExpiries"
                  ::= { x25CircuitEntry 14 }

          x25CircuitResetTimeouts OBJECT-TYPE
                  SYNTAX  Counter
                  ACCESS  read-only
                  STATUS  mandatory
                  DESCRIPTION
                          "The number of times the T22 reset timer
                          expired for this circuit."
                  REFERENCE "10733 5.11 resetTimeouts"
                  ::= { x25CircuitEntry 15 }

          x25CircuitInterruptTimeouts OBJECT-TYPE
                  SYNTAX  Counter
                  ACCESS  read-only
                  STATUS  mandatory
                  DESCRIPTION
                          "The number of times the T26 Interrupt timer
                          expired for this circuit."
                  REFERENCE "10733 interruptTimerExpiries"
                  ::= { x25CircuitEntry 16 }

          x25CircuitCallParamId OBJECT-TYPE
                  SYNTAX  OBJECT IDENTIFIER
                  ACCESS  read-write
                  STATUS  mandatory
                  DESCRIPTION
                          "This identifies the instance of the
                          x25CallParmIndex for the entry in the
                          x25CallParmTable which contains the call
                          parameters in use with this circuit.  The
                          entry referenced must contain the values
                          that are currently in use by the circuit
                          rather than proposed values.  A value of
                          NULL indicates the circuit is a PVC or is
                          using all the default parameters."
                  DEFVAL { {0 0} }
                  ::= { x25CircuitEntry 17 }

          x25CircuitCalledDteAddress OBJECT-TYPE
                  SYNTAX  X121Address
                  ACCESS  read-write
                  STATUS  mandatory
                  DESCRIPTION
                          "For incoming calls, this is the called
                          address from the call indication packet.
                          For outgoing calls, this is the called


                          address from the call confirmation packet.
                          This will be zero length for PVCs."
                  REFERENCE "10733 calledDTEAddress"
                  DEFVAL { ''h }
                  ::= { x25CircuitEntry 18 }

          x25CircuitCallingDteAddress OBJECT-TYPE
                  SYNTAX  X121Address
                  ACCESS  read-write
                  STATUS  mandatory
                  DESCRIPTION
                          "For incoming calls, this is the calling
                          address from the call indication packet.
                          For outgoing calls, this is the calling
                          address from the call confirmation packet.
                          This will be zero length for PVCs."
                  REFERENCE "10733 callingDTEAddress"
                  DEFVAL { ''h }
                  ::= { x25CircuitEntry 19 }

          x25CircuitOriginallyCalledAddress OBJECT-TYPE
                  SYNTAX  X121Address
                  ACCESS  read-write
                  STATUS  mandatory
                  DESCRIPTION
                          "For incoming calls, this is the address in
                          the call Redirection or Call Deflection
                          Notification facility if the call was
                          deflected or redirected, otherwise it will
                          be called address from the call indication
                          packet.  For outgoing calls, this is the
                          address from the call request packet.  This
                          will be zero length for PVCs."
                  REFERENCE "10733 originallyCalledAddress"
                  DEFVAL { ''h }
                  ::= { x25CircuitEntry 20 }

          x25CircuitDescr OBJECT-TYPE
                  SYNTAX  DisplayString (SIZE (0..255))
                  ACCESS  read-write
                  STATUS  mandatory
                  DESCRIPTION
                          "A descriptive string associated with this
                          circuit.  This provides a place for the
                          agent to supply any descriptive information
                          it knows about the use or owner of the
                          circuit.  The agent may return the process
                          identifier and user name for the process


                          using the circuit.  Alternative the agent
                          may return the name of the configuration
                          entry that caused a bridge to establish the
                          circuit.  A zero length value indicates the
                          agent doesn't have any additional
                          information."
                  DEFVAL { ''h }
                  ::= { x25CircuitEntry 21 }

          -- ###########################################################
          --              The Cleared Circuit Table
          -- ###########################################################

          x25ClearedCircuitEntriesRequested OBJECT-TYPE
                  SYNTAX  PositiveInteger
                  ACCESS  read-write
                  STATUS  mandatory
                  DESCRIPTION
                          "The requested number of entries for the
                          agent to keep in the x25ClearedCircuit
                          table."
                  ::= { x25 6 }

          x25ClearedCircuitEntriesGranted OBJECT-TYPE
                  SYNTAX  PositiveInteger
                  ACCESS  read-only
                  STATUS  mandatory
                  DESCRIPTION
                          "The actual number of entries the agent will
                          keep in the x25ClearedCircuit Table."
                  ::= { x25 7 }

          x25ClearedCircuitTable  OBJECT-TYPE
                  SYNTAX SEQUENCE OF      X25ClearedCircuitEntry
                  ACCESS not-accessible
                  STATUS  mandatory
                  DESCRIPTION
                          "A table of entries about closed circuits.
                          Entries must be made in this table whenever
                          circuits are closed and the close request or
                          close indication packet contains a clearing
                          cause other than DTE Originated or a
                          Diagnostic code field other than Higher
                          Layer Initiated disconnection-normal.  An
                          agent may optionally make entries for normal
                          closes (to record closing facilities or


                          other information).

                          Agents will delete the oldest entry in the
                          table when adding a new entry would exceed
                          agent resources.  Agents are required to
                          keep the last entry put in the table and may
                          keep more entries.  The object
                          x25OperClearEntriesGranted returns the
                          maximum number of entries kept in the
                          table."
                  REFERENCE "See ISO 8208 Section 12.2.3.1.1
                                  and 12.2.3.1.2"
                  ::= { x25 8 }

          x25ClearedCircuitEntry  OBJECT-TYPE
                  SYNTAX  X25ClearedCircuitEntry
                  ACCESS  not-accessible
                  STATUS  mandatory
                  DESCRIPTION
                          "Information about a cleared circuit."
                  INDEX { x25ClearedCircuitIndex }
                  ::= { x25ClearedCircuitTable 1 }

          X25ClearedCircuitEntry ::= SEQUENCE {
                  x25ClearedCircuitIndex
                          PositiveInteger,
                  x25ClearedCircuitPleIndex
                          IfIndexType,
                  x25ClearedCircuitTimeEstablished
                          TimeTicks,
                  x25ClearedCircuitTimeCleared
                          TimeTicks,
                  x25ClearedCircuitChannel
                          INTEGER,
                  x25ClearedCircuitClearingCause
                          INTEGER,
                  x25ClearedCircuitDiagnosticCode
                          INTEGER,
                  x25ClearedCircuitInPdus
                          Counter,
                  x25ClearedCircuitOutPdus
                          Counter,
                  x25ClearedCircuitCalledAddress
                          X121Address,
                  x25ClearedCircuitCallingAddress
                          X121Address,
                  x25ClearedCircuitClearFacilities
                          OCTET STRING


                  }

          x25ClearedCircuitIndex OBJECT-TYPE
                  SYNTAX  PositiveInteger
                  ACCESS  read-only
                  STATUS  mandatory
                  DESCRIPTION
                          "An index that uniquely distinguishes one
                          entry in the clearedCircuitTable from
                          another.  This index will start at
                          2147483647 and will decrease by one for each
                          new entry added to the table.  Upon reaching
                          one, the index will reset to 2147483647.
                          Because the index starts at 2147483647 and
                          decreases, a manager may do a getnext on
                          entry zero and obtain the most recent entry.
                          When the index has the value of 1, the next
                          entry will delete all entries in the table
                          and that entry will be numbered 2147483647."
                  ::= { x25ClearedCircuitEntry 1 }

          x25ClearedCircuitPleIndex OBJECT-TYPE
                  SYNTAX  IfIndexType
                  ACCESS  read-only
                  STATUS  mandatory
                  DESCRIPTION
                          "The value of ifIndex for the PLE which
                          cleared the circuit that created the entry."
                  ::= { x25ClearedCircuitEntry 2 }

          x25ClearedCircuitTimeEstablished OBJECT-TYPE
                  SYNTAX  TimeTicks
                  ACCESS  read-only
                  STATUS  mandatory
                  DESCRIPTION
                          "The value of sysUpTime when the circuit was
                          established.  This will be the same value
                          that was in the x25CircuitEstablishTime for
                          the circuit."
                  ::= { x25ClearedCircuitEntry 3 }

          x25ClearedCircuitTimeCleared OBJECT-TYPE
                  SYNTAX  TimeTicks
                  ACCESS  read-only
                  STATUS  mandatory
                  DESCRIPTION
                          "The value of sysUpTime when the circuit was
                          cleared.  For locally initiated clears, this


                          will be the time when the clear confirmation
                          was received.  For remotely initiated
                          clears, this will be the time when the clear
                          indication was received."
                  ::= { x25ClearedCircuitEntry 4 }

          x25ClearedCircuitChannel OBJECT-TYPE
                  SYNTAX  INTEGER (0..4095)
                  ACCESS  read-only
                  STATUS  mandatory
                  DESCRIPTION
                          "The channel number for the circuit that was
                          cleared."
                  ::= { x25ClearedCircuitEntry 5 }

          x25ClearedCircuitClearingCause OBJECT-TYPE
                  SYNTAX  INTEGER (0..255)
                  ACCESS  read-only
                  STATUS  mandatory
                  DESCRIPTION
                          "The Clearing Cause from the clear request
                          or clear indication packet that cleared the
                          circuit."
                  REFERENCE "See ISO 8208 Section 12.2.3.1.1"
                  ::= { x25ClearedCircuitEntry 6 }

          x25ClearedCircuitDiagnosticCode OBJECT-TYPE
                  SYNTAX  INTEGER (0..255)
                  ACCESS  read-only
                  STATUS  mandatory
                  DESCRIPTION
                          "The Diagnostic Code from the clear request
                          or clear indication packet that cleared the
                          circuit."
                  REFERENCE "See ISO 8208 Section 12.2.3.1.2"
                  ::= { x25ClearedCircuitEntry 7 }

          x25ClearedCircuitInPdus OBJECT-TYPE
                  SYNTAX  Counter
                  ACCESS  read-only
                  STATUS  mandatory
                  DESCRIPTION
                          "The number of PDUs received on the
                          circuit."
                  ::= { x25ClearedCircuitEntry 8 }

          x25ClearedCircuitOutPdus OBJECT-TYPE
                  SYNTAX  Counter


                  ACCESS  read-only
                  STATUS  mandatory
                  DESCRIPTION
                          "The number of PDUs transmitted on the
                          circuit."
                  ::= { x25ClearedCircuitEntry 9 }

          x25ClearedCircuitCalledAddress OBJECT-TYPE
                  SYNTAX  X121Address
                  ACCESS  read-only
                  STATUS  mandatory
                  DESCRIPTION
                          "The called address from the cleared
                          circuit."
                  ::= { x25ClearedCircuitEntry 10 }

          x25ClearedCircuitCallingAddress OBJECT-TYPE
                  SYNTAX  X121Address
                  ACCESS  read-only
                  STATUS  mandatory
                  DESCRIPTION
                          "The calling address from the cleared
                          circuit."
                  ::= { x25ClearedCircuitEntry 11 }

          x25ClearedCircuitClearFacilities OBJECT-TYPE
                  SYNTAX  OCTET STRING (SIZE (0..109))
                  ACCESS  read-only
                  STATUS  mandatory
                  DESCRIPTION
                          "The facilities field from the clear request
                          or clear indication packet that cleared the
                          circuit.  A size of zero indicates no
                          facilities were present."
                  ::= { x25ClearedCircuitEntry 12 }

          -- ###########################################################
          --                The Call Parameter Table
          -- ###########################################################

          x25CallParmTable OBJECT-TYPE
                  SYNTAX  SEQUENCE OF X25CallParmEntry
                  ACCESS  not-accessible
                  STATUS  mandatory
                  DESCRIPTION


                          "These objects contain the parameters that
                          can be varied between X.25 calls.  The
                          entries in this table are independent of the
                          PLE.  There exists only one of these tables
                          for the entire system.  The indexes for the
                          entries are independent of any PLE or any
                          circuit.  Other tables reference entries in
                          this table.  Entries in this table can be
                          used for default PLE parameters, for
                          parameters to use to place/answer a call,
                          for the parameters currently in use for a
                          circuit, or parameters that were used by a
                          circuit.

                          The number of references to a given set of
                          parameters can be found in the
                          x25CallParmRefCount object sharing the same
                          instance identifier with the parameters.
                          The value of this reference count also
                          affects the access of the objects in this
                          table.  An object in this table with the
                          same instance identifier as the instance
                          identifier of an x25CallParmRefCount must be
                          consider associated with that reference
                          count.  An object with an associated
                          reference count of zero can be written (if
                          its ACCESS clause allows it).  An object
                          with an associated reference count greater
                          than zero can not be written (regardless of
                          the ACCESS clause).  This ensures that a set
                          of call parameters being referenced from
                          another table can not be modified or changed
                          in a ways inappropriate for continued use by
                          that table."
                  ::= { x25 9 }

          x25CallParmEntry OBJECT-TYPE
                  SYNTAX  X25CallParmEntry
                  ACCESS  not-accessible
                  STATUS  mandatory
                  DESCRIPTION
                          "Entries of x25CallParmTable."
                  INDEX { x25CallParmIndex }
                  ::= { x25CallParmTable 1 }

          X25CallParmEntry ::= SEQUENCE {
                  x25CallParmIndex
                          PositiveInteger,


                  x25CallParmStatus
                          EntryStatus,
                  x25CallParmRefCount
                          PositiveInteger,
                  x25CallParmInPacketSize
                          INTEGER,
                  x25CallParmOutPacketSize
                          INTEGER,
                  x25CallParmInWindowSize
                          INTEGER,
                  x25CallParmOutWindowSize
                          INTEGER,
                  x25CallParmAcceptReverseCharging
                          INTEGER,
                  x25CallParmProposeReverseCharging
                          INTEGER,
                  x25CallParmFastSelect
                          INTEGER,
                  x25CallParmInThruPutClasSize
                          INTEGER,
                  x25CallParmOutThruPutClasSize
                          INTEGER,
                  x25CallParmCug
                          DisplayString,
                  x25CallParmCugoa
                          DisplayString,
                  x25CallParmBcug
                          DisplayString,
                  x25CallParmNui
                          OCTET STRING,
                  x25CallParmChargingInfo
                          INTEGER,
                  x25CallParmRpoa
                          DisplayString,
                  x25CallParmTrnstDly
                          INTEGER,
                  x25CallParmCallingExt
                          DisplayString,
                  x25CallParmCalledExt
                          DisplayString,
                  x25CallParmInMinThuPutCls
                          INTEGER,
                  x25CallParmOutMinThuPutCls
                          INTEGER,
                  x25CallParmEndTrnsDly
                          OCTET STRING,
                  x25CallParmPriority
                          OCTET STRING,


                  x25CallParmProtection
                          DisplayString,
                  x25CallParmExptData
                          INTEGER,
                  x25CallParmUserData
                          OCTET STRING,
                  x25CallParmCallingNetworkFacilities
                          OCTET STRING,
                  x25CallParmCalledNetworkFacilities
                          OCTET STRING
                  }

          x25CallParmIndex OBJECT-TYPE
                  SYNTAX  PositiveInteger
                  ACCESS  read-only
                  STATUS  mandatory
                  DESCRIPTION
                          "A value that distinguishes this entry from
                          another entry.  Entries in this table are
                          referenced from other objects which identify
                          call parameters.

                          It is impossible to know which other objects
                          in the MIB reference entries in the table by
                          looking at this table.  Because of this,
                          changes to parameters must be accomplished
                          by creating a new entry in this table and
                          then changing the referencing table to
                          identify the new entry.

                          Note that an agent will only use the values
                          in this table when another table is changed
                          to reference those values.  The number of
                          other tables that reference an index object
                          in this table can be found in
                          x25CallParmRefCount.  The value of the
                          reference count will affect the writability
                          of the objects as explained above.

                          Entries in this table which have a reference
                          count of zero maybe deleted at the convence
                          of the agent.  Care should be taken by the
                          agent to give the NMS sufficient time to
                          create a reference to newly created entries.

                          Should a Management Station not find a free
                          index with which to create a new entry, it
                          may feel free to delete entries with a


                          reference count of zero.  However in doing
                          so the Management Station much realize it
                          may impact other Management Stations."
                  ::= { x25CallParmEntry 1 }

          x25CallParmStatus OBJECT-TYPE
                  SYNTAX  EntryStatus
                  ACCESS  read-write
                  STATUS  mandatory
                  DESCRIPTION
                          "The status of this call parameter entry.
                          See RFC 1271 for details of usage."
                  ::= { x25CallParmEntry 2 }

          x25CallParmRefCount OBJECT-TYPE
                  SYNTAX  PositiveInteger
                  ACCESS  read-only
                  STATUS  mandatory
                  DESCRIPTION
                          "The number of references know by a
                          management station to exist to this set of
                          call parameters.  This is the number of
                          other objects that have returned a value of,
                          and will return a value of, the index for
                          this set of call parameters.  Examples of
                          such objects are the x25AdmnDefCallParamId,
                          x25OperDataLinkId, or x25AdmnDefCallParamId
                          objects defined above."
                  ::= { x25CallParmEntry 3 }

          x25CallParmInPacketSize OBJECT-TYPE
                  SYNTAX  INTEGER (0..4096)
                  ACCESS  read-write
                  STATUS  mandatory
                  DESCRIPTION
                          "The maximum receive packet size in octets
                          for a circuit.  A size of zero for a circuit
                          means use the PLE default size.  A size of
                          zero for the PLE means use a default size of
                          128."
                  REFERENCE "10733 proposedPacketSize;
                          See ISO 8208 Section 15.2.2.1.1"
                  DEFVAL { 128 }
                  ::= { x25CallParmEntry 4 }

          x25CallParmOutPacketSize OBJECT-TYPE
                  SYNTAX  INTEGER (0..4096)
                  ACCESS  read-write


                  STATUS  mandatory
                  DESCRIPTION
                          "The maximum transmit packet size in octets
                          for a circuit.  A size of zero for a circuit
                          means use the PLE default size.  A size of
                          zero for the PLE default means use a default
                          size of 128."
                  REFERENCE "10733 proposedPacketSize;
                          See ISO 8208 Section 15.2.2.1.1"
                  DEFVAL { 128 }
                  ::= { x25CallParmEntry 5 }

          x25CallParmInWindowSize OBJECT-TYPE
                  SYNTAX  INTEGER (0..127)
                  ACCESS  read-write
                  STATUS  mandatory
                  DESCRIPTION
                          "The receive window size for a circuit.  A
                          size of zero for a circuit means use the PLE
                          default size.  A size of zero for the PLE
                          default means use 2."
                  REFERENCE "10733 proposedWindowSize;
                          See ISO 8208 Section 15.2.2.1.2"
                  DEFVAL { 2 }
                  ::= { x25CallParmEntry 6 }

          x25CallParmOutWindowSize OBJECT-TYPE
                  SYNTAX  INTEGER (0..127)
                  ACCESS  read-write
                  STATUS  mandatory
                  DESCRIPTION
                          "The transmit window size for a circuit.  A
                          size of zero for a circuit means use the PLE
                          default size.  A size of zero for the PLE
                          default means use 2."
                  REFERENCE "10733 proposedWindowSize;
                          See ISO 8208 Section 15.2.2.1.2"
                  DEFVAL { 2 }
                  ::= { x25CallParmEntry 7 }

          x25CallParmAcceptReverseCharging OBJECT-TYPE
                  SYNTAX  INTEGER {
                                  default (1),
                                  accept (2),
                                  refuse (3),
                                  neverAccept (4)
                          }
                  ACCESS  read-write


                  STATUS  mandatory
                  DESCRIPTION
                          "An enumeration defining if the PLE will
                          accept or refuse charges.  A value of
                          default for a circuit means use the PLE
                          default value.  A value of neverAccept is
                          only used for the PLE default and indicates
                          the PLE will never accept reverse charging.
                          A value of default for a PLE default means
                          refuse."
                  REFERENCE "10733 acceptReverseCharging"
                  DEFVAL { refuse }
                  ::= { x25CallParmEntry 8 }

          x25CallParmProposeReverseCharging OBJECT-TYPE
                  SYNTAX  INTEGER {
                                  default (1),
                                  reverse (2),
                                  local (3)
                          }
                  ACCESS  read-write
                  STATUS  mandatory
                  DESCRIPTION
                          "An enumeration defining if the PLE should
                          propose reverse or local charging.  The
                          value of default for a circuit means use the
                          PLE default.  The value of default for the
                          PLE default means use local."
                  REFERENCE "10733 proposedPacketSize;
                          See ISO 8208 Section 15.2.2.6"
                  DEFVAL { local }
                  ::= { x25CallParmEntry 9 }

          x25CallParmFastSelect OBJECT-TYPE
                  SYNTAX  INTEGER {
                                  default (1),
                                  notSpecified (2),
                                  fastSelect (3),
                                  restrictedFastResponse (4),
                                  noFastSelect (5),
                                  noRestrictedFastResponse (6)
                          }
                  ACCESS  read-write
                  STATUS  mandatory
                  DESCRIPTION
                          "Expresses preference for use of fast select
                          facility.  The value of default for a
                          circuit is the PLE default.  A value of


                          default for the PLE means noFastSelect.  A
                          value of noFastSelect or
                          noRestrictedFastResponse indicates a circuit
                          may not use fast select or restricted fast
                          response."
                  REFERENCE "10733 fastSelect;
                  Sec ISO 8208 Section 15.2.2.6"
                  DEFVAL { noFastSelect }
                  ::= { x25CallParmEntry 10 }

          x25CallParmInThruPutClasSize    OBJECT-TYPE
                  SYNTAX  INTEGER {
                                  tcReserved1 (1),
                                  tcReserved2 (2),
                                  tc75 (3),
                                  tc150 (4),
                                  tc300 (5),
                                  tc600 (6),
                                  tc1200  (7),
                                  tc2400  (8),
                                  tc4800  (9),
                                  tc9600  (10),
                                  tc19200 (11),
                                  tc48000 (12),
                                  tc64000 (13),
                                  tcReserved14 (14),
                                  tcReserved15 (15),
                                  tcReserved0 (16),
                                  tcNone  (17),
                                  tcDefault (18)
                          }
                  ACCESS  read-write
                  STATUS  mandatory
                  DESCRIPTION
                          "The incoming throughput class to negotiate.
                          A value of tcDefault for a circuit means use
                          the PLE default.  A value of tcDefault for
                          the PLE default means tcNone.  A value of
                          tcNone means do not negotiate throughtput
                          class."
                  REFERENCE "See ISO 8208 Section 15.2.2.2, table 18"
                  DEFVAL { tcNone }
                  ::= { x25CallParmEntry 11 }

          x25CallParmOutThruPutClasSize   OBJECT-TYPE
                  SYNTAX  INTEGER {
                                  tcReserved1 (1),
                                  tcReserved2 (2),


                                  tc75 (3),
                                  tc150 (4),
                                  tc300 (5),
                          tc600 (6),
                                  tc1200  (7),
                                  tc2400  (8),
                                  tc4800  (9),
                                  tc9600  (10),
                                  tc19200 (11),
                                  tc48000 (12),
                                  tc64000 (13),
                                  tcReserved14 (14),
                                  tcReserved15 (15),
                                  tcReserved0 (16),
                                  tcNone  (17),
                                  tcDefault (18)
                          }
                  ACCESS  read-write
                  STATUS  mandatory
                  DESCRIPTION
                          "The outgoing throughput class to negotiate.
                          A value of tcDefault for a circuit means use
                          the PLE default.  A value of tcDefault for
                          the PLE default means use tcNone.  A value
                          of tcNone means do not negotiate throughtput
                          class."
                  REFERENCE "See ISO 8208 Section 15.2.2.2, table 18"
                  DEFVAL { tcNone }
                  ::= { x25CallParmEntry 12 }

          x25CallParmCug  OBJECT-TYPE
                  SYNTAX  DisplayString (SIZE(0..4))
                  ACCESS  read-write
                  STATUS  mandatory
                  DESCRIPTION
                          "The Closed User Group to specify.  This
                          consists of two or four octets containing
                          the characters 0 through 9.  A zero length
                          string indicates no facility requested.  A
                          string length of three containing the
                          characters DEF for a circuit means use the
                          PLE default, (the PLE default parameter may
                          not reference an entry of DEF.)"
                  REFERENCE "See ISO 8208 Section 15.2.2.3"
                  DEFVAL { ''h }
                  ::= { x25CallParmEntry 13 }

          x25CallParmCugoa        OBJECT-TYPE


                  SYNTAX  DisplayString (SIZE(0..4))
                  ACCESS  read-write
                  STATUS  mandatory
                  DESCRIPTION
                          "The Closed User Group with Outgoing Access
                          to specify.  This consists of two or four
                          octets containing the characters 0 through
                          9.  A string length of three containing the
                          characters DEF for a circuit means use the
                          PLE default (the PLE default parameters may
                          not reference an entry of DEF).  A zero
                          length string indicates no facility
                          requested."
                  REFERENCE "See ISO 8208 Section 15.2.2.4"
                  DEFVAL { ''h }
                  ::= { x25CallParmEntry 14 }

          x25CallParmBcug OBJECT-TYPE
                  SYNTAX  DisplayString (SIZE(0..3))
                  ACCESS  read-write
                  STATUS  mandatory
                  DESCRIPTION
                          "The Bilateral Closed User Group to specify.
                          This consists of two octets containing the
                          characters 0 through 9.  A string length of
                          three containing the characters DEF for a
                          circuit means use the PLE default (the PLE
                          default parameter may not reference an entry
                          of DEF).  A zero length string indicates no
                          facility requested."
                  REFERENCE "See ISO 8208 Section 15.2.2.5"
                  DEFVAL { ''h }
                  ::= { x25CallParmEntry 15 }

          x25CallParmNui  OBJECT-TYPE
                  SYNTAX  OCTET STRING (SIZE(0..108))
                  ACCESS  read-write
                  STATUS  mandatory
                  DESCRIPTION
                          "The Network User Identifier facility.  This
                          is binary value to be included immediately
                          after the length field.  The PLE will supply
                          the length octet.  A zero length string
                          indicates no facility requested.  This value
                          is ignored for the PLE default parameters
                          entry."
                  REFERENCE "See ISO 8208 Section 15.2.2.7"
                  DEFVAL { ''h }


                  ::= { x25CallParmEntry 16 }

          x25CallParmChargingInfo OBJECT-TYPE
                  SYNTAX INTEGER {
                                  default (1),
                                  noFacility (2),
                                  noChargingInfo (3),
                                  chargingInfo (4)
                          }
                  ACCESS  read-write
                  STATUS  mandatory
                  DESCRIPTION
                          "The charging Information facility.  A value
                          of default for a circuit means use the PLE
                          default.  The value of default for the
                          default PLE parameters means use noFacility.
                          The value of noFacility means do not include
                          a facility."
                  REFERENCE "See ISO 8208 Section 15.2.2.8"
                  DEFVAL { noFacility }
                  ::= { x25CallParmEntry 17 }

          x25CallParmRpoa OBJECT-TYPE
                  SYNTAX  DisplayString (SIZE(0..108))
                  ACCESS  read-write
                  STATUS  mandatory
                  DESCRIPTION
                          "The RPOA facility.  The octet string
                          contains n * 4 sequences of the characters
                          0-9 to specify a facility with n entries.
                          The octet string containing the 3 characters
                          DEF for a circuit specifies use of the PLE
                          default (the entry for the PLE default may
                          not contain DEF).  A zero length string
                          indicates no facility requested."
                  REFERENCE "See ISO 8208, section 15.2.2.9"
                  DEFVAL { ''h }
                  ::= { x25CallParmEntry 18 }

          x25CallParmTrnstDly     OBJECT-TYPE
                  SYNTAX  INTEGER (0..65537)
                  ACCESS  read-write
                  STATUS  mandatory
                  DESCRIPTION
                          "The Transit Delay Selection and Indication
                          value.  A value of 65536 indicates no
                          facility requested.  A value of 65537 for a
                          circuit means use the PLE default (the PLE


                          default parameters entry may not use the
                          value 65537).  The value 65535 may only be
                          used to indicate the value in use by a
                          circuit."
                  REFERENCE "See ISO 8208, Section 15.2.2.13"
                  DEFVAL { 65536 }
                  ::= { x25CallParmEntry 19 }

                  -- The following parameters are for CCITT facilities.

          x25CallParmCallingExt OBJECT-TYPE
                  SYNTAX  DisplayString (SIZE(0..40))
                  ACCESS  read-write
                  STATUS  mandatory
                  DESCRIPTION
                          "The Calling Extension facility.  This
                          contains one of the following:

                          A sequence of hex digits with the value to
                          be put in the facility. These digits will be
                          converted to binary by the agent and put in
                          the facility.  These octets do not include
                          the length octet.

                          A value containing the three character DEF
                          for a circuit means use the PLE default,
                          (the entry for the PLE default parameters
                          may not use the value DEF).

                          A zero length string indicates no facility
                          requested."
                  REFERENCE "See ISO 8208 Section 15.3.2.1"
                  DEFVAL { ''h }
                  ::= { x25CallParmEntry 20 }

          x25CallParmCalledExt OBJECT-TYPE
                  SYNTAX  DisplayString (SIZE(0..40))
                  ACCESS  read-write
                  STATUS  mandatory
                  DESCRIPTION
                          "The Called Extension facility.  This
                          contains one of the following:

                          A sequence of hex digits with the value to
                          be put in the facility.  These digits will be
                          converted to binary by the agent and put in
                          the facility.  These octets do not include


                          the length octet.

                          A value containing the three character DEF
                          for a circuit means use the PLE default,
                          (the entry for the PLE default parameters
                          may not use the value DEF).

                          A zero length string indicates no facility
                          requested."
                  REFERENCE "See ISO 8208 Section 15.3.2.2"
                  DEFVAL { ''h }
                  ::= { x25CallParmEntry 21 }

          x25CallParmInMinThuPutCls       OBJECT-TYPE
                  SYNTAX  INTEGER (0..17)
                  ACCESS  read-write
                  STATUS  mandatory
                  DESCRIPTION
                          "The minimum input throughput Class.  A
                          value of 16 for a circuit means use the PLE
                          default (the PLE parameters entry may not
                          use this value).  A value of 17 indicates no
                          facility requested."
                  REFERENCE "See ISO 8208 Section 15.3.2.3"
                  DEFVAL { 17 }
                  ::= { x25CallParmEntry 22 }

          x25CallParmOutMinThuPutCls OBJECT-TYPE
                  SYNTAX  INTEGER (0..17)
                  ACCESS  read-write
                  STATUS  mandatory
                  DESCRIPTION
                          "The minimum output throughput Class.  A
                          value of 16 for a circuit means use the PLE
                          default (the PLE parameters entry may not
                          use this value).  A value of 17 indicates no
                          facility requested."
                  REFERENCE "See ISO 8208 Section 15.3.2.3"
                  DEFVAL { 17 }
                  ::= { x25CallParmEntry 23 }

          x25CallParmEndTrnsDly OBJECT-TYPE
                  SYNTAX  OCTET STRING (SIZE(0..6))
                  ACCESS  read-write
                  STATUS  mandatory
                  DESCRIPTION
                          "The End-to-End Transit Delay to negotiate.
                          An octet string of length 2, 4, or 6


                          contains the facility encoded as specified
                          in ISO/IEC 8208 section 15.3.2.4.  An octet
                          string of length 3 containing the three
                          character DEF for a circuit means use the
                          PLE default (the entry for the PLE default
                          can not contain the characters DEF).  A zero
                          length string indicates no facility
                          requested."
                  REFERENCE "See ISO 8208 Section 15.3.2.4"
                  DEFVAL { ''h }
                  ::= { x25CallParmEntry 24 }

          x25CallParmPriority OBJECT-TYPE
                  SYNTAX  OCTET STRING (SIZE(0..6))
                  ACCESS  read-write
                  STATUS  mandatory
                  DESCRIPTION
                          "The priority facility to negotiate.  The
                          octet string encoded as specified in ISO/IEC
                          8208 section 15.3.2.5.  A zero length string
                          indicates no facility requested.  The entry
                          for the PLE default parameters must be zero
                          length."
                  REFERENCE "See ISO 8208 Section 15.3.2.5"
                  DEFVAL { ''h }
                  ::= { x25CallParmEntry 25 }

          x25CallParmProtection OBJECT-TYPE
                  SYNTAX  DisplayString (SIZE(0..108))
                  ACCESS  read-write
                  STATUS  mandatory
                  DESCRIPTION
                          "A string contains the following:
                          A hex string containing the value for the
                          protection facility.  This will be converted
                          from hex to the octets actually in the
                          packet by the agent.  The agent will supply
                          the length field and the length octet is not
                          contained in this string.

                          An string containing the 3 characters DEF
                          for a circuit means use the PLE default (the
                          entry for the PLE default parameters may not
                          use the value DEF).

                          A zero length string mean no facility
                          requested."
                  REFERENCE "See ISO 8208 Section 15.3.2.5"


                  DEFVAL { ''h }
                  ::= { x25CallParmEntry 26 }

          x25CallParmExptData OBJECT-TYPE
                  SYNTAX  INTEGER {
                                  default (1),
                                  noExpeditedData (2),
                                  expeditedData (3)
                          }
                  ACCESS  read-write
                  STATUS  mandatory
                  DESCRIPTION
                          "The Expedited Data facility to negotiate.
                          A value of default for a circuit means use
                          the PLE default value.  The entry for the
                          PLE default parameters may not have the
                          value default."
                  REFERENCE "See ISO 8208 Section 15.3.2.7"
                  DEFVAL { noExpeditedData }
                  ::= { x25CallParmEntry 27 }

          x25CallParmUserData     OBJECT-TYPE
                  SYNTAX  OCTET STRING (SIZE (0..128))
                  ACCESS  read-write
                  STATUS  mandatory
                  DESCRIPTION
                          "The call user data as placed in the packet.
                          A zero length string indicates no call user
                          data.  If both the circuit call parameters
                          and the PLE default have call user data
                          defined, the data from the circuit call
                          parameters will be used.  If only the PLE
                          has data defined, the PLE entry will be
                          used.  If neither the circuit call
                          parameters or the PLE default entry has a
                          value, no call user data will be sent."
                  REFERENCE "See ISO 8208 Section 12.2.1.1.6, 12.2.1.2"
                  DEFVAL { ''h }
                  ::= { x25CallParmEntry 28 }

          x25CallParmCallingNetworkFacilities     OBJECT-TYPE
                  SYNTAX  OCTET STRING (SIZE (0..108))
                  ACCESS  read-write
                  STATUS  mandatory
                  DESCRIPTION
                          "The calling network facilities.  The
                          facilities are encoded here exactly as
                          encoded in the call packet.  These


                          facilities do not include the marker
                          facility code.

                          A zero length string in the entry for the
                          parameter to use when establishing a circuit
                          means use the PLE default.  A zero length
                          string in the entry for PLE default
                          parameters indicates no default facilities."
                  REFERENCE "See ISO 8206 Section 15.1, category b"
                  DEFVAL { ''h }
                  ::= { x25CallParmEntry 29 }

          x25CallParmCalledNetworkFacilities      OBJECT-TYPE
                  SYNTAX  OCTET STRING (SIZE (0..108))
                  ACCESS  read-write
                  STATUS  mandatory
                  DESCRIPTION
                          "The called network facilities.  The
                          facilities are encoded here exactly as
                          encoded in the call packet.  These
                          facilities do not include the marker
                          facility code.

                          A zero length string in the entry for the
                          parameter to use when establishing a circuit
                          means use the PLE default.  A zero length
                          string in the entry for PLE default
                          parameters indicates no default facilities."
                  REFERENCE "See ISO 8206 Section 15.1, category c"
                  DEFVAL { ''h }
                  ::= { x25CallParmEntry 30 }

          -- ###########################################################
          --              X.25 Traps
          -- ###########################################################

          x25Restart      TRAP-TYPE
                  ENTERPRISE  x25
                  VARIABLES { x25OperIndex }
                  DESCRIPTION
                          "This trap means the X.25 PLE sent or
                          received a restart packet.  The restart that
                          brings up the link should not send a
                          x25Restart trap so the interface should send
                          a linkUp trap.  Sending this trap means the
                          agent does not send a linkDown and linkUp
                          trap."
                  ::= 1


          x25Reset        TRAP-TYPE
                  ENTERPRISE  x25
                  VARIABLES {  x25CircuitIndex,
                          x25CircuitChannel }
                  DESCRIPTION
                          "If the PLE sends or receives a reset, the
                          agent should send an x25Reset trap."
                  ::= 2

          -- ###########################################################
          --              X.25 Protocol Version Identifiers
          -- ###########################################################

          x25ProtocolVersion OBJECT IDENTIFIER
                  ::= { x25 10 }

                  -- X.25 CCITT 1976 version.
          x25protocolCcittV1976 OBJECT IDENTIFIER
                  ::= { x25ProtocolVersion 1 }

                  -- X.25 CCITT 1980 version.
          x25protocolCcittV1980 OBJECT IDENTIFIER
                  ::= { x25ProtocolVersion 2 }

                  -- X.25 CCITT 1984 version.
          x25protocolCcittV1984 OBJECT IDENTIFIER
                  ::= { x25ProtocolVersion 3 }

                  -- X.25 CCITT 1988 version.
          x25protocolCcittV1988 OBJECT IDENTIFIER
                  ::= { x25ProtocolVersion 4 }

                  -- X.25 1987 version of ISO 8208.
          x25protocolIso8208V1987 OBJECT IDENTIFIER
                  ::= { x25ProtocolVersion 5 }

                  -- X.25 1989 version of ISO 8208.
          x25protocolIso8208V1989 OBJECT IDENTIFIER
                  ::= { x25ProtocolVersion 6 }

          -- ###########################################################


--
-- FILE: /users/sse/mibs/src/rfc/rfc1516.mib
--

-- imported MacAddress from BRIDGE-MIB


   snmpDot3RptrMgt OBJECT IDENTIFIER ::= { mib-2 22 }

   -- All representations of MAC addresses in this MIB Module use,
   -- as a textual convention (i.e., this convention does not affect
   -- their encoding), the data type:

   -- MacAddress ::= OCTET STRING (SIZE (6))    a 6 octet address in
                                             -- the "canonical" order
   -- defined by IEEE 802.1a, i.e., as if it were transmitted least
   -- significant bit first.

   --                      References
   --
   -- The following references are used throughout this MIB:
   --

   -- [IEEE 802.3 Std]
   --    refers to IEEE 802.3/ISO 8802-3 Information processing
   --    systems - Local area networks - Part 3: Carrier sense
   --    multiple access with collision detection (CSMA/CD)
   --    access method and physical layer specifications
   --    (2nd edition, September 21, 1990).
   --
   -- [IEEE 802.3 Rptr Mgt]
   --    refers to IEEE P802.3K, 'Layer Management for 10 Mb/s
   --    Baseband Repeaters, Section 19,' Draft Supplement to
   --    ANSI/IEEE 802.3, (Draft 8, April 9, 1992)

   --                      MIB Groups
   --
   -- The rptrBasicPackage group is mandatory.
   -- The rptrMonitorPackage and rptrAddrTrackPackage
   -- groups are optional.

   rptrBasicPackage
       OBJECT IDENTIFIER ::= { snmpDot3RptrMgt 1 }

   rptrMonitorPackage
       OBJECT IDENTIFIER ::= { snmpDot3RptrMgt 2 }

   rptrAddrTrackPackage
       OBJECT IDENTIFIER ::= { snmpDot3RptrMgt 3 }

   -- object identifiers for organizing the information
   -- in the groups by repeater, port-group, and port

   rptrRptrInfo
       OBJECT IDENTIFIER ::= { rptrBasicPackage 1 }
   rptrGroupInfo
       OBJECT IDENTIFIER ::= { rptrBasicPackage 2 }
   rptrPortInfo
       OBJECT IDENTIFIER ::= { rptrBasicPackage 3 }

   rptrMonitorRptrInfo
       OBJECT IDENTIFIER ::= { rptrMonitorPackage 1 }
   rptrMonitorGroupInfo
       OBJECT IDENTIFIER ::= { rptrMonitorPackage 2 }
   rptrMonitorPortInfo
       OBJECT IDENTIFIER ::= { rptrMonitorPackage 3 }

   rptrAddrTrackRptrInfo     -- this subtree is currently unused

       OBJECT IDENTIFIER ::= { rptrAddrTrackPackage 1 }
   rptrAddrTrackGroupInfo    -- this subtree is currently unused
       OBJECT IDENTIFIER ::= { rptrAddrTrackPackage 2 }
   rptrAddrTrackPortInfo
       OBJECT IDENTIFIER ::= { rptrAddrTrackPackage 3 }

   --
   --                    The BASIC GROUP
   --
   -- Implementation of the Basic Group is mandatory for all
   -- managed repeaters.

   --
   -- Basic Repeater Information
   --
   -- Configuration, status, and control objects for the overall
   -- repeater
   --

   rptrGroupCapacity OBJECT-TYPE
       SYNTAX    INTEGER (1..1024)
       ACCESS    read-only
       STATUS    mandatory
       DESCRIPTION
               "The rptrGroupCapacity is the number of groups
               that can be contained within the repeater.  Within
               each managed repeater, the groups are uniquely
               numbered in the range from 1 to rptrGroupCapacity.

               Some groups may not be present in the repeater, in
               which case the actual number of groups present
               will be less than rptrGroupCapacity.  The number
               of groups present will never be greater than
               rptrGroupCapacity.

               Note:  In practice, this will generally be the
               number of field-replaceable units (i.e., modules,
               cards, or boards) that can fit in the physical
               repeater enclosure, and the group numbers will
               correspond to numbers marked on the physical
               enclosure."
       REFERENCE
               "Reference IEEE 802.3 Rptr Mgt, 19.2.3.2,
               aRepeaterGroupCapacity."
       ::= { rptrRptrInfo 1 }

   rptrOperStatus OBJECT-TYPE

       SYNTAX  INTEGER {
                   other(1),            -- undefined or unknown status
                   ok(2),               -- no known failures
                   rptrFailure(3),      -- repeater-related failure
                   groupFailure(4),     -- group-related failure
                   portFailure(5),      -- port-related failure
                   generalFailure(6)    -- failure, unspecified type
               }
       ACCESS    read-only
       STATUS    mandatory
       DESCRIPTION
               "The rptrOperStatus object indicates the
               operational state of the repeater.  The
               rptrHealthText object may be consulted for more
               specific information about the state of the
               repeater's health.

               In the case of multiple kinds of failures (e.g.,
               repeater failure and port failure), the value of
               this attribute shall reflect the highest priority
               failure in the following order, listed highest
               priority first:

                   rptrFailure(3)
                   groupFailure(4)
                   portFailure(5)
                   generalFailure(6)."
       REFERENCE
               "Reference IEEE 802.3 Rptr Mgt, 19.2.3.2,
               aRepeaterHealthState."
       ::= { rptrRptrInfo 2 }

   rptrHealthText OBJECT-TYPE
       SYNTAX    DisplayString (SIZE (0..255))
       ACCESS    read-only
       STATUS    mandatory
       DESCRIPTION
               "The health text object is a text string that
               provides information relevant to the operational
               state of the repeater.  Agents may use this string
               to provide detailed information on current
               failures, including how they were detected, and/or
               instructions for problem resolution.  The contents
               are agent-specific."
       REFERENCE
               "Reference IEEE 802.3 Rptr Mgt, 19.2.3.2,
               aRepeaterHealthText."
       ::= { rptrRptrInfo 3 }

   rptrReset OBJECT-TYPE
       SYNTAX    INTEGER {
                     noReset(1),
                     reset(2)
                 }
       ACCESS    read-write
       STATUS    mandatory
       DESCRIPTION
               "Setting this object to reset(2) causes a
               transition to the START state of Fig 9-2 in
               section 9 [IEEE 802.3 Std].

               Setting this object to noReset(1) has no effect.
               The agent will always return the value noReset(1)
               when this object is read.

               After receiving a request to set this variable to
               reset(2), the agent is allowed to delay the reset
               for a short period.  For example, the implementor
               may choose to delay the reset long enough to allow
               the SNMP response to be transmitted.  In any
               event, the SNMP response must be transmitted.

               This action does not reset the management counters
               defined in this document nor does it affect the
               portAdminStatus parameters.  Included in this
               action is the execution of a disruptive Self-Test
               with the following characteristics:  a) The nature
               of the tests is not specified.  b) The test resets
               the repeater but without affecting management
               information about the repeater.  c) The test does
               not inject packets onto any segment.  d) Packets
               received during the test may or may not be
               transferred.  e) The test does not interfere with
               management functions.

               After performing this self-test, the agent will
               update the repeater health information (including
               rptrOperStatus and rptrHealthText), and send a
               rptrHealth trap."
       REFERENCE
               "Reference IEEE 802.3 Rptr Mgt, 19.2.3.3,
               acResetRepeater."
       ::= { rptrRptrInfo 4 }

   rptrNonDisruptTest OBJECT-TYPE
       SYNTAX    INTEGER {
                     noSelfTest(1),

                     selfTest(2)
                 }
       ACCESS    read-write
       STATUS    mandatory
       DESCRIPTION
               "Setting this object to selfTest(2) causes the
               repeater to perform a agent-specific, non-
               disruptive self-test that has the following
               characteristics:  a) The nature of the tests is
               not specified.  b) The test does not change the
               state of the repeater or management information
               about the repeater.  c) The test does not inject
               packets onto any segment.  d) The test does not
               prevent the relay of any packets.  e) The test
               does not interfere with management functions.

               After performing this test, the agent will update
               the repeater health information (including
               rptrOperStatus and rptrHealthText) and send a
               rptrHealth trap.

               Note that this definition allows returning an
               'okay' result after doing a trivial test.

               Setting this object to noSelfTest(1) has no
               effect.  The agent will always return the value
               noSelfTest(1) when this object is read."
       REFERENCE
               "Reference IEEE 802.3 Rptr Mgt, 19.2.3.3,
               acExecuteNonDisruptiveSelfTest."
       ::= { rptrRptrInfo 5 }

   rptrTotalPartitionedPorts OBJECT-TYPE
       SYNTAX    Gauge
       ACCESS    read-only
       STATUS    mandatory
       DESCRIPTION
               "This object returns the total number of ports in
               the repeater whose current state meets all three
               of the following criteria:  rptrPortOperStatus
               does not have the value notPresent(3),
               rptrPortAdminStatus is enabled(1), and
               rptrPortAutoPartitionState is autoPartitioned(2)."
       ::= { rptrRptrInfo 6 }

   --
   -- The Basic Port Group Table
   --

   rptrGroupTable OBJECT-TYPE
       SYNTAX    SEQUENCE OF RptrGroupEntry
       ACCESS    not-accessible
       STATUS    mandatory
       DESCRIPTION
               "Table of descriptive and status information about
               the groups of ports."
       ::= { rptrGroupInfo 1 }

   rptrGroupEntry OBJECT-TYPE
       SYNTAX    RptrGroupEntry
       ACCESS    not-accessible
       STATUS    mandatory
       DESCRIPTION
               "An entry in the table, containing information
               about a single group of ports."
       INDEX    { rptrGroupIndex }
       ::= { rptrGroupTable 1 }

   RptrGroupEntry ::=
       SEQUENCE {
           rptrGroupIndex
               INTEGER,
           rptrGroupDescr
               DisplayString,
           rptrGroupObjectID
               OBJECT IDENTIFIER,
           rptrGroupOperStatus
               INTEGER,
           rptrGroupLastOperStatusChange
               TimeTicks,
           rptrGroupPortCapacity
               INTEGER
       }

   rptrGroupIndex OBJECT-TYPE
       SYNTAX    INTEGER (1..1024)
       ACCESS    read-only
       STATUS    mandatory
       DESCRIPTION
               "This object identifies the group within the
               repeater for which this entry contains
               information.  This value is never greater than
               rptrGroupCapacity."

       REFERENCE
               "Reference IEEE 802.3 Rptr Mgt, 19.2.5.2,
               aGroupID."
       ::= { rptrGroupEntry 1 }

   rptrGroupDescr OBJECT-TYPE
       SYNTAX    DisplayString (SIZE (0..255))
       ACCESS    read-only
       STATUS    mandatory
       DESCRIPTION
               "A textual description of the group.  This value
               should include the full name and version
               identification of the group's hardware type and
               indicate how the group is differentiated from
               other types of groups in the repeater.  Plug-in
               Module, Rev A' or 'Barney Rubble 10BASE-T 4-port
               SIMM socket Version 2.1' are examples of valid
               group descriptions.

               It is mandatory that this only contain printable
               ASCII characters."
       ::= { rptrGroupEntry 2 }

   rptrGroupObjectID OBJECT-TYPE
       SYNTAX    OBJECT IDENTIFIER
       ACCESS    read-only
       STATUS    mandatory
       DESCRIPTION
               "The vendor's authoritative identification of the
               group.  This value may be allocated within the SMI
               enterprises subtree (1.3.6.1.4.1) and provides a
               straight-forward and unambiguous means for
               determining what kind of group is being managed.

               For example, this object could take the value
               1.3.6.1.4.1.4242.1.2.14 if vendor 'Flintstones,
               Inc.' was assigned the subtree 1.3.6.1.4.1.4242,
               and had assigned the identifier
               1.3.6.1.4.1.4242.1.2.14 to its 'Wilma Flintstone
               6-Port FOIRL Plug-in Module.'"
       ::= { rptrGroupEntry 3 }

   rptrGroupOperStatus OBJECT-TYPE
       SYNTAX    INTEGER {
                     other(1),
                     operational(2),
                     malfunctioning(3),
                     notPresent(4),

                     underTest(5),
                     resetInProgress(6)
                 }
       ACCESS    read-only
       STATUS    mandatory
       DESCRIPTION
               "An object that indicates the operational status
               of the group.

               A status of notPresent(4) indicates that the group
               is temporarily or permanently physically and/or
               logically not a part of the repeater.  It is an
               implementation-specific matter as to whether the
               agent effectively removes notPresent entries from
               the table.

               A status of operational(2) indicates that the
               group is functioning, and a status of
               malfunctioning(3) indicates that the group is
               malfunctioning in some way."
       ::= { rptrGroupEntry 4 }

   rptrGroupLastOperStatusChange OBJECT-TYPE
       SYNTAX    TimeTicks
       ACCESS    read-only
       STATUS    mandatory
       DESCRIPTION
               "An object that contains the value of sysUpTime at
               the time that the value of the rptrGroupOperStatus
               object for this group last changed.

               A value of zero indicates that the group's
               operational status has not changed since the agent
               last restarted."
       ::= { rptrGroupEntry 5 }

   rptrGroupPortCapacity OBJECT-TYPE
       SYNTAX    INTEGER (1..1024)
       ACCESS    read-only
       STATUS    mandatory
       DESCRIPTION
               "The rptrGroupPortCapacity is the number of ports
               that can be contained within the group.  Valid
               range is 1-1024.  Within each group, the ports are
               uniquely numbered in the range from 1 to
               rptrGroupPortCapacity.

               Note:  In practice, this will generally be the

               number of ports on a module, card, or board, and
               the port numbers will correspond to numbers marked
               on the physical embodiment."
       REFERENCE
               "Reference IEEE 802.3 Rptr Mgt, 19.2.5.2,
               aGroupPortCapacity."
       ::= { rptrGroupEntry 6 }

   --
   -- The Basic Port Table
   --

   rptrPortTable OBJECT-TYPE
       SYNTAX    SEQUENCE OF RptrPortEntry
       ACCESS    not-accessible
       STATUS    mandatory
       DESCRIPTION
               "Table of descriptive and status information about
               the ports."
       ::= { rptrPortInfo 1 }

   rptrPortEntry OBJECT-TYPE
       SYNTAX    RptrPortEntry
       ACCESS    not-accessible
       STATUS    mandatory
       DESCRIPTION
               "An entry in the table, containing information
               about a single port."
       INDEX    { rptrPortGroupIndex, rptrPortIndex }
       ::= { rptrPortTable 1 }

   RptrPortEntry ::=
       SEQUENCE {
           rptrPortGroupIndex
               INTEGER,
           rptrPortIndex
               INTEGER,
           rptrPortAdminStatus
               INTEGER,
           rptrPortAutoPartitionState
               INTEGER,
           rptrPortOperStatus
               INTEGER
       }

   rptrPortGroupIndex OBJECT-TYPE
       SYNTAX    INTEGER (1..1024)

       ACCESS    read-only
       STATUS    mandatory
       DESCRIPTION
               "This object identifies the group containing the
               port for which this entry contains information."
       ::= { rptrPortEntry 1 }

   rptrPortIndex OBJECT-TYPE
       SYNTAX    INTEGER (1..1024)
       ACCESS    read-only
       STATUS    mandatory
       DESCRIPTION
               "This object identifies the port within the group
               for which this entry contains information.  This
               value can never be greater than
               rptrGroupPortCapacity for the associated group."
       REFERENCE
               "Reference IEEE 802.3 Rptr Mgt, 19.2.6.2,
               aPortID."
       ::= { rptrPortEntry 2 }

   rptrPortAdminStatus OBJECT-TYPE
       SYNTAX    INTEGER {
                     enabled(1),
                     disabled(2)
                 }
       ACCESS    read-write
       STATUS    mandatory
       DESCRIPTION
               "Setting this object to disabled(2) disables the
               port.  A disabled port neither transmits nor
               receives.  Once disabled, a port must be
               explicitly enabled to restore operation.  A port
               which is disabled when power is lost or when a
               reset is exerted shall remain disabled when normal
               operation resumes.

               The admin status takes precedence over auto-
               partition and functionally operates between the
               auto-partition mechanism and the AUI/PMA.

               Setting this object to enabled(1) enables the port
               and exerts a BEGIN on the port's auto-partition
               state machine.

               (In effect, when a port is disabled, the value of
               rptrPortAutoPartitionState for that port is frozen
               until the port is next enabled.  When the port

               becomes enabled, the rptrPortAutoPartitionState
               becomes notAutoPartitioned(1), regardless of its
               pre-disabling state.)"
       REFERENCE
               "Reference IEEE 802.3 Rptr Mgt, 19.2.6.2,
               aPortAdminState and 19.2.6.3, acPortAdminControl."
       ::= { rptrPortEntry 3 }

   rptrPortAutoPartitionState OBJECT-TYPE
       SYNTAX    INTEGER {
                     notAutoPartitioned(1),
                     autoPartitioned(2)
                 }
       ACCESS    read-only
       STATUS    mandatory
       DESCRIPTION
               "The autoPartitionState flag indicates whether the
               port is currently partitioned by the repeater's
               auto-partition protection.

               The conditions that cause port partitioning are
               specified in partition state machine in Section 9
               [IEEE 802.3 Std].  They are not differentiated
               here."
       REFERENCE
               "Reference IEEE 802.3 Rptr Mgt, 19.2.6.2,
               aAutoPartitionState."
       ::= { rptrPortEntry 4 }

   rptrPortOperStatus  OBJECT-TYPE
       SYNTAX    INTEGER {
                     operational(1),
                     notOperational(2),
                     notPresent(3)
                 }
       ACCESS    read-only
       STATUS    mandatory
       DESCRIPTION
               "This object indicates the port's operational
               status.  The notPresent(3) status indicates the
               port is physically removed (note this may or may
               not be possible depending on the type of port.)
               The operational(1) status indicates that the port
               is enabled (see rptrPortAdminStatus) and working,
               even though it might be auto-partitioned (see
               rptrPortAutoPartitionState).

               If this object has the value operational(1) and

               rptrPortAdminStatus is set to disabled(2), it is
               expected that this object's value will soon change
               to notOperational(2)."
       ::= { rptrPortEntry 5 }

   --
   --                    The MONITOR GROUP
   --
   -- Implementation of this group is optional, but within the
   -- group all elements are mandatory.  If a managed repeater
   -- implements any part of this group, the entire group shall
   -- be implemented.

   --
   -- Repeater Monitor Information
   --
   -- Performance monitoring statistics for the repeater
   --

   rptrMonitorTransmitCollisions OBJECT-TYPE
       SYNTAX    Counter
       ACCESS    read-only
       STATUS    mandatory
       DESCRIPTION
               "This counter is incremented every time the
               repeater state machine enters the TRANSMIT
               COLLISION state from any state other than ONE PORT
               LEFT (Ref: Fig 9-2, IEEE 802.3 Std).

               The approximate minimum time for rollover of this
               counter is 16 hours."
       REFERENCE
               "Reference IEEE 802.3 Rptr Mgt, 19.2.3.2,
               aTransmitCollisions."
       ::= { rptrMonitorRptrInfo 1 }

   --
   -- The Group Monitor Table
   --

   rptrMonitorGroupTable OBJECT-TYPE
       SYNTAX    SEQUENCE OF RptrMonitorGroupEntry
       ACCESS    not-accessible
       STATUS    mandatory
       DESCRIPTION
               "Table of performance and error statistics for the

               groups."
       ::= { rptrMonitorGroupInfo 1 }

   rptrMonitorGroupEntry OBJECT-TYPE
       SYNTAX    RptrMonitorGroupEntry
       ACCESS    not-accessible
       STATUS    mandatory
       DESCRIPTION
               "An entry in the table, containing total
               performance and error statistics for a single
               group.  Regular retrieval of the information in
               this table provides a means of tracking the
               performance and health of the networked devices
               attached to this group's ports.

               The counters in this table are redundant in the
               sense that they are the summations of information
               already available through other objects.  However,
               these sums provide a considerable optimization of
               network management traffic over the otherwise
               necessary retrieval of the individual counters
               included in each sum."
       INDEX    { rptrMonitorGroupIndex }
       ::= { rptrMonitorGroupTable 1 }

   RptrMonitorGroupEntry ::=
       SEQUENCE {
           rptrMonitorGroupIndex
               INTEGER,
           rptrMonitorGroupTotalFrames
               Counter,
           rptrMonitorGroupTotalOctets
               Counter,
           rptrMonitorGroupTotalErrors
               Counter
       }

   rptrMonitorGroupIndex OBJECT-TYPE
       SYNTAX    INTEGER (1..1024)
       ACCESS    read-only
       STATUS    mandatory
       DESCRIPTION
               "This object identifies the group within the
               repeater for which this entry contains
               information."
       ::= { rptrMonitorGroupEntry 1 }

   rptrMonitorGroupTotalFrames OBJECT-TYPE

       SYNTAX    Counter
       ACCESS    read-only
       STATUS    mandatory
       DESCRIPTION
               "The total number of frames of valid frame length
               that have been received on the ports in this group
               and for which the FCSError and CollisionEvent
               signals were not asserted.  This counter is the
               summation of the values of the
               rptrMonitorPortReadableFrames counters for all of
               the ports in the group.

               This statistic provides one of the parameters
               necessary for obtaining the packet error rate.
               The approximate minimum time for rollover of this
               counter is 80 hours."
       ::= { rptrMonitorGroupEntry 2 }

   rptrMonitorGroupTotalOctets OBJECT-TYPE
       SYNTAX    Counter
       ACCESS    read-only
       STATUS    mandatory
       DESCRIPTION
               "The total number of octets contained in the valid
               frames that have been received on the ports in
               this group.  This counter is the summation of the
               values of the rptrMonitorPortReadableOctets
               counters for all of the ports in the group.

               This statistic provides an indicator of the total
               data transferred.  The approximate minimum time
               for rollover of this counter is 58 minutes."
       ::= { rptrMonitorGroupEntry 3 }

   rptrMonitorGroupTotalErrors OBJECT-TYPE
       SYNTAX    Counter
       ACCESS    read-only
       STATUS    mandatory
       DESCRIPTION
               "The total number of errors which have occurred on
               all of the ports in this group.  This counter is
               the summation of the values of the
               rptrMonitorPortTotalErrors counters for all of the
               ports in the group."
       ::= { rptrMonitorGroupEntry 4 }

   --
   -- The Port Monitor Table

   --

   rptrMonitorPortTable OBJECT-TYPE
       SYNTAX    SEQUENCE OF RptrMonitorPortEntry
       ACCESS    not-accessible
       STATUS    mandatory
       DESCRIPTION
               "Table of performance and error statistics for the
               ports."
       ::= { rptrMonitorPortInfo 1 }

   rptrMonitorPortEntry OBJECT-TYPE
       SYNTAX    RptrMonitorPortEntry
       ACCESS    not-accessible
       STATUS    mandatory
       DESCRIPTION
               "An entry in the table, containing performance and
               error statistics for a single port."
       INDEX    { rptrMonitorPortGroupIndex, rptrMonitorPortIndex }
       ::= { rptrMonitorPortTable 1 }

   RptrMonitorPortEntry ::=
       SEQUENCE {
           rptrMonitorPortGroupIndex
               INTEGER,
           rptrMonitorPortIndex
               INTEGER,
           rptrMonitorPortReadableFrames
               Counter,
           rptrMonitorPortReadableOctets
               Counter,
           rptrMonitorPortFCSErrors
               Counter,
           rptrMonitorPortAlignmentErrors
               Counter,
           rptrMonitorPortFrameTooLongs
               Counter,
           rptrMonitorPortShortEvents
               Counter,
           rptrMonitorPortRunts
               Counter,
           rptrMonitorPortCollisions
               Counter,
           rptrMonitorPortLateEvents
               Counter,
           rptrMonitorPortVeryLongEvents
               Counter,
           rptrMonitorPortDataRateMismatches

               Counter,
           rptrMonitorPortAutoPartitions
               Counter,
           rptrMonitorPortTotalErrors
               Counter
       }

   rptrMonitorPortGroupIndex OBJECT-TYPE
       SYNTAX    INTEGER (1..1024)
       ACCESS    read-only
       STATUS    mandatory
       DESCRIPTION
               "This object identifies the group containing the
               port for which this entry contains information."
       ::= { rptrMonitorPortEntry 1 }

   rptrMonitorPortIndex OBJECT-TYPE
       SYNTAX    INTEGER (1..1024)
       ACCESS    read-only
       STATUS    mandatory
       DESCRIPTION
               "This object identifies the port within the group
               for which this entry contains information."
       REFERENCE
               "Reference IEEE 802.3 Rptr Mgt, 19.2.6.2,
               aPortID."
       ::= { rptrMonitorPortEntry 2 }

   rptrMonitorPortReadableFrames OBJECT-TYPE
       SYNTAX    Counter
       ACCESS    read-only
       STATUS    mandatory
       DESCRIPTION
               "This object is the number of frames of valid
               frame length that have been received on this port.
               This counter is incremented by one for each frame
               received on this port whose OctetCount is greater
               than or equal to minFrameSize and less than or
               equal to maxFrameSize (Ref: IEEE 802.3 Std,
               4.4.2.1) and for which the FCSError and
               CollisionEvent signals are not asserted.

               This statistic provides one of the parameters
               necessary for obtaining the packet error rate.
               The approximate minimum time for rollover of this
               counter is 80 hours."
       REFERENCE
               "Reference IEEE 802.3 Rptr Mgt, 19.2.6.2,

               aReadableFrames."
       ::= { rptrMonitorPortEntry 3 }

   rptrMonitorPortReadableOctets OBJECT-TYPE
       SYNTAX    Counter
       ACCESS    read-only
       STATUS    mandatory
       DESCRIPTION
               "This object is the number of octets contained in
               valid frames that have been received on this port.
               This counter is incremented by OctetCount for each
               frame received on this port which has been
               determined to be a readable frame (i.e., including
               FCS octets but excluding framing bits and dribble
               bits).

               This statistic provides an indicator of the total
               data transferred.  The approximate minimum time
               for rollover of this counter is 58 minutes."
       REFERENCE
               "Reference IEEE 802.3 Rptr Mgt, 19.2.6.2,
               aReadableOctets."
       ::= { rptrMonitorPortEntry 4 }

   rptrMonitorPortFCSErrors OBJECT-TYPE
       SYNTAX    Counter
       ACCESS    read-only
       STATUS    mandatory
       DESCRIPTION
               "This counter is incremented by one for each frame
               received on this port with the FCSError signal
               asserted and the FramingError and CollisionEvent
               signals deasserted and whose OctetCount is greater
               than or equal to minFrameSize and less than or
               equal to maxFrameSize (Ref: 4.4.2.1, IEEE 802.3
               Std).

               The approximate minimum time for rollover of this
               counter is 80 hours."
       REFERENCE
               "Reference IEEE 802.3 Rptr Mgt, 19.2.6.2,
               aFrameCheckSequenceErrors."
       ::= { rptrMonitorPortEntry 5 }

   rptrMonitorPortAlignmentErrors OBJECT-TYPE
       SYNTAX    Counter
       ACCESS    read-only
       STATUS    mandatory

       DESCRIPTION
               "This counter is incremented by one for each frame
               received on this port with the FCSError and
               FramingError signals asserted and CollisionEvent
               signal deasserted and whose OctetCount is greater
               than or equal to minFrameSize and less than or
               equal to maxFrameSize (Ref: IEEE 802.3 Std,
               4.4.2.1).  If rptrMonitorPortAlignmentErrors is
               incremented then the rptrMonitorPortFCSErrors
               Counter shall not be incremented for the same
               frame.

               The approximate minimum time for rollover of this
               counter is 80 hours."
       REFERENCE
               "Reference IEEE 802.3 Rptr Mgt, 19.2.6.2,
               aAlignmentErrors."
       ::= { rptrMonitorPortEntry 6 }

   rptrMonitorPortFrameTooLongs OBJECT-TYPE
       SYNTAX    Counter
       ACCESS    read-only
       STATUS    mandatory
       DESCRIPTION
               "This counter is incremented by one for each frame
               received on this port whose OctetCount is greater
               than maxFrameSize (Ref: 4.4.2.1, IEEE 802.3 Std).
               If rptrMonitorPortFrameTooLongs is incremented
               then neither the rptrMonitorPortAlignmentErrors
               nor the rptrMonitorPortFCSErrors counter shall be
               incremented for the frame.

               The approximate minimum time for rollover of this
               counter is 61 days."
       REFERENCE
               "Reference IEEE 802.3 Rptr Mgt, 19.2.6.2,
               aFramesTooLong."
       ::= { rptrMonitorPortEntry 7 }

   rptrMonitorPortShortEvents OBJECT-TYPE
       SYNTAX    Counter
       ACCESS    read-only
       STATUS    mandatory
       DESCRIPTION
               "This counter is incremented by one for each
               CarrierEvent on this port with ActivityDuration
               less than ShortEventMaxTime.  ShortEventMaxTime is
               greater than 74 bit times and less than 82 bit

               times.  ShortEventMaxTime has tolerances included
               to provide for circuit losses between a
               conformance test point at the AUI and the
               measurement point within the state machine.

               Note:  shortEvents may indicate externally
               generated noise hits which will cause the repeater
               to transmit Runts to its other ports, or propagate
               a collision (which may be late) back to the
               transmitting DTE and damaged frames to the rest of
               the network.

               Implementors may wish to consider selecting the
               ShortEventMaxTime towards the lower end of the
               allowed tolerance range to accommodate bit losses
               suffered through physical channel devices not
               budgeted for within this standard.

               The approximate minimum time for rollover of this
               counter is 16 hours."
       REFERENCE
               "Reference IEEE 802.3 Rptr Mgt, 19.2.6.2,
               aShortEvents."
       ::= { rptrMonitorPortEntry 8 }

   rptrMonitorPortRunts OBJECT-TYPE
       SYNTAX    Counter
       ACCESS    read-only
       STATUS    mandatory
       DESCRIPTION
               "This counter is incremented by one for each
               CarrierEvent on this port that meets one of the
               following two conditions.  Only one test need be
               made.  a) The ActivityDuration is greater than
               ShortEventMaxTime and less than ValidPacketMinTime
               and the CollisionEvent signal is deasserted.  b)
               The OctetCount is less than 64, the
               ActivityDuration is greater than ShortEventMaxTime
               and the CollisionEvent signal is deasserted.
               ValidPacketMinTime is greater than or equal to 552
               bit times and less than 565 bit times.

               An event whose length is greater than 74 bit times
               but less than 82 bit times shall increment either
               the shortEvents counter or the runts counter but
               not both.  A CarrierEvent greater than or equal to
               552 bit times but less than 565 bit times may or
               may not be counted as a runt.

               ValidPacketMinTime has tolerances included to
               provide for circuit losses between a conformance
               test point at the AUI and the measurement point
               within the state machine.

               Runts usually indicate collision fragments, a
               normal network event.  In certain situations
               associated with large diameter networks a
               percentage of collision fragments may exceed
               ValidPacketMinTime.

               The approximate minimum time for rollover of this
               counter is 16 hours."
       REFERENCE
               "Reference IEEE 802.3 Rptr Mgt, 19.2.6.2, aRunts."
       ::= { rptrMonitorPortEntry 9 }

   rptrMonitorPortCollisions OBJECT-TYPE
       SYNTAX    Counter
       ACCESS    read-only
       STATUS    mandatory
       DESCRIPTION
               "This counter is incremented by one for any
               CarrierEvent signal on any port for which the
               CollisionEvent signal on this port is also
               asserted.

               The approximate minimum time for rollover of this
               counter is 16 hours."
       REFERENCE
               "Reference IEEE 802.3 Rptr Mgt, 19.2.6.2,
               aCollisions."
       ::= { rptrMonitorPortEntry 10 }

   rptrMonitorPortLateEvents OBJECT-TYPE
       SYNTAX    Counter
       ACCESS    read-only
       STATUS    mandatory
       DESCRIPTION
               "This counter is incremented by one for each
               CarrierEvent on this port in which the CollIn(X)
               variable transitions to the value SQE (Ref:
               9.6.6.2, IEEE 802.3 Std) while the
               ActivityDuration is greater than the
               LateEventThreshold.  Such a CarrierEvent is
               counted twice, as both a collision and as a
               lateEvent.

               The LateEventThreshold is greater than 480 bit
               times and less than 565 bit times.
               LateEventThreshold has tolerances included to
               permit an implementation to build a single
               threshold to serve as both the LateEventThreshold
               and ValidPacketMinTime threshold.

               The approximate minimum time for rollover of this
               counter is 81 hours."
       REFERENCE
               "Reference IEEE 802.3 Rptr Mgt, 19.2.6.2,
               aLateEvents."
       ::= { rptrMonitorPortEntry 11 }

   rptrMonitorPortVeryLongEvents OBJECT-TYPE
       SYNTAX    Counter
       ACCESS    read-only
       STATUS    mandatory
       DESCRIPTION
               "This counter is incremented by one for each
               CarrierEvent on this port whose ActivityDuration
               is greater than the MAU Jabber Lockup Protection
               timer TW3 (Ref: 9.6.1 & 9.6.5, IEEE 802.3 Std).
               Other counters may be incremented as appropriate."
       REFERENCE
               "Reference IEEE 802.3 Rptr Mgt, 19.2.6.2,
               aVeryLongEvents."
       ::= { rptrMonitorPortEntry 12 }

   rptrMonitorPortDataRateMismatches OBJECT-TYPE
       SYNTAX    Counter
       ACCESS    read-only
       STATUS    mandatory
       DESCRIPTION
               "This counter is incremented by one for each frame
               received on this port that meets all of the
               following conditions:  a) The CollisionEvent
               signal is not asserted.  b) The ActivityDuration
               is greater than ValidPacketMinTime.  c) The
               frequency (data rate) is detectably mismatched
               from the local transmit frequency.  The exact
               degree of mismatch is vendor specific and is to be
               defined by the vendor for conformance testing.

               When this event occurs, other counters whose
               increment conditions were satisfied may or may not
               also be incremented, at the implementor's
               discretion.  Whether or not the repeater was able

               to maintain data integrity is beyond the scope of
               this standard."
       REFERENCE
               "Reference IEEE 802.3 Rptr Mgt, 19.2.6.2,
               aDataRateMismatches."
       ::= { rptrMonitorPortEntry 13 }

   rptrMonitorPortAutoPartitions OBJECT-TYPE
       SYNTAX    Counter
       ACCESS    read-only
       STATUS    mandatory
       DESCRIPTION
               "This counter is incremented by one for each time
               the repeater has automatically partitioned this
               port.  The conditions that cause port partitioning
               are specified in the partition state machine in
               Section 9 [IEEE 802.3 Std].  They are not
               differentiated here."
       REFERENCE
               "Reference IEEE 802.3 Rptr Mgt, 19.2.6.2,
               aAutoPartitions."
       ::= { rptrMonitorPortEntry 14 }

   rptrMonitorPortTotalErrors OBJECT-TYPE
       SYNTAX    Counter
       ACCESS    read-only
       STATUS    mandatory
       DESCRIPTION
               "The total number of errors which have occurred on
               this port.  This counter is the summation of the
               values of other error counters (for the same
               port), namely:

                   rptrMonitorPortFCSErrors,
                   rptrMonitorPortAlignmentErrors,
                   rptrMonitorPortFrameTooLongs,
                   rptrMonitorPortShortEvents,
                   rptrMonitorPortLateEvents,
                   rptrMonitorPortVeryLongEvents, and
                   rptrMonitorPortDataRateMismatches.

               This counter is redundant in the sense that it is
               the summation of information already available
               through other objects.  However, it is included
               specifically because the regular retrieval of this
               object as a means of tracking the health of a port
               provides a considerable optimization of network
               management traffic over the otherwise necessary

               retrieval of the summed counters."
       ::= { rptrMonitorPortEntry 15 }

   --
   --                    The ADDRESS TRACKING GROUP
   --
   -- Implementation of this group is optional; it is appropriate
   -- for all systems which have the necessary instrumentation.  If a
   -- managed repeater implements any part of this group, the entire
   -- group shall be implemented.

   --
   -- The Port Address Tracking Table
   --

   rptrAddrTrackTable OBJECT-TYPE
       SYNTAX    SEQUENCE OF RptrAddrTrackEntry
       ACCESS    not-accessible
       STATUS    mandatory
       DESCRIPTION
               "Table of address mapping information about the
               ports."
       ::= { rptrAddrTrackPortInfo 1 }

   rptrAddrTrackEntry OBJECT-TYPE
       SYNTAX    RptrAddrTrackEntry
       ACCESS    not-accessible
       STATUS    mandatory
       DESCRIPTION
               "An entry in the table, containing address mapping
               information about a single port."
       INDEX    { rptrAddrTrackGroupIndex, rptrAddrTrackPortIndex }
       ::= { rptrAddrTrackTable 1 }

   RptrAddrTrackEntry ::=
       SEQUENCE {
           rptrAddrTrackGroupIndex
               INTEGER,
           rptrAddrTrackPortIndex
               INTEGER,
           rptrAddrTrackLastSourceAddress     -- DEPRECATED OBJECT
               MacAddress,
           rptrAddrTrackSourceAddrChanges
               Counter,
           rptrAddrTrackNewLastSrcAddress
               OCTET STRING
       }

   rptrAddrTrackGroupIndex OBJECT-TYPE
       SYNTAX    INTEGER (1..1024)
       ACCESS    read-only
       STATUS    mandatory
       DESCRIPTION
               "This object identifies the group containing the
               port for which this entry contains information."
       ::= { rptrAddrTrackEntry 1 }

   rptrAddrTrackPortIndex OBJECT-TYPE
       SYNTAX    INTEGER (1..1024)
       ACCESS    read-only
       STATUS    mandatory
       DESCRIPTION
               "This object identifies the port within the group
               for which this entry contains information."
       REFERENCE
               "Reference IEEE 802.3 Rptr Mgt, 19.2.6.2,
               aPortID."
       ::= { rptrAddrTrackEntry 2 }

   rptrAddrTrackLastSourceAddress OBJECT-TYPE
       SYNTAX    MacAddress
       ACCESS    read-only
       STATUS    deprecated
       DESCRIPTION
               "This object is the SourceAddress of the last
               readable frame (i.e., counted by
               rptrMonitorPortReadableFrames) received by this
               port.

               This object has been deprecated because its value
               is undefined when no frames have been observed on
               this port.  The replacement object is
               rptrAddrTrackNewLastSrcAddress."
       REFERENCE
               "Reference IEEE 802.3 Rptr Mgt, 19.2.6.2,
               aLastSourceAddress."
       ::= { rptrAddrTrackEntry 3 }

   rptrAddrTrackSourceAddrChanges OBJECT-TYPE
       SYNTAX    Counter
       ACCESS    read-only
       STATUS    mandatory
       DESCRIPTION
               "This counter is incremented by one for each time
               that the rptrAddrTrackLastSourceAddress attribute
               for this port has changed.

               This may indicate whether a link is connected to a
               single DTE or another multi-user segment.

               The approximate minimum time for rollover of this
               counter is 81 hours."
       REFERENCE
               "Reference IEEE 802.3 Rptr Mgt, 19.2.6.2,
               aSourceAddressChanges."
       ::= { rptrAddrTrackEntry 4 }

   rptrAddrTrackNewLastSrcAddress OBJECT-TYPE
       SYNTAX    OCTET STRING
       ACCESS    read-only
       STATUS    mandatory
       DESCRIPTION
               "This object is the SourceAddress of the last
               readable frame (i.e., counted by
               rptrMonitorPortReadableFrames) received by this
               port.  If no frames have been received by this
               port since the agent began monitoring the port
               activity, the agent shall return a string of
               length zero."
       REFERENCE
               "Reference IEEE 802.3 Rptr Mgt, 19.2.6.2,
               aLastSourceAddress."
       ::= { rptrAddrTrackEntry 5 }

   -- Traps for use by Repeaters

   -- Traps are defined using the conventions in RFC 1215 [6].

   rptrHealth TRAP-TYPE
       ENTERPRISE  snmpDot3RptrMgt
       VARIABLES   { rptrOperStatus }
       DESCRIPTION
               "The rptrHealth trap conveys information related
               to the operational status of the repeater.  This
               trap is sent either when the value of
               rptrOperStatus changes, or upon completion of a
               non-disruptive test.

               The rptrHealth trap must contain the
               rptrOperStatus object.  The agent may optionally
               include the rptrHealthText object in the varBind
               list.  See the rptrOperStatus and rptrHealthText
               objects for descriptions of the information that
               is sent.

               The agent must throttle the generation of
               consecutive rptrHealth traps so that there is at
               least a five-second gap between traps of this
               type.  When traps are throttled, they are dropped,
               not queued for sending at a future time.  (Note
               that 'generating' a trap means sending to all
               configured recipients.)"
       REFERENCE
               "Reference IEEE 802.3 Rptr Mgt, 19.2.3.4,
               hubHealth notification."
       ::= 1

   rptrGroupChange TRAP-TYPE
       ENTERPRISE  snmpDot3RptrMgt
       VARIABLES   { rptrGroupIndex }
       DESCRIPTION
               "This trap is sent when a change occurs in the
               group structure of a repeater.  This occurs only
               when a group is logically or physically removed
               from or added to a repeater.  The varBind list
               contains the identifier of the group that was
               removed or added.

               The agent must throttle the generation of
               consecutive rptrGroupChange traps for the same
               group so that there is at least a five-second gap
               between traps of this type.  When traps are
               throttled, they are dropped, not queued for
               sending at a future time.  (Note that 'generating'
               a trap means sending to all configured
               recipients.)"
       REFERENCE
               "Reference IEEE 802.3 Rptr Mgt, 19.2.3.4,
               groupMapChange notification."
       ::= 2

   rptrResetEvent TRAP-TYPE
       ENTERPRISE  snmpDot3RptrMgt
       VARIABLES   { rptrOperStatus }
       DESCRIPTION
               "The rptrResetEvent trap conveys information
               related to the operational status of the repeater.
               This trap is sent on completion of a repeater
               reset action.  A repeater reset action is defined
               as an a transition to the START state of Fig 9-2
               in section 9 [IEEE 802.3 Std], when triggered by a
               management command (e.g., an SNMP Set on the
               rptrReset object).

               The agent must throttle the generation of
               consecutive rptrResetEvent traps so that there is
               at least a five-second gap between traps of this
               type.  When traps are throttled, they are dropped,
               not queued for sending at a future time.  (Note
               that 'generating' a trap means sending to all
               configured recipients.)

               The rptrResetEvent trap is not sent when the agent
               restarts and sends an SNMP coldStart or warmStart
               trap.  However, it is recommended that a repeater
               agent send the rptrOperStatus object as an
               optional object with its coldStart and warmStart
               trap PDUs.

               The rptrOperStatus object must be included in the
               varbind list sent with this trap.  The agent may
               optionally include the rptrHealthText object as
               well."
       REFERENCE
               "Reference IEEE 802.3 Rptr Mgt, 19.2.3.4, hubReset
               notification."
       ::= 3


--
-- FILE: /users/sse/mibs/src/rfc/rfc1243.mib
--

-- Changes to rfc1243 (AppleTalk MIB):
--      Changed llapInBads in definition of sequence LlapEntry
--              to llapInErros.



          -- RFC1243
          -- July '91


          --  This MIB module uses the extended OBJECT-TYPE macro as
          --  defined in [9]


          --  AppleTalk MIB

                  appletalk    OBJECT IDENTIFIER ::= { mib-2 13 }


                  DdpAddress ::=  -- 2 octets of net number
                                  -- 1 octet of node number
                          OCTET STRING (SIZE (3))
                  -- This data type is used for encoding a DDP protocol
                  -- address.  The format of this address is a serial
                  -- encoding of the two octets of network number in
                  -- network byte order, followed by the 1 octet node
                  -- number.

                  llap     OBJECT IDENTIFIER ::= { appletalk 1 }
                  aarp     OBJECT IDENTIFIER ::= { appletalk 2 }
                  atport   OBJECT IDENTIFIER ::= { appletalk 3 }
                  ddp      OBJECT IDENTIFIER ::= { appletalk 4 }
                  rtmp     OBJECT IDENTIFIER ::= { appletalk 5 }
                  kip      OBJECT IDENTIFIER ::= { appletalk 6 }
                  zip      OBJECT IDENTIFIER ::= { appletalk 7 }
                  nbp      OBJECT IDENTIFIER ::= { appletalk 8 }
                  atecho   OBJECT IDENTIFIER ::= { appletalk 9 }


          -- The LLAP Group















          -- The AARP Group







          -- The ATPort Group
















          -- The DDP Group

















          -- The RTMP Group












          -- The KIP Group













          -- The ZIP Group










          -- The NBP Group









          -- The ATEcho Group



--
-- FILE: /users/sse/mibs/src/itouch/it-appletalk-mib.mib
--

-- $Id: it-appletalk-mib.mib,v 1.1 2000/07/25 14:03:24 sse Exp $


            xApple          OBJECT IDENTIFIER ::= { iTouch 21 }

            -- ITouch AppleTalk subgroups

            xAppleSystem        OBJECT IDENTIFIER ::= { xApple 1 }
            xApplePort          OBJECT IDENTIFIER ::= { xApple 2 }
            xApplePolicy        OBJECT IDENTIFIER ::= { xApple 3 }
            xAppleNbp           OBJECT IDENTIFIER ::= { xApple 4 }
            xAppleTraffic       OBJECT IDENTIFIER ::= { xApple 5 }
            xAppleRemoteAccess  OBJECT IDENTIFIER ::= { xApple 6 }

            -- This is a MIB module for all iTouch Communications systems that
            -- implement Appletalk.

            -- Copyright 2000 iTouch Communications, Inc. All Rights Reserved.
            -- Reproduction of this document is authorized on
            -- condition that this copyright notice is included.
            -- This MIB document embodies iTouch Communications, Inc.'s 
            -- proprietary intellectual property.  iTouch Communications, Inc.
            -- retains all title and ownership in this MIB, including any
            -- revisions.
            --
            -- It is iTouch Communications, Inc.'s intent to encourage the
            -- widespread use of this MIB in connection with the management of
            -- iTouch Communications, Inc. products. iTouch Communications,
            -- Inc. grants vendors,end-users, and other interested parties a
            -- non-exclusive license to use this MIB in connection with the
            -- management of iTouch Communications, Inc. products.
            --
            -- This MIB document is supplied "AS IS," and iTouch 
            -- Communications, Inc. makes no warranty, either express or
            -- implied, as to the use operation, condition, or performance of
            -- the MIB.


            -- the AppleTalk System group

            appleState OBJECT-TYPE
                SYNTAX INTEGER { disabled(1), enabled(2) }
                ACCESS read-write
                STATUS mandatory
                DESCRIPTION
                    "Controls whether the router will perform AppleTalk 
                    routing."
                ::= { xAppleSystem 1 }

            appleStatus OBJECT-TYPE
                SYNTAX INTEGER { disabled(1), active(2), noInterface(3),
                                 badConfig(4), noInterfaceActive (5) }
                ACCESS read-only
                STATUS mandatory
                DESCRIPTION
                    "Indicates whether the router is performing 
                    AppleTalk routing."
                ::= { xAppleSystem 2 }

            appleStatusIf OBJECT-TYPE
                SYNTAX INTEGER
                ACCESS read-only
                STATUS mandatory
                DESCRIPTION
                    "The ifIndex of the bad interface if appleStatus is 
                    'badConfig'."
                ::= { xAppleSystem 3 }


            -- the AppleTalk Port group

            applePortTable OBJECT-TYPE
                SYNTAX SEQUENCE OF ApplePortEntry
                ACCESS not-accessible
                STATUS mandatory
                DESCRIPTION
                    "Table of fields indexed by interface."
                ::= { xApplePort 1 }

            applePortEntry OBJECT-TYPE
                SYNTAX ApplePortEntry
                ACCESS not-accessible
                STATUS mandatory
                DESCRIPTION
                    "A particular entry."
                INDEX { applePortIndex }
                ::= { applePortTable 1 }

            ApplePortEntry ::=
                SEQUENCE {
                    applePortIndex
                        INTEGER,
                    applePortProtocolPriority
                        INTEGER,
                    applePortArpInterval
                        INTEGER,
                    applePortArpRetransmitCount
                        INTEGER,
                    applePortChecksum
                        INTEGER,
                    applePortPacketsIn
                        Counter,
                    applePortPacketsOut
                        Counter,
                    applePortForwardsIn
                        Counter,
                    applePortForwardsOut
                        Counter,
                    applePortNetAddress
                        DdpAddress,
                    applePortNetStart
                        OCTET STRING,
                    applePortNetEnd
                        OCTET STRING,
                    applePortErrors
                        Counter,
                    applePortLastError
                        INTEGER,
                    applePortLastErrorTime
                        TimeTicks,
                    applePortLastErrorData
                        OCTET STRING,
                    applePortBringBackTime
                        INTEGER,
                    applePortUseNeighborNotify
                        INTEGER,
                    applePortRouterType
                        INTEGER
                }

            applePortIndex OBJECT-TYPE
                SYNTAX INTEGER
                ACCESS read-only
                STATUS mandatory
                DESCRIPTION
                    "The index of the interface; same as IfIndex."
                ::= { applePortEntry 1 }

            applePortProtocolPriority OBJECT-TYPE
                SYNTAX INTEGER { low(1), medium(3), high(5) }
                ACCESS read-write
                STATUS mandatory
                DESCRIPTION
                    "This value defines the priority at which all Apple 
                    routed packets will be placed on the WAN output 
                    queue."
                DEFVAL { medium }
                ::= { applePortEntry 2 }

            applePortArpInterval OBJECT-TYPE
                SYNTAX INTEGER (33..65535)
                ACCESS read-write
                STATUS mandatory
                DESCRIPTION
                    "The interval at which ARP messages should be sent 
                    during the process of selecting a network address."
                DEFVAL { 33 }
                ::= { applePortEntry 3 }

            applePortArpRetransmitCount OBJECT-TYPE
                SYNTAX INTEGER (1..65535)
                ACCESS read-write
                STATUS mandatory
                DESCRIPTION
                    "The number of ARP messages that should be sent 
                    during the process of selecting a network address."
                DEFVAL { 20 }
                ::= { applePortEntry 4 }

            applePortChecksum OBJECT-TYPE
                SYNTAX INTEGER { disabled(1), enabled(2) }
                ACCESS read-write
                STATUS mandatory
                DESCRIPTION
                    "Controls whether checksums are generated on all DDP 
                    packets sent out the interface."
                DEFVAL { disabled }
                ::= { applePortEntry 5 }

            applePortPacketsIn OBJECT-TYPE
                SYNTAX Counter
                ACCESS read-only
                STATUS mandatory
                DESCRIPTION
                    "The number of AppleTalk packets received on this 
                    interface."
                ::= { applePortEntry 6 }

            applePortPacketsOut OBJECT-TYPE
                SYNTAX Counter
                ACCESS read-only
                STATUS mandatory
                DESCRIPTION
                    "The number of AppleTalk packets transmitted on this 
                    interface."
                ::= { applePortEntry 7 }

            applePortForwardsIn OBJECT-TYPE
                SYNTAX Counter
                ACCESS read-only
                STATUS mandatory
                DESCRIPTION
                    "The number of AppleTalk packets received on this 
                    interface which were not addressed to this router."
                ::= { applePortEntry 8 }

            applePortForwardsOut OBJECT-TYPE
                SYNTAX Counter
                ACCESS read-only
                STATUS mandatory
                DESCRIPTION
                    "The number of AppleTalk packets transmitted on this 
                    interface which were not originated by this 
                    router."
                ::= { applePortEntry 9 }

            applePortNetAddress OBJECT-TYPE
                SYNTAX DdpAddress
                ACCESS read-only
                STATUS mandatory
                DESCRIPTION
                    "The actual address used by this port."
                ::= { applePortEntry 10 }

            applePortNetStart OBJECT-TYPE
                SYNTAX OCTET STRING ( SIZE(2) )
                ACCESS read-only
                STATUS mandatory
                DESCRIPTION
                    "The start of the actual network range used by this 
                    port."
                ::= { applePortEntry 11 }

            applePortNetEnd OBJECT-TYPE
                SYNTAX OCTET STRING ( SIZE(2) )
                ACCESS read-only
                STATUS mandatory
                DESCRIPTION
                    "The end of the actual network range used by this 
                    port."
                ::= { applePortEntry 12 }

            applePortErrors OBJECT-TYPE
                SYNTAX Counter
                ACCESS read-only
                STATUS mandatory
                DESCRIPTION
                    "The number of AppleTalk packets received in 
                    error."
                ::= { applePortEntry 13 }

            applePortLastError OBJECT-TYPE
                SYNTAX INTEGER { broadcast(1), checksum(2), hopCount(3),
                                 noProtocol(4), noRoute(5), shortDDP(6),
                                 tooLong(7), tooShort(8) }
                ACCESS read-only
                STATUS mandatory
                DESCRIPTION
                    "The type of the most recent error counted in 
                    applePortErrors.  A value of zero means no error."
                ::= { applePortEntry 14 }

            applePortLastErrorTime OBJECT-TYPE
                SYNTAX TimeTicks
                ACCESS read-only
                STATUS mandatory
                DESCRIPTION
                    "The value of sysUptime when applePortLastError last 
                    occured."
                ::= { applePortEntry 15 }

            applePortLastErrorData OBJECT-TYPE
                SYNTAX OCTET STRING ( SIZE(22) )
                ACCESS read-only
                STATUS mandatory
                DESCRIPTION
                    "The first 22 bytes of the packet from 
                    applePortLastError."
                ::= { applePortEntry 16 }

            applePortBringBackTime OBJECT-TYPE
                SYNTAX INTEGER (0..65535)
                ACCESS read-write
                STATUS mandatory
                DESCRIPTION
                    "The number of seconds to shut down an interface 
                    while waiting for a manager-initiated configuration 
                    change to propagate."
                ::= { applePortEntry 17 }

            applePortUseNeighborNotify OBJECT-TYPE
                SYNTAX INTEGER { disabled(1), enabled(2) }
                ACCESS read-write
                STATUS mandatory
                DESCRIPTION
                    "Controls generation of neighbor notify messages 
                    when an interface is disabled or system is shut 
                    down."
                ::= { applePortEntry 18 }

            applePortRouterType OBJECT-TYPE
                SYNTAX INTEGER { full(1), half(2) }
                ACCESS read-write
                STATUS mandatory
                DESCRIPTION
                    "Type of router operation over this port."
                ::= { applePortEntry 19 }


            -- the Port Zone table

            applePortZoneTable OBJECT-TYPE
                SYNTAX SEQUENCE OF ApplePortZoneEntry
                ACCESS not-accessible
                STATUS mandatory
                DESCRIPTION
                    "Table of fields indexed by interface and zone."
                ::= { xApplePort 2 }

            applePortZoneEntry OBJECT-TYPE
                SYNTAX ApplePortZoneEntry
                ACCESS not-accessible
                STATUS mandatory
                DESCRIPTION
                    "A particular entry."
                INDEX { applePortZoneIndex, applePortZoneName }
                ::= { applePortZoneTable 1 }

            ApplePortZoneEntry ::=
                SEQUENCE {
                    applePortZoneIndex
                        INTEGER,
                    applePortZoneName
                        OCTET STRING,
                    applePortZoneStatus
                        INTEGER
                }

            applePortZoneIndex OBJECT-TYPE
                SYNTAX INTEGER
                ACCESS read-only
                STATUS mandatory
                DESCRIPTION
                    "The index of the interface; same as IfIndex."
                ::= { applePortZoneEntry 1 }

            applePortZoneName OBJECT-TYPE
                SYNTAX OCTET STRING ( SIZE(32) )
                ACCESS read-only
                STATUS mandatory
                DESCRIPTION
                    "The name of the zone."
                ::= { applePortZoneEntry 2 }

            applePortZoneStatus OBJECT-TYPE
                SYNTAX INTEGER { invalid(1), valid(2) }
                ACCESS read-write
                STATUS mandatory
                DESCRIPTION
                    "The status of the entry.  Set to 'invalid' to 
                    remove the entry."
                DEFVAL { valid }
                ::= { applePortZoneEntry 3 }


            -- the AppleTalk Port Policy group

            applePortExportTable OBJECT-TYPE
                SYNTAX SEQUENCE OF ApplePortExportEntry
                ACCESS not-accessible
                STATUS mandatory
                DESCRIPTION
                    "Table of fields indexed by interface and zone."
                ::= { xApplePolicy 1 }

            applePortExportEntry OBJECT-TYPE
                SYNTAX ApplePortExportEntry
                ACCESS not-accessible
                STATUS mandatory
                DESCRIPTION
                    "A particular entry."
                INDEX { applePortExportIndex, applePortExportZone,
                        applePortExportName, applePortExportType }
                ::= { applePortExportTable 1 }

            ApplePortExportEntry ::=
                SEQUENCE {
                    applePortExportIndex
                        INTEGER,
                    applePortExportZone
                        OCTET STRING,
                    applePortExportName
                        OCTET STRING,
                    applePortExportType
                        OCTET STRING,
                    applePortExportAction
                        INTEGER,
                    applePortExportStatus
                        INTEGER
                }

            applePortExportIndex OBJECT-TYPE
                SYNTAX INTEGER
                ACCESS read-only
                STATUS mandatory
                DESCRIPTION
                    "The index of the interface; same as IfIndex."
                ::= { applePortExportEntry 1 }

            applePortExportZone OBJECT-TYPE
                SYNTAX OCTET STRING ( SIZE(0..32) )
                ACCESS read-only
                STATUS mandatory
                DESCRIPTION
                    "The name of the zone."
                ::= { applePortExportEntry 2 }

            applePortExportName OBJECT-TYPE
                SYNTAX OCTET STRING ( SIZE(0..32) )
                ACCESS read-only
                STATUS mandatory
                DESCRIPTION
                    "The name of the name."
                ::= { applePortExportEntry 3 }

            applePortExportType OBJECT-TYPE
                SYNTAX OCTET STRING ( SIZE(0..32) )
                ACCESS read-only
                STATUS mandatory
                DESCRIPTION
                    "The name of the type."
                ::= { applePortExportEntry 4 }

            applePortExportAction OBJECT-TYPE
                SYNTAX INTEGER { hide(1), advertise(2) }
                ACCESS read-write
                STATUS mandatory
                DESCRIPTION
                    "Control whether the data will be hidden or 
                    advertised."
                DEFVAL { advertise }
                ::= { applePortExportEntry 5 }

            applePortExportStatus OBJECT-TYPE
                SYNTAX INTEGER { invalid(1), valid(2) }
                ACCESS read-write
                STATUS mandatory
                DESCRIPTION
                    "The status of the entry.  Set to 'invalid' to 
                    remove the entry."
                DEFVAL { valid }
                ::= { applePortExportEntry 6 }

            applePortImportTable OBJECT-TYPE
                SYNTAX SEQUENCE OF ApplePortImportEntry
                ACCESS not-accessible
                STATUS mandatory
                DESCRIPTION
                    "Table of fields indexed by interface and zone."
                ::= { xApplePolicy 2 }

            applePortImportEntry OBJECT-TYPE
                SYNTAX ApplePortImportEntry
                ACCESS not-accessible
                STATUS mandatory
                DESCRIPTION
                    "A particular entry."
                INDEX { applePortImportIndex, applePortImportZone,
                        applePortImportName, applePortImportType }
                ::= { applePortImportTable 1 }

            ApplePortImportEntry ::=
                SEQUENCE {
                    applePortImportIndex
                        INTEGER,
                    applePortImportZone
                        OCTET STRING,
                    applePortImportName
                        OCTET STRING,
                    applePortImportType
                        OCTET STRING,
                    applePortImportAction
                        INTEGER,
                    applePortImportStatus
                        INTEGER
                }

            applePortImportIndex OBJECT-TYPE
                SYNTAX INTEGER
                ACCESS read-only
                STATUS mandatory
                DESCRIPTION
                    "The index of the interface; same as IfIndex."
                ::= { applePortImportEntry 1 }

            applePortImportZone OBJECT-TYPE
                SYNTAX OCTET STRING ( SIZE(0..32) )
                ACCESS read-only
                STATUS mandatory
                DESCRIPTION
                    "The name of the zone."
                ::= { applePortImportEntry 2 }

            applePortImportName OBJECT-TYPE
                SYNTAX OCTET STRING ( SIZE(0..32) )
                ACCESS read-only
                STATUS mandatory
                DESCRIPTION
                    "The name of the name."
                ::= { applePortImportEntry 3 }

            applePortImportType OBJECT-TYPE
                SYNTAX OCTET STRING ( SIZE(0..32) )
                ACCESS read-only
                STATUS mandatory
                DESCRIPTION
                    "The name of the type."
                ::= { applePortImportEntry 4 }

            applePortImportAction OBJECT-TYPE
                SYNTAX INTEGER { discard(1), accept(2) }
                ACCESS read-write
                STATUS mandatory
                DESCRIPTION
                    "Control whether the data will be discarded or 
                    accepted."
                DEFVAL { accept }
                ::= { applePortImportEntry 5 }

            applePortImportStatus OBJECT-TYPE
                SYNTAX INTEGER { invalid(1), valid(2) }
                ACCESS read-write
                STATUS mandatory
                DESCRIPTION
                    "The status of the entry.  Set to 'invalid' to 
                    remove the entry."
                DEFVAL { valid }
                ::= { applePortImportEntry 6 }


            -- the AppleTalk Name group

            appleNbpTable OBJECT-TYPE
                SYNTAX SEQUENCE OF AppleNbpEntry
                ACCESS not-accessible
                STATUS mandatory
                DESCRIPTION
                    "Table of fields indexed by interface and zone."
                ::= { xAppleNbp 1 }

            appleNbpEntry OBJECT-TYPE
                SYNTAX AppleNbpEntry
                ACCESS not-accessible
                STATUS mandatory
                DESCRIPTION
                    "A particular entry."
                INDEX { appleNbpZone, appleNbpName, appleNbpType }
                ::= { appleNbpTable 1 }

            AppleNbpEntry ::=
                SEQUENCE {
                    appleNbpZone
                        OCTET STRING,
                    appleNbpName
                        OCTET STRING,
                    appleNbpType
                        OCTET STRING,
                    appleNbpNode
                        DdpAddress,
                    appleNbpSocket
                        INTEGER
                }

            appleNbpZone OBJECT-TYPE
                SYNTAX OCTET STRING ( SIZE(0..32) )
                ACCESS read-only
                STATUS mandatory
                DESCRIPTION
                    "The name of the zone."
                ::= { appleNbpEntry 1 }

            appleNbpName OBJECT-TYPE
                SYNTAX OCTET STRING ( SIZE(0..32) )
                ACCESS read-only
                STATUS mandatory
                DESCRIPTION
                    "The name of the name."
                ::= { appleNbpEntry 2 }

            appleNbpType OBJECT-TYPE
                SYNTAX OCTET STRING ( SIZE(0..32) )
                ACCESS read-only
                STATUS mandatory
                DESCRIPTION
                    "The name of the type."
                ::= { appleNbpEntry 3 }

            appleNbpNode OBJECT-TYPE
                SYNTAX DdpAddress
                ACCESS read-only
                STATUS mandatory
                DESCRIPTION
                    "The address of the node who offers the service 
                    associated with this entry."
                ::= { appleNbpEntry 4 }

            appleNbpSocket OBJECT-TYPE
                SYNTAX INTEGER
                ACCESS read-only
                STATUS mandatory
                DESCRIPTION
                    "The socket of the service associated with this 
                    entry.  The value 0 means no socket."
                ::= { appleNbpEntry 5 }


            -- the AppleTalk Traffic group

            appleTrafficSort OBJECT-TYPE
                SYNTAX INTEGER { ready(1), execute(2) }
                ACCESS read-write
                STATUS mandatory
                DESCRIPTION
                    "Setting to EXECUTE causes the most recent traffic 
                    information to be sorted into the appleTrafficTable.  
                    The sorting precedence is: decreasing percentage, 
                    increasing destination address, increasing source 
                    address, and increasing interface number.  Setting 
                    to READY has no effect."
                ::= { xAppleTraffic 1 }

            -- Additional single objects follow the Traffic table

            -- the Traffic table

            appleTrafficTable OBJECT-TYPE
                SYNTAX SEQUENCE OF AppleTrafficEntry
                ACCESS not-accessible
                STATUS mandatory
                DESCRIPTION
                    "A list of traffic entries, sorted in the order 
                    specified by appleTrafficSort."
                ::= { xAppleTraffic 2 }

            appleTrafficEntry OBJECT-TYPE
                SYNTAX AppleTrafficEntry
                ACCESS not-accessible
                STATUS mandatory
                DESCRIPTION
                    "Parameter values for an Filter filter."
                INDEX { appleTrafficIndex }
                ::= { appleTrafficTable 1 }

            AppleTrafficEntry ::=
                SEQUENCE {
                    appleTrafficIndex
                        INTEGER,
                    appleTrafficPercent
                        INTEGER,
                    appleTrafficDst
                        DdpAddress,
                    appleTrafficSrc
                        DdpAddress,
                    appleTrafficIntf
                        INTEGER
                }

            appleTrafficIndex OBJECT-TYPE
                SYNTAX INTEGER
                ACCESS read-only
                STATUS mandatory
                DESCRIPTION
                    "Identification of a traffic entry."
                ::= { appleTrafficEntry 1 }

            appleTrafficPercent OBJECT-TYPE
                SYNTAX INTEGER ( 0..1000 )
                ACCESS read-only
                STATUS mandatory
                DESCRIPTION
                    "The percent of total traffic that this traffic 
                    entryrepresents, in tenths of a percent."
                ::= { appleTrafficEntry 2 }

            appleTrafficDst OBJECT-TYPE
                SYNTAX DdpAddress
                ACCESS read-only
                STATUS mandatory
                DESCRIPTION
                    "The destination to which the traffic entry 
                    applies."
                ::= { appleTrafficEntry 3 }

            appleTrafficSrc OBJECT-TYPE
                SYNTAX DdpAddress
                ACCESS read-only
                STATUS mandatory
                DESCRIPTION
                    "The source to which the traffic entry applies."
                ::= { appleTrafficEntry 4 }

            appleTrafficIntf OBJECT-TYPE
                SYNTAX INTEGER
                ACCESS read-only
                STATUS mandatory
                DESCRIPTION
                    "The inbound interface to which the traffic entry 
                    applies."
                ::= { appleTrafficEntry 5 }

            -- Additional individual objects

            appleTrafficMonitoring OBJECT-TYPE
                SYNTAX INTEGER { disable(1), enable(2) }
                ACCESS read-write
                STATUS mandatory
                DESCRIPTION
                    "Controls whether internet traffic information will 
                    be recorded."
                ::= { xAppleTraffic 3 }

            -- The ITouch ARAP MIB branch

            arapPassword OBJECT-TYPE
                SYNTAX DisplayString (SIZE (0..8))
                ACCESS read-write
                STATUS mandatory
                DESCRIPTION
                    "The server's ARAP password.  To increase security, Gets
                    of this object return the NULL string."
                ::= { xAppleRemoteAccess 1 }

            arapDefaultZoneName OBJECT-TYPE
                SYNTAX DisplayString (SIZE (0..32))
                ACCESS read-write
                STATUS mandatory
                DESCRIPTION
                    "The name of the AppleTalk zone that the server should
                    try to choose at boot time."
                ::= { xAppleRemoteAccess 2 }

            -- the ARAP Port table

            arapPortTable OBJECT-TYPE
                SYNTAX SEQUENCE OF ArapPortEntry
                ACCESS not-accessible
                STATUS mandatory
                DESCRIPTION
                    "A list of ARAP port entries."
                ::= { xAppleRemoteAccess 3 }

            arapPortEntry OBJECT-TYPE
                SYNTAX ArapPortEntry
                ACCESS not-accessible
                STATUS mandatory
                DESCRIPTION
                    "ARAP parameter values for a port."
                INDEX { charPortIndex }
                ::= { arapPortTable 1 }

            ArapPortEntry ::=
                SEQUENCE {
                    arapPortEnabled
                        INTEGER,
                    arapPortZoneAccess
                        INTEGER,
                    arapPortZoneName
                        DisplayString,
                    arapPortMaxConnectTime
                        INTEGER,
                    arapPortGuestLoginsOk
                        INTEGER,
                    arapPortTimeConnected
                        INTEGER,
                    arapPortTimeRemaining
                        INTEGER
                }

            arapPortEnabled OBJECT-TYPE
                SYNTAX INTEGER { disabled(1), enabled(2) }
                ACCESS read-write
                STATUS mandatory
                DESCRIPTION
                    "Indicates if ARAP connections are allowed on this port."
                ::= { arapPortEntry 1 }

            arapPortZoneAccess OBJECT-TYPE
                SYNTAX INTEGER { all(1), local(2), none(3), namedzone(4) }
                ACCESS read-write
                STATUS mandatory
                DESCRIPTION
                    "Indicates the AppleTalk zones that ARAP connections on
                    this port may access: none, local, all, or named zone."
                ::= { arapPortEntry 2 }

            arapPortZoneName OBJECT-TYPE
                SYNTAX DisplayString (SIZE (0..32))
                ACCESS read-write
                STATUS mandatory
                DESCRIPTION
                    "If this port's arapPortZoneAccess field indicates a
                    named zone, this field contains the zone name."
                ::= { arapPortEntry 3 }

            arapPortMaxConnectTime OBJECT-TYPE
                SYNTAX INTEGER
                ACCESS read-write
                STATUS mandatory
                DESCRIPTION
                    "Maximum number of minutes a single ARAP connection may
                    exist on the port before a server initiated disconnect.
                    To set no limit on the amount of time that an ARAP user
                    may be connected, set this object to -1."
                ::= { arapPortEntry 4 }

            arapPortGuestLoginsOk OBJECT-TYPE
                SYNTAX INTEGER { disabled(1), enabled(2) }
                ACCESS read-write
                STATUS mandatory
                DESCRIPTION
                    "Indicates if 'Guest' logins (with no password) are
                    allowed on the port."
                ::= { arapPortEntry 5 }

            arapPortTimeConnected OBJECT-TYPE
                SYNTAX INTEGER
                ACCESS read-only
                STATUS mandatory
                DESCRIPTION
                    "Indicates the number of minutes the current ARAP
                    connection has been established on the port, rounded
                    up to the nearest minute.  Gets return -1 if no ARAP
                    user is currently connected on the port or if ARAP is
                    not enabled on the port."
                ::= { arapPortEntry 6 }

            arapPortTimeRemaining OBJECT-TYPE
                SYNTAX INTEGER
                ACCESS read-write
                STATUS mandatory
                DESCRIPTION
                    "Indicates the number of minutes the current ARAP
                    connection may remain on the port before a server
                    initiated disconnect will occur, rounded up to the
                    nearest minute.  To set no limit on the amount of
                    time that the current ARAP user may continue to be
                    connected, set this object to the maximum value
                    in the range.  Gets return -1 if no ARAP user is
                    currently connected on the port or if ARAP is not
                    enabled on the port.  Gets also return -1 if there
                    is a user connected and there is no limit on the
                    amount of time that the current user may be connected."
                ::= { arapPortEntry 7 }


--
-- FILE: /users/sse/mibs/src/itouch/it-boot-server-mib.mib
--

-- $Id: it-boot-server-mib.mib,v 1.1 2000/07/25 14:08:22 sse Exp $


            xBootServer     OBJECT IDENTIFIER ::= { iTouch 6 }

            -- ITouch Boot Server subgroups

            xBsBasic        OBJECT IDENTIFIER ::= { xBootServer 1 }
            xDump           OBJECT IDENTIFIER ::= { xBootServer 2 }
            xLoad           OBJECT IDENTIFIER ::= { xBootServer 3 }
            xParam          OBJECT IDENTIFIER ::= { xBootServer 4 }

            --  This is the MIB module for providers of iTouch
            --  bootstrap service.

            -- Copyright 2000 iTouch Communications, Inc. All Rights Reserved.
            -- Reproduction of this document is authorized on
            -- condition that this copyright notice is included.
            -- This MIB document embodies iTouch Communications, Inc.'s 
            -- proprietary intellectual property.  iTouch Communications, Inc.
            -- retains all title and ownership in this MIB, including any
            -- revisions.
            --
            -- It is iTouch Communications, Inc.'s intent to encourage the
            -- widespread use of this MIB in connection with the management of
            -- iTouch Communications, Inc. products. iTouch Communications,
            -- Inc. grants vendors,end-users, and other interested parties a
            -- non-exclusive license to use this MIB in connection with the
            -- management of iTouch Communications, Inc. products.
            --
            -- This MIB document is supplied "AS IS," and iTouch 
            -- Communications, Inc. makes no warranty, either express or
            -- implied, as to the use operation, condition, or performance of
            -- the MIB.


            -- Textual Conventions

            DialogStatus ::=
                INTEGER { none(1),
                          fileTooLarge(2),
                          notImageFile(3),
                          notExecutableFile(4),
                          badFileData(5),
                          deviceWriteProtected(6),
                          operationTimeout(7),
                          remoteFileNotFound(8),
                          remoteFileAccessViolation(9),
                          protocolError(10),
                          fileSystemError(11),
                          temporaryResourceConflict(12),
                          success(13) }
            -- Final status of a boot dialog.


            -- the Bootstrap Server Basic group

            -- Implementation of this group is mandatory for all iTouch
            -- systems that provide the iTouch bootstrap service

            basicLogLimit OBJECT-TYPE
                SYNTAX INTEGER (1..100)
                ACCESS read-write
                STATUS mandatory
                DESCRIPTION
                    "Maximum allowed number of kilobytes for recording 
                    events.  Corresponds directly to MANAGER LOG FILE 
                    SIZE and the value labeled 'Log File Size:' in the 
                    MANAGER CHARACTERISTICS display."
                ::= { xBsBasic 1 }

            basicActiveLimit OBJECT-TYPE
                SYNTAX INTEGER (0..32)
                ACCESS read-write
                STATUS mandatory
                DESCRIPTION
                    "Maximum allowed number of simultaneous service 
                    dialogs.  Corresponds directly to MANAGER 
                    SIMULTANEOUS and the value labeled 'Maximum 
                    simultaneous requests:' in the MANAGER 
                    CHARACTERISTICS display."
                ::= { xBsBasic 2 }

            basicActiveNumber OBJECT-TYPE
                SYNTAX Gauge
                ACCESS read-only
                STATUS mandatory
                DESCRIPTION
                    "Number of active service dialogs.  Corresponds 
                    indirectly to the list of active clients in the 
                    MANAGER STATUS display."
                ::= { xBsBasic 3 }

            basicClientNumber OBJECT-TYPE
                SYNTAX Gauge
                ACCESS read-only
                STATUS mandatory
                DESCRIPTION
                    "Number of defined clients.  Corresponds indirectly 
                    to the list of defined clients in the MANAGER LOCAL, 
                    MANAGER GLOBAL, and MANAGER NODE displays."


                ::= { xBsBasic 4 }

            basicOffersSent OBJECT-TYPE
                SYNTAX Counter
                ACCESS read-only
                STATUS mandatory
                DESCRIPTION
                    "Total number of service offers sent in response to 
                    client requests.  Corresponds directly to the value 
                    labeled 'Total service offers sent:' in the MANAGER 
                    STATUS display."
                ::= { xBsBasic 5 }

            basicEventTotal OBJECT-TYPE
                SYNTAX Gauge
                ACCESS read-only
                STATUS mandatory
                DESCRIPTION
                    "Total number of events that have been written to 
                    the event log since it was last purged.  This may be 
                    less than the number currently in the log.  
                    Corresponds directly to the value labeled 'Total 
                    Messages Logged:' in the MANAGER EVENTS display."
                ::= { xBsBasic 6 }

            basicEventPurge OBJECT-TYPE
                SYNTAX INTEGER { ready(1), execute(2) }
                ACCESS read-write
                STATUS mandatory
                DESCRIPTION
                    "Control to cause emptying the event log.  In 
                    response to a get-request or get-next-request, the 
                    agent always returns 'ready' for this value.  
                    Setting the value to 'ready' has no effect.  Setting 
                    it to 'execute' causes the event log to immediately 
                    become empty.  Corresponds directly to the PURGE 
                    MANAGER LOG FILE command."
                ::= { xBsBasic 7 }


            -- The Active table

            activeTable OBJECT-TYPE
                SYNTAX SEQUENCE OF ActiveEntry
                ACCESS not-accessible
                STATUS mandatory
                DESCRIPTION
                    "A list of active client dialog entries.  The number 
                    of entries is given by basicActiveNumber."
                ::= { xBsBasic 8 }

            activeEntry OBJECT-TYPE
                SYNTAX ActiveEntry
                ACCESS not-accessible
                STATUS mandatory
                DESCRIPTION
                    "Parameter values for an active client dialog 
                    entry."
                INDEX { activeIdentificationType, activeIdentification }
                ::= { activeTable 1 }

            ActiveEntry ::=
                SEQUENCE {
                    activeIdentificationType
                        AddressType,
                    activeIdentification
                        OCTET STRING,
                    activeFunction
                        INTEGER,
                    activeSoftwareVersionType
                        INTEGER,
                    activeSoftwareVersion
                        OCTET STRING,
                    activeParameterVersion
                        INTEGER,
                    activeCurrentSequence
                        INTEGER,
                    activeBytesRemaining
                        INTEGER,
                    activeFile
                        DisplayString,
                    activeStatus
                        DialogStatus,
                    activeState
                        INTEGER
                }


            activeIdentificationType OBJECT-TYPE
                SYNTAX AddressType
                ACCESS read-only
                STATUS mandatory
                DESCRIPTION
                    "The type of identification value in 
                    activeIdentification.  Corresponds indirectly to the 
                    value labeled 'EthernetAddress' in the MANAGER 
                    STATUS display."
                ::= { activeEntry 1 }

            activeIdentification OBJECT-TYPE
                SYNTAX OCTET STRING (SIZE (1..6))
                ACCESS read-only
                STATUS mandatory
                DESCRIPTION
                    "Identification of the active partner.  Corresponds 
                    directly to the value labeled 'EthernetAddress' in 
                    the MANAGER STATUS display."
                ::= { activeEntry 2 }

            activeFunction OBJECT-TYPE
                SYNTAX INTEGER { parameterStore(1), load(2), dump(3),
                                 imageUpdate(4) }
                ACCESS read-only
                STATUS mandatory
                DESCRIPTION
                    "The function the server is performing with the 
                    partner.  Corresponds directly to the value labeled 
                    'Function' in the MANAGER STATUS display."
                ::= { activeEntry 3 }

            activeSoftwareVersionType OBJECT-TYPE
                SYNTAX INTEGER { alpha(1), beta(2),
                                 production(3), special(4),
                                 diagnostic(5),notApplicable(6) }
                ACCESS read-only
                STATUS mandatory
                DESCRIPTION
                    "If activeFunction is 'load', the software version 
                    being sent to the client, otherwise 'notApplicable'.  
                    Corresponds to the letter in the software version 
                    labeled 'Version' in the MANAGER STATUS display.

                    alpha         'A':   alpha test


                    beta          'B':   beta test
                    production    null:  normal, production software
                    special       'S':   special, custom software
                    diagnostic    'D':   diagnostic, debug software
                    "
                ::= { activeEntry 4 }

            activeSoftwareVersion OBJECT-TYPE
                SYNTAX OCTET STRING (SIZE (0..4))
                ACCESS read-only
                STATUS mandatory
                DESCRIPTION
                    "If activeFunction is 'load', the 4-byte software 
                    version being sent to the client, otherwise zero 
                    length.  In order, the octets contain major version, 
                    minor version, ECO, and pre-release number.  
                    Corresponds to the numbers in the software version 
                    labeled 'Version' in the MANAGER STATUS display.

                    For example, the version display for 
                    activeSoftwareVersionType 'production' and 
                    activeSoftwareVersion '2.2.0.0' is 'V2.2'.

                    The version display for activeSoftwareVersionType 
                    'beta' and activeSoftwareVersion '3.1.0.4' is 
                    'V3.1B4'."
                ::= { activeEntry 5 }

            activeParameterVersion OBJECT-TYPE
                SYNTAX INTEGER
                ACCESS read-only
                STATUS mandatory
                DESCRIPTION
                    "If activeFunction is 'parameterStore', the 
                    parameter version being stored by the client, 
                    otherwise zero.  Corresponds directly to the value 
                    labeled 'Version' in the MANAGER STATUS display."
                ::= { activeEntry 6 }

            activeCurrentSequence OBJECT-TYPE
                SYNTAX INTEGER
                ACCESS read-only
                STATUS mandatory
                DESCRIPTION
                    "The current dialog sequence number.  Corresponds 
                    directly to the value labeled 'Seq' in the MANAGER 
                    STATUS display."


                ::= { activeEntry 7 }

            activeBytesRemaining OBJECT-TYPE
                SYNTAX INTEGER
                ACCESS read-only
                STATUS mandatory
                DESCRIPTION
                    "The number of bytes remaining to be transferred in 
                    the dialog.  Corresponds directly to the value 
                    labeled 'Left' in the MANAGER STATUS display."
                ::= { activeEntry 8 }

            activeFile OBJECT-TYPE
                SYNTAX DisplayString (SIZE (1..64))
                ACCESS read-only
                STATUS mandatory
                DESCRIPTION
                    "The name of the file being used in the dialog.  
                    Corresponds directly to the value labeled 'File' in 
                    the MANAGER STATUS display."
                ::= { activeEntry 9 }

            activeStatus OBJECT-TYPE
                SYNTAX DialogStatus
                ACCESS read-only
                STATUS mandatory
                DESCRIPTION
                    "The final status of the most recent attempt to get 
                    an image.  Corresponds directly to the value labeled 
                    'Get Status:' in the DEVICE STATUS display."
                ::= { activeEntry 10 }

            activeState OBJECT-TYPE
                SYNTAX INTEGER { idle(1),
                                 internal1(2),
                                 internal2(3),
                                 openPartner(4),
                                 openFile(5),
                                 receivePartner(6),
                                 writeFile(7),
                                 closePartner(8),
                                 closeFile(9),
                                 cleanup(10),
                                 done(11),
                                 error(12) }
                ACCESS read-only


                STATUS mandatory
                DESCRIPTION
                    "The dynamic state of an active attempt to get an 
                    image.  Corresponds directly to the value labeled 
                    'Get State:' in the DEVICE STATUS display."
                ::= { activeEntry 11 }


            -- The Client table

            clientTable OBJECT-TYPE
                SYNTAX SEQUENCE OF ClientEntry
                ACCESS not-accessible
                STATUS mandatory
                DESCRIPTION
                    "A list of client data base entries.  The number of 
                    entries is given by basicClientNumber."
                ::= { xBsBasic 9 }

            clientEntry OBJECT-TYPE
                SYNTAX ClientEntry
                ACCESS not-accessible
                STATUS mandatory
                DESCRIPTION
                    "Parameter values for a client data base entry."
                INDEX { clientIdentificationType, clientIdentification }
                ::= { clientTable 1 }

            ClientEntry ::=
                SEQUENCE {
                    clientIdentificationType
                        AddressType,
                    clientIdentification
                        OCTET STRING,
                    clientEntryStatus
                        INTEGER,
                    clientName
                        DisplayString,
                    clientLoadFile
                        DisplayString,
                    clientDiagnosticFile
                        DisplayString,
                    clientLoadService
                        INTEGER,
                    clientDumpService
                        INTEGER
                }

            clientIdentificationType OBJECT-TYPE
                SYNTAX AddressType
                ACCESS read-only
                STATUS mandatory
                DESCRIPTION
                    "The type of identification value in 


                            clientIdentification.  Corresponds directly to 
                    MANAGER NODE, MANAGER GLOBAL, and MANAGER LOCAL, and  
                    the value labeled 'Ethernet Address' in the MANAGER 
                    NODE display or 'Ethernet Address', 'Device', and 
                    'Global Devices' or 'Local Devices' in the MANAGER 
                    GLOBAL and LOCAL displays."
                ::= { clientEntry 1 }

            clientIdentification OBJECT-TYPE
                SYNTAX OCTET STRING (SIZE (1..6))
                ACCESS read-only
                STATUS mandatory
                DESCRIPTION
                    "Identification of the client, either a hardware 
                    type or an Ethernet address, depending on 
                    clientIdentificationType.  Corresponds directly to 
                    MANAGER NODE, MANAGER GLOBAL, and MANAGER LOCAL, and  
                    the value labeled 'Ethernet Address' in the MANAGER 
                    NODE display or 'Ethernet Address', 'Device', and 
                    'Global Devices' or 'Local Devices' in the MANAGER 
                    GLOBAL and LOCAL displays."
                ::= { clientEntry 2 }

            clientEntryStatus OBJECT-TYPE
                SYNTAX INTEGER { invalid(1), valid(2) }
                ACCESS read-write
                STATUS mandatory
                DESCRIPTION
                    "The status of the entry.  Set to 'invalid' to 
                    remove the entry, which corresponds directly to the 
                    PURGE LOCAL, PURGE GLOBAL, and PURGE NODE commands.  
                    Actual removal of the entry is implementation 
                    specific."
                DEFVAL { valid }
                ::= { clientEntry 3 }

            clientName OBJECT-TYPE
                SYNTAX DisplayString (SIZE (0..16))
                ACCESS read-write
                STATUS mandatory
                DESCRIPTION
                    "A name that may be used to identify the client.  
                    Corresponds directly to the value labeled 'Name' in 
                    the MANAGER NODE display."
                DEFVAL { "" }
                ::= { clientEntry 4 }


            clientLoadFile OBJECT-TYPE
                SYNTAX DisplayString (SIZE (0..16))
                ACCESS read-write
                STATUS mandatory
                DESCRIPTION
                    "The file with the client's load image.  Corresponds 
                    directly to the value labeled 'Load File' in the 
                    MANAGER LOCAL, MANAGER GLOBAL, and MANAGER NODE 
                    displays."
                DEFVAL { "" }
                ::= { clientEntry 5 }

            clientDiagnosticFile OBJECT-TYPE
                SYNTAX DisplayString (SIZE (0..16))
                ACCESS read-write
                STATUS mandatory
                DESCRIPTION
                    "The file with the client's diagnostic test image.  
                    Corresponds directly to the value labeled 'Diag 
                    File' in the MANAGER LOCAL, MANAGER GLOBAL, and 
                    MANAGER NODE displays."
                DEFVAL { "" }
                ::= { clientEntry 6 }

            clientLoadService OBJECT-TYPE
                SYNTAX INTEGER { disabled(1), enabled(2) }
                ACCESS read-write
                STATUS mandatory
                DESCRIPTION
                    "Control for allowing load service for the client.  
                    Corresponds directly to the value labeled 'Load' in 
                    the MANAGER LOCAL, MANAGER GLOBAL, and MANAGER NODE 
                    displays."
                DEFVAL { enabled }
                ::= { clientEntry 7 }

            clientDumpService OBJECT-TYPE
                SYNTAX INTEGER { disabled(1), enabled(2) }
                ACCESS read-write
                STATUS mandatory
                DESCRIPTION
                    "Control for allowing dump service for the client.  
                    Corresponds directly to the value labeled 'Dump' in 
                    the MANAGER LOCAL, MANAGER GLOBAL, and MANAGER NODE 
                    displays."


                DEFVAL { disabled }
                ::= { clientEntry 8 }


            -- The Named Client table

            -- This table is strict subset of the Client table, being
            -- the same information in the same form with client name
            -- as the table index instead of client identification.
            -- It does not contain clients that have no name.

            namedTable OBJECT-TYPE
                SYNTAX SEQUENCE OF NamedEntry
                ACCESS not-accessible
                STATUS mandatory
                DESCRIPTION
                    "A list of named client data base entries.  The 
                    number of entries is given by basicClientNumber."
                ::= { xBsBasic 10 }

            namedEntry OBJECT-TYPE
                SYNTAX NamedEntry
                ACCESS not-accessible
                STATUS mandatory
                DESCRIPTION
                    "Parameter values for a named client data base 
                    entry."
                INDEX { namedName }
                ::= { namedTable 1 }

            NamedEntry ::=
                SEQUENCE {
                    namedIdentificationType
                        AddressType,
                    namedIdentification
                        OCTET STRING,
                    namedEntryStatus
                        INTEGER,
                    namedName
                        DisplayString,
                    namedLoadFile
                        DisplayString,
                    namedDiagnosticFile
                        DisplayString,
                    namedLoadService
                        INTEGER,
                    namedDumpService
                        INTEGER
                }


            namedIdentificationType OBJECT-TYPE
                SYNTAX AddressType
                ACCESS read-only
                STATUS mandatory
                DESCRIPTION
                    "The type of identification value in 
                    namedIdentification.  Corresponds directly to 
                    MANAGER NODE, MANAGER GLOBAL, and MANAGER LOCAL, and  
                    the value labeled 'Ethernet Address' in the MANAGER 
                    NODE display or 'Ethernet Address', 'Device', and 
                    'Global Devices' or 'Local Devices' in the MANAGER 
                    GLOBAL and LOCAL displays."
                ::= { namedEntry 1 }

            namedIdentification OBJECT-TYPE
                SYNTAX OCTET STRING (SIZE (1..6))
                ACCESS read-only
                STATUS mandatory
                DESCRIPTION
                    "Identification of the client, either a hardware 
                    type or an Ethernet address, depending on 
                    namedIdentificationType.  Corresponds directly to 
                    MANAGER NODE, MANAGER GLOBAL, and MANAGER LOCAL, and  
                    the value labeled 'Ethernet Address' in the MANAGER 
                    NODE display or 'Ethernet Address', 'Device', and 
                    'Global Devices' or 'Local Devices' in the MANAGER 
                    GLOBAL and LOCAL displays."
                ::= { namedEntry 2 }

            namedEntryStatus OBJECT-TYPE
                SYNTAX INTEGER { invalid(1), valid(2) }
                ACCESS read-only
                STATUS mandatory
                DESCRIPTION
                    "The status of the entry.  Set to 'invalid' to 
                    remove the entry, which corresponds directly to the 
                    PURGE LOCAL, PURGE GLOBAL, and PURGE NODE commands.  
                    Actual removal of the entry is implementation 
                    specific."
                DEFVAL { valid }
                ::= { namedEntry 3 }

            namedName OBJECT-TYPE
                SYNTAX DisplayString (SIZE (0..16))
                ACCESS read-only
                STATUS mandatory


                DESCRIPTION
                    "A name that may be used to identify the client.  
                    Corresponds directly to the value labeled 'Name' in 
                    the MANAGER NODE display."
                ::= { namedEntry 4 }

            namedLoadFile OBJECT-TYPE
                SYNTAX DisplayString (SIZE (0..16))
                ACCESS read-only
                STATUS mandatory
                DESCRIPTION
                    "The file with the client's load image.  Corresponds 
                    directly to the value labeled 'Load File' in the 
                    MANAGER LOCAL, MANAGER GLOBAL, and MANAGER NODE 
                    displays."
                DEFVAL { "" }
                ::= { namedEntry 5 }

            namedDiagnosticFile OBJECT-TYPE
                SYNTAX DisplayString (SIZE (0..16))
                ACCESS read-only
                STATUS mandatory
                DESCRIPTION
                    "The file with the client's diagnostic test image.  
                    Corresponds directly to the value labeled 'Diag 
                    File' in the MANAGER LOCAL, MANAGER GLOBAL, and 
                    MANAGER NODE displays."
                DEFVAL { "" }
                ::= { namedEntry 6 }

            namedLoadService OBJECT-TYPE
                SYNTAX INTEGER { disabled(1), enabled(2) }
                ACCESS read-only
                STATUS mandatory
                DESCRIPTION
                    "Control for allowing load service for the client.  
                    Corresponds directly to the value labeled 'Load' in 
                    the MANAGER LOCAL, MANAGER GLOBAL, and MANAGER NODE 
                    displays."
                DEFVAL { enabled }
                ::= { namedEntry 7 }

            namedDumpService OBJECT-TYPE
                SYNTAX INTEGER { disabled(1), enabled(2) }
                ACCESS read-only
                STATUS mandatory


                DESCRIPTION
                    "Control for allowing dump service for the client.  
                    Corresponds directly to the value labeled 'Dump' in 
                    the MANAGER LOCAL, MANAGER GLOBAL, and MANAGER NODE 
                    displays."
                DEFVAL { disabled }
                ::= { namedEntry 8 }


            -- The Event table

            xEventTable OBJECT-TYPE
                SYNTAX SEQUENCE OF XEventEntry
                ACCESS not-accessible
                STATUS mandatory
                DESCRIPTION
                    "A list of event entries.  The number of entries is 
                    given by basicEventNumber."
                ::= { xBsBasic 11 }

            xEventEntry OBJECT-TYPE
                SYNTAX XEventEntry
                ACCESS not-accessible
                STATUS mandatory
                DESCRIPTION
                    "Parameter values for a event entry."
                INDEX { xEventIndex }
                ::= { xEventTable 1 }

            XEventEntry ::=
                SEQUENCE {
                    xEventIndex
                        INTEGER,
                    xEventText
                        DisplayString
                }

            xEventIndex OBJECT-TYPE
                SYNTAX INTEGER
                ACCESS read-only
                STATUS mandatory
                DESCRIPTION
                    "In identification number for an event.  The value 1 
                    indicates the oldest event in the file, with 
                    subsequent numbers indicating sequential events.  
                    The event text for a given number may change as a 
                    circular event log wraps over its beginning.  
                    Corresponds directly to the relative position of an 
                    event in the MANAGER EVENTS display."
                ::= { xEventEntry 1 }

            xEventText OBJECT-TYPE
                SYNTAX DisplayString (SIZE (1..255))
                ACCESS read-only
                STATUS mandatory


                DESCRIPTION
                    "The text of the event, including date, time and 
                    other information.  Corresponds directly to the 
                    individual event text in the MANAGER EVENTS 
                    display."
                ::= { xEventEntry 2 }


            -- The Device table

            basicDeviceNumber OBJECT-TYPE
                SYNTAX INTEGER
                ACCESS read-only
                STATUS mandatory
                DESCRIPTION
                    "The system's number of mass-storage devices."
                ::= { xBsBasic 12 }

            deviceTable OBJECT-TYPE
                SYNTAX SEQUENCE OF DeviceEntry
                ACCESS not-accessible
                STATUS mandatory
                DESCRIPTION
                    "A list of device entries.  The number of entries is 
                    given by basicDeviceNumber."
                ::= { xBsBasic 13 }

            deviceEntry OBJECT-TYPE
                SYNTAX DeviceEntry
                ACCESS not-accessible
                STATUS mandatory
                DESCRIPTION
                    "Parameter values for a device entry."
                INDEX { deviceIndex }
                ::= { deviceTable 1 }

            DeviceEntry ::=
                SEQUENCE {
                    deviceIndex
                        INTEGER,
                    deviceName
                        DisplayString,
                    deviceDescr
                        DisplayString,
                    deviceOperation
                        INTEGER,
                    deviceFormat
                        INTEGER,
                    deviceProtection
                        INTEGER,
                    deviceFormatMedium
                        INTEGER,
                    deviceGetFile
                        INTEGER,


                    deviceGetFileHostIdentificationType
                        AddressType,
                    deviceGetFileHostIdentification
                        OCTET STRING,
                    deviceGetFileName
                        DisplayString,
                    deviceGetFileArea
                        INTEGER,
                    deviceFormatOption
                        INTEGER,
                    deviceFormatRedundantParams
                        INTEGER,
                    devicePreviousStatus
                        DialogStatus
                }

            deviceIndex OBJECT-TYPE
                SYNTAX INTEGER
                ACCESS read-only
                STATUS mandatory
                DESCRIPTION
                    "In identification number for a device, in the range 
                    1 to basicDeviceNumber"
                ::= { deviceEntry 1 }

            deviceName OBJECT-TYPE
                SYNTAX DisplayString (SIZE (0..16))
                ACCESS read-only
                STATUS mandatory
                DESCRIPTION
                    "A name by which the device is known in other 
                    displays, such as 'C1' or 'D2'."
                ::= { deviceEntry 2 }

            deviceDescr OBJECT-TYPE
                SYNTAX DisplayString (SIZE (0..80))
                ACCESS read-only
                STATUS mandatory
                DESCRIPTION
                    "Details of the device type, including, for example, 
                    size, manufacturer, Flash versus RAM, and such.  
                    Corresponds directly to the value labeled 'Device 
                    Type: in the MANAGER DEVICE STATUS display."
                ::= { deviceEntry 3 }

            deviceOperation OBJECT-TYPE


                SYNTAX INTEGER { read(1), write(2), format(3), idle(4),
                                 erase(5), paramStore(6), unpack(7),
                                 loadingClient(8) }
                ACCESS read-only
                STATUS mandatory
                DESCRIPTION
                    "Current operational state of the device.  
                    Corresponds directly the value labeled 'Device 
                    Operation:' in the MANAGER DEVICE STATUS display."
                ::= { deviceEntry 4 }

            deviceFormat OBJECT-TYPE
                SYNTAX INTEGER { unformatted(1), formatted(2),
                                 unknown(3) }
                ACCESS read-only
                STATUS mandatory
                DESCRIPTION
                    "Formatting status of the device.  Corresponds 
                    directly the presence of one of the value labels 
                    under the label 'Device Status:' in the MANAGER 
                    DEVICE STATUS display."
                ::= { deviceEntry 5 }

            deviceProtection OBJECT-TYPE
                SYNTAX INTEGER { write-enabled(1), write-protected(2),
                                 unknown(3) }
                ACCESS read-only
                STATUS mandatory
                DESCRIPTION
                    "Write-protect status of the device.  Corresponds 
                    directly the presence of one of the value labels 
                    under the label 'Device Status:' in the MANAGER 
                    DEVICE STATUS display."
                ::= { deviceEntry 6 }

            deviceFormatMedium OBJECT-TYPE
                SYNTAX INTEGER { ready(1), execute(2) }
                ACCESS read-write
                STATUS mandatory
                DESCRIPTION
                    "Control to cause formatting of the medium in the 
                    device.  In response to a get-request or 
                    get-next-request, the agent always returns 'ready' 
                    for this value.  Setting the value to 'ready' has no 
                    effect.  Setting it to 'execute' causes the device 
                    to be formatted.  Corresponds directly to the FORMAT 


                            DEVICE command."
                ::= { deviceEntry 7 }

            deviceGetFile OBJECT-TYPE
                SYNTAX INTEGER { ready(1), execute(2), abort(3) }
                ACCESS read-write
                STATUS mandatory
                DESCRIPTION
                    "Control to cause getting a file to the device from 
                    a remote host system.  In response to a get-request 
                    or get-next-request, the agent always returns 
                    'ready' for this value.  Setting the value to 
                    'ready' has no effect.  Setting it to 'execute' 
                    causes the get to be attempted.  Corresponds 
                    directly to the GET DEVICE command.

                    When set to 'execute', the objects 
                    deviceGetFileHostIdentificationType, 
                    deviceGetFileHostIdentification,
                    deviceGetFileName and deviceGetFileArea
                    must be somewhere in the same set 
                    request message."
                ::= { deviceEntry 8 }

            deviceGetFileHostIdentificationType OBJECT-TYPE
                SYNTAX AddressType
                ACCESS read-write
                STATUS mandatory
                DESCRIPTION
                    "The type of identification value in 
                    deviceIdentification.  Corresponds indirectly to 
                    ADDRESS in the GET DEVICE command.

                    This object may not be set outside the context of 
                    setting deviceGetFile to 'execute'.  In response to 
                    a get-request or get-next-request, the value of this 
                    object is 'undefined'."
                ::= { deviceEntry 9 }

            deviceGetFileHostIdentification OBJECT-TYPE
                SYNTAX OCTET STRING (SIZE (1..6))
                ACCESS read-write
                STATUS mandatory
                DESCRIPTION
                    "Identification of the host to get the file from, 
                    with type depending on deviceIdentificationType.  
                    Corresponds directly to ADDRESS in the GET DEVICE 
                    command.

                    This object may not be set outside the context of 
                    setting deviceGetFile to 'execute'.  In response to 
                    a get-request or get-next-request, the value of this 
                    object is zero length."
                ::= { deviceEntry 10 }

            deviceGetFileName OBJECT-TYPE
                SYNTAX DisplayString (SIZE (1..64))
                ACCESS read-write
                STATUS mandatory
                DESCRIPTION
                    "The name of the file to get.  Corresponds directly 
                    to LOAD FILE in the GET DEVICE command.

                    This object may not be set outside the context of 
                    setting deviceGetFile to 'execute'.  In response to 
                    a get-request or get-next-request, the value of this 
                    object is zero length."
                ::= { deviceEntry 11 }

            deviceGetFileArea OBJECT-TYPE
                SYNTAX INTEGER (1..16)
                ACCESS read-write
                STATUS mandatory
                DESCRIPTION
                    "The area number in which to put the file.  
                    Corresponds directly to AREA in the GET DEVICE 
                    command. If it is not relevant to the particular 
                    device, it is ignored.

                    This object may not be set outside the context of 
                    setting deviceGetFile to 'execute'.  In response to 
                    a get-request or get-next-request, the value of this 
                    object is zero."
                ::= { deviceEntry 12 }

            deviceFormatOption OBJECT-TYPE
                SYNTAX INTEGER (1..3)
                ACCESS read-write
                STATUS mandatory
                DESCRIPTION
                    "Formatting option to apply.  Corresponds directly 
                    to the OPTION in the FORMAT DEVICE command.

                    This object may not be set outside the context of 
                    setting deviceFormatMedium to 'execute'.  In 
                    response to a get-request or get-next-request, the 
                    value of this object is zero."
                DEFVAL { 1 }
                ::= { deviceEntry 13 }

            deviceFormatRedundantParams OBJECT-TYPE
                SYNTAX INTEGER { nonredundant(1), redundant(2) }
                ACCESS read-write
                STATUS mandatory
                DESCRIPTION
                    "Control for creating redundant parameter storage 
                    areas when formatting.    Corresponds directly to 
                    NONREDUNDANT in the FORMAT DEVICE command.

                    This object may not be set outside the context of 
                    setting deviceFormatMedium to 'execute'.  In 
                    response to a get-request or get-next-request, the 
                    value of this object is zero."
                DEFVAL { redundant }
                ::= { deviceEntry 14 }

            devicePreviousStatus OBJECT-TYPE
                SYNTAX DialogStatus
                ACCESS read-only
                STATUS mandatory
                DESCRIPTION
                    "Result of the immediately previous concluded boot 
                    dialog.  Corresponds directly to the value labeled 
                    'Get File Previous Status:' in the SHOW CARD STATUS 
                    display."
                ::= { deviceEntry 15 }


            -- the Bootstrap Server Dump group

            -- Implementation of this group is mandatory for all iTouch
            -- systems that provide the iTouch bootstrap dump service

            dumpService OBJECT-TYPE
                SYNTAX INTEGER { disabled(1), enabled(2) }
                ACCESS read-write
                STATUS mandatory
                DESCRIPTION
                    "Control for allowing dump service for any client.  
                    Corresponds directly to DUMP and the value labeled 
                    'Dump:' in the MANAGER CHARACTERISTICS display."
                ::= { xDump 1 }

            dumpDrive OBJECT-TYPE
                SYNTAX INTEGER (1..2)
                ACCESS read-write
                STATUS mandatory
                DESCRIPTION
                    "Identification number of the disk drive where dumps 
                    are stored.  Corresponds directly to DUMP DRIVE and 
                    the value labeled 'Dump Drive:' in the MANAGER 
                    CHARACTERISTICS display."
                ::= { xDump 2 }

            dumpMerit OBJECT-TYPE
                SYNTAX INTEGER (0..15)
                ACCESS read-write
                STATUS mandatory
                DESCRIPTION
                    "Relative preference for this dump server over 
                    others.  Corresponds directly to DUMP MERIT and the 
                    value labeled 'Dump Merit:' in the MANAGER 
                    CHARACTERISTICS display."
                ::= { xDump 3 }

            dumpSize OBJECT-TYPE
                SYNTAX INTEGER { small(1), full(2) }
                ACCESS read-write
                STATUS mandatory
                DESCRIPTION
                    "Type of dump file to keep.  Corresponds directly to 
                    DUMP SIZE and the value labeled 'Dump Size:' in the 
                    MANAGER CHARACTERISTICS display."
                ::= { xDump 4 }


            dumpCompleted OBJECT-TYPE
                SYNTAX Counter
                ACCESS read-only
                STATUS mandatory
                DESCRIPTION
                    "The number of dumps completed since system 
                    initialization.  Corresponds directly to the value 
                    labeled 'Dump Operations Completed:' in the MANAGER 
                    STATUS display."
                ::= { xDump 5 }

            dumpActive OBJECT-TYPE
                SYNTAX Gauge
                ACCESS read-only
                STATUS mandatory
                DESCRIPTION
                    "The number of dumps in progress.  Corresponds 
                    directly to the value labeled 'Currently Dumping:' 
                    in the MANAGER STATUS display."
                ::= { xDump 6 }

            dumpFileNumber OBJECT-TYPE
                SYNTAX Gauge
                ACCESS read-only
                STATUS mandatory
                DESCRIPTION
                    "The number of dump files currently stored.  
                    Corresponds directly to the value labeled 'Network 
                    dump files' and 'files' in the MANAGER FILES 
                    display."
                ::= { xDump 7 }


            -- The Dump File table

            dumpFileTable OBJECT-TYPE
                SYNTAX SEQUENCE OF DumpFileEntry
                ACCESS not-accessible
                STATUS mandatory
                DESCRIPTION
                    "A list of dump file entries.  The number of entries 
                    is given by dumpFileNumber."
                ::= { xDump 8 }

            dumpFileEntry OBJECT-TYPE
                SYNTAX DumpFileEntry
                ACCESS not-accessible
                STATUS mandatory
                DESCRIPTION
                    "Parameter values for a dump file entry."
                INDEX { dumpFileIdentificationType,
                        dumpFileIdentification }
                ::= { dumpFileTable 1 }

            DumpFileEntry ::=
                SEQUENCE {
                    dumpFileIdentificationType
                        AddressType,
                    dumpFileIdentification
                        OCTET STRING,
                    dumpFileEntryStatus
                        INTEGER,
                    dumpFileCreation
                        DateTime,
                    dumpFileSize
                        INTEGER
                }

            dumpFileIdentificationType OBJECT-TYPE
                SYNTAX AddressType
                ACCESS read-only
                STATUS mandatory
                DESCRIPTION
                    "The type of identification value in 
                    dumpFileIdentification.  Corresponds indirectly to a 
                    file name part in the section labeled 'Network dump 
                    files' in the MANAGER FILES display."
                ::= { dumpFileEntry 1 }


            dumpFileIdentification OBJECT-TYPE
                SYNTAX OCTET STRING (SIZE (1..6))
                ACCESS read-only
                STATUS mandatory
                DESCRIPTION
                    "Identification of the dump file, an Ethernet 
                    address, as indicated by dumpFileIdentificationType.  
                    Corresponds indirectly to a file name part in the 
                    section labeled 'Network dump files' in the MANAGER 
                    FILES display."
                ::= { dumpFileEntry 2 }

            dumpFileEntryStatus OBJECT-TYPE
                SYNTAX INTEGER { invalid(1), valid(2) }
                ACCESS read-write
                STATUS mandatory
                DESCRIPTION
                    "The status of the entry.  Set to 'invalid' to 
                    remove the entry, which corresponds indirectly to 
                    the PURGE MANAGER DUMP FILES command.  Actual 
                    removal of the entry is implementation specific."
                ::= { dumpFileEntry 3 }

            dumpFileCreation OBJECT-TYPE
                SYNTAX DateTime
                ACCESS read-only
                STATUS mandatory
                DESCRIPTION
                    "The time the dump file was created.  Corresponds 
                    directly to a date and time in the section labeled 
                    'Network dump files' in the MANAGER FILES display."
                ::= { dumpFileEntry 4 }

            dumpFileSize OBJECT-TYPE
                SYNTAX INTEGER
                ACCESS read-only
                STATUS mandatory
                DESCRIPTION
                    "The number of bytes stored in the dump file.  
                    Corresponds directly to the value labeled 'bytes' in 
                    the section labeled 'Network dump files' in the 
                    MANAGER FILES display."
                ::= { dumpFileEntry 5 }


            -- the Bootstrap Server Load group

            -- Implementation of this group is mandatory for all iTouch
            -- systems that provide the iTouch bootstrap load service

            loadService OBJECT-TYPE
                SYNTAX INTEGER { disabled(1), enabled(2) }
                ACCESS read-write
                STATUS mandatory
                DESCRIPTION
                    "Control for allowing load service for any client.  
                    Corresponds directly to LOAD and the value labeled 
                    'Load:' in the MANAGER CHARACTERISTICS display."
                ::= { xLoad 1 }

            loadMerit OBJECT-TYPE
                SYNTAX INTEGER (0..15)
                ACCESS read-write
                STATUS mandatory
                DESCRIPTION
                    "Relative preference for this load server over 
                    others.  Corresponds directly to LOAD MERIT and the 
                    value labeled 'Load Merit:' in the MANAGER 
                    CHARACTERISTICS display."
                ::= { xLoad 2 }

            loadCompleted OBJECT-TYPE
                SYNTAX Counter
                ACCESS read-only
                STATUS mandatory
                DESCRIPTION
                    "The number of loads completed since system 
                    initialization.  Corresponds directly to the value 
                    labeled 'Load Operations Completed:' in the MANAGER 
                    STATUS display."
                ::= { xLoad 3 }

            loadActive OBJECT-TYPE
                SYNTAX Gauge
                ACCESS read-only
                STATUS mandatory
                DESCRIPTION
                    "The number of loads in progress.  Corresponds 
                    directly to the value labeled 'Currently Loading:' 
                    in the MANAGER STATUS display."
                ::= { xLoad 4 }


            loadFileNumber OBJECT-TYPE
                SYNTAX Gauge
                ACCESS read-only
                STATUS mandatory
                DESCRIPTION
                    "The number of load files currently stored.  
                    Corresponds directly to the value labeled 'Load 
                    image files' and 'files' in the MANAGER FILES 
                    display."
                ::= { xLoad 5 }


            -- The Load File table

            loadFileTable OBJECT-TYPE
                SYNTAX SEQUENCE OF LoadFileEntry
                ACCESS not-accessible
                STATUS mandatory
                DESCRIPTION
                    "A list of load file entries.  The number of entries 
                    is given by loadFileNumber."
                ::= { xLoad 6 }

            loadFileEntry OBJECT-TYPE
                SYNTAX LoadFileEntry
                ACCESS not-accessible
                STATUS mandatory
                DESCRIPTION
                    "Parameter values for a load file entry."
                INDEX { loadFileName }
                ::= { loadFileTable 1 }

            LoadFileEntry ::=
                SEQUENCE {
                    loadFileName
                        DisplayString,
                    loadFileCreation
                        DateTime,
                    loadFileSize
                        INTEGER,
                    loadFileSoftwareVersionType
                        INTEGER,
                    loadFileSoftwareVersion
                        OCTET STRING
                }

            loadFileName OBJECT-TYPE
                SYNTAX DisplayString (SIZE (1..16))
                ACCESS read-only
                STATUS mandatory
                DESCRIPTION
                    "The name of a load file.  Corresponds directly to a 
                    file name part in the section labeled 'Load image 
                    files' in the MANAGER FILES display."
                ::= { loadFileEntry 1 }

            loadFileCreation OBJECT-TYPE
                SYNTAX DateTime


                ACCESS read-only
                STATUS mandatory
                DESCRIPTION
                    "The time the load file was created.  Corresponds 
                    directly to a date and time in the section labeled 
                    'Load image files' in the MANAGER FILES display."
                ::= { loadFileEntry 2 }

            loadFileSize OBJECT-TYPE
                SYNTAX INTEGER
                ACCESS read-only
                STATUS mandatory
                DESCRIPTION
                    "The number of bytes stored in the load file.  
                    Corresponds directly to the value labeled 'bytes' in 
                    the section labeled 'Load image files' in the 
                    MANAGER FILES display."
                ::= { loadFileEntry 3 }

            loadFileSoftwareVersionType OBJECT-TYPE
                SYNTAX INTEGER { alpha(1), beta(2),
                                 production(3), special(4) }
                ACCESS read-only
                STATUS mandatory
                DESCRIPTION
                    "The software version type of the image in the load 
                    file.  Corresponds directly to a software version in 
                    the section labeled 'Load image files' in the 
                    MANAGER FILES display.

                    alpha         'A':   alpha test
                    beta          'B':   beta test
                    production    null:  normal, production software
                    special       'S':   special, custom software
                    "
                ::= { loadFileEntry 4 }

            loadFileSoftwareVersion OBJECT-TYPE
                SYNTAX OCTET STRING (SIZE (0..4))
                ACCESS read-only
                STATUS mandatory
                DESCRIPTION
                    "The software version of the image in the load file.  
                    Corresponds directly to a software version in the 
                    section labeled 'Load image files' in the MANAGER 
                    FILES display.


                    For example, the version display for 
                    loadFileSoftwareVersionType 'production' and 
                    loadFileSoftwareVersion '2.2.0.0' is 'V2.2'.

                    The version display for loadFileSoftwareVersionType 
                    'beta' and loadFileSoftwareVersion '3.1.0.4' is 
                    'V3.1B4'."
                ::= { loadFileEntry 5 }


            -- the Bootstrap Server Parameter Storage group

            -- Implementation of this group is mandatory for all iTouch
            -- systems that provide the iTouch bootstrap parameter
            -- storage service

            paramService OBJECT-TYPE
                SYNTAX INTEGER { disabled(1), enabled(2) }
                ACCESS read-write
                STATUS mandatory
                DESCRIPTION
                    "Control for allowing parameter storage service for 
                    any client.  Corresponds directly to PARAMETER 
                    SERVICE and the value labeled 'Parameter Service:' 
                    in the MANAGER CHARACTERISTICS display."
                ::= { xParam 1 }

            paramDefaultService OBJECT-TYPE
                SYNTAX INTEGER { disabled(1), enabled(2) }
                ACCESS read-write
                STATUS mandatory
                DESCRIPTION
                    "Control for allowing default parameter loading 
                    service for any client.  Corresponds directly to 
                    PARAMETER DEFAULT SERVICE and the value labeled 
                    'Parameter Default Service:' in the MANAGER 
                    CHARACTERISTICS display."
                ::= { xParam 2 }

            paramDrive OBJECT-TYPE
                SYNTAX INTEGER (1..2)
                ACCESS read-write
                STATUS mandatory
                DESCRIPTION
                    "Identification number of the disk drive where 
                    parameters are stored.  Corresponds directly to 
                    PARAMETER DRIVE and the value labeled 'Parameter 
                    Drive:' in the MANAGER CHARACTERISTICS display."
                ::= { xParam 3 }

            paramActive OBJECT-TYPE
                SYNTAX Gauge
                ACCESS read-only
                STATUS mandatory
                DESCRIPTION
                    "The number of params in progress.  Corresponds 


                            directly to the value labeled 'Currently Paraming:' 
                    in the MANAGER STATUS display."
                ::= { xParam 4 }

            paramStorageActive OBJECT-TYPE
                SYNTAX Gauge
                ACCESS read-only
                STATUS mandatory
                DESCRIPTION
                    "The number of parameter storage operations in 
                    progress.  Corresponds directly to the value labeled 
                    'Currently saving parameters:' in the MANAGER STATUS 
                    display."
                ::= { xParam 5 }

            paramFileNumber OBJECT-TYPE
                SYNTAX Gauge
                ACCESS read-only
                STATUS mandatory
                DESCRIPTION
                    "The number of parameter files currently stored.  
                    Corresponds directly to the value labeled 'Parameter 
                    files' and 'files' in the MANAGER FILES display."
                ::= { xParam 6 }


            -- The Param File table

            paramFileTable OBJECT-TYPE
                SYNTAX SEQUENCE OF ParamFileEntry
                ACCESS not-accessible
                STATUS mandatory
                DESCRIPTION
                    "A list of param file entries.  The number of 
                    entries is given by paramFileNumber."
                ::= { xParam 7 }

            paramFileEntry OBJECT-TYPE
                SYNTAX ParamFileEntry
                ACCESS not-accessible
                STATUS mandatory
                DESCRIPTION
                    "Parameter values for a param file entry."
                INDEX { paramFileIdentificationType,
                        paramFileIdentification }
                ::= { paramFileTable 1 }

            ParamFileEntry ::=
                SEQUENCE {
                    paramFileIdentificationType
                        AddressType,
                    paramFileIdentification
                        OCTET STRING,
                    paramFileEntryStatus
                        INTEGER,
                    paramFileWrite
                        DateTime,
                    paramFileSize
                        INTEGER,
                    paramFileParameterVersion
                        INTEGER
                }

            paramFileIdentificationType OBJECT-TYPE
                SYNTAX AddressType
                ACCESS read-only
                STATUS mandatory
                DESCRIPTION
                    "The type of identification value in 
                    paramFileIdentification.  Corresponds indirectly to 
                    a file name part in the section labeled 'Parameter 
                    files' in the MANAGER FILES display."


                ::= { paramFileEntry 1 }

            paramFileIdentification OBJECT-TYPE
                SYNTAX OCTET STRING (SIZE (1..6))
                ACCESS read-only
                STATUS mandatory
                DESCRIPTION
                    "Identification of the param file, an Ethernet 
                    address, as indicated by 
                    paramFileIdentificationType.  Corresponds indirectly 
                    to a file name part in the section labeled 
                    'Parameter files' in the MANAGER FILES display."
                ::= { paramFileEntry 2 }

            paramFileEntryStatus OBJECT-TYPE
                SYNTAX INTEGER { invalid(1), valid(2) }
                ACCESS read-write
                STATUS mandatory
                DESCRIPTION
                    "The status of the entry.  Set to 'invalid' to 
                    remove the entry, which corresponds indirectly to 
                    the PURGE MANAGER PARAMETER FILES command.  Actual 
                    removal of the entry is implementation specific."
                ::= { paramFileEntry 3 }

            paramFileWrite OBJECT-TYPE
                SYNTAX DateTime
                ACCESS read-only
                STATUS mandatory
                DESCRIPTION
                    "The time the parameter file was last written.  
                    Corresponds directly to a date and time in the 
                    section labeled 'Parameter files' in the MANAGER 
                    FILES display."
                ::= { paramFileEntry 4 }

            paramFileSize OBJECT-TYPE
                SYNTAX INTEGER
                ACCESS read-only
                STATUS mandatory
                DESCRIPTION
                    "The number of bytes stored in the param file.  
                    Corresponds directly to the value labeled 'bytes' in 
                    the section labeled 'Parameter files' in the MANAGER 
                    FILES display."
                ::= { paramFileEntry 5 }


            paramFileParameterVersion OBJECT-TYPE
                SYNTAX INTEGER
                ACCESS read-only
                STATUS mandatory
                DESCRIPTION
                    "The version number of the parameter data in the 
                    file.  Corresponds directly to the value labeled 
                    'ver' in the section labeled 'Parameter files' in 
                    the MANAGER FILES display."
                ::= { paramFileEntry 6 }


--
-- FILE: /users/sse/mibs/src/itouch/it-bridge-mib.mib
--

-- $Id: it-bridge-mib.mib,v 1.2 2001/06/25 19:28:47 sse Exp $


       bridgeDep       OBJECT IDENTIFIER ::= { iTouch 5 }
       xBridge         OBJECT IDENTIFIER ::= { iTouch 19 }

       -- ITouch Bridge subgroups

       xBridgeSystem   OBJECT IDENTIFIER ::= { xBridge 1 }
       --              2 is reserved for IF
       xBridgeProtocol OBJECT IDENTIFIER ::= { xBridge 3 }
       xBridgeFilter   OBJECT IDENTIFIER ::= { xBridge 4 }

       -- This is a MIB module for all iTouch systems that
       -- implement Ethernet bridging.

            -- Copyright 2000 iTouch Communications, Inc. All Rights Reserved.
            -- Reproduction of this document is authorized on
            -- condition that this copyright notice is included.
            -- This MIB document embodies iTouch Communications, Inc.'s 
            -- proprietary intellectual property.  iTouch Communications, Inc.
            -- retains all title and ownership in this MIB, including any
            -- revisions.
            --
            -- It is iTouch Communications, Inc.'s intent to encourage the
            -- widespread use of this MIB in connection with the management of
            -- iTouch Communications, Inc. products. iTouch Communications,
            -- Inc. grants vendors,end-users, and other interested parties a
            -- non-exclusive license to use this MIB in connection with the
            -- management of iTouch Communications, Inc. products.
            --
            -- This MIB document is supplied "AS IS," and iTouch 
            -- Communications, Inc. makes no warranty, either express or
            -- implied, as to the use operation, condition, or performance of
            -- the MIB.


       -- the Bridge System group

       -- Implementation of this group is mandatory for all iTouch
       -- bridges

       bridgeState OBJECT-TYPE
           SYNTAX INTEGER { disabled(1), enabled(2) }
           ACCESS read-write
           STATUS mandatory
           DESCRIPTION
               "Controls whether the bridge will perform 
               bridging."
           DEFVAL { enabled }
           ::= { xBridgeSystem 1 }

       bridgeEarlyLoopState OBJECT-TYPE
           SYNTAX INTEGER { disabled(1), enabled(2) }
           ACCESS read-write
           STATUS mandatory
           DESCRIPTION
               "Controls whether the bridge will implement the 
               early loop detection algorithm of restarting the 
               Spanning Tree Protocol when a packet is received 
               from a source on one interface when the source was 
               learned on a different interface."
           DEFVAL { disabled }
           ::= { xBridgeSystem 2 }

       bridgeEarlyLoopCount OBJECT-TYPE
           SYNTAX Counter
           ACCESS read-only
           STATUS mandatory
           DESCRIPTION
               "The number of times that an early loop was detected 
               while the early loop state was enabled."
           ::= { xBridgeSystem 3 }

       bridgeEarlyLoopAddress OBJECT-TYPE
           SYNTAX MacAddress
           ACCESS read-only
           STATUS mandatory
           DESCRIPTION
               "The last address to cause an early loop to be 
               detected while the early loop state was enabled."
           ::= { xBridgeSystem 4 }

       bridgeSpanningTreeState OBJECT-TYPE
           SYNTAX INTEGER { disabled(1), enabled(2) }
           ACCESS read-write
           STATUS mandatory
           DESCRIPTION
               "Controls whether the bridge will run the Spanning 
               Tree Protocol."
           DEFVAL { enabled }
           ::= { xBridgeSystem 5 }

       bridgeFilterDiscardTimeout OBJECT-TYPE
           SYNTAX INTEGER (0..65535)
           ACCESS read-write
           STATUS mandatory
           DESCRIPTION
               "The number of seconds before an inactive filter is 
               deleted. Learned filters become inactive when the 
               use timeout (dot1dTpAgingTime) has been exceeded."
           DEFVAL { 43200 }
           ::= { xBridgeSystem 6 }

       bridgeTopologyState OBJECT-TYPE
           SYNTAX INTEGER { stable(1), changing(2) }
           ACCESS read-only
           STATUS mandatory
           DESCRIPTION
               "Indicates whether the Spanning Tree Protocol's 
               topology is stable or changing."
           ::= { xBridgeSystem 7 }

       bridgeTopologyChangeAddr OBJECT-TYPE
           SYNTAX MacAddress
           ACCESS read-only
           STATUS mandatory
           DESCRIPTION
               "The ethernet address of the last bridge from which 
               a Topology Change Notification packet was 
               received."
           ::= { xBridgeSystem 8 }

       -- Bridge Protocol Filter Group

       bridgeProtocolFilterState OBJECT-TYPE
           SYNTAX INTEGER { disabled(1), enabled(2) }
           ACCESS read-write
           STATUS mandatory
           DESCRIPTION
               "Controls whether protocol filtering is active."
           DEFVAL { enabled }
           ::= { xBridgeProtocol 1 }

       bridgeProtocolDefaultPriority OBJECT-TYPE
           SYNTAX INTEGER { low(1), medium(3), high(5),
                            discard(101) }
           ACCESS read-write
           STATUS mandatory
           DESCRIPTION
               "Controls the default priority if no entry exists 
               for the protocol."
           DEFVAL { medium }
           ::= { xBridgeProtocol 2 }

       bridgeProtocolTable OBJECT-TYPE
           SYNTAX SEQUENCE OF BridgeProtocolEntry
           ACCESS not-accessible
           STATUS mandatory
           DESCRIPTION
               "A list of bridge protocol filters."
           ::= { xBridgeProtocol 3 }

       bridgeProtocolEntry OBJECT-TYPE
           SYNTAX BridgeProtocolEntry
           ACCESS not-accessible
           STATUS mandatory
           DESCRIPTION
               "Bridge protocol filter entry."
           INDEX { bridgeProtocolProtocol }
           ::= { bridgeProtocolTable 1 }

       BridgeProtocolEntry ::=
           SEQUENCE {
               bridgeProtocolProtocol
                   OCTET STRING,
               bridgeProtocolName
                   DisplayString,
               bridgeProtocolPriority
                   INTEGER,
               bridgeProtocolUses
                   Counter,
               bridgeProtocolStatus
                   INTEGER
           }

       bridgeProtocolProtocol OBJECT-TYPE
           SYNTAX OCTET STRING (SIZE (2)) 
           ACCESS read-only
           STATUS mandatory
           DESCRIPTION
               "The protocol type associated with the entry. The 
               value 65536 is for all 802.3 MAC frames."
           ::= { bridgeProtocolEntry 1 }

       bridgeProtocolName OBJECT-TYPE
           SYNTAX DisplayString (SIZE(0..24))
           ACCESS read-write
           STATUS mandatory
           DESCRIPTION
               "The name associated with the protocol."
           DEFVAL { "" }
           ::= { bridgeProtocolEntry 2 }

       bridgeProtocolPriority OBJECT-TYPE
           SYNTAX INTEGER { low(1), medium(3), high(5),
                            discard(101) }
           ACCESS read-write
           STATUS mandatory
           DESCRIPTION
               "The priority or action to take with the protocol."
           DEFVAL { medium }
           ::= { bridgeProtocolEntry 3 }

       bridgeProtocolUses OBJECT-TYPE
           SYNTAX Counter
           ACCESS read-only
           STATUS mandatory
           DESCRIPTION
               "The number of times the filter has been used."
           ::= { bridgeProtocolEntry 4 }

       bridgeProtocolStatus OBJECT-TYPE
           SYNTAX INTEGER { invalid(1), valid(2) }
           ACCESS read-write
           STATUS mandatory
           DESCRIPTION
               "The status of the protocol entry.  Set to 'invalid' 
               to remove the entry."
           DEFVAL { valid }
           ::= { bridgeProtocolEntry 5 }

       -- Bridge Filter Group

       bridgeFilterTable OBJECT-TYPE
           SYNTAX SEQUENCE OF BridgeFilterEntry
           ACCESS not-accessible
           STATUS mandatory
           DESCRIPTION
               "A list of bridge filters."
           ::= { xBridgeFilter 1 }

       bridgeFilterEntry OBJECT-TYPE
           SYNTAX BridgeFilterEntry
           ACCESS not-accessible
           STATUS mandatory
           DESCRIPTION
               "Bridge filter entry."
           INDEX { dot1dTpFdbAddress }
           ::= { bridgeFilterTable 1 }

       BridgeFilterEntry ::=
           SEQUENCE {
               bridgeFilterForwardSubPort
                   INTEGER,
               bridgeFilterUses
                   Counter,
               bridgeFilterAge
                   INTEGER
           }

       bridgeFilterForwardSubPort OBJECT-TYPE
           SYNTAX INTEGER
           ACCESS read-write
           STATUS mandatory
           DESCRIPTION
               "The unique identifier from which the address has 
               been seen within the port.  It is the DLCI for frame 
               relay or VC for X25."
           DEFVAL { 0 }
           ::= { bridgeFilterEntry 1 }

       bridgeFilterUses OBJECT-TYPE
           SYNTAX Counter
           ACCESS read-only
           STATUS mandatory
           DESCRIPTION
               "The number of times the filter has been used for 
               forwarding packets."
           ::= { bridgeFilterEntry 2 }

       bridgeFilterAge OBJECT-TYPE
           SYNTAX INTEGER
           ACCESS read-only
           STATUS mandatory
           DESCRIPTION
               "The number of seconds that a learned filter has 
               been active or inactive.  This value has no meaning 
               for non-learned filters."
           ::= { bridgeFilterEntry 3 }


       -- Bridge Filter Link table
       
       bridgeFilterLinkTable OBJECT-TYPE
           SYNTAX SEQUENCE OF BridgeFilterLinkEntry
           ACCESS not-accessible
           STATUS mandatory
           DESCRIPTION
               "Bridge filtering characteristics of all links."
           ::= { xBridgeFilter 2 }
       
       bridgeFilterLinkEntry OBJECT-TYPE
           SYNTAX BridgeFilterLinkEntry
           ACCESS not-accessible
           STATUS mandatory
           DESCRIPTION
               "Bridge filtering characteristics of a specific 
               link."
           INDEX { ifIndex }
           ::= { bridgeFilterLinkTable 1 }
       
       BridgeFilterLinkEntry ::=
           SEQUENCE {
               bridgeFilterLinkOverflowCam
                   INTEGER
           }

       bridgeFilterLinkOverflowCam OBJECT-TYPE
           SYNTAX INTEGER
           ACCESS read-write
           STATUS mandatory
           DESCRIPTION
               "Identifies the number of extra entries in a 
               hardware assist filter CAM that the user wants to 
               have available to cover CAM entry overflow 
               conditions.  If filtering hardware is present, this 
               field defaults to 400.  Otherwise, it is zero."
           ::= { bridgeFilterLinkEntry 1 }
       

--
-- FILE: /users/sse/mibs/src/itouch/it-chassis-mib.mib
--

-- $Id: it-chassis-mib.mib,v 1.3 2001/06/25 19:28:49 sse Exp $


       xChassis         OBJECT IDENTIFIER ::= { iTouch 16 }

       -- ITouch Character subgroups

       xChassisBasic    OBJECT IDENTIFIER ::= { xChassis 1 }
       xSegment         OBJECT IDENTIFIER ::= { xChassis 2 }
       xPort            OBJECT IDENTIFIER ::= { xChassis 3 }
       xController      OBJECT IDENTIFIER ::= { xChassis 4 }
       xInterface       OBJECT IDENTIFIER ::= { xChassis 5 }
       xSlotBootControl OBJECT IDENTIFIER ::= { xChassis 6 }
       xSlot            OBJECT IDENTIFIER ::= { xChassis 7 }
       xPowerSupply     OBJECT IDENTIFIER ::= { xChassis 8 }
       xFirmwareUpdate  OBJECT IDENTIFIER ::= { xChassis 9 }


            -- This is a MIB module for all iTouch Communications systems that
            -- are on the management bus of a Network 9000 chassis.

            -- Copyright 2000 iTouch Communications, Inc. All Rights Reserved.
            -- Reproduction of this document is authorized on
            -- condition that this copyright notice is included.
            -- This MIB document embodies iTouch Communications, Inc.'s 
            -- proprietary intellectual property.  iTouch Communications, Inc.
            -- retains all title and ownership in this MIB, including any
            -- revisions.
            --
            -- It is iTouch Communications, Inc.'s intent to encourage the
            -- widespread use of this MIB in connection with the management of
            -- iTouch Communications, Inc. products. iTouch Communications,
            -- Inc. grants vendors,end-users, and other interested parties a
            -- non-exclusive license to use this MIB in connection with the
            -- management of iTouch Communications, Inc. products.
            --
            -- This MIB document is supplied "AS IS," and iTouch 
            -- Communications, Inc. makes no warranty, either express or
            -- implied, as to the use operation, condition, or performance of
            -- the MIB.


       -- Textual Conventions

       NetworkType ::=
           INTEGER { unknown(1), other(2), ethernet(3),
                            tokenRing(4), fddi(5), wan(6),
                            ethernetRepeater(7),
                            tokenRingConcentrator(8),
                            fddiConcentrator(9),
							atm(10), isdn(11),
							switchplane(12), switchedEthernet(13) }
       -- This data type is used in the ITouch Chassis MIB
       -- to indicate the type of segment or port.

       SerialNumber ::=
           OCTET STRING (SIZE (0..6))
       -- This data type is used in the ITouch Chassis MIB
       -- to indicate a 6-byte serial number, stored high-
       -- order byte first.  A zero-length value indicates
       -- unknown.

       Letter ::=
           INTEGER { a(1), b(2), c(3), d(4), e(5), f(6), g(7),
                     h(8), i(9), j(10), k(11), l(12), m(13),
                     n(14), o(15), p(16), q(17), r(18), s(19),
                     t(20), u(21), v(22), w(23), x(24), y(25),
                     z(26) }
       -- This data type is used in the ITouch Chassis MIB
       -- to identify an object with a letter.


       -- the Chassis Basic group

       -- Implementation of this group is mandatory for all ITouch
       -- Network 9000 management bus systems

       -- Chassis type, revision, and status are found in the
       -- ITouch System MIB objects sysChassisType,
       -- sysChassisVersion, and sysChassisState

       basicBase802Address OBJECT-TYPE
           SYNTAX MacAddress
           ACCESS read-only
           STATUS mandatory
           DESCRIPTION
               "Base IEEE 802 global address for the chassis."
           ::= { xChassisBasic 1 }

       basicSlot OBJECT-TYPE
           SYNTAX INTEGER
           ACCESS read-only
           STATUS mandatory
           DESCRIPTION
               "Chassis slot number (slotIndex) of the system whose 
               agent is supplying this MIB."
           ::= { xChassisBasic 2 }

       basicSlotNumber OBJECT-TYPE
           SYNTAX INTEGER
           ACCESS read-only
           STATUS mandatory
           DESCRIPTION
               "Number of slots in the chassis."
           ::= { xChassisBasic 3 }

       basicNewBase802Address OBJECT-TYPE
           SYNTAX MacAddress
           ACCESS read-write
           STATUS mandatory
           DESCRIPTION
               "New base IEEE 802 global address for the chassis.  
               Must be set in conjunction with featType 
               'changeEthernetAddress' and featKey from the ITouch 
               System MIB."
           ::= { xChassisBasic 4 }


       -- the Chassis Segment group

       -- Implementation of this group is mandatory for all ITouch
       -- Network 9000 management bus systems

       -- the Segment table

       segmentTable OBJECT-TYPE
           SYNTAX SEQUENCE OF SegmentEntry
           ACCESS not-accessible
           STATUS mandatory
           DESCRIPTION
               "A list of segment entries, one for each segment of 
               each type on the chassis."
           ::= { xSegment 1 }

       segmentEntry OBJECT-TYPE
           SYNTAX SegmentEntry
           ACCESS not-accessible
           STATUS mandatory
           DESCRIPTION
               "Values for a chassis segment."
           INDEX { segmentType, segmentIndex }
           ::= { segmentTable 1 }

       SegmentEntry ::=
           SEQUENCE {
               segmentType
                   NetworkType,
               segmentIndex
                   Letter
           }

       segmentType OBJECT-TYPE
           SYNTAX NetworkType
           ACCESS read-only
           STATUS mandatory
           DESCRIPTION
               "The segment type."
           ::= { segmentEntry 1 }

       segmentIndex OBJECT-TYPE
           SYNTAX Letter
           ACCESS read-only
           STATUS mandatory
           DESCRIPTION
               "An index value that uniquely identifies a 
               segment."
           ::= { segmentEntry 2 }


       -- the Chassis Port group

       -- Implementation of this group is mandatory for all ITouch
       -- Network 9000 management bus systems.  It describes only
       -- the local system's own ports and is intended for network
       -- ports as opposed to terminal or printer ports.

       portIOCardType OBJECT-TYPE
           SYNTAX IOType
           ACCESS read-only
           STATUS mandatory
           DESCRIPTION
               "The hardware type of the I/O card in this slot."
           ::= { xPort 1 }

       portIOCardSerialNumber OBJECT-TYPE
           SYNTAX SerialNumber
           ACCESS read-only
           STATUS mandatory
           DESCRIPTION
               "The ITouch serial number of the I/O card in this 
               slot."
           ::= { xPort 2 }

       portIOCardOperStatus OBJECT-TYPE
           SYNTAX INTEGER { unknown(1), mismatch(2), good(3) }
           ACCESS read-only
           STATUS mandatory
           DESCRIPTION
               "Status of the I/O card relative to the function 
               card in this slot."
           ::= { xPort 3 }

       -- the Port table

       portTable OBJECT-TYPE
           SYNTAX SEQUENCE OF PortEntry
           ACCESS not-accessible
           STATUS mandatory
           DESCRIPTION
               "A list of port entries, one for each port of each 
               type on the slots I/O card."
           ::= { xPort 4 }

       portEntry OBJECT-TYPE
           SYNTAX PortEntry
           ACCESS not-accessible
           STATUS mandatory
           DESCRIPTION
               "Values for an I/O card port."
           INDEX { portType, portIndex }
           ::= { portTable 1 }

       PortEntry ::=
           SEQUENCE {
               portType
                   NetworkType,
               portIndex
                   INTEGER
           }

       portType OBJECT-TYPE
           SYNTAX NetworkType
           ACCESS read-only
           STATUS mandatory
           DESCRIPTION
               "The port type."
           ::= { portEntry 1 }

       portIndex OBJECT-TYPE
           SYNTAX INTEGER
           ACCESS read-only
           STATUS mandatory
           DESCRIPTION
               "An index value that uniquely identifies a port."
           ::= { portEntry 2 }


       -- the Chassis Controller group

       -- Implementation of this group is mandatory for all ITouch
       -- Network 9000 management bus systems.  It describes only
       -- the local system's own controllers.

       -- the Controller table

       controllerTable OBJECT-TYPE
           SYNTAX SEQUENCE OF ControllerEntry
           ACCESS not-accessible
           STATUS mandatory
           DESCRIPTION
               "A list of controller entries, one for each 
               controller of each type on the local system."
           ::= { xController 1 }

       controllerEntry OBJECT-TYPE
           SYNTAX ControllerEntry
           ACCESS not-accessible
           STATUS mandatory
           DESCRIPTION
               "Values for a controller."
           INDEX { controllerType, controllerIndex }
           ::= { controllerTable 1 }

       ControllerEntry ::=
           SEQUENCE {
               controllerType
                   NetworkType,
               controllerIndex
                   INTEGER,
               controllerNetwork
                   OBJECT IDENTIFIER
           }

       controllerType OBJECT-TYPE
           SYNTAX NetworkType
           ACCESS read-only
           STATUS mandatory
           DESCRIPTION
               "The controller type."
           ::= { controllerEntry 1 }

       controllerIndex OBJECT-TYPE
           SYNTAX INTEGER
           ACCESS read-only
           STATUS mandatory
           DESCRIPTION
               "An index value that uniquely identifies a 
               controller."
           ::= { controllerEntry 2 }

       controllerNetwork OBJECT-TYPE
           SYNTAX OBJECT IDENTIFIER
           ACCESS read-write
           STATUS mandatory
           DESCRIPTION
               "The instance identifier of the first object in the 
               conceptual row entry for the segment, port, or 
               controller this controller is to use, that is, 
               segmentType, portType or controllerType."
           ::= { controllerEntry 3 }


       -- the Chassis Interface group

       -- Implementation of this group is mandatory for all ITouch
       -- Network 9000 management bus systems.  It describes only
       -- the local system's own interfaces.

       -- the Interface table

       interfaceTable OBJECT-TYPE
           SYNTAX SEQUENCE OF InterfaceEntry
           ACCESS not-accessible
           STATUS mandatory
           DESCRIPTION
               "A list of interface entries, corresponding to the 
               MIB II Interface group.  These are directly 
               equivalent to hardware network controllers, and must 
               be the lowest numbered interfaces on the system."
           ::= { xInterface 1 }

       interfaceEntry OBJECT-TYPE
           SYNTAX InterfaceEntry
           ACCESS not-accessible
           STATUS mandatory
           DESCRIPTION
               "Values for an interface."
           INDEX { interfaceIndex }
           ::= { interfaceTable 1 }

       InterfaceEntry ::=
           SEQUENCE {
               interfaceIndex
                   INTEGER,
               interfaceNetwork
                   OBJECT IDENTIFIER
           }

       interfaceIndex OBJECT-TYPE
           SYNTAX INTEGER
           ACCESS read-only
           STATUS mandatory
           DESCRIPTION
               "An index value that uniquely identifies an 
               interface.  The interface identified by a particular 
               value of this index is the same interface as 
               identified by the same value of ifIndex."
           ::= { interfaceEntry 1 }

       interfaceNetwork OBJECT-TYPE
           SYNTAX OBJECT IDENTIFIER
           ACCESS read-write
           STATUS mandatory
           DESCRIPTION
               "The instance identifier of the first object in the 
               conceptual row entry for the segment, port, or 
               controller this interface is to use, that is, 
               segmentType, portType, or controllerType."
           ::= { interfaceEntry 2 }


       -- the Chassis Boot Control group

       -- Full implementation of this group is optional for ITouch
       -- Network 9000 management bus systems.  It is fully
       -- implemented on such systems that supply cross chassis
       -- management.  All systems must implement the instance
       -- corresponding to their own slot number.

       -- the Slot Boot Control table

       slotBootControlTable OBJECT-TYPE
           SYNTAX SEQUENCE OF SlotBootControlEntry
           ACCESS not-accessible
           STATUS mandatory
           DESCRIPTION
               "A list of slot boot control entries."
           ::= { xSlotBootControl 1 }

       slotBootControlEntry OBJECT-TYPE
           SYNTAX SlotBootControlEntry
           ACCESS not-accessible
           STATUS mandatory
           DESCRIPTION
               "Values for a chassis slot."
           INDEX { slotBootControlSlot, slotBootControlIndex }
           ::= { slotBootControlTable 1 }

       SlotBootControlEntry ::=
           SEQUENCE {
               slotBootControlSlot
                   INTEGER,
               slotBootControlIndex
                   INTEGER,
               slotBootControlStatus
                   INTEGER,
               slotBootControlController
                   OBJECT IDENTIFIER,
               slotBootControlNetwork
                   OBJECT IDENTIFIER,
               slotBootControlMopFile
                   DisplayString,
               slotBootControlInternetFile
                   DisplayString,
               slotBootControlInternetAddress
                   IpAddress,
               slotBootControlInternetServer
                   IpAddress,
               slotBootControlInternetGateway
                   IpAddress,
               slotBootControlInternetDelimiter
                   DisplayString
      }

       slotBootControlSlot OBJECT-TYPE
           SYNTAX INTEGER
           ACCESS read-only
           STATUS mandatory
           DESCRIPTION
               "An index value that uniquely identifies a slot, 
               defined the same as slotIndex."
           ::= { slotBootControlEntry 1 }

       slotBootControlIndex OBJECT-TYPE
           SYNTAX INTEGER
           ACCESS read-only
           STATUS mandatory
           DESCRIPTION
               "An index value that uniquely identifies a boot 
               control entry, from 1 to the number of entries for 
               the slot."
           ::= { slotBootControlEntry 2 }

       slotBootControlStatus OBJECT-TYPE
           SYNTAX INTEGER { disabled(1), enabled(2) }
           ACCESS read-write
           STATUS mandatory
           DESCRIPTION
               "The status of the entry.  Set to 'disabled' to 
               disable the entry."
           DEFVAL { enabled }
           ::= { slotBootControlEntry 3 }

       slotBootControlController OBJECT-TYPE
           SYNTAX OBJECT IDENTIFIER
           ACCESS read-write
           STATUS mandatory
           DESCRIPTION
               "The instance identifier of the first object in the 
               conceptual row entry for the controller this entry 
               selects for bootstrap operation, that is, 
               controllerType.  This entry must be compatible with 
               slotBootControlNetwork, including being of the same 
               network type.  The value 0.0 indicates default 
               action."
           DEFVAL { { 0 0 } }  -- 0.0
           ::= { slotBootControlEntry 4 }

       slotBootControlNetwork OBJECT-TYPE
           SYNTAX OBJECT IDENTIFIER
           ACCESS read-write
           STATUS mandatory
           DESCRIPTION
               "The instance identifier of the first object in the 
               conceptual row entry for the segment or port this                entry selects for bootstrap operation, that is, 
               segmentType or portType.  This entry must be 
               compatible with slotBootControlController, including 
               being of the same network type.  The value 0.0 
               indicates default action."
           DEFVAL { { 0 0 } }  -- 0.0
           ::= { slotBootControlEntry 5 }

       slotBootControlMopFile OBJECT-TYPE
           SYNTAX DisplayString (SIZE (0..15))
           ACCESS read-write
           STATUS mandatory
           DESCRIPTION
               "The software file name to request for down-line 
               load of the server via MOP or XMOP."
           DEFVAL { '00'h }  -- the null string
           ::= { slotBootControlEntry 6 }

       slotBootControlInternetFile OBJECT-TYPE
           SYNTAX DisplayString (SIZE (0..64))
           ACCESS read-write
           STATUS mandatory
           DESCRIPTION
               "The filename to request when loading an image via 
               TFTP."
           DEFVAL { '00'h }  -- the null string
           ::= { slotBootControlEntry 7 }

       slotBootControlInternetAddress OBJECT-TYPE
           SYNTAX IpAddress
           ACCESS read-write
           STATUS mandatory
           DESCRIPTION
               "The internet address of the system is to use for 
               itself when loading via TFTP.  The value 0.0.0.0 
               indicates default action."
           DEFVAL { 0 }
           ::= { slotBootControlEntry 8 }

       slotBootControlInternetServer OBJECT-TYPE
           SYNTAX IpAddress
           ACCESS read-write
           STATUS mandatory
           DESCRIPTION
               "The internet address of the server to use when 
               loading an image via TFTP.  The value 0.0.0.0 
               indicates default action."
           DEFVAL { 0 }
           ::= { slotBootControlEntry 9 }

       slotBootControlInternetGateway OBJECT-TYPE
           SYNTAX IpAddress
           ACCESS read-write
           STATUS mandatory
           DESCRIPTION
               "The internet address of the gateway to use when 
               loading an image via TFTP.  The value 0.0.0.0 
               indicates default action."
           DEFVAL { 0 }
           ::= { slotBootControlEntry 10 }

       slotBootControlInternetDelimiter OBJECT-TYPE
           SYNTAX DisplayString (SIZE (0..1))
           ACCESS read-write
           STATUS mandatory
           DESCRIPTION
               "The character separating the load file directory name  
               from the file name."
           DEFVAL { '00'h }  -- the null string
           ::= { slotBootControlEntry 11 }

       -- the Slot Boot Control Flag table

       -- Entries in this table are directly connected to a 
       -- particular slotBootControlIndex, and are created and 
       -- deleted together with that entry.

       -- By convention, this table contains flags in recurring
       -- groups of three operations for each protocol.  Adding
       -- a new protocol will add three new objects in the same
       -- order of operations.

       slotBootControlFlagTable OBJECT-TYPE
           SYNTAX SEQUENCE OF SlotBootControlFlagEntry
           ACCESS not-accessible
           STATUS mandatory
           DESCRIPTION
               "A list of slot boot control source flag entries."
           ::= { xSlotBootControl 2 }

       slotBootControlFlagEntry OBJECT-TYPE
           SYNTAX SlotBootControlFlagEntry
           ACCESS not-accessible
           STATUS mandatory
           DESCRIPTION
               "Values for a boot control flag."
           INDEX { slotBootControlSlot, slotBootControlIndex }
           ::= { slotBootControlFlagTable 1 }

       SlotBootControlFlagEntry ::=
           SEQUENCE {
               slotBootControlFlagLoadBootpTftp
                   INTEGER,
               slotBootControlFlagParamBootpTftp
                   INTEGER,
               slotBootControlFlagDumpBootpTftp
                   INTEGER,
               slotBootControlFlagLoadTftpDirect
                   INTEGER,
               slotBootControlFlagParamTftpDirect
                   INTEGER,
               slotBootControlFlagDumpTftpDirect
                   INTEGER,
               slotBootControlFlagLoadLocal
                   INTEGER,
               slotBootControlFlagParamLocal
                   INTEGER,
               slotBootControlFlagDumpLocal
                   INTEGER,
               slotBootControlFlagLoadMop
                   INTEGER,
               slotBootControlFlagParamMop
                   INTEGER,
               slotBootControlFlagDumpMop
                   INTEGER,
               slotBootControlFlagLoadXmop
                   INTEGER,
               slotBootControlFlagParamXmop
                   INTEGER,
               slotBootControlFlagDumpXmop
                   INTEGER,
               slotBootControlFlagLoadRarpTftp
                   INTEGER,
               slotBootControlFlagParamRarpTftp
                   INTEGER,
               slotBootControlFlagDumpRarpTftp
                   INTEGER
           }

       slotBootControlFlagLoadBootpTftp OBJECT-TYPE
           SYNTAX INTEGER { disabled(1), enabled(2) }
           ACCESS read-write
           STATUS mandatory
           DESCRIPTION
               "Control for performing load over BOOTP/TFTP."
           ::= { slotBootControlFlagEntry 1 }

       slotBootControlFlagParamBootpTftp OBJECT-TYPE
           SYNTAX INTEGER { disabled(1), enabled(2) }
           ACCESS read-write
           STATUS mandatory
           DESCRIPTION
               "Control for performing parameter load over 
               BOOTP/TFTP."
           ::= { slotBootControlFlagEntry 2 }

       slotBootControlFlagDumpBootpTftp OBJECT-TYPE
           SYNTAX INTEGER { disabled(1), enabled(2) }
           ACCESS read-write
           STATUS mandatory
           DESCRIPTION
               "Control for performing dump over BOOTP/TFTP."
           ::= { slotBootControlFlagEntry 3 }

       slotBootControlFlagLoadTftpDirect OBJECT-TYPE
           SYNTAX INTEGER { disabled(1), enabled(2) }
           ACCESS read-write
           STATUS mandatory
           DESCRIPTION
               "Control for performing load over direct TFTP."
           ::= { slotBootControlFlagEntry 4 }

       slotBootControlFlagParamTftpDirect OBJECT-TYPE
           SYNTAX INTEGER { disabled(1), enabled(2) }
           ACCESS read-write
           STATUS mandatory
           DESCRIPTION
               "Control for performing parameter load over direct 
               TFTP."
           ::= { slotBootControlFlagEntry 5 }

       slotBootControlFlagDumpTftpDirect OBJECT-TYPE
           SYNTAX INTEGER { disabled(1), enabled(2) }
           ACCESS read-write
           STATUS mandatory
           DESCRIPTION
               "Control for performing dump over direct TFTP."
           ::= { slotBootControlFlagEntry 6 }

       slotBootControlFlagLoadLocal OBJECT-TYPE
           SYNTAX INTEGER { disabled(1), enabled(2) }
           ACCESS read-write
           STATUS mandatory
           DESCRIPTION
               "Control for performing load from a local device."
           ::= { slotBootControlFlagEntry 7 }

       slotBootControlFlagParamLocal OBJECT-TYPE
           SYNTAX INTEGER { disabled(1), enabled(2) }
           ACCESS read-write
           STATUS mandatory
           DESCRIPTION
               "Control for performing parameter load from a local 
               device."
           ::= { slotBootControlFlagEntry 8 }

       slotBootControlFlagDumpLocal OBJECT-TYPE
           SYNTAX INTEGER { disabled(1), enabled(2) }
           ACCESS read-write
           STATUS mandatory
           DESCRIPTION
               "Control for performing dump from a local device."
           ::= { slotBootControlFlagEntry 9 }

       slotBootControlFlagLoadMop OBJECT-TYPE
           SYNTAX INTEGER { disabled(1), enabled(2) }
           ACCESS read-write
           STATUS mandatory
           DESCRIPTION
               "Control for performing load over Digital's MOP."
           ::= { slotBootControlFlagEntry 10 }

       slotBootControlFlagParamMop OBJECT-TYPE
           SYNTAX INTEGER { disabled(1), enabled(2) }
           ACCESS read-write
           STATUS mandatory
           DESCRIPTION
               "Control for performing parameter load over 
               Digital's MOP."
           ::= { slotBootControlFlagEntry 11 }

       slotBootControlFlagDumpMop OBJECT-TYPE
           SYNTAX INTEGER { disabled(1), enabled(2) }
           ACCESS read-write
           STATUS mandatory
           DESCRIPTION
               "Control for performing dump over Digital's MOP."
           ::= { slotBootControlFlagEntry 12 }

       slotBootControlFlagLoadXmop OBJECT-TYPE
           SYNTAX INTEGER { disabled(1), enabled(2) }
           ACCESS read-write
           STATUS mandatory
           DESCRIPTION
               "Control for performing load over ITouch extended 
               MOP."
           ::= { slotBootControlFlagEntry 13 }

       slotBootControlFlagParamXmop OBJECT-TYPE
           SYNTAX INTEGER { disabled(1), enabled(2) }
           ACCESS read-write
           STATUS mandatory
           DESCRIPTION
               "Control for performing parameter load over ITouch 
               extended MOP."
           ::= { slotBootControlFlagEntry 14 }

       slotBootControlFlagDumpXmop OBJECT-TYPE
           SYNTAX INTEGER { disabled(1), enabled(2) }
           ACCESS read-write
           STATUS mandatory
           DESCRIPTION
               "Control for performing dump over ITouch extended 
               MOP."
           ::= { slotBootControlFlagEntry 15 }

       slotBootControlFlagLoadRarpTftp OBJECT-TYPE
           SYNTAX INTEGER { disabled(1), enabled(2) }
           ACCESS read-write
           STATUS mandatory
           DESCRIPTION
               "Control for performing load over RARP/TFTP."
           ::= { slotBootControlFlagEntry 16 }

       slotBootControlFlagParamRarpTftp OBJECT-TYPE
           SYNTAX INTEGER { disabled(1), enabled(2) }
           ACCESS read-write
           STATUS mandatory
           DESCRIPTION
               "Control for performing parameter load over 
               RARP/TFTP."
           ::= { slotBootControlFlagEntry 17 }

       slotBootControlFlagDumpRarpTftp OBJECT-TYPE
           SYNTAX INTEGER { disabled(1), enabled(2) }
           ACCESS read-write
           STATUS mandatory
           DESCRIPTION
               "Control for performing dump over RARP/TFTP."
           ::= { slotBootControlFlagEntry 18 }


       slotBootControlStorageTable OBJECT-TYPE
           SYNTAX SEQUENCE OF SlotBootControlStorageEntry
           ACCESS not-accessible 
           STATUS mandatory 
           DESCRIPTION
               "A list of slot boot control Storage entries."
           ::= { xSlotBootControl 3 }
                
       slotBootControlStorageEntry OBJECT-TYPE
           SYNTAX SlotBootControlStorageEntry 
           ACCESS not-accessible
           STATUS mandatory 
           DESCRIPTION 
               "Values for a chassis slot."
           INDEX { slotBootControlStorageClientSlot,  slotBootControlStorageServerSlot}
           ::= { slotBootControlStorageTable 1 }
                
       SlotBootControlStorageEntry ::= 
           SEQUENCE {
               slotBootControlStorageClientSlot 
                   INTEGER, 
               slotBootControlStorageServerSlot
                   INTEGER, 
               slotBootControlStorageStatus
                   INTEGER,
               slotBootControlStorageFailures
                   Counter
              }

       slotBootControlStorageClientSlot OBJECT-TYPE
           SYNTAX INTEGER 
           ACCESS read-only 
           STATUS mandatory 
           DESCRIPTION 
               "An index value that uniquely identifies a slot,
               defined the same as slotIndex."
           ::= { slotBootControlStorageEntry 1 }
             
       slotBootControlStorageServerSlot OBJECT-TYPE
           SYNTAX INTEGER
           ACCESS read-only
           STATUS mandatory 
           DESCRIPTION    
               "An index value that uniquely identifies the slot in
               which the Storage record resides, with the same values
               as slotIndex."
           ::= { slotBootControlStorageEntry 2 } 
            
       slotBootControlStorageStatus OBJECT-TYPE
           SYNTAX INTEGER { present(1), failed(2), ok(3), notpresent(4) }
           ACCESS read-only
           STATUS mandatory
           DESCRIPTION 
               "The status of the entry."
           ::= { slotBootControlStorageEntry 3 } 

       slotBootControlStorageFailures OBJECT-TYPE
           SYNTAX Counter
           ACCESS read-only
           STATUS mandatory
           DESCRIPTION 
               "The number of times a read from or write to a given 
               Storage location failed"
           ::= { slotBootControlStorageEntry 4 } 


       -- the Chassis Slot group

       -- Implementation of this group is optional for ITouch
       -- Network 9000 management bus systems.  It is implemented
       -- on such systems that supply cross chassis management.

       -- the Slot table

       slotTable OBJECT-TYPE
           SYNTAX SEQUENCE OF SlotEntry
           ACCESS not-accessible
           STATUS mandatory
           DESCRIPTION
               "A list of slot entries."
           ::= { xSlot 1 }

       slotEntry OBJECT-TYPE
           SYNTAX SlotEntry
           ACCESS not-accessible
           STATUS mandatory
           DESCRIPTION
               "Values for a chassis slot."
           INDEX { slotIndex }
           ::= { slotTable 1 }

       SlotEntry ::=
           SEQUENCE {
               slotIndex
                   INTEGER,
               slotAdminAction
                   INTEGER,
               slotOperStatus
                   INTEGER,
               slotSecondsSinceReset
                   Gauge,
               slotHardwareType
                   HardwareType,
               slotHardwareSerialNumber
                   SerialNumber,
               slotHardwareRevision
                   INTEGER,
               slotIOCardType
                   IOType,
               slotIOCardSerialNumber
                   SerialNumber,
               slotIOCardOperStatus
                   INTEGER,
               slotBootstrapFirmwareRevision
                   INTEGER,
               slotElementalFirmwareRevision
                   INTEGER,
               slotMemorySize
                   INTEGER,
               slotLedNumber
                   Gauge,
               slotLedStatus
                   OCTET STRING,
               slotBase802Address
                   MacAddress,
               slotIpAddress
                   IpAddress,
               slotPlus5Status
                   INTEGER,
               slotPlus12Status
                   INTEGER,
               slotMinus12Status
                   INTEGER,
               slotPlus5Watts
                   Gauge,
               slotPlus12Watts
                   Gauge,
               slotMinus12Watts
                   Gauge,
               slotIOCardHardwareVersion
                   INTEGER,
               slotRestoreNVS
                   INTEGER,
               slotDefaultNVS
                   INTEGER
                   }

       slotIndex OBJECT-TYPE
           SYNTAX INTEGER
           ACCESS read-only
           STATUS mandatory
           DESCRIPTION
               "An index value that uniquely identifies a slot, in 
               the range 0 to basicSlotNumber, where the value 0 
               indicates the same slot as basicSlot.  As the 
               objects found at instance zero are duplicates, that 
               instance does not appear in responses a get-next, 
               that is, the lowest numbered slotIndex returned by 
               get-next is 1."
           ::= { slotEntry 1 }

       slotAdminAction OBJECT-TYPE
           SYNTAX INTEGER { ready(1), reset(2), resetHold(3) }
           ACCESS read-write
           STATUS mandatory
           DESCRIPTION
               "Control to cause reset of the system in a slot.  
               When read, the value is always 'ready'.  Setting to 
               'reset' or 'resetHold' causes a single attempt to 
               take that action, but does not ensure transition to 
               any particular value of slotOperStatus."
           ::= { slotEntry 2 }

       slotOperStatus OBJECT-TYPE
           SYNTAX INTEGER { loadRequested(1),
                            loading(2),
                            dumpRequested(3),
                            dumping(4),
                            paramRequested(5),
                            paramLoading(6),
                            running(7),
                            initializing(8),     -- ROM wait
                            attended(9),         -- in config menu
                            internal10(10),      -- read chas info
                            internal11(11),      -- read config
                            inhibited(12),       -- run inhibited
                            maxserverCard(13),
                            invalidConfigStorage(14), -- suspended
                            securityLockdown(15),

                            resetHold(64),       -- SCM, reset
                            selfTest(65),        -- SCM, diag.
                            notResponding(66),   -- SCM running
                            broken(67),          -- SCM, failed
                            unknown(68),         -- SCM
                            notApplicable(69)    -- SCM
                           }
           ACCESS read-only
           STATUS mandatory
           DESCRIPTION
               "Relative to the chassis, the current operating 
               status of the system in the slot."
           ::= { slotEntry 3 }

       slotSecondsSinceReset OBJECT-TYPE
           SYNTAX Gauge
           ACCESS read-only
           STATUS mandatory
           DESCRIPTION
               "The number of seconds since the system in the slot 
               was last reset by hardware or software."
           ::= { slotEntry 4 }

       slotHardwareType OBJECT-TYPE
           SYNTAX HardwareType
           ACCESS read-only
           STATUS mandatory
           DESCRIPTION
               "The type of hardware in the slot."
           ::= { slotEntry 5 }

       slotHardwareSerialNumber OBJECT-TYPE
           SYNTAX SerialNumber
           ACCESS read-only
           STATUS mandatory
           DESCRIPTION
               "The ITouch serial number of the function card 
               hardware in this slot."
           ::= { slotEntry 6 }

       slotHardwareRevision OBJECT-TYPE
           SYNTAX INTEGER
           ACCESS read-only
           STATUS mandatory
           DESCRIPTION
               "This revision level of the function card hardware 
               in the slot."
           ::= { slotEntry 7 }

       slotIOCardType OBJECT-TYPE
           SYNTAX IOType
           ACCESS read-only
           STATUS mandatory
           DESCRIPTION
               "The hardware type of the I/O card in this slot."
           ::= { slotEntry 8 }

       slotIOCardSerialNumber OBJECT-TYPE
           SYNTAX SerialNumber
           ACCESS read-only
           STATUS mandatory
           DESCRIPTION
               "The ITouch serial number of the I/O card in this 
               slot."
           ::= { slotEntry 9 }

       slotIOCardOperStatus OBJECT-TYPE
           SYNTAX INTEGER { unknown(1), mismatch(2), good(3),
                            notApplicable(4) }
           ACCESS read-only
           STATUS mandatory
           DESCRIPTION
               "Status of the I/O card relative to the function 
               card in this slot."
           ::= { slotEntry 10 }

       slotBootstrapFirmwareRevision OBJECT-TYPE
           SYNTAX INTEGER
           ACCESS read-only
           STATUS mandatory
           DESCRIPTION
               "The firmware revision level of the bootstrap ROM 
               installed in the system in the slot."
           ::= { slotEntry 11 }

       slotElementalFirmwareRevision OBJECT-TYPE
           SYNTAX INTEGER
           ACCESS read-only
           STATUS mandatory
           DESCRIPTION
               "The firmware revision level of the minimal function 
               ROM (management bus microprocessor) installed in the 
               system in the slot."
           ::= { slotEntry 12 }

       slotMemorySize OBJECT-TYPE
           SYNTAX INTEGER
           ACCESS read-only
           STATUS mandatory
           DESCRIPTION
               "The number of bytes of memory installed in the 
               system in the slot."
           ::= { slotEntry 13 }

       slotLedNumber OBJECT-TYPE
           SYNTAX Gauge
           ACCESS read-only
           STATUS mandatory
           DESCRIPTION
               "The number of LEDs on the system in the slot.  A 
               value of 0 indicates none, unknown, or status not 
               readable."
           ::= { slotEntry 14 }

       slotLedStatus OBJECT-TYPE
           SYNTAX OCTET STRING (SIZE (0..9))
           ACCESS read-only
           STATUS mandatory
           DESCRIPTION
               "The status of the LEDs displayed on the front and 
               back of the system in the slot.  The first bit is 
               the high-order bit of the first byte of the value, 
               proceeding to the low-order bit, then to then next 
               byte.  On the system hardware, the first LED is at 
               the top, left, front, proceeding left to right, top 
               to bottom, and front to back."
           ::= { slotEntry 15 }

       slotBase802Address OBJECT-TYPE
           SYNTAX MacAddress
           ACCESS read-only
           STATUS mandatory
           DESCRIPTION
               "Base IEEE 802 global address for the slot."
           ::= { slotEntry 16 }

       slotIpAddress OBJECT-TYPE
           SYNTAX IpAddress
           ACCESS read-only
           STATUS mandatory
           DESCRIPTION
               "An internet address to which the system in this 
               slot might respond.  May be one of many."
           ::= { slotEntry 17 }

       slotPlus5Status OBJECT-TYPE
           SYNTAX INTEGER { unknown(1), broken(2), good(3) }
           ACCESS read-only
           STATUS mandatory
           DESCRIPTION
               "Status of the +5 volt power to the slot."
           ::= { slotEntry 18 }

       slotPlus12Status OBJECT-TYPE
           SYNTAX INTEGER { unknown(1), broken(2), good(3) }
           ACCESS read-only
           STATUS mandatory
           DESCRIPTION
               "Status of the +12 volt power to the slot."
           ::= { slotEntry 19 }

       slotMinus12Status OBJECT-TYPE
           SYNTAX INTEGER { unknown(1), broken(2), good(3) }
           ACCESS read-only
           STATUS mandatory
           DESCRIPTION
               "Status of the -12 volt power to the slot."
           ::= { slotEntry 20 }

       slotPlus5Watts OBJECT-TYPE
           SYNTAX Gauge
           ACCESS read-only
           STATUS mandatory
           DESCRIPTION
               "Tenths of watts of +5 volt power currently drawn by 
               the slot."
           ::= { slotEntry 21 }

       slotPlus12Watts OBJECT-TYPE
           SYNTAX Gauge
           ACCESS read-only
           STATUS mandatory
           DESCRIPTION
               "Tenths of watts of +12 volt power currently drawn 
               by the slot."
           ::= { slotEntry 22 }

       slotMinus12Watts OBJECT-TYPE
           SYNTAX Gauge
           ACCESS read-only
           STATUS mandatory
           DESCRIPTION
               "Tenths of watts of -12 volt power currently drawn 
               by the slot."
           ::= { slotEntry 23 }

       slotIOCardHardwareVersion OBJECT-TYPE
           SYNTAX INTEGER
           ACCESS read-only
           STATUS mandatory
           DESCRIPTION
               "Version number of I/O card in the slot."
           ::= { slotEntry 24 }

       slotRestoreNVS OBJECT-TYPE
           SYNTAX INTEGER { ready(1), execute(2) }
           ACCESS read-write
           STATUS mandatory
           DESCRIPTION
               "Setting to 'execute' causes the non-volatile 
               parameter storage to be restored from an installed 
               memory card.  Setting to 'ready' has no effect."
           ::= { slotEntry 25 }

       slotDefaultNVS OBJECT-TYPE
           SYNTAX INTEGER { ready(1), execute(2) }
           ACCESS read-write
           STATUS mandatory
           DESCRIPTION
               "Setting to 'execute' causes non-volatile stored 
               parameters to be reset to factory defaults.  Setting 
               to 'ready' has no effect."
           ::= { slotEntry 26 }


       -- the Slot Bootstrap Status table

       slotBootTable OBJECT-TYPE
           SYNTAX SEQUENCE OF SlotBootEntry
           ACCESS not-accessible
           STATUS mandatory
           DESCRIPTION
               "A list of slot bootstrap status entries.  A given 
               slot has an entry in this table only when 
               slotOperStatus is one of:  loadRequested, loading, 
               dumpRequested, dumping, paramRequested, 
               paramLoading"
           ::= { xSlot 2 }

       slotBootEntry OBJECT-TYPE
           SYNTAX SlotBootEntry
           ACCESS not-accessible
           STATUS mandatory
           DESCRIPTION
               "Bootstrap status values for a chassis slot."
           INDEX { slotBootIndex }
           ::= { slotBootTable 1 }

       SlotBootEntry ::=
           SEQUENCE {
               slotBootIndex
                   INTEGER,
               slotBootIfIndex
                   INTEGER,
               slotBootNetwork
                   OBJECT IDENTIFIER,
               slotBootProtocol
                   INTEGER,
               slotBoot802Address
                   MacAddress,
               slotBootAddressType
                   AddressType,
               slotBootAddress
                   OCTET STRING,
               slotBootServerAddressType
                   AddressType,
               slotBootServerAddress
                   OCTET STRING,
               slotBootGatewayAddress
                   IpAddress,
               slotBootFileName
                   DisplayString,
               slotBootBlockNumber
                   Gauge,
               slotBootCrashCode
                   OCTET STRING
           }

       slotBootIndex OBJECT-TYPE
           SYNTAX INTEGER
           ACCESS read-only
           STATUS mandatory
           DESCRIPTION
               "An index value that uniquely identifies a slot, 
               defined the same as slotIndex."
           ::= { slotBootEntry 1 }

       slotBootIfIndex OBJECT-TYPE
           SYNTAX INTEGER
           ACCESS read-only
           STATUS mandatory
           DESCRIPTION
               "An index value that uniquely identifies the 
               interface in use for bootstrap functions.  The 
               interface identified by a particular value of this 
               index is the same interface as identified by the 
               same value of ifIndex."
           ::= { slotBootEntry 2 }

       slotBootNetwork OBJECT-TYPE
           SYNTAX OBJECT IDENTIFIER
           ACCESS read-only
           STATUS mandatory
           DESCRIPTION
               "The instance identifier of the first object in the 
               conceptual row entry for the segment or port this 
               interface is using, that is, segmentType or 
               portType."
           ::= { slotBootEntry 3 }

       slotBootProtocol OBJECT-TYPE
           SYNTAX INTEGER { other(1), unknown(2), mop(3), xmop(4),
                            rarpTftp(5), bootpTftp(6), tftp(7),
                            local(8), managementBus(9) }
           ACCESS read-only
           STATUS mandatory
           DESCRIPTION
               "The protocol in use for bootstrap operation."
           ::= { slotBootEntry 4 }

       slotBoot802Address OBJECT-TYPE
           SYNTAX MacAddress
           ACCESS read-only
           STATUS mandatory
           DESCRIPTION
               "IEEE 802 global address in use for bootstrap 
               operation."
           ::= { slotBootEntry 5 }

       slotBootAddressType OBJECT-TYPE
           SYNTAX AddressType
           ACCESS read-only
           STATUS mandatory
           DESCRIPTION
               "The type of network address contained in 
               slotBootAddress."
           ::= { slotBootEntry 6 }

       slotBootAddress OBJECT-TYPE
           SYNTAX OCTET STRING (SIZE (0..6))
           ACCESS read-only
           STATUS mandatory
           DESCRIPTION
               "The network address the system in the slot is using 
               to identify itself for bootstrap operation."
           ::= { slotBootEntry 7 }

       slotBootServerAddressType OBJECT-TYPE
           SYNTAX AddressType
           ACCESS read-only
           STATUS mandatory
           DESCRIPTION
               "The type of network address contained in 
               slotBootServerAddress."
           ::= { slotBootEntry 8 }

       slotBootServerAddress OBJECT-TYPE
           SYNTAX OCTET STRING (SIZE (0..6))
           ACCESS read-only
           STATUS mandatory
           DESCRIPTION
               "The network address of the system supplying 
               bootstrap services to the system in the slot."
           ::= { slotBootEntry 9 }

       slotBootGatewayAddress OBJECT-TYPE
           SYNTAX IpAddress
           ACCESS read-only
           STATUS mandatory
           DESCRIPTION
               "The internet address of the router in use for 
               bootstrap operation."
           ::= { slotBootEntry 10 }

       slotBootFileName OBJECT-TYPE
           SYNTAX DisplayString (SIZE (0..64))
           ACCESS read-only
           STATUS mandatory
           DESCRIPTION
               "The full name of the file in use for bootstrap 
               operation."
           ::= { slotBootEntry 11 }

       slotBootBlockNumber OBJECT-TYPE
           SYNTAX Gauge
           ACCESS read-only
           STATUS mandatory
           DESCRIPTION
               "The current block number being transferred for 
               bootstrap operation, zero if unknown or not 
               applicable."
           ::= { slotBootEntry 12 }

       slotBootCrashCode OBJECT-TYPE
           SYNTAX OCTET STRING (SIZE (0..4))
           ACCESS read-only
           STATUS mandatory
           DESCRIPTION
               "If slotOperStatus is dumpRequested or dumping, a 
               code number to identify the crash reason; otherwise 
               zero length."
           ::= { slotBootEntry 13 }


       -- the Slot Controller table

       slotControllerTable OBJECT-TYPE
           SYNTAX SEQUENCE OF SlotControllerEntry
           ACCESS not-accessible
           STATUS mandatory
           DESCRIPTION
               "A list of controller entries, one for each 
               controller of each type in each slot."
           ::= { xSlot 3 }

       slotControllerEntry OBJECT-TYPE
           SYNTAX SlotControllerEntry
           ACCESS not-accessible
           STATUS mandatory
           DESCRIPTION
               "Values for a controller."
           INDEX { slotControllerType,
                   slotControllerIndex }
           ::= { slotControllerTable 1 }

       SlotControllerEntry ::=
           SEQUENCE {
               slotControllerType
                   NetworkType,
               slotControllerIndex
                   INTEGER,
               slotControllerNetwork
                   OBJECT IDENTIFIER
           }

       slotControllerType OBJECT-TYPE
           SYNTAX NetworkType
           ACCESS read-only
           STATUS mandatory
           DESCRIPTION
               "The controller type."
           ::= { slotControllerEntry 1 }

       slotControllerIndex OBJECT-TYPE
           SYNTAX INTEGER
           ACCESS read-only
           STATUS mandatory
           DESCRIPTION
               "An index value that uniquely identifies a 
               controller."
           ::= { slotControllerEntry 2 }

       slotControllerNetwork OBJECT-TYPE
           SYNTAX OBJECT IDENTIFIER
           ACCESS read-only
           STATUS mandatory
           DESCRIPTION
               "The instance identifier of the first object in the 
               conceptual row entry for the segment or port this 
               controller is to use, that is, segmentType or 
               portType."
           ::= { slotControllerEntry 3 }


       -- the Chassis Power Supply group

       -- Implementation of this group is optional for ITouch
       -- Network 9000 management bus systems.  It is implemented
       -- on such systems that supply full chassis management.

       -- the Power Supply table

       powerSupplyTable OBJECT-TYPE
           SYNTAX SEQUENCE OF PowerSupplyEntry
           ACCESS not-accessible
           STATUS mandatory
           DESCRIPTION
               "A list of power supply entries."
           ::= { xPowerSupply 1 }

       powerSupplyEntry OBJECT-TYPE
           SYNTAX PowerSupplyEntry
           ACCESS not-accessible
           STATUS mandatory
           DESCRIPTION
               "Values for a chassis power supply."
           INDEX { powerSupplyIndex }
           ::= { powerSupplyTable 1 }

       PowerSupplyEntry ::=
           SEQUENCE {
               powerSupplyIndex
                   INTEGER,
               powerSupplyAdminAction
                   INTEGER,
               powerSupplyFirmwareVersion
                   INTEGER,
               powerSupplyRedundancyStatus
                   INTEGER,
               powerSupplyPlus5Status
                   INTEGER,
               powerSupplyPlus12Status
                   INTEGER,
               powerSupplyMinus12Status
                   INTEGER,
               powerSupplyThermalWarningStatus
                   INTEGER,
               powerSupplyThermalShutdownStatus
                   INTEGER,
               powerSupplyFanStatus
                   INTEGER,
               powerSupplyHardwareInhibitStatus
                   INTEGER,
               powerSupplyPlus5History
                   INTEGER,
               powerSupplyPlus12History
                   INTEGER,
               powerSupplyMinus12History
                   INTEGER,
               powerSupplyThermalWarningHistory
                   INTEGER,
               powerSupplyThermalShutdownHistory
                   INTEGER,
               powerSupplyFanHistory
                   INTEGER,
               powerSupplyHardwareInhibitHistory
                   INTEGER,
               powerSupplyPlus5Volts
                   Gauge,
               powerSupplyPlus12Volts
                   Gauge,
               powerSupplyMinus12Volts
                   Gauge,
               powerSupplyWatts
                   Gauge,
               powerSupplyWattsMax
                   Gauge,
               powerSupplyChassisWatts
                   Gauge,
               powerSupplyChassisWattsMax
                   Gauge,
               powerSupplyHardwareType
                   INTEGER
           }

       powerSupplyIndex OBJECT-TYPE
           SYNTAX INTEGER
           ACCESS read-only
           STATUS mandatory
           DESCRIPTION
               "An index value that uniquely identifies a power 
               supply, in the range 1 to the number of power supply 
               slots in the chassis."
           ::= { powerSupplyEntry 1 }

       powerSupplyAdminAction OBJECT-TYPE
           SYNTAX INTEGER { ready(1), reset(2), resetHold(3) }
           ACCESS read-write
           STATUS mandatory
           DESCRIPTION
               "Control to cause reset of the power supply.  When 
               read, the value is always 'ready'.  Setting to 
               'reset' or 'resetHold' causes a single attempt to 
               take that action, but does not ensure transition to 
               any particular value of 
               powerSupplyRedundancyStatus."
           ::= { powerSupplyEntry 2 }

       powerSupplyFirmwareVersion OBJECT-TYPE
           SYNTAX INTEGER
           ACCESS read-only
           STATUS mandatory
           DESCRIPTION
               "Version number of power supply firmware."
           ::= { powerSupplyEntry 3 }

       powerSupplyRedundancyStatus OBJECT-TYPE
           SYNTAX INTEGER { unknown(1), disabled(2),
                            redundant(3), engaged(4) }
           ACCESS read-only
           STATUS mandatory
           DESCRIPTION
               "The current redundancy status of the power 
               supply."
           ::= { powerSupplyEntry 4 }

       powerSupplyPlus5Status OBJECT-TYPE
           SYNTAX INTEGER { unknown(1), good(2), broken(3) }
           ACCESS read-only
           STATUS mandatory
           DESCRIPTION
               "Status of the +5 volt power from the power 
               supply."
           ::= { powerSupplyEntry 5 }

       powerSupplyPlus12Status OBJECT-TYPE
           SYNTAX INTEGER { unknown(1), good(2), broken(3) }
           ACCESS read-only
           STATUS mandatory
           DESCRIPTION
               "Status of the +12 volt power from the power 
               supply."
           ::= { powerSupplyEntry 6 }

       powerSupplyMinus12Status OBJECT-TYPE
           SYNTAX INTEGER { unknown(1), good(2), broken(3) }
           ACCESS read-only
           STATUS mandatory
           DESCRIPTION
               "Status of the -12 volt power from the power 
               supply."
           ::= { powerSupplyEntry 7 }

       powerSupplyThermalWarningStatus OBJECT-TYPE
           SYNTAX INTEGER { unknown(1), good(2), broken(3) }
           ACCESS read-only
           STATUS mandatory
           DESCRIPTION
               "The current thermal warning status of the power 
               supply."
           ::= { powerSupplyEntry 8 }

       powerSupplyThermalShutdownStatus OBJECT-TYPE
           SYNTAX INTEGER { unknown(1), good(2), broken(3) }
           ACCESS read-only
           STATUS mandatory
           DESCRIPTION
               "The current thermal shutdown status of the power 
               supply."
           ::= { powerSupplyEntry 9 }

       powerSupplyFanStatus OBJECT-TYPE
           SYNTAX INTEGER { unknown(1), good(2), broken(3) }
           ACCESS read-only
           STATUS mandatory
           DESCRIPTION
               "The current status of the power supply's fan."
           ::= { powerSupplyEntry 10 }

       powerSupplyHardwareInhibitStatus OBJECT-TYPE
           SYNTAX INTEGER { unknown(1), good(2), broken(3) }
           ACCESS read-only
           STATUS mandatory
           DESCRIPTION
               "The current status of the power supply's hardware 
               inhibit."
           ::= { powerSupplyEntry 11 }

       powerSupplyPlus5History OBJECT-TYPE
           SYNTAX INTEGER { unknown(1), good(2), broken(3) }
           ACCESS read-only
           STATUS mandatory
           DESCRIPTION
               "History of the +5 volt power from the power 
               supply."
           ::= { powerSupplyEntry 12 }

       powerSupplyPlus12History OBJECT-TYPE
           SYNTAX INTEGER { unknown(1), good(2), broken(3) }
           ACCESS read-only
           STATUS mandatory
           DESCRIPTION
               "History of the +12 volt power from the power 
               supply."
           ::= { powerSupplyEntry 13 }

       powerSupplyMinus12History OBJECT-TYPE
           SYNTAX INTEGER { unknown(1), good(2), broken(3) }
           ACCESS read-only
           STATUS mandatory
           DESCRIPTION
               "History of the -12 volt power from the power 
               supply."
           ::= { powerSupplyEntry 14 }

       powerSupplyThermalWarningHistory OBJECT-TYPE
           SYNTAX INTEGER { unknown(1), good(2), broken(3) }
           ACCESS read-only
           STATUS mandatory
           DESCRIPTION
               "The thermal warning history of the power supply."
           ::= { powerSupplyEntry 15 }

       powerSupplyThermalShutdownHistory OBJECT-TYPE
           SYNTAX INTEGER { unknown(1), good(2), broken(3) }
           ACCESS read-only
           STATUS mandatory
           DESCRIPTION
               "The thermal shutdown history of the power supply."
           ::= { powerSupplyEntry 16 }

       powerSupplyFanHistory OBJECT-TYPE
           SYNTAX INTEGER { unknown(1), good(2), broken(3) }
           ACCESS read-only
           STATUS mandatory
           DESCRIPTION
               "The status history of the power supply's fan."
           ::= { powerSupplyEntry 17 }

       powerSupplyHardwareInhibitHistory OBJECT-TYPE
           SYNTAX INTEGER { unknown(1), good(2), broken(3) }
           ACCESS read-only
           STATUS mandatory
           DESCRIPTION
               "The status history of the power supply's hardware 
               inhibit."
           ::= { powerSupplyEntry 18 }

       powerSupplyPlus5Volts OBJECT-TYPE
           SYNTAX Gauge
           ACCESS read-only
           STATUS mandatory
           DESCRIPTION
               "In hundredths, volts of +5 volt power currently 
               provided by the power supply.  A value of 0 
               indicates unknown."
           ::= { powerSupplyEntry 19 }

       powerSupplyPlus12Volts OBJECT-TYPE
           SYNTAX Gauge
           ACCESS read-only
           STATUS mandatory
           DESCRIPTION
               "In hundredths, volts of +12 volt power currently 
               provided by the power supply.  A value of 0 
               indicates unknown."
           ::= { powerSupplyEntry 20 }

       powerSupplyMinus12Volts OBJECT-TYPE
           SYNTAX Gauge
           ACCESS read-only
           STATUS mandatory
           DESCRIPTION
               "In hundredths, volts of -12 volt power currently 
               provided by the power supply.  A value of 0 
               indicates unknown."
           ::= { powerSupplyEntry 21 }

       powerSupplyWatts OBJECT-TYPE
           SYNTAX Gauge
           ACCESS read-only
           STATUS mandatory
           DESCRIPTION
               "Watts of power currently drawn from this power 
               supply.  A value of 0 indicates unknown."
           ::= { powerSupplyEntry 22 }

       powerSupplyWattsMax OBJECT-TYPE
           SYNTAX Gauge
           ACCESS read-only
           STATUS mandatory
           DESCRIPTION
               "Maximum watts of power available from this power 
               supply.  A value of 0 indicates unknown."
           ::= { powerSupplyEntry 23 }

       powerSupplyChassisWatts OBJECT-TYPE
           SYNTAX Gauge
           ACCESS read-only
           STATUS mandatory
           DESCRIPTION
               "Total watts of power currently drawn by the entire 
               chassis.  A value of 0 indicates unknown."
           ::= { powerSupplyEntry 24 }

       powerSupplyChassisWattsMax OBJECT-TYPE
           SYNTAX Gauge
           ACCESS read-only
           STATUS mandatory
           DESCRIPTION
               "Total maximum watts of power available from all the 
               power supplies in the chassis.  A value of 0 
               indicates unknown."
           ::= { powerSupplyEntry 25 }

       powerSupplyHardwareType OBJECT-TYPE
           SYNTAX INTEGER { other(1), ps130(2), bb190(3) }
           ACCESS read-only
           STATUS mandatory
           DESCRIPTION
               "The type of power supply."
           ::= { powerSupplyEntry 26 }

       -- The firmware update group

       -- A table which contains information and status
       -- concerning the writing of firmware to a target
       -- I/O card.

       -- The firmware update table

       firmwareUpdateTable OBJECT-TYPE
           SYNTAX SEQUENCE OF FirmwareUpdateEntry
           ACCESS not-accessible
           STATUS mandatory
           DESCRIPTION
               "Table of descriptive and status information concerning
               the writing of firmware to a target I/O card."
           ::= { xFirmwareUpdate 1 }

       firmwareUpdateEntry OBJECT-TYPE
           SYNTAX FirmwareUpdateEntry
           ACCESS not-accessible
           STATUS mandatory
           DESCRIPTION
               "An entry in the table concerning the writing of
               firmware to a target I/O card."
           INDEX { firmwareUpdateSlotIndex }
           ::= { firmwareUpdateTable 1 }

       FirmwareUpdateEntry  ::=
           SEQUENCE {
               firmwareUpdateSlotIndex
                   INTEGER,
               firmwareUpdateDefaultFileName
                   DisplayString,
               firmwareUpdateFileName
                   DisplayString,
               firmwareUpdateStatus
                   INTEGER,
               firmwareUpdateState
                   INTEGER,
               firmwareUpdateCompletionStatus
                   INTEGER,
			   firmwareUpdateMethod
                   INTEGER
           }

       firmwareUpdateSlotIndex  OBJECT-TYPE
           SYNTAX INTEGER
           ACCESS read-only
           STATUS mandatory
           DESCRIPTION
               "This variable identifies the slot to which is to
               be the target of the firmware update."
           ::= { firmwareUpdateEntry 1 }

       firmwareUpdateDefaultFileName  OBJECT-TYPE
           SYNTAX DisplayString
           ACCESS read-only
           STATUS mandatory
           DESCRIPTION
               "This variable when read will obtain the default
               file name from the target."
           ::= { firmwareUpdateEntry 2 }

       firmwareUpdateFileName  OBJECT-TYPE
           SYNTAX DisplayString
           ACCESS read-write
           STATUS mandatory
           DESCRIPTION
               "This variable contains the name of the file to be
               read from the flash memory card and written to the
               target."
           ::= { firmwareUpdateEntry 3 }

       firmwareUpdateStatus  OBJECT-TYPE
           SYNTAX INTEGER { ready(1), execute(2) }
           ACCESS read-write
           STATUS mandatory
           DESCRIPTION
               "This variable is used to start the update process.
               The agent always 'ready' for this value.  Setting this
               value to 'execute' causes the agent to write the file
               specified by firmwareUpdateFileName to be written to
               the taget.  Setting this value to 'execute' when
               firmwareUpdateFileName has not been written or when
               firmwareUpdateState is 'writing' causes bad value to be
               returned."
           ::= { firmwareUpdateEntry 4 }

       firmwareUpdateState  OBJECT-TYPE
           SYNTAX INTEGER { idle(1), writing(2) }
           ACCESS read-only
           STATUS mandatory
           DESCRIPTION
               "This variable indicates the current state of firmware
               update, 'idle' indicates that firmware update may be
               initiated, and 'writing' indicates that an update is in
               process."
           ::= { firmwareUpdateEntry 5 }

       firmwareUpdateCompletionStatus  OBJECT-TYPE
           SYNTAX INTEGER { none(1),
                            success(2),
                            noTarget(3),
                            busError(4),
                            badFileName(5),
                            targetError(6),
                            timeout(7)
                          }
           ACCESS read-only
           STATUS mandatory
           DESCRIPTION
               "This variable indicates the completion status of the
               the last firmware update attempt.  'none' indicates
               that no firmware update has yet been attempted."
           ::= { firmwareUpdateEntry 6 }

       firmwareUpdateMethod  OBJECT-TYPE
           SYNTAX INTEGER { card(1), local(2) }
           ACCESS read-write
           STATUS mandatory
           DESCRIPTION
               "This variable indicates the method of update of the
               firmware update attempt. "
           ::= { firmwareUpdateEntry 7 }


--
-- FILE: /users/sse/mibs/src/itouch/it-concentrator-mib.mib
--

-- $Id: it-concentrator-mib.mib,v 1.1 2000/07/25 14:36:26 sse Exp $


            xConcentrator      OBJECT IDENTIFIER ::= { iTouch 25 }


            -- This is a MIB module for all iTouch Ethernet repeaters.

            -- Copyright 2000 iTouch Communications, Inc. All Rights Reserved.
            -- Reproduction of this document is authorized on
            -- condition that this copyright notice is included.
            -- This MIB document embodies iTouch Communications, Inc.'s 
            -- proprietary intellectual property.  iTouch Communications, Inc.
            -- retains all title and ownership in this MIB, including any
            -- revisions.
            --
            -- It is iTouch Communications, Inc.'s intent to encourage the
            -- widespread use of this MIB in connection with the management of
            -- iTouch Communications, Inc. products. iTouch Communications,
            -- Inc. grants vendors,end-users, and other interested parties a
            -- non-exclusive license to use this MIB in connection with the
            -- management of iTouch Communications, Inc. products.
            --
            -- This MIB document is supplied "AS IS," and iTouch 
            -- Communications, Inc. makes no warranty, either express or
            -- implied, as to the use operation, condition, or performance of
            -- the MIB.



            -- The basic information group contains information and
            -- status concerning the chassis:
    
            concentratorMode OBJECT-TYPE
                SYNTAX INTEGER { twoRing(1), fourRing(2) }
                ACCESS read-write
                STATUS mandatory
                DESCRIPTION
                    "This variable controls the ring mode of the
                    chassis."
                ::= { xConcentrator 1 }
    
            concentratorManagement OBJECT-TYPE
                SYNTAX INTEGER { disabled(1), enabled(2) }
                ACCESS read-write
                STATUS mandatory
                DESCRIPTION
                    "This variable controls the ability to manage token
                    ring concentrators."
                ::= { xConcentrator 2 }
    
            concentratorBuildTopology OBJECT-TYPE
                SYNTAX INTEGER { ready(1), execute(2) }
                ACCESS read-write
                STATUS mandatory
                DESCRIPTION
                    "This variable causes the chassis token ring
                    topology database to be constructed."
                ::= { xConcentrator 3 }
    
            concentratorTopologyLastBuild OBJECT-TYPE
                SYNTAX TimeTicks
                ACCESS read-only
                STATUS mandatory
                DESCRIPTION
                    "This variable contains the value of sysUpTime at
                    the time the chassis token ring topology database
                    was last constructed."
                ::= { xConcentrator 4 }
    
            concentratorChassisRingDefaults OBJECT-TYPE
                SYNTAX INTEGER { ready(1), execute(2) }
                ACCESS read-write
                STATUS mandatory
                DESCRIPTION
                    "This variable causes the chassis ring area of NVS
                    to be set to defaults."
                ::= { xConcentrator 5 }
    

            -- The slot group contains information and status concerning
            -- the individual slots of the chassis:
    
            concentratorSlotTable OBJECT-TYPE
                SYNTAX SEQUENCE OF ConcentratorSlotEntry
                ACCESS not-accessible
                STATUS mandatory
                DESCRIPTION
                    "Table of descriptive and status information about a
                    Token Ring Concentrator."
                ::= { xConcentrator 6 }
    
            concentratorSlotEntry OBJECT-TYPE
                SYNTAX ConcentratorSlotEntry
                ACCESS not-accessible
                STATUS mandatory
                DESCRIPTION
                    "An entry in the table containing information about
                    a specific concentrator."
                INDEX { concentratorSlotIndex }
                ::= { concentratorSlotTable 1 }
    
            ConcentratorSlotEntry ::=
                SEQUENCE {
                    concentratorSlotIndex
                         INTEGER,
                    concentratorSlotIOType
                         IOType,
                    concentratorSlotIOFirmwareVersion
                         INTEGER,
                    concentratorSlotIOOperStatus
                         INTEGER,
                    concentratorSlotUptime
                         TimeTicks,
                    concentratorSlotNumPorts
                         INTEGER
                }
    
            concentratorSlotIndex OBJECT-TYPE
                SYNTAX INTEGER
                ACCESS read-only
                STATUS mandatory
                DESCRIPTION
                    "This variable identifies the slot of the chassis."
                ::= { concentratorSlotEntry 1 }
    
            concentratorSlotIOType OBJECT-TYPE
                SYNTAX IOType
                ACCESS read-only
                STATUS mandatory
                DESCRIPTION
                    "This variable represents the type of the I/O card."
                ::= { concentratorSlotEntry 2 }
    
            concentratorSlotIOFirmwareVersion OBJECT-TYPE
                SYNTAX INTEGER
                ACCESS read-only
                STATUS mandatory
                DESCRIPTION
                    "This variable represents the revision level of the
                    firmware on the I/O card."
                ::= { concentratorSlotEntry 3 }
    
            concentratorSlotIOOperStatus OBJECT-TYPE
                SYNTAX INTEGER { loadRequested(1),
                  loading(2),
                  dumpRequested(3),
                  dumping(4),
                  paramRequested(5),
                  paramLoading(6),
                  running(7),
                  initializing(8),
                  attended(9),
                  internal10(10),
                  internal11(11),
                  inhibited(12),
                  maxserverCard(13),
                  invalidConfigStorage(14),
                  securityLockdown(15) }
                ACCESS read-only
                STATUS mandatory
                DESCRIPTION
                    "This variable represents the current operating
                    status of the I/O card."
                ::= { concentratorSlotEntry 4 }
    
            concentratorSlotUptime OBJECT-TYPE
                SYNTAX TimeTicks
                ACCESS read-only
                STATUS mandatory
                DESCRIPTION
                    "This variable contains the value of sysUpTime at
                    the time the concentrator was last reset."
                ::= { concentratorSlotEntry 5 }
    
            concentratorSlotNumPorts OBJECT-TYPE
                SYNTAX INTEGER
                ACCESS read-only
                STATUS mandatory
                DESCRIPTION
                    "This variable represents the number of Token Ring
                    ports supported by the concentrator."
                ::= { concentratorSlotEntry 6 }
    
            -- The slot ring group contains information and status
            -- concerning the individual rings of a slot:
    
            concentratorSlotRingTable OBJECT-TYPE
                SYNTAX SEQUENCE OF ConcentratorSlotRingEntry
                ACCESS not-accessible
                STATUS mandatory
                DESCRIPTION
                    "Table of descriptive and status information about
                    the rings of a controller."
                ::= { xConcentrator 7 }
    
            concentratorSlotRingEntry OBJECT-TYPE
                SYNTAX ConcentratorSlotRingEntry
                ACCESS not-accessible
                STATUS mandatory
                DESCRIPTION
                    "An entry in the table containing information about
                    a specific ring."
                INDEX { concentratorSlotIndex,
                 concentratorSlotRingIndex }
                ::= { concentratorSlotRingTable 1 }
    
            ConcentratorSlotRingEntry ::=
                SEQUENCE {
                    concentratorSlotSlotIndex
                         INTEGER,
                    concentratorSlotRingIndex
                         INTEGER,
                    concentratorSlotRingAdminName
                         DisplayString,
                    concentratorSlotRingAdminSpeed
                         INTEGER,
                    concentratorSlotRingAdminState
                         INTEGER,
                    concentratorSlotRingZero
                         INTEGER,
                    concentratorSlotRingSinceZero
                         TimeTicks,
                    concentratorSlotRingChassisRing
                         Letter,
                    concentratorSlotRingOperName
                         DisplayString,
                    concentratorSlotRingOperSpeed
                         INTEGER,
                    concentratorSlotRingOperState
                         INTEGER,
                    concentratorSlotRingChassisRingsAllowed
                         OCTET STRING
            }
    
            concentratorSlotSlotIndex OBJECT-TYPE
                SYNTAX INTEGER
                ACCESS read-only
                STATUS mandatory
                DESCRIPTION
                    "This variable identifies the slot of the chassis."
                ::= { concentratorSlotRingEntry 1 }
    
            concentratorSlotRingIndex OBJECT-TYPE
                SYNTAX INTEGER
                ACCESS read-only
                STATUS mandatory
                DESCRIPTION
                    "This variable identifies the ring within the slot."
                ::= { concentratorSlotRingEntry 2 }
    
            concentratorSlotRingAdminName OBJECT-TYPE
                SYNTAX DisplayString (SIZE (0..16))
                ACCESS read-write
                STATUS mandatory
                DESCRIPTION
                    "This variable represents the user defined name of
                    the ring."
                ::= { concentratorSlotRingEntry 3 }
    
            concentratorSlotRingAdminSpeed OBJECT-TYPE
                SYNTAX INTEGER { mbps4(1), mbps16(2) }
                ACCESS read-write
                STATUS mandatory
                DESCRIPTION
                    "This variable represents the user defined speed of
                    the ring."
                ::= { concentratorSlotRingEntry 4 }
    
            concentratorSlotRingAdminState OBJECT-TYPE
                SYNTAX INTEGER { isolated(1), inserted(2) }
                ACCESS read-write
                STATUS mandatory
                DESCRIPTION
                    "This variable defines whether the slot ring is to
                    be inserted into the defined chassis ring or is to
                    be isolated."
                ::= { concentratorSlotRingEntry 5 }
    
            concentratorSlotRingZero OBJECT-TYPE
                SYNTAX INTEGER { ready(1), execute(2) }
                ACCESS read-write
                STATUS mandatory
                DESCRIPTION
                    "This variable is used to control the slot ring's
                    counters.  The agent always returns 'ready' for this
                    value.  Setting the value to 'ready' has no effect."
                ::= { concentratorSlotRingEntry 6 }
    
            concentratorSlotRingSinceZero OBJECT-TYPE
                SYNTAX TimeTicks
                ACCESS read-only
                STATUS mandatory
                DESCRIPTION
                    "This variable reflects the number of time ticks
                    since the counters were last zeroed.  This variable
                    is set to zero when concentratoSlotRingZero is
                    written with the value 2"
                ::= { concentratorSlotRingEntry 7 }
    
            concentratorSlotRingChassisRing OBJECT-TYPE
                SYNTAX Letter
                ACCESS read-write
                STATUS mandatory
                DESCRIPTION
                    "This variable represents the chassis ring into
                    which the slot ring is to be inserted if it is to be
                    inserted."
                ::= { concentratorSlotRingEntry 8 }
    
            concentratorSlotRingOperName OBJECT-TYPE
                SYNTAX DisplayString (SIZE (0..16))
                ACCESS read-only
                STATUS mandatory
                DESCRIPTION
                    "This variable represents the name currently being
                    used to identify the slot ring.  If inserted, this
                    name will be the user defined name of the chassis
                    ring into which it is inserted.  If isolated, this
                    name will be the user defined name of the slot
                    ring."
                ::= { concentratorSlotRingEntry 9 }
    
            concentratorSlotRingOperSpeed OBJECT-TYPE
                SYNTAX INTEGER { mbps4(1), mbps16(2) }
                ACCESS read-only
                STATUS mandatory
                DESCRIPTION
                    "This variable represents the current speed of the
                    slot ring.  If inserted, this speed will be the user
                    defined speed of the chassis ring into which it is
                    inserted.  If isolated, this speed will be the user
                    defined speed of the slot ring."
                ::= { concentratorSlotRingEntry 10 }
    
            concentratorSlotRingOperState OBJECT-TYPE
                SYNTAX INTEGER { isolated(1), inserted(2) }
                ACCESS read-only
                STATUS mandatory
                DESCRIPTION
                    "This variable indicates whether the slot ring is
                    inserted into the defined chassis ring or is
                    isolated."
                ::= { concentratorSlotRingEntry 11 }
    
            concentratorSlotRingChassisRingsAllowed OBJECT-TYPE
                SYNTAX OCTET STRING
                ACCESS read-only
                STATUS mandatory
                DESCRIPTION
                    "The list of chassis rings into which this slot ring
                    may be inserted.  The OCTET STRING contains a bit
                    map, with a bit for 'none' (indicating it may be
                    isolated) and one bit for each chassis ring, and
                    enough octets for all chassis rings.  The high order
                    bit of the first octet corresponds to 'none' and
                    each subsequent bit in ascending order corresponds
                    to the chassis rings in order beginning with A."
                ::= { concentratorSlotRingEntry 12 }
    
            -- The chassis ring group contains information and status
            -- for the rings of the chassis:
    
            concentratorChassisRingTable OBJECT-TYPE
                SYNTAX SEQUENCE OF ConcentratorChassisRingEntry
                ACCESS not-accessible
                STATUS mandatory
                DESCRIPTION
                    "Table of descriptive and status information about
                    the rings of a the chassis."
                ::= { xConcentrator 8 }
    
            concentratorChassisRingEntry OBJECT-TYPE
                SYNTAX ConcentratorChassisRingEntry
                ACCESS not-accessible
                STATUS mandatory
                DESCRIPTION
                    "An entry in the table containing information about
                    a specific ring."
                INDEX { concentratorChassisRingIndex }
                ::= { concentratorChassisRingTable 1 }
    
            ConcentratorChassisRingEntry ::=
                SEQUENCE {
                    concentratorChassisRingIndex
                         Letter,
                    concentratorChassisRingName
                         DisplayString,
                    concentratorChassisRingSpeed
                         INTEGER,
                    concentratorChassisRingTopologyChanges
                         Counter,
                    concentratorChassisRingZero
                         INTEGER,
                    concentratorChassisRingSinceZero
                         TimeTicks
                }
    
            concentratorChassisRingIndex OBJECT-TYPE
                SYNTAX Letter
                ACCESS read-only
                STATUS mandatory
                DESCRIPTION
                    "This variable identifies the ring of the chassis."
                ::= { concentratorChassisRingEntry 1 }
    
            concentratorChassisRingName OBJECT-TYPE
                SYNTAX DisplayString (SIZE (0..14))
                ACCESS read-write
                STATUS mandatory
                DESCRIPTION
                    "This variable represents the name of the ring.  All
                    segments of a given chassis ring will have the same
                    base name, All segment of that ring will appear as
                    'baseNamex' where x is the identified segment"
                ::= { concentratorChassisRingEntry 2 }
    
            concentratorChassisRingSpeed OBJECT-TYPE
                SYNTAX INTEGER { mbps4(1), mbps16(2) }
                ACCESS read-write
                STATUS mandatory
                DESCRIPTION
                    "This variable indicates the speed of the ring
                    segment.  All segments of a given chassis ring are
                    at the same speed."
                ::= { concentratorChassisRingEntry 3 }
    
            concentratorChassisRingTopologyChanges OBJECT-TYPE
                SYNTAX Counter
                ACCESS read-only
                STATUS mandatory
                DESCRIPTION
                    "This variable reflects the number of times the
                    topology has changed for this ring.  This variable
                    is set to zero when concentratorChassisRingZero is
                    written with the value 2."
                ::= { concentratorChassisRingEntry 4 }
    
            concentratorChassisRingZero OBJECT-TYPE
                SYNTAX INTEGER { ready(1), execute(2) }
                ACCESS read-write
                STATUS mandatory
                DESCRIPTION
                    "This variable is used to control the ring's
                    counters.  The agent always returns 'ready' for this
                    value.  Setting the value to 'ready' has no effect."
                ::= { concentratorChassisRingEntry 5 }
    
            concentratorChassisRingSinceZero OBJECT-TYPE
                SYNTAX TimeTicks
                ACCESS read-only
                STATUS mandatory
                DESCRIPTION
                    "This variable reflects the number of time ticks
                    since the counters were last zeroed.  This variable
                    is set to zero when concentratoChassisRingZero is
                    written with the value 2"
                ::= { concentratorChassisRingEntry 6 }
    
            -- The chassis ring topology group is a table which contains
            -- information and status concerningthe segments of the
            -- chassis rings:
    
            concentratorChassisRingTopologyTable OBJECT-TYPE
                SYNTAX SEQUENCE OF ConcentratorChassisRingTopologyEntry
                ACCESS not-accessible
                STATUS mandatory
                DESCRIPTION
                    "Table of descriptive and status information about
                    the segments of the chassis rings."
                ::= { xConcentrator 9 }
    
            concentratorChassisRingTopologyEntry OBJECT-TYPE
                SYNTAX ConcentratorChassisRingTopologyEntry
                ACCESS not-accessible
                STATUS mandatory
                DESCRIPTION
                    "An entry in the table containing information about
                    a specific ring segment."
                INDEX { concentratorChassisRingTopologySlotIndex,
                        concentratorChassisRingTopologyRingIndex }
                ::= { concentratorChassisRingTopologyTable 1 }
    
            ConcentratorChassisRingTopologyEntry ::=
                SEQUENCE {
                    concentratorChassisRingTopologySlotIndex
                         INTEGER,
                    concentratorChassisRingTopologyRingIndex
                         Letter,
                    concentratorChassisRingTopologyWrapUp
                         INTEGER,
                    concentratorChassisRingTopologyWrapDown
                         INTEGER,
                    concentratorChassisRingTopologyUpState
                         INTEGER,
                    concentratorChassisRingTopologyDownState
                         INTEGER,
                    concentratorChassisRingTopologySegment
                         INTEGER,
                    concentratorChassisRingTopologyName
                         DisplayString,
                    concentratorChassisRingTopologySpeed
                         INTEGER,
                    concentratorChassisRingTopologyCardType
                         IOType,
                    concentratorChassisRingTopologyAutoUpChanges
                         Counter,
                    concentratorChassisRingTopologyAutoDownChanges
                         Counter
    }
    
            concentratorChassisRingTopologySlotIndex OBJECT-TYPE
                SYNTAX INTEGER
                ACCESS read-only
                STATUS mandatory
                DESCRIPTION
                    "This variable identifies a slot number that is
                    included in the ring segment."
                ::= { concentratorChassisRingTopologyEntry 1 }
    
            concentratorChassisRingTopologyRingIndex OBJECT-TYPE
                SYNTAX Letter
                ACCESS read-only
                STATUS mandatory
                DESCRIPTION
                    "This variable identifies the ring of the chassis."
                ::= { concentratorChassisRingTopologyEntry 2 }
    
            concentratorChassisRingTopologyWrapUp OBJECT-TYPE
                SYNTAX INTEGER { unwrap(1), wrap(2) }
                ACCESS read-only
                STATUS mandatory
                DESCRIPTION
                    "This variable represents the upper wrap state for
                    the chassis ring which passes through this slot.  By
                    setting this variable to Wrap, the user can create a
                    segment which would contain this slot, and all slots
                    above this one which are on the same segment. "
                ::= { concentratorChassisRingTopologyEntry 3 }
    
            concentratorChassisRingTopologyWrapDown OBJECT-TYPE
                SYNTAX INTEGER { unwrap(1), wrap(2) }
                ACCESS read-only
                STATUS mandatory
                DESCRIPTION
                    "This variable represents the lower wrap state for
                    the chassis ring which passes through this slot.  By
                    setting this variable to Wrap, the user can create a
                    segment which would contain this slot, and all slots
                    below this one which are on the same segment. "
                ::= { concentratorChassisRingTopologyEntry 4 }
    
            concentratorChassisRingTopologyUpState OBJECT-TYPE
                SYNTAX INTEGER { static(1), dynamic(2) }
                ACCESS read-only
                STATUS mandatory
                DESCRIPTION
                    "This variable represents the type of upper wrap for
                    the chassis ring which passes through this slot. "
                ::= { concentratorChassisRingTopologyEntry 5 }
    
            concentratorChassisRingTopologyDownState OBJECT-TYPE
                SYNTAX INTEGER { static(1), dynamic(2) }
                ACCESS read-only
                STATUS mandatory
                DESCRIPTION
                    "This variable represents the type of lower wrap for
                    the chassis ring which passes through this slot. "
                ::= { concentratorChassisRingTopologyEntry 6 }
    
            concentratorChassisRingTopologySegment OBJECT-TYPE
                SYNTAX INTEGER
                ACCESS read-only
                STATUS mandatory
                DESCRIPTION
                    "This variable represents the segment number for the
                    chassis ring which passes through this slot. "
                ::= { concentratorChassisRingTopologyEntry 7 }
    
            concentratorChassisRingTopologyName OBJECT-TYPE
                SYNTAX DisplayString (SIZE (0..16))
                ACCESS read-only
                STATUS mandatory
                DESCRIPTION
                    "This variable represents the name of the ring
                    segment.  The ring segment name is the base ring
                    name with '-segment number' appended to the end."
                ::= { concentratorChassisRingTopologyEntry 8 }
    
            concentratorChassisRingTopologySpeed OBJECT-TYPE
                SYNTAX INTEGER { mbps4(1), mbps16(2) }
                ACCESS read-only
                STATUS mandatory
                DESCRIPTION
                    "This variable indicates the speed of the ring
                    segment.  All segments of a given chassis ring are
                    at the same speed as the parent ring."
                ::= { concentratorChassisRingTopologyEntry 9 }
    
            concentratorChassisRingTopologyCardType OBJECT-TYPE
                SYNTAX IOType
                ACCESS read-only
                STATUS mandatory
                DESCRIPTION
                    "This variable represents the type of the I/O card."
                ::= { concentratorChassisRingTopologyEntry 10}
    
            concentratorChassisRingTopologyAutoUpChanges OBJECT-TYPE
                SYNTAX Counter
                ACCESS read-only
                STATUS mandatory
                DESCRIPTION
                    "This variable reflects the number of times the
                    topology has changed for this ring due to a dynamic
                    wrap up.  This variable is set to zero when
                    concentratorSlotRingZero is written with the value
                    2."
                ::= { concentratorChassisRingTopologyEntry 11 }
    
            concentratorChassisRingTopologyAutoDownChanges OBJECT-TYPE
                SYNTAX Counter
                ACCESS read-only
                STATUS mandatory
                DESCRIPTION
                    "This variable reflects the number of times the
                    topology has changed for this ring due to a dynamic
                    wrap down.  This variable is set to zero when
                    concentratorSlotRingZero is written with the value
                    2."
                ::= { concentratorChassisRingTopologyEntry 12 }
    
            -- The port group contains information and status concerning
            -- the ports of a concentrator:
    
            concentratorPortTable OBJECT-TYPE
                SYNTAX SEQUENCE OF ConcentratorPortEntry
                ACCESS not-accessible
                STATUS mandatory
                DESCRIPTION
                    "Table of information and status concerning the
                    ports of a concentrator."
                ::= { xConcentrator 10 }
    
            concentratorPortEntry OBJECT-TYPE
                SYNTAX ConcentratorPortEntry
                ACCESS not-accessible
                STATUS mandatory
                DESCRIPTION
                    "An entry in the table containing control and status
                    information for a port."
                INDEX { concentratorSlotIndex, concentratorPortIndex }
                ::= { concentratorPortTable 1 }
    
            ConcentratorPortEntry ::=
                SEQUENCE {
                    concentratorPortSlotIndex
                         INTEGER,
                    concentratorPortIndex
                         INTEGER,
                    concentratorPortName
                         DisplayString,
                    concentratorPortType
                         INTEGER,
                    concentratorPortZero
                         INTEGER,
                    concentratorPortSinceZero
                         TimeTicks,
                    concentratorPortAdminState
                         INTEGER,
                    concentratorPortOperState
                         INTEGER,
                    concentratorPortInsertions
                         Counter,
                    concentratorPortInsertFailures
                         Counter,
                    concentratorPortAdminInsert
                         INTEGER,
                    concentratorPortOperInsert
                         INTEGER,
                    concentratorPortSpeed
                         INTEGER,
                    concentratorPortAdminLoopback
                         INTEGER,
                    concentratorPortStationType
                         INTEGER,
                    concentratorPortAdminTrunkInsert
                         INTEGER,
                    concentratorPortSlotRingsAllowed
                         OCTET STRING
            }
    
            concentratorPortSlotIndex OBJECT-TYPE
                SYNTAX INTEGER
                ACCESS read-only
                STATUS mandatory
                DESCRIPTION
                    "This variable identifies the slot of the chassis."
                ::= { concentratorPortEntry 1 }
    
            concentratorPortIndex OBJECT-TYPE
                SYNTAX INTEGER
                ACCESS read-only
                STATUS mandatory
                DESCRIPTION
                    "This variable identifies target port."
                ::= { concentratorPortEntry 2 }
    
            concentratorPortName OBJECT-TYPE
                SYNTAX DisplayString (SIZE (0..16))
                ACCESS read-write
                STATUS mandatory
                DESCRIPTION
                    "This variable represents the user defined name of
                    the port."
                ::= { concentratorPortEntry 3 }
    
            concentratorPortType OBJECT-TYPE
                SYNTAX INTEGER { rj45(1), fiber(2) }
                ACCESS read-only
                STATUS mandatory
                DESCRIPTION
                    "This variable represents the type of connector
                    provided for the port."
                ::= { concentratorPortEntry 4 }
    
            concentratorPortZero OBJECT-TYPE
                SYNTAX INTEGER { ready(1), execute(2) }
                ACCESS read-write
                STATUS mandatory
                DESCRIPTION
                    "This variable is used to control the ports
                    counters.  The agent always returns 'ready' for this
                    value.  Setting the value to 'ready' has no effect."
                ::= { concentratorPortEntry 5 }
    
            concentratorPortSinceZero OBJECT-TYPE
                SYNTAX TimeTicks
                ACCESS read-only
                STATUS mandatory
                DESCRIPTION
                    "This variable reflects the number of time ticks
                    since the counters were las zeroed.  This variable
                    is set to zero when concentratorPortZero is written
                    with the value 2"
                ::= { concentratorPortEntry 6 }
    
            concentratorPortAdminState OBJECT-TYPE
                SYNTAX INTEGER { disabled(1), enabled(2) }
                ACCESS read-write
                STATUS mandatory
                DESCRIPTION
                    "This variable reflects the enable/disable state of
                    the port."
                ::= { concentratorPortEntry 7 }
    
            concentratorPortOperState OBJECT-TYPE
                SYNTAX INTEGER { inserted(1), notInserted(2), rateMismatch(3) }
                ACCESS read-only
                STATUS mandatory
                DESCRIPTION
                    "This variable reflects the enable/disable state of
                    the port."
                ::= { concentratorPortEntry 8 }
    
            concentratorPortInsertions OBJECT-TYPE
                SYNTAX Counter
                ACCESS read-only
                STATUS mandatory
                DESCRIPTION
                    "This variable reflects the number of times the port
                    was inserted into the ring."
                ::= { concentratorPortEntry 9 }
    
            concentratorPortInsertFailures OBJECT-TYPE
                SYNTAX Counter
                ACCESS read-only
                STATUS mandatory
                DESCRIPTION
                    "This variable reflects the number of times the port
                    was not inserted due to a data rate mismatch."
                ::= { concentratorPortEntry 10 }
    
            concentratorPortAdminInsert OBJECT-TYPE
                SYNTAX INTEGER { auto(1),
                                 ring1(2),
                                 ring2(3),
                                 ring3(4),
                                 ring4(5),
                                 ring5(6),
                                 ring6(7),
                                 ring7(8),
                                 ring8(9),
                                 ring9(10),
                                 ring10(11) }
                ACCESS read-write
                STATUS mandatory
                DESCRIPTION
                    "This variable reflects the desired insertion of the
                    port.  Auto indicates to insert the port into the
                    first slot ring with a matching data rate beginning
                    with 1."
                ::= { concentratorPortEntry 11 }
    
            concentratorPortOperInsert OBJECT-TYPE
                SYNTAX INTEGER { notInserted(1),
                  ring1(2),
                  ring2(3),
                  ring3(4),
                  ring4(5),
                  ring5(6),
                  ring6(7),
                  ring7(8),
                  ring8(9),
                  ring9(10),
                  ring10(11) }
                ACCESS read-only
                STATUS mandatory
                DESCRIPTION
                    "This variable reflects the slot ring to which the
                    port is attached."
                ::= { concentratorPortEntry 12 }
    
            concentratorPortSpeed OBJECT-TYPE
                SYNTAX INTEGER { mbs4(1), mbs16(2) }
                ACCESS read-only
                STATUS mandatory
                DESCRIPTION
                    "This variable reflects the measured speed of the
                    port."
                ::= { concentratorPortEntry 13 }
    
            concentratorPortAdminLoopback OBJECT-TYPE
                SYNTAX INTEGER { insert(1), loopback(2) }
                ACCESS read-write
                STATUS mandatory
                DESCRIPTION
                    "This variable reflects the whether this port will
                    be inserted into a ring or the data loop backed."
                ::= { concentratorPortEntry 14 }
    
            concentratorPortStationType OBJECT-TYPE
                SYNTAX INTEGER { station(1), trunk(2) }
                ACCESS read-write
                STATUS mandatory
                DESCRIPTION
                    "This variable reflects the concentrator port type."
                ::= { concentratorPortEntry 15 }
    
            concentratorPortAdminTrunkInsert OBJECT-TYPE
                SYNTAX INTEGER { ready(1), execute(2) }
                ACCESS read-write
                STATUS mandatory
                DESCRIPTION
                    "This variable is used to control the insertion of
                    trunk ports.  When set to 'execute' the trunk port
                    will be inserted into the ring immediately and not
                    wait for the trunk timer to expire. The agent always
                    returns 'ready' for this value.  Setting the value
                    to 'ready' has no effect."
                ::= { concentratorPortEntry 16 }
    
            concentratorPortSlotRingsAllowed OBJECT-TYPE
                SYNTAX OCTET STRING
                ACCESS read-only
                STATUS mandatory
                DESCRIPTION
                    "The list of slot rings into which this port may be
                    inserted.  The OCTET STRING contains a bit map, with
                    a bit for 'none' (indicating it may be isolated) and
                    one bit for each slot ring, and enough octets for
                    all slot rings.  The high order bit of the first
                    octet corresponds to 'none' and each subsequent bit
                    in ascending order corresponds to the slot rings in
                    order beginning with 1."
                ::= { concentratorPortEntry 17 }


--
-- FILE: /users/sse/mibs/src/itouch/it-decnet-mib.mib
--

-- $Id: it-decnet-mib.mib,v 1.1 2000/07/25 14:21:27 sse Exp $


            xDecnet         OBJECT IDENTIFIER ::= { iTouch 14 }

            -- iTouch DECnet groups

            xRcp            OBJECT IDENTIFIER ::= { xDecnet 1 }
            xPhiv           OBJECT IDENTIFIER ::= { xDecnet 2 }

            -- Phase IV subgroups

            xPhivRoute      OBJECT IDENTIFIER ::= { xPhiv 1 }
            xPhivCircuit    OBJECT IDENTIFIER ::= { xPhiv 2 }
            xPhivImport     OBJECT IDENTIFIER ::= { xPhiv 3 }
            xPhivImportArea OBJECT IDENTIFIER ::= { xPhiv 4 }
            xPhivExport     OBJECT IDENTIFIER ::= { xPhiv 5 }
            xPhivExportArea OBJECT IDENTIFIER ::= { xPhiv 6 }
            xPhivFilter     OBJECT IDENTIFIER ::= { xPhiv 7 }
            xPhivTraffic    OBJECT IDENTIFIER ::= { xPhiv 8 }




            -- This is a MIB module for all iTouch Communications DECnet
            -- implementations.

            -- Copyright 2000 iTouch Communications, Inc. All Rights Reserved.
            -- Reproduction of this document is authorized on
            -- condition that this copyright notice is included.
            -- This MIB document embodies iTouch Communications, Inc.'s 
            -- proprietary intellectual property.  iTouch Communications, Inc.
            -- retains all title and ownership in this MIB, including any
            -- revisions.
            --
            -- It is iTouch Communications, Inc.'s intent to encourage the
            -- widespread use of this MIB in connection with the management of
            -- iTouch Communications, Inc. products. iTouch Communications,
            -- Inc. grants vendors,end-users, and other interested parties a
            -- non-exclusive license to use this MIB in connection with the
            -- management of iTouch Communications, Inc. products.
            --
            -- This MIB document is supplied "AS IS," and iTouch 
            -- Communications, Inc. makes no warranty, either express or
            -- implied, as to the use operation, condition, or performance of
            -- the MIB.


            -- the Remote Console group

            -- Implementation of this group is mandatory for all iTouch
            -- systems that implement DECnet remote console (RCP)

            rcpRemoteAddress OBJECT-TYPE
                SYNTAX OCTET STRING (SIZE (0..6))
                ACCESS read-only
                STATUS mandatory
                DESCRIPTION
                    "If a remote console session exists, the Ethernet 
                    address of the remote partner, otherwise zero 
                    length."
                ::= { xRcp 1 }


            -- the Phase IV group

            -- Implementation of this group is mandatory for all iTouch
            -- systems that implement DECnet Phase IV routing

            -- the Phase IV Route subgroup

            phivPathSelection OBJECT-TYPE
                SYNTAX INTEGER { roundRobin(1), samePath(2) }
                ACCESS read-write
                STATUS mandatory
                DESCRIPTION
                    "The algorithm used to balance traffic between equal 
                    next hop paths.  'roundRobin' selects the next hop 
                    using a round robin algorithm for each hop.  
                    'samePath' selects the next hop guaranteeing that 
                    all packets with the same source/destination pair 
                    will always use the same next hop."
                DEFVAL { roundRobin }
                ::= { xPhivRoute 1 }

            phivMaxPaths OBJECT-TYPE
                SYNTAX INTEGER (1..255)
                ACCESS read-write
                STATUS mandatory
                DESCRIPTION
                    "The maximum number of equal cost next hops that the 
                    router can remember and successfully load balance 
                    between."
                DEFVAL { 1 }
                ::= { xPhivRoute 2 }

            phivStatus OBJECT-TYPE
                SYNTAX INTEGER { active(1), disabled(2),
                                 noAddressSpecified(3),
                                 noInterfacesEnabled(4),
                                 badCost(5) }
                ACCESS read-only
                STATUS mandatory
                DESCRIPTION
                    "The status of the DECnet routing software."
                ::= { xPhivRoute 3 }


            -- the Phase IV Circuit subgroup

            phivCircuitTable OBJECT-TYPE
                SYNTAX SEQUENCE OF PhivCircuitEntry
                ACCESS not-accessible
                STATUS mandatory
                DESCRIPTION
                    "A list of DECnet circuit entries."
                ::= { xPhivCircuit 1 }

            phivCircuitEntry OBJECT-TYPE
                SYNTAX PhivCircuitEntry
                ACCESS not-accessible
                STATUS mandatory
                DESCRIPTION
                    "Parameter values for a DECnet circuit."
                INDEX { xPhivCircuitIndex }
                ::= { phivCircuitTable 1 }

            PhivCircuitEntry ::=
                SEQUENCE {
                    xPhivCircuitIndex
                        INTEGER,
                    phivCircuitRoutingTimer
                        INTEGER,
                    phivCircuitOperCost
                        INTEGER,
                    phivCircuitErrors
                        Counter,
                    phivCircuitLastError
                        INTEGER,
                    phivCircuitLastErrorTime
                        DateTime,
                    phivCircuitLastErrorData
                        OCTET STRING,
                    phivCircuitProtocolPriority
                        INTEGER,
                    phivCircuitRoutingPriority
                        INTEGER
                }

            xPhivCircuitIndex OBJECT-TYPE
                SYNTAX INTEGER
                ACCESS read-only
                STATUS mandatory
                DESCRIPTION
                    "Identification of a circuit entry.  Same as an 
                    interface index (ifIndex)."
                ::= { phivCircuitEntry 1 }

            phivCircuitRoutingTimer OBJECT-TYPE
                SYNTAX INTEGER (1..65535)
                ACCESS read-write
                STATUS mandatory
                DESCRIPTION
                    "The maximum time in seconds allowed between Routing 
                    updates on the circuit. Different values for LANs 
                    vs. WANs."
                DEFVAL { 40 }
                ::= { phivCircuitEntry 2 }

            phivCircuitOperCost OBJECT-TYPE
                SYNTAX INTEGER
                ACCESS read-only
                STATUS mandatory
                DESCRIPTION
                    "The actual cost associated with the circuit."
                ::= { phivCircuitEntry 3 }

            phivCircuitErrors OBJECT-TYPE
                SYNTAX Counter
                ACCESS read-only
                STATUS mandatory
                DESCRIPTION
                    "The number of routed DECnet packets received in 
                    error on this circuit."
                ::= { phivCircuitEntry 4 }

            phivCircuitLastError OBJECT-TYPE
                SYNTAX INTEGER { noError(1),
                                 addressOutOfRange(2),
                                 ageExceeded(3),
                                 destinationUnreachable(4),
                                 packetFormatError(5),
                                 packetOversized(6),
                                 partialRoutingUpdate(7),
                                 verificationReject(8) }
                ACCESS read-only
                STATUS mandatory
                DESCRIPTION
                    "The error of the last routed DECnet packet received 
                    in error on this circuit."
                ::= { phivCircuitEntry 5 }

            phivCircuitLastErrorTime OBJECT-TYPE
                SYNTAX DateTime
                ACCESS read-only
                STATUS mandatory
                DESCRIPTION
                    "The date and time that the last routed DECnet 
                    packet was received in error on this circuit."
                ::= { phivCircuitEntry 6 }

            phivCircuitLastErrorData OBJECT-TYPE
                SYNTAX OCTET STRING (SIZE (22))
                ACCESS read-only
                STATUS mandatory
                DESCRIPTION
                    "The first 22 bytes of the last routed DECnet packet 
                    received in error on this circuit."
                ::= { phivCircuitEntry 7 }

            phivCircuitProtocolPriority OBJECT-TYPE
                SYNTAX INTEGER { low(1), medium(3), high(5) }
                ACCESS read-write
                STATUS mandatory
                DESCRIPTION
                    "The priority at which all DECnet routed packets 
                    will be placed on the WAN output queue."
                DEFVAL { medium }
                ::= { phivCircuitEntry 8 }

            phivCircuitRoutingPriority OBJECT-TYPE
                SYNTAX INTEGER (0..127)
                ACCESS read-write
                STATUS mandatory
                DESCRIPTION
                    "Router's priority to be designated router on this 
                    circuit."
                DEFVAL { 64 }
                ::= { phivCircuitEntry 9 }


            -- the Phase IV Import Filter subgroup

            phivCircuitImportTable OBJECT-TYPE
                SYNTAX SEQUENCE OF PhivCircuitImportEntry
                ACCESS not-accessible
                STATUS mandatory
                DESCRIPTION
                    "A list of circuit import filter entries."
                ::= { xPhivImport 1 }

            phivCircuitImportEntry OBJECT-TYPE
                SYNTAX PhivCircuitImportEntry
                ACCESS not-accessible
                STATUS mandatory
                DESCRIPTION
                    "Parameter values for an import filter."
                INDEX { phivCircuitImportIf, phivCircuitImportAddr,
                        phivCircuitImportMask }
                ::= { phivCircuitImportTable 1 }

            PhivCircuitImportEntry ::=
                SEQUENCE {
                    phivCircuitImportIf
                        INTEGER,
                    phivCircuitImportAddr
                        PhivAddr,
                    phivCircuitImportMask
                        PhivAddr,
                    phivCircuitImportAction
                        INTEGER,
                    phivCircuitImportStatus
                        INTEGER
                }

            phivCircuitImportIf OBJECT-TYPE
                SYNTAX INTEGER
                ACCESS read-only
                STATUS mandatory
                DESCRIPTION
                    "The interface associated with the import routing 
                    filter."
                ::= { phivCircuitImportEntry 1 }

            phivCircuitImportAddr OBJECT-TYPE
                SYNTAX PhivAddr
                ACCESS read-only
                STATUS mandatory
                DESCRIPTION
                    "The address (node or area) to match against learned 
                    route entries to decide whether to import the entry 
                    to the routing database."
                ::= { phivCircuitImportEntry 2 }

            phivCircuitImportMask OBJECT-TYPE
                SYNTAX PhivAddr
                ACCESS read-only
                STATUS mandatory
                DESCRIPTION
                    "The mask which is ANDed with the address field as 
                    well as the route entries address to determine 
                    whether the address matches the route entry."
                ::= { phivCircuitImportEntry 3 }

            phivCircuitImportAction OBJECT-TYPE
                SYNTAX INTEGER { discard(1), accept(2) }
                ACCESS read-write
                STATUS mandatory
                DESCRIPTION
                    "The action to take if the address field along with 
                    the mask field matches the route entry."
                DEFVAL { accept }
                ::= { phivCircuitImportEntry 4 }

            phivCircuitImportStatus OBJECT-TYPE
                SYNTAX INTEGER { invalid(1), valid(2) }
                ACCESS read-write
                STATUS mandatory
                DESCRIPTION
                    "Setting to 'invalid' removes this import filter 
                    from the table. Setting to 'valid' has no effect."
                DEFVAL { valid }
                ::= { phivCircuitImportEntry 5 }


            -- the Phase IV Import Area Filters subgroup

            phivCircuitImportAreaTable OBJECT-TYPE
                SYNTAX SEQUENCE OF PhivCircuitImportAreaEntry
                ACCESS not-accessible
                STATUS mandatory
                DESCRIPTION
                    "A list of circuit import area filter entries."
                ::= { xPhivImportArea 1 }

            phivCircuitImportAreaEntry OBJECT-TYPE
                SYNTAX PhivCircuitImportAreaEntry
                ACCESS not-accessible
                STATUS mandatory
                DESCRIPTION
                    "Parameter values for an import area filter."
                INDEX { phivCircuitImportAreaIf,
                        phivCircuitImportAreaAddr,
                        phivCircuitImportAreaMask }
                ::= { phivCircuitImportAreaTable 1 }

            PhivCircuitImportAreaEntry ::=
                SEQUENCE {
                    phivCircuitImportAreaIf
                        INTEGER,
                    phivCircuitImportAreaAddr
                        PhivAddr,
                    phivCircuitImportAreaMask
                        PhivAddr,
                    phivCircuitImportAreaAction
                        INTEGER,
                    phivCircuitImportAreaStatus
                        INTEGER
                }

            phivCircuitImportAreaIf OBJECT-TYPE
                SYNTAX INTEGER
                ACCESS read-only
                STATUS mandatory
                DESCRIPTION
                    "The interface associated with the import area 
                    routing filter."
                ::= { phivCircuitImportAreaEntry 1 }

            phivCircuitImportAreaAddr OBJECT-TYPE
                SYNTAX PhivAddr
                ACCESS read-only
                STATUS mandatory
                DESCRIPTION
                    "The address (node or area) to match against learned 
                    route entries to decide whether to import the entry 
                    to the routing database."
                ::= { phivCircuitImportAreaEntry 2 }

            phivCircuitImportAreaMask OBJECT-TYPE
                SYNTAX PhivAddr
                ACCESS read-only
                STATUS mandatory
                DESCRIPTION
                    "The mask which is ANDed with the address field as 
                    well as the route entries address to determine 
                    whether the address matches the route entry."
                ::= { phivCircuitImportAreaEntry 3 }

            phivCircuitImportAreaAction OBJECT-TYPE
                SYNTAX INTEGER { discard(1), accept(2) }
                ACCESS read-write
                STATUS mandatory
                DESCRIPTION
                    "The action to take if the address field along with 
                    the mask field matches the route entry."
                DEFVAL { accept }
                ::= { phivCircuitImportAreaEntry 4 }

            phivCircuitImportAreaStatus OBJECT-TYPE
                SYNTAX INTEGER { invalid(1), valid(2) }
                ACCESS read-write
                STATUS mandatory
                DESCRIPTION
                    "Setting to 'invalid' removes this import area 
                    filter from the table.  Setting to 'valid' has no 
                    effect."
                DEFVAL { valid }
                ::= { phivCircuitImportAreaEntry 5 }


            -- the Phase IV Export Filters subgroup

            phivCircuitExportTable OBJECT-TYPE
                SYNTAX SEQUENCE OF PhivCircuitExportEntry
                ACCESS not-accessible
                STATUS mandatory
                DESCRIPTION
                    "A list of circuit export filter entries."
                ::= { xPhivExport 1 }

            phivCircuitExportEntry OBJECT-TYPE
                SYNTAX PhivCircuitExportEntry
                ACCESS not-accessible
                STATUS mandatory
                DESCRIPTION
                    "Parameter values for an export filter."
                INDEX { phivCircuitExportIf, phivCircuitExportAddr,
                        phivCircuitExportMask }
                ::= { phivCircuitExportTable 1 }

            PhivCircuitExportEntry ::=
                SEQUENCE {
                    phivCircuitExportIf
                        INTEGER,
                    phivCircuitExportAddr
                        PhivAddr,
                    phivCircuitExportMask
                        PhivAddr,
                    phivCircuitExportAction
                        INTEGER,
                    phivCircuitExportStatus
                        INTEGER
                }

            phivCircuitExportIf OBJECT-TYPE
                SYNTAX INTEGER
                ACCESS read-only
                STATUS mandatory
                DESCRIPTION
                    "The interface associated with the export routing 
                    filter."
                ::= { phivCircuitExportEntry 1 }

            phivCircuitExportAddr OBJECT-TYPE
                SYNTAX PhivAddr
                ACCESS read-only
                STATUS mandatory
                DESCRIPTION
                    "The address (node or area) to match against learned 
                    route entries to decide whether to export the entry 
                    to the routing database."
                ::= { phivCircuitExportEntry 2 }

            phivCircuitExportMask OBJECT-TYPE
                SYNTAX PhivAddr
                ACCESS read-only
                STATUS mandatory
                DESCRIPTION
                    "The mask which is ANDed with the address field as 
                    well as the route entries address to determine 
                    whether the address matches the route entry."
                ::= { phivCircuitExportEntry 3 }

            phivCircuitExportAction OBJECT-TYPE
                SYNTAX INTEGER { hide(1), advertise(2) }
                ACCESS read-write
                STATUS mandatory
                DESCRIPTION
                    "The action to take if the address field along with 
                    the mask field matches the route entry."
                DEFVAL { advertise }
                ::= { phivCircuitExportEntry 4 }

            phivCircuitExportStatus OBJECT-TYPE
                SYNTAX INTEGER { invalid(1), valid(2) }
                ACCESS read-write
                STATUS mandatory
                DESCRIPTION
                    "Setting to 'invalid' removes this export filter 
                    from the table.  Setting to 'valid' has no effect."
                DEFVAL { valid }
                ::= { phivCircuitExportEntry 5 }


            -- the Phase IV Export Area Filters subgroup

            phivCircuitExportAreaTable OBJECT-TYPE
                SYNTAX SEQUENCE OF PhivCircuitExportAreaEntry
                ACCESS not-accessible
                STATUS mandatory
                DESCRIPTION
                    "A list of circuit export area filter entries."
                ::= { xPhivExportArea 1 }

            phivCircuitExportAreaEntry OBJECT-TYPE
                SYNTAX PhivCircuitExportAreaEntry
                ACCESS not-accessible
                STATUS mandatory
                DESCRIPTION
                    "Parameter values for an export area filter."
                INDEX { phivCircuitExportAreaIf,
                        phivCircuitExportAreaAddr,
                        phivCircuitExportAreaMask }
                ::= { phivCircuitExportAreaTable 1 }

            PhivCircuitExportAreaEntry ::=
                SEQUENCE {
                    phivCircuitExportAreaIf
                        INTEGER,
                    phivCircuitExportAreaAddr
                        PhivAddr,
                    phivCircuitExportAreaMask
                        PhivAddr,
                    phivCircuitExportAreaAction
                        INTEGER,
                    phivCircuitExportAreaStatus
                        INTEGER
                }

            phivCircuitExportAreaIf OBJECT-TYPE
                SYNTAX INTEGER
                ACCESS read-only
                STATUS mandatory
                DESCRIPTION
                    "The interface associated with the export area 
                    routing filter."
                ::= { phivCircuitExportAreaEntry 1 }

            phivCircuitExportAreaAddr OBJECT-TYPE
                SYNTAX PhivAddr
                ACCESS read-only
                STATUS mandatory
                DESCRIPTION
                    "The address (node or area) to match against learned 
                    route entries to decide whether to export the entry 
                    to the routing database."
                ::= { phivCircuitExportAreaEntry 2 }

            phivCircuitExportAreaMask OBJECT-TYPE
                SYNTAX PhivAddr
                ACCESS read-only
                STATUS mandatory
                DESCRIPTION
                    "The mask which is ANDed with the address field as 
                    well as the route entries address to determine 
                    whether the address matches the route entry."
                ::= { phivCircuitExportAreaEntry 3 }

            phivCircuitExportAreaAction OBJECT-TYPE
                SYNTAX INTEGER { hide(1), advertise(2) }
                ACCESS read-write
                STATUS mandatory
                DESCRIPTION
                    "The action to take if the address field along with 
                    the mask field matches the route entry."
                DEFVAL { advertise }
                ::= { phivCircuitExportAreaEntry 4 }

            phivCircuitExportAreaStatus OBJECT-TYPE
                SYNTAX INTEGER { invalid(1), valid(2) }
                ACCESS read-write
                STATUS mandatory
                DESCRIPTION
                    "Setting to 'invalid' removes this export area 
                    filter from the table.  Setting to 'valid' has no 
                    effect."
                DEFVAL { valid }
                ::= { phivCircuitExportAreaEntry 5 }


            -- the Phase IV Filters subgroup

            phivCircuitFilterTable OBJECT-TYPE
                SYNTAX SEQUENCE OF PhivCircuitFilterEntry
                ACCESS not-accessible
                STATUS mandatory
                DESCRIPTION
                    "A list of circuit filter entries."
                ::= { xPhivFilter 1 }

            phivCircuitFilterEntry OBJECT-TYPE
                SYNTAX PhivCircuitFilterEntry
                ACCESS not-accessible
                STATUS mandatory
                DESCRIPTION
                    "Parameter values for a filter."
                INDEX { phivCircuitFilterIf,
                        phivCircuitFilterDstAddr,
                        phivCircuitFilterDstMask,
                        phivCircuitFilterSrcAddr,
                        phivCircuitFilterSrcMask }
                ::= { phivCircuitFilterTable 1 }

            PhivCircuitFilterEntry ::=
                SEQUENCE {
                    phivCircuitFilterIf
                        INTEGER,
                    phivCircuitFilterDstAddr
                        PhivAddr,
                    phivCircuitFilterDstMask
                        PhivAddr,
                    phivCircuitFilterSrcAddr
                        PhivAddr,
                    phivCircuitFilterSrcMask
                        PhivAddr,
                    phivCircuitFilterAction
                        INTEGER,
                    phivCircuitFilterStatus
                        INTEGER
                }

            phivCircuitFilterIf OBJECT-TYPE
                SYNTAX INTEGER
                ACCESS read-only
                STATUS mandatory
                DESCRIPTION
                    "The interface associated with the filter entry."
                ::= { phivCircuitFilterEntry 1 }

            phivCircuitFilterDstAddr OBJECT-TYPE
                SYNTAX PhivAddr
                ACCESS read-only
                STATUS mandatory
                DESCRIPTION
                    "The address (node or area) to match against the 
                    destination address of the packet to decide whether 
                    to forward the packet."
                ::= { phivCircuitFilterEntry 2 }

            phivCircuitFilterDstMask OBJECT-TYPE
                SYNTAX PhivAddr
                ACCESS read-only
                STATUS mandatory
                DESCRIPTION
                    "The mask which is ANDed with the destination 
                    address field and the packet's destination address 
                    to determine whether the address matches the 
                    packet's address."
                ::= { phivCircuitFilterEntry 3 }

            phivCircuitFilterSrcAddr OBJECT-TYPE
                SYNTAX PhivAddr
                ACCESS read-only
                STATUS mandatory
                DESCRIPTION
                    "The address (node or area) to match against the 
                    source address of the packet to decide whether to 
                    forward the packet."
                ::= { phivCircuitFilterEntry 4 }

            phivCircuitFilterSrcMask OBJECT-TYPE
                SYNTAX PhivAddr
                ACCESS read-only
                STATUS mandatory
                DESCRIPTION
                    "The mask which is ANDed with the source address 
                    field and the packet's source address to determine 
                    whether the address matches the packet's address."
                ::= { phivCircuitFilterEntry 5 }

            phivCircuitFilterAction OBJECT-TYPE
                SYNTAX INTEGER { discard(1), forward(2) }
                ACCESS read-write
                STATUS mandatory
                DESCRIPTION
                    "The action to take if the address fields along with 
                    the mask fields match the packet."
                DEFVAL { forward }
                ::= { phivCircuitFilterEntry 6 }

            phivCircuitFilterStatus OBJECT-TYPE
                SYNTAX INTEGER { invalid(1), valid(2) }
                ACCESS read-write
                STATUS mandatory
                DESCRIPTION
                    "Setting to 'invalid' removes this Filter filter 
                    from the table.  Setting to 'valid' has no effect."
                DEFVAL { valid }
                ::= { phivCircuitFilterEntry 7 }


            -- the Phase IV Traffic subgroup

            phivTrafficSort OBJECT-TYPE
                SYNTAX INTEGER { ready(1), execute(2) }
                ACCESS read-write
                STATUS mandatory
                DESCRIPTION
                    "Setting to 'execute' causes the most recent traffic 
                    information to be sorted into the phivTrafficTable. 
                    The sorting precedence is: decreasing percentage, 
                    increasing destination address, increasing source 
                    address, and increasing interface number.  Setting 
                    to 'ready' has no effect."
                ::= { xPhivTraffic 1 }

            phivTrafficTable OBJECT-TYPE
                SYNTAX SEQUENCE OF PhivTrafficEntry
                ACCESS not-accessible
                STATUS mandatory
                DESCRIPTION
                    "A list of traffic entries, sorted in the order 
                    specified by phivTrafficSort."
                ::= { xPhivTraffic 2 }

            phivTrafficEntry OBJECT-TYPE
                SYNTAX PhivTrafficEntry
                ACCESS not-accessible
                STATUS mandatory
                DESCRIPTION
                    "A traffic entry."
                INDEX { phivTrafficIndex }
                ::= { phivTrafficTable 1 }

            PhivTrafficEntry ::=
                SEQUENCE {
                    phivTrafficIndex
                        INTEGER,
                    phivTrafficPercent
                        INTEGER,
                    phivTrafficDst
                        PhivAddr,
                    phivTrafficSrc
                        PhivAddr,
                    phivTrafficIf
                        INTEGER
                }

            phivTrafficIndex OBJECT-TYPE
                SYNTAX INTEGER
                ACCESS read-only
                STATUS mandatory
                DESCRIPTION
                    "Identification of this traffic entry."
                ::= { phivTrafficEntry 1 }

            phivTrafficPercent OBJECT-TYPE
                SYNTAX INTEGER (0..1000)
                ACCESS read-only
                STATUS mandatory
                DESCRIPTION
                    "The percentage of total traffic that this traffic 
                    entry represents, in tenths of a percent."
                ::= { phivTrafficEntry 2 }

            phivTrafficDst OBJECT-TYPE
                SYNTAX PhivAddr
                ACCESS read-only
                STATUS mandatory
                DESCRIPTION
                    "The destination to which the traffic entry 
                    applies."
                ::= { phivTrafficEntry 3 }

            phivTrafficSrc OBJECT-TYPE
                SYNTAX PhivAddr
                ACCESS read-only
                STATUS mandatory
                DESCRIPTION
                    "The source to which the traffic entry applies."
                ::= { phivTrafficEntry 4 }

            phivTrafficIf OBJECT-TYPE
                SYNTAX INTEGER
                ACCESS read-only
                STATUS mandatory
                DESCRIPTION
                    "The inbound interface to which the traffic entry 
                    applies.  This value is the same as IfIndex."
                ::= { phivTrafficEntry 5 }


--
-- FILE: /users/sse/mibs/src/itouch/it-ethernet-mib.mib
--

-- $Id: it-ethernet-mib.mib,v 1.1 2000/07/25 14:19:16 sse Exp $


            xEthernet        OBJECT IDENTIFIER ::= { iTouch 11 }

            -- This is the MIB module for iTouch Ethernet interfaces.

            -- Copyright 2000 iTouch Communications, Inc. All Rights Reserved.
            -- Reproduction of this document is authorized on
            -- condition that this copyright notice is included.
            -- This MIB document embodies iTouch Communications, Inc.'s 
            -- proprietary intellectual property.  iTouch Communications, Inc.
            -- retains all title and ownership in this MIB, including any
            -- revisions.
            --
            -- It is iTouch Communications, Inc.'s intent to encourage the
            -- widespread use of this MIB in connection with the management of
            -- iTouch Communications, Inc. products. iTouch Communications,
            -- Inc. grants vendors,end-users, and other interested parties a
            -- non-exclusive license to use this MIB in connection with the
            -- management of iTouch Communications, Inc. products.
            --
            -- This MIB document is supplied "AS IS," and iTouch 
            -- Communications, Inc. makes no warranty, either express or
            -- implied, as to the use operation, condition, or performance of
            -- the MIB.


            -- the Generic Ethernet group

            -- Implementation of this group is mandatory for all iTouch
            -- systems that have an Ethernet interface

            etherTable OBJECT-TYPE
                SYNTAX SEQUENCE OF EtherEntry
                ACCESS not-accessible
                STATUS mandatory
                DESCRIPTION
                    "A list of generic entries."
                ::= { xEthernet 1 }

            etherEntry OBJECT-TYPE
                SYNTAX EtherEntry
                ACCESS not-accessible
                STATUS mandatory
                DESCRIPTION
                    "Generic status and parameter values for an Ethernet 
                    interface."
                INDEX { etherIndex }
                ::= { etherTable 1 }

            EtherEntry ::=
                SEQUENCE {
                    etherIndex
                        INTEGER,
                    etherAlignmentErrors
                        Counter,
                    etherFCSErrors
                        Counter
                }

            etherIndex OBJECT-TYPE
                SYNTAX INTEGER
                ACCESS read-only
                STATUS mandatory
                DESCRIPTION
                    "An index value that uniquely identifies an Ethernet 
                    interface.  The interface identified by a particular 
                    value of this index is the same interface as 
                    identified by the same value of ifIndex."
                ::= { etherEntry 1 }

            etherAlignmentErrors OBJECT-TYPE
                SYNTAX Counter
                ACCESS read-only
                STATUS mandatory
                DESCRIPTION
                    "A count of frames received on a particular 
                    interface that are not an integral number of octets 
                    in length and do not pass the FCS check."
                ::= { etherEntry 2 }

            etherFCSErrors OBJECT-TYPE
                SYNTAX Counter
                ACCESS read-only
                STATUS mandatory
                DESCRIPTION
                    "A count of frames received on a particular 
                    interface that are an integral number of octets in 
                    length that do not pass the FCS check."
                ::= { etherEntry 3 }


            -- the Ethernet Transmit group

            -- Implementation of this group is mandatory for all iTouch
            -- systems that transmit messages on an Ethernet interface

            etherTxTable OBJECT-TYPE
                SYNTAX SEQUENCE OF EtherTxEntry
                ACCESS not-accessible
                STATUS mandatory
                DESCRIPTION
                    "A list of Ethernet transmit entries."
                ::= { xEthernet 2 }

            etherTxEntry OBJECT-TYPE
                SYNTAX EtherTxEntry
                ACCESS not-accessible
                STATUS mandatory
                DESCRIPTION
                    "Transmit status and parameter values for an 
                    Ethernet interface."
                INDEX { etherTxIndex }
                ::= { etherTxTable 1 }

            EtherTxEntry ::=
                SEQUENCE {
                    etherTxIndex
                        INTEGER,
                    etherTxSingleCollisionFrames
                        Counter,
                    etherTxMultipleCollisionFrames
                        Counter
                }

            etherTxIndex OBJECT-TYPE
                SYNTAX INTEGER
                ACCESS read-only
                STATUS mandatory
                DESCRIPTION
                    "An index value that uniquely identifies an Ethernet 
                    interface.  The interface identified by a particular 
                    value of this index is the same interface as 
                    identified by the same value of ifIndex."
                ::= { etherTxEntry 1 }

            etherTxSingleCollisionFrames OBJECT-TYPE
                SYNTAX Counter
                ACCESS read-only
                STATUS mandatory
                DESCRIPTION
                    "A count of successfully transmitted frames on a 
                    particular interface for which transmission is 
                    inhibited by exactly one collision.  A frame that is 
                    counted by an instance of this object is also 
                    counted by the corresponding instance of either the 
                    ifOutUcastPkts or ifOutNUcastPkts object and is not 
                    counted by the corresponding instance of the 
                    etherTxMultipleCollisionFrames object."
                ::= { etherTxEntry 2 }

            etherTxMultipleCollisionFrames OBJECT-TYPE
                SYNTAX Counter
                ACCESS read-only
                STATUS mandatory
                DESCRIPTION
                    "A count of successfully transmitted frames on a 
                    particular interface for which transmission is 
                    inhibited by more than one collision.  A frame that 
                    is counted by an instance of this object is also 
                    counted by the corresponding instance of either the 
                    ifOutUcastPkts or ifOutNUcastPkts object and is not 
                    counted by the corresponding instance of the 
                    etherTxSingleCollisionFrames object."
                ::= { etherTxEntry 3 }


            -- the Ethernet Multicast group

            -- Implementation of this group is optional;  it is
            -- appropriate for all iTouch systems on which the
            -- necessary monitoring is feasible

            etherMulticastTable OBJECT-TYPE
                SYNTAX SEQUENCE OF EtherMulticastEntry
                ACCESS not-accessible
                STATUS mandatory
                DESCRIPTION
                    "A list of etherMulticast entries."
                ::= { xEthernet 3 }

            etherMulticastEntry OBJECT-TYPE
                SYNTAX EtherMulticastEntry
                ACCESS not-accessible
                STATUS mandatory
                DESCRIPTION
                    "EtherMulticast status and parameter values for an 
                    Ethernet interface."
                INDEX { etherMulticastIndex }
                ::= { etherMulticastTable 1 }

            EtherMulticastEntry ::=
                SEQUENCE {
                    etherMulticastIndex
                        INTEGER,
                    etherMulticastBytesIn
                        Counter,
                    etherMulticastBytesOut
                        Counter
                }

            etherMulticastIndex OBJECT-TYPE
                SYNTAX INTEGER
                ACCESS read-only
                STATUS mandatory
                DESCRIPTION
                    "An index value that uniquely identifies an Ethernet 
                    interface.  The interface identified by a particular 
                    value of this index is the same interface as 
                    identified by the same value of ifIndex."
                ::= { etherMulticastEntry 1 }

            etherMulticastBytesIn OBJECT-TYPE
                SYNTAX Counter
                ACCESS read-only
                STATUS mandatory
                DESCRIPTION
                    "A count of frames successfully received on a 
                    particular interface and for which the destination 
                    address multicast bit was set.  Bytes that are 
                    counted by an instance of this object are also 
                    counted by the corresponding instance of the 
                    ifInOctets object."
                ::= { etherMulticastEntry 2 }

            etherMulticastBytesOut OBJECT-TYPE
                SYNTAX Counter
                ACCESS read-only
                STATUS mandatory
                DESCRIPTION
                    "A count of successfully frames successfully 
                    transmitted on a particular interface and for which 
                    the destination address multicast bit was set.  
                    Bytes that are counted by an instance of this object 
                    are also counted by the corresponding instance of 
                    the ifOutOctets object."
                ::= { etherMulticastEntry 3 }


            -- the Ethernet Extended Transmit group

            -- Implementation of this group is optional;  it is
            -- appropriate for all iTouch systems on which the
            -- necessary monitoring is feasible

            etherXTxTable OBJECT-TYPE
                SYNTAX SEQUENCE OF EtherXTxEntry
                ACCESS not-accessible
                STATUS mandatory
                DESCRIPTION
                    "A list of Ethernet extended transmit entries."
                ::= { xEthernet 4 }

            etherXTxEntry OBJECT-TYPE
                SYNTAX EtherXTxEntry
                ACCESS not-accessible
                STATUS mandatory
                DESCRIPTION
                    "Extended transmit status and parameter values for 
                    an Ethernet interface."
                INDEX { etherXTxIndex }
                ::= { etherXTxTable 1 }

            EtherXTxEntry ::=
                SEQUENCE {
                    etherXTxIndex
                        INTEGER,
                    etherXTxExcessiveCollisions
                        Counter
                }

            etherXTxIndex OBJECT-TYPE
                SYNTAX INTEGER
                ACCESS read-only
                STATUS mandatory
                DESCRIPTION
                    "An index value that uniquely identifies an Ethernet 
                    interface.  The interface identified by a particular 
                    value of this index is the same interface as 
                    identified by the same value of ifIndex."
                ::= { etherXTxEntry 1 }

            etherXTxExcessiveCollisions OBJECT-TYPE
                SYNTAX Counter
                ACCESS read-only
                STATUS mandatory
                DESCRIPTION
                    "A count of frames for which transmission on a 
                    particular interface fails due to excessive 
                    collisions."
                ::= { etherXTxEntry 2 }


--
-- FILE: /users/sse/mibs/src/itouch/it-frame-relay-mib.mib
--

-- $Id: it-frame-relay-mib.mib,v 1.1 2000/07/25 14:06:05 sse Exp $

       xFrameRelay     OBJECT IDENTIFIER ::= { iTouch 23 }

      
            -- This is a MIB module for all iTouch Communications systems that
            -- implement frame relay.

            -- Copyright 2000 iTouch Communications, Inc. All Rights Reserved.
            -- Reproduction of this document is authorized on
            -- condition that this copyright notice is included.
            -- This MIB document embodies iTouch Communications, Inc.'s 
            -- proprietary intellectual property.  iTouch Communications, Inc.
            -- retains all title and ownership in this MIB, including any
            -- revisions.
            --
            -- It is iTouch Communications, Inc.'s intent to encourage the
            -- widespread use of this MIB in connection with the management of
            -- iTouch Communications, Inc. products. iTouch Communications,
            -- Inc. grants vendors,end-users, and other interested parties a
            -- non-exclusive license to use this MIB in connection with the
            -- management of iTouch Communications, Inc. products.
            --
            -- This MIB document is supplied "AS IS," and iTouch 
            -- Communications, Inc. makes no warranty, either express or
            -- implied, as to the use operation, condition, or performance of
            -- the MIB.


       -- the Frame Relay Circuit table

       -- Implementation of this group is mandatory for all iTouch
       -- systems that implement frame relay

       xFrCircuitTable OBJECT-TYPE
           SYNTAX SEQUENCE OF XFrCircuitEntry
           ACCESS not-accessible
           STATUS mandatory
           DESCRIPTION
               "A table containing iTouch extensions to the 
               standard Frame Relay Circuit table."
           ::= { xFrameRelay 1 }

       xFrCircuitEntry OBJECT-TYPE
           SYNTAX XFrCircuitEntry
           ACCESS not-accessible
           STATUS mandatory
           DESCRIPTION
               "Entry parameters."
           INDEX { frCircuitIfIndex, frCircuitDlci }
           ::= { xFrCircuitTable 1 }

       XFrCircuitEntry ::=
           SEQUENCE {
               xFrCircuitIf
                   INTEGER
           }

       xFrCircuitIf OBJECT-TYPE
           SYNTAX INTEGER
           ACCESS read-write
           STATUS mandatory
           DESCRIPTION
               "The ifIndex value of the corresponding ifEntry, 
               that is, the interface to which the DLCI is 
               attached."
           ::= { xFrCircuitEntry 1 }


--
-- FILE: /users/sse/mibs/src/itouch/it-internet-mib.mib
--

-- $Id: it-internet-mib.mib,v 1.5 2001/05/08 13:35:22 sse Exp $


            xInternetDep    OBJECT IDENTIFIER ::= { iTouch 4 }
            xInternet       OBJECT IDENTIFIER ::= { iTouch 10 }

            -- ITouch Internet subgroups

            xIp             OBJECT IDENTIFIER ::= { xInternet 1 }
            xTcp            OBJECT IDENTIFIER ::= { xInternet 2 }
            xSnmpAgent      OBJECT IDENTIFIER ::= { xInternet 3 }
            xDomainResolver OBJECT IDENTIFIER ::= { xInternet 4 }
            xSlip           OBJECT IDENTIFIER ::= { xInternet 5 }
            xTelnet         OBJECT IDENTIFIER ::= { xInternet 6 }
            xTn3270         OBJECT IDENTIFIER ::= { xInternet 7 }
            xKerberos       OBJECT IDENTIFIER ::= { xInternet 8 }
            xPortSecurity   OBJECT IDENTIFIER ::= { xInternet 9 }
            xXremote        OBJECT IDENTIFIER ::= { xInternet 10 }
            xRotary         OBJECT IDENTIFIER ::= { xInternet 11 }
            xEgp            OBJECT IDENTIFIER ::= { xInternet 12 }
            xOspf           OBJECT IDENTIFIER ::= { xInternet 13 }
            xRouterIp       OBJECT IDENTIFIER ::= { xInternet 14 }
            xRouterUdp      OBJECT IDENTIFIER ::= { xInternet 15 }
            xRouterPolicy   OBJECT IDENTIFIER ::= { xInternet 16 }
            -- number 17 reserved
            xRip            OBJECT IDENTIFIER ::= { xInternet 18 }
            xlpd            OBJECT IDENTIFIER ::= { xInternet 19 }
            xSecurID        OBJECT IDENTIFIER ::= { xInternet 20 }
            -- numbers 21, 22 reserved
            xSsh            OBJECT IDENTIFIER ::= { xInternet 23 }


            -- This is a MIB module for all iTouch Communications systems that
            -- implement IP.

            -- Copyright 2000 iTouch Communications, Inc. All Rights Reserved.
            -- Reproduction of this document is authorized on
            -- condition that this copyright notice is included.
            -- This MIB document embodies iTouch Communications, Inc.'s 
            -- proprietary intellectual property.  iTouch Communications, Inc.
            -- retains all title and ownership in this MIB, including any
            -- revisions.
            --
            -- It is iTouch Communications, Inc.'s intent to encourage the
            -- widespread use of this MIB in connection with the management of
            -- iTouch Communications, Inc. products. iTouch Communications,
            -- Inc. grants vendors,end-users, and other interested parties a
            -- non-exclusive license to use this MIB in connection with the
            -- management of iTouch Communications, Inc. products.
            --
            -- This MIB document is supplied "AS IS," and iTouch 
            -- Communications, Inc. makes no warranty, either express or
            -- implied, as to the use operation, condition, or performance of
            -- the MIB.


            -- the IP group

            -- Implementation of this group is mandatory for all iTouch
            -- systems that implement IP

            ipGatewayAddress1 OBJECT-TYPE
                SYNTAX IpAddress
                ACCESS read-write
                STATUS mandatory
                DESCRIPTION
                    "The internet address of the system's primary (first 
                    choice) gateway.  A value of 0.0.0.0 indicates no 
                    address.  Corresponds directly to SERVER INTERNET 
                    PRIMARY GATEWAY ADDRESS and the value labeled 
                    'Primary Gateway Address:' in the SERVER INTERNET 
                    CHARACTERISTICS display."
                ::= { xIp 1 }

            ipGatewayAddress2 OBJECT-TYPE
                SYNTAX IpAddress
                ACCESS read-write
                STATUS mandatory
                DESCRIPTION
                    "The internet address of the system's secondary 
                    (second choice) gateway.  A value of 0.0.0.0 
                    indicates no address.  Corresponds directly to 
                    SERVER INTERNET SECONDARY GATEWAY ADDRESS and the 
                    value labeled 'Secondary Gateway Address:' in the 
                    SERVER INTERNET CHARACTERISTICS display."
                ::= { xIp 2 }

            ipAutoSubnetMask OBJECT-TYPE
                SYNTAX INTEGER { disabled(1), enabled(2) }
                ACCESS read-write
                STATUS deprecated
                DESCRIPTION
                    "A control for automatic determination of subnet 
                    mask.  'disabled' indicates the system must use the 
                    mask as configured by the network manager.  
                    'enabled' indicates that the system is to 
                    automatically change the subnet mask when the 
                    system's Internet address is changed.  Corresponds 
                    directly to SERVER INTERNET SUBNET MASK 
                    AUTOCONFIGURE and the value labeled 'Subnet Mask 
                    Autoconfigure:' in the SERVER INTERNET 
                    CHARACTERISTICS display."
                ::= { xIp 3 }

            ipReassembly OBJECT-TYPE
                SYNTAX INTEGER { disabled(1), enabled(2) }
                ACCESS read-write
                STATUS mandatory
                DESCRIPTION
                    "A control for reassembly of IP fragments.  
                    Corresponds directly to SERVER INTERNET REASSEMBLY 
                    and the value labeled 'Reassembly:' in the SERVER 
                    INTERNET CHARACTERISTICS display."
                ::= { xIp 4 }

            ipFragmentsQueuedHigh OBJECT-TYPE
                SYNTAX Gauge
                ACCESS read-only
                STATUS mandatory
                DESCRIPTION
                    "Highest number of IP fragments queued."
                ::= { xIp 5 }

            ipFragmentsQueuedCurrent OBJECT-TYPE
                SYNTAX Gauge
                ACCESS read-only
                STATUS mandatory
                DESCRIPTION
                    "Current number of IP fragments queued."
                ::= { xIp 6 }

            ipGenAdExtTable OBJECT-TYPE
                SYNTAX SEQUENCE OF IpGenAdExtEntry
                ACCESS not-accessible
                STATUS mandatory
                DESCRIPTION
                    "Table of additional fields indexed by local IP 
                    address.  An entry in this table is created or 
                    deleted when an entry in the MIB-II ipAddrTable is 
                    created or deleted.  Although MIB-II specifies the 
                    ipAddrTable as read-only, iTouch implementations 
                    typically implement it as read-write to support 
                    modification of local IP addresses, network masks, 
                    and such."
                ::= { xIp 7 }

            ipARPTimeout OBJECT-TYPE
                SYNTAX INTEGER (1..255)
                ACCESS read-write
                STATUS mandatory 
                DESCRIPTION
                    "A control to set the length of time in minutes 
                    before an unused ARP entry is purged from the ARP 
                    table. The default is 60 minutes. Corresponds
                    directly to the value labeled 'Translation Table TTL'
                    in the SERVER INTERNET CHARACTERISTICS display."
                ::= { xIp 8 } 

            ipGatewayPingInterval OBJECT-TYPE
                SYNTAX INTEGER (1..300)
                ACCESS read-write
                STATUS mandatory 
                DESCRIPTION
                    "A control to set the interval of time in seconds
                    between successive pings to the primary gateway
                    so as to determine its status.
                    The default is 60 seconds. Corresponds
                    directly to the value labeled 'Gateway Timeout'
                    in the SERVER INTERNET CHARACTERISTICS display."
                ::= { xIp 9 } 

 	ipConfigureBootp OBJECT-TYPE
		SYNTAX INTEGER { disabled(1), enabled(2) }
		ACCESS read-write
		STATUS mandatory
		DESCRIPTION
		    "Control to use the BOOTP protocol upon startup to learn
                     the unit's own internet address, subnet mask, primary and 
                     secondary gateway servers, domain name servers, time 
                     server and domain name."
		DEFVAL { enabled }
		::= { xIp 11 }

            -- the Generic Address Extensions table

            ipGenAdExtEntry OBJECT-TYPE
                SYNTAX IpGenAdExtEntry
                ACCESS not-accessible
                STATUS mandatory
                DESCRIPTION
                    "A particular entry."
                INDEX { ipAdEntAddr }
                ::= { ipGenAdExtTable 1 }

            IpGenAdExtEntry ::=
                SEQUENCE {
                    ipGenAdEntExtType
                        INTEGER,
                    ipGenAdEntExtBroadcast
                        IpAddress
                }

            ipGenAdEntExtType OBJECT-TYPE
                SYNTAX INTEGER { primary(1), rotary(2), slip(3),
                                 ppp(4) }
                ACCESS read-write
                STATUS mandatory
                DESCRIPTION
                    "The way this local IP address is used, which may 
                    imply alternate, more intuitive ways to set it.

                    primary   general purpose for ordinary use
                    rotary    identificaton for rotary selection
                    slip      use for SLIP connection
                    ppp       use for PPP connection
                    "
                DEFVAL { primary }
                ::= { ipGenAdExtEntry 1 }

            ipGenAdEntExtBroadcast OBJECT-TYPE
                SYNTAX IpAddress
                ACCESS read-write
                STATUS mandatory
                DESCRIPTION
                    "Outgoing IP broadcast address associated with this 
                    local address.  Value may be confined to logical 
                    compatibility with associated network mask."
                DEFVAL { 'ffffffff'h }    -- 255.255.255.255
                ::= { ipGenAdExtEntry 2 }


            -- the TCP group

            -- Implementation of this group is mandatory for all iTouch
            -- systems that implement TCP

            -- scalar parameters follow Port table

            -- the TCP Character Port table

            tcpPortTable OBJECT-TYPE
                SYNTAX SEQUENCE OF TcpPortEntry
                ACCESS not-accessible
                STATUS mandatory
                DESCRIPTION
                    "A list of TCP character port entries."
                ::= { xTcp 1 }

            tcpPortEntry OBJECT-TYPE
                SYNTAX TcpPortEntry
                ACCESS not-accessible
                STATUS mandatory
                DESCRIPTION
                    "TCP parameter values for a character port."
                INDEX { tcpPortIndex }
                ::= { tcpPortTable 1 }

            TcpPortEntry ::=
                SEQUENCE {
                    tcpPortIndex
                        INTEGER,
                    tcpPortConnectByAddress
                        INTEGER,
                    tcpPortWindowSize
                        INTEGER,
                    tcpPortKeepAliveLimit
                        INTEGER
                }

            tcpPortIndex OBJECT-TYPE
                SYNTAX INTEGER
                ACCESS read-only
                STATUS mandatory
                DESCRIPTION
                    "An index value that uniquely identifies a port.  
                    The port identified by a particular value of this 
                    index is the same port as identified by 
                    charPortIndex in the Proposed Standard Internet 
                    Character MIB."
                ::= { tcpPortEntry 1 }

            tcpPortConnectByAddress OBJECT-TYPE
                SYNTAX INTEGER { disabled(1), enabled(2) }
                ACCESS read-write
                STATUS mandatory
                DESCRIPTION
                    "A control for requesting outgoing connection by 
                    internet address.  'disabled' indicates outgoing 
                    connections must be by Domain name.  'enabled' 
                    indicates that outgoing connections may be requested 
                    by internet address.  Corresponds directly to PORT 
                    INTERNET CONNECTIONS and the presence of the label 
                    'Internet Connections' following the label 'Enabled 
                    Characteristics:' in the PORT CHARACTERISTICS 
                    display."
                ::= { tcpPortEntry 2 }

            tcpPortWindowSize OBJECT-TYPE
                SYNTAX INTEGER (64..8192)
                ACCESS read-write
                STATUS mandatory
                DESCRIPTION
                    "Size of the TCP window for TCP connections on the 
                    port.  Corresponds directly to PORT INTERNET TCP 
                    WINDOW SIZE and the value labeled 'TCP Window Size:' 
                    in the PORT ALTERNATE CHARACTERISTICS display."
                ::= { tcpPortEntry 3 }

            tcpPortKeepAliveLimit OBJECT-TYPE
                SYNTAX INTEGER (0..30)
                ACCESS read-write
                STATUS mandatory
                DESCRIPTION
                    "Number of minutes to maintain a TCP connection 
                    without response to keep-alive communication.  A 
                    value of zero indicates no limit."
                ::= { tcpPortEntry 4 }

            -- additional scalar parameters

            tcpResequencing OBJECT-TYPE
                SYNTAX INTEGER { disabled(1), enabled(2) }
                ACCESS read-write
                STATUS mandatory
                DESCRIPTION
                    "A control for keeping TCP messages received 
                    out-of-order to resequence them before using them.   
                    Corresponds directly to SERVER INTERNET TCP 
                    RESEQUENCING and the value labeled 'Resequencing:' 
                    in the SERVER INTERNET CHARACTERISTICS display."
                ::= { xTcp 2 }

            tcpQueuedSegs OBJECT-TYPE
                SYNTAX Gauge
                ACCESS read-only
                STATUS mandatory
                DESCRIPTION
                    "Number of TCP segments in the TCP receive queues.  
                    Corresponds directly to the value labeled 'TCP 
                    Packets Queued:' in the SERVER INTERNET COUNTERS 
                    display."
                ::= { xTcp 3 }

            tcpDiscardSegs OBJECT-TYPE
                SYNTAX Counter
                ACCESS read-only
                STATUS mandatory
                DESCRIPTION
                    "Number of TCP segments discarded due to exceeding 
                    the TCP receive queue limit.  Corresponds directly 
                    to the value labeled 'TCP Packets Discarded:' in the 
                    SERVER INTERNET COUNTERS display."
                ::= { xTcp 4 }

            tcpConnectTimer OBJECT-TYPE
                SYNTAX INTEGER (4..32)
                ACCESS read-write
                STATUS mandatory
                DESCRIPTION
                    "Number of seconds to attempt a TCP connection 
                    without a response from the other side. The default 
                    value is 32 seconds.  Corresponds directly to the 
                    SERVER INTERNET TCP CONNECT TIMER and the value 
                    labeled 'TCP Connect Timer' in the SERVER INTERNET 
                    CHARACTERISTICS display"
                ::= { xTcp 5 }

            tcpLocalPortBase OBJECT-TYPE
                SYNTAX INTEGER (1..32767)
                ACCESS read-write
                STATUS mandatory
                DESCRIPTION
                    "The value for port 0's tcp source port number."
                ::= { xTcp 6 }

            tcpLocalPortIncrement OBJECT-TYPE
                SYNTAX INTEGER (1..1024)
                ACCESS read-write
                STATUS mandatory
                DESCRIPTION
                    "The value by which the tcp source port number
                    increases for each port greater than port 0."
                ::= { xTcp 7 }

            tcpRoutingTblSz OBJECT-TYPE
                SYNTAX INTEGER (64..512)
                ACCESS read-write
                STATUS mandatory 
                DESCRIPTION
                    "A control to set the size of the working routing table.
                    The default is the current size of the table (64)."
                ::= {xTcp 8  } 

            tcpDataSendDelay OBJECT-TYPE
                SYNTAX INTEGER (0..3000)
                ACCESS read-write
                STATUS mandatory 
                DESCRIPTION
                    "A control to delay for the specified number of 10
                     millisecond ticks before sending the userdata string
                     over the telnet connection."
                DEFVAL { 50 }
                ::= {xTcp 9  } 

             tcpAckDelay OBJECT-TYPE
                SYNTAX INTEGER { disabled(1), enabled(2) }
                ACCESS read-write
                STATUS mandatory
                DESCRIPTION
                    "A Control to prevent sending a TCP ACK when we
                     we change TCP window size."
                DEFVAL { disabled }
                ::= {xTcp 10 }

             tcpRetransmitMin OBJECT-TYPE
                SYNTAX INTEGER (600..3000)
                ACCESS read-write
                STATUS mandatory
                DESCRIPTION
                    "Number of milliseconds for the initial TCP Retransmit
                     timer. This is the time at which a TCP session will
                     initially retransmit unacknowledged packets."
                DEFVAL { 640 }
                ::= {xTcp 11 }


             -- the SNMP Agent group

            -- Implementation of this group is mandatory for all iTouch
            -- systems that implement SNMP

            snmpAgentGetCommunity OBJECT-TYPE
                SYNTAX DisplayString (SIZE (0..32))
                ACCESS read-write
                STATUS mandatory
                DESCRIPTION
                    "The SNMP community name allowed to perform 
                    get-requests or get-next requests to this agent.  
                    Use of this value is case-insensitive.  If the size 
                    is 0, the agent does not check the community name 
                    for these operations.  Corresponds directly to 
                    SERVER INTERNET SNMP GET COMMUNITY and the value 
                    labeled 'Get Community:' in the SERVER INTERNET SNMP 
                    CHARACTERISTICS display."
                ::= { xSnmpAgent 1 }

            snmpAgentSetCommunity OBJECT-TYPE
                SYNTAX DisplayString (SIZE (0..32))
                ACCESS read-write
                STATUS mandatory
                DESCRIPTION
                    "The SNMP community name allowed to perform 
                    set-requests to this agent.  Use of this value is 
                    case-insensitive.  If the size is 0, the agent does 
                    not check the community name for these operations.  
                    Corresponds directly to SERVER INTERNET SNMP SET 
                    COMMUNITY and the value labeled 'Set Community:' in 
                    the SERVER INTERNET SNMP CHARACTERISTICS display."
                ::= { xSnmpAgent 2 }

            snmpAgentTrapCommunity OBJECT-TYPE
                SYNTAX DisplayString (SIZE (0..32))
                ACCESS read-write
                STATUS mandatory
                DESCRIPTION
                    "The SNMP community name sent in traps from this 
                    agent.  Use of this value preserves case.  
                    Corresponds directly to SERVER INTERNET SNMP TRAP 
                    COMMUNITY and the value labeled 'Trap Community:' in 
                    the SERVER INTERNET SNMP CHARACTERISTICS display."
                ::= { xSnmpAgent 3 }

            snmpAgentGetClientNumber OBJECT-TYPE
                SYNTAX INTEGER
                ACCESS read-only
                STATUS mandatory
                DESCRIPTION
                    "The number of client source addresses allowed to 
                    perform get-requests or get-next requests to this 
                    agent.  If the value is 0, the agent does not check 
                    source address for these operations.  Corresponds 
                    indirectly to the values labeled 'Get Client n:' in 
                    the SERVER INTERNET SNMP CHARACTERISTICS display."
                ::= { xSnmpAgent 4 }

            snmpAgentSetClientNumber OBJECT-TYPE
                SYNTAX INTEGER
                ACCESS read-only
                STATUS mandatory
                DESCRIPTION
                    "The number of client source addresses allowed to 
                    perform set-requests to this agent.  If the value is 
                    0, the agent does not check source address for these 
                    operations.  Corresponds indirectly to the values 
                    labeled 'Set Client n:' in the SERVER INTERNET SNMP 
                    CHARACTERISTICS display."
                ::= { xSnmpAgent 5 }

            snmpAgentTrapClientNumber OBJECT-TYPE
                SYNTAX INTEGER
                ACCESS read-only
                STATUS mandatory
                DESCRIPTION
                    "The number of client source addresses to which this 
                    agent sends traps.  If the value is 0, the agent 
                    does not perform this operation.  Corresponds 
                    indirectly to the values labeled 'Trap Client n:' in 
                    the SERVER INTERNET SNMP CHARACTERISTICS display."
                ::= { xSnmpAgent 6 }

            -- More individual objects follow 
            -- the Get Client table

            getClientTable OBJECT-TYPE
                SYNTAX SEQUENCE OF GetClientEntry
                ACCESS not-accessible
                STATUS mandatory
                DESCRIPTION
                    "A list of get client entries.  The number of 
                    entries is given by the value of 
                    snmpAgentGetClientNumber."
                ::= { xSnmpAgent 7 }

            getClientEntry OBJECT-TYPE
                SYNTAX GetClientEntry
                ACCESS not-accessible
                STATUS mandatory
                DESCRIPTION
                    "Parameter values for a get client."
                INDEX { getClientIndex }
                ::= { getClientTable 1 }

            GetClientEntry ::=
                SEQUENCE {
                    getClientIndex
                        INTEGER,
                    getClientEntryStatus
                        INTEGER,
                    getClientAddressType
                        AddressType,
                    getClientAddress
                        OCTET STRING
                }

            getClientIndex OBJECT-TYPE
                SYNTAX INTEGER
                ACCESS read-only
                STATUS mandatory
                DESCRIPTION
                    "Identification of a get client entry.  Corresponds 
                    directly to the number in the label 'Get Client n:' 
                    in the SERVER INTERNET SNMP CHARACTERISTICS 
                    display."
                ::= { getClientEntry 1 }

            getClientEntryStatus OBJECT-TYPE
                SYNTAX INTEGER { invalid(1), valid(2) }
                ACCESS read-write
                STATUS mandatory
                DESCRIPTION
                    "Status of this entry.  Setting the value to 
                    'invalid' invalidates the entry.  It is an 
                    implementation-specific matter as to whether the 
                    agent removes an invalidated entry from the table."
                DEFVAL { valid }
                ::= { getClientEntry 2 }

            getClientAddressType OBJECT-TYPE
                SYNTAX AddressType
                ACCESS read-write
                STATUS mandatory
                DESCRIPTION
                    "The type of network address contained in 
                    getClientAddress.  'unknown' means no address has 
                    been defined.  'other' means no other type value 
                    applies.  'ip' is an Internet IP address.  
                    'ethernet' is an 802.3 MAC address.  If 
                    getClientAddressType does not accompany 
                    getClientAddress in a set request, the default type 
                    is 'ip'.  Corresponds indirectly to the address 
                    value labeled 'Get Client n:' in the SERVER INTERNET 
                    SNMP CHARACTERISTICS display."
                DEFVAL { unknown }
                ::= { getClientEntry 3 }

            getClientAddress OBJECT-TYPE
                SYNTAX OCTET STRING
                ACCESS read-write
                STATUS mandatory
                DESCRIPTION
                    "The client's network address.  If 
                    getClientAddressType does not accompany 
                    getClientAddress in a set request, the default type 
                    is 'ip'.  Corresponds directly to the address value 
                    labeled 'Get Client n:' in the SERVER INTERNET SNMP 
                    CHARACTERISTICS display."
                DEFVAL { "" }  -- zero length
                ::= { getClientEntry 4 }


            -- the Set Client table

            setClientTable OBJECT-TYPE
                SYNTAX SEQUENCE OF SetClientEntry
                ACCESS not-accessible
                STATUS mandatory
                DESCRIPTION
                    "A list of set client entries.  The number of 
                    entries is given by the value of 
                    snmpAgentSetClientNumber."
                ::= { xSnmpAgent 8 }

            setClientEntry OBJECT-TYPE
                SYNTAX SetClientEntry
                ACCESS not-accessible
                STATUS mandatory
                DESCRIPTION
                    "Parameter values for a set client."
                INDEX { setClientIndex }
                ::= { setClientTable 1 }

            SetClientEntry ::=
                SEQUENCE {
                    setClientIndex
                        INTEGER,
                    setClientEntryStatus
                        INTEGER,
                    setClientAddressType
                        AddressType,
                    setClientAddress
                        OCTET STRING
                }

            setClientIndex OBJECT-TYPE
                SYNTAX INTEGER
                ACCESS read-only
                STATUS mandatory
                DESCRIPTION
                    "Identification of a set client entry.  Corresponds 
                    directly to the number in the label 'Set Client n:' 
                    in the SERVER INTERNET SNMP CHARACTERISTICS 
                    display."
                ::= { setClientEntry 1 }

            setClientEntryStatus OBJECT-TYPE
                SYNTAX INTEGER { invalid(1), valid(2) }
                ACCESS read-write
                STATUS mandatory
                DESCRIPTION
                    "Status of this entry.  Setting the value to 
                    'invalid' invalidates the entry.  It is an 
                    implementation-specific matter as to whether the 
                    agent removes an invalidated entry from the table."
                DEFVAL { valid }
                ::= { setClientEntry 2 }

            setClientAddressType OBJECT-TYPE
                SYNTAX AddressType
                ACCESS read-write
                STATUS mandatory
                DESCRIPTION
                    "The type of network address contained in 
                    setClientAddress.  'unknown' means no address has 
                    been defined.  'other' means no other type value 
                    applies.  'ip' is an Internet IP address.  
                    'ethernet' is an 802.3 MAC address.  If 
                    setClientAddressType does not accompany 
                    setClientAddress in a set request, the default type 
                    is 'ip'.  Corresponds indirectly to the address 
                    value labeled 'Set Client n:' in the SERVER INTERNET 
                    SNMP CHARACTERISTICS display."
                DEFVAL { unknown }
                ::= { setClientEntry 3 }

            setClientAddress OBJECT-TYPE
                SYNTAX OCTET STRING
                ACCESS read-write
                STATUS mandatory
                DESCRIPTION
                    "The client's network address.  When setting this 
                    value, the requester must supply 
                    setClientAddressType.  If setClientAddressType does 
                    not accompany setClientAddress in a set request, the 
                    default type is 'ip'.  Corresponds directly to the 
                    address value labeled 'Set Client n:' in the SERVER 
                    INTERNET SNMP CHARACTERISTICS display."
                DEFVAL { "" }  -- zero length
                ::= { setClientEntry 4 }


            -- the Trap Client table

            trapClientTable OBJECT-TYPE
                SYNTAX SEQUENCE OF TrapClientEntry
                ACCESS not-accessible
                STATUS mandatory
                DESCRIPTION
                    "A list of trap client entries.  The number of 
                    entries is given by the value of 
                    snmpAgentTrapClientNumber."
                ::= { xSnmpAgent 9 }

            trapClientEntry OBJECT-TYPE
                SYNTAX TrapClientEntry
                ACCESS not-accessible
                STATUS mandatory
                DESCRIPTION
                    "Parameter values for a trap client."
                INDEX { trapClientIndex }
                ::= { trapClientTable 1 }

            TrapClientEntry ::=
                SEQUENCE {
                    trapClientIndex
                        INTEGER,
                    trapClientEntryStatus
                        INTEGER,
                    trapClientAddressType
                        AddressType,
                    trapClientAddress
                        OCTET STRING
                }

            trapClientIndex OBJECT-TYPE
                SYNTAX INTEGER
                ACCESS read-only
                STATUS mandatory
                DESCRIPTION
                    "Identification of a trap client entry.  Corresponds 
                    directly to the number in the label 'Trap Client n:' 
                    in the SERVER INTERNET SNMP CHARACTERISTICS 
                    display."
                ::= { trapClientEntry 1 }

            trapClientEntryStatus OBJECT-TYPE
                SYNTAX INTEGER { invalid(1), valid(2) }
                ACCESS read-write
                STATUS mandatory
                DESCRIPTION
                    "Status of this entry.  Setting the value to 
                    'invalid' invalidates the entry.  It is an 
                    implementation-specific matter as to whether the 
                    agent removes an invalidated entry from the table."
                DEFVAL { valid }
                ::= { trapClientEntry 2 }

            trapClientAddressType OBJECT-TYPE
                SYNTAX AddressType
                ACCESS read-write
                STATUS mandatory
                DESCRIPTION
                    "The type of network address contained in 
                    trapClientAddress.  'unknown' means no address has 
                    been defined.  'other' means no other type value 
                    applies.  'ip' is an Internet IP address.  
                    'ethernet' is an 802.3 MAC address.  If 
                    trapClientAddressType does not accompany 
                    trapClientAddress in a set request, the default type 
                    is 'ip'.  Corresponds indirectly to the address 
                    value labeled 'Trap Client n:' in the SERVER 
                    INTERNET SNMP CHARACTERISTICS display."
                DEFVAL { unknown }
                ::= { trapClientEntry 3 }

            trapClientAddress OBJECT-TYPE
                SYNTAX OCTET STRING
                ACCESS read-write
                STATUS mandatory
                DESCRIPTION
                    "The client's network address.  When setting this 
                    value, the requester must supply 
                    trapClientAddressType.  If trapClientAddressType 
                    does not accompany trapClientAddress in a set 
                    request, the default type is 'ip'.  Corresponds 
                    directly to the address value labeled 'Trap Client 
                    n:' in the SERVER INTERNET SNMP CHARACTERISTICS 
                    display."
                DEFVAL { "" }  -- zero length
                ::= { trapClientEntry 4 }


            -- Additional individual SNMP agent objects

            snmpAgentAuthFailureAddress OBJECT-TYPE
                SYNTAX TypedAddress
                ACCESS read-only
                STATUS mandatory
                DESCRIPTION
                    "The address of the client to most recently fail 
                    SNMP authorization."
                ::= { xSnmpAgent 10 }

            snmpAgentCommunityAuthenticationAlways OBJECT-TYPE
                SYNTAX INTEGER { disabled(1), enabled(2) }
                ACCESS read-write
                STATUS mandatory
                DESCRIPTION
                  "When enabled, indicates that community string authentication
                   is done always for Gets, Sets, and GetNexts. When disabled,
                   community string authentication is done once; but bypassed
                   on subsequent Gets, Sets or GetNexts from the same address."
                DEFVAL { enabled }
                ::= { xSnmpAgent 14 }


            -- the Domain Resolver group

            -- Implementation of this group is mandatory for all iTouch
            -- systems that implement Domain name resolution

            domainResolverSuffix OBJECT-TYPE
                SYNTAX DisplayString (SIZE (0..115))
                ACCESS read-write
                STATUS mandatory
                DESCRIPTION
                    "A partial domain name for the server to append to 
                    the end of an incomplete domain name provided by the 
                    user.  Corresponds directly to SERVER INTERNET 
                    DEFAULT DOMAIN SUFFIX and the value labeled 'Domain 
                    Suffix:' in the SERVER INTERNET CHARACTERISTICS 
                    display."
                ::= { xDomainResolver 1 }

            domainResolverAddress1 OBJECT-TYPE
                SYNTAX IpAddress
                ACCESS read-write
                STATUS mandatory
                DESCRIPTION
                    "The internet address of a Domain Name Server.  The 
                    system can use one or two such addresses, without 
                    preference.  A value of 0.0.0.0 indicates no 
                    address.  Corresponds directly to SERVER INTERNET 
                    PRIMARY DOMAIN ADDRESS and the value labeled 
                    'Primary Domain Address:' in the SERVER INTERNET 
                    CHARACTERISTICS display."
                ::= { xDomainResolver 2 }

            domainResolverAddress2 OBJECT-TYPE
                SYNTAX IpAddress
                ACCESS read-write
                STATUS mandatory
                DESCRIPTION
                    "The internet address of a Domain Name Server.  The 
                    system can use one or two such addresses, without 
                    preference.  A value of 0.0.0.0 indicates no 
                    address.  Corresponds directly to SERVER INTERNET 
                    SECONDARY DOMAIN ADDRESS and the value labeled 
                    'Secondary Domain Address:' in the SERVER INTERNET 
                    CHARACTERISTICS display."
                ::= { xDomainResolver 3 }

            domainResolverTtl OBJECT-TYPE
                SYNTAX INTEGER (0..168)
                ACCESS read-write
                STATUS mandatory
                DESCRIPTION
                    "The number of hours to keep received Domain 
                    information.  Corresponds directly to SERVER 
                    INTERNET DOMAIN TTL and the value labeled ' Domain 
                    TTL:' in the SERVER INTERNET CHARACTERISTICS 
                    display."
                ::= { xDomainResolver 4 }

            domainResolverNameNumber OBJECT-TYPE
                SYNTAX INTEGER
                ACCESS read-only
                STATUS mandatory
                DESCRIPTION
                    "The number of Domain name mappings in this system's 
                    name cache."
                ::= { xDomainResolver 5 }


            -- the Name table

            nameTable OBJECT-TYPE
                SYNTAX SEQUENCE OF NameEntry
                ACCESS not-accessible
                STATUS mandatory
                DESCRIPTION
                    "A list of Domain name entries.  The number of 
                    entries is given by the value of 
                    domainResolverNameNumber."
                ::= { xDomainResolver 6 }

            nameEntry OBJECT-TYPE
                SYNTAX NameEntry
                ACCESS not-accessible
                STATUS mandatory
                DESCRIPTION
                    "Parameter values for a Domain name."
                INDEX { nameName, nameAddress }
                ::= { nameTable 1 }

            NameEntry ::=
                SEQUENCE {
                    nameName
                        DisplayString,
                    nameAddress
                        IpAddress,
                    nameStatus
                        INTEGER,
                    nameSource
                        INTEGER,
                    nameTtl
                        INTEGER
                }

            nameName OBJECT-TYPE
                SYNTAX DisplayString (SIZE (1..50))
                ACCESS read-only
                STATUS mandatory
                DESCRIPTION
                    "A fully qualified domain name.  Corresponds 
                    directly to the value labeled 'Domain Name' in the 
                    DOMAIN display."
                ::= { nameEntry 1 }

            nameAddress OBJECT-TYPE
                SYNTAX IpAddress
                ACCESS read-only
                STATUS mandatory
                DESCRIPTION
                    "An Internet address corresponding to the Domain 
                    name.  Corresponds directly to the value labeled 
                    'Internet Address' in the DOMAIN display."
                ::= { nameEntry 2 }

            nameStatus OBJECT-TYPE
                SYNTAX INTEGER { invalid(1), valid(2) }
                ACCESS read-write
                STATUS mandatory
                DESCRIPTION
                    "The status of the entry.  Set to 'invalid' to 
                    remove the entry, which corresponds directly to the 
                    PURGE DOMAIN command.  Actual removal of the entry 
                    is implementation specific."
                ::= { nameEntry 3 }

            nameSource OBJECT-TYPE
                SYNTAX INTEGER { manager(1), primary(2), secondary(3),
                                 rwho(4) }
                ACCESS read-only
                STATUS mandatory
                DESCRIPTION
                    "Source of this entry.  The value meanings are:

                    local       defined by manager (LOCAL)
                    primary     obtained from a primary name server
                    secondary   obtained from a secondary name server
                    rwho        obtained from rwho

                    Corresponds directly to the value labeled 'Source' 
                    in the DOMAIN display."
                ::= { nameEntry 4 }

            nameTtl OBJECT-TYPE
                SYNTAX INTEGER
                ACCESS read-only
                STATUS mandatory
                DESCRIPTION
                    "The number of minutes remaining in the entry's time 
                    to live.  Corresponds directly to the value labeled 
                    'TTL' in the DOMAIN display."
                ::= { nameEntry 5 }


            domainResolverPpp OBJECT IDENTIFIER ::= { xDomainResolver 7 }
            
            domainResolverPppPrimaryServer OBJECT-TYPE
                SYNTAX IpAddress
                ACCESS read-write
                STATUS mandatory
                DESCRIPTION
                    "The internet address of the primary Domain Name Server to
                     use in PPP IPCP negotiations. A value of 0.0.0.0 indicates
                     no address. Corresponds directly to the value labeled 
                     'Primary WINS Address:' in the SERVER INTERNET
                     CHARACTERISTICS display."
                ::= { domainResolverPpp 1 }

            domainResolverPppSecondaryServer OBJECT-TYPE
                SYNTAX IpAddress
                ACCESS read-write
                STATUS mandatory
                DESCRIPTION
                    "The internet address of the secondary Domain Name Server to
                     use in PPP IPCP negotiations. A value of 0.0.0.0 indicates
                     no address. Corresponds directly to the value labeled 
                     'Secondary WINS Address:' in the SERVER INTERNET
                     CHARACTERISTICS display."
                ::= { domainResolverPpp 2 }


            -- the SLIP group

            -- Implementation of this group is mandatory for all iTouch
            -- systems that implement SLIP ports

            slipTable OBJECT-TYPE
                SYNTAX SEQUENCE OF SlipEntry
                ACCESS not-accessible
                STATUS mandatory
                DESCRIPTION
                    "A list of SLIP character port entries."
                ::= { xSlip 1 }

            slipEntry OBJECT-TYPE
                SYNTAX SlipEntry
                ACCESS not-accessible
                STATUS mandatory
                DESCRIPTION
                    "Parameter values for a SLIP port."
                INDEX { slipIndex }
                ::= { slipTable 1 }

            SlipEntry ::=
                SEQUENCE {
                    slipIndex
                        INTEGER,
                    slipState
                        INTEGER,
                    slipLocalAddress
                        IpAddress,
                    slipRemoteAddress
                        IpAddress,
                    slipMask
                        IpAddress,
                    slipPortPacketsReceived
                        Counter,
                    slipPortPacketsSent
                        Counter,
                    slipPortPacketsDiscarded
                        Counter,
                    slipPortPacketLengthErrors
                        Counter,
                    slipPortPacketChecksumErrors
                        Counter,
                    slipNetworkPacketsReceived
                        Counter,
                    slipNetworkPacketsSent
                        Counter,
                    slipNetworkPacketsDiscarded
                        Counter
                }

            slipIndex OBJECT-TYPE
                SYNTAX INTEGER
                ACCESS read-only
                STATUS mandatory
                DESCRIPTION
                    "An index value that uniquely identifies a port that 
                    can run SLIP.  The port identified by a particular 
                    value of this index is the same port as identified 
                    by charPortIndex in the Proposed Standard Internet 
                    Character MIB."
                ::= { slipEntry 1 }

            slipState OBJECT-TYPE
                SYNTAX INTEGER { off(1), on(2), compressed(3) }
                ACCESS read-write
                STATUS mandatory
                DESCRIPTION
                    "A control indicating whether SLIP is in operation 
                    on the port.  Corresponds directly to PORT INTERNET 
                    SLIP and the value labeled 'SLIP' in the PORT 
                    CHARACTERISTICS display."
                ::= { slipEntry 2 }

            slipLocalAddress OBJECT-TYPE
                SYNTAX IpAddress
                ACCESS read-write
                STATUS mandatory
                DESCRIPTION
                    "The IP address assigned to the port.  Corresponds 
                    directly to PORT SLIP ADDRESS and the value labeled 
                    'SLIP Address:' in the PORT ALTERNATE 
                    CHARACTERISTICS display."
                ::= { slipEntry 3 }

            slipRemoteAddress OBJECT-TYPE
                SYNTAX IpAddress
                ACCESS read-write
                STATUS mandatory
                DESCRIPTION
                    "The IP address of the remote system attached to the 
                    port.  Corresponds directly to PORT SLIP REMOTE and 
                    the value labeled 'Remote SLIP Address:' in the PORT 
                    ALTERNATE CHARACTERISTICS display."
                ::= { slipEntry 4 }

            slipMask OBJECT-TYPE
                SYNTAX IpAddress
                ACCESS read-write
                STATUS mandatory
                DESCRIPTION
                    "The subnet mask to use for SLIP operation on the 
                    port.  Corresponds directly to PORT SLIP MASK and 
                    the value labeled 'SLIP Mask:' in the PORT ALTERNATE 
                    CHARACTERISTICS display."
                ::= { slipEntry 5 }

            slipPortPacketsReceived OBJECT-TYPE
                SYNTAX Counter
                ACCESS read-only
                STATUS mandatory
                DESCRIPTION
                    "The number of SLIP packets received from the port.  
                    Corresponds directly to the value labeled 'Serial 
                    Packets Received:' in the PORT COUNTERS display."
                ::= { slipEntry 6 }

            slipPortPacketsSent OBJECT-TYPE
                SYNTAX Counter
                ACCESS read-only
                STATUS mandatory
                DESCRIPTION
                    "The number of SLIP packets sent to the port.  
                    Corresponds directly to the value labeled 'Serial 
                    Packets Sent:' in the PORT COUNTERS display."
                ::= { slipEntry 7 }

            slipPortPacketsDiscarded OBJECT-TYPE
                SYNTAX Counter
                ACCESS read-only
                STATUS mandatory
                DESCRIPTION
                    "The number of SLIP packets received from the port 
                    and discarded.  Corresponds directly to the value 
                    labeled 'Serial Packets Discarded:' in the PORT 
                    COUNTERS display."
                ::= { slipEntry 8 }

            slipPortPacketLengthErrors OBJECT-TYPE
                SYNTAX Counter
                ACCESS read-only
                STATUS mandatory
                DESCRIPTION
                    "The number of SLIP packets received from the port 
                    with an incorrect number of bytes.  Corresponds 
                    directly to the value labeled 'Serial Packet Length 
                    Errors:' in the PORT COUNTERS display."
                ::= { slipEntry 9 }

            slipPortPacketChecksumErrors OBJECT-TYPE
                SYNTAX Counter
                ACCESS read-only
                STATUS mandatory
                DESCRIPTION
                    "The number of SLIP packets received from the port 
                    with an invalid checksum.  Corresponds directly to 
                    the value labeled 'Serial Packet Checksum Errors:' 
                    in the PORT COUNTERS display."
                ::= { slipEntry 10 }

            slipNetworkPacketsReceived OBJECT-TYPE
                SYNTAX Counter
                ACCESS read-only
                STATUS mandatory
                DESCRIPTION
                    "The number of SLIP packets received from the 
                    network for this port.  Corresponds directly to the 
                    value labeled 'Network Packets Received:' in the 
                    PORT COUNTERS display."
                ::= { slipEntry 11 }

            slipNetworkPacketsSent OBJECT-TYPE
                SYNTAX Counter
                ACCESS read-only
                STATUS mandatory
                DESCRIPTION
                    "The number of SLIP packets sent to the network from 
                    this port.  Corresponds directly to the value 
                    labeled 'Network Packets Sent:' in the PORT COUNTERS 
                    display."
                ::= { slipEntry 12 }

            slipNetworkPacketsDiscarded OBJECT-TYPE
                SYNTAX Counter
                ACCESS read-only
                STATUS mandatory
                DESCRIPTION
                    "The number of SLIP packets received from the 
                    network for this port and discarded.  Corresponds 
                    directly to the value labeled 'Network Packets 
                    Discarded:' in the PORT COUNTERS display."
                ::= { slipEntry 13 }


            -- the Telnet group

            -- Implementation of this group is mandatory for all iTouch
            -- systems that implement Telnet

            -- the Telnet Character Port table

            -- Ports in this table are either serial or parallel

            telnetPortTable OBJECT-TYPE
                SYNTAX SEQUENCE OF TelnetPortEntry
                ACCESS not-accessible
                STATUS mandatory
                DESCRIPTION
                    "A list of Telnet character port entries."
                ::= { xTelnet 1 }

            telnetPortEntry OBJECT-TYPE
                SYNTAX TelnetPortEntry
                ACCESS not-accessible
                STATUS mandatory
                DESCRIPTION
                    "Telnet parameter values for a character port."
                INDEX { telnetPortIndex }
                ::= { telnetPortTable 1 }

            TelnetPortEntry ::=
                SEQUENCE {
                    telnetPortIndex
                        INTEGER,
                    telnetPortIncomingTcpPort
                        INTEGER,
                    telnetPortOutgoingTcpPort
                        INTEGER,
                    telnetPortNewlineTranslation
                        INTEGER,
                    telnetPortTerminalType
                        DisplayString,
                    telnetPortEorReflection
                        INTEGER,
                    telnetPortBinaryMode
                        INTEGER,
                    telnetPortSendLocation
                        INTEGER,
                    telnetPortClientLocation
                        DisplayString,
                    telnetPortPassiveSendLocation
                        INTEGER
                }

            telnetPortIndex OBJECT-TYPE
                SYNTAX INTEGER
                ACCESS read-only
                STATUS mandatory
                DESCRIPTION
                    "An index value that uniquely identifies a port.  
                    The port identified by a particular value of this 
                    index is the same port as identified by 
                    charPortIndex in the Proposed Standard Internet 
                    Character MIB."
                ::= { telnetPortEntry 1 }

            telnetPortIncomingTcpPort OBJECT-TYPE
                SYNTAX INTEGER (1..32767)
                ACCESS read-write
                STATUS mandatory
                DESCRIPTION
                    "The TCP port number offered for incoming 
                    connections to this character port.  Corresponds 
                    directly to PORT TELNET REMOTE PORT and the value 
                    labeled 'Remote Port:' in the PORT TELNET 
                    CHARACTERISTICS display."
                ::= { telnetPortEntry 2 }

            telnetPortOutgoingTcpPort OBJECT-TYPE
                SYNTAX INTEGER
                ACCESS read-write
                STATUS mandatory
                DESCRIPTION
                    "The TCP port number used by default for outgoing 
                    connections from this character port.  Corresponds 
                    directly to PORT TELNET DEFAULT PORT and the value 
                    labeled 'Default Port:' in the PORT TELNET 
                    CHARACTERISTICS display."
                ::= { telnetPortEntry 3 }

            telnetPortNewlineTranslation OBJECT-TYPE
                SYNTAX INTEGER { none(1), cr(2), crNull(3), 
                                crLf(4), std(5), lfToCrLf(6) }
                ACCESS read-write
                STATUS mandatory
                DESCRIPTION
                    "Translation to apply to newline sequences (CR/NULL 
                    or CR/LF) received from the network, before sending 
                    the newline to the character port.  The value 
                    indicates the sequence sent to the character port, 
                    with 'none' meaning no translation.  The lfToCrLf 
                    value converts the newline character LF received
                    from the network to a CR/LF.  Corresponds
                    directly to PORT TELNET NEWLINE FILTERING and the 
                    value labeled 'Newline Filtering:' in the PORT 
                    TELNET CHARACTERISTICS display."
                ::= { telnetPortEntry 4 }

            telnetPortTerminalType OBJECT-TYPE
                SYNTAX DisplayString (SIZE (0..21))
                ACCESS read-write
                STATUS mandatory
                DESCRIPTION
                    "The terminal type character string for Telnet 
                    negotiations.  Corresponds directly to PORT TELNET 
                    TERMINALTYPE and the value labeled 'TerminalType:' 
                    in the PORT TELNET CHARACTERISTICS display."
                ::= { telnetPortEntry 5 }

            telnetPortEorReflection OBJECT-TYPE
                SYNTAX INTEGER { disabled(1), enabled(2) }
                ACCESS read-write
                STATUS mandatory
                DESCRIPTION
                    "Control for end-of-record handshake.  Corresponds 
                    directly to PORT TELNET EOR REFLECTION and the value 
                    labeled 'EOR Reflection:' in the PORT TELNET 
                    CHARACTERISTICS display."
                ::= { telnetPortEntry 6 }

            telnetPortBinaryMode OBJECT-TYPE
                SYNTAX INTEGER { flowControl(1), complete(2),
                                 disabled(3) }
                ACCESS read-write
                STATUS mandatory
                DESCRIPTION
                    "Control for operation of Telnet binary mode.  The 
                    value meanings are:

                    disabled      refuse binary mode negotiation
                                  (INTERACTIVE)
                    flowControl   pass all but XON and XOFF (PASTHRU)
                    complete      pass all characters (PASSALL)

                    Corresponds directly to PORT TELNET BINARY SESSION 
                    MODE and the value labeled 'Binary Session Mode:' in 
                    the PORT TELNET CHARACTERISTICS display."
                ::= { telnetPortEntry 7 }

            telnetPortSendLocation OBJECT-TYPE
                SYNTAX INTEGER { disabled(1), enabled(2) }
                ACCESS read-write
                STATUS mandatory
                DESCRIPTION
                    "A control indicating whether a Telnet session will 
                    initiate negotiation of the Send Location option. 
                    Corresponds directly to the PORT TELNET LOCATION and 
                    the value labeled 'Location' in the PORT TELNET 
                    CHARACTERISTICS display."
                ::= { telnetPortEntry 8 }

            telnetPortClientLocation OBJECT-TYPE
                SYNTAX DisplayString (SIZE (0..50))
                ACCESS read-only
                STATUS mandatory
                DESCRIPTION
                    "The location of the Telnet client port. Corresponds 
                    directly to the value labeled 'Telnet Client 
                    Location' in the SESSION display."
                ::= { telnetPortEntry 9 }
         
            telnetPortPassiveSendLocation OBJECT-TYPE
                SYNTAX INTEGER { disabled(1), enabled(2) }
                ACCESS read-write
                STATUS mandatory
                DESCRIPTION
                    "A control indicating whether a Telnet session will 
                    passively respond to negotiation of the Send Location
                    option. When disabled and telnetPortSendLocation is 
                    disabled, we will refuse to negotiate this option.
                    When telnetPortSendLocation is enabled, it takes 
                    precedence. Corresponds directly to the value labeled
                    'Passive Location' in the PORT TELNET CHARACTERISTICS
                    display."
                DEFVAL { enabled }
                ::= { telnetPortEntry 10 }
            

            -- the Telnet Serial Character Port table

            telnetSerialPortTable OBJECT-TYPE
                SYNTAX SEQUENCE OF TelnetSerialPortEntry
                ACCESS not-accessible
                STATUS mandatory
                DESCRIPTION
                    "A list of Telnet character port entries."
                ::= { xTelnet 2 }

            telnetSerialPortEntry OBJECT-TYPE
                SYNTAX TelnetSerialPortEntry
                ACCESS not-accessible
                STATUS mandatory
                DESCRIPTION
                    "Telnet parameter values for a character port."
                INDEX { telnetSerialPortIndex }
                ::= { telnetSerialPortTable 1 }

            TelnetSerialPortEntry ::=
                SEQUENCE {
                    telnetSerialPortIndex
                        INTEGER,
                    telnetSerialPortOptionDisplay
                        INTEGER,
                    telnetSerialPortCsiEscape
                        INTEGER,
                    telnetSerialPortEchoMode
                        INTEGER,
                    telnetSerialPortNewlineMode
                        INTEGER,
                    telnetSerialPortTransmitMode
                        INTEGER,
                    telnetSerialPortTransmitCharacterTimes
                        INTEGER,
                    telnetSerialPortAbortOutputCharacter
                        INTEGER,
                    telnetSerialPortAttentionCharacter
                        INTEGER,
                    telnetSerialPortEraseKeyCharacter
                        INTEGER,
                    telnetSerialPortEraseLineCharacter
                        INTEGER,
                    telnetSerialPortInterruptCharacter
                        INTEGER,
                    telnetSerialPortQueryCharacter
                        INTEGER,
                    telnetSerialPortSynchronizeCharacter
                        INTEGER,
                    telnetSerialPortUrgentBreak
                        INTEGER,
                    telnetSerialPortRs491
                        INTEGER,
                    telnetSerialPortTransmitBufferedTime
                        INTEGER,
                    telnetSerialPortInterpretInterruptAsBreak
                        INTEGER,
                    telnetSerialPortPass8d
                        INTEGER,
                    telnetSerialPortComControlClient
                        INTEGER,
                    telnetSerialPortComControlServer
                        INTEGER,
                    telnetSerialPortComControlServerRaisesDtr
                        INTEGER,
                    telnetSerialPortComControlClientTogglesDtr
                        INTEGER
                }

            telnetSerialPortIndex OBJECT-TYPE
                SYNTAX INTEGER
                ACCESS read-only
                STATUS mandatory
                DESCRIPTION
                    "An index value that uniquely identifies a port.  
                    The port identified by a particular value of this 
                    index is the same port as identified by 
                    charPortIndex in the Proposed Standard Internet 
                    Character MIB."
                ::= { telnetSerialPortEntry 1 }

            telnetSerialPortOptionDisplay OBJECT-TYPE
                SYNTAX INTEGER { disabled(1), enabled(2) }
                ACCESS read-write
                STATUS mandatory
                DESCRIPTION
                    "Control for display of Telnet option negotiations.  
                    Corresponds directly to PORT TELNET OPTION DISPLAY 
                    and the value labeled 'Option Display:' in the PORT 
                    TELNET CHARACTERISTICS display."
                ::= { telnetSerialPortEntry 2 }

            telnetSerialPortCsiEscape OBJECT-TYPE
                SYNTAX INTEGER { disabled(1), enabled(2) }
                ACCESS read-write
                STATUS mandatory
                DESCRIPTION
                    "Control for translation of 8-bit escape sequences 
                    received from the character port to 7-bit 
                    equivalents before transmission to the remote 
                    partner.  Corresponds directly to PORT TELNET CSI 
                    ESCAPE and the value labeled 'CSI Escape:' in the 
                    PORT TELNET CHARACTERISTICS display."
                ::= { telnetSerialPortEntry 3 }

            telnetSerialPortEchoMode OBJECT-TYPE
                SYNTAX INTEGER { local(1), remote(2), disabled(3), passive(4),
                                  character(5), line(6), noecho(7) }
                ACCESS read-write
                STATUS mandatory
                DESCRIPTION
                    "Control for who echoes characters that come from 
                    the character port.  The value meanings are:

                    local    terminal server echoes locally
                    remote   remote system echoes
                    disabled don't default to local echo
                    passive  don't initiate negotiating of echo
                    character initiate remote echo and suppress go ahead
                    line     reject remote echo and reject suppress go ahead
                    noecho   will not initiate echo, but will negotiate it

                    Corresponds directly to PORT TELNET ECHO MODE and 
                    the value labeled 'Echo Mode:' in the PORT TELNET 
                    CHARACTERISTICS display."
                ::= { telnetSerialPortEntry 4 }

            telnetSerialPortNewlineMode OBJECT-TYPE
                SYNTAX INTEGER { crNull(1), crLf(2), verbatim(3) }
                ACCESS read-write
                STATUS mandatory
                DESCRIPTION
                    "Translation to apply to newline (carriage return) 
                    received from the character port, before sending the 
                    newline to the remote partner.  The correspondence 
                    to command keywords is 'crNull' to NULL, 'crLF' to 
                    LINEFEED, and 'verbatim' to NOTHING (that is, no 
                    translation).  Corresponds directly to PORT TELNET 
                    NEWLINE and the value labeled 'Newline:' in the PORT 
                    TELNET CHARACTERISTICS display."
                ::= { telnetSerialPortEntry 5 }

            telnetSerialPortTransmitMode OBJECT-TYPE
                SYNTAX INTEGER { immediate(1), buffered(2), timed(3), controlchar(4) }
                ACCESS read-write
                STATUS mandatory
                DESCRIPTION
                    "Criterion for deciding to send to the remote 
                    partner characters received from the character port.  
                    Corresponds directly to PORT TELNET TRANSMIT and the 
                    value labeled 'Transmit:' in the PORT TELNET 
                    CHARACTERISTICS display."
                ::= { telnetSerialPortEntry 6 }

            telnetSerialPortTransmitCharacterTimes OBJECT-TYPE
                SYNTAX INTEGER (0..255)
                ACCESS read-write
                STATUS mandatory
                DESCRIPTION
                    "Number of character times to wait before 
                    transmitting when telnetSerialPortTransmitMode value 
                    is 'timed'.  Corresponds directly to PORT TELNET 
                    TRANSMIT IDLETIME and the value labeled 'Transmit:  
                    Idle Time -' in the PORT TELNET CHARACTERISTICS 
                    display. This object may only be set to values 1..255.
                    A value of 0 may be read if telnetSerialPortTransmitMode
                    has a value of immediate or buffered"
                ::= { telnetSerialPortEntry 7 }

            telnetSerialPortAbortOutputCharacter OBJECT-TYPE
                SYNTAX INTEGER (0..255)
                ACCESS read-write
                STATUS mandatory
                DESCRIPTION
                    "Character input from the character port to cause 
                    aborting output.  The value 0 indicates no character 
                    has this effect.  Corresponds directly to PORT 
                    TELNET ABORT OUTPUT and the value labeled 'Abort 
                    Output Character:' in the PORT TELNET 
                    CHARACTERISTICS display."
                ::= { telnetSerialPortEntry 8 }

            telnetSerialPortAttentionCharacter OBJECT-TYPE
                SYNTAX INTEGER (0..255)
                ACCESS read-write
                STATUS mandatory
                DESCRIPTION
                    "Character input from the character port to cause an 
                    attention notification to the remote partner.  The 
                    value 0 indicates no character has this effect.  
                    Corresponds directly to PORT TELNET ATTENTION and 
                    the value labeled 'Attention Character:' in the PORT 
                    TELNET CHARACTERISTICS display."
                ::= { telnetSerialPortEntry 9 }

            telnetSerialPortEraseKeyCharacter OBJECT-TYPE
                SYNTAX INTEGER (0..255)
                ACCESS read-write
                STATUS mandatory
                DESCRIPTION
                    "Character input from the character port to cause 
                    erasure of the previous input character.  The value 
                    0 indicates no character has this effect.  
                    Corresponds directly to PORT TELNET ERASE CHARACTER 
                    and the value labeled 'Erase Keystroke Character:' 
                    in the PORT TELNET CHARACTERISTICS display."
                ::= { telnetSerialPortEntry 10 }

            telnetSerialPortEraseLineCharacter OBJECT-TYPE
                SYNTAX INTEGER (0..255)
                ACCESS read-write
                STATUS mandatory
                DESCRIPTION
                    "Character input from the character port to cause 
                    erasure of the previous line of input.  The value 0 
                    indicates no character has this effect.  Corresponds 
                    directly to PORT TELNET ERASE LINE and the value 
                    labeled 'Erase Line Character:' in the PORT TELNET 
                    CHARACTERISTICS display."
                ::= { telnetSerialPortEntry 11 }

            telnetSerialPortInterruptCharacter OBJECT-TYPE
                SYNTAX INTEGER (0..255)
                ACCESS read-write
                STATUS mandatory
                DESCRIPTION
                    "Character input from the character port to cause 
                    sending an interrupt notification to the remote 
                    partner.  The value 0 indicates no character has 
                    this effect.  Corresponds directly to PORT TELNET 
                    INTERRUPT and the value labeled 'Interrupt 
                    Character:' in the PORT TELNET CHARACTERISTICS 
                    display."
                ::= { telnetSerialPortEntry 12 }

            telnetSerialPortQueryCharacter OBJECT-TYPE
                SYNTAX INTEGER (0..255)
                ACCESS read-write
                STATUS mandatory
                DESCRIPTION
                    "Character input from the character port to cause 
                    sending a status query to the remote partner.  The 
                    value 0 indicates no character has this effect.  
                    Corresponds directly to PORT TELNET QUERY and the 
                    value labeled 'Query Character:' in the PORT TELNET 
                    CHARACTERISTICS display."
                ::= { telnetSerialPortEntry 13 }

            telnetSerialPortSynchronizeCharacter OBJECT-TYPE
                SYNTAX INTEGER (0..255)
                ACCESS read-write
                STATUS mandatory
                DESCRIPTION
                    "Character input from the character port to cause 
                    sending a synchronization attempt to the remote 
                    partner.  The value 0 indicates no character has 
                    this effect.  Corresponds directly to PORT TELNET 
                    SYNCHRONIZE and the value labeled 'Synchronize 
                    Character:' in the PORT TELNET CHARACTERISTICS 
                    display."
                ::= { telnetSerialPortEntry 14 }

            telnetSerialPortUrgentBreak OBJECT-TYPE
                SYNTAX INTEGER { disabled(1), enabled(2) }
                ACCESS read-write
                STATUS mandatory
                DESCRIPTION
                    "Control for encoding breaks as Telnet urgent data.  
                    Corresponds directly to PORT TELNET URGENT BREAK and 
                    the value labeled 'Urgent Break:' in the PORT TELNET 
                    CHARACTERISTICS display."
                ::= { telnetSerialPortEntry 15 }

            telnetSerialPortRs491 OBJECT-TYPE
                SYNTAX INTEGER { disabled(1), enabled(2) }
                ACCESS read-write
                STATUS mandatory 
                DESCRIPTION
                   "A control to enable RS491 protocol processing on a port."
                DEFVAL  { disabled }
                ::= { telnetSerialPortEntry 16 }

            telnetSerialPortTransmitBufferedTime OBJECT-TYPE
                SYNTAX INTEGER (30..1500)
                ACCESS read-write
                STATUS mandatory
                DESCRIPTION
                   "Number of milliseconds to wait before transmitting
                    when telnetSerialPortTransmitMode value is 'timed'.
                    Corresponds directly to PORT TELNET TRANSMIT BUFFERED
                    and the value labeled 'Transmit: Buff Time -' in the
                    PORT TELNET CHARACTERISTICS display. This object may
                    only be set to values 30..1500. A value of 0 may be
                    read if telnetSerialPortTransmitMode has a value of
                    immediate, idletime or controlchar"
                DEFVAL   { 80 }
                ::= { telnetSerialPortEntry 17 }

            telnetSerialPortInterpretInterruptAsBreak OBJECT-TYPE
                SYNTAX INTEGER { enabled(1), disabled(2) }
                ACCESS read-write
                STATUS mandatory
                DESCRIPTION
                    "Control to interpret a Telnet Interrupt Character coming
                     from the network as a Telnet Break Character, and to send
                     a break out the serial port. This control is necessary 
                     for those devices which can send Telnet Interrupt but not
                     Telnet Break. Corresponds directly to the presence of 
                     'Telnet Interrupts Interpreted as Break' under the label 
                     'Enabled Characteristics' in the PORT TELNET 
                     CHARACTERISTICS display."
                DEFVAL { disabled }
                ::= { telnetSerialPortEntry 18 }

            telnetSerialPortPass8d OBJECT-TYPE
                SYNTAX INTEGER { enabled(1), disabled(2) }
                ACCESS read-write
                STATUS mandatory
                DESCRIPTION
                    "Control to pass unaltered the hexadecimal character '8D'.
                     This control is added to ensure that this character will
                     pass through directly in a session with 8-bit characters
                     and parity odd or even.  Corresponds directly to the 
                     presence of 'Telnet Pass 8D' under the label 'Enabled
                     Characteristics' in the PORT TELNET CHARACTERISTICS 
                     display."
                DEFVAL { disabled }
                ::= { telnetSerialPortEntry 19 }

            telnetSerialPortComControlClient OBJECT-TYPE
                SYNTAX INTEGER { enabled(1), disabled(2) }
                ACCESS read-write
                STATUS mandatory
                DESCRIPTION
                    "Control to begin Telnet comport control option negotiations
                     as a client when a Telnet session is initiated. The comport
                     control option enables a port to do outbound modem dialing
                     on a Telnet connection. Corresponds to the value labeled
                     'Client:' in the PORT TELNET COMPORTCONTROL CHARACTERISTICS
                     display."
                DEFVAL { disabled }
                ::= { telnetSerialPortEntry 20 }

            telnetSerialPortComControlServer OBJECT-TYPE
                SYNTAX INTEGER { enabled(1), disabled(2) }
                ACCESS read-write
                STATUS mandatory
                DESCRIPTION
                    "Control to begin Telnet comport control option negotiations
                     as a server when a Telnet session is initiated. Corresponds
                     to the value labeled 'Server:' in the PORT TELNET 
                     COMPORTCONTROL CHARACTERISTICS display."
                DEFVAL { disabled }
                ::= { telnetSerialPortEntry 21 }
 
            telnetSerialPortComControlServerRaisesDtr OBJECT-TYPE
                SYNTAX INTEGER { enabled(1), disabled(2) }
                ACCESS read-write
                STATUS mandatory
                DESCRIPTION
                    "Control for the client to request that the server raises
                     its DTR signal on the port at the begining of the Telnet 
                     connection. Corresponds to the value labeled 'Server 
                     Raises DTR:' in the PORT TELNET COMPORTCONTROL
                     CHARACTERISTICS display."
                DEFVAL { disabled }
                ::= { telnetSerialPortEntry 22 }
 
            telnetSerialPortComControlClientTogglesDtr OBJECT-TYPE
                SYNTAX INTEGER { enabled(1), disabled(2) }
                ACCESS read-write
                STATUS mandatory
                DESCRIPTION
                    "Control to respond to the server's notification that its 
                     DCD has come high (or low)  by raising (or lowering) DTR
                     accordingly on the local port. Corresponds to the value 
                     labeled 'Client Toggles DTR:' in the PORT TELNET 
                     COMPORTCONTROL CHARACTERISTICS display."
                DEFVAL { disabled }
                ::= { telnetSerialPortEntry 23 }
 

               


            -- the tn3270 group

            -- Implementation of this group is mandatory for all iTouch
            -- systems that implement tn3270

            tn3270DeviceNumber OBJECT-TYPE
                SYNTAX INTEGER
                ACCESS read-only
                STATUS mandatory
                DESCRIPTION
                    "The number of entries in the tn3270 Device table."
                ::= { xTn3270 1 }

            tn3270LanguageNumber OBJECT-TYPE
                SYNTAX INTEGER
                ACCESS read-only
                STATUS mandatory
                DESCRIPTION
                    "The number of entries in the tn3270 Language 
                    table."
                ::= { xTn3270 2 }

            tn3270PortKeymapStatus OBJECT-TYPE
                SYNTAX INTEGER { disabled(1), enabled(2) }
                ACCESS read-write
                STATUS mandatory
                DESCRIPTION
                    "Control for individual ports to create their own 
                    keymaps.  Corresponds directly to SERVER TN3270 PORT 
                    KEYMAPS and the value labeled 'Port Keymaps:' in the 
                    SERVER TN3270 display."
                ::= { xTn3270 3 }


            -- The tn3270 Device table

            tn3270DeviceTable OBJECT-TYPE
                SYNTAX SEQUENCE OF Tn3270DeviceEntry
                ACCESS not-accessible
                STATUS mandatory
                DESCRIPTION
                    "A list of tn3270 terminal device entries."
                ::= { xTn3270 4 }

            tn3270DeviceEntry OBJECT-TYPE
                SYNTAX Tn3270DeviceEntry
                ACCESS not-accessible
                STATUS mandatory
                DESCRIPTION
                    "Tn3270 parameter values for a terminal device 
                    entry."
                INDEX { tn3270DeviceName }
                ::= { tn3270DeviceTable 1 }

            Tn3270DeviceEntry ::=
                SEQUENCE {
                    tn3270DeviceName
                        DisplayString,
                    tn3270DeviceStatus
                        INTEGER,
                    tn3270DeviceType
                        DisplayString,
                    tn3270Device3278Model
                        INTEGER,
                    tn3270DeviceKeyNumber
                        INTEGER,
                    tn3270DeviceScreenNumber
                        INTEGER
                }

            tn3270DeviceName OBJECT-TYPE
                SYNTAX DisplayString (SIZE (1..8))
                ACCESS read-only
                STATUS mandatory
                DESCRIPTION
                    "The name of a generic terminal device.  Corresponds 
                    directly to SERVER TN3270 DEVICE and the value 
                    labeled 'Device Name:' in the SERVER TN3270 DEVICE 
                    display."
                ::= { tn3270DeviceEntry 1 }

            tn3270DeviceStatus OBJECT-TYPE
                SYNTAX INTEGER { invalid(1), valid(2) }
                ACCESS read-write
                STATUS mandatory
                DESCRIPTION
                    "Status of this entry.  Setting the value to 
                    'invalid' invalidates the entry, corresponding 
                    directly to the PURGE SERVER TN3270 DEVICE command.  
                    It is an implementation-specific matter as to 
                    whether the agent removes an invalidated entry from 
                    the table. If a new device table entry is added to
                    the table, the agent will copy the VT100 table as
                    a default. If one plans to add a new table entry, one
                    should not remove the VT100 entry."
                DEFVAL { valid }
                ::= { tn3270DeviceEntry 2 }

            tn3270DeviceType OBJECT-TYPE
                SYNTAX DisplayString (SIZE (0..21))
                ACCESS read-write
                STATUS mandatory
                DESCRIPTION
                    "The terminal type character string for use when 
                    tn3270DeviceTn3270Type is insufficient.  Corresponds 
                    directly to SERVER TN3270 DEVICE TERMINALTYPE and 
                    the value labeled 'TerminalType:' in the SERVER 
                    TN3270 DEVICE display."
                DEFVAL { "VT100" }
                ::= { tn3270DeviceEntry 3 }

            tn3270Device3278Model OBJECT-TYPE
                SYNTAX INTEGER { model2(1), model5(2) }
                ACCESS read-write
                STATUS mandatory
                DESCRIPTION
                    "The 3278 model for the device.  Corresponds 
                    directly to SERVER TN3270 DEVICE 3278Model and the 
                    value labeled '3278Model:' in the SERVER TN3270 
                    DEVICE display."
                DEFVAL { model2 }
                ::= { tn3270DeviceEntry 4 }

            tn3270DeviceKeyNumber OBJECT-TYPE
                SYNTAX INTEGER
                ACCESS read-only
                STATUS mandatory
                DESCRIPTION
                    "The number of Key table entries for this device."
                DEFVAL { 70 }
                ::= { tn3270DeviceEntry 5 }

            tn3270DeviceScreenNumber OBJECT-TYPE
                SYNTAX INTEGER
                ACCESS read-only
                STATUS mandatory
                DESCRIPTION
                    "The number of Screen table entries for this 
                    device."
                DEFVAL { 24 }
                ::= { tn3270DeviceEntry 6 }


            -- The Key table

            tn3270KeyTable OBJECT-TYPE
                SYNTAX SEQUENCE OF Tn3270KeyEntry
                ACCESS not-accessible
                STATUS mandatory
                DESCRIPTION
                    "A list of tn3270 key entries by device."
                ::= { xTn3270 5 }

            tn3270KeyEntry OBJECT-TYPE
                SYNTAX Tn3270KeyEntry
                ACCESS not-accessible
                STATUS mandatory
                DESCRIPTION
                    "Tn3270 parameter values for a key entry for a 
                    device."
                INDEX { tn3270KeyDeviceName, tn3270KeyName }
                ::= { tn3270KeyTable 1 }

            Tn3270KeyEntry ::=
                SEQUENCE {
                    tn3270KeyDeviceName
                        DisplayString,
                    tn3270KeyName
                        INTEGER,
                    tn3270KeyStatus
                        INTEGER,
                    tn3270KeyCharacterSequence
                        OCTET STRING,
                    tn3270KeyDescription
                        DisplayString
                }

            tn3270KeyDeviceName OBJECT-TYPE
                SYNTAX DisplayString (SIZE (1..8))
                ACCESS read-only
                STATUS mandatory
                DESCRIPTION
                    "The name of a generic terminal device as in 
                    tn3270DeviceName.  Corresponds directly to SERVER 
                    TN3270 DEVICE and the value labeled 'Device Name:' 
                    in the SERVER TN3270 DEVICE display."
                ::= { tn3270KeyEntry 1 }

            tn3270KeyName OBJECT-TYPE
                SYNTAX INTEGER { newline(1), tab(2), backtab(3),
                                 cursorup(4), cursorleft(5),
                                 cursorright(6), cursordown(7),
                                 home(8), delete(9), eraseeof(10),
                                 eraseinput(11), insert(12),
                                 flushinput(13), refresh(14),
                                 centsign(15), duplicate(16),
                                 fieldmark(17), scroll(18),
                                 status(19), reset(20),
                                 fastleft(21), fastright(22),
                                 showkeys(23), print(24),
                                 pf1(39), pf2(40), pf3(41),
                                 pf4(42), pf5(43), pf6(44),
                                 pf7(45), pf8(46), pf9(47), pf10(48),
                                 pf11(49), pf12(50), pf13(51),
                                 pf14(52), pf15(53), pf16(54),
                                 pf17(55), pf18(56), pf19(57),
                                 pf20(58), pf21(59), pf22(60),
                                 pf23(61), pf24(62), pa1(63),
                                 pa2(64), pa3(65), sysreq(66),
                                 enter(67), clear(68), cursorsel(69),
                                 test(70) }
                ACCESS read-only
                STATUS mandatory
                DESCRIPTION
                    "The key name to which this entry applies.  
                    Corresponds directly to the key portion of SERVER 
                    TN3270 DEVICE KEYMAP and the value labeled 
                    '3270-key' in the 'Keymap:' section of the SERVER 
                    TN3270 DEVICE display."
                ::= { tn3270KeyEntry 2 }

            tn3270KeyStatus OBJECT-TYPE
                SYNTAX INTEGER { invalid(1), valid(2) }
                ACCESS read-write
                STATUS deprecated
                DESCRIPTION
                    "Status of this entry.  Setting the value to 
                    'invalid' invalidates the entry.  It is an 
                    implementation-specific matter as to whether the 
                    agent removes an invalidated entry from the table."
                DEFVAL { valid }
                ::= { tn3270KeyEntry 3 }

            tn3270KeyCharacterSequence OBJECT-TYPE
                SYNTAX OCTET STRING (SIZE (0..8))
                ACCESS read-write
                STATUS mandatory
                DESCRIPTION
                    "The ASCII character sequence for the key.  
                    Corresponds directly to the escape-sequence portion 
                    of SERVER TN3270 DEVICE KEYMAP and the value labeled 
                    'KeyCode' in the 'Keymap:' section of the SERVER 
                    TN3270 DEVICE display."
                ::= { tn3270KeyEntry 4 }

            tn3270KeyDescription OBJECT-TYPE
                SYNTAX DisplayString (SIZE (0..5))
                ACCESS read-write
                STATUS mandatory
                DESCRIPTION
                    "Descriptive text for the key.  Corresponds directly 
                    to the description portion of SERVER TN3270 DEVICE 
                    KEYMAP and the value labeled 'Description' in the 
                    SERVER TN3270 DEVICE display."
                ::= { tn3270KeyEntry 5 }


            -- The Screen Action table

            tn3270ScreenTable OBJECT-TYPE
                SYNTAX SEQUENCE OF Tn3270ScreenEntry
                ACCESS not-accessible
                STATUS mandatory
                DESCRIPTION
                    "A list of tn3270 screen action entries by device."
                ::= { xTn3270 6 }

            tn3270ScreenEntry OBJECT-TYPE
                SYNTAX Tn3270ScreenEntry
                ACCESS not-accessible
                STATUS mandatory
                DESCRIPTION
                    "Tn3270 parameter values for a screen action entry 
                    for a device."
                INDEX { tn3270ScreenDeviceName, tn3270ScreenActionName }
                ::= { tn3270ScreenTable 1 }

            Tn3270ScreenEntry ::=
                SEQUENCE {
                    tn3270ScreenDeviceName
                        DisplayString,
                    tn3270ScreenActionName
                        INTEGER,
                    tn3270ScreenStatus
                        INTEGER,
                    tn3270ScreenCharacterSequence
                        OCTET STRING
                }

            tn3270ScreenDeviceName OBJECT-TYPE
                SYNTAX DisplayString (SIZE (1..8))
                ACCESS read-only
                STATUS mandatory
                DESCRIPTION
                    "The name of a generic terminal device as in 
                    tn3270DeviceName.  Corresponds directly to SERVER 
                    TN3270 DEVICE and the value labeled 'Device Name:' 
                    in the SERVER TN3270 DEVICE display."
                ::= { tn3270ScreenEntry 1 }

            tn3270ScreenActionName OBJECT-TYPE
                SYNTAX INTEGER { eraseeol(1), clearscr(2),
                                 movecursor(3), col132(4), col80(5),
                                 beep(6), charset(7), boldon(8),
                                 boldoff(9), blinkon(10),
                                 blinkoff(11), underscoreon(12),
                                 underscoreoff(13), reverseon(14),
                                 reverseoff(15),
                                 colorBlue(16), colorRed(17),
                                 colorPink(18), colorGreen(19),
                                 colorTurquoise(20),
                                 colorYellow(21), colorWhite(22),
                                 status1(26), status2(27),
                                 reset1(28), reset2(29),
                                 reset3(30), reset4(31),
                                 base(32), sgr(33) }
                ACCESS read-only
                STATUS mandatory
                DESCRIPTION
                    "The screen action to which this entry applies.  
                    Corresponds directly to the action portion of SERVER 
                    TN3270 DEVICE SCREENMAP and the value labeled 
                    'Terminal Function' in the 'Screenmap: section of 
                    the SERVER TN3270 DEVICE display."
                ::= { tn3270ScreenEntry 2 }

            tn3270ScreenStatus OBJECT-TYPE
                SYNTAX INTEGER { invalid(1), valid(2) }
                ACCESS read-write
                STATUS deprecated
                DESCRIPTION
                    "Status of this entry.  Setting the value to 
                    'invalid' invalidates the entry.  It is an 
                    implementation-specific matter as to whether the 
                    agent removes an invalidated entry from the table."
                DEFVAL { valid }
                ::= { tn3270ScreenEntry 3 }

            tn3270ScreenCharacterSequence OBJECT-TYPE
                SYNTAX OCTET STRING (SIZE (0..15))
                ACCESS read-write
                STATUS mandatory
                DESCRIPTION
                    "The ASCII character sequence for the screen action.  
                    Some actions may have a lesser length limit.  
                    Corresponds directly to the escape-sequence portion 
                    of SERVER TN3270 DEVICE SCREENMAP and the value 
                    labeled 'HexCode' in the 'Screenmap: section of the 
                    SERVER TN3270 DEVICE display."
                ::= { tn3270ScreenEntry 4 }


            -- The Language table

            tn3270LanguageTable OBJECT-TYPE
                SYNTAX SEQUENCE OF Tn3270LanguageEntry
                ACCESS not-accessible
                STATUS mandatory
                DESCRIPTION
                    "A list of tn3270 language entries."
                ::= { xTn3270 7 }

            tn3270LanguageEntry OBJECT-TYPE
                SYNTAX Tn3270LanguageEntry
                ACCESS not-accessible
                STATUS mandatory
                DESCRIPTION
                    "Tn3270 parameter values for a language entry."
                INDEX { tn3270LanguageName }
                ::= { tn3270LanguageTable 1 }

            Tn3270LanguageEntry ::=
                SEQUENCE {
                    tn3270LanguageName
                        DisplayString,
                    tn3270LanguageStatus
                        INTEGER
                }

            tn3270LanguageName OBJECT-TYPE
                SYNTAX DisplayString (SIZE (1..8))
                ACCESS read-only
                STATUS mandatory
                DESCRIPTION
                    "The name of language for character translation 
                    tables.  Corresponds directly to SERVER TN3270 
                    LANGUAGE and the value labeled 'Language Name:' in 
                    the SERVER LANGUAGE display."
                ::= { tn3270LanguageEntry 1 }

            tn3270LanguageStatus OBJECT-TYPE
                SYNTAX INTEGER { invalid(1), valid(2) }
                ACCESS read-write
                STATUS mandatory
                DESCRIPTION
                    "Status of this entry.  Setting the value to 
                    'invalid' invalidates the entry.  It is an 
                    implementation-specific matter as to whether the 
                    agent removes an invalidated entry from the table.
                    If a new device table entry is added to the table,
                    the agent will copy the USENGLSH table as the default." 
                DEFVAL { valid }
                ::= { tn3270LanguageEntry 2 }


            -- The Language EBCDIC to ASCII table

            eToALanguageTable OBJECT-TYPE
                SYNTAX SEQUENCE OF EToALanguageEntry
                ACCESS not-accessible
                STATUS mandatory
                DESCRIPTION
                    "A list of language EBCDIC to ASCII conversion 
                    entries."
                ::= { xTn3270 8 }

            eToALanguageEntry OBJECT-TYPE
                SYNTAX EToALanguageEntry
                ACCESS not-accessible
                STATUS mandatory
                DESCRIPTION
                    "EBCDIC to ASCII parameter values for a language 
                    entry."
                INDEX { eToALanguageName, eToAOffset }
                ::= { eToALanguageTable 1 }

            EToALanguageEntry ::=
                SEQUENCE {
                    eToALanguageName
                        DisplayString,
                    eToAOffset
                        INTEGER,
                    eToAValue
                        INTEGER
                }

            eToALanguageName OBJECT-TYPE
                SYNTAX DisplayString (SIZE (1..8))
                ACCESS read-only
                STATUS mandatory
                DESCRIPTION
                    "The name of language from the language table."
                ::= { eToALanguageEntry 1 }

            eToAOffset OBJECT-TYPE
                SYNTAX INTEGER (65..256)
                ACCESS read-only
                STATUS mandatory
                DESCRIPTION
                    "EBCDIC character offset plus one, that is, the 
                    value 1 corresponds to an operational offset of 0.  
                    Corresponds directly to the offset portion of SERVER 
                    TN3270 LANGUAGE and the hexadecimal labels around 
                    the conversion table labeled 'EBCDIC to ASCII' in 
                    the SERVER LANGUAGE display."
                ::= { eToALanguageEntry 2 }

            eToAValue OBJECT-TYPE
                SYNTAX INTEGER (32..255)
                ACCESS read-write
                STATUS mandatory
                DESCRIPTION
                    "ASCII character value for the EBCDIC offset.  
                    Corresponds directly to the value portion of SERVER 
                    TN3270 LANGUAGE and the values in the conversion 
                    table labeled 'EBCDIC to ASCII' in the SERVER 
                    LANGUAGE display."
                ::= { eToALanguageEntry 3 }


            -- The Language ASCII to EBCDIC table

            aToELanguageTable OBJECT-TYPE
                SYNTAX SEQUENCE OF AToELanguageEntry
                ACCESS not-accessible
                STATUS mandatory
                DESCRIPTION
                    "A list of language ASCII to EBCDIC conversion 
                    entries."
                ::= { xTn3270 9 }

            aToELanguageEntry OBJECT-TYPE
                SYNTAX AToELanguageEntry
                ACCESS not-accessible
                STATUS mandatory
                DESCRIPTION
                    "ASCII to EBCDIC parameter values for a language 
                    entry."
                INDEX { aToELanguageName, aToEOffset }
                ::= { aToELanguageTable 1 }

            AToELanguageEntry ::=
                SEQUENCE {
                    aToELanguageName
                        DisplayString,
                    aToEOffset
                        INTEGER,
                    aToEValue
                        INTEGER
                }

            aToELanguageName OBJECT-TYPE
                SYNTAX DisplayString (SIZE (1..8))
                ACCESS read-only
                STATUS mandatory
                DESCRIPTION
                    "The name of language from the language table."
                ::= { aToELanguageEntry 1 }

            aToEOffset OBJECT-TYPE
                SYNTAX INTEGER (33..256)
                ACCESS read-only
                STATUS mandatory
                DESCRIPTION
                    "ASCII character offset plus one, that is, the value 
                    1 corresponds to an operational offset of 0.  
                    Corresponds directly to the offset portion of SERVER 
                    TN3270 LANGUAGE and the hexadecimal labels around 
                    the conversion table labeled 'ASCII to EBCDIC' in 
                    the SERVER LANGUAGE display."
                ::= { aToELanguageEntry 2 }

            aToEValue OBJECT-TYPE
                SYNTAX INTEGER (0..255)
                ACCESS read-write
                STATUS mandatory
                DESCRIPTION
                    "EBCDIC character value for the ASCII offset.  
                    Corresponds directly to the value portion of SERVER 
                    TN3270 LANGUAGE and the values in the conversion 
                    table labeled 'ASCII to EBCDIC' in the SERVER 
                    LANGUAGE display."
                ::= { aToELanguageEntry 3 }


            -- the tn3270 Port table

            tn3270PortTable OBJECT-TYPE
                SYNTAX SEQUENCE OF Tn3270PortEntry
                ACCESS not-accessible
                STATUS mandatory
                DESCRIPTION
                    "A list of tn3270 character port entries."
                ::= { xTn3270 10 }

            tn3270PortEntry OBJECT-TYPE
                SYNTAX Tn3270PortEntry
                ACCESS not-accessible
                STATUS mandatory
                DESCRIPTION
                    "Parameter values for a tn3270 port."
                INDEX { tn3270PortIndex }
                ::= { tn3270PortTable 1 }

            Tn3270PortEntry ::=
                SEQUENCE {
                    tn3270PortIndex
                        INTEGER,
                    tn3270PortDeviceName
                        DisplayString,
                    tn3270PortLanguageName
                        DisplayString,
                    tn3270PortExtendedAttributes
                        INTEGER,
                    tn3270PortEorNegotiation
                        INTEGER,
                    tn3270PortErrorLock
                        INTEGER,
                    tn3270PortPrinterPort
                        INTEGER,
                    tn3270PortOutgoingTcpPort
                        INTEGER,
                    tn3270PortSpaceInsert
                        INTEGER,
                    tn3270PortTypeAhead
                        INTEGER,
                    tn3270PrefixKeyMap
                        INTEGER,
                    tn3270PortScanner
                        INTEGER
                }

            tn3270PortIndex OBJECT-TYPE
                SYNTAX INTEGER
                ACCESS read-only
                STATUS mandatory
                DESCRIPTION
                    "An index value that uniquely identifies a port.  
                    The port identified by a particular value of this 
                    index is the same port as identified by 
                    charPortIndex in the Proposed Standard Internet 
                    Character MIB."
                ::= { tn3270PortEntry 1 }

            tn3270PortDeviceName OBJECT-TYPE
                SYNTAX DisplayString (SIZE (0..8))
                ACCESS read-write
                STATUS mandatory
                DESCRIPTION
                    "The name of a generic terminal device from the 
                    tn3270 device table.  Corresponds directly to PORT 
                    TELNET TN3270 DEVICE and the value labeled 'Tn3270 
                    Device:' in the PORT TELNET display."
                ::= { tn3270PortEntry 2 }

            tn3270PortLanguageName OBJECT-TYPE
                SYNTAX DisplayString (SIZE (0..8))
                ACCESS read-write
                STATUS mandatory
                DESCRIPTION
                    "The name of language from the tn3270 language 
                    table.  Corresponds directly to PORT TELNET TN3270 
                    LANGUAGE and the value labeled 'Tn3270 Language:' in 
                    the PORT TELNET display."
                ::= { tn3270PortEntry 3 }

            tn3270PortExtendedAttributes OBJECT-TYPE
                SYNTAX INTEGER { disabled(1), enabled(2) }
                ACCESS read-write
                STATUS mandatory
                DESCRIPTION
                    "A control indicating that certain 3270 extended 
                    attributes are supported on the port.  Corresponds 
                    directly to PORT TELNET TN3270 XTDATTRS and the 
                    label 'Tn3270 XtdAttrs' following the label 'Enabled 
                    Characteristics' in the PORT TELNET display."
                ::= { tn3270PortEntry 4 }

            tn3270PortEorNegotiation OBJECT-TYPE
                SYNTAX INTEGER { disabled(1), enabled(2) }
                ACCESS read-write
                STATUS mandatory
                DESCRIPTION
                    "A control for negotiation of the Telnet EOR option 
                    when establishing a tn3270 session on the port.  
                    Corresponds directly to PORT TELNET TN3270 EOR and 
                    the label 'Tn3270 EOR' following the label 'Enabled 
                    Characteristics' in the PORT TELNET display."
                ::= { tn3270PortEntry 5 }

            tn3270PortErrorLock OBJECT-TYPE
                SYNTAX INTEGER { disabled(1), enabled(2) }
                ACCESS read-write
                STATUS mandatory
                DESCRIPTION
                    "A control for requiring use the RESET key when the 
                    host reports an error during a tn3270 session on the 
                    port.  Corresponds directly to PORT TELNET TN3270 
                    ERRORLOCK and the label 'Tn3270 ErrorLock' following 
                    the label 'Enabled Characteristics' in the PORT 
                    TELNET display."
                ::= { tn3270PortEntry 6 }

            tn3270PortPrinterPort OBJECT-TYPE
                SYNTAX INTEGER
                ACCESS read-write
                STATUS mandatory
                DESCRIPTION
                    "The port number of the tn3270 printer.  Corresponds 
                    directly to PORT TELNET TN3270 PRINTER and the value 
                    labeled 'Tn3270 Printer:' in the PORT TELNET 
                    display."
                ::= { tn3270PortEntry 7 }

            tn3270PortOutgoingTcpPort OBJECT-TYPE
                SYNTAX INTEGER (1..32767)
                ACCESS read-write
                STATUS mandatory
                DESCRIPTION
                    "The TCP port which is used for a TN3270 session when
                     connecting to a remote host from this serial port. 
                     Corresponds directly to the value labeled 'Tn3270 Default 
                     Port:' in the PORT TELNET CHARACTERISTICS display."
                DEFVAL { 23 }
                ::= { tn3270PortEntry 8 }
           
          tn3270PortSpaceInsert OBJECT-TYPE
            SYNTAX INTEGER { disabled(1), enabled(2) }
            ACCESS read-write
            STATUS mandatory
            DESCRIPTION
                "Control to allow insert mode within a space filled field, and
                 write characters over EBCDIC spaces.  Corresponds directly to
                 the presence of 'Tn3270 Space_Insert' under the label 'Enabled
                 Characteristics' in the PORT TELNET CHARACTERISTICS display."
            DEFVAL { disabled }
            ::= { tn3270PortEntry 9 }
           
          tn3270PortTypeAhead OBJECT-TYPE
            SYNTAX INTEGER { disabled(1), enabled(2) }
            ACCESS read-write  
            STATUS mandatory
            DESCRIPTION
                "Control to permit typing ahead in a tn3270 session prior to
                 receiving a response from the host for the previous command
                 entered. Corresponds directly to the presence of
                 'Tn3270 TypeAhead' under the label 'Enabled Characteristics'
                 in the PORT TELNET CHARACTERISTICS display."
            DEFVAL { enabled }
            ::= { tn3270PortEntry 10 }

          tn3270PrefixKeyMap OBJECT-TYPE
            SYNTAX INTEGER { disabled(1), enabled(2) }
            ACCESS read-write
            STATUS mandatory
            DESCRIPTION
                "Control to prepend a prefix function to another function key.
                 When the operator hits the key the prepended function(s) and
                 then the main function for the key are transmitted to the host.
                 Corresponds directly to the presence of 'Tn3270 PrefixKeyMap'
                 under the label 'Enabled Characteristics' in the PORT
                 TELNET CHARACTERISTICS display."
            DEFVAL { disabled  }
            ::= { tn3270PortEntry 11 }

          tn3270PortScanner OBJECT-TYPE
            SYNTAX INTEGER { disabled(1), enabled(2) }
            ACCESS read-write
            STATUS mandatory
            DESCRIPTION
                "Indicates that this is a tn3270 scanner port. Corresponds
                 directly to the presence of 'Tn3270 SCANNER' under the
                 label 'Enabled Characteristics' in the PORT TELNET
                 CHARACTERISTICS display."
            DEFVAL { disabled  }
            ::= { tn3270PortEntry 12 }



            -- the Kerberos group

            -- Implementation of this group is mandatory for all iTouch
            -- systems that implement a Kerberos client

            kerbStatus OBJECT-TYPE
                SYNTAX INTEGER { none(1), login(2) }
                ACCESS read-write
                STATUS mandatory
                DESCRIPTION
                    "A control indicating the level of Kerberos 
                    operation on the system.  Corresponds directly to 
                    SERVER KERBEROS STATUS and the value labeled 
                    'Kerberos Security:' in the SERVER KERBEROS 
                    display."
                ::= { xKerberos 1 }

            kerbRealm OBJECT-TYPE
                SYNTAX DisplayString (SIZE (0..40))
                ACCESS read-write
                STATUS mandatory
                DESCRIPTION
                    "The Kerberos realm with which the kerbServerName1 
                    and kerbServerName2 are associated.  Corresponds 
                    directly to SERVER KERBEROS REALM and the value 
                    labeled 'Kerberos Realm:' in the SERVER KERBEROS 
                    display."
                ::= { xKerberos 2 }

            kerbQueryLimit OBJECT-TYPE
                SYNTAX INTEGER (1..16)
                ACCESS read-write
                STATUS mandatory
                DESCRIPTION
                    "The maximum number of attempts the system can make 
                    when trying to verify a Kerberos ID.  Corresponds 
                    directly to SERVER KERBEROS QUERY LIMIT and the 
                    value labeled 'Kerberos Query Limit:' in the SERVER 
                    KERBEROS display."
                ::= { xKerberos 3 }

            kerbMasterName OBJECT-TYPE
                SYNTAX DisplayString (SIZE (0..50))
                ACCESS read-write
                STATUS mandatory
                DESCRIPTION
                    "The Domain name of the Kerberos master host system, 
                    which holds the Kerberos database.  Corresponds 
                    directly to SERVER KERBEROS MASTER and the value 
                    labeled 'Kerberos Master:' in the SERVER KERBEROS 
                    display."
                ::= { xKerberos 4 }

            kerbServerName1 OBJECT-TYPE
                SYNTAX DisplayString (SIZE (0..50))
                ACCESS read-write
                STATUS mandatory
                DESCRIPTION
                    "The Domain name of the first Kerberos server to try 
                    when the system verifys a Kerberos ID.  Corresponds 
                    directly to SERVER KERBEROS PRIMARY SERVER and the 
                    value labeled 'Kerberos Primary Server:' in the 
                    SERVER KERBEROS display."
                ::= { xKerberos 5 }

            kerbServerName2 OBJECT-TYPE
                SYNTAX DisplayString (SIZE (0..50))
                ACCESS read-write
                STATUS mandatory
                DESCRIPTION
                    "The Domain name of the Kerberos server to try when 
                    the system verifys a Kerberos ID and cannot reach 
                    the Kerberos primary server.  Corresponds directly 
                    to SERVER KERBEROS SECONDARY SERVER and the value 
                    labeled 'Kerberos Secondary Server:' in the SERVER 
                    KERBEROS display."
                ::= { xKerberos 6 }

            kerbInsecureLogins OBJECT-TYPE
                SYNTAX Counter
                ACCESS read-only
                STATUS mandatory
                DESCRIPTION
                    "The number of user logins on ports for which 
                    Kerberos user verification is not enabled.  
                    Corresponds directly to the value labeled 'Logins 
                    without Kerberos:' in the SERVER KERBEROS display."
                ::= { xKerberos 7 }

            kerbSecureLogins OBJECT-TYPE
                SYNTAX Counter
                ACCESS read-only
                STATUS mandatory
                DESCRIPTION
                    "The number of successful user logins on ports for 
                    which Kerberos user verification is enabled.  
                    Corresponds directly to the value labeled 
                    'Successful Logins:' in the SERVER KERBEROS 
                    display."
                ::= { xKerberos 8 }

            kerbSecureLoginsFailed OBJECT-TYPE
                SYNTAX Counter
                ACCESS read-only
                STATUS mandatory
                DESCRIPTION
                    "The number of verification failures due to 
                    incorrect ID or password for attempted user logins 
                    on ports for which Kerberos user verification is 
                    enabled.  Corresponds directly to the value labeled 
                    'Unsuccessful Logins:' in the SERVER KERBEROS 
                    display."
                ::= { xKerberos 9 }

            kerbPasswordChangeFailed OBJECT-TYPE
                SYNTAX Counter
                ACCESS read-only
                STATUS mandatory
                DESCRIPTION
                    "The number of user failures to change their 
                    Kerberos password due to invalid old password or new 
                    password verification.  Corresponds directly to the 
                    value labeled 'Password Change Failures:' in the 
                    SERVER KERBEROS display."
                ::= { xKerberos 10 }

            kerbError OBJECT-TYPE
                SYNTAX INTEGER
                ACCESS read-only
                STATUS mandatory
                DESCRIPTION
                    "The error number of the most recent 
                    Kerberos-related failure.  Corresponds directly to 
                    the value labeled 'Last Kerberos Error:' in the 
                    SERVER KERBEROS display.  For a list of error 
                    numbers and their meanings, consult relevant iTouch 
                    or Kerberos documentation."
                ::= { xKerberos 11 }

            kerbErrorTime OBJECT-TYPE
                SYNTAX DateTime
                ACCESS read-only
                STATUS mandatory
                DESCRIPTION
                    "The date and time that kerbError was last updated.  
                    Corresponds directly to the value labeled 
                    'Occurred:' in the SERVER KERBEROS display."
                ::= { xKerberos 12 }

            kerbMasterAccess OBJECT-TYPE
                SYNTAX Counter
                ACCESS read-only
                STATUS mandatory
                DESCRIPTION
                    "The number of times the system successfully 
                    accessed the Kerberos master host.  Corresponds 
                    directly to the value labeled 'Attempts to access:', 
                    'Master', and 'Successful:' in the SERVER KERBEROS 
                    display."
                ::= { xKerberos 13 }

            kerbMasterAccessFailed OBJECT-TYPE
                SYNTAX Counter
                ACCESS read-only
                STATUS mandatory
                DESCRIPTION
                    "The number of times the system failed access to the 
                    Kerberos master host.  Corresponds directly to the 
                    value labeled 'Attempts to access:', 'Master', and 
                    'Unsuccessful:' in the SERVER KERBEROS display."
                ::= { xKerberos 14 }

            kerbServerAccess1 OBJECT-TYPE
                SYNTAX Counter
                ACCESS read-only
                STATUS mandatory
                DESCRIPTION
                    "The number of times the system successfully 
                    accessed the Kerberos primary server.  Corresponds 
                    directly to the value labeled 'Attempts to access:', 
                    'Server1', and 'Successful:' in the SERVER KERBEROS 
                    display."
                ::= { xKerberos 15 }

            kerbServerAccessFailed1 OBJECT-TYPE
                SYNTAX Counter
                ACCESS read-only
                STATUS mandatory
                DESCRIPTION
                    "The number of times the system failed access to the 
                    Kerberos primary server.  Corresponds directly to 
                    the value labeled 'Attempts to access:', 'Server1', 
                    and 'Unsuccessful:' in the SERVER KERBEROS 
                    display."
                ::= { xKerberos 16 }

            kerbServerAccess2 OBJECT-TYPE
                SYNTAX Counter
                ACCESS read-only
                STATUS mandatory
                DESCRIPTION
                    "The number of times the system successfully 
                    accessed the Kerberos secondary server.  Corresponds 
                    directly to the value labeled 'Attempts to access:', 
                    'Server2', and 'Successful:' in the SERVER KERBEROS 
                    display."
                ::= { xKerberos 17 }

            kerbServerAccessFailed2 OBJECT-TYPE
                SYNTAX Counter
                ACCESS read-only
                STATUS mandatory
                DESCRIPTION
                    "The number of times the system failed access to the 
                    Kerberos secondary server.  Corresponds directly to 
                    the value labeled 'Attempts to access:', 'Server2', 
                    and 'Unsuccessful:' in the SERVER KERBEROS 
                    display."
                ::= { xKerberos 18 }

            -- additional scalar values below


            -- the Kerberos Port table

            kerbPortTable OBJECT-TYPE
                SYNTAX SEQUENCE OF KerbPortEntry
                ACCESS not-accessible
                STATUS mandatory
                DESCRIPTION
                    "A list of Kerberos character port entries."
                ::= { xKerberos 19 }

            kerbPortEntry OBJECT-TYPE
                SYNTAX KerbPortEntry
                ACCESS not-accessible
                STATUS mandatory
                DESCRIPTION
                    "Parameter values for a Kerberos port."
                INDEX { kerbPortIndex }
                ::= { kerbPortTable 1 }

            KerbPortEntry ::=
                SEQUENCE {
                    kerbPortIndex
                        INTEGER,
                    kerbPortStatus
                        INTEGER
                }

            kerbPortIndex OBJECT-TYPE
                SYNTAX INTEGER
                ACCESS read-only
                STATUS mandatory
                DESCRIPTION
                    "An index value that uniquely identifies a port 
                    could relate to Kerberos.  The port identified by a 
                    particular value of this index is the same port as 
                    identified by charPortIndex in the Proposed Standard 
                    Internet Character MIB."
                ::= { kerbPortEntry 1 }

            kerbPortStatus OBJECT-TYPE
                SYNTAX INTEGER { none(1), login(2) }
                ACCESS read-write
                STATUS mandatory
                DESCRIPTION
                    "A control indicating the level of Kerberos 
                    operation on the port.  Corresponds directly to PORT 
                    KERBEROS and the value 'Kerberos' following the 
                    label 'Enabled Characteristics' in the PORT 
                    CHARACTERISTICS display."
                ::= { kerbPortEntry 2 }

            -- additional scalars

            kerbServerPort OBJECT-TYPE
                SYNTAX INTEGER { standardPort(88), experimentalPort(750) }
                ACCESS read-write
                STATUS mandatory
                DESCRIPTION
                    "The UDP port number on the Kerberos server where
                    Kerberos messages are sent."
                ::= { xKerberos 20 }


            -- the Port Security group

            -- Implementation of this group is mandatory for all iTouch
            -- systems that implement Internet port security

            psEntryNumber OBJECT-TYPE
                SYNTAX INTEGER
                ACCESS read-only
                STATUS mandatory
                DESCRIPTION
                    "The number of security entries in this system's 
                    port security table with psEntryStatus of 'valid'."
                ::= { xPortSecurity 1 }

            psEntryNumberLimit OBJECT-TYPE
                SYNTAX INTEGER
                ACCESS read-only
                STATUS mandatory
                DESCRIPTION
                    "The maximum number of security entries in this 
                    system's port security table."
                ::= { xPortSecurity 2 }

            psEntryInvalidIndex OBJECT-TYPE
                SYNTAX INTEGER
                ACCESS read-only
                STATUS mandatory
                DESCRIPTION
                    "A value of psEntryIndex for an entry that has 
                    psEntryStatus of 'invalid'.  A management station 
                    may choose this value when adding a new entry.  
                    Collisions between independent management stations 
                    simultaneously using the same number are beyond the 
                    scope of this document."
                ::= { xPortSecurity 3 }


            -- the Port Security table

            psPortTable OBJECT-TYPE
                SYNTAX SEQUENCE OF PsPortEntry
                ACCESS not-accessible
                STATUS mandatory
                DESCRIPTION
                    "A list of port security character port entries."
                ::= { xPortSecurity 4 }

            psPortEntry OBJECT-TYPE
                SYNTAX PsPortEntry
                ACCESS not-accessible
                STATUS mandatory
                DESCRIPTION
                    "Port security parameter values for a port."
                INDEX { psPortIndex }
                ::= { psPortTable 1 }

            PsPortEntry ::=
                SEQUENCE {
                    psPortIndex
                        INTEGER,
                    psPortDefaultInboundAccess
                        INTEGER,
                    psPortDefaultOutboundAccess
                        INTEGER,
                    psClrInternetSecurity
                        INTEGER
                }

            psPortIndex OBJECT-TYPE
                SYNTAX INTEGER
                ACCESS read-only
                STATUS mandatory
                DESCRIPTION
                    "An index value that uniquely identifies a port for 
                    security purposes.  The port identified by a 
                    particular value of this index is the same port as 
                    identified by charPortIndex in the Proposed Standard 
                    Internet Character MIB."
                ::= { psPortEntry 1 }

            psPortDefaultInboundAccess OBJECT-TYPE
                SYNTAX INTEGER { allow(1), deny(2) }
                ACCESS read-write
                STATUS mandatory
                DESCRIPTION
                    "The default access to the port for incoming TCP 
                    connections.  Corresponds directly to PORT INTERNET 
                    SECURITY DEFAULT INBOUND and the value labeled 
                    'Inbound Default:' in the PORT INTERNET SECURITY 
                    display."
                ::= { psPortEntry 2 }

            psPortDefaultOutboundAccess OBJECT-TYPE
                SYNTAX INTEGER { allow(1), deny(2) }
                ACCESS read-write
                STATUS mandatory
                DESCRIPTION
                    "The default access to the port for outgoing TCP 
                    connections.  Corresponds directly to PORT INTERNET 
                    SECURITY DEFAULT OUTBOUND and the value labeled 
                    'Outbound Default:' in the PORT INTERNET SECURITY 
                    display."
                ::= { psPortEntry 3 }

            psClrInternetSecurity OBJECT-TYPE
                SYNTAX INTEGER { disabled(1), enabled(2) }
                ACCESS read-write
                STATUS mandatory
                DESCRIPTION
                   "A control for if the internet security entries for this
                   port will be cleared upon port logout. The default is
                   disabled."
                ::={ psPortEntry 4 }

            -- the Port Security table

            psTable OBJECT-TYPE
                SYNTAX SEQUENCE OF PsEntry
                ACCESS not-accessible
                STATUS mandatory
                DESCRIPTION
                    "A list of port security entries."
                ::= { xPortSecurity 5 }

            psEntry OBJECT-TYPE
                SYNTAX PsEntry
                ACCESS not-accessible
                STATUS mandatory
                DESCRIPTION
                    "Port security parameter values for an entry for a 
                    port."
                INDEX { psEntryIndex }
                ::= { psTable 1 }

            PsEntry ::=
                SEQUENCE {
                    psEntryIndex
                        INTEGER,
                    psEntryStatus
                        INTEGER,
                    psEntryAddress
                        IpAddress,
                    psEntryMask
                        IpAddress,
                    psEntryAccess
                        INTEGER,
                    psEntryDirection
                        INTEGER,
                    psEntryPortMap
                        OCTET STRING
                }

            psEntryIndex OBJECT-TYPE
                SYNTAX INTEGER
                ACCESS read-only
                STATUS mandatory
                DESCRIPTION
                    "A small, numeric distinguisher for port security 
                    entries.  When adding a new entry, the client should 
                    specify an unused value, such as 
                    psEntryInvalidIndex.  Corresponds directly to the 
                    value labeled 'Entry' in the SERVER INTERNET 
                    SECURITY display."
                ::= { psEntry 1 }

            psEntryStatus OBJECT-TYPE
                SYNTAX INTEGER { invalid(1), valid(2) }
                ACCESS read-write
                STATUS mandatory
                DESCRIPTION
                    "Status of this entry.  Setting the value to 
                    'invalid' invalidates the entry, corresponding 
                    directly to the CLEAR INTERNET SECURITY command.  It 
                    is an implementation-specific matter as to whether 
                    the agent removes an invalidated entry from the 
                    table. Setting this object to 'valid' has no effect.
                    When creating a new instance, one must set 
                    psEntryAddress, psEntryMask, psEntryAccess,
                    psEntryDirection and psEntryPortList for the new
                    instance in the same physical set request. Furthermore,
                    if one wishes to change an entry, one must first
                    delete it and then add it with its new values."
                DEFVAL { valid }
                ::= { psEntry 2 }

            psEntryAddress OBJECT-TYPE
                SYNTAX IpAddress
                ACCESS read-write
                STATUS mandatory
                DESCRIPTION
                    "The IP address to which the entry pertains.  
                    Corresponds directly to the PORT INTERNET SECURITY 
                    internet address and the value labeled 'Internet 
                    Address' in the SERVER INTERNET SECURITY display."
                ::= { psEntry 3 }

            psEntryMask OBJECT-TYPE
                SYNTAX IpAddress
                ACCESS read-write
                STATUS mandatory
                DESCRIPTION
                    "The mask applied to psEntryAddress when making a 
                    security check based on this entry.  Corresponds 
                    directly to PORT INTERNET SECURITY MASK and the 
                    value labeled 'Security Mask' in the SERVER INTERNET 
                    SECURITY display."
                ::= { psEntry 4 }

            psEntryAccess OBJECT-TYPE
                SYNTAX INTEGER { allow(1), deny(2) }
                ACCESS read-write
                STATUS mandatory
                DESCRIPTION
                    "The access to the port for TCP connections when 
                    making a security check based on this entry.  
                    Corresponds directly to PORT INTERNET SECURITY ALLOW 
                    or DENY and the value labeled 'Access' in the SERVER 
                    INTERNET SECURITY display."
                ::= { psEntry 5 }

            psEntryDirection OBJECT-TYPE
                SYNTAX INTEGER { inbound(1), outbound(2) }
                ACCESS read-write
                STATUS mandatory
                DESCRIPTION
                    "The direction of TCP connections to which this 
                    entry applies.  Corresponds directly to PORT 
                    INTERNET SECURITY INBOUND or OUTBOUND and the value 
                    labeled 'Direction' in the SERVER INTERNET SECURITY 
                    display."
                ::= { psEntry 6 }

            psEntryPortMap OBJECT-TYPE
                SYNTAX OCTET STRING
                ACCESS read-write
                STATUS mandatory
                DESCRIPTION
                    "The list of character ports to which this entry 
                    applies.  The OCTET STRING contains a bitmap, with 
                    one bit for each port, and enough octets for all the 
                    ports on the system.  Port numbers are as defined 
                    for charPortIndex in the Proposed Standard Internet 
                    Character MIB.  Corresponding bit numbers start with 
                    1 as the high-order bit of the first octet.  
                    Corresponds directly to PORT INTERNET SECURITY and 
                    the value labeled 'Ports' in the SERVER INTERNET 
                    SECURITY display."
                ::= { psEntry 7 }


            -- the XREMOTE group

            -- Implementation of this group is mandatory for all iTouch
            -- systems that implement XREMOTE

            xremoteServerName1 OBJECT-TYPE
                SYNTAX DisplayString (SIZE (0..50))
                ACCESS read-write
                STATUS mandatory
                DESCRIPTION
                    "The Domain name of the first XREMOTE font server to 
                    try for downloading fonts.  Corresponds directly to 
                    SERVER XREMOTE PRIMARY SERVER and the value labeled 
                    'Xremote Primary Font Server:' in the SERVER XREMOTE 
                    display."
                ::= { xXremote 1 }

            xremoteServerName2 OBJECT-TYPE
                SYNTAX DisplayString (SIZE (0..50))
                ACCESS read-write
                STATUS mandatory
                DESCRIPTION
                    "The Domain name of the XREMOTE font server to try 
                    for downloading fonts and the primary font server 
                    does not respond.  Corresponds directly to SERVER 
                    XREMOTE SECONDARY SERVER and the value labeled 
                    'Xremote Secondary Font Server:' in the SERVER 
                    XREMOTE display."
                ::= { xXremote 2 }

            xremoteServerAccess1 OBJECT-TYPE
                SYNTAX Counter
                ACCESS read-only
                STATUS mandatory
                DESCRIPTION
                    "The number of times the system successfully 
                    accessed the XREMOTE primary font server.  
                    Corresponds directly to the value labeled 'Attempts 
                    to access:', 'Server1', and 'Successful:' in the 
                    SERVER XREMOTE display."
                ::= { xXremote 3 }

            xremoteServerAccessFailed1 OBJECT-TYPE
                SYNTAX Counter
                ACCESS read-only
                STATUS mandatory
                DESCRIPTION
                    "The number of times the system failed access to the 
                    XREMOTE primary font server.  Corresponds directly 
                    to the value labeled 'Attempts to access:', 
                    'Server1', and 'Unsuccessful:' in the SERVER XREMOTE 
                    display."
                ::= { xXremote 4 }

            xremoteServerAccess2 OBJECT-TYPE
                SYNTAX Counter
                ACCESS read-only
                STATUS mandatory
                DESCRIPTION
                    "The number of times the system successfully 
                    accessed the XREMOTE secondary font server.  
                    Corresponds directly to the value labeled 'Attempts 
                    to access:', 'Server2', and 'Successful:' in the 
                    SERVER XREMOTE display."
                ::= { xXremote 5 }

            xremoteServerAccessFailed2 OBJECT-TYPE
                SYNTAX Counter
                ACCESS read-only
                STATUS mandatory
                DESCRIPTION
                    "The number of times the system failed access to the 
                    XREMOTE secondary font server.  Corresponds directly 
                    to the value labeled 'Attempts to access:', 
                    'Server2', and 'Unsuccessful:' in the SERVER XREMOTE 
                    display."
                ::= { xXremote 6 }

            xremoteSessions OBJECT-TYPE
                SYNTAX Gauge
                ACCESS read-only
                STATUS mandatory
                DESCRIPTION
                    "The number of connected XREMOTE sessions.  
                    Corresponds directly to the value labeled 'Current 
                    Number of Xremote Sessions:' in the SERVER XREMOTE 
                    display."
                ::= { xXremote 7 }

            -- Additional individual objects follow port table


            -- the XREMOTE Port table

            xremotePortTable OBJECT-TYPE
                SYNTAX SEQUENCE OF XremotePortEntry
                ACCESS not-accessible
                STATUS mandatory
                DESCRIPTION
                    "A list of XREMOTE character port entries."
                ::= { xXremote 8 }

            xremotePortEntry OBJECT-TYPE
                SYNTAX XremotePortEntry
                ACCESS not-accessible
                STATUS mandatory
                DESCRIPTION
                    "XREMOTE parameter values for a port."
                INDEX { xremotePortIndex }
                ::= { xremotePortTable 1 }

            XremotePortEntry ::=
                SEQUENCE {
                    xremotePortIndex
                        INTEGER,
                    xremotePortXremote
                        INTEGER,
                    xremotePortXdmQuery
                        INTEGER,
                    xremotePortXdmHost
                        DisplayString
                }

            xremotePortIndex OBJECT-TYPE
                SYNTAX INTEGER
                ACCESS read-only
                STATUS mandatory
                DESCRIPTION
                    "An index value that uniquely identifies a port.  
                    The port identified by a particular value of this 
                    index is the same port as identified by 
                    charPortIndex in the Proposed Standard Internet 
                    Character MIB."
                ::= { xremotePortEntry 1 }

            xremotePortXremote OBJECT-TYPE
                SYNTAX INTEGER { disabled(1), enabled(2) }
                ACCESS read-write
                STATUS mandatory
                DESCRIPTION
                    "Control for use of XREMOTE on the port.  
                    Corresponds directly to PORT XREMOTE and the 
                    presence of the label 'Xremote' following the label 
                    'Enabled Characteristics:' in the PORT 
                    CHARACTERISTICS display."
                ::= { xremotePortEntry 2 }

            xremotePortXdmQuery OBJECT-TYPE
                SYNTAX INTEGER { specific(1), broadcast(2),
                                 indirect(3) }
                ACCESS read-write
                STATUS mandatory
                DESCRIPTION
                    "The type of query message issued by a port when 
                    searching for an X Display Manager (XDM). 
                    Corresponds directly to the PORT XDM QUERY and the 
                    'XDM Query:' in the PORT ALTERNATE CHARACTERISTICS 
                    display"
                ::= { xremotePortEntry 3 }

            xremotePortXdmHost OBJECT-TYPE
                SYNTAX DisplayString (SIZE (0..50))
                ACCESS read-write
                STATUS mandatory
                DESCRIPTION
                    "The Domain name or Internet address of the X 
                    Display Manager (XDM) for a port. Corresponds 
                    directly to the PORT XDM HOST and the 'XDM Host:' in 
                    the PORT ALTERNATE CHARACTERISTICS display"
                ::= { xremotePortEntry 4 }

            -- Additional individual objects

            xremoteServerClients OBJECT-TYPE
                SYNTAX Gauge
                ACCESS read-only
                STATUS mandatory
                DESCRIPTION
                    "The number of active X clients.  Corresponds 
                    directly to the value labeled 'Current Number of 
                    XClients:' in the SERVER XREMOTE display."
                ::= { xXremote 9 }


            -- the Rotary group

            -- Implementation of this group is mandatory for all iTouch
            -- systems that implement rotaries

            rotaryNumber OBJECT-TYPE
                SYNTAX INTEGER
                ACCESS read-only
                STATUS mandatory
                DESCRIPTION
                    "The number of entries in the Rotary  table."
                ::= { xRotary 1 }


            -- The Rotary  table

            rotaryTable OBJECT-TYPE
                SYNTAX SEQUENCE OF RotaryEntry
                ACCESS not-accessible
                STATUS mandatory
                DESCRIPTION
                    "A list of rotary  entries."
                ::= { xRotary 2 }

            rotaryEntry OBJECT-TYPE
                SYNTAX RotaryEntry
                ACCESS not-accessible
                STATUS mandatory
                DESCRIPTION
                    "Parameter values for a rotary."
                INDEX { rotaryAddress }
                ::= { rotaryTable 1 }

            RotaryEntry ::=
                SEQUENCE {
                    rotaryAddress
                        IpAddress,
                    rotaryStatus
                        INTEGER,
                    rotaryPortMap
                        OCTET STRING
                }

            rotaryAddress OBJECT-TYPE
                SYNTAX IpAddress
                ACCESS read-only
                STATUS mandatory
                DESCRIPTION
                    "The internet address to be recognized as a rotary.  
                    Corresponds directly to the ip-address portion of 
                    SERVER INTERNET ROTARY and the value labeled 
                    'Internet Address' in the SERVER INTERNET ROTARY 
                    display."
                ::= { rotaryEntry 1 }

            rotaryStatus OBJECT-TYPE
                SYNTAX INTEGER { invalid(1), valid(2) }
                ACCESS read-write
                STATUS mandatory
                DESCRIPTION
                    "Status of this entry.  Setting the value to 
                    'invalid' invalidates the entry, corresponding 
                    directly to the CLEAR SERVER INTERNET ROTARY 
                    command.  It is an implementation-specific matter as 
                    to whether the agent removes an invalidated entry 
                    from the table. Setting the value to 'valid' in 
                    conjunction with a new rotaryAddress will add a 
                    new entry to the table. When adding a new entry,
                    one should also specify a rotaryPortMap as the DEFVAL
                    of 0..0 for rotaryPortMap is meaningless."
                DEFVAL { valid }
                ::= { rotaryEntry 2 }

            rotaryPortMap OBJECT-TYPE
                SYNTAX OCTET STRING
                ACCESS read-write
                STATUS mandatory
                DESCRIPTION
                    "The list of character ports that compose the 
                    rotary.  The OCTET STRING contains a bitmap, with 
                    one bit for each port, and enough octets for all the 
                    ports on the system.  Port numbers are as defined 
                    for charPortIndex in the Proposed Standard Internet 
                    Character MIB.  Corresponding bit numbers start with 
                    1 as the high-order bit of the first octet.  
                    Corresponds directly to port-list portion of SERVER 
                    INTERNET ROTARY and the value labeled 'Ports' in the 
                    SERVER INTERNET ROTARY display."
                DEFVAL { "" }  -- zero length
                ::= { rotaryEntry 3 }


            -- the EGP group

            -- Implementation of this group is mandatory for all iTouch
            -- systems that implement EGP

            egpRouting OBJECT-TYPE
                SYNTAX INTEGER { disabled(1), enabled(2) }
                ACCESS read-write
                STATUS mandatory
                DESCRIPTION
                    "Control for EGP routing services."
                ::= { xEgp 1 }

            egpStatus OBJECT-TYPE
                SYNTAX INTEGER { active(1), noMemory(2), noIpRouting(3),
                                 noEgpRouting(4), noNeighbors(5),
                                 noAS(6) }
                ACCESS read-only
                STATUS mandatory
                DESCRIPTION
                    "Status of the EGP routing services indicating why 
                    it is not running."
                ::= { xEgp 2 }

            egpNbrTable OBJECT-TYPE
                SYNTAX SEQUENCE OF EgpNbrEntry
                ACCESS not-accessible
                STATUS mandatory
                DESCRIPTION
                    "The EGP neighbor table."
                ::= { xEgp 3 }

            egpNbrEntry OBJECT-TYPE
                SYNTAX EgpNbrEntry
                ACCESS not-accessible
                STATUS mandatory
                DESCRIPTION
                    "Information about this entity's relationship with a 
                    particular EGP neighbor."
                INDEX { egpNbrAddr }
                ::= { egpNbrTable 1 }

            EgpNbrEntry ::=
                SEQUENCE {
                    egpNbrAddr
                        IpAddress,
                    egpNbrIntervalDead
                        INTEGER,
                    egpNbrStatus
                        INTEGER
                }

            egpNbrAddr OBJECT-TYPE
                SYNTAX IpAddress
                ACCESS read-only
                STATUS mandatory
                DESCRIPTION
                    "The IP address of this entry's EGP neighbor."
                ::= { egpNbrEntry 1 }

            egpNbrIntervalDead OBJECT-TYPE
                SYNTAX INTEGER (0..65535)
                ACCESS read-write
                STATUS mandatory
                DESCRIPTION
                    "The interval upon entering the cease or idle state 
                    before automatically assuming a Start Event has 
                    occured.  If a neighbor does not respond within 5 
                    minutes, a Stop Event will automatically occur.  The 
                    interval is in hundredths of seconds."
                DEFVAL { 30000 }
                ::= { egpNbrEntry 2 }

            egpNbrStatus OBJECT-TYPE
                SYNTAX INTEGER { invalid(1), valid(2) }
                ACCESS read-write
                STATUS mandatory
                DESCRIPTION
                    "The status of the entry for this neighbor.  Set to 
                    'invalid' to remove the entry."
                DEFVAL { valid }
                ::= { egpNbrEntry 3 }


            -- the OSPF group

            -- Implementation of this group is mandatory for all iTouch
            -- systems that implement OSPF

            ospfAutoConfigure OBJECT-TYPE
                SYNTAX INTEGER { disabled(1), enabled(2) }
                ACCESS read-write
                STATUS mandatory
                DESCRIPTION
                    "Control whether OSPF will automatically configure 
                    itself."
                ::= { xOspf 1 }

            ospfStatus OBJECT-TYPE
                SYNTAX INTEGER { active(1), noMemory(2), noIpRouting(3),
                                 noOspfRouting(4), noAreas(5),
                                 noInterfaces(6), noRtrId(7), 
                                 noBackBoneAndVirtualInterfaces(8),
                                 noBackBoneAndInterface(9),
                                 noBackBone(10) }
                ACCESS read-only
                STATUS mandatory
                DESCRIPTION
                    "Status of the OSPF routing services indicating why 
                    it is not running."
                ::= { xOspf 2 }

            -- the OSPF Interface Metric table

            ospfIfMtrcTable OBJECT-TYPE
                SYNTAX SEQUENCE OF OspfIfMtrcEntry
                ACCESS not-accessible
                STATUS mandatory
                DESCRIPTION
                    "The TOS metrics for a non-virtual interface 
                    identified by the interface index."
                ::= { xOspf 3 }

            ospfIfMtrcEntry OBJECT-TYPE
                SYNTAX OspfIfMtrcEntry
                ACCESS not-accessible
                STATUS mandatory
                DESCRIPTION
                    "A particular TOS metric for a non-virtual interface 
                    identified by the interface index."
                INDEX { ospfIfMtrcIpAddress, ospfIfMtrcAddressLessIf,
                        ospfIfMtrcTos }
                ::= { ospfIfMtrcTable 1 }

            OspfIfMtrcEntry ::=
                SEQUENCE {
                    ospfIfMtrcIpAddress
                        IpAddress,
                    ospfIfMtrcAddressLessIf
                        INTEGER,
                    ospfIfMtrcTos
                        INTEGER,
                    ospfIfMtrcCostActual
                        INTEGER
                }

            ospfIfMtrcIpAddress OBJECT-TYPE
                SYNTAX IpAddress
                ACCESS read-only
                STATUS mandatory
                DESCRIPTION
                    "Same as ospfIfMetricIpAddress in OSPF MIB, the IP 
                    address of this OSPF interface."
                REFERENCE
                    "OSPF Version 2 Management Information Base, RFC 
                    1253"
                ::= { ospfIfMtrcEntry 1 }

            ospfIfMtrcAddressLessIf OBJECT-TYPE
                SYNTAX INTEGER
                ACCESS read-only
                STATUS mandatory
                DESCRIPTION
                    "Same as ospfIfMetricAddressLessIf in OSPF MIB, for 
                    the purpose of easing the instancing of addressed 
                    and addressless interfaces.  This variable takes the 
                    value 0 on interfaces with IP Addresses, and the 
                    value of ifIndex for interfaces having no IP 
                    Address."
                REFERENCE
                    "OSPF Version 2 Management Information Base, RFC 
                    1253"
                ::= { ospfIfMtrcEntry 2 }

            ospfIfMtrcTos OBJECT-TYPE
                SYNTAX INTEGER ( 1..16 )
                ACCESS read-only
                STATUS mandatory
                DESCRIPTION
                    "Same as ospfIfMetricTOS in OSPF MIB, the type of 
                    service metric being referenced."
                REFERENCE
                    "OSPF Version 2 Management Information Base, RFC 
                    1253"
                ::= { ospfIfMtrcEntry 3 }

            ospfIfMtrcCostActual OBJECT-TYPE
                SYNTAX INTEGER ( 1..65535 )
                ACCESS read-only
                STATUS mandatory
                DESCRIPTION
                    "The actual cost of the metric in case it was set to 
                    auto."
                ::= { ospfIfMtrcEntry 4 }

            -- the OSPF Interface table

            ospfXIfTable OBJECT-TYPE
                SYNTAX SEQUENCE OF OspfXIfEntry
                ACCESS not-accessible
                STATUS mandatory
                DESCRIPTION
                    "The TOS metrics for a non-virtual interface 
                    identified by the interface index."
                ::= { xOspf 4 }

            ospfXIfEntry OBJECT-TYPE
                SYNTAX OspfXIfEntry
                ACCESS not-accessible
                STATUS mandatory
                DESCRIPTION
                    "Interface parameters for OSPF."
                INDEX { ospfXIfIpAddress, ospfXIfAddressLessIf }
                ::= { ospfXIfTable 1 }

            OspfXIfEntry ::=
                SEQUENCE {
                    ospfXIfIpAddress
                        IpAddress,
                    ospfXIfAddressLessIf
                        INTEGER,
                    ospfXIfTypeActual
                        INTEGER,
                    ospfXIfStatus
                        INTEGER
                }

            ospfXIfIpAddress OBJECT-TYPE
                SYNTAX IpAddress
                ACCESS read-only
                STATUS mandatory
                DESCRIPTION
                    "Same as ospfIfIpAddress in OSPF MIB, the IP address 
                    of this OSPF interface."
                REFERENCE
                    "OSPF Version 2 Management Information Base, RFC 
                    1253"
                ::= { ospfXIfEntry 1 }

            ospfXIfAddressLessIf OBJECT-TYPE
                SYNTAX INTEGER
                ACCESS read-only
                STATUS mandatory
                DESCRIPTION
                    "Same as ospfIfAddressLessIf in OSPF MIB, for the 
                    purpose of easing the instancing of addressed and 
                    addressless interfaces.  This variable takes the 
                    value 0 on interfaces with IP Addresses, and the 
                    value of ifIndex for interfaces having no IP 
                    Address."
                REFERENCE
                    "OSPF Version 2 Management Information Base, RFC 
                    1253"
                ::= { ospfXIfEntry 2 }

            ospfXIfTypeActual OBJECT-TYPE
                SYNTAX INTEGER { broadcast(1), nonbroadcast(2),
                                 pointToPoint(3) }
                ACCESS read-only
                STATUS mandatory
                DESCRIPTION
                    "The interface type."
                ::= { ospfXIfEntry 3 }

            ospfXIfStatus OBJECT-TYPE
                SYNTAX INTEGER { invalid(1), valid(2) }
                ACCESS read-write
                STATUS mandatory
                DESCRIPTION
                    "The status of the interface entry, including the 
                    entry in the standard OSPF MIB.  Set to 'invalid' to 
                    remove the entry."
                DEFVAL { valid }
                ::= { ospfXIfEntry 4 }

            -- the OSPF Area table

            ospfXAreaTable OBJECT-TYPE
                SYNTAX SEQUENCE OF OspfXAreaEntry
                ACCESS not-accessible
                STATUS mandatory
                DESCRIPTION
                    "Parameters for an OSPF area."
                ::= { xOspf 5 }

            ospfXAreaEntry OBJECT-TYPE
                SYNTAX OspfXAreaEntry
                ACCESS not-accessible
                STATUS mandatory
                DESCRIPTION
                    "An area entry."
                INDEX { ospfXAreaId }
                ::= { ospfXAreaTable 1 }

            OspfXAreaEntry ::=
                SEQUENCE {
                    ospfXAreaId
                        IpAddress,
                    ospfXAreaStatus
                        INTEGER
                }

            ospfXAreaId OBJECT-TYPE
                SYNTAX IpAddress
                ACCESS read-only
                STATUS mandatory
                DESCRIPTION
                    "Same as ospfAreaId in OSPF MIB, the ID of the 
                    area."
                REFERENCE
                    "OSPF Version 2 Management Information Base, RFC 
                    1253"
                ::= { ospfXAreaEntry 1 }

            ospfXAreaStatus OBJECT-TYPE
                SYNTAX INTEGER { invalid(1), valid(2) }
                ACCESS read-write
                STATUS mandatory
                DESCRIPTION
                    "The status of the area entry, including the entry 
                    in the standard OSPF MIB.  Set to 'invalid' to 
                    remove the entry."
                DEFVAL { valid }
                ::= { ospfXAreaEntry 2 }


            -- the Router IP group

            -- Implementation of this group is mandatory for all iTouch
            -- systems that implement IP and do through routing

            ipAdExtTable OBJECT-TYPE
                SYNTAX SEQUENCE OF IpAdExtEntry
                ACCESS not-accessible
                STATUS mandatory
                DESCRIPTION
                    "Table of additional fields indexed by local IP 
                    address.  An entry in this table is created or 
                    deleted when an entry in the ipAddrTable is created 
                    or deleted."
                ::= { xRouterIp 1 }

            ipAdExtEntry OBJECT-TYPE
                SYNTAX IpAdExtEntry
                ACCESS not-accessible
                STATUS mandatory
                DESCRIPTION
                    "A particular entry."
                INDEX { ipAdEntExtAddress }
                ::= { ipAdExtTable 1 }

            IpAdExtEntry ::=
                SEQUENCE {
                    ipAdEntExtAddress
                        IpAddress,
                    ipAdEntExtProxyArp
                        INTEGER,
                    ipAdEntExtRip
                        INTEGER
                }

            ipAdEntExtAddress OBJECT-TYPE
                SYNTAX IpAddress
                ACCESS read-only
                STATUS mandatory
                DESCRIPTION
                    "Same as ipAdEntAddr, a local address representing a 
                    network connection."
                ::= { ipAdExtEntry 1 }

            ipAdEntExtProxyArp OBJECT-TYPE
                SYNTAX INTEGER { enabled(2), disabled(1) }   
                ACCESS read-write
                STATUS mandatory
                DESCRIPTION
                    "Controls whether proxy ARP is active for this local 
                    address."
                DEFVAL { disabled }
                ::= { ipAdExtEntry 2 }

            ipAdEntExtRip OBJECT-TYPE
                SYNTAX INTEGER { enabled(2), disabled(1) }   
                ACCESS read-only
                STATUS deprecated
                DESCRIPTION
                    "Controls whether RIP as a router discovery protocol 
                    is active for this local address."
                DEFVAL { disabled }
                ::= { ipAdExtEntry 3 }


            -- the IP Router Interface table

            ipRouterIfTable OBJECT-TYPE
                SYNTAX SEQUENCE OF IpRouterIfEntry
                ACCESS not-accessible
                STATUS mandatory
                DESCRIPTION
                    "Table of IP router values indexed by interface."
                ::= { xRouterIp 2 }

            ipRouterIfEntry OBJECT-TYPE
                SYNTAX IpRouterIfEntry
                ACCESS not-accessible
                STATUS mandatory
                DESCRIPTION
                    "A particular entry."
                INDEX { ipRouterIfIndex }
                ::= { ipRouterIfTable 1 }

            IpRouterIfEntry ::=
                SEQUENCE {
                    ipRouterIfIndex
                        INTEGER,
                    ipRouterIfProtocolPriority
                        INTEGER,
                    ipRouterIfMTU
                        INTEGER,
                    ipRouterIfRDP
                        INTEGER,
                    ipRouterIfArpPacketsIn
                        Counter,
                    ipRouterIfArpPacketsOut
                        Counter,
                    ipRouterIfPacketsIn
                        Counter,
                    ipRouterIfPacketsOut
                        Counter,
                    ipRouterIfForwardsIn
                        Counter,
                    ipRouterIfForwardsOut
                        Counter
                }

            ipRouterIfIndex OBJECT-TYPE
                SYNTAX INTEGER
                ACCESS read-only
                STATUS mandatory
                DESCRIPTION
                    "The index of the interface; same as IfIndex."
                ::= { ipRouterIfEntry 1 }

            ipRouterIfProtocolPriority OBJECT-TYPE
                SYNTAX INTEGER { low(1), medium(3), high(5) }
                ACCESS read-write
                STATUS mandatory
                DESCRIPTION
                    "The priority at which all Internet routed packets 
                    will be placed on the WAN output queue."
                DEFVAL { medium }
                ::= { ipRouterIfEntry 2 }

            ipRouterIfMTU OBJECT-TYPE
                SYNTAX INTEGER (128..65535)
                ACCESS read-write
                STATUS mandatory
                DESCRIPTION
                    "The size of the largest datagram that IP can
                     transmit on this interface.  The default value
                     is actually hardware dependent."
                DEFVAL { 1500 }
                ::= { ipRouterIfEntry 3 }

            ipRouterIfRDP OBJECT-TYPE
                SYNTAX INTEGER { enabled(1), disabled(2) }
                ACCESS read-write
                STATUS mandatory
                DESCRIPTION
                    "Control for whether the router side of the Router 
                    Discovery Protocol is running on this interface."
                DEFVAL { disabled }
                ::= { ipRouterIfEntry 4 }

            ipRouterIfArpPacketsIn OBJECT-TYPE
                SYNTAX Counter
                ACCESS read-only
                STATUS mandatory
                DESCRIPTION
                    "The number of ARP packets received on this 
                    interface."
                ::= { ipRouterIfEntry 5 }

            ipRouterIfArpPacketsOut OBJECT-TYPE
                SYNTAX Counter
                ACCESS read-only
                STATUS mandatory
                DESCRIPTION
                    "The number of ARP packets sent on this interface."
                ::= { ipRouterIfEntry 6 }

            ipRouterIfPacketsIn OBJECT-TYPE
                SYNTAX Counter
                ACCESS read-only
                STATUS mandatory
                DESCRIPTION
                    "The number of IP packets received on this 
                    interface."
                ::= { ipRouterIfEntry 7 }

            ipRouterIfPacketsOut OBJECT-TYPE
                SYNTAX Counter
                ACCESS read-only
                STATUS mandatory
                DESCRIPTION
                    "The number of IP packets sent on this interface."
                ::= { ipRouterIfEntry 8 }

            ipRouterIfForwardsIn OBJECT-TYPE
                SYNTAX Counter
                ACCESS read-only
                STATUS mandatory
                DESCRIPTION
                    "The number of IP packets received on this interface 
                    that were forwarded."
                ::= { ipRouterIfEntry 9 }

            ipRouterIfForwardsOut OBJECT-TYPE
                SYNTAX Counter
                ACCESS read-only
                STATUS mandatory
                DESCRIPTION
                    "The number of IP packets sent on this interface 
                    that were forwarded."
                ::= { ipRouterIfEntry 10 }


            -- the IP Router Traffic subgroup

            -- Implementation of this subgroup is mandatory for all
            -- iTouch IP router systems that implement traffic
            -- monitoring

            xIpTraffic   OBJECT IDENTIFIER ::= { xRouterIp 3 }

            ipTrafficSort OBJECT-TYPE
                SYNTAX INTEGER { ready(1), execute(2) }
                ACCESS read-write
                STATUS mandatory
                DESCRIPTION
                    "Setting to 'execute' causes the most recent traffic 
                    information to be sorted into the ipTrafficTable. 
                    The sorting precedence is: decreasing percentage, 
                    increasing destination address, increasing source 
                    address, and increasing interface number.  Setting 
                    to 'ready' has no effect."
                ::= { xIpTraffic 1 }

            -- Note:  additional individual objects follow table

            ipTrafficTable OBJECT-TYPE
                SYNTAX SEQUENCE OF IpTrafficEntry
                ACCESS not-accessible
                STATUS mandatory
                DESCRIPTION
                    "A list of traffic entries, sorted in the order 
                    specified by ipTrafficSort."
                ::= { xIpTraffic 2 }

            ipTrafficEntry OBJECT-TYPE
                SYNTAX IpTrafficEntry
                ACCESS not-accessible
                STATUS mandatory
                DESCRIPTION
                    "A traffic entry."
                INDEX { ipTrafficIndex }
                ::= { ipTrafficTable 1 }

            IpTrafficEntry ::=
                SEQUENCE {
                    ipTrafficIndex
                        INTEGER,
                    ipTrafficPercent
                         INTEGER,
                    ipTrafficDstAddr
                        IpAddress,
                    ipTrafficSrcAddr
                        IpAddress,
                    ipTrafficProtocol
                         INTEGER,
                    ipTrafficDstPort
                         INTEGER,
                    ipTrafficSrcPort
                         INTEGER,
                    ipTrafficIf
                        INTEGER

                }

            ipTrafficIndex OBJECT-TYPE
                SYNTAX INTEGER
                ACCESS read-only
                STATUS mandatory
                DESCRIPTION
                    "Identification of this traffic entry."
                ::= { ipTrafficEntry 1 }

            ipTrafficPercent OBJECT-TYPE
                SYNTAX INTEGER 
                ACCESS read-only
                STATUS mandatory
                DESCRIPTION
                    "The percentage of total traffic that this traffic 
                    entry represents, in tenths of a percent."
                ::= { ipTrafficEntry 2 }

            ipTrafficDstAddr OBJECT-TYPE
                SYNTAX IpAddress
                ACCESS read-only
                STATUS mandatory
                DESCRIPTION
                    "The destination IP address of the traffic entry."
                ::= { ipTrafficEntry 3 }

            ipTrafficSrcAddr OBJECT-TYPE
                SYNTAX IpAddress
                ACCESS read-only
                STATUS mandatory
                DESCRIPTION
                    "The source IP address of the traffic entry."
                ::= { ipTrafficEntry 4 }

            ipTrafficProtocol OBJECT-TYPE
                SYNTAX INTEGER ( 0..255 )
                ACCESS read-only
                STATUS mandatory
                DESCRIPTION
                    "The IP protocol type of the traffic entry."
                ::= { ipTrafficEntry 5 }

            ipTrafficDstPort OBJECT-TYPE
                SYNTAX INTEGER ( 0..65535 )
                ACCESS read-only
                STATUS mandatory
                DESCRIPTION
                    "The destination TCP/UDP port of the traffic 
                    entry."
                ::= { ipTrafficEntry 6 }

            ipTrafficSrcPort OBJECT-TYPE
                SYNTAX INTEGER ( 0..65535 )
                ACCESS read-only
                STATUS mandatory
                DESCRIPTION
                    "The source TCP/UDP port of the traffic entry."
                ::= { ipTrafficEntry 7 }

            ipTrafficIf OBJECT-TYPE
                SYNTAX INTEGER
                ACCESS read-only
                STATUS mandatory
                DESCRIPTION
                    "The inbound interface to which the traffic entry 
                    applies.  This value is the same as IfIndex."
                ::= { ipTrafficEntry 8 }

            -- additional individual objects

            ipTrafficMonitoring OBJECT-TYPE
                SYNTAX INTEGER { enabled(1), disabled(2) }
                ACCESS read-write
                STATUS mandatory
                DESCRIPTION
                    "Control for whether the router side of the Router 
                    Discovery Protocol is running on this interface."
                ::= { xIpTraffic 3 }

            -- IP Net to Media table extension

            xIpNetToMediaTable OBJECT-TYPE
                SYNTAX SEQUENCE OF XIpNetToMediaEntry
                ACCESS not-accessible
                STATUS mandatory
                DESCRIPTION
                    "iTouch extensions to the IP Address Translation 
                    Table."
                ::= { xRouterIp 4 }

            xIpNetToMediaEntry OBJECT-TYPE
                SYNTAX XIpNetToMediaEntry
                ACCESS not-accessible
                STATUS mandatory
                DESCRIPTION
                    "Entry parameters."
                INDEX { ifIndex, ipNetToMediaNetAddress }
                ::= { xIpNetToMediaTable 1 }

            XIpNetToMediaEntry ::=
                SEQUENCE {
                    xIpNetToMediaCircuit
                        INTEGER,
                    xIpNetToMediaReverseArp
                        INTEGER
                }

            xIpNetToMediaCircuit OBJECT-TYPE
                SYNTAX INTEGER
                ACCESS read-write
                STATUS mandatory
                DESCRIPTION
                    "An additional identifier for the circuit (i.e. 
                    Frame Relay DLCI or X.25 VC) which the entry 
                    extends."
                ::= { xIpNetToMediaEntry 1 }

            xIpNetToMediaReverseArp OBJECT-TYPE
                SYNTAX INTEGER { disabled(1), enabled(2) }
                ACCESS read-write
                STATUS mandatory
                DESCRIPTION
                    "Whether reverse ARP is supported on this entry."
                ::= { xIpNetToMediaEntry 2 }


            -- the Router UDP group

            -- Implementation of this group is mandatory for all iTouch
            -- systems that implement UDP and do through routing

            -- Individual objects follow the UDP Port table

            -- the UDP Broadcast Server table

            udpBcstServerTable OBJECT-TYPE
                SYNTAX SEQUENCE OF UdpBcstServerEntry
                ACCESS not-accessible
                STATUS mandatory
                DESCRIPTION
                    "Table of servers to whom UDP broadcast messages 
                    will be forwarded."
                ::= { xRouterUdp 1 }

            udpBcstServerEntry OBJECT-TYPE
                SYNTAX UdpBcstServerEntry
                ACCESS not-accessible
                STATUS mandatory
                DESCRIPTION
                    "A particular entry."
                INDEX { udpBcstServerAddress }
                ::= { udpBcstServerTable 1 }

            UdpBcstServerEntry ::=
                SEQUENCE {
                    udpBcstServerAddress
                        IpAddress,
                    udpBcstServerStatus
                        INTEGER
                }

            udpBcstServerAddress OBJECT-TYPE
                SYNTAX IpAddress
                ACCESS read-only
                STATUS mandatory
                DESCRIPTION
                    "Internet address of the server."
                ::= { udpBcstServerEntry 1 }

            udpBcstServerStatus OBJECT-TYPE
                SYNTAX INTEGER { invalid(1), valid(2) }
                ACCESS read-write
                STATUS mandatory
                DESCRIPTION
                    "The status of the server.  Set to 'invalid' to 
                    remove the entry."
                DEFVAL { valid }
                ::= { udpBcstServerEntry 2 }


            -- the UDP Broadcast Port table

            udpBcstPortTable OBJECT-TYPE
                SYNTAX SEQUENCE OF UdpBcstPortEntry
                ACCESS not-accessible
                STATUS mandatory
                DESCRIPTION
                    "Table of incoming UDP destination port numbers for 
                    which UDP broadcasts will be forwarded."
                ::= { xRouterUdp 2 }

            udpBcstPortEntry OBJECT-TYPE
                SYNTAX UdpBcstPortEntry
                ACCESS not-accessible
                STATUS mandatory
                DESCRIPTION
                    "A particular entry."
                INDEX { udpBcstPort }
                ::= { udpBcstPortTable 1 }

            UdpBcstPortEntry ::=
                SEQUENCE {
                    udpBcstPort
                        INTEGER,
                    udpBcstPortStatus
                        INTEGER
                }

            udpBcstPort OBJECT-TYPE
                SYNTAX INTEGER
                ACCESS read-only
                STATUS mandatory
                DESCRIPTION
                    "The incoming destination UDP port number."
                ::= { udpBcstPortEntry 1 }

            udpBcstPortStatus OBJECT-TYPE
                SYNTAX INTEGER { invalid(1), valid(2) }
                ACCESS read-write
                STATUS mandatory
                DESCRIPTION
                    "The status of broadcast forwarding for the port.  
                    Set to 'invalid' to remove the entry."
                DEFVAL { valid }
                ::= { udpBcstPortEntry 2 }


            -- Individual objects

            udpBcstRouting OBJECT-TYPE
                SYNTAX INTEGER { disabled(1), enabled(2) }
                ACCESS read-write
                STATUS mandatory
                DESCRIPTION
                    "The indication of whether this entity forwards UDP 
                    broadcasts."
                DEFVAL { disabled }
                ::= { xRouterUdp 3 }


            -- the Router Policy group

            -- Implementation of this group is mandatory for all iTouch
            -- systems that implement routing policy and do through
            -- routing

            -- the Router Policy group contains three subgroups:

            xImport OBJECT IDENTIFIER ::= { xRouterPolicy 1 }
            xExport OBJECT IDENTIFIER ::= { xRouterPolicy 2 }
            xFilter OBJECT IDENTIFIER ::= { xRouterPolicy 3 }

            -- the Import subgroup

            -- the EGP Import table

            impEgpRuleTable OBJECT-TYPE
                SYNTAX SEQUENCE OF ImpEgpRuleEntry
                ACCESS not-accessible
                STATUS mandatory
                DESCRIPTION
                    "The EGP import table."
                ::= { xImport 1 }

            impEgpRuleEntry OBJECT-TYPE
                SYNTAX ImpEgpRuleEntry
                ACCESS not-accessible
                STATUS mandatory
                DESCRIPTION
                    "An EGP import rule.  Each rule is keyed by the 
                    Autonomous System of the EGP neighbor and the IP 
                    network of the route learned from the  neighbor.  
                    The AS can be set to a wild card as can the IP 
                    network. When a route is learned from a neighbor, 
                    the most specific import rule is applied to the 
                    route.  The route is either accepted or discarded 
                    and its metrics are applied according to the rule.  
                    An exact match on the AS and IP network is the most 
                    exact rule.  An exact match on the AS and a wild 
                    card match on the IP network is the 2nd most exact 
                    rule. A wild card match on the AS and an exact match 
                    on the IP network is the 3rd most exact match.  
                    Finally, a total wild card match is the least exact 
                    rule."
                INDEX { impEgpRuleAs, impEgpRuleNetwork }
                ::= { impEgpRuleTable 1 }

            ImpEgpRuleEntry ::=
                SEQUENCE { 
                    impEgpRuleAs
                        INTEGER,
                    impEgpRuleNetwork
                        IpAddress,
                    impEgpRuleAction
                        INTEGER,
                    impEgpRulePreference
                        INTEGER,
                    impEgpRuleType
                        INTEGER,
                    impEgpRuleMetricAction
                        INTEGER,
                    impEgpRuleMetric
                        INTEGER,
                    impEgpRuleStatus
                        INTEGER
                }

            impEgpRuleAs OBJECT-TYPE
                SYNTAX INTEGER ( 0..65535 )
                ACCESS read-only
                STATUS mandatory
                DESCRIPTION
                    "The Autonomous System of the neighbor.  The value 
                    65535 is a wild card matching any AS number."
                ::= { impEgpRuleEntry 1 }

            impEgpRuleNetwork OBJECT-TYPE
                SYNTAX IpAddress
                ACCESS read-only
                STATUS mandatory
                DESCRIPTION
                    "The IP network learned from the neighbor.  The 
                    value 255.255.255.255 is a wild card matching any 
                    network."
                ::= { impEgpRuleEntry 2 }

            impEgpRuleAction OBJECT-TYPE
                SYNTAX INTEGER { discard(1), accept(2) }
                ACCESS read-write
                STATUS mandatory
                DESCRIPTION
                    "Control whether the route is learned or 
                    discarded."
                DEFVAL { accept }
                ::= { impEgpRuleEntry 3 }

            impEgpRulePreference OBJECT-TYPE
                SYNTAX INTEGER ( 1..255 )
                ACCESS read-write
                STATUS mandatory
                DESCRIPTION
                    "Preference to be stored with the route. The lower 
                    preference is preferred."
                DEFVAL { 2 }
                ::= { impEgpRuleEntry 4 }

            impEgpRuleType OBJECT-TYPE
                SYNTAX INTEGER ( 1..2 )
                ACCESS read-write
                STATUS mandatory
                DESCRIPTION
                    "Type to be stored with the route. The type is based 
                    on the OSPF external type and used to help compare 
                    metrics.  Type 1 is preferred over type 2."
                DEFVAL { 1 }
                ::= { impEgpRuleEntry 5 }

            impEgpRuleMetricAction OBJECT-TYPE
                SYNTAX INTEGER { replace(1), increment(2),
                                 decrement(3) }
                ACCESS read-write
                STATUS mandatory
                DESCRIPTION
                    "How to apply the impEgpRuleMetric field to the 
                    metric learned with the route before storing it in 
                    the routing table."
                DEFVAL { increment }
                ::= { impEgpRuleEntry 6 }

            impEgpRuleMetric OBJECT-TYPE
                SYNTAX INTEGER (0..16777215)
                ACCESS read-write
                STATUS mandatory
                DESCRIPTION
                    "Metric value to be applied to the metric learned 
                    learned with the route before storing it in the 
                    routing table."
                DEFVAL { 0 }
                ::= { impEgpRuleEntry 7 }

            impEgpRuleStatus OBJECT-TYPE
                SYNTAX INTEGER { invalid(1), valid(2) }
                ACCESS read-write
                STATUS mandatory
                DESCRIPTION
                    "The status of the rule.  Set to 'invalid' to remove 
                    the rule.  If the all wild card rule is removed, it 
                    is  automatically readded with default values."
                DEFVAL { valid }
                ::= { impEgpRuleEntry 8 }

            -- the OSPF Import table

            impOspfRuleTable OBJECT-TYPE
                SYNTAX SEQUENCE OF ImpOspfRuleEntry
                ACCESS not-accessible
                STATUS mandatory
                DESCRIPTION
                    "The OSPF import table."
                ::= { xImport 2 }

            impOspfRuleEntry OBJECT-TYPE
                SYNTAX ImpOspfRuleEntry
                ACCESS not-accessible
                STATUS mandatory
                DESCRIPTION
                    "An OSPF import rule.  Each rule is keyed by the IP 
                    network of the route and the AS from which it was 
                    learned.  The Ip network and the AS can both be set 
                    to a wild card.  When an OSPF route is added to the 
                    routing table, the most specific import rule is 
                    applied to set the preference of the route.  An 
                    exact match on the Ip network and on the AS is the 
                    most exact rule.  An exact match on the IP network 
                    and a wild card match on the AS is the 2nd most 
                    exact rule.  A wild card match on both the  on the 
                    AS and IP network is the next and least exact 
                    rule."
                INDEX { impOspfRuleNetwork }
                ::= { impOspfRuleTable 1 }

            ImpOspfRuleEntry ::=
                SEQUENCE {
                    impOspfRuleNetwork
                        IpAddress,
                    impOspfRulePreference
                        INTEGER,
                    impOspfRuleStatus
                        INTEGER
                }

            impOspfRuleNetwork OBJECT-TYPE
                SYNTAX IpAddress
                ACCESS read-only
                STATUS mandatory
                DESCRIPTION
                    "The IP network of the route.  The value 
                    255.255.255.255 is a wild card matching any 
                    network."
                ::= { impOspfRuleEntry 1 }

            impOspfRulePreference OBJECT-TYPE
                SYNTAX INTEGER ( 1..255 )
                ACCESS read-write
                STATUS mandatory
                DESCRIPTION
                    "Preference to be stored with the route. The lower 
                    preference is preferred."
                DEFVAL { 8 }
                ::= { impOspfRuleEntry 2 }

            impOspfRuleStatus OBJECT-TYPE
                SYNTAX INTEGER { invalid(1), valid(2) }
                ACCESS read-write
                STATUS mandatory
                DESCRIPTION
                    "The status of the rule.  Set to 'invalid' to remove 
                    the rule.  If the all wild card rule is removed, it 
                    is  automatically readded with default values."
                DEFVAL { valid }
                ::= { impOspfRuleEntry 3 }

            -- the RIP Import table

            impRipRuleTable OBJECT-TYPE
                SYNTAX SEQUENCE OF ImpRipRuleEntry
                ACCESS not-accessible
                STATUS mandatory
                DESCRIPTION
                    "The RIP import table."
                ::= { xImport 3 }

            impRipRuleEntry OBJECT-TYPE
                SYNTAX ImpRipRuleEntry
                ACCESS not-accessible
                STATUS mandatory
                DESCRIPTION
                    "A RIP import rule.  Each rule is keyed by the 
                    interface and the IP network of the route learned 
                    from the neighbor.  The route is either accepted or 
                    discarded and its metrics are applied according to 
                    the rule.  An exact match on the IP network is the 
                    rule that will be applied.  If an exact match does 
                    not exist, the rule with the wild card IP network is 
                    used."
                INDEX { impRipRuleFromIf, impRipRuleNetwork }
                ::= { impRipRuleTable 1 }

            ImpRipRuleEntry ::=
                SEQUENCE {
                    impRipRuleFromIf
                        IpAddress,
                    impRipRuleNetwork
                        IpAddress,
                    impRipRuleAction
                        INTEGER,
                    impRipRulePreference
                        INTEGER,
                    impRipRuleType
                        INTEGER,
                    impRipRuleMetricAction
                        INTEGER,
                    impRipRuleMetric
                        INTEGER,
                    impRipRuleStatus
                        INTEGER
                }

            impRipRuleFromIf OBJECT-TYPE
                SYNTAX IpAddress
                ACCESS read-only
                STATUS mandatory
                DESCRIPTION
                    "The interface index of the interface where the rule 
                    applies, same as ifIndex."
                ::= { impRipRuleEntry 1 }

            impRipRuleNetwork OBJECT-TYPE
                SYNTAX IpAddress
                ACCESS read-only
                STATUS mandatory
                DESCRIPTION
                    "The IP network learned from the neighbor.  The 
                    value 255.255.255.255 is a wild card matching any 
                    network."
                ::= { impRipRuleEntry 2 }

            impRipRuleAction OBJECT-TYPE
                SYNTAX INTEGER { discard(1), accept(2) }
                ACCESS read-write
                STATUS mandatory
                DESCRIPTION
                    "Control whether the route is learned or 
                    discarded."
                DEFVAL { accept }
                ::= { impRipRuleEntry 3 }

            impRipRulePreference OBJECT-TYPE
                SYNTAX INTEGER ( 0..255 )
                ACCESS read-write
                STATUS mandatory
                DESCRIPTION
                    "Preference to be stored with the route. The lower 
                    preference are preferred."
                DEFVAL { 12 }
                ::= { impRipRuleEntry 4 }

            impRipRuleType OBJECT-TYPE
                SYNTAX INTEGER ( 1..2 )
                ACCESS read-write
                STATUS mandatory
                DESCRIPTION
                    "Type to be stored with the route. The type is based 
                    on the OSPF external type and used to help compare 
                    metrics.  Type 1 is preferred over type 2."
                DEFVAL { 1 }
                ::= { impRipRuleEntry 5 }

            impRipRuleMetricAction OBJECT-TYPE
                SYNTAX INTEGER { replace(1), increment(2), decrement(3) }
                ACCESS read-write
                STATUS mandatory
                DESCRIPTION
                    "How to apply the impRipRuleMetric field to the 
                    metric learned with the route before storing it in 
                    the routing table."
                DEFVAL { increment }
                ::= { impRipRuleEntry 6 }

            impRipRuleMetric OBJECT-TYPE
                SYNTAX INTEGER (0..16777215)
                ACCESS read-write
                STATUS mandatory
                DESCRIPTION
                    "Metric value to be applied to the metric learned 
                    learned with the route before storing it in the 
                    routing table."
                DEFVAL { 0 }
                ::= { impRipRuleEntry 7 }

            impRipRuleStatus OBJECT-TYPE
                SYNTAX INTEGER { invalid(1), valid(2) }
                ACCESS read-write
                STATUS mandatory
                DESCRIPTION
                    "The status of the rule.  Set to 'invalid' to remove 
                    the rule.  If the all wild card rule is removed, it 
                    is automatically readded with default values."
                DEFVAL { valid }
                ::= { impRipRuleEntry 8 }

            -- the ISIS Import table

            impIsisRuleTable OBJECT-TYPE
            	SYNTAX SEQUENCE OF ImpIsisRuleEntry
            	ACCESS not-accessible
            	STATUS mandatory
            	DESCRIPTION
            		"The Isis import table."
            	::= { xImport 4 }
            
            impIsisRuleEntry OBJECT-TYPE
            	SYNTAX ImpIsisRuleEntry
            	ACCESS not-accessible
            	STATUS mandatory
            	DESCRIPTION
            		"An Isis import rule.  Each rule is keyed by the IP
                    network of the route learned from the neighbor.  The
                    route is either accepted or discarded and its metrics
                    are applied according to the rule.  An exact match on the
                    IP network is the rule that will be applied.  If an exact
            		match does not exist, the rule with the wild card IP
                    network is used."
            	INDEX { impIsisRuleNetwork }
            	::= { impIsisRuleTable 1 }
            
            ImpIsisRuleEntry ::=
            	SEQUENCE {
            		impIsisRuleNetwork
            			IpAddress,
            		impIsisRuleAction
            			INTEGER,
            		impIsisRulePreference
            			INTEGER,
            		impIsisRuleType
            			INTEGER,
            		impIsisRuleMetricAction
            			INTEGER,
            		impIsisRuleMetric
            			INTEGER,
            		impIsisRuleStatus
            			INTEGER
            	}
            
            impIsisRuleNetwork OBJECT-TYPE
            	SYNTAX IpAddress
            	ACCESS read-only
            	STATUS mandatory
            	DESCRIPTION
            		"The IP network learned from the neighbor.  The value
                    255.255.255.255 is a wild card matching any network."
            	::= { impIsisRuleEntry 1 }
            
            impIsisRuleAction OBJECT-TYPE
            	SYNTAX INTEGER { discard(1), accept(2) }
            	ACCESS read-write
            	STATUS mandatory
            	DESCRIPTION
            		"Control whether the route is learned or discarded."
            	DEFVAL { accept }
            	::= { impIsisRuleEntry 2 }
            
            impIsisRulePreference OBJECT-TYPE
            	SYNTAX INTEGER ( 0..255 )
            	ACCESS read-write
            	STATUS mandatory
            	DESCRIPTION
            		"Preference to be stored with the route. The lower
                    preference are preferred."
            	DEFVAL { 6 }
            	::= { impIsisRuleEntry 3 }
            
            impIsisRuleType OBJECT-TYPE
            	SYNTAX INTEGER ( 1..2 )
            	ACCESS read-write
            	STATUS mandatory
            	DESCRIPTION
            		"Type to be stored with the route. The type is based on
                    the OSPF external type and used to help compare metrics.
                    Type 1 is preferred over type 2."
            	DEFVAL { 1 }
            	::= { impIsisRuleEntry 4 }
            
            impIsisRuleMetricAction OBJECT-TYPE
            	SYNTAX INTEGER { replace(1), increment(2), decrement(3) }
            	ACCESS read-write
            	STATUS mandatory
            	DESCRIPTION
            		"How to apply the impIsisRuleMetric field to the metric
                    learned with the route before storing it in the routing
                    table."
            	DEFVAL { increment }
            	::= { impIsisRuleEntry 5 }
            
            impIsisRuleMetric OBJECT-TYPE
            	SYNTAX INTEGER 
            	ACCESS read-write
            	STATUS mandatory
            	DESCRIPTION
            		"Metric value to be applied to the metric learned learned
                    with the route before storing it in the routing table."
            	DEFVAL { 0 }
            	::= { impIsisRuleEntry 6 }
            
            impIsisRuleStatus OBJECT-TYPE
            	SYNTAX INTEGER { invalid(1), valid(2) }
            	ACCESS read-write
            	STATUS mandatory
            	DESCRIPTION
            		"The status of the rule.  Set to 'invalid' to remove
            		the rule.  If the all wild card rule is removed, it is 
            		automatically readded with default values."
            	DEFVAL { valid }
            	::= { impIsisRuleEntry 7 }


            -- the Export subgroup

            expEgpToEgpRuleTable OBJECT-TYPE
                SYNTAX SEQUENCE OF ExpEgpToEgpRuleEntry
                ACCESS not-accessible
                STATUS mandatory
                DESCRIPTION
                    "The EGP to EGP export table."
                ::= { xExport 1 }

            expEgpToEgpRuleEntry OBJECT-TYPE
                SYNTAX ExpEgpToEgpRuleEntry
                ACCESS not-accessible
                STATUS mandatory
                DESCRIPTION
                    "An EGP to EGP export rule.  Each rule is keyed by 
                    the Autonomous  System of the EGP neighbor, the IP 
                    network of the EGP route in the  routing table, and 
                    the Autonomous System from which the route was 
                    learned.  The neighbor (to) AS can be set to a wild 
                    card as can the IP network and the (from) AS.  The 
                    route is either accepted to be  advertised to the 
                    neighbor or discarded from being advertised, and its 
                    metric is applied according to the rule.  The best 
                    match is as  follows: 

                            To As  IP Network     From AS  Rank

                            exact       exact       exact   1st
                            exact       exact   wild card   2nd
                            exact   wild card       exact   3rd
                            exact   wild card   wild card   4th
                        wild card       exact       exact   5th
                        wild card       exact   wild card   6th
                        wild card   wild card       exact   7th
                        wild card   wild card   wild card   8th
                    "
                INDEX { expEgpToEgpRuleToAs, expEgpToEgpRuleNetwork,
                        expEgpToEgpRuleFromAs }
                ::= { expEgpToEgpRuleTable 1 }

            ExpEgpToEgpRuleEntry ::=
                SEQUENCE {
                    expEgpToEgpRuleToAs
                        INTEGER,
                    expEgpToEgpRuleNetwork
                        IpAddress,
                    expEgpToEgpRuleFromAs
                        INTEGER,
                    expEgpToEgpRuleAction
                        INTEGER,
                    expEgpToEgpRuleMetricAction
                        INTEGER,
                    expEgpToEgpRuleMetric
                        INTEGER,
                    expEgpToEgpRuleStatus
                        INTEGER
                }

            expEgpToEgpRuleToAs OBJECT-TYPE
                SYNTAX INTEGER ( 0..65535 )
                ACCESS read-only
                STATUS mandatory
                DESCRIPTION
                    "The Autonomous System of the neighbor.  The value 
                    65535 is  a wild card matching any AS number."
                ::= { expEgpToEgpRuleEntry 1 }

            expEgpToEgpRuleNetwork OBJECT-TYPE
                SYNTAX IpAddress 
                ACCESS read-only
                STATUS mandatory
                DESCRIPTION
                    "The IP network of the route in the route table.  
                    The value 255.255.255.255 is a wild card matching 
                    any network."
                ::= { expEgpToEgpRuleEntry 2 }

            expEgpToEgpRuleFromAs OBJECT-TYPE
                SYNTAX INTEGER ( 0..65535 )
                ACCESS read-only
                STATUS mandatory
                DESCRIPTION
                    "The Autonomous System of the route in the route 
                    table.  The value 65535 is  a wild card matching any 
                    AS number."
                ::= { expEgpToEgpRuleEntry 3 }

            expEgpToEgpRuleAction OBJECT-TYPE
                SYNTAX INTEGER { hide(1), advertise(2) }
                ACCESS read-write
                STATUS mandatory
                DESCRIPTION
                    "Control whether the route is advertised or not."
                DEFVAL { advertise }
                ::= { expEgpToEgpRuleEntry 4 }

            expEgpToEgpRuleMetricAction OBJECT-TYPE
                SYNTAX INTEGER { replace(1), increment(2),
                                 decrement(3) }
                ACCESS read-write
                STATUS mandatory
                DESCRIPTION
                    "How to apply the expEgpToEgpRuleMetric field to the 
                    metric in the route table entry before the route is 
                    advertised."
                DEFVAL { increment }
                ::= { expEgpToEgpRuleEntry 5 }

            expEgpToEgpRuleMetric OBJECT-TYPE
                SYNTAX INTEGER (0..16777215)
                ACCESS read-write
                STATUS mandatory
                DESCRIPTION
                    "Metric value to be applied to the metric in the 
                    route table entry before the route is advertised."
                DEFVAL { 0 }
                ::= { expEgpToEgpRuleEntry 6 }

            expEgpToEgpRuleStatus OBJECT-TYPE
                SYNTAX INTEGER { invalid(1), valid(2) }
                ACCESS read-write
                STATUS mandatory
                DESCRIPTION
                    "The status of the rule.  Set to 'invalid' to remove 
                    the rule.  If the all wild card rule is removed, it 
                    is  automatically readded with default values."
                DEFVAL { valid }
                ::= { expEgpToEgpRuleEntry 7 }

            -- ospf to egp

            expOspfToEgpRuleTable OBJECT-TYPE
                SYNTAX SEQUENCE OF ExpOspfToEgpRuleEntry
                ACCESS not-accessible
                STATUS mandatory
                DESCRIPTION
                    "The OSPF to EGP export table."
                ::= { xExport 2 }

            expOspfToEgpRuleEntry OBJECT-TYPE
                SYNTAX ExpOspfToEgpRuleEntry
                ACCESS not-accessible
                STATUS mandatory
                DESCRIPTION
                    "An OSPF to EGP export rule.  Each rule is keyed by 
                    the Autonomous  System of the EGP neighbor, the IP 
                    network of the OSPF route in the  routing table, and 
                    the Autonomous System from which the route was 
                    learned.  The neighbor (to) AS can be set to a wild 
                    card as can the IP network and the (from) AS.  The 
                    route is either accepted to be  advertised to the 
                    neighbor or discarded from being advertised, and its 
                    metric is applied according to the rule.  The best 
                    match is as  follows:

                            To As  IP Network     From AS  Rank

                            exact       exact       exact   1st
                            exact       exact   wild card   2nd
                            exact   wild card       exact   3rd
                            exact   wild card   wild card   4th
                        wild card       exact       exact   5th
                        wild card       exact   wild card   6th
                        wild card   wild card       exact   7th
                        wild card   wild card   wild card   8th
                    "
                INDEX { expOspfToEgpRuleToAs, expOspfToEgpRuleNetwork,
                        expOspfToEgpRuleFromAs }
                ::= { expOspfToEgpRuleTable 1 }

            ExpOspfToEgpRuleEntry ::=
                SEQUENCE {
                    expOspfToEgpRuleToAs
                        INTEGER,
                    expOspfToEgpRuleNetwork
                        IpAddress,
                    expOspfToEgpRuleFromAs
                        INTEGER,
                    expOspfToEgpRuleAction
                        INTEGER,
                    expOspfToEgpRuleMetricAction
                        INTEGER,
                    expOspfToEgpRuleMetric
                        INTEGER,
                    expOspfToEgpRuleStatus
                        INTEGER
                }

            expOspfToEgpRuleToAs OBJECT-TYPE
                SYNTAX INTEGER ( 0..65535 )
                ACCESS read-only
                STATUS mandatory
                DESCRIPTION
                    "The Autonomous System of the neighbor.  The value 
                    65535 is  a wild card matching any AS number."
                ::= { expOspfToEgpRuleEntry 1 }

            expOspfToEgpRuleNetwork OBJECT-TYPE
                SYNTAX IpAddress
                ACCESS read-only
                STATUS mandatory
                DESCRIPTION
                    "The IP network of the route in the route table.  
                    The value 255.255.255.255 is a wild card matching 
                    any network."
                ::= { expOspfToEgpRuleEntry 2 }

            expOspfToEgpRuleFromAs OBJECT-TYPE
                SYNTAX INTEGER ( 0..65535 )
                ACCESS read-only
                STATUS mandatory
                DESCRIPTION
                    "The Autonomous System of the route in the route 
                    table.  Local indicates that the route was not an 
                    external OSPF route.  The  value 65535 is a wild 
                    card matching any AS number, and the value 65534 is 
                    for routes within the local AS."
                ::= { expOspfToEgpRuleEntry 3 }

            expOspfToEgpRuleAction OBJECT-TYPE
                SYNTAX INTEGER { hide(1), advertise(2) }
                ACCESS read-write
                STATUS mandatory
                DESCRIPTION
                    "Control whether the route is advertised or not."
                DEFVAL { advertise }
                ::= { expOspfToEgpRuleEntry 4 }

            expOspfToEgpRuleMetricAction OBJECT-TYPE
                SYNTAX INTEGER { replace(1), increment(2),
                                 decrement(3) }
                ACCESS read-write
                STATUS mandatory
                DESCRIPTION
                    "How to apply the expOspfToEgpRuleMetric field to 
                    the metric in the route table entry before the route 
                    is advertised."
                DEFVAL { increment }
                ::= { expOspfToEgpRuleEntry 5 }

            expOspfToEgpRuleMetric OBJECT-TYPE
                SYNTAX INTEGER (0..16777215)
                ACCESS read-write
                STATUS mandatory
                DESCRIPTION
                    "Metric value to be applied to the metric in the 
                    route table entry before the route is advertised."
                DEFVAL { 0 }
                ::= { expOspfToEgpRuleEntry 6 }

            expOspfToEgpRuleStatus OBJECT-TYPE
                SYNTAX INTEGER { invalid(1), valid(2) }
                ACCESS read-write
                STATUS mandatory
                DESCRIPTION
                    "The status of the rule.  Set to 'invalid' to remove 
                    the rule.  If the all wild card rule is removed, it 
                    is  automatically readded with default values."
                DEFVAL { valid }
                ::= { expOspfToEgpRuleEntry 7 }

            -- static to egp

            expStaticToEgpRuleTable OBJECT-TYPE
                SYNTAX SEQUENCE OF ExpStaticToEgpRuleEntry
                ACCESS not-accessible
                STATUS mandatory
                DESCRIPTION
                    "The Static to EGP export table."
                ::= { xExport 3 }

            expStaticToEgpRuleEntry OBJECT-TYPE
                SYNTAX ExpStaticToEgpRuleEntry
                ACCESS not-accessible
                STATUS mandatory
                DESCRIPTION
                    "An Static to EGP export rule.  Each rule is keyed 
                    by the Autonomous  System of the EGP neighbor and 
                    the IP network of the Static route in the  routing 
                    table.  The neighbor (to) AS can be set to a wild 
                    card as can the IP network.  The route is either 
                    accepted to be advertised to the  neighbor or 
                    discarded from being advertised, and its metric is 
                    applied  according to the rule.  The best match is 
                    as follows:

                            To As  IP Network  Rank

                            exact       exact   1st
                            exact   wild card   2nd
                        wild card       exact   3rd
                        wild card   wild card   4th
                    "
                INDEX { expStaticToEgpRuleToAs,
                        expStaticToEgpRuleNetwork }
                ::= { expStaticToEgpRuleTable 1 }

            ExpStaticToEgpRuleEntry ::=
                SEQUENCE {
                    expStaticToEgpRuleToAs
                        INTEGER,
                    expStaticToEgpRuleNetwork
                        IpAddress,
                    expStaticToEgpRuleAction
                        INTEGER,
                    expStaticToEgpRuleMetricAction
                        INTEGER,
                    expStaticToEgpRuleMetric
                        INTEGER,
                    expStaticToEgpRuleStatus
                        INTEGER
                }

            expStaticToEgpRuleToAs OBJECT-TYPE
                SYNTAX INTEGER ( 0..65535 )
                ACCESS read-only
                STATUS mandatory
                DESCRIPTION
                    "The Autonomous System of the neighbor.  The value 
                    65535 is  a wild card matching any AS number."
                ::= { expStaticToEgpRuleEntry 1 }

            expStaticToEgpRuleNetwork OBJECT-TYPE
                SYNTAX IpAddress
                ACCESS read-only
                STATUS mandatory
                DESCRIPTION
                    "The IP network of the route in the route table.  
                    The value 255.255.255.255 is a wild card matching 
                    any network."
                ::= { expStaticToEgpRuleEntry 2 }

            expStaticToEgpRuleAction OBJECT-TYPE
                SYNTAX INTEGER { hide(1), advertise(2) }
                ACCESS read-write
                STATUS mandatory
                DESCRIPTION
                    "Control whether the route is advertised or not."
                DEFVAL { advertise }
                ::= { expStaticToEgpRuleEntry 3 }

            expStaticToEgpRuleMetricAction OBJECT-TYPE
                SYNTAX INTEGER { replace(1), increment(2),
                                 decrement(3) }
                ACCESS read-write
                STATUS mandatory
                DESCRIPTION
                    "How to apply the expStaticToEgpRuleMetric field to 
                    the metric in the route table entry before the route 
                    is advertised."
                DEFVAL { increment }
                ::= { expStaticToEgpRuleEntry 4 }

            expStaticToEgpRuleMetric OBJECT-TYPE
                SYNTAX INTEGER (0..16777215)
                ACCESS read-write
                STATUS mandatory
                DESCRIPTION
                    "Metric value to be applied to the metric in the 
                    route table entry before the route is advertised."
                DEFVAL { 0 }
                ::= { expStaticToEgpRuleEntry 5 }

            expStaticToEgpRuleStatus OBJECT-TYPE
                SYNTAX INTEGER { invalid(1), valid(2) }
                ACCESS read-write
                STATUS mandatory
                DESCRIPTION
                    "The status of the rule.  Set to 'invalid' to remove 
                    the rule.  If the all wild card rule is removed, it 
                    is  automatically readded with default values."
                DEFVAL { valid }
                ::= { expStaticToEgpRuleEntry 6 }

            -- egp to ospf

            expEgpToOspfRuleTable OBJECT-TYPE
                SYNTAX SEQUENCE OF ExpEgpToOspfRuleEntry
                ACCESS not-accessible
                STATUS mandatory
                DESCRIPTION
                    "The EGP to OSPF export table."
                ::= { xExport 4 }

            expEgpToOspfRuleEntry OBJECT-TYPE
                SYNTAX ExpEgpToOspfRuleEntry
                ACCESS not-accessible
                STATUS mandatory
                DESCRIPTION
                    "An EGP to OSPF export rule.  Each rule is keyed by 
                    the IP network  of the EGP route in the routing 
                    table, and the Autonomous System  from which the 
                    route was learned.  The Ip network can be set to a 
                    wild card as can the (from) AS.  The route is either 
                    accepted to be  advertised to the neighbor or 
                    discarded from being advertised, and its metric is 
                    applied according to the rule.  The best match is as  
                    follows:

                       IP Network     From AS  Rank

                            exact       exact   1st
                            exact   wild card   2nd
                        wild card       exact   3rd
                        wild card   wild card   4th
                    "
                INDEX { expEgpToOspfRuleNetwork, expEgpToOspfRuleFromAs }
                ::= { expEgpToOspfRuleTable 1 }

            ExpEgpToOspfRuleEntry ::=
                SEQUENCE {
                    expEgpToOspfRuleNetwork
                        IpAddress,
                    expEgpToOspfRuleFromAs
                        INTEGER,
                    expEgpToOspfRuleAction
                        INTEGER,
                    expEgpToOspfRuleStatus
                        INTEGER
                }

            expEgpToOspfRuleNetwork OBJECT-TYPE
                SYNTAX IpAddress
                ACCESS read-only
                STATUS mandatory
                DESCRIPTION
                    "The IP network of the route in the route table.  
                    The value 255.255.255.255 is a wild card matching 
                    any network."
                ::= { expEgpToOspfRuleEntry 1 }

            expEgpToOspfRuleFromAs OBJECT-TYPE
                SYNTAX INTEGER ( 0..65535 )
                ACCESS read-only
                STATUS mandatory
                DESCRIPTION
                    "The Autonomous System of the route in the route 
                    table.  The value 65535 is  a wild card matching any 
                    AS number."
                ::= { expEgpToOspfRuleEntry 2 }

            expEgpToOspfRuleAction OBJECT-TYPE
                SYNTAX INTEGER { hide(1), advertise(2) }
                ACCESS read-write
                STATUS mandatory
                DESCRIPTION
                    "Control whether the route is advertised or not."
                DEFVAL { advertise }
                ::= { expEgpToOspfRuleEntry 3 }

            expEgpToOspfRuleStatus OBJECT-TYPE
                SYNTAX INTEGER { invalid(1), valid(2) }
                ACCESS read-write
                STATUS mandatory
                DESCRIPTION
                    "The status of the rule.  Set to 'invalid' to remove 
                    the rule.  If the all wild card rule is removed, it 
                    is  automatically readded with default values."
                DEFVAL { valid }
                ::= { expEgpToOspfRuleEntry 4 }

            -- rip to egp

            expRipToEgpRuleTable OBJECT-TYPE
                SYNTAX SEQUENCE OF ExpRipToEgpRuleEntry
                ACCESS not-accessible
                STATUS mandatory
                DESCRIPTION
                    "The Rip to EGP export table."
                ::= { xExport 5 }

            expRipToEgpRuleEntry OBJECT-TYPE
                SYNTAX ExpRipToEgpRuleEntry
                ACCESS not-accessible
                STATUS mandatory
                DESCRIPTION
                    "An Rip to EGP export rule.  Each rule is keyed by 
                    the Autonomous System of the EGP neighbor and the IP 
                    network of the Rip route in the routing table.  The 
                    neighbor (to) AS can be set to a wild card as can 
                    the IP network.  The route is either accepted to be 
                    advertised to the neighbor or discarded from being 
                    advertised, and its metric is applied according to 
                    the rule.  The best match is as follows:

                    To As       IP Network   Best Match Rank

                    exact       exact        1st
                    exact       wild card    2nd
                    wild card   exact        3rd
                    wild card   wild card    4th
                    "
                INDEX { expRipToEgpRuleToAs,
                        expRipToEgpRuleNetwork }
                ::= { expRipToEgpRuleTable 1 }

            ExpRipToEgpRuleEntry ::=
                SEQUENCE {
                    expRipToEgpRuleToAs
                        INTEGER,
                    expRipToEgpRuleNetwork
                        IpAddress,
                    expRipToEgpRuleAction
                        INTEGER,
                    expRipToEgpRuleMetricAction
                        INTEGER,
                    expRipToEgpRuleMetric
                        INTEGER,
                    expRipToEgpRuleStatus
                        INTEGER
                }

            expRipToEgpRuleToAs OBJECT-TYPE
                SYNTAX INTEGER ( 0..65535 )
                ACCESS read-only
                STATUS mandatory
                DESCRIPTION
                    "The Autonomous System of the neighbor.  The value 
                    65535 is a wild card matching any AS number."
                ::= { expRipToEgpRuleEntry 1 }

            expRipToEgpRuleNetwork OBJECT-TYPE
                SYNTAX IpAddress
                ACCESS read-only
                STATUS mandatory
                DESCRIPTION
                    "The IP network of the route in the route table.  
                    The value 255.255.255.255 is a wild card matching 
                    any network."
                ::= { expRipToEgpRuleEntry 2 }

            expRipToEgpRuleAction OBJECT-TYPE
                SYNTAX INTEGER { hide(1), advertise(2) }
                ACCESS read-write
                STATUS mandatory
                DESCRIPTION
                    "Control whether the route is advertised or not."
                DEFVAL { advertise }
                ::= { expRipToEgpRuleEntry 3 }

            expRipToEgpRuleMetricAction OBJECT-TYPE
                SYNTAX INTEGER { replace(1), increment(2), decrement(3) }
                ACCESS read-write
                STATUS mandatory
                DESCRIPTION
                    "How to apply the expRipToEgpRuleMetric field to the 
                    metric in the route table entry before the route is 
                    advertised."
                DEFVAL { increment }
                ::= { expRipToEgpRuleEntry 4 }

            expRipToEgpRuleMetric OBJECT-TYPE
                SYNTAX INTEGER (0..16777215)
                ACCESS read-write
                STATUS mandatory
                DESCRIPTION
                    "Metric value to be applied to the metric in the 
                    route table entry before the route is advertised."
                DEFVAL { 0 }
                ::= { expRipToEgpRuleEntry 5 }

            expRipToEgpRuleStatus OBJECT-TYPE
                SYNTAX INTEGER { invalid(1), valid(2) }
                ACCESS read-write
                STATUS mandatory
                DESCRIPTION
                    "The status of the rule.  Set to 'invalid' to remove 
                    the rule.  If the all wild card rule is removed, it 
                    is automatically readded with default values."
                DEFVAL { valid }
                ::= { expRipToEgpRuleEntry 6 }

            -- rip to ospf

            expRipToOspfRuleTable OBJECT-TYPE
                SYNTAX SEQUENCE OF ExpRipToOspfRuleEntry
                ACCESS not-accessible
                STATUS mandatory
                DESCRIPTION
                    "The RIP to OSPF export table."
                ::= { xExport 6 }

            expRipToOspfRuleEntry OBJECT-TYPE
                SYNTAX ExpRipToOspfRuleEntry
                ACCESS not-accessible
                STATUS mandatory
                DESCRIPTION
                    "A RIP to OSPF export rule.  Each rule is keyed by 
                    the IP network of the RIP route in the routing 
                    table.  The IP network can be set to a wild card.  
                    The route is either accepted to be advertised to the 
                    neighbor or discarded from being advertised, and its 
                    metric is applied according to the rule.  The best 
                    match is as follows:

                    IP Network     Best Match Rank

                    exact          1st
                    wild card      2nd
                    "
                INDEX { expRipToOspfRuleNetwork }
                ::= { expRipToOspfRuleTable 1 }

            ExpRipToOspfRuleEntry ::=
                SEQUENCE {
                    expRipToOspfRuleNetwork
                        IpAddress,
                    expRipToOspfRuleAction
                        INTEGER,
                    expRipToOspfRuleStatus
                        INTEGER
                }

            expRipToOspfRuleNetwork OBJECT-TYPE
                SYNTAX IpAddress
                ACCESS read-only
                STATUS mandatory
                DESCRIPTION
                    "The IP network of the route in the route table.  
                    The value 255.255.255.255 is a wild card matching 
                    any network."
                ::= { expRipToOspfRuleEntry 1 }

            expRipToOspfRuleAction OBJECT-TYPE
                SYNTAX INTEGER { hide(1), advertise(2) }
                ACCESS read-write
                STATUS mandatory
                DESCRIPTION
                    "Control whether the route is advertised or not."
                DEFVAL { advertise }
                ::= { expRipToOspfRuleEntry 2 }

            expRipToOspfRuleStatus OBJECT-TYPE
                SYNTAX INTEGER { invalid(1), valid(2) }
                ACCESS read-write
                STATUS mandatory
                DESCRIPTION
                    "The status of the rule.  Set to 'invalid' to remove 
                    the rule.  If the all wild card rule is removed, it 
                    is automatically readded with default values."
                DEFVAL { valid }
                ::= { expRipToOspfRuleEntry 3 }


            -- egp to rip

            expEgpToRipRuleTable OBJECT-TYPE
                SYNTAX SEQUENCE OF ExpEgpToRipRuleEntry
                ACCESS not-accessible
                STATUS mandatory
                DESCRIPTION
                    "The EGP to RIP export table."
                ::= { xExport 7 }

            expEgpToRipRuleEntry OBJECT-TYPE
                SYNTAX ExpEgpToRipRuleEntry
                ACCESS not-accessible
                STATUS mandatory
                DESCRIPTION
                    "An EGP to RIP export rule.  Each rule is keyed by 
                    the Autonomous System of the EGP neighbor, the IP 
                    network of the EGP route in the routing table, and 
                    the Autonomous System from which the route was 
                    learned.  The IP network can be set to a wild card 
                    as can the the from AS.  The route is either 
                    accepted to be advertised to the neighbor or 
                    discarded from being advertised, and its metric is 
                    applied according to the rule.  The best match is as 
                    follows:

                    IP Network   From AS     Best Match Rank

                    exact        exact       1st
                    exact        wild card   2nd
                    wild card    exact       3rd
                    wild card    wild card   4th
                    "
                INDEX { expEgpToRipRuleToIf, expEgpToRipRuleNetwork,
                        expEgpToRipRuleFromAs }
                ::= { expEgpToRipRuleTable 1 }

            ExpEgpToRipRuleEntry ::=
                SEQUENCE {
                    expEgpToRipRuleToIf
                        IpAddress,
                    expEgpToRipRuleNetwork
                        IpAddress,
                    expEgpToRipRuleFromAs
                        INTEGER,
                    expEgpToRipRuleAction
                        INTEGER,
                    expEgpToRipRuleMetricAction
                        INTEGER,
                    expEgpToRipRuleMetric
                        INTEGER,
                    expEgpToRipRuleStatus
                        INTEGER
                }

            expEgpToRipRuleToIf OBJECT-TYPE
                SYNTAX IpAddress 
                ACCESS read-only
                STATUS mandatory
                DESCRIPTION
                    "The IP address of the RIP interface to which the 
                    rule applies."
                ::= { expEgpToRipRuleEntry 1 }

            expEgpToRipRuleNetwork OBJECT-TYPE
                SYNTAX IpAddress 
                ACCESS read-only
                STATUS mandatory
                DESCRIPTION
                    "The IP network of the route in the route table.  
                    The value 255.255.255.255 is a wild card matching 
                    any network."
                ::= { expEgpToRipRuleEntry 2 }

            expEgpToRipRuleFromAs OBJECT-TYPE
                SYNTAX INTEGER ( 0..65535 )
                ACCESS read-only
                STATUS mandatory
                DESCRIPTION
                    "The Autonomous System of the route in the route 
                    table.  The value 65535 is a wild card matching any 
                    AS number."
                ::= { expEgpToRipRuleEntry 3 }

            expEgpToRipRuleAction OBJECT-TYPE
                SYNTAX INTEGER { hide(1), advertise(2) }
                ACCESS read-write
                STATUS mandatory
                DESCRIPTION
                    "Control whether the route is advertised or not."
                DEFVAL { advertise }
                ::= { expEgpToRipRuleEntry 4 }

            expEgpToRipRuleMetricAction OBJECT-TYPE
                SYNTAX INTEGER { replace(1), increment(2), decrement(3) }
                ACCESS read-write
                STATUS mandatory
                DESCRIPTION
                    "How to apply the expEgpToRipRuleMetric field to the 
                    metric in the route table entry before the route is 
                    advertised."
                DEFVAL { increment }
                ::= { expEgpToRipRuleEntry 5 }

            expEgpToRipRuleMetric OBJECT-TYPE
                SYNTAX INTEGER (0..16777215)
                ACCESS read-write
                STATUS mandatory
                DESCRIPTION
                    "Metric value to be applied to the metric in the 
                    route table entry before the route is advertised."
                DEFVAL { 0 }
                ::= { expEgpToRipRuleEntry 6 }

            expEgpToRipRuleStatus OBJECT-TYPE
                SYNTAX INTEGER { invalid(1), valid(2) }
                ACCESS read-write
                STATUS mandatory
                DESCRIPTION
                    "The status of the rule.  Set to 'invalid' to remove 
                    the rule.  If the all wild card rule is removed, it 
                    is automatically readded with default values."
                DEFVAL { valid }
                ::= { expEgpToRipRuleEntry 7 }

            -- Ospf to rip

            expOspfToRipRuleTable OBJECT-TYPE
                SYNTAX SEQUENCE OF ExpOspfToRipRuleEntry
                ACCESS not-accessible
                STATUS mandatory
                DESCRIPTION
                    "The OSPF to RIP export table."
                ::= { xExport 8 }

            expOspfToRipRuleEntry OBJECT-TYPE
                SYNTAX ExpOspfToRipRuleEntry
                ACCESS not-accessible
                STATUS mandatory
                DESCRIPTION
                    "An Ospf to RIP export rule.  Each rule is keyed by 
                    the Autonomous System of the Ospf neighbor, the IP 
                    network of the Ospf route in the routing table, and 
                    the Autonomous System from which the route was 
                    learned.  The IP network can be set to a wild card 
                    as can the the from AS.  The route is either 
                    accepted to be advertised to the neighbor or 
                    discarded from being advertised, and its metric is 
                    applied according to the rule.  The best match is as 
                    follows:

                    IP Network   From AS     Best Match Rank

                    exact        exact       1st
                    exact        wild card   2nd
                    wild card    exact       3rd
                    wild card    wild card   4th
                    "
                INDEX { expOspfToRipRuleToIf, expOspfToRipRuleNetwork,
                        expOspfToRipRuleFromAs }
                ::= { expOspfToRipRuleTable 1 }

            ExpOspfToRipRuleEntry ::=
                SEQUENCE {
                    expOspfToRipRuleToIf
                        IpAddress,
                    expOspfToRipRuleNetwork
                        IpAddress,
                    expOspfToRipRuleFromAs
                        INTEGER,
                    expOspfToRipRuleAction
                        INTEGER,
                    expOspfToRipRuleMetricAction
                        INTEGER,
                    expOspfToRipRuleMetric
                        INTEGER,
                    expOspfToRipRuleStatus
                        INTEGER
                }

            expOspfToRipRuleToIf OBJECT-TYPE
                SYNTAX IpAddress
                ACCESS read-only
                STATUS mandatory
                DESCRIPTION
                    "The IP address of the RIP interface to which the 
                    rule applies."
                ::= { expOspfToRipRuleEntry 1 }

            expOspfToRipRuleNetwork OBJECT-TYPE
                SYNTAX IpAddress 
                ACCESS read-only
                STATUS mandatory
                DESCRIPTION
                    "The IP network of the route in the route table.  
                    The value 255.255.255.255 is a wild card matching 
                    any network."
                ::= { expOspfToRipRuleEntry 2 }

            expOspfToRipRuleFromAs OBJECT-TYPE
                SYNTAX INTEGER ( 0..65535 )
                ACCESS read-only
                STATUS mandatory
                DESCRIPTION
                    "The Autonomous System of the route in the route 
                    table.  The value 65535 is a wild card matching any 
                    AS number, and the value 65534 is for routes within 
                    the local AS."
                ::= { expOspfToRipRuleEntry 3 }

            expOspfToRipRuleAction OBJECT-TYPE
                SYNTAX INTEGER { hide(1), advertise(2) }
                ACCESS read-write
                STATUS mandatory
                DESCRIPTION
                    "Control whether the route is advertised or not."
                DEFVAL { advertise }
                ::= { expOspfToRipRuleEntry 4 }

            expOspfToRipRuleMetricAction OBJECT-TYPE
                SYNTAX INTEGER { replace(1), increment(2), decrement(3) }
                ACCESS read-write
                STATUS mandatory
                DESCRIPTION
                    "How to apply the expOspfToRipRuleMetric field to 
                    the metric in the route table entry before the route 
                    is advertised."
                DEFVAL { increment }
                ::= { expOspfToRipRuleEntry 5 }

            expOspfToRipRuleMetric OBJECT-TYPE
                SYNTAX INTEGER (0..16777215)
                ACCESS read-write
                STATUS mandatory
                DESCRIPTION
                    "Metric value to be applied to the metric in the 
                    route table entry before the route is advertised."
                DEFVAL { 0 }
                ::= { expOspfToRipRuleEntry 6 }

            expOspfToRipRuleStatus OBJECT-TYPE
                SYNTAX INTEGER { invalid(1), valid(2) }
                ACCESS read-write
                STATUS mandatory
                DESCRIPTION
                    "The status of the rule.  Set to 'invalid' to remove 
                    the rule.  If the all wild card rule is removed, it 
                    is automatically readded with default values.  The 
                    same is true for the all wild cards where the AS is 
                    set to local"
                DEFVAL { valid }
                ::= { expOspfToRipRuleEntry 7 }

            -- rip to rip

            expRipToRipRuleTable OBJECT-TYPE
                SYNTAX SEQUENCE OF ExpRipToRipRuleEntry
                ACCESS not-accessible
                STATUS mandatory
                DESCRIPTION
                    "The Rip to Rip export table."
                ::= { xExport 9 }

            expRipToRipRuleEntry OBJECT-TYPE
                SYNTAX ExpRipToRipRuleEntry
                ACCESS not-accessible
                STATUS mandatory
                DESCRIPTION
                    "An Rip to Rip export rule.  Each rule is keyed by 
                    the IP network of the Rip route in the routing 
                    table.  The neighbor IP network can be set to a wild 
                    card.  The route is either accepted to be advertised 
                    to the neighbor or discarded from being advertised, 
                    and its metric is applied according to the rule.  
                    The best match is as follows:

                    IP Network   Best Match Rank

                    exact        1st
                    wild card    2nd
                    "
                INDEX { expRipToRipRuleToIf, expRipToRipRuleNetwork }
                ::= { expRipToRipRuleTable 1 }

            ExpRipToRipRuleEntry ::=
                SEQUENCE {
                    expRipToRipRuleToIf
                        IpAddress,
                    expRipToRipRuleNetwork
                        IpAddress,
                    expRipToRipRuleAction
                        INTEGER,
                    expRipToRipRuleMetricAction
                        INTEGER,
                    expRipToRipRuleMetric
                        INTEGER,
                    expRipToRipRuleStatus
                        INTEGER
                }

            expRipToRipRuleToIf OBJECT-TYPE
                SYNTAX IpAddress
                ACCESS read-only
                STATUS mandatory
                DESCRIPTION
                    "The IP address of the RIP interface to which the 
                    rule applies."
                ::= { expRipToRipRuleEntry 1 }

            expRipToRipRuleNetwork OBJECT-TYPE
                SYNTAX IpAddress
                ACCESS read-only
                STATUS mandatory
                DESCRIPTION
                    "The IP network of the route in the route table.  
                    The value 255.255.255.255 is a wild card matching 
                    any network."
                ::= { expRipToRipRuleEntry 2 }

            expRipToRipRuleAction OBJECT-TYPE
                SYNTAX INTEGER { hide(1), advertise(2) }
                ACCESS read-write
                STATUS mandatory
                DESCRIPTION
                    "Control whether the route is advertised or not."
                DEFVAL { advertise }
                ::= { expRipToRipRuleEntry 3 }

            expRipToRipRuleMetricAction OBJECT-TYPE
                SYNTAX INTEGER { replace(1), increment(2), decrement(3) }
                ACCESS read-write
                STATUS mandatory
                DESCRIPTION
                    "How to apply the expRipToRipRuleMetric field to the 
                    metric in the route table entry before the route is 
                    advertised."
                DEFVAL { increment }
                ::= { expRipToRipRuleEntry 4 }

            expRipToRipRuleMetric OBJECT-TYPE
                SYNTAX INTEGER (0..16777215)
                ACCESS read-write
                STATUS mandatory
                DESCRIPTION
                    "Metric value to be applied to the metric in the 
                    route table entry before the route is advertised."
                DEFVAL { 0 }
                ::= { expRipToRipRuleEntry 5 }

            expRipToRipRuleStatus OBJECT-TYPE
                SYNTAX INTEGER { invalid(1), valid(2) }
                ACCESS read-write
                STATUS mandatory
                DESCRIPTION
                    "The status of the rule.  Set to 'invalid' to remove 
                    the rule.  If the all wild card rule is removed, it 
                    is automatically readded with default values."
                DEFVAL { valid }
                ::= { expRipToRipRuleEntry 6 }

            -- static to rip

            expStaticToRipRuleTable OBJECT-TYPE
                SYNTAX SEQUENCE OF ExpStaticToRipRuleEntry
                ACCESS not-accessible
                STATUS mandatory
                DESCRIPTION
                    "The Static to Rip export table."
                ::= { xExport 10 }

            expStaticToRipRuleEntry OBJECT-TYPE
                SYNTAX ExpStaticToRipRuleEntry
                ACCESS not-accessible
                STATUS mandatory
                DESCRIPTION
                    "An Static to Rip export rule.  Each rule is keyed 
                    by the IP network of the Static route in the routing 
                    table.  The neighbor IP network can be set to a wild 
                    card.  The route is either accepted to be advertised 
                    to the neighbor or discarded from being advertised, 
                    and its metric is applied according to the rule.  
                    The best match is as follows:

                    IP Network   Best Match Rank

                    exact        1st
                    wild card    2nd
                    "
                INDEX { expStaticToRipRuleToIf,
                        expStaticToRipRuleNetwork }
                ::= { expStaticToRipRuleTable 1 }

            ExpStaticToRipRuleEntry ::=
                SEQUENCE {
                    expStaticToRipRuleToIf
                        IpAddress,
                    expStaticToRipRuleNetwork
                        IpAddress,
                    expStaticToRipRuleAction
                        INTEGER,
                    expStaticToRipRuleMetricAction
                        INTEGER,
                    expStaticToRipRuleMetric
                        INTEGER,
                    expStaticToRipRuleStatus
                        INTEGER
                }

            expStaticToRipRuleToIf OBJECT-TYPE
                SYNTAX IpAddress
                ACCESS read-only
                STATUS mandatory
                DESCRIPTION
                    "The IP address of the RIP interface to which the 
                    rule applies."
                ::= { expStaticToRipRuleEntry 1 }

            expStaticToRipRuleNetwork OBJECT-TYPE
                SYNTAX IpAddress
                ACCESS read-only
                STATUS mandatory
                DESCRIPTION
                    "The IP network of the route in the route table.  
                    The value 255.255.255.255 is a wild card matching 
                    any network."
                ::= { expStaticToRipRuleEntry 2 }

            expStaticToRipRuleAction OBJECT-TYPE
                SYNTAX INTEGER { hide(1), advertise(2) }
                ACCESS read-write
                STATUS mandatory
                DESCRIPTION
                    "Control whether the route is advertised or not."
                DEFVAL { advertise }
                ::= { expStaticToRipRuleEntry 3 }

            expStaticToRipRuleMetricAction OBJECT-TYPE
                SYNTAX INTEGER { replace(1), increment(2), decrement(3) }
                ACCESS read-write
                STATUS mandatory
                DESCRIPTION
                    "How to apply the expStaticToRipRuleMetric field to 
                    the metric in the route table entry before the route 
                    is advertised."
                DEFVAL { increment }
                ::= { expStaticToRipRuleEntry 4 }

            expStaticToRipRuleMetric OBJECT-TYPE
                SYNTAX INTEGER (0..16777215)
                ACCESS read-write
                STATUS mandatory
                DESCRIPTION
                    "Metric value to be applied to the metric in the 
                    route table entry before the route is advertised."
                DEFVAL { 0 }
                ::= { expStaticToRipRuleEntry 5 }

            expStaticToRipRuleStatus OBJECT-TYPE
                SYNTAX INTEGER { invalid(1), valid(2) }
                ACCESS read-write
                STATUS mandatory
                DESCRIPTION
                    "The status of the rule.  Set to 'invalid' to remove 
                    the rule.  If the all wild card rule is removed, it 
                    is automatically readded with default values."
                DEFVAL { valid }
                ::= { expStaticToRipRuleEntry 6 }

            -- Isis to egp
            
            expIsisToEgpRuleTable OBJECT-TYPE
            	SYNTAX SEQUENCE OF ExpIsisToEgpRuleEntry
            	ACCESS not-accessible
            	STATUS mandatory
            	DESCRIPTION
            		"The Isis to EGP export table."
            	::= { xExport 11 }
            
            expIsisToEgpRuleEntry OBJECT-TYPE
            	SYNTAX ExpIsisToEgpRuleEntry
            	ACCESS not-accessible
            	STATUS mandatory
            	DESCRIPTION
            		"An Isis to EGP export rule.  Each rule is keyed by the Autonomous 
            		System of the EGP neighbor and the IP network of the Isis route in the 
            		routing table.  The neighbor (to) AS can be set to a wild card as can
            		the IP network.  The route is either accepted to be advertised to the 
            		neighbor or discarded from being advertised, and its metric is applied 
            		according to the rule.  The best match is as follows:
            
            				To As       IP Network      Best Match Rank
            
            				exact		exact			1st
            				exact		wild card		2nd
            				wild card	exact			3rd
            				wild card	wild card		4th
            
            		."
            	INDEX { expIsisToEgpRuleToAs, expIsisToEgpRuleNetwork }
            	::= { expIsisToEgpRuleTable 1 }
            
            ExpIsisToEgpRuleEntry ::=
            	SEQUENCE {
            		expIsisToEgpRuleToAs
            			INTEGER,
            		expIsisToEgpRuleNetwork
            			IpAddress,
            		expIsisToEgpRuleAction
            			INTEGER,
            		expIsisToEgpRuleMetricAction
            			INTEGER,
            		expIsisToEgpRuleMetric
            			INTEGER,
            		expIsisToEgpRuleStatus
            			INTEGER
            	}
            
            expIsisToEgpRuleToAs OBJECT-TYPE
            	SYNTAX INTEGER ( 0..65535 )
            	ACCESS read-only
            	STATUS mandatory
            	DESCRIPTION
            		"The Autonomous System of the neighbor.  The value 65535 is 
            		a wild card matching any AS number."
            	::= { expIsisToEgpRuleEntry 1 }
            
            expIsisToEgpRuleNetwork OBJECT-TYPE
            	SYNTAX IpAddress
            	ACCESS read-only
            	STATUS mandatory
            	DESCRIPTION
            		"The IP network of the route in the route table.  The value 
            		255.255.255.255	is a wild card matching any network."
            	::= { expIsisToEgpRuleEntry 2 }
            
            expIsisToEgpRuleAction OBJECT-TYPE
            	SYNTAX INTEGER { hide(1), advertise(2) }
            	ACCESS read-write
            	STATUS mandatory
            	DESCRIPTION
            		"Control whether the route is advertised or not."
            	DEFVAL { advertise }
            	::= { expIsisToEgpRuleEntry 3 }
            
            expIsisToEgpRuleMetricAction OBJECT-TYPE
            	SYNTAX INTEGER { replace(1), increment(2), decrement(3) }
            	ACCESS read-write
            	STATUS mandatory
            	DESCRIPTION
            		"How to apply the expIsisToEgpRuleMetric field to the metric in the route
            		table entry before the route is advertised."
            	DEFVAL { increment }
            	::= { expIsisToEgpRuleEntry 4 }
            
            expIsisToEgpRuleMetric OBJECT-TYPE
            	SYNTAX INTEGER 
            	ACCESS read-write
            	STATUS mandatory
            	DESCRIPTION
            		"Metric value to be applied to the metric in the route table entry
            		before the route is advertised."
            	DEFVAL { 0 }
            	::= { expIsisToEgpRuleEntry 5 }
            
            expIsisToEgpRuleStatus OBJECT-TYPE
            	SYNTAX INTEGER { invalid(1), valid(2) }
            	ACCESS read-write
            	STATUS mandatory
            	DESCRIPTION
            		"The status of the rule.  Set to 'invalid' to remove
            		the rule.  If the all wild card rule is removed, it is 
            		automatically readded with default values."
            	DEFVAL { valid }
            	::= { expIsisToEgpRuleEntry 6 }
            
            
            -- Isis to ospf
            
            expIsisToOspfRuleTable OBJECT-TYPE
            	SYNTAX SEQUENCE OF ExpIsisToOspfRuleEntry
            	ACCESS not-accessible
            	STATUS mandatory
            	DESCRIPTION
            		"The Isis to Ospf export table."
            	::= { xExport 12 }
            
            expIsisToOspfRuleEntry OBJECT-TYPE
            	SYNTAX ExpIsisToOspfRuleEntry
            	ACCESS not-accessible
            	STATUS mandatory
            	DESCRIPTION
            		"An Isis to Ospf export rule.  Each rule is keyed by the IP network of
            		the Isis route in the routing table.  The IP network can be set to a
            		wild card.  The route is either accepted to be advertised to the 
            		neighbor or discarded from being advertised, and its metric is applied 
            		according to the rule.  The best match is as follows:
            
            				IP Network      Best Match Rank
            
            				exact			1st
            				wild card		2nd
            
            		."
            	INDEX { expIsisToOspfRuleNetwork }
            	::= { expIsisToOspfRuleTable 1 }
            
            ExpIsisToOspfRuleEntry ::=
            	SEQUENCE {
            		expIsisToOspfRuleNetwork
            			IpAddress,
            		expIsisToOspfRuleAction
            			INTEGER,
            		expIsisToOspfRuleStatus
            			INTEGER
            	}
            
            expIsisToOspfRuleNetwork OBJECT-TYPE
            	SYNTAX IpAddress
            	ACCESS read-only
            	STATUS mandatory
            	DESCRIPTION
            		"The IP network of the route in the route table.  The value 
            		255.255.255.255	is a wild card matching any network."
            	::= { expIsisToOspfRuleEntry 1 }
            
            expIsisToOspfRuleAction OBJECT-TYPE
            	SYNTAX INTEGER { hide(1), advertise(2) }
            	ACCESS read-write
            	STATUS mandatory
            	DESCRIPTION
            		"Control whether the route is advertised or not."
            	DEFVAL { advertise }
            	::= { expIsisToOspfRuleEntry 2 }
            
            expIsisToOspfRuleStatus OBJECT-TYPE
            	SYNTAX INTEGER { invalid(1), valid(2) }
            	ACCESS read-write
            	STATUS mandatory
            	DESCRIPTION
            		"The status of the rule.  Set to 'invalid' to remove
            		the rule.  If the all wild card rule is removed, it is 
            		automatically readded with default values."
            	DEFVAL { valid }
            	::= { expIsisToOspfRuleEntry 3 }
            
            
            -- Isis to Rip
            
            expIsisToRipRuleTable OBJECT-TYPE
            	SYNTAX SEQUENCE OF ExpIsisToRipRuleEntry
            	ACCESS not-accessible
            	STATUS mandatory
            	DESCRIPTION
            		"The Isis to Rip export table."
            	::= { xExport 13 }
            
            expIsisToRipRuleEntry OBJECT-TYPE
            	SYNTAX ExpIsisToRipRuleEntry
            	ACCESS not-accessible
            	STATUS mandatory
            	DESCRIPTION
             		"An Isis to Rip export rule.  Each rule is keyed by the IP
                    network of the Isis route in the routing table.  The IP
                    network can be set to a	wild card.  The route is either
                    accepted to be advertised to the neighbor or discarded
                    from being advertised, and its metric is applied 
            		according to the rule.  The best match is as follows:
            
            				IP Network      Best Match Rank
            
            				exact			1st
            				wild card		2nd
            
            		."
            	INDEX { expIsisToRipRuleNetwork }
            	::= { expIsisToRipRuleTable 1 }
            
            ExpIsisToRipRuleEntry ::=
            	SEQUENCE {
                    expIsisToRipRuleToIf
                        IpAddress,
            		expIsisToRipRuleNetwork
            			IpAddress,
            		expIsisToRipRuleAction
            			INTEGER,
            		expIsisToRipRuleMetricAction
            			INTEGER,
            		expIsisToRipRuleMetric
            			INTEGER,
            		expIsisToRipRuleStatus
            			INTEGER
            	}
            
            expIsisToRipRuleToIf OBJECT-TYPE
                SYNTAX IpAddress
                ACCESS read-only
                STATUS mandatory
                DESCRIPTION
                    "The IP address of the RIP interface to which the 
                    rule applies."
                ::= { expIsisToRipRuleEntry 1 }

            expIsisToRipRuleNetwork OBJECT-TYPE
            	SYNTAX IpAddress
            	ACCESS read-only
            	STATUS mandatory
            	DESCRIPTION
            		"The IP network of the route in the route table.  The value 
            		255.255.255.255	is a wild card matching any network."
            	::= { expIsisToRipRuleEntry 2 }
            
            expIsisToRipRuleAction OBJECT-TYPE
            	SYNTAX INTEGER { hide(1), advertise(2) }
            	ACCESS read-write
            	STATUS mandatory
            	DESCRIPTION
            		"Control whether the route is advertised or not."
            	DEFVAL { advertise }
            	::= { expIsisToRipRuleEntry 3 }
            
            expIsisToRipRuleMetricAction OBJECT-TYPE
            	SYNTAX INTEGER { replace(1), increment(2), decrement(3) }
            	ACCESS read-write
            	STATUS mandatory
            	DESCRIPTION
            		"How to apply the expIsisToRipRuleMetric field to the metric in the route
            		table entry before the route is advertised."
            	DEFVAL { increment }
            	::= { expIsisToRipRuleEntry 4 }
            
            expIsisToRipRuleMetric OBJECT-TYPE
            	SYNTAX INTEGER 
            	ACCESS read-write
            	STATUS mandatory
            	DESCRIPTION
            		"Metric value to be applied to the metric in the route table entry
            		before the route is advertised."
            	DEFVAL { 0 }
            	::= { expIsisToRipRuleEntry 5 }
            
            expIsisToRipRuleStatus OBJECT-TYPE
            	SYNTAX INTEGER { invalid(1), valid(2) }
            	ACCESS read-write
            	STATUS mandatory
            	DESCRIPTION
            		"The status of the rule.  Set to 'invalid' to remove
            		the rule.  If the all wild card rule is removed, it is 
            		automatically readded with default values."
            	DEFVAL { valid }
            	::= { expIsisToRipRuleEntry 6 }
            
            
            -- egp to Isis
            
            expEgpToIsisRuleTable OBJECT-TYPE
            	SYNTAX SEQUENCE OF ExpEgpToIsisRuleEntry
            	ACCESS not-accessible
            	STATUS mandatory
            	DESCRIPTION
            		"The EGP to Isis export table."
            	::= { xExport 14 }
            
            expEgpToIsisRuleEntry OBJECT-TYPE
            	SYNTAX ExpEgpToIsisRuleEntry
            	ACCESS not-accessible
            	STATUS mandatory
            	DESCRIPTION
            		"An EGP to Isis export rule.  Each rule is keyed by the Autonomous 
            		System of the EGP neighbor, the IP network of the EGP route in the 
            		routing table, and the Autonomous System from which the route was
            		learned.  The IP network can be set to a wild card as can the
            		from AS.  The route is either accepted to be advertised to the 
            		neighbor or discarded from being advertised, and its metric is applied 
            		according to the rule.  The best match is as follows:
            
            				IP Network      From AS			Best Match Rank
            
            				exact			exact			1st
            				exact			wild card		2nd
            				wild card		exact			3rd
            				wild card		wild card		4th
            
            		."
            	INDEX { expEgpToIsisRuleNetwork, expEgpToIsisRuleFromAs }
            	::= { expEgpToIsisRuleTable 1 }
            
            ExpEgpToIsisRuleEntry ::=
            	SEQUENCE {
            		expEgpToIsisRuleNetwork
            			IpAddress,
            		expEgpToIsisRuleFromAs
            			INTEGER,
            		expEgpToIsisRuleAction
            			INTEGER,
            		expEgpToIsisRuleMetricType
            			INTEGER,
            		expEgpToIsisRuleDefaultMetricAction
            			INTEGER,
            		expEgpToIsisRuleDefaultMetric
            			INTEGER,
            		expEgpToIsisRuleDelayMetricAction
            			INTEGER,
            		expEgpToIsisRuleDelayMetric
            			INTEGER,
            		expEgpToIsisRuleErrorMetricAction
            			INTEGER,
            		expEgpToIsisRuleErrorMetric
            			INTEGER,
            		expEgpToIsisRuleExpenseMetricAction
            			INTEGER,
            		expEgpToIsisRuleExpenseMetric
            			INTEGER,
            		expEgpToIsisRuleStatus
            			INTEGER
            	}
            
            expEgpToIsisRuleNetwork OBJECT-TYPE
            	SYNTAX IpAddress 
            	ACCESS read-only
            	STATUS mandatory
            	DESCRIPTION
            		"The IP network of the route in the route table.  The value 
            		255.255.255.255	is a wild card matching any network."
            	::= { expEgpToIsisRuleEntry 1 }
            
            expEgpToIsisRuleFromAs OBJECT-TYPE
            	SYNTAX INTEGER ( 0..65535 )
            	ACCESS read-only
            	STATUS mandatory
            	DESCRIPTION
            		"The Autonomous System of the route in the route table.  The value 
            		65535 is a wild card matching any AS number."
            	::= { expEgpToIsisRuleEntry 2 }
            
            expEgpToIsisRuleAction OBJECT-TYPE
            	SYNTAX INTEGER { hide(1), advertise(2) }
            	ACCESS read-write
            	STATUS mandatory
            	DESCRIPTION
            		"Control whether the route is advertised or not."
            	DEFVAL { advertise }
            	::= { expEgpToIsisRuleEntry 3 }
            
            expEgpToIsisRuleMetricType OBJECT-TYPE
            	SYNTAX INTEGER { internal(1), external(2) }
            	ACCESS read-write
            	STATUS mandatory
            	DESCRIPTION
            		"Whether to advertise the metric as Internal or External."
            	DEFVAL { external }
            	::= { expEgpToIsisRuleEntry 4 }
            
            expEgpToIsisRuleDefaultMetricAction OBJECT-TYPE
            	SYNTAX INTEGER { replace(1), increment(2), decrement(3) }
            	ACCESS read-write
            	STATUS mandatory
            	DESCRIPTION
            		"How to apply the expEgpToIsisDefaultRuleMetric field to the metric in the route
            		table entry before the route is advertised."
            	DEFVAL { increment }
            	::= { expEgpToIsisRuleEntry 5 }
            
            expEgpToIsisRuleDefaultMetric OBJECT-TYPE
            	SYNTAX INTEGER 
            	ACCESS read-write
            	STATUS mandatory
            	DESCRIPTION
            		"Default metric value to be applied to the metric in the route table entry
            		before the route is advertised."
            	DEFVAL { 1 }
            	::= { expEgpToIsisRuleEntry 6 }
            
            expEgpToIsisRuleDelayMetricAction OBJECT-TYPE
            	SYNTAX INTEGER { replace(1), increment(2), decrement(3) }
            	ACCESS read-write
            	STATUS mandatory
            	DESCRIPTION
            		"How to apply the expEgpToIsisDelayRuleMetric field to the metric in the 
            		route table entry before the route is advertised."
            	DEFVAL { replace }
            	::= { expEgpToIsisRuleEntry 7 }
            
            expEgpToIsisRuleDelayMetric OBJECT-TYPE
            	SYNTAX INTEGER 
            	ACCESS read-write
            	STATUS mandatory
            	DESCRIPTION
            		"Delay metric value to be applied to the metric in the route table entry
            		before the route is advertised."
            	DEFVAL { 0 }
            	::= { expEgpToIsisRuleEntry 8 }
            
            expEgpToIsisRuleErrorMetricAction OBJECT-TYPE
            	SYNTAX INTEGER { replace(1), increment(2), decrement(3) }
            	ACCESS read-write
            	STATUS mandatory
            	DESCRIPTION
            		"How to apply the expEgpToIsisErrorRuleMetric field to the metric in the route
            		table entry before the route is advertised."
            	DEFVAL { replace }
            	::= { expEgpToIsisRuleEntry 9 }
            
            expEgpToIsisRuleErrorMetric OBJECT-TYPE
            	SYNTAX INTEGER 
            	ACCESS read-write
            	STATUS mandatory
            	DESCRIPTION
            		"Error metric value to be applied to the metric in the route table entry
            		before the route is advertised."
            	DEFVAL { 0 }
            	::= { expEgpToIsisRuleEntry 10 }
            
            expEgpToIsisRuleExpenseMetricAction OBJECT-TYPE
            	SYNTAX INTEGER { replace(1), increment(2), decrement(3) }
            	ACCESS read-write
            	STATUS mandatory
            	DESCRIPTION
            		"How to apply the expEgpToIsisExpenseRuleMetric field to the metric in the route
            		table entry before the route is advertised."
            	DEFVAL { replace }
            	::= { expEgpToIsisRuleEntry 11 }
            
            expEgpToIsisRuleExpenseMetric OBJECT-TYPE
            	SYNTAX INTEGER 
            	ACCESS read-write
            	STATUS mandatory
            	DESCRIPTION
            		"Expense metric value to be applied to the metric in the route table entry
            		before the route is advertised."
            	DEFVAL { 0 }
            	::= { expEgpToIsisRuleEntry 12 }
            
            expEgpToIsisRuleStatus OBJECT-TYPE
            	SYNTAX INTEGER { invalid(1), valid(2) }
            	ACCESS read-write
            	STATUS mandatory
            	DESCRIPTION
            		"The status of the rule.  Set to 'invalid' to remove
            		the rule.  If the all wild card rule is removed, it is 
            		automatically readded with default values."
            	DEFVAL { valid }
            	::= { expEgpToIsisRuleEntry 13 }
            
            
            -- Ospf to Isis
            
            expOspfToIsisRuleTable OBJECT-TYPE
            	SYNTAX SEQUENCE OF ExpOspfToIsisRuleEntry
            	ACCESS not-accessible
            	STATUS mandatory
            	DESCRIPTION
            		"The Ospf to Isis export table."
            	::= { xExport 15 }
            
            expOspfToIsisRuleEntry OBJECT-TYPE
            	SYNTAX ExpOspfToIsisRuleEntry
            	ACCESS not-accessible
            	STATUS mandatory
            	DESCRIPTION
            		"An Ospf to Isis export rule.  Each rule is keyed by the
                    Autonomous System of the Ospf neighbor, the IP network of
                    the Ospf route in the routing table, and the Autonomous
                    System from which the route was learned.  The IP network
                    can be set to a wild card as can the the from AS.  The
                    route is either accepted to be advertised to the neighbor
                    or discarded from being advertised, and its metric is
                    applied according to the rule.  The best match is as
                    follows:
            
            				IP Network      From AS			Best Match Rank
            
            				exact			exact			1st
            				exact			wild card		2nd
            				wild card		exact			3rd
            				wild card		wild card		4th
            
            		."
            	INDEX { expOspfToIsisRuleNetwork, expOspfToIsisRuleFromAs }
            	::= { expOspfToIsisRuleTable 1 }
            
            ExpOspfToIsisRuleEntry ::=
            	SEQUENCE {
            		expOspfToIsisRuleNetwork
            			IpAddress,
            		expOspfToIsisRuleFromAs
            			INTEGER,
            		expOspfToIsisRuleAction
            			INTEGER,
            		expOspfToIsisRuleMetricType
            			INTEGER,
            		expOspfToIsisRuleDefaultMetricAction
            			INTEGER,
            		expOspfToIsisRuleDefaultMetric
            			INTEGER,
            		expOspfToIsisRuleDelayMetricAction
            			INTEGER,
            		expOspfToIsisRuleDelayMetric
            			INTEGER,
            		expOspfToIsisRuleErrorMetricAction
            			INTEGER,
            		expOspfToIsisRuleErrorMetric
            			INTEGER,
            		expOspfToIsisRuleExpenseMetricAction
            			INTEGER,
            		expOspfToIsisRuleExpenseMetric
            			INTEGER,
            		expOspfToIsisRuleStatus
            			INTEGER
            	}
            
            expOspfToIsisRuleNetwork OBJECT-TYPE
            	SYNTAX IpAddress 
            	ACCESS read-only
            	STATUS mandatory
            	DESCRIPTION
            		"The IP network of the route in the route table.  The value
            		255.255.255.255	is a wild card matching any network."
            	::= { expOspfToIsisRuleEntry 1 }
            
            expOspfToIsisRuleFromAs OBJECT-TYPE
            	SYNTAX INTEGER ( 0..65535 )
            	ACCESS read-only
            	STATUS mandatory
            	DESCRIPTION
            		"The Autonomous System of the route in the route table.
                    The value 65535 is a wild card matching any AS number,
                    and the value 65534 is for routes within the local AS."
            	::= { expOspfToIsisRuleEntry 2 }
            
            expOspfToIsisRuleAction OBJECT-TYPE
            	SYNTAX INTEGER { hide(1), advertise(2) }
            	ACCESS read-write
            	STATUS mandatory
            	DESCRIPTION
            		"Control whether the route is advertised or not."
            	DEFVAL { advertise }
            	::= { expOspfToIsisRuleEntry 3 }
            
            expOspfToIsisRuleMetricType OBJECT-TYPE
            	SYNTAX INTEGER { internal(1), external(2) }
            	ACCESS read-write
            	STATUS mandatory
            	DESCRIPTION
            		"Whether to advertise the metric as Internal or External."
            	DEFVAL { external }
            	::= { expOspfToIsisRuleEntry 4 }
            
            expOspfToIsisRuleDefaultMetricAction OBJECT-TYPE
            	SYNTAX INTEGER { replace(1), increment(2), decrement(3) }
            	ACCESS read-write
            	STATUS mandatory
            	DESCRIPTION
            		"How to apply the expOspfToIsisDefaultRuleMetric field to
                    the metric in the route table entry before the route is
                    advertised."
            	DEFVAL { increment }
            	::= { expOspfToIsisRuleEntry 5 }
            
            expOspfToIsisRuleDefaultMetric OBJECT-TYPE
            	SYNTAX INTEGER 
            	ACCESS read-write
            	STATUS mandatory
            	DESCRIPTION
            		"Default metric value to be applied to the metric in the route table entry
            		before the route is advertised."
            	DEFVAL { 1 }
            	::= { expOspfToIsisRuleEntry 6 }
            
            expOspfToIsisRuleDelayMetricAction OBJECT-TYPE
            	SYNTAX INTEGER { replace(1), increment(2), decrement(3) }
            	ACCESS read-write
            	STATUS mandatory
            	DESCRIPTION
            		"How to apply the expOspfToIsisDelayRuleMetric field to the metric in the route
            		table entry before the route is advertised."
            	DEFVAL { replace }
            	::= { expOspfToIsisRuleEntry 7 }
            
            expOspfToIsisRuleDelayMetric OBJECT-TYPE
            	SYNTAX INTEGER 
            	ACCESS read-write
            	STATUS mandatory
            	DESCRIPTION
            		"Delay metric value to be applied to the metric in the route table entry
            		before the route is advertised."
            	DEFVAL { 0 }
            	::= { expOspfToIsisRuleEntry 8 }
            
            expOspfToIsisRuleErrorMetricAction OBJECT-TYPE
            	SYNTAX INTEGER { replace(1), increment(2), decrement(3) }
            	ACCESS read-write
            	STATUS mandatory
            	DESCRIPTION
            		"How to apply the expOspfToIsisErrorRuleMetric field to the metric in the route
            		table entry before the route is advertised."
            	DEFVAL { replace }
            	::= { expOspfToIsisRuleEntry 9 }
            
            expOspfToIsisRuleErrorMetric OBJECT-TYPE
            	SYNTAX INTEGER 
            	ACCESS read-write
            	STATUS mandatory
            	DESCRIPTION
            		"Error metric value to be applied to the metric in the route table entry
            		before the route is advertised."
            	DEFVAL { 0 }
            	::= { expOspfToIsisRuleEntry 10 }
            
            expOspfToIsisRuleExpenseMetricAction OBJECT-TYPE
            	SYNTAX INTEGER { replace(1), increment(2), decrement(3) }
            	ACCESS read-write
            	STATUS mandatory
            	DESCRIPTION
            		"How to apply the expOspfToIsisExpenseRuleMetric field to the metric in the route
            		table entry before the route is advertised."
            	DEFVAL { replace }
            	::= { expOspfToIsisRuleEntry 11 }
            
            expOspfToIsisRuleExpenseMetric OBJECT-TYPE
            	SYNTAX INTEGER 
            	ACCESS read-write
            	STATUS mandatory
            	DESCRIPTION
            		"Expense metric value to be applied to the metric in the route table entry
            		before the route is advertised."
            	DEFVAL { 0 }
            	::= { expOspfToIsisRuleEntry 12 }
            
            expOspfToIsisRuleStatus OBJECT-TYPE
            	SYNTAX INTEGER { invalid(1), valid(2) }
            	ACCESS read-write
            	STATUS mandatory
            	DESCRIPTION
            		"The status of the rule.  Set to 'invalid' to remove
            		the rule.  If the all wild card rule is removed, it is 
            		automatically readded with default values.  The same is
            		true for the all wild cards where the AS is set to local"
            	DEFVAL { valid }
            	::= { expOspfToIsisRuleEntry 13 }
            
            
            -- Rip to Isis
            
            expRipToIsisRuleTable OBJECT-TYPE
            	SYNTAX SEQUENCE OF ExpRipToIsisRuleEntry
            	ACCESS not-accessible
            	STATUS mandatory
            	DESCRIPTION
            		"The Isis to Isis export table."
            	::= { xExport 16 }
            
            expRipToIsisRuleEntry OBJECT-TYPE
            	SYNTAX ExpRipToIsisRuleEntry
            	ACCESS not-accessible
            	STATUS mandatory
            	DESCRIPTION
            		"An Isis to Isis export rule.  Each rule is keyed by the
                    IP network of the Isis route in the routing table.  The
                    neighbor IP network can be set to a wild card.  The route
                    is either accepted to be advertised to the neighbor or
                    discarded from being advertised, and its metric is applied
                    according to the rule.  The best match is as follows:
            
            				IP Network      Best Match Rank
            
            				exact			1st
            				wild card		2nd
            
            		."
            	INDEX { expRipToIsisRuleNetwork }
            	::= { expRipToIsisRuleTable 1 }
            
            ExpRipToIsisRuleEntry ::=
            	SEQUENCE {
            		expRipToIsisRuleNetwork
            			IpAddress,
            		expRipToIsisRuleAction
            			INTEGER,
            		expRipToIsisRuleMetricType
            			INTEGER,
            		expRipToIsisRuleDefaultMetricAction
            			INTEGER,
            		expRipToIsisRuleDefaultMetric
            			INTEGER,
            		expRipToIsisRuleDelayMetricAction
            			INTEGER,
            		expRipToIsisRuleDelayMetric
            			INTEGER,
            		expRipToIsisRuleErrorMetricAction
            			INTEGER,
            		expRipToIsisRuleErrorMetric
            			INTEGER,
            		expRipToIsisRuleExpenseMetricAction
            			INTEGER,
            		expRipToIsisRuleExpenseMetric
            			INTEGER,
            		expRipToIsisRuleStatus
            			INTEGER
            	}
            
            expRipToIsisRuleNetwork OBJECT-TYPE
            	SYNTAX IpAddress
            	ACCESS read-only
            	STATUS mandatory
            	DESCRIPTION
            		"The IP network of the route in the route table.  The value 
            		255.255.255.255	is a wild card matching any network."
            	::= { expRipToIsisRuleEntry 1 }
            
            expRipToIsisRuleAction OBJECT-TYPE
            	SYNTAX INTEGER { hide(1), advertise(2) }
            	ACCESS read-write
            	STATUS mandatory
            	DESCRIPTION
            		"Control whether the route is advertised or not."
            	DEFVAL { advertise }
            	::= { expRipToIsisRuleEntry 2 }
            
            expRipToIsisRuleMetricType OBJECT-TYPE
            	SYNTAX INTEGER { internal(1), external(2) }
            	ACCESS read-write
            	STATUS mandatory
            	DESCRIPTION
            		"Whether to advertise the metric as Internal or External."
            	DEFVAL { external }
            	::= { expRipToIsisRuleEntry 3 }
            
            expRipToIsisRuleDefaultMetricAction OBJECT-TYPE
            	SYNTAX INTEGER { replace(1), increment(2), decrement(3) }
            	ACCESS read-write
            	STATUS mandatory
            	DESCRIPTION
            		"How to apply the expRipToIsisDefaultRuleMetric field to the metric in the route
            		table entry before the route is advertised."
            	DEFVAL { increment }
            	::= { expRipToIsisRuleEntry 4 }
            
            expRipToIsisRuleDefaultMetric OBJECT-TYPE
            	SYNTAX INTEGER 
            	ACCESS read-write
            	STATUS mandatory
            	DESCRIPTION
            		"Default metric value to be applied to the metric in the route table entry
            		before the route is advertised."
            	DEFVAL { 1 }
            	::= { expRipToIsisRuleEntry 5 }
            
            expRipToIsisRuleDelayMetricAction OBJECT-TYPE
            	SYNTAX INTEGER { replace(1), increment(2), decrement(3) }
            	ACCESS read-write
            	STATUS mandatory
            	DESCRIPTION
            		"How to apply the expRipToIsisDelayRuleMetric field to the metric in the route
            		table entry before the route is advertised."
            	DEFVAL { replace }
            	::= { expRipToIsisRuleEntry 6 }
            
            expRipToIsisRuleDelayMetric OBJECT-TYPE
            	SYNTAX INTEGER 
            	ACCESS read-write
            	STATUS mandatory
            	DESCRIPTION
            		"Delay metric value to be applied to the metric in the route table entry
            		before the route is advertised."
            	DEFVAL { 0 }
            	::= { expRipToIsisRuleEntry 7 }
            
            expRipToIsisRuleErrorMetricAction OBJECT-TYPE
            	SYNTAX INTEGER { replace(1), increment(2), decrement(3) }
            	ACCESS read-write
            	STATUS mandatory
            	DESCRIPTION
            		"How to apply the expRipToIsisErrorRuleMetric field to the metric in the route
            		table entry before the route is advertised."
            	DEFVAL { replace }
            	::= { expRipToIsisRuleEntry 8 }
            
            expRipToIsisRuleErrorMetric OBJECT-TYPE
            	SYNTAX INTEGER 
            	ACCESS read-write
            	STATUS mandatory
            	DESCRIPTION
            		"Error metric value to be applied to the metric in the
                    route table entry before the route is advertised."
            	DEFVAL { 0 }
            	::= { expRipToIsisRuleEntry 9 }
            
            expRipToIsisRuleExpenseMetricAction OBJECT-TYPE
            	SYNTAX INTEGER { replace(1), increment(2), decrement(3) }
            	ACCESS read-write
            	STATUS mandatory
            	DESCRIPTION
            		"How to apply the expRipToIsisExpenseRuleMetric field to
                    the metric in the route	table entry before the route is
                    advertised."
            	DEFVAL { replace }
            	::= { expRipToIsisRuleEntry 10 }
            
            expRipToIsisRuleExpenseMetric OBJECT-TYPE
            	SYNTAX INTEGER 
            	ACCESS read-write
            	STATUS mandatory
            	DESCRIPTION
            		"Expense metric value to be applied to the metric in the
                    route table entry before the route is advertised."
            	DEFVAL { 0 }
            	::= { expRipToIsisRuleEntry 11 }
            
            expRipToIsisRuleStatus OBJECT-TYPE
            	SYNTAX INTEGER { invalid(1), valid(2) }
            	ACCESS read-write
            	STATUS mandatory
            	DESCRIPTION
            		"The status of the rule.  Set to 'invalid' to remove
            		the rule.  If the all wild card rule is removed, it is 
            		automatically readded with default values."
            	DEFVAL { valid }
            	::= { expRipToIsisRuleEntry 12 }
            
            
            
            -- Static to Isis
            
            expStaticToIsisRuleTable OBJECT-TYPE
            	SYNTAX SEQUENCE OF ExpStaticToIsisRuleEntry
            	ACCESS not-accessible
            	STATUS mandatory
            	DESCRIPTION
            		"The Static to Isis export table."
            	::= { xExport 17 }
            
            expStaticToIsisRuleEntry OBJECT-TYPE
            	SYNTAX ExpStaticToIsisRuleEntry
            	ACCESS not-accessible
            	STATUS mandatory
            	DESCRIPTION
            		"An Static to Isis export rule.  Each rule is keyed by the
                    IP network of the Static route in the routing table.  The
                    neighbor IP network can be set to a wild card.  The route
                    is either accepted to be advertised to the neighbor or
                    discarded from being advertised, and its metric is applied
                    according to the rule.  The best match is as follows:
            
            				IP Network      Best Match Rank
            
            				exact			1st
            				wild card		2nd
            
            		."
            	INDEX { expStaticToIsisRuleNetwork }
            	::= { expStaticToIsisRuleTable 1 }
            
            ExpStaticToIsisRuleEntry ::=
            	SEQUENCE {
            		expStaticToIsisRuleNetwork
            			IpAddress,
            		expStaticToIsisRuleAction
            			INTEGER,
            		expStaticToIsisRuleMetricType
            			INTEGER,
            		expStaticToIsisRuleDefaultMetricAction
            			INTEGER,
            		expStaticToIsisRuleDefaultMetric
            			INTEGER,
            		expStaticToIsisRuleDelayMetricAction
            			INTEGER,
            		expStaticToIsisRuleDelayMetric
            			INTEGER,
            		expStaticToIsisRuleErrorMetricAction
            			INTEGER,
            		expStaticToIsisRuleErrorMetric
            			INTEGER,
            		expStaticToIsisRuleExpenseMetricAction
            			INTEGER,
            		expStaticToIsisRuleExpenseMetric
            			INTEGER,
            		expStaticToIsisRuleStatus
            			INTEGER
            	}
            
            expStaticToIsisRuleNetwork OBJECT-TYPE
            	SYNTAX IpAddress
            	ACCESS read-only
            	STATUS mandatory
            	DESCRIPTION
            		"The IP network of the route in the route table.  The value
            		255.255.255.255	is a wild card matching any network."
            	::= { expStaticToIsisRuleEntry 1 }
            
            expStaticToIsisRuleAction OBJECT-TYPE
            	SYNTAX INTEGER { hide(1), advertise(2) }
            	ACCESS read-write
            	STATUS mandatory
            	DESCRIPTION
            		"Control whether the route is advertised or not."
            	DEFVAL { advertise }
            	::= { expStaticToIsisRuleEntry 2 }
            
            expStaticToIsisRuleMetricType OBJECT-TYPE
            	SYNTAX INTEGER { internal(1), external(2) }
            	ACCESS read-write
            	STATUS mandatory
            	DESCRIPTION
            		"Whether to advertise the metric as Internal or External."
            	DEFVAL { external }
            	::= { expStaticToIsisRuleEntry 3 }
            
            expStaticToIsisRuleDefaultMetricAction OBJECT-TYPE
            	SYNTAX INTEGER { replace(1), increment(2), decrement(3) }
            	ACCESS read-write
            	STATUS mandatory
            	DESCRIPTION
            		"How to apply the expStaticToIsisDefaultRuleMetric field
                    to the metric in the route table entry before the route
                    is advertised."
            	DEFVAL { increment }
            	::= { expStaticToIsisRuleEntry 4 }
            
            expStaticToIsisRuleDefaultMetric OBJECT-TYPE
            	SYNTAX INTEGER 
            	ACCESS read-write
            	STATUS mandatory
            	DESCRIPTION
            		"Default metric value to be applied to the metric in the
                    route table entry before the route is advertised."
            	DEFVAL { 1 }
            	::= { expStaticToIsisRuleEntry 5 }
            
            expStaticToIsisRuleDelayMetricAction OBJECT-TYPE
            	SYNTAX INTEGER { replace(1), increment(2), decrement(3) }
            	ACCESS read-write
            	STATUS mandatory
            	DESCRIPTION
            		"How to apply the expStaticToIsisDelayRuleMetric field
                    to the metric in the route table entry before the route
                    is advertised."
            	DEFVAL { replace }
            	::= { expStaticToIsisRuleEntry 6 }
            
            expStaticToIsisRuleDelayMetric OBJECT-TYPE
            	SYNTAX INTEGER 
            	ACCESS read-write
            	STATUS mandatory
            	DESCRIPTION
            		"Delay metric value to be applied to the metric in the
                    route table entry before the route is advertised."
            	DEFVAL { 0 }
            	::= { expStaticToIsisRuleEntry 7 }
            
            expStaticToIsisRuleErrorMetricAction OBJECT-TYPE
            	SYNTAX INTEGER { replace(1), increment(2), decrement(3) }
            	ACCESS read-write
            	STATUS mandatory
            	DESCRIPTION
            		"How to apply the expStaticToIsisErrorRuleMetric field
                    to the metric in the route table entry before the route
                    is advertised."
            	DEFVAL { replace }
            	::= { expStaticToIsisRuleEntry 8 }
            
            expStaticToIsisRuleErrorMetric OBJECT-TYPE
            	SYNTAX INTEGER 
            	ACCESS read-write
            	STATUS mandatory
            	DESCRIPTION
            		"Error metric value to be applied to the metric in the
                    route table entry before the route is advertised."
            	DEFVAL { 0 }
            	::= { expStaticToIsisRuleEntry 9 }
            
            expStaticToIsisRuleExpenseMetricAction OBJECT-TYPE
            	SYNTAX INTEGER { replace(1), increment(2), decrement(3) }
            	ACCESS read-write
            	STATUS mandatory
            	DESCRIPTION
            		"How to apply the expStaticToIsisExpenseRuleMetric field
                    to the metric in the route table entry before the route
                    is advertised."
            	DEFVAL { replace }
            	::= { expStaticToIsisRuleEntry 10 }
            
            expStaticToIsisRuleExpenseMetric OBJECT-TYPE
            	SYNTAX INTEGER 
            	ACCESS read-write
            	STATUS mandatory
            	DESCRIPTION
            		"Expense metric value to be applied to the metric in the
                    route table entry before the route is advertised."
            	DEFVAL { 0 }
            	::= { expStaticToIsisRuleEntry 11 }
            
            expStaticToIsisRuleStatus OBJECT-TYPE
            	SYNTAX INTEGER { invalid(1), valid(2) }
            	ACCESS read-write
            	STATUS mandatory
            	DESCRIPTION
            		"The status of the rule.  Set to 'invalid' to remove
            		the rule.  If the all wild card rule is removed, it is 
            		automatically readded with default values."
            	DEFVAL { valid }
            	::= { expStaticToIsisRuleEntry 12 }


            -- the Filter subgroup

            -- Note: individual parameters follow table

            ipIfFilterTable OBJECT-TYPE
                SYNTAX SEQUENCE OF IpIfFilterEntry
                ACCESS not-accessible
                STATUS deprecated
                DESCRIPTION
                    "Table of filter entries."
                ::= { xFilter 1 }

            ipIfFilterEntry OBJECT-TYPE
                SYNTAX IpIfFilterEntry
                ACCESS not-accessible
                STATUS deprecated
                DESCRIPTION
                    "A particular entry."
                INDEX { ipIfFilterIndex, ipIfFilterProtocol,
                        ipIfFilterDstPort, ipIfFilterSrcPort,
                        ipIfFilterDstAddr, ipIfFilterDstMask,
                        ipIfFilterSrcAddr, ipIfFilterSrcMask }
                ::= { ipIfFilterTable 1 }

            IpIfFilterEntry ::=
                SEQUENCE {
                    ipIfFilterIndex
                        INTEGER,
                    ipIfFilterDstAddr
                        IpAddress,
                    ipIfFilterDstMask
                        IpAddress,
                    ipIfFilterSrcAddr
                        IpAddress,
                    ipIfFilterSrcMask
                         IpAddress,
                    ipIfFilterProtocol
                         INTEGER,
                    ipIfFilterDstPort
                         INTEGER,
                    ipIfFilterSrcPort
                         INTEGER,
                    ipIfFilterAction
                         INTEGER,
                    ipIfFilterStatus
                         INTEGER
                }

            ipIfFilterIndex OBJECT-TYPE
                SYNTAX INTEGER
                ACCESS read-only
                STATUS deprecated
                DESCRIPTION
                    "The interface index with which this entry is 
                    associated.  This value is the same as IfIndex."
                ::= { ipIfFilterEntry 1 }

            ipIfFilterDstAddr OBJECT-TYPE
                SYNTAX IpAddress
                ACCESS read-only
                STATUS deprecated
                DESCRIPTION
                    "The destination IP address to use in the filter 
                    match."
                ::= { ipIfFilterEntry 2 }

            ipIfFilterDstMask OBJECT-TYPE
                SYNTAX IpAddress
                ACCESS read-only
                STATUS deprecated
                DESCRIPTION
                    "The destination IP mask to use in the filter 
                    match."
                ::= { ipIfFilterEntry 3 }

            ipIfFilterSrcAddr OBJECT-TYPE
                SYNTAX IpAddress
                ACCESS read-only
                STATUS deprecated
                DESCRIPTION
                    "The source IP address to use in the filter match."
                ::= { ipIfFilterEntry 4 }

            ipIfFilterSrcMask OBJECT-TYPE
                SYNTAX IpAddress
                ACCESS read-only
                STATUS deprecated
                DESCRIPTION
                    "The source IP mask to use in the filter match."
                ::= { ipIfFilterEntry 5 }

            ipIfFilterProtocol OBJECT-TYPE
                SYNTAX INTEGER ( 0..256 )
                ACCESS read-only
                STATUS deprecated
                DESCRIPTION
                    "The protocol to use in the filter match.  The value 
                    256 indicates any protocol."
                ::= { ipIfFilterEntry 6 }

            ipIfFilterDstPort OBJECT-TYPE
                SYNTAX INTEGER ( 0..65536 )
                ACCESS read-only
                STATUS deprecated
                DESCRIPTION
                    "The destination port to use in the filter match.  
                    This field only applies to TCP and UDP protocol 
                    packets.  The value 65536 indicates any destination 
                    port."
                ::= { ipIfFilterEntry 7 }

            ipIfFilterSrcPort OBJECT-TYPE
                SYNTAX INTEGER ( 0..65536 )
                ACCESS read-only
                STATUS deprecated
                DESCRIPTION
                    "The source port to use in the filter match.  This 
                    field only applies to TCP and UDP protocol packets.  
                    The value 65536 indicates any source port."
                ::= { ipIfFilterEntry 8 }

            ipIfFilterAction OBJECT-TYPE
                SYNTAX INTEGER { discard(1), forward(2) }
                ACCESS read-write
                STATUS deprecated
                DESCRIPTION
                    "Control whether the packet for which this filter is 
                    the best match should be forwarded or discarded."
                DEFVAL { forward }
                ::= { ipIfFilterEntry 9 }

            ipIfFilterStatus OBJECT-TYPE
                SYNTAX INTEGER { invalid(1), valid(2) }
                ACCESS read-write
                STATUS deprecated
                DESCRIPTION
                    "The status of the filter entry.  Set to 'invalid' 
                    to remove the entry."
                DEFVAL { valid }
                ::= { ipIfFilterEntry 10 }

            -- individual parameters

            ipFilterState OBJECT-TYPE
                SYNTAX INTEGER { disabled(1), enabled(2) }
                ACCESS read-write
                STATUS mandatory
                DESCRIPTION
                    "The indication of whether this system does IP 
                    filtering."
                ::= { xFilter 2 }


            -- new filter table

            ipIfFilter2Table OBJECT-TYPE
                SYNTAX SEQUENCE OF IpIfFilter2Entry
                ACCESS not-accessible
                STATUS mandatory
                DESCRIPTION
                    "Table of filter entries."
                ::= { xFilter 3 }

            ipIfFilter2Entry OBJECT-TYPE
                SYNTAX IpIfFilter2Entry
                ACCESS not-accessible
                STATUS mandatory
                DESCRIPTION
                    "A particular entry."
                INDEX { ipIfFilter2Index, ipIfFilter2Protocol,
                        ipIfFilter2DstPortStart, ipIfFilter2DstPortEnd,
						ipIfFilter2TcpSyn,
                        ipIfFilter2SrcPortStart, ipIfFilter2SrcPortEnd,
                        ipIfFilter2DstMask, ipIfFilter2DstAddr,
                        ipIfFilter2SrcMask, ipIfFilter2SrcAddr }
                ::= { ipIfFilter2Table 1 }

            IpIfFilter2Entry ::=
                SEQUENCE {
                    ipIfFilter2Index
                        INTEGER,
                    ipIfFilter2DstAddr
                        IpAddress,
                    ipIfFilter2DstMask
                        IpAddress,
                    ipIfFilter2SrcAddr
                        IpAddress,
                    ipIfFilter2SrcMask
                         IpAddress,
                    ipIfFilter2Protocol
                         INTEGER,
                    ipIfFilter2DstPortStart
                         INTEGER,
                    ipIfFilter2SrcPortStart
                         INTEGER,
                    ipIfFilter2Action
                         INTEGER,
                    ipIfFilter2Status
                         INTEGER,
					ipIfFilter2DstPortEnd
						 INTEGER,
					ipIfFilter2SrcPortEnd
						 INTEGER,
					ipIfFilter2TcpSyn
						 INTEGER,
					ipIfFilter2ProtocolPriority
						 INTEGER
                }

            ipIfFilter2Index OBJECT-TYPE
                SYNTAX INTEGER
                ACCESS read-only
                STATUS mandatory
                DESCRIPTION
                    "The interface index with which this entry is 
                    associated.  This value is the same as IfIndex."
                ::= { ipIfFilter2Entry 1 }

            ipIfFilter2DstAddr OBJECT-TYPE
                SYNTAX IpAddress
                ACCESS read-only
                STATUS mandatory
                DESCRIPTION
                    "The destination IP address to use in the filter 
                    match."
                ::= { ipIfFilter2Entry 2 }

            ipIfFilter2DstMask OBJECT-TYPE
                SYNTAX IpAddress
                ACCESS read-only
                STATUS mandatory
                DESCRIPTION
                    "The destination IP mask to use in the filter 
                    match."
                ::= { ipIfFilter2Entry 3 }

            ipIfFilter2SrcAddr OBJECT-TYPE
                SYNTAX IpAddress
                ACCESS read-only
                STATUS mandatory
                DESCRIPTION
                    "The source IP address to use in the filter match."
                ::= { ipIfFilter2Entry 4 }

            ipIfFilter2SrcMask OBJECT-TYPE
                SYNTAX IpAddress
                ACCESS read-only
                STATUS mandatory
                DESCRIPTION
                    "The source IP mask to use in the filter match."
                ::= { ipIfFilter2Entry 5 }

            ipIfFilter2Protocol OBJECT-TYPE
                SYNTAX INTEGER ( 0..256 )
                ACCESS read-only
                STATUS mandatory
                DESCRIPTION
                    "The protocol to use in the filter match.  The value 
                    256 indicates any protocol."
                ::= { ipIfFilter2Entry 6 }

            ipIfFilter2DstPortStart OBJECT-TYPE
                SYNTAX INTEGER ( 0..65535 )
                ACCESS read-only
                STATUS mandatory
                DESCRIPTION
                    "The starting destination port in a range of 
					destination ports to use in the filter match.  
                    This field only applies to TCP and UDP protocol 
                    packets."
                ::= { ipIfFilter2Entry 7 }

            ipIfFilter2SrcPortStart OBJECT-TYPE
                SYNTAX INTEGER ( 0..65535 )
                ACCESS read-only
                STATUS mandatory
                DESCRIPTION
                    "The starting source port in a range of 
					source ports to use in the filter match.  
                    This field only applies to TCP and UDP protocol 
                    packets."
                ::= { ipIfFilter2Entry 8 }

            ipIfFilter2Action OBJECT-TYPE
                SYNTAX INTEGER { discard(1), forward(2) }
                ACCESS read-write
                STATUS mandatory
                DESCRIPTION
                    "Control whether the packet for which this filter is 
                    the best match should be forwarded or discarded."
                DEFVAL { forward }
                ::= { ipIfFilter2Entry 9 }

            ipIfFilter2Status OBJECT-TYPE
                SYNTAX INTEGER { invalid(1), valid(2) }
                ACCESS read-write
                STATUS mandatory
                DESCRIPTION
                    "The status of the filter entry.  Set to 'invalid' 
                    to remove the entry."
                DEFVAL { valid }
                ::= { ipIfFilter2Entry 10 }

            ipIfFilter2DstPortEnd OBJECT-TYPE
                SYNTAX INTEGER ( 0..65535 )
                ACCESS read-only
                STATUS mandatory
                DESCRIPTION
                    "The ending destination port in a range of 
					destination ports to use in the filter match.  
                    This field only applies to TCP and UDP protocol 
                    packets.  This filed must also be greater or
					equal to the ipIfFilter2DstPortStart field."
                ::= { ipIfFilter2Entry 11 }

            ipIfFilter2SrcPortEnd OBJECT-TYPE
                SYNTAX INTEGER ( 0..65535 )
                ACCESS read-only
                STATUS mandatory
                DESCRIPTION
                    "The starting source port in a range of 
					source ports to use in the filter match.  
                    This field only applies to TCP and UDP protocol 
                    packets.  This filed must also be greater or
					equal to the ipIfFilter2SrcPortStart field."
                ::= { ipIfFilter2Entry 12 }

            ipIfFilter2TcpSyn OBJECT-TYPE
                SYNTAX INTEGER { off(1), on(2), all(3) }
                ACCESS read-only
                STATUS mandatory
                DESCRIPTION
                    "The value of the TCP SYN and ACK bit to
					ues in the filter match.  This field only
					applies to TCP packets.  On indicates
					that the SYN bit is on and the ACK bit is 
					off.  Off is any other combination."
                ::= { ipIfFilter2Entry 13 }

            ipIfFilter2ProtocolPriority OBJECT-TYPE
                SYNTAX INTEGER { low(1), medium(3), high(5), none(256) }
                ACCESS read-write
                STATUS mandatory
                DESCRIPTION
                    "Control the priority at which the packet for which
					this filter is the best match should be placed on 
					the WAN output queue.  None indicates that the 
					sending interfaces protocol priority should be used." 
                DEFVAL { none }
                ::= { ipIfFilter2Entry 14 }

            -- the RIP group

            -- Implementation of this group is mandatory for all iTouch
            -- systems that implement RIP and route traffic through

            ripState OBJECT-TYPE
                SYNTAX INTEGER { disabled(1), enabled(2) }
                ACCESS read-write
                STATUS mandatory
                DESCRIPTION
                    "The indication of whether this system participates 
                    in RIP."
                DEFVAL { disabled }
                ::= { xRip 1 }

            ripStatus OBJECT-TYPE
                SYNTAX INTEGER { active(1), ripDisabled(2),
                                 ipDisabled(3), noNetworksEnabled(4),
                                 noMemory(5) }
                ACCESS read-only
                STATUS mandatory
                DESCRIPTION
                    "The status of the RIP software."
                ::= { xRip 2 }

            -- the RIP Network table

            ripNetTable OBJECT-TYPE
                SYNTAX SEQUENCE OF RipNetEntry
                ACCESS not-accessible
                STATUS mandatory
                DESCRIPTION
                    "Table of RIP entries."
                ::= { xRip 3 }

            ripNetEntry OBJECT-TYPE
                SYNTAX RipNetEntry
                ACCESS not-accessible
                STATUS mandatory
                DESCRIPTION
                    "A particular entry."
                INDEX { ripNetNet }
                ::= { ripNetTable 1 }

            RipNetEntry ::=
                SEQUENCE {
                    ripNetNet
                        IpAddress,
                    ripNetState
                        INTEGER,
                    ripNetRipsIn
                         Counter,
                    ripNetRipsOut
                         Counter,
                    ripNetAlgorithm
                        INTEGER
                }

            ripNetNet OBJECT-TYPE
                SYNTAX IpAddress
                ACCESS read-only
                STATUS mandatory
                DESCRIPTION
                    "The IP Network to which this entry applies."
                ::= { ripNetEntry 1 }

            ripNetState OBJECT-TYPE
                SYNTAX INTEGER { disabled(1), routerDiscovery(2),
                                 full(3) }
                ACCESS read-write
                STATUS mandatory
                DESCRIPTION
                    "This value controls the RIP protocol on this 
                    network."
                DEFVAL { full }
                ::= { ripNetEntry 2 }

            ripNetRipsIn OBJECT-TYPE
                SYNTAX Counter
                ACCESS read-only
                STATUS mandatory
                DESCRIPTION
                    "The number of RIP packets received from routers on 
                    this IP network."
                ::= { ripNetEntry 3 }

            ripNetRipsOut OBJECT-TYPE
                SYNTAX Counter
                ACCESS read-only
                STATUS mandatory
                DESCRIPTION
                    "The number of RIP packets sent to routers on this 
                    IP network."
                ::= { ripNetEntry 4 }

            ripNetAlgorithm OBJECT-TYPE
                SYNTAX INTEGER { poisonedReverse(1), splitHorizon(2) }
                ACCESS read-write
                STATUS mandatory
                DESCRIPTION
                    "This value controls the RIP algorithm on this 
                    network."
                ::= { ripNetEntry 5 }

            --  the lpd group

            --  Implementation of this group is mandatory for all iTouch 
            --  systems that implement lpd.

            --  The lpd Queue table

            lpdQueueTable OBJECT-TYPE
                SYNTAX SEQUENCE OF LpdQueueEntry
                ACCESS not-accessible
                STATUS mandatory
                DESCRIPTION
                    "A list of lpd queues on the server."
                ::= { xlpd 1 }

            lpdQueueEntry OBJECT-TYPE
                SYNTAX LpdQueueEntry
                ACCESS not-accessible
                STATUS mandatory
                DESCRIPTION
                    "Lpd parameter values plus counters for an 
                     individual lpd queue."
                INDEX { lpdQueueName }
                ::= { lpdQueueTable 1 }

            LpdQueueEntry ::=
                SEQUENCE {
                    lpdQueueStatus
                        INTEGER,
                    lpdQueueName
                        DisplayString,
                    lpdQueuePorts
                        OCTET STRING,
                    lpdQueueEnabled
                        INTEGER,
                    lpdQueueLfConversion
                        INTEGER,
                    lpdQueueTotalJobs
                        Gauge,
                    lpdQueueActiveJobs
                        Gauge,
                    lpdQueueWaitingJobs
                        Gauge,
                    lpdQueueProcessedJobs
                        Counter,
                    lpdQueueFormFeed
                        INTEGER,
                    lpdQueueBypass
                        INTEGER
                }

            lpdQueueStatus OBJECT-TYPE
                SYNTAX INTEGER { invalid(1), valid(2) }
                ACCESS read-write
                STATUS mandatory
                DESCRIPTION
                    "Status of this entry.  Setting the value to
                    'invalid' invalidates the entry, corresponding
                    directly to the CLEAR/PURGE SERVER LPD QUEUE 
                    command.  Setting the value to 'valid' validates
                    (creates) the entry, corresonding directly to 
                    the DEF/SET SERVER LPD QUEUE and lpd create 
                    commands."
                DEFVAL { valid }
                ::= { lpdQueueEntry 1 }

            lpdQueueName OBJECT-TYPE
                SYNTAX DisplayString (SIZE (1..16))
                ACCESS read-only
                STATUS mandatory
                DESCRIPTION
                    "Name of the LPD queue, case sensitive."
                ::= { lpdQueueEntry 2 }

            lpdQueuePorts OBJECT-TYPE
                SYNTAX OCTET STRING (SIZE (16))
                ACCESS read-write
                STATUS mandatory
                DESCRIPTION
                    "List of ports assigned to the queue.  An lpd queue 
                     can be associated with more than 1 port.  This 
                     object corresponds to the port-list in the
                     DEF/SET SERVER LPD QUEUE and lpc/create commands.
		     The OCTET STRING contains a bitmap, with one bit for
                     each port, and enough octets for all the ports on
                     the system.  Port numbers are as defined for
                     charPortIndex in the Character MIB [11].
                     Corresponding bit numbers start with 1 as the
                     high-order bit of the first octet. "
                ::= { lpdQueueEntry 3 }

            lpdQueueEnabled OBJECT-TYPE
                SYNTAX INTEGER { disabled(1), enabled(2) }
                ACCESS read-write
                STATUS mandatory
                DESCRIPTION
                    "Flag indicates if the queue is enabled.  A 'disabled'
                     queue will reject print requests from remote systems.
                     A 'enabled' queue accepts requests for printing."
		DEFVAL { disabled }
                ::= { lpdQueueEntry 4 }

            lpdQueueLfConversion OBJECT-TYPE
                SYNTAX INTEGER { lf(1), lfcr(2) }
                ACCESS read-write
                STATUS mandatory
                DESCRIPTION
                    "Flag indicates if the queue is converting linefeeds
                     to linefeeds, carriagereturns.  'lfcr' does the
                     converion, 'lf' does not."
		DEFVAL { lf }
                ::= { lpdQueueEntry 5 }

            lpdQueueTotalJobs OBJECT-TYPE
                SYNTAX Gauge
                ACCESS read-only
                STATUS mandatory
                DESCRIPTION
                    "The total number of jobs on the queue.  This number
                     should be equal to the number of active and waiting
                     jobs.  (lpdQueueActive + lpdQueueWaiting)"
                ::= { lpdQueueEntry 6 }

            lpdQueueActiveJobs OBJECT-TYPE
                SYNTAX Gauge
                ACCESS read-only
                STATUS mandatory
                DESCRIPTION
                    "The number of active jobs on the queue.  An active 
                     job is a job that has been assigned a port is in the
                     process of receiving data from a remote host and 
                     sending it out the port."
                ::= { lpdQueueEntry 7 }

            lpdQueueWaitingJobs OBJECT-TYPE
                SYNTAX Gauge
                ACCESS read-only
                STATUS mandatory
                DESCRIPTION
                    "The number of waiting jobs on the queue.  A waiting
                     job is a job that needs a port to send its data to.
                     This implies that the ports associated with this
                     queue are busy."
                ::= { lpdQueueEntry 8 }

            lpdQueueProcessedJobs OBJECT-TYPE
                SYNTAX Counter
                ACCESS read-only
                STATUS mandatory
                DESCRIPTION
                    "The total number of jobs processed by this queue
                     since server boot."
                ::= { lpdQueueEntry 9 }

            lpdQueueFormFeed OBJECT-TYPE
                SYNTAX INTEGER { formfeedafter(1), formfeedbefore(2),
                               formfeednone(3) }
                ACCESS read-write
                STATUS mandatory 
                DESCRIPTION
                     "A control to determine how we will send out a formfeed
                     when printing a lpd job. formfeedafter:  Send after job,
                     formfeedbefore: Send before job,
                     formfeednone: Send no formfeed."
                DEFVAL  { formfeedafter }
                ::= { lpdQueueEntry 10 }

            lpdQueueBypass OBJECT-TYPE 
                SYNTAX INTEGER { disabled(1), enabled(2) }
                ACCESS read-write
                STATUS mandatory
                DESCRIPTION
                     "Control for a queue to bypass a LPD port which has output
                      inhibited via flow control. Corresponds directly to the 
                      value labeled 'Bypass' in the SERVER LPD QUEUE display."
                DEFVAL { disabled }
                ::= { lpdQueueEntry 11 }
                

            -- lpd Job table

            lpdJobTable OBJECT-TYPE
                SYNTAX SEQUENCE OF LpdJobEntry
                ACCESS not-accessible
                STATUS mandatory
                DESCRIPTION
                    "A list of lpd jobs."
                ::= { xlpd 2 }

            lpdJobEntry OBJECT-TYPE
                SYNTAX LpdJobEntry
                ACCESS not-accessible
                STATUS mandatory
                DESCRIPTION
                    "A single lpd Job."
                INDEX { lpdQueueName, lpdJobNumber }
                ::= { lpdJobTable 1 }

            LpdJobEntry ::=
                SEQUENCE {
                    lpdJobStatus
                        INTEGER,
                    lpdJobNumber
                        INTEGER,
                    lpdJobAssignedPort
                        INTEGER,
                    lpdJobFileSize
                        INTEGER,
                    lpdJobHostName
                        DisplayString,
                    lpdJobFileName
                        DisplayString,
                    lpdJobState
                        INTEGER
                }

            lpdJobStatus OBJECT-TYPE
                SYNTAX INTEGER {invalid(1), valid(2)}
                ACCESS read-write
                STATUS mandatory
                DESCRIPTION
                    "Status of this entry.  Setting this object to
                     'invalid' will remove the job from the queue.  
                     Setting this object ot 'valid' has no effect since
                     the only way to create an lpd job is with the lpd
                     protocol."
                ::= { lpdJobEntry 1 }
        
            lpdJobNumber OBJECT-TYPE
                SYNTAX INTEGER (1..5000)
                ACCESS read-only
                STATUS mandatory
                DESCRIPTION
                    "The queue relative job number for this lpd job.  
                     Job numbers are assigned as jobs are accepted onto
                     the queue.  Job numbers are reset to 1 when they
                     reach a value greater than 1000 and the queue goes
                     empty."
                ::= { lpdJobEntry 2 }
        
            lpdJobAssignedPort OBJECT-TYPE
                SYNTAX INTEGER (0..256)
                ACCESS read-only
                STATUS mandatory
                DESCRIPTION
                    "The number of the port assigned to the lpd job."
                ::= { lpdJobEntry 3 }
        
            lpdJobFileSize OBJECT-TYPE
                SYNTAX INTEGER (0..2147483647)
                ACCESS read-only
                STATUS mandatory
                DESCRIPTION
                    "The size of the file being sent from the remote 
                     system."
                ::= { lpdJobEntry 4 }
        
            lpdJobHostName OBJECT-TYPE
                SYNTAX DisplayString (SIZE (1..34))
                ACCESS read-only
                STATUS mandatory
                DESCRIPTION
                    "The name of the host sending the job."
                ::= { lpdJobEntry 5 }
        
            lpdJobFileName OBJECT-TYPE
                SYNTAX DisplayString (SIZE (1..34))
                ACCESS read-only
                STATUS mandatory
                DESCRIPTION
                    "The name of the file being sent."
                ::= { lpdJobEntry 6 }

            lpdJobState OBJECT-TYPE
                SYNTAX INTEGER { initialized(1), waiting(2), 
                                 assigned(3), printingData(4),
                                 printingControl(5), aborted(6),
                                 completed(7), error(8),
                                 flushing(9) }
                ACCESS read-only
                STATUS mandatory
                DESCRIPTION
                    "The current state of the lpd job.  A typical job
                     transistions through the following states:
                     initialize->waiting->assigned->printingdata->
                     printingcontrol->completed."
                ::= { lpdJobEntry 7 }


            -- the SecurID group
            
            -- Implementation of this group is mandatory for all iTouch
            -- systems that implement a SecurID client
            
            securIDServerName0 OBJECT-TYPE
                SYNTAX DisplayString (SIZE (0..50))
                ACCESS read-write
                STATUS mandatory
                DESCRIPTION
                    "The Domain name of the first SecurID server to try 
                    when the system verifies a SecurID PASSCODE.  Corresponds 
                    directly to SERVER SECURID SERVER0 and the 
                    value labeled 'SecurID Server0:' in the 
                    SERVER SECURID display."
                ::= { xSecurID 1 }
            
            securIDServerName1 OBJECT-TYPE
                SYNTAX DisplayString (SIZE (0..50))
                ACCESS read-write
                STATUS mandatory
                DESCRIPTION
                    "The Domain name of the second SecurID server to try 
                    when the system verifies a SecurID PASSCODE.  Corresponds 
                    directly to SERVER SECURID SERVER1 and the 
                    value labeled 'SecurID Server1:' in the 
                    SERVER SECURID display."
                ::= { xSecurID 2 }
            
            securIDServerName2 OBJECT-TYPE
                SYNTAX DisplayString (SIZE (0..50))
                ACCESS read-write
                STATUS mandatory
                DESCRIPTION
                    "The Domain name of the third SecurID server to try 
                    when the system verifies a SecurID PASSCODE.  Corresponds 
                    directly to SERVER SECURID SERVER2 and the 
                    value labeled 'SecurID Server2:' in the 
                    SERVER SECURID display."
                ::= { xSecurID 3 }
            
            securIDServerName3 OBJECT-TYPE
                SYNTAX DisplayString (SIZE (0..50))
                ACCESS read-write
                STATUS mandatory
                DESCRIPTION
                    "The Domain name of the fourth SecurID server to try 
                    when the system verifies a SecurID PASSCODE.  Corresponds 
                    directly to SERVER SECURID SERVER3 and the 
                    value labeled 'SecurID Server3:' in the 
                    SERVER SECURID display."
                ::= { xSecurID 4 }
            
            securIDServerName4 OBJECT-TYPE
                SYNTAX DisplayString (SIZE (0..50))
                ACCESS read-write
                STATUS mandatory
                DESCRIPTION
                    "The Domain name of the fifth SecurID server to try 
                    when the system verifies a SecurID PASSCODE.  Corresponds 
                    directly to SERVER SECURID SERVER4 and the 
                    value labeled 'SecurID Server4:' in the 
                    SERVER SECURID display."
                ::= { xSecurID 5 }
            
            securIDMaxRetries OBJECT-TYPE
                SYNTAX INTEGER (1..10)
                ACCESS read-write
                STATUS mandatory
                DESCRIPTION
                    "The maximum number of times the server will 
                    try any single SecurID server to validate a
                    PASSCODE.  Corresponds directly to SERVER SECURID 
                    ACMMAXRETRIES and the value labeled 'SecurID 
                    ACMMAXRETRIES:' in the SERVER SECURID display."
                ::= { xSecurID 6 }
            
            securIDBaseTimeout OBJECT-TYPE
                SYNTAX INTEGER (1..10)
                ACCESS read-write
                STATUS mandatory
                DESCRIPTION
                    "The initial timeout value to be used between prompts
                    for a SecurID PASSCODE.
                    Corresponds directly to SERVER SECURID 
                    ACMBASETIMEOUT and the value labeled 'SecurID 
                    ACMBASETIMEOUT:' in the SERVER SECURID display."
                ::= { xSecurID 7 }
            
            securIDPort OBJECT-TYPE
                SYNTAX INTEGER (1..32767)
                ACCESS read-write
                STATUS mandatory
                DESCRIPTION
                    "The UDP port number to be used when communicating
                    with the SecurID servers. Corresponds directly to 
                    SERVER SECURID ACM_PORT and the value labeled 'SecurID 
                    ACM_PORT:' in the SERVER SECURID display."
                ::= { xSecurID 8 }
            
            securIDQueryLimit OBJECT-TYPE
                SYNTAX INTEGER (1..10)
                ACCESS read-write
                STATUS mandatory
                DESCRIPTION
                    "The maximum number of times a user will be queried 
                    for a SecurID PASSCODE before being logged out.
                    Corresponds directly to 
                    SERVER SECURID QUERY LIMIT and the value labeled 'SecurID 
                    Query Limit:' in the SERVER SECURID display."
                ::= { xSecurID 9 }
            
            securIDEncryptionMode OBJECT-TYPE
                SYNTAX INTEGER { sdiBlockCipher(1), des(2) }
                ACCESS read-write
                STATUS mandatory
                DESCRIPTION
                    "The type of encryption to use in SecurID validation.
                    Corresponds directly to the value labeled 'Encryption
                    Mode' in the SERVER SECURID display."
                ::= { xSecurID 10 }
            
            securIDInsecureLogins OBJECT-TYPE
                SYNTAX Counter
                ACCESS read-only
                STATUS mandatory
                DESCRIPTION
                    "The number of user logins on ports for which 
                    SecurID user verification is not enabled.  
                    Corresponds directly to the value labeled 'Logins 
                    without SecurID:' in the SERVER SECURID display."
                ::= { xSecurID 11 }
            
            securIDSecureLogins OBJECT-TYPE
                SYNTAX Counter
                ACCESS read-only
                STATUS mandatory
                DESCRIPTION
                    "The number of successful user logins on ports for 
                    which SecurID user verification is enabled.  
                    Corresponds directly to the value labeled 
                    'Successful Logins:' in the SERVER SECURID 
                    display."
                ::= { xSecurID 12 }
            
            securIDSecureLoginsFailed OBJECT-TYPE
                SYNTAX Counter
                ACCESS read-only
                STATUS mandatory
                DESCRIPTION
                    "The number of verification failures due to 
                    incorrect PASSCODE for attempted user logins 
                    on ports for which SecurID user verification is 
                    enabled.  Corresponds directly to the value labeled 
                    'Unsuccessful Logins:' in the SERVER SECURID 
                    display."
                ::= { xSecurID 13 }
            
            securIDServerAccess0 OBJECT-TYPE
                SYNTAX Counter
                ACCESS read-only
                STATUS mandatory
                DESCRIPTION
                    "The number of times the system successfully 
                    accessed the SecurID server0.  Corresponds 
                    directly to the value labeled 'Attempts to access:', 
                    'Server0', and 'Successful:' in the SERVER SECURID 
                    display."
                ::= { xSecurID 14 }
            
            securIDServerAccessFailed0 OBJECT-TYPE
                SYNTAX Counter
                ACCESS read-only
                STATUS mandatory
                DESCRIPTION
                    "The number of times the system unsuccessfully 
                    accessed the SecurID server0.  Corresponds 
                    directly to the value labeled 'Attempts to access:', 
                    'Server0', and 'UnSuccessful:' in the SERVER SECURID 
                    display."
                ::= { xSecurID 15 }
            
            securIDServerAccess1 OBJECT-TYPE
                SYNTAX Counter
                ACCESS read-only
                STATUS mandatory
                DESCRIPTION
                    "The number of times the system successfully 
                    accessed the SecurID server1.  Corresponds 
                    directly to the value labeled 'Attempts to access:', 
                    'Server1', and 'Successful:' in the SERVER SECURID 
                    display."
                ::= { xSecurID 16 }
            
            securIDServerAccessFailed1 OBJECT-TYPE
                SYNTAX Counter
                ACCESS read-only
                STATUS mandatory
                DESCRIPTION
                    "The number of times the system unsuccessfully 
                    accessed the SecurID server1.  Corresponds 
                    directly to the value labeled 'Attempts to access:', 
                    'Server1', and 'UnSuccessful:' in the SERVER SECURID 
                    display."
                ::= { xSecurID 17 }
            
            securIDServerAccess2 OBJECT-TYPE
                SYNTAX Counter
                ACCESS read-only
                STATUS mandatory
                DESCRIPTION
                    "The number of times the system successfully 
                    accessed the SecurID server2.  Corresponds 
                    directly to the value labeled 'Attempts to access:', 
                    'Server2', and 'Successful:' in the SERVER SECURID 
                    display."
                ::= { xSecurID 18 }
            
            securIDServerAccessFailed2 OBJECT-TYPE
                SYNTAX Counter
                ACCESS read-only
                STATUS mandatory
                DESCRIPTION
                    "The number of times the system unsuccessfully 
                    accessed the SecurID server2.  Corresponds 
                    directly to the value labeled 'Attempts to access:', 
                    'Server2', and 'UnSuccessful:' in the SERVER SECURID 
                    display."
                ::= { xSecurID 19 }
            
            securIDServerAccess3 OBJECT-TYPE
                SYNTAX Counter
                ACCESS read-only
                STATUS mandatory
                DESCRIPTION
                    "The number of times the system successfully 
                    accessed the SecurID server3.  Corresponds 
                    directly to the value labeled 'Attempts to access:', 
                    'Server3', and 'Successful:' in the SERVER SECURID 
                    display."
                ::= { xSecurID 20 }
            
            securIDServerAccessFailed3 OBJECT-TYPE
                SYNTAX Counter
                ACCESS read-only
                STATUS mandatory
                DESCRIPTION
                    "The number of times the system unsuccessfully 
                    accessed the SecurID server3.  Corresponds 
                    directly to the value labeled 'Attempts to access:', 
                    'Server3', and 'UnSuccessful:' in the SERVER SECURID 
                    display."
                ::= { xSecurID 21 }
            
            securIDServerAccess4 OBJECT-TYPE
                SYNTAX Counter
                ACCESS read-only
                STATUS mandatory
                DESCRIPTION
                    "The number of times the system successfully 
                    accessed the SecurID server4.  Corresponds 
                    directly to the value labeled 'Attempts to access:', 
                    'Server4', and 'Successful:' in the SERVER SECURID 
                    display."
                ::= { xSecurID 22 }
            
            securIDServerAccessFailed4 OBJECT-TYPE
                SYNTAX Counter
                ACCESS read-only
                STATUS mandatory
                DESCRIPTION
                    "The number of times the system unsuccessfully 
                    accessed the SecurID server4.  Corresponds 
                    directly to the value labeled 'Attempts to access:', 
                    'Server4', and 'UnSuccessful:' in the SERVER SECURID 
                    display."
                ::= { xSecurID 23 }
            
            securIDErrorPortIndex OBJECT-TYPE
                SYNTAX INTEGER (0..40)
                ACCESS read-only
                STATUS mandatory
                DESCRIPTION
                    "The index of the most recent port on which a SecurID 
                    access violation occurred.  Corresponds 
                    directly to the value labeled 'Last Unsuccessful
                    Login:' in the SERVER SECURID display."
                ::= { xSecurID 24 }
            
            securIDError OBJECT-TYPE
                SYNTAX INTEGER (0..40)
                ACCESS read-only
                STATUS mandatory
                DESCRIPTION
                    "The error number of the most recent SecurID-related
                    error.  Corresponds directly to the value labeled 
                    'Reason:' in the SERVER SECURID display.  See
                    iTouch documentation for a complete list of 
                    error numbers and their meaning."
                ::= { xSecurID 25 }
            
            securIDErrorUsername OBJECT-TYPE
                SYNTAX DisplayString (SIZE (0..17))
                ACCESS read-only
                STATUS mandatory
                DESCRIPTION
                    "The username associated with the most recent
                    SecurID-related error.  Corresponds directly to the value
                    labeled 'Username:' in the SERVER SECURID display."
                ::= { xSecurID 26 }
            
            
            -- the SecurID Port table
            
            securIDPortTable OBJECT-TYPE
                SYNTAX SEQUENCE OF SecurIDPortEntry
                ACCESS not-accessible
                STATUS mandatory
                DESCRIPTION
                    "A list of SecurID character port entries."
                ::= { xSecurID 27 }
            
            securIDPortEntry OBJECT-TYPE
                SYNTAX SecurIDPortEntry
                ACCESS not-accessible
                STATUS mandatory
                DESCRIPTION
                    "Parameter values for a SecurID port."
                INDEX { securIDPortIndex }
                ::= { securIDPortTable 1 }
            
            SecurIDPortEntry ::=
                SEQUENCE {
                    securIDPortIndex
                        INTEGER,
                    securIDPortStatus
                        INTEGER
                }
            
            securIDPortIndex OBJECT-TYPE
                SYNTAX INTEGER
                ACCESS read-only
                STATUS mandatory
                DESCRIPTION
                    "An index value that uniquely identifies a port 
                    could relate to SecurID.  The port identified by a 
                    particular value of this index is the same port as 
                    identified by charPortIndex in the Proposed Standard 
                    Internet Character MIB."
                ::= { securIDPortEntry 1 }
            
            securIDPortStatus OBJECT-TYPE
                SYNTAX INTEGER { disabled(1), enabled(2) }
                ACCESS read-write
                STATUS mandatory
                DESCRIPTION
                    "A control indicating the level of SecurID 
                    operation on the port.  Corresponds directly to PORT 
                    SECURID and the value 'SecurID' following the 
                    label 'Enabled Characteristics' in the PORT 
                    CHARACTERISTICS display."
                ::= { securIDPortEntry 2 }


-- the SSH Port Table

sshPortTable OBJECT-TYPE
   SYNTAX SEQUENCE OF SshPortEntry
   ACCESS not-accessible
   STATUS mandatory
   DESCRIPTION
      "A list of SSH port entries"
   ::= { xSsh 1 }

sshPortEntry OBJECT-TYPE
   SYNTAX SshPortEntry
   ACCESS not-accessible
   STATUS mandatory
   DESCRIPTION
      "Parameter values for an SSH port."
   INDEX { sshPortIndex }
   ::= { sshPortTable 1 }

SshPortEntry ::=
   SEQUENCE {
      sshPortIndex
         INTEGER,
      sshPortIncomingTcpPort
         INTEGER,
      sshPortNewlineFiltering
         INTEGER,
      sshPortNewline
         INTEGER,
      sshPortTransmitBufferedTime
         INTEGER,
      sshPortRemoteProtocol
         INTEGER
   }

sshPortIndex  OBJECT-TYPE
   SYNTAX INTEGER
   ACCESS read-only
   STATUS mandatory
   DESCRIPTION
      "An index value that uniquely identifies an SSH port. The port 
       identified by a particular value of this index is the same port as 
       identified by charPortIndex in the proposed standard Internet 
       Character MIB."
   ::= { sshPortEntry 1 }                

sshPortIncomingTcpPort  OBJECT-TYPE
   SYNTAX INTEGER (1..32767)
   ACCESS read-write
   STATUS mandatory
   DESCRIPTION
      "Specifies the TCP port number used to identify the port when a SSH
       connection request arrives at the server. The default for a physical
       port is 2022 + 100 * port's physical port number. The default is 22
       for virtual ports. Corresponds directly to the value labeled 'Remote 
       Port:' in the PORT SSH CHARACTERISTICS display."
   ::= { sshPortEntry 2 }                

sshPortNewlineFiltering  OBJECT-TYPE
   SYNTAX INTEGER { none(1), crToCrLf(2), crToCrNull(3), crLfToCr(4),
                    crLfToCrNull(5), crNullToCr(6), crNullToCrLf(7) }
   ACCESS read-write
   STATUS mandatory
   DESCRIPTION
      "Translation to apply to newline sequences (CR/NULL or CR/LF) received
       from the network during a SSH session, before sending the newline to 
       the character port. The value indicates which input sequence is 
       converted to which output sequence and sent to the 
       character port, with 'none' meaning no translation.
       Corresponds directly to the value labeled 'Newline Filtering:'
       in the PORT SSH CHARACTERISTICS display."
   DEFVAL { none }
   ::= { sshPortEntry 3 }                

sshPortNewline  OBJECT-TYPE
   SYNTAX INTEGER { none(1), crToCrLf(2), crToCrNull(3), crLfToCr(4),
                    crLfToCrNull(5), crNullToCr(6), crNullToCrLf(7) }
   ACCESS read-write
   STATUS mandatory
   DESCRIPTION
      "Translation to apply to newline (carriage return) received from the 
       character port during an SSH session, before sending the newline to the
       remote partner. Corresponds directly to the value labeled 'Newline:' 
       in the PORT SSH CHARACTERISTICS display."
   DEFVAL { none }       
   ::= { sshPortEntry 4 }                

sshPortTransmitBufferedTime  OBJECT-TYPE
   SYNTAX INTEGER (30..1500)
   ACCESS read-write
   STATUS mandatory
   DESCRIPTION
      "Number of milliseconds to wait before transmitting data received from 
       a character port during an interactive SSH session. 
       Corresponds directly to the value labeled 'Transmit Buffered Time:' in
       the PORT SSH CHARACTERISTICS display."
   DEFVAL { 80 } 
   ::= { sshPortEntry 5 }                

sshPortRemoteProtocol  OBJECT-TYPE
   SYNTAX INTEGER { ssh(1), telnet(2), both(3) }
   ACCESS read-write
   STATUS mandatory
   DESCRIPTION
      "Indicates which remote protocols will be accepted at this port.
       Corresponds indirectly to the presence of 'Telnet' or 'SSH' under the 
       label 'Enabled Characteristics:' in the PORT SSH CHARACTERISTICS 
       display. If both protocols are accepted at the port, the choice of 
       protocol is determined by which features are enabled on the server with
       SSH taking precedence over Telnet."
   DEFVAL { both }
   ::= { sshPortEntry 6 }                



sshCipherMask  OBJECT-TYPE
   SYNTAX OCTET STRING (SIZE (2)) 
   ACCESS read-write 
   STATUS mandatory
   DESCRIPTION
      "This is a list of the encryption methods supported.
       The OCTET STRING contains a bitmap, with one bit for each cipher type.
       Corresponding bit numbers start with 0 as the low-order bit of the
       second octet. The following bit positions are defined:  
       none(0), des(2), tripleDes(3), and blowfish(6). Corresponds directly to
       the value labeled 'SSH Cipher Enabled:' in the SERVER SSH 
       CHARACTERISTICS display."
   ::= { xSsh 2 }                

sshAuthenticationTimeout  OBJECT-TYPE
   SYNTAX INTEGER (1..120)
   ACCESS read-write
   STATUS mandatory
   DESCRIPTION
      "The timeout in minutes before disconnecting if no successful 
       authentication of SSH parties has been made. Corresponds directly to 
       the value labeled 'Authentication Timeout:' in the SERVER SSH 
       CHARACTERISTICS display."
   DEFVAL { 5 }
   ::= { xSsh 3 }                

sshHostKeyLength  OBJECT-TYPE
   SYNTAX INTEGER (512..2048)
   ACCESS read-write
   STATUS mandatory
   DESCRIPTION
      "The bit length of the SSH host encryption key. When modified, the 
      desired change does not occur until the next system initialization.
      Corresponds directly to the value labeled 'Host Key Length:' in the 
      SERVER SSH CHARACTERISTICS display."
   DEFVAL { 1024 }
   ::= { xSsh 4 }                

sshHostKeyGenerate  OBJECT-TYPE
   SYNTAX INTEGER { ready(1), generate(2), update(3) }
   ACCESS read-write
   STATUS mandatory
   DESCRIPTION
      "For a set-request with a value of generate or update, a new host key
       will be generated in the background. When modified with generate, the
       desired change does not occur until the next system initialization
       whereas when modified with update the change goes into effect upon
       completion of the new key.   

       In response to a get-request or a get-next-request the agent will
       respond ready except when a host key is being created in which case 
       the agent responds generate."
   ::= { xSsh 5 }                
  
sshServerKeyLength  OBJECT-TYPE
   SYNTAX INTEGER (512..2048)
   ACCESS read-write
   STATUS mandatory
   DESCRIPTION
      "The bit length of the SSH server encryption key. The difference between
       the server and host key lengths should be greater than 128 bits.
      Corresponds directly to the value labeled 'Server Key Length:' in the 
      SERVER SSH CHARACTERISTICS display."
   DEFVAL { 768 }
   ::= { xSsh 6 }                

sshServerKeyTtl  OBJECT-TYPE
   SYNTAX INTEGER (30..1440)
   ACCESS read-write
   STATUS mandatory
   DESCRIPTION
      "The time in minutes that the server key remains valid. After this time
       the server key is automatically re-generated. Corresponds directly to
       the value labeled 'Server Key Timeout:' in the SERVER SSH 
       CHARACTERISTICS display."
   DEFVAL { 60 }
   ::= { xSsh 7 }                

   sshServerMaxBufferSize OBJECT-TYPE
	SYNTAX INTEGER (4096..262144)
	ACCESS read-write
	STATUS mandatory
	DESCRIPTION
	    "The size of the four buffers used by SSH for input and
	     output. These buffers are used for data coming from the 
             console, going to the network, coming from the network and
	     going to the console."
	DEFVAL { 4096 }
	::= { xSsh 8 }






--
-- FILE: /users/sse/mibs/src/itouch/it-ipx-mib.mib
--

-- $Id: it-ipx-mib.mib,v 1.1 2000/07/25 14:32:09 sse Exp $


            xIpx            OBJECT IDENTIFIER ::= { iTouch 15 }

            -- ITouch IPX subgroups

            xIpxSystem      OBJECT IDENTIFIER ::= { xIpx 1 }
            xIpxIf          OBJECT IDENTIFIER ::= { xIpx 2 }
            xIpxNetbios     OBJECT IDENTIFIER ::= { xIpx 3 }
            xIpxRip         OBJECT IDENTIFIER ::= { xIpx 4 }
            xIpxSap         OBJECT IDENTIFIER ::= { xIpx 5 }
	    xIpxFilter      OBJECT IDENTIFIER ::= { xIpx 6 }
            -- number 7 reserved
            xIpxPrinter     OBJECT IDENTIFIER ::= { xIpx 8 }


            -- This is a MIB module for all iTouch Communications systems that
            -- implement IPX.

            -- Copyright 2000 iTouch Communications, Inc. All Rights Reserved.
            -- Reproduction of this document is authorized on
            -- condition that this copyright notice is included.
            -- This MIB document embodies iTouch Communications, Inc.'s 
            -- proprietary intellectual property.  iTouch Communications, Inc.
            -- retains all title and ownership in this MIB, including any
            -- revisions.
            --
            -- It is iTouch Communications, Inc.'s intent to encourage the
            -- widespread use of this MIB in connection with the management of
            -- iTouch Communications, Inc. products. iTouch Communications,
            -- Inc. grants vendors,end-users, and other interested parties a
            -- non-exclusive license to use this MIB in connection with the
            -- management of iTouch Communications, Inc. products.
            --
            -- This MIB document is supplied "AS IS," and iTouch 
            -- Communications, Inc. makes no warranty, either express or
            -- implied, as to the use operation, condition, or performance of
            -- the MIB.


            -- the System group

            -- Implementation of this group is mandatory for all iTouch
            -- systems that implement IPX

            ipxRouting OBJECT-TYPE
                SYNTAX INTEGER { disabled(1), enabled(2) }
                ACCESS read-write
                STATUS mandatory
                DESCRIPTION
                    "Control for IPX routing services."
                ::= { xIpxSystem 1 }

            ipxInternalNetwork OBJECT-TYPE
                SYNTAX INTEGER (1..4294967294)
                ACCESS read-write
                STATUS mandatory
                DESCRIPTION
                    "The IPX Internal Network to use on the the IPX Router."
		DEFVAL { 1 }
                ::= { xIpxSystem 2 }

            -- the Interface group

            -- Implementation of this group is mandatory for all iTouch
            -- systems that implement IPX

            ipxIfTable OBJECT-TYPE
                SYNTAX SEQUENCE OF IpxIfEntry
                ACCESS not-accessible
                STATUS mandatory
                DESCRIPTION
                    "A list of IPX interface entries."
                ::= { xIpxIf 1 }

            ipxIfEntry OBJECT-TYPE
                SYNTAX IpxIfEntry
                ACCESS not-accessible
                STATUS mandatory
                DESCRIPTION
                    "IPX interface parameters and counters."
                INDEX { ipxIfIndex }
                ::= { ipxIfTable 1 }

            IpxIfEntry ::=
                SEQUENCE {
                    ipxIfIndex
                        INTEGER,
                    ipxIfState
                        INTEGER,
                    ipxIfNetwork
                        INTEGER,
                    ipxIfFrameStyle
                        INTEGER,
                    ipxIfFramesIn
                        Counter,
                    ipxIfFramesOut
                        Counter,
                    ipxIfErrors
                        Counter,
                    ipxIfTransitDelay
                        INTEGER,
                    ipxIfTransitDelayActual
                        INTEGER,
                    ipxIfProtocolPriority
                        INTEGER,
                    ipxIfWatchdogSpoof
                        INTEGER,
                    ipxIfStatusNetwork
                        INTEGER
                }

            ipxIfIndex OBJECT-TYPE
                SYNTAX INTEGER
                ACCESS read-only
                STATUS mandatory
                DESCRIPTION
                    "An index value that uniquely identifies an IPX 
                    interface.  The interface identified by a particular 
                    value of this index is the same interface as 
                    identified by the same value of ifIndex."
                ::= { ipxIfEntry 1 }

            ipxIfState OBJECT-TYPE
                SYNTAX INTEGER { disabled(1), enabled(2) }
                ACCESS read-write
                STATUS mandatory
                DESCRIPTION
                    "Control for IPX routing services for this 
                    interface."
                DEFVAL { enabled }
                ::= { ipxIfEntry 2 }

            ipxIfNetwork OBJECT-TYPE
                SYNTAX INTEGER
                ACCESS read-write
                STATUS mandatory
                DESCRIPTION
                    "The IPX network number of the network to which this 
                    interface is attached."
                DEFVAL { 0 }
                ::= { ipxIfEntry 3 }

            ipxIfFrameStyle OBJECT-TYPE
                SYNTAX INTEGER { ethernet(1), ieee8023(2), ieee8022(3), ieee802Snap(4) }
                ACCESS read-write
                STATUS mandatory
                DESCRIPTION
                    "Control for the CSMA/CD frame style to use on this 
                    interface."
                DEFVAL { ieee8023 }
                ::= { ipxIfEntry 4 }

            ipxIfFramesIn OBJECT-TYPE
                SYNTAX Counter
                ACCESS read-only
                STATUS mandatory
                DESCRIPTION
                    "The number of IPX frames received on this 
                    interface."
                ::= { ipxIfEntry 5 }

            ipxIfFramesOut OBJECT-TYPE
                SYNTAX Counter
                ACCESS read-only
                STATUS mandatory
                DESCRIPTION
                    "The number of IPX frames sent on this interface."
                ::= { ipxIfEntry 6 }

            ipxIfErrors OBJECT-TYPE
                SYNTAX Counter
                ACCESS read-only
                STATUS mandatory
                DESCRIPTION
                    "The number of IPX errors seen on this interface."
                ::= { ipxIfEntry 7 }

            ipxIfTransitDelay OBJECT-TYPE
                SYNTAX INTEGER
                ACCESS read-write
                STATUS mandatory
                DESCRIPTION
                    "The number of 55 millisecond ticks it takes for a 
                    packet to  travel from one destination to another on 
                    the interface.  A value of 0 means that the system 
                    will calculate this value based on the measured 
                    speed of the interface."
                ::= { ipxIfEntry 8 }

            ipxIfTransitDelayActual OBJECT-TYPE
                SYNTAX INTEGER     
                ACCESS read-only
                STATUS mandatory
                DESCRIPTION
                    "The number of 55 millisecond ticks it takes for a 
                    packet to travel from one destination to another on 
                    the interface."
                ::= { ipxIfEntry 9 }

            ipxIfProtocolPriority OBJECT-TYPE
                SYNTAX INTEGER { low(1), medium(3), high(5) }
                ACCESS read-write
                STATUS mandatory
                DESCRIPTION
                    "This value defines the priority at which all 
                    Internet Routed packets will be placed on the WAN 
                    output queue."
                DEFVAL { medium }
                ::= { ipxIfEntry 10 }

            ipxIfWatchdogSpoof OBJECT-TYPE
                SYNTAX INTEGER { disabled(1), enabled(2) }
                ACCESS read-write
                STATUS mandatory
                DESCRIPTION
                    "Control for whether or not this router
                    responds to IPX watchog requests on this
                    interface."
                DEFVAL { disabled }
                ::= { ipxIfEntry 11 }

            ipxIfStatusNetwork OBJECT-TYPE
               SYNTAX INTEGER
                ACCESS read-only
                STATUS mandatory
                DESCRIPTION
                    "The IPX network number that is actually in use on the 
                    attached interface.  This value may have been learned 
		     via listening to the attached network."
                DEFVAL { 0 }
                ::= { ipxIfEntry 12 }


            -- the Netbios group

            -- Implementation of this group is mandatory for all iTouch
            -- systems that implement IPX Netbios

            ipxNetbiosHopLimit OBJECT-TYPE
                SYNTAX INTEGER (0..255)
                ACCESS read-write
                STATUS mandatory
                DESCRIPTION
                    "Maximum number of hops that an IPX Netbios packet 
                    may make."
                ::= { xIpxNetbios 1 }

            ipxNetbiosIfTable OBJECT-TYPE
                SYNTAX SEQUENCE OF IpxNetbiosIfEntry
                ACCESS not-accessible
                STATUS mandatory
                DESCRIPTION
                    "A list of IPX interface entries."
                ::= { xIpxNetbios 2 }

            ipxNetbiosIfEntry OBJECT-TYPE
                SYNTAX IpxNetbiosIfEntry
                ACCESS not-accessible
                STATUS mandatory
                DESCRIPTION
                    "IPX interface parameters and counters."
                INDEX { ipxNetbiosIfIndex }
                ::= { ipxNetbiosIfTable 1 }

            IpxNetbiosIfEntry ::=
                SEQUENCE {
                    ipxNetbiosIfIndex
                        INTEGER,
                    ipxIfNetbiosForwarding
                        INTEGER,
                    ipxIfNetbiosIn
                        Counter,
                    ipxIfNetbiosOut
                        Counter
                }

            ipxNetbiosIfIndex OBJECT-TYPE
                SYNTAX INTEGER
                ACCESS read-only
                STATUS mandatory
                DESCRIPTION
                    "An index value that uniquely identifies an IPX 
                    interface.  The interface identified by a particular 
                    value of this index is the same interface as 
                    identified by the same value of ifIndex."
                ::= { ipxNetbiosIfEntry 1 }

            ipxIfNetbiosForwarding OBJECT-TYPE
                SYNTAX INTEGER { disabled(1), enabled(2) }
                ACCESS read-write
                STATUS mandatory
                DESCRIPTION
                    "Control whether Netbios packet will be forwarded in 
                    or out on this interface."
                DEFVAL { enabled }
                ::= { ipxNetbiosIfEntry 2 }

            ipxIfNetbiosIn OBJECT-TYPE
                SYNTAX Counter
                ACCESS read-only
                STATUS mandatory
                DESCRIPTION
                    "The number of IPX Netbios frames received on this 
                    interface."
                ::= { ipxNetbiosIfEntry 3 }

            ipxIfNetbiosOut OBJECT-TYPE
                SYNTAX Counter
                ACCESS read-only
                STATUS mandatory
                DESCRIPTION
                    "The number of IPX Netbios frames sent on this 
                    interface."
                ::= { ipxNetbiosIfEntry 4 }


            -- the RIP group

            -- Implementation of this group is mandatory for all iTouch
            -- systems that implement IPX RIP

            ipxRipIfTable OBJECT-TYPE
                SYNTAX SEQUENCE OF IpxRipIfEntry
                ACCESS not-accessible
                STATUS mandatory
                DESCRIPTION
                    "A list of IPX interface entries."
                ::= { xIpxRip 1 }

            ipxRipIfEntry OBJECT-TYPE
                SYNTAX IpxRipIfEntry
                ACCESS not-accessible
                STATUS mandatory
                DESCRIPTION
                    "IPX interface parameters and counters."
                INDEX { ipxRipIfIndex }
                ::= { ipxRipIfTable 1 }

            IpxRipIfEntry ::=
                SEQUENCE {
                    ipxRipIfIndex
                        INTEGER,
                    ipxIfRipBcst
                        INTEGER,
                    ipxIfRipBcstDiscardTimeout
                        INTEGER,
                    ipxIfRipBcstTimer
                        INTEGER,
                    ipxIfRipIn
                        Counter,
                    ipxIfRipOut
                        Counter,
                    ipxIfRipAgedOut
                        Counter
                }

            ipxRipIfIndex OBJECT-TYPE
                SYNTAX INTEGER
                ACCESS read-only
                STATUS mandatory
                DESCRIPTION
                    "An index value that uniquely identifies an IPX 
                    interface.  The interface identified by a particular 
                    value of this index is the same interface as 
                    identified by the same value of ifIndex."
                ::= { ipxRipIfEntry 1 }

            ipxIfRipBcst OBJECT-TYPE
                SYNTAX INTEGER { disabled(1), enabled(2), propUpdateOnly(3), demandCircuit(4) }
                ACCESS read-write
                STATUS mandatory
                DESCRIPTION
                    "Control whether RIP packets will be broadcasted out 
                    this interface."
                DEFVAL { enabled }
                ::= { ipxRipIfEntry 2 }

            ipxIfRipBcstDiscardTimeout OBJECT-TYPE
                SYNTAX INTEGER
                ACCESS read-write
                STATUS mandatory
                DESCRIPTION
                    "The number of seconds to wait before discarding 
                    information learned from a RIP broadcast."
                DEFVAL { 180 }
                ::= { ipxRipIfEntry 3 }

            ipxIfRipBcstTimer OBJECT-TYPE
                SYNTAX INTEGER
                ACCESS read-write
                STATUS mandatory
                DESCRIPTION
                    "The number of seconds to wait between sending out 
                    RIP broadcasts."
                DEFVAL { 60 }
                ::= { ipxRipIfEntry 4 }

            ipxIfRipIn OBJECT-TYPE
                SYNTAX Counter
                ACCESS read-only
                STATUS mandatory
                DESCRIPTION
                    "The number of RIP broadcasts received on this 
                    interface."
                ::= { ipxRipIfEntry 5 }

            ipxIfRipOut OBJECT-TYPE
                SYNTAX Counter
                ACCESS read-only
                STATUS mandatory
                DESCRIPTION
                    "The number of RIP broadcasts sent on this 
                    interface."
                ::= { ipxRipIfEntry 6 }

            ipxIfRipAgedOut OBJECT-TYPE
                SYNTAX Counter
                ACCESS read-only
                STATUS mandatory
                DESCRIPTION
                    "The number of entries timed out and discarded on 
                    this interface."
                ::= { ipxRipIfEntry 7 }

            ipxRipTable OBJECT-TYPE
                SYNTAX SEQUENCE OF IpxRipEntry
                ACCESS not-accessible
                STATUS mandatory
                DESCRIPTION
                    "A list of RIP entries."
                ::= { xIpxRip 2 }

            ipxRipEntry OBJECT-TYPE
                SYNTAX IpxRipEntry
                ACCESS not-accessible
                STATUS mandatory
                DESCRIPTION
                    "IPX interface parameters and counters."
                INDEX { ipxRipNetwork }
                ::= { ipxRipTable 1 }

            IpxRipEntry ::=
                SEQUENCE {
                    ipxRipNetwork
                        INTEGER,
                    ipxRipRouter
                        OCTET STRING,
                    ipxRipInterface
                        INTEGER,
                    ipxRipHops
                        INTEGER,
                    ipxRipTransTime
                        INTEGER,
                    ipxRipAge
                        INTEGER
                }

            ipxRipNetwork OBJECT-TYPE
                SYNTAX INTEGER
                ACCESS read-only
                STATUS mandatory
                DESCRIPTION
                    "An IPX network number to which this router knows a 
                    path."
                ::= { ipxRipEntry 1 }

            ipxRipRouter OBJECT-TYPE
                SYNTAX OCTET STRING ( SIZE(6) )
                ACCESS read-only
                STATUS mandatory
                DESCRIPTION
                    "The Ethernet address of an IPX router on this 
                    network."
                ::= { ipxRipEntry 2 }

            ipxRipInterface OBJECT-TYPE
                SYNTAX INTEGER
                ACCESS read-only
                STATUS mandatory
                DESCRIPTION
                    "The interface to reach the router.  A value of 
                    ifIndex."
                ::= { ipxRipEntry 3 }

            ipxRipHops OBJECT-TYPE
                SYNTAX INTEGER
                ACCESS read-only
                STATUS mandatory
                DESCRIPTION
                    "The number of hops to reach the router."
                ::= { ipxRipEntry 4 }

            ipxRipTransTime OBJECT-TYPE
                SYNTAX INTEGER
                ACCESS read-only
                STATUS mandatory
                DESCRIPTION
                    "The number of 55 millisecond ticks it takes for a 
                    packet to travel to the router."
                ::= { ipxRipEntry 5 }

            ipxRipAge OBJECT-TYPE
                SYNTAX INTEGER
                ACCESS read-only
                STATUS mandatory
                DESCRIPTION
                    "The age of the RIP entry in seconds."
                ::= { ipxRipEntry 6 }

            ipxRipRtTable OBJECT-TYPE
                SYNTAX SEQUENCE OF IpxRipRtEntry
                ACCESS not-accessible
                STATUS mandatory
                DESCRIPTION
                    "A list of RIP Routing entries."
                ::= { xIpxRip 3 }

            ipxRipRtEntry OBJECT-TYPE
                SYNTAX IpxRipRtEntry
                ACCESS not-accessible
                STATUS mandatory
                DESCRIPTION
                    "IPX Routing Entry information"
                INDEX { ipxRipRtNetwork, ipxRipRtInterface, ipxRipRtOrigin,
                         ipxRipRtRouter  }
                ::= { ipxRipRtTable 1 }

            IpxRipRtEntry ::=
                SEQUENCE {
                    ipxRipRtNetwork
                        INTEGER,
                    ipxRipRtRouter
                        OCTET STRING,
                    ipxRipRtInterface
                        INTEGER,
                    ipxRipRtHops
                        INTEGER,
                    ipxRipRtTransTime
                        INTEGER,
		     ipxRipRtOrigin
			INTEGER,
		     ipxRipRtRowStatus
			INTEGER
                }

            ipxRipRtNetwork OBJECT-TYPE
                SYNTAX INTEGER
                ACCESS read-only
                STATUS mandatory
                DESCRIPTION
                    "An IPX network number to which this router knows a 
                    path."
                ::= { ipxRipRtEntry 1 }

            ipxRipRtRouter OBJECT-TYPE
                SYNTAX OCTET STRING ( SIZE(6) )
                ACCESS read-only
                STATUS mandatory
                DESCRIPTION
                    "The Ethernet address of an IPX router on this 
                    network."
                ::= { ipxRipRtEntry 2 }

            ipxRipRtInterface OBJECT-TYPE
                SYNTAX INTEGER
                ACCESS read-only
                STATUS mandatory
                DESCRIPTION
                    "The interface to reach the router.  A value of 
                    ifIndex."
                ::= { ipxRipRtEntry 3 }

            ipxRipRtHops OBJECT-TYPE
                SYNTAX INTEGER (0..16)
                ACCESS read-write
                STATUS mandatory
                DESCRIPTION
                    "The number of hops to reach the router."
                ::= { ipxRipRtEntry 4 }

            ipxRipRtTransTime OBJECT-TYPE
                SYNTAX INTEGER (0..65535)
                ACCESS read-write
                STATUS mandatory
                DESCRIPTION
                    "The number of 55 millisecond ticks it takes for a 
                    packet to travel to the router."
                ::= { ipxRipRtEntry 5 }

            ipxRipRtOrigin OBJECT-TYPE
                SYNTAX INTEGER { ripLearned(1), static(2), nlspLearned(3) }
                ACCESS read-only
                STATUS mandatory
                DESCRIPTION
                    "The source of the RIP entry, either Learned via RIP or Static."
                ::= { ipxRipRtEntry 6 }


            ipxRipRtRowStatus OBJECT-TYPE
                SYNTAX INTEGER { invalid(1), valid(2) }
                ACCESS read-write
                STATUS mandatory
                DESCRIPTION
                    "Create or Delete RIP routing table entries."
                DEFVAL { valid }
                ::= { ipxRipRtEntry 7}


            -- the SAP group

            -- Implementation of this group is mandatory for all iTouch
            -- systems that implement IPX SAP

            ipxSapIfTable OBJECT-TYPE
                SYNTAX SEQUENCE OF IpxSapIfEntry
                ACCESS not-accessible
                STATUS mandatory
                DESCRIPTION
                    "A list of IPX interface entries."
                ::= { xIpxSap 1 }

            ipxSapIfEntry OBJECT-TYPE
                SYNTAX IpxSapIfEntry
                ACCESS not-accessible
                STATUS mandatory
                DESCRIPTION
                    "IPX interface parameters and counters."
                INDEX { ipxSapIfIndex }
                ::= { ipxSapIfTable 1 }

            IpxSapIfEntry ::=
                SEQUENCE {
                    ipxSapIfIndex
                        INTEGER,
                    ipxIfSapBcst
                        INTEGER,
                    ipxIfSapBcstDiscardTimeout
                        INTEGER,
                    ipxIfSapBcstTimer
                        INTEGER,
                    ipxIfSapIn
                        Counter,
                    ipxIfSapOut
                        Counter,
                    ipxIfSapAgedOut
                        Counter
                }

            ipxSapIfIndex OBJECT-TYPE
                SYNTAX INTEGER
                ACCESS read-only
                STATUS mandatory
                DESCRIPTION
                    "An index value that uniquely identifies an IPX 
                    interface.  The interface identified by a particular 
                    value of this index is the same interface as 
                    identified by the same value of ifIndex."
                ::= { ipxSapIfEntry 1 }

            ipxIfSapBcst OBJECT-TYPE
                SYNTAX INTEGER { disabled(1), enabled(2), propUpdateOnly(3), demandCircuit(4) }
                ACCESS read-write
                STATUS mandatory
                DESCRIPTION
                    "Control whether SAP packets will be broadcasted out 
                    this interface."
                DEFVAL { enabled }
                ::= { ipxSapIfEntry 2 }

            ipxIfSapBcstDiscardTimeout OBJECT-TYPE
                SYNTAX INTEGER
                ACCESS read-write
                STATUS mandatory
                DESCRIPTION
                    "The number of seconds to wait before discarding 
                    information learned from a SAP broadcast."
                DEFVAL { 180 }
                ::= { ipxSapIfEntry 3 }

            ipxIfSapBcstTimer OBJECT-TYPE
                SYNTAX INTEGER
                ACCESS read-write
                STATUS mandatory
                DESCRIPTION
                    "The number of seconds to wait between sending out 
                    SAP broadcasts."
                DEFVAL { 60 }
                ::= { ipxSapIfEntry 4 }

            ipxIfSapIn OBJECT-TYPE
                SYNTAX Counter
                ACCESS read-only
                STATUS mandatory
                DESCRIPTION
                    "The number SAP broadcasts received on this 
                    interface."
                ::= { ipxSapIfEntry 5 }

            ipxIfSapOut OBJECT-TYPE
                SYNTAX Counter
                ACCESS read-only
                STATUS mandatory
                DESCRIPTION
                    "The number SAP broadcasts sent on this interface."
                ::= { ipxSapIfEntry 6 }

            ipxIfSapAgedOut OBJECT-TYPE
                SYNTAX Counter
                ACCESS read-only
                STATUS mandatory
                DESCRIPTION
                    "The number entries for this interface discarded due 
                    to aging timeout."
                ::= { ipxSapIfEntry 7 }

            ipxSapTable OBJECT-TYPE
                SYNTAX SEQUENCE OF IpxSapEntry
                ACCESS not-accessible
                STATUS mandatory
                DESCRIPTION
                    "A list of SAP entries."
                ::= { xIpxSap 2 }

            ipxSapEntry OBJECT-TYPE
                SYNTAX IpxSapEntry
                ACCESS not-accessible
                STATUS mandatory
                DESCRIPTION
                    "IPX interface parameters and counters."
                INDEX { ipxSapName, ipxSapType }
                ::= { ipxSapTable 1 }

            IpxSapEntry ::=
                SEQUENCE {
                    ipxSapName
                        DisplayString,
                    ipxSapNetwork
                        INTEGER,
                    ipxSapHost
                        OCTET STRING,
                    ipxSapSocket
                        INTEGER,
                    ipxSapInterface
                        INTEGER,
                    ipxSapType
                        INTEGER,
                    ipxSapAge
                        INTEGER
                }

            ipxSapName OBJECT-TYPE
                SYNTAX DisplayString (SIZE (48))
                ACCESS read-only
                STATUS mandatory
                DESCRIPTION
                    "The name of the service, null filled."
                ::= { ipxSapEntry 1 }

            ipxSapNetwork OBJECT-TYPE
                SYNTAX INTEGER
                ACCESS read-only
                STATUS mandatory
                DESCRIPTION
                    "The IPX network number on which the service's host 
                    resides."
                ::= { ipxSapEntry 2 }

            ipxSapHost OBJECT-TYPE
                SYNTAX OCTET STRING ( SIZE(6))
                ACCESS read-only
                STATUS mandatory
                DESCRIPTION
                    "The Ethernet address of the IPX host of the 
                    service."
                ::= { ipxSapEntry 3 }

            ipxSapSocket OBJECT-TYPE
                SYNTAX INTEGER
                ACCESS read-only
                STATUS mandatory
                DESCRIPTION
                    "The socket number of the service on the host."
                ::= { ipxSapEntry 4 }

            ipxSapInterface OBJECT-TYPE
                SYNTAX INTEGER
                ACCESS read-only
                STATUS mandatory
                DESCRIPTION
                    "The interface of the router in the direction of the 
                    service.  A value of ifIndex."
                ::= { ipxSapEntry 5 }

            ipxSapType OBJECT-TYPE
                SYNTAX INTEGER {
                            user(1),
                            userGroup(2),
                            printQueue(3),
                            novellFileServer(4),
                            jobServer(5),
                            gateway1(6),
                            printServer(7),
                            archiveQueue(8),
                            archiveServer(9),
                            jobQueue(10),
                            administration(11)
                        }
                ACCESS read-only
                STATUS mandatory
                DESCRIPTION
                    "The type of the service.  The enumeration is an 
					incomplete set of all possible values."
                ::= { ipxSapEntry 6 }

            ipxSapAge OBJECT-TYPE
                SYNTAX INTEGER
                ACCESS read-only
                STATUS mandatory
                DESCRIPTION
                    "The age of the Sap entry in seconds."
                ::= { ipxSapEntry 7 }

            ipxSapSvTable OBJECT-TYPE
                SYNTAX SEQUENCE OF IpxSapSvEntry
                ACCESS not-accessible
                STATUS mandatory
                DESCRIPTION
                    "A list of SAP entries."
                ::= { xIpxSap 3 }

            ipxSapSvEntry OBJECT-TYPE
                SYNTAX IpxSapSvEntry
                ACCESS not-accessible
                STATUS mandatory
                DESCRIPTION
                    "IPX interface parameters and counters."
                INDEX { ipxSapSvName, ipxSapSvType, ipxSapSvOrigin,
	                ipxSapSvNetwork, ipxSapSvSocket, ipxSapSvHost  }
                ::= { ipxSapSvTable 1 }

            IpxSapSvEntry ::=
                SEQUENCE {
                    ipxSapSvName
                        DisplayString,
                    ipxSapSvNetwork
                        INTEGER,
                    ipxSapSvHost
                        OCTET STRING,
                    ipxSapSvSocket
                        INTEGER,
                    ipxSapSvInterface
                        INTEGER,
                    ipxSapSvOrigin
                        INTEGER,
                    ipxSapSvType
                        INTEGER,
		     ipxSapSvHops
			INTEGER,
		     ipxSapSvRowStatus
			INTEGER,
		     ipxSapSvAge
			INTEGER
                }

            ipxSapSvName OBJECT-TYPE
                SYNTAX DisplayString (SIZE (0..48))
                ACCESS read-only
                STATUS mandatory
                DESCRIPTION
                    "The name of the service."
                ::= { ipxSapSvEntry 1 }

            ipxSapSvNetwork OBJECT-TYPE
                SYNTAX INTEGER
                ACCESS read-only
                STATUS mandatory
                DESCRIPTION
                    "The IPX network number on which the service's host 
                    resides."
                ::= { ipxSapSvEntry 2 }

            ipxSapSvHost OBJECT-TYPE
                SYNTAX OCTET STRING ( SIZE(6))
                ACCESS read-only
                STATUS mandatory
                DESCRIPTION
                    "The Ethernet address of the IPX host of the 
                    service."
                ::= { ipxSapSvEntry 3 }

            ipxSapSvSocket OBJECT-TYPE
                SYNTAX INTEGER (0..65535)
                ACCESS read-only
                STATUS mandatory
                DESCRIPTION
                    "The socket number of the service on the host."
                ::= { ipxSapSvEntry 4 }

            ipxSapSvInterface OBJECT-TYPE
                SYNTAX INTEGER
                ACCESS read-only
                STATUS mandatory
                DESCRIPTION
                    "The interface of the router in the direction of the 
                    service.  A value of ifIndex."
                ::= { ipxSapSvEntry 5 }

            ipxSapSvOrigin OBJECT-TYPE
                SYNTAX INTEGER {
                            ipxSapLearned(1),
                            ipxStatic(2)
                       }
                ACCESS read-only
                STATUS mandatory
                DESCRIPTION
                    "The source of the RIP entry, either Learned via RIP or Static."
                ::= { ipxSapSvEntry 6 }

            ipxSapSvType OBJECT-TYPE
                SYNTAX INTEGER {
                            user(1),
                            userGroup(2),
                            printQueue(3),
                            novellFileServer(4),
                            jobServer(5),
                            gateway1(6),
                            printServer(7),
                            archiveQueue(8),
                            archiveServer(9),
                            jobQueue(10),
                            administration(11)
                        }
                ACCESS read-only
                STATUS mandatory
                DESCRIPTION
                    "The type of the service.  The enumeration is an 
					incomplete set of all possible values."
                ::= { ipxSapSvEntry 7 }

            ipxSapSvHops OBJECT-TYPE
                SYNTAX INTEGER (0..16)
                ACCESS read-write
                STATUS mandatory
                DESCRIPTION
                    "The number of hops to the Service."
                ::= { ipxSapSvEntry 8 }

            ipxSapSvRowStatus OBJECT-TYPE
                SYNTAX INTEGER { disabled(1), enabled(2) }
                ACCESS read-write
                STATUS mandatory
                DESCRIPTION
                    "Create or Delete SAP Service table entries."
                DEFVAL { enabled }
                ::= { ipxSapSvEntry 9}

            ipxSapSvAge OBJECT-TYPE
                SYNTAX INTEGER
                ACCESS read-only
                STATUS mandatory
                DESCRIPTION
                    "The age of the Sap entry in seconds."
                ::= { ipxSapSvEntry 10 }

            -- the IPX Filter group

            -- Implementation of this group is mandatory for all iTouch
            -- systems that implement IPX Filtering

            ipxIfFilterTable OBJECT-TYPE
                SYNTAX SEQUENCE OF IpxIfFilterEntry
                ACCESS not-accessible
                STATUS mandatory
                DESCRIPTION
                    "A list of IPX interface Source and Destination
                     address Filter entries."
                ::= { xIpxFilter 1 }

            ipxIfFilterEntry OBJECT-TYPE
                SYNTAX IpxIfFilterEntry
                ACCESS not-accessible
                STATUS mandatory
                DESCRIPTION
                    "IPX Source and Destination interface Filters."
                INDEX { ipxIfIndex, ipxIfFilterDestNetwork, ipxIfFilterDestNode,
                        ipxIfFilterSourceNetwork, ipxIfFilterSourceNode, 
                        ipxIfFilterPacketType, ipxIfFilterStatusDestNetworkAll,
			ipxIfFilterStatusDestNodeAll,ipxIfFilterStatusSourceNetworkAll,
			ipxIfFilterStatusSourceNodeAll,ipxIfFilterStatusPacketTypeAll  }
                ::= { ipxIfFilterTable 1 }

            IpxIfFilterEntry ::=
                SEQUENCE {
                    ipxIfFilterIndex
                        INTEGER,
                    ipxIfFilterDestNetwork
                        INTEGER,
                    ipxIfFilterDestNode
                        OCTET STRING,
                    ipxIfFilterSourceNetwork
                        INTEGER,
                    ipxIfFilterSourceNode
                        OCTET STRING,
                    ipxIfFilterPacketType
                        INTEGER,
                    ipxIfFilterAction
                        INTEGER,
                    ipxIfFilterRowStatus
                        INTEGER,
                    ipxIfFilterStatusDestNetworkAll
                        INTEGER,
                    ipxIfFilterStatusDestNodeAll
                        INTEGER,
                    ipxIfFilterStatusSourceNetworkAll
                        INTEGER,
                    ipxIfFilterStatusSourceNodeAll
                        INTEGER,
                    ipxIfFilterStatusPacketTypeAll
                        INTEGER
                }

            ipxIfFilterIndex OBJECT-TYPE
                SYNTAX INTEGER
                ACCESS read-only
                STATUS mandatory
                DESCRIPTION
                    "The interface to which this IPX Address filter applies.
                     A value of ifIndex."
                ::= { ipxIfFilterEntry 1 }

            ipxIfFilterDestNetwork OBJECT-TYPE
                SYNTAX INTEGER
                ACCESS read-only
                STATUS mandatory
                DESCRIPTION
                    "The destination IPX network to be filtered."
                ::= { ipxIfFilterEntry 2 }

            ipxIfFilterDestNode OBJECT-TYPE
                SYNTAX OCTET STRING ( SIZE(6))
                ACCESS read-only
                STATUS mandatory
                DESCRIPTION
                    "The destination IPX node to be filtered."
                ::= { ipxIfFilterEntry 3 }

            ipxIfFilterSourceNetwork OBJECT-TYPE
                SYNTAX INTEGER
                ACCESS read-only
                STATUS mandatory
                DESCRIPTION
                    "The destination IPX network to be filtered."
                ::= { ipxIfFilterEntry 4 }

            ipxIfFilterSourceNode OBJECT-TYPE
                SYNTAX OCTET STRING ( SIZE(6))
                ACCESS read-only
                STATUS mandatory
                DESCRIPTION
                    "The destination IPX node to be filtered."
                ::= { ipxIfFilterEntry 5 }

            ipxIfFilterPacketType OBJECT-TYPE
                SYNTAX INTEGER (0..255) 
                ACCESS read-only
                STATUS mandatory
                DESCRIPTION
                    "The IPX packet type to be filtered."
                ::= { ipxIfFilterEntry 6 }

            ipxIfFilterAction OBJECT-TYPE
                SYNTAX INTEGER {
                           forward(1),
                           discard(2)
                       }
                ACCESS read-write
                STATUS mandatory
                DESCRIPTION
                    "The IPX filter action to be taken, either Forward or Discard."
                ::= { ipxIfFilterEntry 7 }

            ipxIfFilterRowStatus OBJECT-TYPE
                SYNTAX INTEGER {
                           invalid(1),
                           valid(2)
                       }
                ACCESS read-write
                STATUS mandatory
                DESCRIPTION
                    "The IPX Filter create or delete function."
                ::= { ipxIfFilterEntry 8 }

            ipxIfFilterStatusDestNetworkAll OBJECT-TYPE
                SYNTAX INTEGER {
                           disabled(1),
                           enabled(2)
                       }
                ACCESS read-only
                STATUS mandatory
                DESCRIPTION
                    "The IPX Filter flag meaning ALL destination networks."
                ::= { ipxIfFilterEntry 9 }

            ipxIfFilterStatusDestNodeAll OBJECT-TYPE
                SYNTAX INTEGER {
                           disabled(1),
                           enabled(2)
                       }
                ACCESS read-only
                STATUS mandatory
                DESCRIPTION
                    "The IPX Filter flag meaning ALL destination nodes."
                ::= { ipxIfFilterEntry 10 }

            ipxIfFilterStatusSourceNetworkAll OBJECT-TYPE
                SYNTAX INTEGER {
                           disabled(1),
                           enabled(2)
                       }
                ACCESS read-only
                STATUS mandatory
                DESCRIPTION
                    "The IPX Filter flag meaning ALL source networks."
                ::= { ipxIfFilterEntry 11 }

            ipxIfFilterStatusSourceNodeAll OBJECT-TYPE
                SYNTAX INTEGER {
                           disabled(1),
                           enabled(2)
                       }
                ACCESS read-only
                STATUS mandatory
                DESCRIPTION
                    "The IPX Filter flag meaning ALL source nodes."
                ::= { ipxIfFilterEntry 12 }

            ipxIfFilterStatusPacketTypeAll OBJECT-TYPE
                SYNTAX INTEGER {
                           disabled(1),
                           enabled(2)
                       }
                ACCESS read-only
                STATUS mandatory
                DESCRIPTION
                    "The IPX Filter flag meaning ALL packet types."
                ::= { ipxIfFilterEntry 13 }


            ipxIfRipFilterTable OBJECT-TYPE
                SYNTAX SEQUENCE OF IpxIfRipFilterEntry
                ACCESS not-accessible
                STATUS mandatory
                DESCRIPTION
                    "A list of IPX interface RIP Filter entries."
                ::= { xIpxFilter 2 }

            ipxIfRipFilterEntry OBJECT-TYPE
                SYNTAX IpxIfRipFilterEntry
                ACCESS not-accessible
                STATUS mandatory
                DESCRIPTION
                    "IPX RIP interface Filters."
                INDEX { ipxIfIndex, ipxIfRipFilterType, ipxIfRipFilterNetwork, ipxIfRipFilterNetworkAll, 
			ipxIfRipFilterHost }
                ::= { ipxIfRipFilterTable 1 }

            IpxIfRipFilterEntry ::=
                SEQUENCE {
                    ipxIfRipFilterNetwork
                        INTEGER,
                    ipxIfRipFilterType
                        INTEGER,
                    ipxIfRipFilterAction
                        INTEGER,
                    ipxIfRipFilterRowStatus
                        INTEGER,
                    ipxIfRipFilterNetworkAll
                        INTEGER,
                    ipxIfRipFilterHost
			OCTET STRING
                }

            ipxIfRipFilterNetwork OBJECT-TYPE
                SYNTAX INTEGER
                ACCESS read-only
                STATUS mandatory
                DESCRIPTION
                    "The IPX RIP network to be filtered."
                ::= { ipxIfRipFilterEntry 1 }

            ipxIfRipFilterType OBJECT-TYPE
                SYNTAX INTEGER {
                           import(1),
                           export(2)
                       }
                ACCESS read-only
                STATUS mandatory
                DESCRIPTION
                    "The IPX RIP filter type, either IMPORT or EXPORT."
                ::= { ipxIfRipFilterEntry 2 }

            ipxIfRipFilterAction OBJECT-TYPE	
                SYNTAX INTEGER {
                           allow(1),
                           deny(2)
                       }
                ACCESS read-write	
                STATUS mandatory	
                DESCRIPTION	
                    "The IPX RIP filter action to be taken, either ALLOW or DENY."
                ::= { ipxIfRipFilterEntry 3 }

            ipxIfRipFilterRowStatus OBJECT-TYPE
                SYNTAX INTEGER {
                           invalid(1),
                           valid(2)
                       }
                ACCESS read-write
                STATUS mandatory
                DESCRIPTION
                    "The IPX RIP Filter create or delete function."
                ::= { ipxIfRipFilterEntry 4 }

            ipxIfRipFilterNetworkAll OBJECT-TYPE
                SYNTAX INTEGER {
                           disabled(1),
                           enabled(2)
                       }
                ACCESS read-only
                STATUS mandatory
                DESCRIPTION
                    "The IPX RIP Filter flag meaning filter ALL networks."
                ::= { ipxIfRipFilterEntry 5 }


            ipxIfRipFilterHost OBJECT-TYPE
                SYNTAX OCTET STRING (SIZE (6))
                ACCESS read-only
                STATUS mandatory
                DESCRIPTION
                    "The RIP Filter IPX Host Address from which RIP will ALLOW/DENY IMPORT of routes."
                ::= { ipxIfRipFilterEntry 6 }


            ipxIfSapFilterTable OBJECT-TYPE
                SYNTAX SEQUENCE OF IpxIfSapFilterEntry
                ACCESS not-accessible
                STATUS mandatory
                DESCRIPTION
                    "A list of IPX interface SAP Filter entries."
                ::= { xIpxFilter 3 }

            ipxIfSapFilterEntry OBJECT-TYPE
                SYNTAX IpxIfSapFilterEntry
                ACCESS not-accessible
                STATUS mandatory
                DESCRIPTION
                    "IPX SAP interface Filters."
                INDEX { ipxIfIndex, ipxIfSapFilterType, ipxIfSapFilterName, ipxIfSapFilterServiceType, 
                        ipxIfSapFilterServiceTypeAll, ipxIfSapFilterNetwork, ipxIfSapFilterNetworkAll, 
			ipxIfSapFilterHost }
                ::= { ipxIfSapFilterTable 1 }

            IpxIfSapFilterEntry ::=
                SEQUENCE {
                    ipxIfSapFilterNetwork
                        INTEGER,
                    ipxIfSapFilterType
                        INTEGER,
                    ipxIfSapFilterServiceType
                        INTEGER,
                    ipxIfSapFilterAction
                        INTEGER,
                    ipxIfSapFilterRowStatus
                        INTEGER,
                    ipxIfSapFilterNetworkAll
                        INTEGER,
                    ipxIfSapFilterServiceTypeAll
                        INTEGER,
                    ipxIfSapFilterName
                        DisplayString,
                    ipxIfSapFilterHost
                        OCTET STRING
                }

            ipxIfSapFilterNetwork OBJECT-TYPE
                SYNTAX INTEGER
                ACCESS read-only
                STATUS mandatory
                DESCRIPTION
                    "The IPX SAP network to be filtered."
                ::= { ipxIfSapFilterEntry 1 }

            ipxIfSapFilterType OBJECT-TYPE
                SYNTAX INTEGER {
                           import(1),
                           export(2)
                       }
                ACCESS read-only
                STATUS mandatory
                DESCRIPTION
                    "The IPX SAP filter type, either IMPORT or EXPORT."
                ::= { ipxIfSapFilterEntry 2 }

            ipxIfSapFilterServiceType OBJECT-TYPE
                SYNTAX INTEGER (0..65535)
                ACCESS read-only
                STATUS mandatory
                DESCRIPTION
                    "The IPX SAP service type to which this filter applies."
                ::= { ipxIfSapFilterEntry 3 }

            ipxIfSapFilterAction OBJECT-TYPE	
                SYNTAX INTEGER {
                           allow(1),
                           deny(2)
                       }
                ACCESS read-write	
                STATUS mandatory	
                DESCRIPTION	
                    "The IPX SAP filter action to be taken, either ALLOW or DENY."
                ::= { ipxIfSapFilterEntry 4 }

            ipxIfSapFilterRowStatus OBJECT-TYPE
                SYNTAX INTEGER {
                           invalid(1),
                           valid(2)
                       }
                ACCESS read-write
                STATUS mandatory
                DESCRIPTION
                    "The IPX SAP Filter create or delete function."
                ::= { ipxIfSapFilterEntry 5 }

            ipxIfSapFilterNetworkAll OBJECT-TYPE
                SYNTAX INTEGER {
                           disabled(1),
                           enabled(2)
                       }
                ACCESS read-only
                STATUS mandatory
                DESCRIPTION
                    "The IPX SAP Filter flag meaning filter ALL networks."
                ::= { ipxIfSapFilterEntry 6 }

            ipxIfSapFilterServiceTypeAll OBJECT-TYPE
                SYNTAX INTEGER {
                           disabled(1),
                           enabled(2)
                       }
                ACCESS read-only
                STATUS mandatory
                DESCRIPTION
                    "The IPX SAP Filter flag meaning filter ALL service types."
                ::= { ipxIfSapFilterEntry 7 }

            ipxIfSapFilterName OBJECT-TYPE
                SYNTAX DisplayString (SIZE (0..48))
                ACCESS read-only
                STATUS mandatory
                DESCRIPTION
                    "The name of the service to be filtered."
                ::= { ipxIfSapFilterEntry 8 }

            ipxIfSapFilterHost OBJECT-TYPE
                SYNTAX OCTET STRING (SIZE (6))
                ACCESS read-only
                STATUS mandatory
                DESCRIPTION
                    "The IPX Host address from which SAP will ALLOW/DENY IMPORT of services ."
                ::= { ipxIfSapFilterEntry 9 }

            -- the Printer group

            -- Implementation of this group is mandatory for all iTouch
            -- systems that implement IPX printers

            -- Additional single-instance values follow the Port table

            -- the Printer Port table

            ipxPrinterPortTable OBJECT-TYPE
                SYNTAX SEQUENCE OF IpxPrinterPortEntry
                ACCESS not-accessible
                STATUS mandatory
                DESCRIPTION
                    "A list of IPX printer character port entries."
                ::= { xIpxPrinter 1 }

            ipxPrinterPortEntry OBJECT-TYPE
                SYNTAX IpxPrinterPortEntry
                ACCESS not-accessible
                STATUS mandatory
                DESCRIPTION
                    "IPX printer parameter values for a character 
                    port."
                INDEX { ipxPrinterPortIndex }
                ::= { ipxPrinterPortTable 1 }

            IpxPrinterPortEntry ::=
                SEQUENCE {
                    ipxPrinterPortIndex
                        INTEGER,
                    ipxPrinterPortStatus
                        INTEGER,
                    ipxPrinterPortServer
                        DisplayString,
                    ipxPrinterPortPrinter
                        INTEGER,
                    ipxTimeout
                        INTEGER
                }

            ipxPrinterPortIndex OBJECT-TYPE
                SYNTAX INTEGER
                ACCESS read-only
                STATUS mandatory
                DESCRIPTION
                    "An index value that uniquely identifies a port.  
                    The port identified by a particular value of this 
                    index is the same port as identified by 
                    charPortIndex in the Proposed Standard Internet 
                    Character MIB."
                ::= { ipxPrinterPortEntry 1 }

            ipxPrinterPortStatus OBJECT-TYPE
                SYNTAX INTEGER { invalid(1), valid(2) }
                ACCESS read-write
                STATUS mandatory
                DESCRIPTION
                    "Status of this entry.  Setting the value to 
                    'invalid' invalidates the entry.  It is an 
                    implementation-specific matter as to whether the 
                    agent removes an invalidated entry from the table."
                DEFVAL { valid }
                ::= { ipxPrinterPortEntry 2 }

            ipxPrinterPortServer OBJECT-TYPE
                SYNTAX DisplayString (SIZE (0..48))
                ACCESS read-write
                STATUS mandatory
                DESCRIPTION
                    "The name of an active print server on the 
                    network."
                ::= { ipxPrinterPortEntry 3 }

            ipxPrinterPortPrinter OBJECT-TYPE
                SYNTAX INTEGER (0..255)
                ACCESS read-write
                STATUS mandatory
                DESCRIPTION
                    "An available remote printer on 
                    ixpPrinterPortServer."
                ::= { ipxPrinterPortEntry 4 }

             ipxTimeout OBJECT-TYPE
                SYNTAX INTEGER (15..300)
                ACCESS read-write
                STATUS mandatory
                DESCRIPTION
                    "A control to set the the time at which a print job from a
                     print server will be timed out and the port freed."
                DEFVAL { 15 }
                ::= { ipxPrinterPortEntry 5 }

            -- The following are additional single-instance values, 
            -- not part of the Port table.

            ipxPrinterEthernet OBJECT-TYPE
                SYNTAX INTEGER { disabled(1), enabled(2) }
                ACCESS read-write
                STATUS mandatory
                DESCRIPTION
                    "Control for use of Ethernet-style message framing, 
                    with the IPX protocol type.  Mutually exclusive with 
                    ipxPrinterMac, ipxPrinterMac802_2_Snap, and ipxPrinterMac802_2."
                ::= { xIpxPrinter 2 }

            ipxPrinterMac OBJECT-TYPE
                SYNTAX INTEGER { disabled(1), enabled(2) }
                ACCESS read-write
                STATUS mandatory
                DESCRIPTION
                    "Control for use of MAC-only message framing, with 
                    no protocol type.  Mutually exclusive with 
                    ipxPrinterEthernet, ipxPrinterMac802_2_Snap, and ipxPrinterMac802_2."
                ::= { xIpxPrinter 3 }

            ipxPrinterMac802-2 OBJECT-TYPE
                SYNTAX INTEGER { disabled(1), enabled(2) }
                ACCESS read-write
                STATUS mandatory
                DESCRIPTION
                    "Control for use of MAC message framing with 
                    802.2 framing.  Mutually exclusive with 
                    ipxPrinterEthernet, ipxPrinterMac, and ipxPrinterMac802_2_Snap."
                ::= { xIpxPrinter 4 }

            ipxPrinterMac802-2-Snap OBJECT-TYPE
                SYNTAX INTEGER { disabled(1), enabled(2) }
                ACCESS read-write
                STATUS mandatory
                DESCRIPTION
                    "Control for use of MAC-only message framing with 
                    802 Snap framing.  Mutually exclusive with 
                    ipxPrinterEthernet, ipxPrinterMac, and ipxPrinterMac802_2."
                ::= { xIpxPrinter 5 }



--
-- FILE: /users/sse/mibs/src/itouch/it-isis-mib.mib
--

-- $Id: it-isis-mib.mib,v 1.1 2000/07/25 14:30:22 sse Exp $


           ExistState ::= INTEGER
                             {
                                off(1),
                                on(2)
                             }
              -- Type used in row creation and deletion.

           SupportedProtocol ::= INTEGER
                             {
                               iso8473(129),
                               ip(204)
                             }
             -- Types of network protocol supported by Integrated ISIS.
             -- The values for ISO8473 and IP are those registered for
             -- these protocols in ISO TR9577.

xIsis OBJECT IDENTIFIER ::= { iTouch 26 }

   xIsisSystem    OBJECT IDENTIFIER ::= { xIsis 1 }
   xIsisCirc      OBJECT IDENTIFIER ::= { xIsis 2 }
   xIsisISAdj     OBJECT IDENTIFIER ::= { xIsis 3 }
   xIsisESAdj     OBJECT IDENTIFIER ::= { xIsis 4 }
   xIsisReachAddr OBJECT IDENTIFIER ::= { xIsis 5 }
   xIsisCLNPDest  OBJECT IDENTIFIER ::= { xIsis 7 }

            -- This is a MIB module for all iTouch Communications systems that
            -- implement ISIS.

            -- Copyright 2000 iTouch Communications, Inc. All Rights Reserved.
            -- Reproduction of this document is authorized on
            -- condition that this copyright notice is included.
            -- This MIB document embodies iTouch Communications, Inc.'s 
            -- proprietary intellectual property.  iTouch Communications, Inc.
            -- retains all title and ownership in this MIB, including any
            -- revisions.
            --
            -- It is iTouch Communications, Inc.'s intent to encourage the
            -- widespread use of this MIB in connection with the management of
            -- iTouch Communications, Inc. products. iTouch Communications,
            -- Inc. grants vendors,end-users, and other interested parties a
            -- non-exclusive license to use this MIB in connection with the
            -- management of iTouch Communications, Inc. products.
            --
            -- This MIB document is supplied "AS IS," and iTouch 
            -- Communications, Inc. makes no warranty, either express or
            -- implied, as to the use operation, condition, or performance of
            -- the MIB.


-- The System Table

-- The System Table contains one row for each separate instance
-- of the Integrated IS-IS protocol.

xIsisSysTable OBJECT-TYPE
   SYNTAX SEQUENCE OF XIsisSysEntry
   ACCESS not-accessible
   STATUS mandatory
   DESCRIPTION
       "The set of instances of the Integrated IS-IS protocol
       existing on the system."
   ::= { xIsisSystem 1 }

xIsisSysEntry OBJECT-TYPE
   SYNTAX XIsisSysEntry
   ACCESS not-accessible
   STATUS mandatory
   DESCRIPTION
       "Each row defines information specific to a single
       instance of the protocol existing on the system."
   REFERENCE "ANSI {ISIS.poi cLNSISISBasic-P (1)}"
   INDEX { xIsisSysInstance }
   ::= { xIsisSysTable 1 }

XIsisSysEntry ::=
   SEQUENCE {
      xIsisSysInstance
         INTEGER,
      xIsisSysExistState
         INTEGER,
      xIsisSysVersion
         INTEGER,
      xIsisSysType
         INTEGER,
      xIsisSysNET
         OCTET STRING,
      xIsisSysMaxPathSplits
         INTEGER,
      xIsisSysMinLSPTransInt
         INTEGER,
      xIsisSysMaxLSPGenInt
         INTEGER,
      xIsisSysMinBroadLSPTransInt
         INTEGER,
      xIsisSysCompSNPInt
         INTEGER,
      xIsisSysOrigL1LSPBuffSize
         INTEGER,
      xIsisSysMaxAreaAddr
         INTEGER,
      xIsisSysMinLSPGenInt
         INTEGER,
      xIsisSysPollESHelloRate
         INTEGER,
      xIsisSysPartSNPInt
         INTEGER,
      xIsisSysWaitTime
         INTEGER,
      xIsisSysDRISISHelloTimer
         INTEGER,
      xIsisSysOperState
         INTEGER,
      xIsisSysL1State
         INTEGER,
      xIsisSysCorrLSPs
         Counter,
      xIsisSysL1LSPDbaseOloads
         Counter,
      xIsisSysManAddrsDropFromArea
         Counter,
      xIsisSysAttmptsToExMaxSeqNum
         Counter,
      xIsisSysSeqNumSkips
         Counter,
      xIsisSysOwnLSPPurges
         Counter,
      xIsisSysIDFieldLenMismatches
         Counter,
      xIsisSysMaxAreaMis
         Counter,
      xIsisSysOrigL2LSPBuffSize
         INTEGER,
      xIsisSysL2State
         INTEGER,
      xIsisSysL2LSPDbaseOloads
         Counter,
      xIsisSysMaxAreaCheck
         INTEGER
   }


xIsisSysInstance OBJECT-TYPE
   SYNTAX INTEGER
   ACCESS read-only
   STATUS mandatory
   DESCRIPTION
       "The unique identifier of the Integrated IS-IS instance
       to which this row corresponds. This object follows the
       index behaviour."
   ::= { xIsisSysEntry 1 }

xIsisSysExistState OBJECT-TYPE
   SYNTAX INTEGER {
             off(1),
             on(2)
          }
   ACCESS read-only
   STATUS mandatory
   DESCRIPTION
       "The validity of this instance of the Integrated IS-IS
       protocol. This object follows the existenceState
       behaviour."
   ::= { xIsisSysEntry 2 }

xIsisSysVersion OBJECT-TYPE
   SYNTAX INTEGER
   ACCESS read-only
   STATUS mandatory
   DESCRIPTION
       "The version number of the IS-IS protocol to which this
       instance conforms. This value must be set by the
       implementation when the row is valid."
   REFERENCE "ANSI {ISIS.aoi version (1)}"
   ::= { xIsisSysEntry 3 }

xIsisSysType OBJECT-TYPE
   SYNTAX   INTEGER {
               level1IS(1),
               level2IS(2)
            }
   ACCESS read-write
   STATUS mandatory
   DESCRIPTION
       "The type of this instance of the Integrated IS-IS
       protocol. This object follows the
       replaceOnlyWhileDisabled behaviour."
   REFERENCE "ANSI {ISIS.aoi iSType (2)}"
   ::= { xIsisSysEntry 4 }

xIsisSysNET OBJECT-TYPE
   SYNTAX OCTET STRING
   ACCESS read-only
   STATUS mandatory
   DESCRIPTION
       "The ID for this instance of the Integrated IS-IS
       protocol. This value is appended to each of the
       instance's area addresses to form the Network Entity
       Titles valid for this instance. The derivation of a value
       for this object is implementation-specific. Some
       implementations may assign values and not permit write
       access, others may require the value to be set manually."
   REFERENCE "ANSI {ISIS.aoi systemId (119)}"
   ::= { xIsisSysEntry 5 }

xIsisSysMaxPathSplits OBJECT-TYPE
   SYNTAX INTEGER (1..32)
   ACCESS read-write
   STATUS mandatory
   DESCRIPTION
       "Maximum number of paths with equal routing metric value
       which it is permitted to split between. This object
       follows the replaceOnlyWhileDisabled behaviour."
   REFERENCE "ANSI {ISIS.aoi maximumPathSplits (3)}"
   ::= { xIsisSysEntry 6 }

xIsisSysMinLSPTransInt OBJECT-TYPE
   SYNTAX INTEGER (1..65535)
   ACCESS read-write
   STATUS mandatory
   DESCRIPTION
       "Minimum interval, in seconds, between re-transmission of
       an LSP. This object follows the resettingTimer
       behaviour."
   REFERENCE "ANSI {ISIS.aoi minimumLSPTransmissionInterval (5)}"
   ::= { xIsisSysEntry 7 }

xIsisSysMaxLSPGenInt OBJECT-TYPE
   SYNTAX INTEGER (1..65535)
   ACCESS read-write
   STATUS mandatory
   DESCRIPTION
       "Maximum interval, in seconds, between generated LSPs by
       this instance. This object follows the resettingTimer
       behaviour."
   REFERENCE "ANSI {ISIS.aoi maximumLSPGenerationInterval (6)}"
   ::= { xIsisSysEntry 8 }

xIsisSysMinBroadLSPTransInt OBJECT-TYPE
   SYNTAX INTEGER (1..65535)
   ACCESS read-write
   STATUS mandatory
   DESCRIPTION
       "Minimum interval, in milliseconds, between transmission
       of LSPs on a broadcast circuit. This object follows the
       resettingTimer behaviour. This timer shall be capable of
       a resolution not coarser than 10 milliseconds."
   REFERENCE "ANSI {ISIS.aoi
      minimumBroadcastLSPTransmissionInterval (7)}"
   ::= { xIsisSysEntry 9 }

xIsisSysCompSNPInt OBJECT-TYPE
   SYNTAX INTEGER (1..600)
   ACCESS read-write
   STATUS mandatory
   DESCRIPTION
       "Interval, in seconds, between generation of Complete
       Sequence Numbers PDUs by a designated Intermediate System
       on a broadcast circuit. This object follows the
       resettingTimer behaviour."
   REFERENCE "ANSI {ISIS.aoi completeSNPInterval (8)}"
   ::= { xIsisSysEntry 10 }

xIsisSysOrigL1LSPBuffSize OBJECT-TYPE
   SYNTAX INTEGER (512..1492)
   ACCESS read-write
   STATUS mandatory
   DESCRIPTION
       "The maximum size of Level 1 LSPs and SNPs originated by
       this instance. This object follows the
       replaceOnlyWhileDisabled behaviour."
   REFERENCE "ANSI {ISIS.aoi originatingL1LSPBufferSize (9)}"
   ::= { xIsisSysEntry 11 }

xIsisSysMaxAreaAddr OBJECT-TYPE
   SYNTAX INTEGER (0..254)
   ACCESS read-write
   STATUS mandatory
   DESCRIPTION
       "The maximum number of area addresses to be permitted for
       the area in which this instance exists. Note that all
       Intermediate Systems in the same area must have the same
       value configured for this attribute if correct operation
       is to be assumed. This object follows the
       replaceOnlyWhileDisabled behaviour."
   REFERENCE "ANSI {ISIS.aoi maximumAreaAddresses (4)}"
   ::= { xIsisSysEntry 12 }

xIsisSysMinLSPGenInt OBJECT-TYPE
   SYNTAX INTEGER (1..65535)
   ACCESS read-write
   STATUS mandatory
   DESCRIPTION
       "Minimum interval, in seconds, between successive
       generation of LSPs with the same LSPID by this instance.
       This object follows the resettingTimer behaviour."
   REFERENCE "ANSI {ISIS.aoi minimumLSPGenerationInterval (11)}"
   ::= { xIsisSysEntry 13 }

xIsisSysPollESHelloRate OBJECT-TYPE
   SYNTAX INTEGER (1..65535)
   ACCESS read-write
   STATUS mandatory
   DESCRIPTION
       "The value, in seconds, to be used for the suggested ES
       configuration  timer in ISH PDUs when soliciting the ES
       configuration."
   REFERENCE "ANSI {ISIS.aoi pollESHelloRate (13)}"
   ::= { xIsisSysEntry 14 }

xIsisSysPartSNPInt OBJECT-TYPE
   SYNTAX INTEGER (1..65535)
   ACCESS read-write
   STATUS mandatory
   DESCRIPTION
       "Minimum interval between sending Partial Sequence Number
       PDUs. This object follows the resettingTimer behaviour."
   REFERENCE "ANSI {ISIS.aoi partialSNPInterval (14)}"
   ::= { xIsisSysEntry 15 }

xIsisSysWaitTime OBJECT-TYPE
   SYNTAX INTEGER (1..65535)
   ACCESS read-write
   STATUS mandatory
   DESCRIPTION
       "Number of seconds to delay in waiting state before
       entering on state. This object follows the resettingTimer
       behaviour."
   REFERENCE "ANSI {ISIS.aoi waitingTime (15)}"
   ::= { xIsisSysEntry 16 }

xIsisSysDRISISHelloTimer OBJECT-TYPE
   SYNTAX INTEGER (1..65535)
   ACCESS read-write
   STATUS mandatory
   DESCRIPTION
       "The interval, in seconds, between the generation of IIH
       PDUs by the designated IS on a LAN. This object follows
       the resettingTimer behaviour."
   REFERENCE "ANSI {ISIS.aoi dRISISHelloTimer (16)}"
   ::= { xIsisSysEntry 17 }

xIsisSysOperState OBJECT-TYPE
   SYNTAX INTEGER {
		off(1),
		on(2)
		}
   ACCESS read-write
   STATUS mandatory
   DESCRIPTION
       "The operational state of this instance of the Integrated
       IS-IS protocol. Setting this object to the value on when
       its current value is off enables operation of this
       instance of the Integrated IS-IS protocol."
   ::= { xIsisSysEntry 18 }

xIsisSysL1State OBJECT-TYPE
   SYNTAX INTEGER {
		off(1),
		on(2),
		waiting(3)
		}
   ACCESS read-only
   STATUS mandatory
   DESCRIPTION
       "The state of the Level 1 database."
   REFERENCE "ANSI {ISIS.aoi l1State (17)}"
   ::= { xIsisSysEntry 19 }

xIsisSysCorrLSPs OBJECT-TYPE
   SYNTAX Counter
   ACCESS read-only
   STATUS mandatory
   DESCRIPTION
       "Number of corrupted LSPs detected."
   REFERENCE "ANSI {ISIS.aoi corruptedLSPsDetected (19)}"
   ::= { xIsisSysEntry 20 }

xIsisSysL1LSPDbaseOloads OBJECT-TYPE
   SYNTAX Counter
   ACCESS read-only
   STATUS mandatory
   DESCRIPTION
       "Number of times the LSP L1 database has become
       overloaded."
   REFERENCE "ANSI {ISIS.aoi lSPL1DatabaseOverloads (20)}"
   ::= { xIsisSysEntry 21 }

xIsisSysManAddrsDropFromArea OBJECT-TYPE
   SYNTAX Counter
   ACCESS read-only
   STATUS mandatory
   DESCRIPTION
       "Number of times a manual address has been dropped from
       the area."
   REFERENCE "ANSI {ISIS.aoi manualAddressesDroppedFromArea (21)}"
   ::= { xIsisSysEntry 22 }

xIsisSysAttmptsToExMaxSeqNum OBJECT-TYPE
   SYNTAX Counter
   ACCESS read-only
   STATUS mandatory
   DESCRIPTION
       "Number of times the IS has attempted to exceed the
       maximum sequence number."
   REFERENCE "ANSI {ISIS.aoi attemptsToExceedmaximumSequenceNumber (22)}"
   ::= { xIsisSysEntry 23 }

xIsisSysSeqNumSkips OBJECT-TYPE
   SYNTAX Counter
   ACCESS read-only
   STATUS mandatory
   DESCRIPTION
       "Number of times a sequence number skip has occurred."
   REFERENCE "ANSI {ISIS.aoi sequenceNumberSkips (23)}"
   ::= { xIsisSysEntry 24 }

xIsisSysOwnLSPPurges OBJECT-TYPE
   SYNTAX Counter
   ACCESS read-only
   STATUS mandatory
   DESCRIPTION
       "Number of times a zero-aged copy of the system's own LSP
       is received from some other node."
   REFERENCE "ANSI {ISIS.aoi ownLSPPurges (24)}"
   ::= { xIsisSysEntry 25 }

xIsisSysIDFieldLenMismatches OBJECT-TYPE
   SYNTAX Counter
   ACCESS read-only
   STATUS mandatory
   DESCRIPTION
       "Number of times a PDU is received with a different value
       for ID field length to that of the receiving system."
   REFERENCE "ANSI {ISIS.aoi iDFieldLengthMismatches (25)}"
   ::= { xIsisSysEntry 26 }

xIsisSysMaxAreaMis OBJECT-TYPE
   SYNTAX Counter
   ACCESS read-only
   STATUS mandatory
   DESCRIPTION
       "Number of times a PDU is received with a different value
       for MaximumAreaAddresses from that of the receiving
       system."
   REFERENCE "ANSI {ISIS.aoi MaximumAreaAddressesMismatches (118)}"
   ::= { xIsisSysEntry 27 }

-- The following objects map those from the cLNSISISLevel2-P
-- Package

xIsisSysOrigL2LSPBuffSize OBJECT-TYPE
   SYNTAX INTEGER (512..1492)
   ACCESS read-write
   STATUS mandatory
   DESCRIPTION
       "The maximum size of Level 2 LSPs and SNPs originated by
       this system. This object follows the
       replaceOnlyWhileDisabled behaviour."
   REFERENCE "ANSI {ISIS.aoi originatingL2LSPBufferSize (26)}"
   ::= { xIsisSysEntry 28 }

xIsisSysL2State OBJECT-TYPE
   SYNTAX INTEGER 	{
		off(1),
		on(2),
		waiting(3)
		}
   ACCESS read-only
   STATUS mandatory
   DESCRIPTION
       "The state of the Level 2 database."
   REFERENCE "ANSI {ISIS.aoi l2State (28)}"
   ::= { xIsisSysEntry 29 }

xIsisSysL2LSPDbaseOloads OBJECT-TYPE
   SYNTAX Counter
   ACCESS read-only
   STATUS mandatory
   DESCRIPTION
       "Number of times the Level 2 LSP database has become
       overloaded."
   REFERENCE "ANSI {ISIS.aoi lSPL2DatabaseOverloads (32)}"
   ::= { xIsisSysEntry 30 }


xIsisSysMaxAreaCheck OBJECT-TYPE
   SYNTAX INTEGER
   ACCESS read-write
   STATUS mandatory
   DESCRIPTION
       "When on, enables checking of maximum area
       addresses per IS version of ISO10589."
   ::= { xIsisSysEntry 31 }
           
-- The Level 1 Manual Area Address Table

xIsisManAreaAddrTable OBJECT-TYPE
   SYNTAX SEQUENCE OF XIsisManAreaAddrEntry
   ACCESS not-accessible
   STATUS mandatory
   DESCRIPTION
       "The set of manual area addresses configured on this
	       Intermediate System."
	   REFERENCE "ANSI {ISIS.aoi manualAreaAddresses (10)}"
	   ::= { xIsisSystem 2 }

xIsisManAreaAddrEntry OBJECT-TYPE
   SYNTAX XIsisManAreaAddrEntry
   ACCESS not-accessible
   STATUS mandatory
   DESCRIPTION
        "Each entry contains one area address manually configured
       on this system"
   INDEX {  xIsisManAreaAddrSysInstance, xIsisManAreaAddr }
   ::= { xIsisManAreaAddrTable 1 }

XIsisManAreaAddrEntry ::=
   SEQUENCE {
      xIsisManAreaAddrSysInstance
         INTEGER,
      xIsisManAreaAddr
         OCTET STRING,
      xIsisManAreaAddrExistState
         INTEGER
   }

xIsisManAreaAddrSysInstance OBJECT-TYPE
   SYNTAX INTEGER
   ACCESS read-only
   STATUS mandatory
   DESCRIPTION
       "The unique identifier of the Integrated IS-IS instance
       to which this row corresponds. This object follows the
       index behaviour."
   ::= { xIsisManAreaAddrEntry 1 }

xIsisManAreaAddr OBJECT-TYPE
   SYNTAX OCTET STRING
   ACCESS read-only
   STATUS mandatory
   DESCRIPTION
       "A manually configured area address for this system. This
       object follows the index behaviour."
   ::= { xIsisManAreaAddrEntry 2 }

xIsisManAreaAddrExistState OBJECT-TYPE
   SYNTAX INTEGER {
		off(1),
		on(2)
		}
   ACCESS read-write
   STATUS mandatory
   DESCRIPTION
       "The state of the xIsisManAreaAddrEntry. This object
       follows the ExistenceState behaviour. If an attempt is
       made to set this object to the value off when the
       corresponding xIsisManAreaAddrEntry is the only valid
       entry for this instance and when the corresponding ISIS
       instance has xIsisSysOperState set to On then the attempt
       is rejected."
   ::= { xIsisManAreaAddrEntry 3 }


-- The Level 1 Area Address Table

-- The Level 1 Area Address Table contains the
-- union of the sets of area addresses reported in all Level 1
-- LSPs received by this Intermediate System.

xIsisAreaAddrTable OBJECT-TYPE
   SYNTAX SEQUENCE OF XIsisAreaAddrEntry
   ACCESS not-accessible
   STATUS mandatory
   DESCRIPTION
       "The union of the sets of area addresses reported in all
       Level 1 LSPs received by this instance of the protocol."
   REFERENCE "ANSI {ISIS.aoi areaAddresses (18)}"
   ::= { xIsisSystem 3 }

xIsisAreaAddrEntry OBJECT-TYPE
   SYNTAX XIsisAreaAddrEntry
   ACCESS not-accessible
   STATUS mandatory
   DESCRIPTION
       "Each entry contains one area address reported in a
       Level 1 LSP received by this instance of the protocol."
   INDEX {  xIsisAreaAddrSysInstance, xIsisAreaAddr }
   ::= { xIsisAreaAddrTable 1 }
 
XIsisAreaAddrEntry ::=
   SEQUENCE {
      xIsisAreaAddrSysInstance
         INTEGER,
      xIsisAreaAddr
         OCTET STRING
   }

xIsisAreaAddrSysInstance OBJECT-TYPE
   SYNTAX INTEGER
   ACCESS read-only
   STATUS mandatory
   DESCRIPTION
       "The unique identifier of the Integrated IS-IS instance
       to which this row corresponds."
   ::= { xIsisAreaAddrEntry 1 }

xIsisAreaAddr OBJECT-TYPE
   SYNTAX OCTET STRING
   ACCESS read-only
   STATUS mandatory
   DESCRIPTION
       "An area address reported in a Level 1 LSP received by
       this instance of the protocol."
   ::= { xIsisAreaAddrEntry 2 }                    

-- The System Integrated Group

-- The System Integrated Group is present if the system
-- supports Integrated ISIS at Level 1.


-- The System Protocol Supported Table

-- The System Protocol Supported Table contains the manually
-- configured set of protocols supported by each
-- instance of the Integrated ISIS protocol.

xIsisSysProtSuppTable OBJECT-TYPE
   SYNTAX SEQUENCE OF XIsisSysProtSuppEntry
   ACCESS not-accessible
   STATUS mandatory
   DESCRIPTION
       "This table contains the manually configured set of
       protocols supported by each instance of the Integrated
       ISIS protocol."
   ::= { xIsisSystem 4 }

xIsisSysProtSuppEntry OBJECT-TYPE
   SYNTAX XIsisSysProtSuppEntry
   ACCESS not-accessible
   STATUS mandatory
   DESCRIPTION
       "Each entry contains one protocol supported by an
       instance of the Integrated ISIS protocol."
   INDEX {  xIsisSysProtSuppSysInstance,
            xIsisSysProtSuppProtocol }
   ::= { xIsisSysProtSuppTable 1 }

XIsisSysProtSuppEntry ::=
   SEQUENCE {
      xIsisSysProtSuppSysInstance
         INTEGER,
      xIsisSysProtSuppProtocol
         SupportedProtocol,
      xIsisSysProtSuppExistState
         ExistState
   }

xIsisSysProtSuppSysInstance OBJECT-TYPE
   SYNTAX INTEGER
   ACCESS read-only
   STATUS mandatory
   DESCRIPTION
       "The unique identifier of the Integrated IS-IS instance
       to which this row corresponds. This object follows the
       index behaviour."
   ::= { xIsisSysProtSuppEntry 1 }

xIsisSysProtSuppProtocol OBJECT-TYPE
   SYNTAX SupportedProtocol
   ACCESS read-only
   STATUS mandatory
   DESCRIPTION
       "One supported protocol. This object follows the index
       behaviour."
   ::= { xIsisSysProtSuppEntry 2 }

xIsisSysProtSuppExistState OBJECT-TYPE
   SYNTAX ExistState
   ACCESS read-write
   STATUS mandatory
   DESCRIPTION
       "The state of the xIsisSysProtSuppEntry. This object
       follows the ExistenceState and
       ReplaceOnlyWhileInstanceDisabled behaviours."
   DEFVAL { on }
   ::= { xIsisSysProtSuppEntry 3 }


-- The Circuit Group

-- The Circuit Group is mandatory


-- The Circuit Table

-- Each broadcast or point-to-point interface on the system
-- corresponds to one entry in the Circuit table. There may be
-- many X.25 DA circuit entries in the Circuit table for an
-- X.25 interface.

xIsisCircTable OBJECT-TYPE
   SYNTAX SEQUENCE OF XIsisCircEntry
   ACCESS not-accessible
   STATUS mandatory
   DESCRIPTION
       "The table of circuits used by each instance of
       Integrated IS-IS on this system."
   ::= { xIsisCirc 1 }

xIsisCircEntry OBJECT-TYPE
   SYNTAX XIsisCircEntry
   ACCESS not-accessible
   STATUS mandatory
   DESCRIPTION
       "An xIsisCircEntry exists for each circuit used by
       Integrated IS-IS on this system."
   INDEX {  xIsisCircSysInstance, xIsisCircIndex }
   ::= { xIsisCircTable 1 }

XIsisCircEntry ::=
   SEQUENCE {
      xIsisCircSysInstance
         INTEGER,
      xIsisCircIndex
         INTEGER,
      xIsisCircIfIndex
         INTEGER,
      xIsisCircOperState
         INTEGER,
      xIsisCircExistState
         INTEGER,
      xIsisCircType
         INTEGER,
      xIsisCircHelloTimer
         INTEGER,
      xIsisCircL1DefaultMetric
         INTEGER,
      xIsisCircL1DelayMetric
         INTEGER,
      xIsisCircL1ExpenseMetric
         INTEGER,
      xIsisCircL1ErrorMetric
         INTEGER,
      xIsisCircExtDomain
         INTEGER,
      xIsisCircAdjChanges
         Counter,
      xIsisCircInitFails
         Counter,
      xIsisCircRejAdjs
         Counter,
      xIsisCircOutCtrlPDUs
         Counter,
      xIsisCircInCtrlPDUs
         Counter,
      xIsisCircIDFieldLenMismatches
         Counter,
      xIsisCircL2DefaultMetric
         INTEGER,
      xIsisCircL2DelayMetric
         INTEGER,
      xIsisCircL2ExpenseMetric
         INTEGER,
      xIsisCircL2ErrorMetric
         INTEGER,
      xIsisCircManL2Only
         INTEGER,
      xIsisCircL1ISPriority
         INTEGER,
      xIsisCircL1CircID
         OCTET STRING,
      xIsisCircL1DesIS
         OCTET STRING,
      xIsisCircLANL1DesISChanges
         Counter,
      xIsisCircL2ISPriority
         INTEGER,
      xIsisCircL2CircID
         OCTET STRING,
      xIsisCircL2DesIS
         OCTET STRING,
      xIsisCircLANL2DesISChanges
         Counter
   }

xIsisCircSysInstance OBJECT-TYPE
   SYNTAX INTEGER
   ACCESS read-only
   STATUS mandatory
   DESCRIPTION
       "The unique identifier of the Integrated IS-IS instance
       to which this row corresponds. This object follows the
       index behaviour."
   ::= { xIsisCircEntry 1 }

xIsisCircIndex OBJECT-TYPE
   SYNTAX INTEGER (1..255)
   ACCESS read-only
   STATUS mandatory
   DESCRIPTION
       "The identifier of this circuit, unique within the
       instance of the protocol. This object follows the index
       behaviour."
   ::= { xIsisCircEntry 2 }

xIsisCircIfIndex OBJECT-TYPE
   SYNTAX INTEGER
   ACCESS read-only
   STATUS mandatory
   DESCRIPTION
       "The value of ifIndex for the interface to which this
       circuit corresponds. This object follows the
       replaceOnlyWhileDisabled behaviour."
   ::= { xIsisCircEntry 3 }

xIsisCircOperState OBJECT-TYPE
   SYNTAX INTEGER {
                  off(1),
                  on(2)
                  }
   ACCESS read-write
   STATUS mandatory
   DESCRIPTION
       "The operational state of the circuit. This object
       follows the operationalState behaviour."
   ::= { xIsisCircEntry 4 }

xIsisCircExistState OBJECT-TYPE
   SYNTAX INTEGER {
                  off(1),
                  on(2)
                  }
   ACCESS read-only
   STATUS mandatory
   DESCRIPTION
       "The existence state of this circuit. This object follows
       the ExistenceState behaviour."
   ::= { xIsisCircEntry 5 }

xIsisCircType OBJECT-TYPE
   SYNTAX   INTEGER {
               auto(1),
               broadcast(2),
               ptToPt(3)
            }
   ACCESS read-write
   STATUS mandatory
   DESCRIPTION
       "The type of the circuit.  This object follows the
       replaceOnlyWhileDisabled behaviour. The type specified
       must be compatible with the type of the interface defined
       by the value of xIsisCircIfIndex."
   REFERENCE "ANSI {ISIS.aoi type (33)}"
   ::= { xIsisCircEntry 6 }

xIsisCircHelloTimer OBJECT-TYPE
   SYNTAX INTEGER (1..65535)
   ACCESS read-write
   STATUS mandatory
   DESCRIPTION
       "The period, in seconds, between IIH PDUs. It is also
       used as the period between ISH PDUs when polling the ES
       configuration. This object follows the resettingTimer
       behaviour."
   REFERENCE "ANSI {ISIS.aoi iSISHelloTimer (45)}"
   ::= { xIsisCircEntry 7 }

xIsisCircL1DefaultMetric OBJECT-TYPE
   SYNTAX INTEGER (0..63) 
   ACCESS read-write
   STATUS mandatory
   DESCRIPTION
       "The default metric value of this circuit for Level 1
       traffic. 0 means the IS will automatically generate Level 1 default
       metric for the circuit."
   REFERENCE "ANSI {ISIS.aoi l1DefaultMetric (35)}"
   ::= { xIsisCircEntry 8 }

xIsisCircL1DelayMetric OBJECT-TYPE
   SYNTAX INTEGER (0..63) 
   ACCESS read-write
   STATUS mandatory
   DESCRIPTION
       "The delay metric value of this circuit for Level 1
       traffic. The value of zero is reserved to indicate that
       this metric is not supported."
   REFERENCE "ANSI {ISIS.aoi l1DelayMetric (36)}"
   ::= { xIsisCircEntry 9 }

xIsisCircL1ExpenseMetric OBJECT-TYPE
   SYNTAX INTEGER (0..63) 
   ACCESS read-write
   STATUS mandatory
   DESCRIPTION
       "The expense metric value of this circuit for Level 1
       traffic. The value of zero is reserved to indicate that
       this metric is not supported."
   REFERENCE "ANSI {ISIS.aoi l1ExpenseMetric (37)}"
   ::= { xIsisCircEntry 10 }

xIsisCircL1ErrorMetric OBJECT-TYPE
   SYNTAX INTEGER (0..63) 
   ACCESS read-write
   STATUS mandatory
   DESCRIPTION
       "The error metric value of this circuit for Level 1
       traffic. The value of zero is reserved to indicate that
       this metric is not supported."
   REFERENCE "ANSI {ISIS.aoi l1ErrorMetric (38)}"
   ::= { xIsisCircEntry 11 }

xIsisCircExtDomain OBJECT-TYPE
   SYNTAX INTEGER {
                  false(1),
                  true(2)
                  }
   ACCESS read-write
   STATUS mandatory
   DESCRIPTION
       "If true, suppress normal transmission of and
       interpretation of Intra-domain ISIS PDUs on this
       circuit."
   REFERENCE "ANSI {ISIS.aoi externalDomain (46)}"
   ::= { xIsisCircEntry 12 }

xIsisCircAdjChanges OBJECT-TYPE
   SYNTAX Counter
   ACCESS read-only
   STATUS mandatory
   DESCRIPTION
       "The number of times an adjacency state change has
       occurred on this circuit."
   REFERENCE "ANSI {ISIS.aoi changesInAdjacencyState (40)}"
   ::= { xIsisCircEntry 13 }

xIsisCircInitFails OBJECT-TYPE
   SYNTAX Counter
   ACCESS read-only
   STATUS mandatory
   DESCRIPTION
       "The number of times initialization of this circuit has
       failed."
   REFERENCE "ANSI {ISIS.aoi initializationFailures (41)}"
   ::= { xIsisCircEntry 14 }

xIsisCircRejAdjs OBJECT-TYPE
   SYNTAX Counter
   ACCESS read-only
   STATUS mandatory
   DESCRIPTION
       "The number of times an adjacency has been rejected on
       this circuit."
   REFERENCE "ANSI {ISIS.aoi rejectedAdjacencies (42)}"
   ::= { xIsisCircEntry 15 }

xIsisCircOutCtrlPDUs OBJECT-TYPE
   SYNTAX Counter
   ACCESS read-only
   STATUS mandatory
   DESCRIPTION
       "The number of IS-IS control PDUs sent on this circuit."
   REFERENCE "ANSI {ISIS.aoi iSISControlPDUsSent (43)}"
   ::= { xIsisCircEntry 16 }

xIsisCircInCtrlPDUs OBJECT-TYPE
   SYNTAX Counter
   ACCESS read-only
   STATUS mandatory
   DESCRIPTION
       "The number of IS-IS control PDUs received on this
       circuit."
   REFERENCE "ANSI {ISIS.aoi controlPDUsReceived (44)}"
   ::= { xIsisCircEntry 17 }

xIsisCircIDFieldLenMismatches OBJECT-TYPE
   SYNTAX Counter
   ACCESS read-only
   STATUS mandatory
   DESCRIPTION
       "The number of times an IS-IS control PDU with an ID
       field length different to that for this system has been
       received."
   REFERENCE "ANSI {ISIS.aoi iDFieldLengthMismatches (25)}"
   ::= { xIsisCircEntry 18 }

-- The following objects map those from the linkageISISLevel2-P
-- package

xIsisCircL2DefaultMetric OBJECT-TYPE
   SYNTAX INTEGER (0..63) 
   ACCESS read-write
   STATUS mandatory
   DESCRIPTION
       "The default metric value of this circuit for level 2
       traffic. 0 means the IS will automatically generate the Level 2
       default metric for this circuit."
   REFERENCE "ANSI {ISIS.aoi l2DefaultMetric (68)}"
   ::= { xIsisCircEntry 20 }

xIsisCircL2DelayMetric OBJECT-TYPE
   SYNTAX INTEGER (0..63) 
   ACCESS read-write
   STATUS mandatory
   DESCRIPTION
       "The delay metric value of this circuit for level 2
       traffic. The value of zero is reserved to indicate that
       this metric is not supported."
   REFERENCE "ANSI {ISIS.aoi l2DelayMetric (69)}"
   ::= { xIsisCircEntry 21 }

xIsisCircL2ExpenseMetric OBJECT-TYPE
   SYNTAX INTEGER (0..63) 
   ACCESS read-write
   STATUS mandatory
   DESCRIPTION
       "The expense metric value of this circuit for level 2
       traffic. The value of zero is reserved to indicate that
       this metric is not supported."
   REFERENCE "ANSI {ISIS.aoi l2ExpenseMetric (70)}"
   ::= { xIsisCircEntry 22 }

xIsisCircL2ErrorMetric OBJECT-TYPE
   SYNTAX INTEGER (0..63) 
   ACCESS read-write
   STATUS mandatory
   DESCRIPTION
       "The error metric value of this circuit for level 2
       traffic. The value of zero is reserved to indicate that
       this metric is not supported."
   REFERENCE "ANSI {ISIS.aoi l2ErrorMetric (71)}"
   ::= { xIsisCircEntry 23 }

xIsisCircManL2Only OBJECT-TYPE
   SYNTAX INTEGER {
                  false(1),
                  true(2)
                  }
   ACCESS read-write
   STATUS mandatory
   DESCRIPTION
       "When true, indicates that this circuit is to be used
       only for level 2. This object follows the
       replaceOnlyWhileDisabled behaviour."
   REFERENCE "ANSI {ISIS.aoi manualL2OnlyMode (72)}"
   ::= { xIsisCircEntry 24 }

-- The following objects map those from the
-- linkageISISBroadcast-P package

xIsisCircL1ISPriority OBJECT-TYPE
   SYNTAX INTEGER (1..127)
   ACCESS read-write
   STATUS mandatory
   DESCRIPTION
       "The priority for becoming LAN Level 1 Deignated
       Intermediate System on a broadcast circuit."
   REFERENCE "ANSI {ISIS.aoi l1IntermediateSystemPriority (47)}"
   ::= { xIsisCircEntry 25 }

xIsisCircL1CircID OBJECT-TYPE
   SYNTAX OCTET STRING 
   ACCESS read-only
   STATUS mandatory
   DESCRIPTION
       "The LAN ID allocated by the LAN Level 1 Designated
       Intermediate System. Where this system is not aware of
       the value (because it is not participating in the Level 1
       Designated Intermediate System election), this object has
       the value which would be proposed for this circuit (i.e.
       the concatenation of the local system ID and the one
       octet local Circuit ID for this circuit."
   REFERENCE "ANSI {ISIS.aoi l1CircuitID (48)}"
   ::= { xIsisCircEntry 26 }

xIsisCircL1DesIS OBJECT-TYPE
   SYNTAX OCTET STRING
   ACCESS read-only
   STATUS mandatory
   DESCRIPTION
       "The ID of the LAN Level 1 Designated Intermediate System
       on this circuit. If, for any reason this system is not
       partaking in the relevant Designated Intermediate System
       election process, then the value returned is the zero
       length OCTET STRING."
   REFERENCE "ANSI {ISIS.aoi l1DesignatedIntermediateSystem (49)}"
   ::= { xIsisCircEntry 27 }

xIsisCircLANL1DesISChanges OBJECT-TYPE
   SYNTAX Counter
   ACCESS read-only
   STATUS mandatory
   DESCRIPTION
       "The number of times the LAN Level 1 Designated
       Intermediate System has changed."
     REFERENCE "ANSI {ISIS.aoi
       lanL1DesignatedIntermediateSystemChanges (50)}"
   ::= { xIsisCircEntry 28 }

-- The following objects map those from the
-- linkageISISLevel2Broadcast-P package

xIsisCircL2ISPriority OBJECT-TYPE
   SYNTAX INTEGER (1..127)
   ACCESS read-write
   STATUS mandatory
   DESCRIPTION
       "The priority for becoming LAN level 2 Designated
       Intermediate System."
   REFERENCE "ANSI {ISIS.aoi l2IntermediateSystemPriority (73)}"
   ::= { xIsisCircEntry 29 }

xIsisCircL2CircID OBJECT-TYPE
   SYNTAX OCTET STRING 
   ACCESS read-only
   STATUS mandatory
   DESCRIPTION
       "The LAN ID allocated by the LAN Level 2 Designated
       Intermediate System. Where this system is not aware of
       this value (because it is not participating in the Level
       2 Designated Intermediate System election), this object
       has the value which would be proposed for this circuit
       (i.e. the concatenation of the local system ID and the
       one octet local Circuit ID for this circuit."
   REFERENCE "ANSI {ISIS.aoi l2CircuitID (74)}"
   ::= { xIsisCircEntry 30 }

xIsisCircL2DesIS OBJECT-TYPE
   SYNTAX OCTET STRING
   ACCESS read-only
   STATUS mandatory
   DESCRIPTION
       "The ID of the LAN Level 2 Designated Intermediate System
       on this circuit. If, for any reason, this system is not
       partaking in the relevant Designated Intermediate System
       election process, then the value returned is the zero
       length OCTET STRING."
   REFERENCE "ANSI {ISIS.aoi l2DesignatedIntermediateSystem (75)}"
   ::= { xIsisCircEntry 31 }

xIsisCircLANL2DesISChanges OBJECT-TYPE
   SYNTAX Counter
   ACCESS read-only
   STATUS mandatory
   DESCRIPTION
       "The number of times the LAN Level 2 Designated
       Intermediate System has changed."
   REFERENCE "ANSI {ISIS.aoi
      lanL2DesignatedIntermediateSystemChanges (76)}"
   ::= { xIsisCircEntry 32 }

-- The Circuit IS Group

-- The Circuit IS Table


xIsisCircISTable OBJECT-TYPE
   SYNTAX SEQUENCE OF XIsisCircISEntry
   ACCESS not-accessible
   STATUS mandatory
   DESCRIPTION
       "The set of objects controlling the operation of the IS
       functions of the ES-IS protocol (ISO 9542) on each
       circuit over which ISIS is run."
   REFERENCE "ANSI {NLM.poi linkage-ISO9542IS-P (22)}"
   ::= { xIsisCirc 2 }

xIsisCircISEntry OBJECT-TYPE
   SYNTAX XIsisCircISEntry
   ACCESS not-accessible
   STATUS mandatory
   DESCRIPTION
       "Each entry contains objects controlling the operation of
       the IS functions of the ES-IS protocol (ISO 9542) on one
       circuit."
   INDEX {  xIsisCircISIndex }
   ::= { xIsisCircISTable 1 }

XIsisCircISEntry ::=
   SEQUENCE {
      xIsisCircISSysInstance
         INTEGER,
      xIsisCircISIndex
         INTEGER,
      xIsisCircISExistState
         INTEGER,
      xIsisCircISOperState
         INTEGER,
      xIsisCircISHoldTimerMult
         INTEGER,
      xIsisCircISConfTimer
         INTEGER,
      xIsisCircISSuggESConfTimer
         INTEGER,                     
      xIsisCircISRedHoldTime
         INTEGER,
      xIsisCircISESReachChgs
         Counter,
      xIsisCircISInv9542PDUs
         Counter
   }
xIsisCircISSysInstance OBJECT-TYPE
   SYNTAX INTEGER
   ACCESS read-only
   STATUS mandatory
   DESCRIPTION            
       "The identifier of the Integrated IS-IS instance to which
       this row corresponds. This object follows the index and
       manualOrAutomatic behaviours."
   ::= { xIsisCircISEntry 1 }

xIsisCircISIndex OBJECT-TYPE
   SYNTAX INTEGER
   ACCESS read-only
   STATUS mandatory
   DESCRIPTION
       "The unique identifier of this row. This value is the
       same as the value of the ifIndex object which identifies
       the interface which corresponds to this circuit. This
       object follows the index behaviour."
   ::= { xIsisCircISEntry 2 }

xIsisCircISExistState OBJECT-TYPE
   SYNTAX INTEGER {
                  off(1),
                  on(2)
                  }
   ACCESS read-only
   STATUS mandatory
   DESCRIPTION
       "The existence state of this row. This object follows the
       ExistenceState behaviour."
   ::= { xIsisCircISEntry 3 }

xIsisCircISOperState OBJECT-TYPE
   SYNTAX INTEGER {
                  off(1),
                  on(2)
                  }
   ACCESS read-write
   STATUS mandatory
   DESCRIPTION
       "The operational state of the row. This object follows
       the operationalState behaviour."
   ::= { xIsisCircISEntry 4 }

xIsisCircISHoldTimerMult OBJECT-TYPE
   SYNTAX INTEGER (2..63)
   ACCESS read-only
   STATUS mandatory
   DESCRIPTION
       "The factor to derive holding timer from configuration
       timer. This value when multipled by a configuration timer
       yields the value of the holding timer parameter issued
       with configuration information. The semantics of this
       parameter are such that it is permissible to add a delta
       value to the result to compensate for possible delays and
       imprecision of timers. The result of the calculation is
       truncated, upon overflow, to the maximum value for the
       parameter permitted by the protocol (65535)."
   REFERENCE "ANSI {NLM.aoi holdingTimerMutliplier (20)}"
   ::= { xIsisCircISEntry 5 }

xIsisCircISConfTimer OBJECT-TYPE
   SYNTAX INTEGER
   ACCESS read-write
   STATUS mandatory
   DESCRIPTION
       "Value in seconds for the ISO 9542 IS configuration
       timer. It is used to determine how often an IS reports
       configuration information to ESs. This object follows the
       resettingTimer behaviour."
   REFERENCE "ANSI {NLM.aoi iSConfigurationTimer (24)}"
   ::= { xIsisCircISEntry 6 }

xIsisCircISSuggESConfTimer OBJECT-TYPE
   SYNTAX INTEGER
   ACCESS read-write
   STATUS mandatory
   DESCRIPTION
       "Value to be used for the ISO 9542 suggested ES
       configuration timer value (in seconds), advertised in IS
       Hellos generated by the system on this circuit. This
       object follows the resettingTimer behaviour."
   REFERENCE "ANSI {NLM.aoi suggestedESConfigurationTimer (25)}"
   ::= { xIsisCircISEntry 7 }

xIsisCircISRedHoldTime OBJECT-TYPE
   SYNTAX INTEGER (1..65535)
   ACCESS read-write
   STATUS mandatory
   DESCRIPTION
       "The holding time (in seconds) to be specified in
       Redirect PDUs generated by the system on this circuit."
   REFERENCE "ANSI {NLM.aoi redirectHoldingTime (26)}"
   ::= { xIsisCircISEntry 8 }

xIsisCircISESReachChgs OBJECT-TYPE
   SYNTAX Counter
   ACCESS read-only
   STATUS mandatory
   DESCRIPTION
       "Count of the number of changes in reachability of End
       Systems from this circuit."
   REFERENCE "ANSI {NLM.aoi eSReachabilityChanges (27)}"
   ::= { xIsisCircISEntry 9 }

xIsisCircISInv9542PDUs OBJECT-TYPE
   SYNTAX Counter
   ACCESS read-only
   STATUS mandatory
   DESCRIPTION
       "Counter of invalid 9542 PDUs received. This is the
       number of ISO 9452 PDUs received which are discarded as a
       result of the PDU Header Error Detection or Protocol
       Error Processing Functions specified in ISO 9542."
   REFERENCE "ANSI {NLM.aoi invalid9542PDUs (101)}"
   ::= { xIsisCircISEntry 10 }

-- The IS Adjacency Group

-- The IS Adjacency Group is mandatory and contains information
-- about adjacencies to routers maintained by the Integrated
-- IS-IS protocol


-- The IS Adjacency Table

-- Each adjacency to an IS corresponds to one entry in this
-- table.
xIsisISAdjTable OBJECT-TYPE
   SYNTAX SEQUENCE OF XIsisISAdjEntry
   ACCESS not-accessible
   STATUS mandatory
   DESCRIPTION
       "The table of adjacencies to Intermediate Systems."
   ::= { xIsisISAdj 1 }

xIsisISAdjEntry OBJECT-TYPE
   SYNTAX XIsisISAdjEntry
   ACCESS not-accessible
   STATUS mandatory
   DESCRIPTION
       "Each entry corresponds to one adjacency to an
       Intermediate System on this system."
   INDEX {  xIsisISAdjSysInstance, xIsisISAdjCircIndex, xIsisISAdjIndex }
   ::= { xIsisISAdjTable 1 }

XIsisISAdjEntry ::=
   SEQUENCE {
      xIsisISAdjSysInstance
         INTEGER,
      xIsisISAdjCircIndex
         INTEGER,
      xIsisISAdjIndex
         INTEGER,
      xIsisISAdjState
         INTEGER,
      xIsisISAdjNeighSNPAAddress
         OCTET STRING,
      xIsisISAdjNeighSysType
         INTEGER,
      xIsisISAdjNeighSysID
         OCTET STRING,
      xIsisISAdjUsage
         INTEGER,
      xIsisISAdjHoldTimer
         INTEGER,
      xIsisISAdjNeighPriority
         INTEGER
   }

xIsisISAdjSysInstance OBJECT-TYPE
   SYNTAX INTEGER
   ACCESS read-only
   STATUS mandatory
   DESCRIPTION
       "The unique identifier of the Integrated IS-IS instance
       to which this row corresponds."
   ::= { xIsisISAdjEntry 1 }

xIsisISAdjCircIndex OBJECT-TYPE
   SYNTAX INTEGER
   ACCESS read-only
   STATUS mandatory
   DESCRIPTION
       "The identifier of the Circuit which is the parent of the
       IS adjacency."
   ::= { xIsisISAdjEntry 2 }

xIsisISAdjIndex OBJECT-TYPE
   SYNTAX INTEGER
   ACCESS read-only
   STATUS mandatory
   DESCRIPTION
       "A unique value identifying the IS adjacency from all
       other such adjacencies on this circuit. This value is
       assigned by the system when the adjacency is created
       automatically."
   ::= { xIsisISAdjEntry 3 }

xIsisISAdjState OBJECT-TYPE
   SYNTAX   INTEGER {
               initializing(1),
               up(2),
               failed(3),
               down(4)
            }
   ACCESS read-only
   STATUS mandatory
   DESCRIPTION
       "The state of the adjacency"
   REFERENCE "ANSI {ISIS.aoi adjacencyState (78)}"
   ::= { xIsisISAdjEntry 4 }

xIsisISAdjNeighSNPAAddress OBJECT-TYPE
   SYNTAX OCTET STRING
   ACCESS read-only
   STATUS mandatory
   DESCRIPTION
       "The SNPA address of the neighboring system."
   REFERENCE "ANSI {ISIS.aoi neighbourSNPAAddress (79)}"
   ::= { xIsisISAdjEntry 5 }

xIsisISAdjNeighSysType OBJECT-TYPE
   SYNTAX   INTEGER {
               unknown(1),
               intermediateSystem(3),
               l1IntermediateSystem(4),
               l2IntermediateSystem(5)
            }
   ACCESS read-only
   STATUS mandatory
   DESCRIPTION
       "The type of the neighboring system."
   REFERENCE "ANSI {ISIS.aoi neighbourSystemType (80)}"
   ::= { xIsisISAdjEntry 6 }

xIsisISAdjNeighSysID OBJECT-TYPE
   SYNTAX OCTET STRING 
   ACCESS read-only
   STATUS mandatory
   DESCRIPTION
       "The system ID of the neighboring Intermediate System set
       from the source ID field of the neighbor's IIH PDUs."
   REFERENCE "ANSI {ISIS.aoi neighbourSystemIds (83)}"
   ::= { xIsisISAdjEntry 7 }

xIsisISAdjUsage OBJECT-TYPE
   SYNTAX   INTEGER {
               undefined(1),
               level1(2),
               level2(3),
               level1and2(4)
            }
   ACCESS read-only
   STATUS mandatory
   DESCRIPTION
       "The usage of the adjacency. An adjacency of type level1
       will be used for level 1 traffic only. An adjacency of
       type level2 will be used for level 2 traffic only. An
       adjacency of type level1and2 will be used for both level
       1 and level 2 traffic. There may be two adjacencies (of
       types level1 and level2) between the same pair of
       Intermediate Systems."
   REFERENCE "ANSI {ISIS.aoi adjacencyUsage (82)}"
   ::= { xIsisISAdjEntry 8 }

xIsisISAdjHoldTimer OBJECT-TYPE
   SYNTAX INTEGER (1..65535)
   ACCESS read-only
   STATUS mandatory
   DESCRIPTION
       "The holding time for this adjacency updated from
       received IIH PDUs."
   REFERENCE "ANSI {ISIS.aoi holdingTimer (85)}"
   ::= { xIsisISAdjEntry 9 }

xIsisISAdjNeighPriority OBJECT-TYPE
   SYNTAX INTEGER (1..127)
   ACCESS read-only
   STATUS mandatory
   DESCRIPTION
       "Priority of the neighboring Intermediate System for
       becoming the LAN Level 1 Designated Intermediate System
       if the value of xIsisISAdjNeighSysType is
       L1IntermediateSystem or LAN Level 2 Designated
       Intermediate System if the value of
       xIsisISAdjNeighSysType is L2IntermediateSystem."
   REFERENCE "ANSI {ISIS.aoi lANPriority (86)}"
   ::= { xIsisISAdjEntry 10 }

-- The IS Adjacency Area Address Table

-- The IS Adjacency Area Address Table contains the set of
-- Area Addresses of neighboring
-- Intermediate Systems as reported in IIH PDUs.

xIsisISAdjAreaAddrTable OBJECT-TYPE
   SYNTAX SEQUENCE OF XIsisISAdjAreaAddrEntry
   ACCESS not-accessible
   STATUS mandatory
   DESCRIPTION
       "This table contains the set of Area Addresses of
       neighboring Intermediate Systems as reported in received
       IIH PDUs."
   REFERENCE "ANSI {ISIS.aoi areaAddressesOfNeighbour (84)}"
   ::= { xIsisISAdj 2 }

xIsisISAdjAreaAddrEntry OBJECT-TYPE
   SYNTAX XIsisISAdjAreaAddrEntry
   ACCESS not-accessible
   STATUS mandatory
   DESCRIPTION
       "Each entry contains one Area Address reported by a
       neighboring Intermediate System in its IIH PDUs."
   INDEX {  xIsisISAdjAreaAddrSysInstance, xIsisISAdjAreaAddrCircIndex, xIsisISAdjAreaAddrAdjIndex, xIsisISAdjAreaAddress }
   ::= { xIsisISAdjAreaAddrTable 1 }

XIsisISAdjAreaAddrEntry ::=
   SEQUENCE {
      xIsisISAdjAreaAddrSysInstance
         INTEGER,
      xIsisISAdjAreaAddrCircIndex
         INTEGER,
      xIsisISAdjAreaAddrAdjIndex
         INTEGER,
      xIsisISAdjAreaAddress
         OCTET STRING
   }

xIsisISAdjAreaAddrSysInstance OBJECT-TYPE
   SYNTAX INTEGER
   ACCESS read-only
   STATUS mandatory
   DESCRIPTION
       "The unique identifier of the Integrated IS-IS instance
       to which this row corresponds."
   ::= { xIsisISAdjAreaAddrEntry 1 }

xIsisISAdjAreaAddrCircIndex OBJECT-TYPE
   SYNTAX INTEGER
   ACCESS read-only
   STATUS mandatory
   DESCRIPTION
       "The identifier of the Circuit which is the parent of the
       IS adjacency to which this Area Address entry
       corresponds."
   ::= { xIsisISAdjAreaAddrEntry 2 }

xIsisISAdjAreaAddrAdjIndex OBJECT-TYPE
   SYNTAX INTEGER
   ACCESS read-only
   STATUS mandatory
   DESCRIPTION
       "The identifier of the IS adjacency to which this entry
       belongs."
   ::= { xIsisISAdjAreaAddrEntry 3 }

xIsisISAdjAreaAddress OBJECT-TYPE
   SYNTAX OCTET STRING
   ACCESS read-only
   STATUS mandatory
   DESCRIPTION
       "One Area Address as reported in IIH PDUs received from
       the neighbor."
   ::= { xIsisISAdjAreaAddrEntry 4 }


-- The IS Adjacency IP Group

-- The IS Adjacency IP Group is present if the system supports
-- IP Integrated IS-IS


-- The IS Adjacency IP Address Table

-- The IS Adjacency IP Address Table contains the
-- set of IP Addresses of neighboring Intermediate Systems
-- as reported in received IIH PDUs.

xIsisISAdjIPAddrTable OBJECT-TYPE
   SYNTAX SEQUENCE OF XIsisISAdjIPAddrEntry
   ACCESS not-accessible
   STATUS mandatory
   DESCRIPTION
       "This table contains the set of IP Addresses of
       neighboring Intermediate Systems as reported in received
       IIH PDUs."
   ::= { xIsisISAdj 3 }

xIsisISAdjIPAddrEntry OBJECT-TYPE
   SYNTAX XIsisISAdjIPAddrEntry
   ACCESS not-accessible
   STATUS mandatory
   DESCRIPTION
       "Each entry contains one IP Address reported by a
       neighboring Intermediate System in its IIH PDUs."
   INDEX {  xIsisISAdjIPAddrSysInstance,
            xIsisISAdjIPAddrCircIndex,
            xIsisISAdjIPAddrAdjIndex
        			}
   ::= { xIsisISAdjIPAddrTable 1 }

XIsisISAdjIPAddrEntry ::=
   SEQUENCE {
      xIsisISAdjIPAddrSysInstance
         INTEGER,
      xIsisISAdjIPAddrCircIndex
         INTEGER,
      xIsisISAdjIPAddrAdjIndex
         INTEGER,
      xIsisISAdjIPAddress
         IpAddress
   }

xIsisISAdjIPAddrSysInstance OBJECT-TYPE
   SYNTAX INTEGER
   ACCESS read-only
   STATUS mandatory
   DESCRIPTION
       "The unique identifier of the Integrated IS-IS instance
       to which this row corresponds."
   ::= { xIsisISAdjIPAddrEntry 1 }

xIsisISAdjIPAddrCircIndex OBJECT-TYPE
   SYNTAX INTEGER
   ACCESS read-only
   STATUS mandatory
   DESCRIPTION
       "The identifier of the Circuit which is the parent of the
       IS adjacency to which this IP Address entry corresponds."
   ::= { xIsisISAdjIPAddrEntry 2 }

xIsisISAdjIPAddrAdjIndex OBJECT-TYPE
   SYNTAX INTEGER
   ACCESS read-only
   STATUS mandatory
   DESCRIPTION
       "The identifier of the IS adjacency to which this entry
       belongs."
   ::= { xIsisISAdjIPAddrEntry 3 }

xIsisISAdjIPAddress OBJECT-TYPE
   SYNTAX IpAddress
   ACCESS read-only
   STATUS mandatory
   DESCRIPTION
       "One IP Address as reported in IIH PDUs received from the
       neighbor."
   ::= { xIsisISAdjIPAddrEntry 4 }


-- The IS Adjacency Integrated Group

-- The IS Adjacency Integrated Group is present if the system
-- supports Integrated ISIS.


-- The IS Adjacency Protocol Supported Table

-- The IS Adjacency Protocol Supported Table contains the set of
-- protocols supported by neighboring
-- Intermediate Systems as reported in received IIH PDUs.

xIsisISAdjProtSuppTable OBJECT-TYPE
   SYNTAX SEQUENCE OF XIsisISAdjProtSuppEntry
   ACCESS not-accessible
   STATUS mandatory
   DESCRIPTION
       "This table contains the set of protocols supported by
       neighboring Intermediate Systems as reported in received
       IIH PDUs."
   ::= { xIsisISAdj 4 }

xIsisISAdjProtSuppEntry OBJECT-TYPE
   SYNTAX XIsisISAdjProtSuppEntry
   ACCESS not-accessible
   STATUS mandatory
   DESCRIPTION
       "Each entry contains one protocol supported by a
       neighboring Intermediate System as reported in its IIH
       PDUs."
   INDEX {  xIsisISAdjProtSuppSysInstance,
            xIsisISAdjProtSuppCircIndex,
            xIsisISAdjProtSuppAdjIndex,
            xIsisISAdjProtSuppProtocol }
   ::= { xIsisISAdjProtSuppTable 1 }

XIsisISAdjProtSuppEntry ::=
   SEQUENCE {
      xIsisISAdjProtSuppSysInstance
         INTEGER,
      xIsisISAdjProtSuppCircIndex
         INTEGER,
      xIsisISAdjProtSuppAdjIndex
         INTEGER,
      xIsisISAdjProtSuppProtocol
         SupportedProtocol
   }

xIsisISAdjProtSuppSysInstance OBJECT-TYPE
   SYNTAX INTEGER
   ACCESS read-only
   STATUS mandatory
   DESCRIPTION
       "The unique identifier of the Integrated IS-IS instance
       to which this row corresponds."
   ::= { xIsisISAdjProtSuppEntry 1 }

xIsisISAdjProtSuppCircIndex OBJECT-TYPE
   SYNTAX INTEGER
   ACCESS read-only
   STATUS mandatory
   DESCRIPTION
       "The identifier of the Circuit which is the parent of the
       IS adjacency to which this supported protocol entry
       corresponds."
   ::= { xIsisISAdjProtSuppEntry 2 }

xIsisISAdjProtSuppAdjIndex OBJECT-TYPE
   SYNTAX INTEGER
   ACCESS read-only
   STATUS mandatory
   DESCRIPTION
       "The identifier the IS adjacency to which this entry
       corresponds."
   ::= { xIsisISAdjProtSuppEntry 3 }

xIsisISAdjProtSuppProtocol OBJECT-TYPE
   SYNTAX SupportedProtocol
   ACCESS read-only
   STATUS mandatory
   DESCRIPTION
       "One supported protocol as reported in IIH PDUs received
       from the neighbor."
   ::= { xIsisISAdjProtSuppEntry 4 }



-- The ES Adjacency Group

-- The ES Adjacency Group is present if the system supports
-- reception of ES Hellos


-- The ES Adjacency Table

-- The ES Adjacency Table contains one entry for each
-- End System ID of each neighboring End System
-- as reported in ESH PDUs or as configured manually.

xIsisESAdjTable OBJECT-TYPE
   SYNTAX SEQUENCE OF XIsisESAdjEntry
   ACCESS not-accessible
   STATUS mandatory
   DESCRIPTION
       "The table of End System IDs of neighboring End Systems
       as reported in their ESH PDUs or as configured manually"
   ::= { xIsisESAdj 1 }

xIsisESAdjEntry OBJECT-TYPE
   SYNTAX XIsisESAdjEntry
   ACCESS not-accessible
   STATUS mandatory
   DESCRIPTION
       "Each entry contains one End System ID of a neighboring
       End System as reported in an ESH PDU or as configured
       manually."
   INDEX {  xIsisESAdjSysInstance, xIsisESAdjCircIndex, xIsisESAdjIndex,
            xIsisESAdjESID }
   ::= { xIsisESAdjTable 1 }

XIsisESAdjEntry ::=
   SEQUENCE {
      xIsisESAdjSysInstance
         INTEGER,
      xIsisESAdjCircIndex
         INTEGER,
      xIsisESAdjIndex
         INTEGER,
      xIsisESAdjType
         INTEGER,
      xIsisESAdjState
         INTEGER,
      xIsisESAdjNeighSNPAAddress
         OCTET STRING,
      xIsisESAdjExistState
         INTEGER,
      xIsisESAdjESID
         OCTET STRING
   }

xIsisESAdjSysInstance OBJECT-TYPE
   SYNTAX INTEGER
   ACCESS read-only
   STATUS mandatory
   DESCRIPTION
       "The identifier of the Integrated IS-IS instance to which
       this row corresponds. This object follows the index and
       manualOrAutomatic behaviours."
   ::= { xIsisESAdjEntry 1 }

xIsisESAdjCircIndex OBJECT-TYPE
   SYNTAX INTEGER
   ACCESS read-only
   STATUS mandatory
   DESCRIPTION
       "The identifier of the Circuit which is the parent of the
       ES adjacency to which this End System ID entry
       corresponds. This object follows the index and
       manualOrAutomatic behaviours."
   ::= { xIsisESAdjEntry 2 }

xIsisESAdjIndex OBJECT-TYPE
   SYNTAX INTEGER
   ACCESS read-only
   STATUS mandatory
   DESCRIPTION
       "The identifier of the ES adjacency to which this entry
       belongs. This object follows the index and
       manualOrAutomatic behaviours."
   ::= { xIsisESAdjEntry 3 }

xIsisESAdjType OBJECT-TYPE
   SYNTAX   INTEGER  {
               auto(1),
               manual(2)
            }
   ACCESS read-only
   STATUS mandatory
   DESCRIPTION
       "The indication of whether this adjacency was created
       manually by management action or automatically by the
       implementation."
   ::= { xIsisESAdjEntry 4 }

xIsisESAdjState OBJECT-TYPE
   SYNTAX   INTEGER {
               initializing(1),
               up(2),
               failed(3),
               down(4)
            }
   ACCESS read-write
   STATUS mandatory
   DESCRIPTION
       "The state of the adjacency. Adjacencies created manually
       always have this value set to up."
   REFERENCE "ANSI {ISIS.aoi adjacencyState (78)}"
   ::= { xIsisESAdjEntry 5 }

xIsisESAdjNeighSNPAAddress OBJECT-TYPE
   SYNTAX OCTET STRING
   ACCESS read-write
   STATUS mandatory
   DESCRIPTION
       "The SNPA address of the neighboring system. This object
       follows the manualOrAutomatic behaviour."
   REFERENCE "ANSI {ISIS.aoi neighbourSNPAAddress (79)}"
   ::= { xIsisESAdjEntry 6 }

xIsisESAdjExistState OBJECT-TYPE
   SYNTAX INTEGER {
                  off(1),
                  on(2)
                  }
   ACCESS read-write
   STATUS mandatory
   DESCRIPTION
       "The existence state of this ES Adjacency. This object
       follows the ExistenceState behaviour. This object follows
       the manualOrAutomatic behaviour."
   ::= { xIsisESAdjEntry 7 }

xIsisESAdjESID OBJECT-TYPE
   SYNTAX OCTET STRING
   ACCESS read-only
   STATUS mandatory
   DESCRIPTION
       "An End System ID of a neighboring End System. This
       object follows the index and manualOrAutomatic
       behaviour."
   ::= { xIsisESAdjEntry 8 }                     


-- The Reachable Address Group

-- The Reachable Address Group is optional.


-- The Reachable Address Table

-- Each entry records information about a reachable address
-- (NSAP or address prefix) manually configured on the system
-- or learned through another protocol.

xIsisRATable OBJECT-TYPE
   SYNTAX SEQUENCE OF XIsisRAEntry
   ACCESS not-accessible
   STATUS mandatory
   DESCRIPTION
       "The table of Reachable Addresses to NSAPs or Address
       Prefixes."
   ::= { xIsisReachAddr 1 }

xIsisRAEntry OBJECT-TYPE
   SYNTAX XIsisRAEntry
   ACCESS not-accessible
   STATUS mandatory
   DESCRIPTION
       "Each entry defines a Reachable Address to a NSAP or
       Address Prefix."
   INDEX {  xIsisRASysInstance, xIsisRACircIndex, xIsisRAIndex }
   ::= { xIsisRATable 1 }

XIsisRAEntry ::=
   SEQUENCE {
      xIsisRASysInstance
         INTEGER,
      xIsisRACircIndex
         INTEGER,
      xIsisRAIndex
         INTEGER,
      xIsisRAExistState
         INTEGER,
      xIsisRAOperState
         INTEGER,
      xIsisRAAddrPrefix
        OCTET STRING,
      xIsisRAMapType
         INTEGER,
      xIsisRADefMetric
         INTEGER,
      xIsisRADelMetric
         INTEGER,
      xIsisRAExpMetric
         INTEGER,
      xIsisRAErrMetric
         INTEGER,
      xIsisRADefMetricType
         INTEGER,
      xIsisRADelMetricType
         INTEGER,
      xIsisRAExpMetricType
         INTEGER,
      xIsisRAErrMetricType
         INTEGER,
      xIsisRASNPAAddress
         OCTET STRING,
      xIsisRASNPAMask
         OCTET STRING,
      xIsisRASNPAPrefix
         OCTET STRING,
      xIsisRAType
         INTEGER
   }

xIsisRASysInstance OBJECT-TYPE
   SYNTAX INTEGER
   ACCESS read-only
   STATUS mandatory
   DESCRIPTION
       "The identifier of the Integrated IS-IS instance to which
       this row corresponds. This object follows the index and
       manualOrAutomatic behaviours."
   ::= { xIsisRAEntry 1 }

xIsisRACircIndex OBJECT-TYPE
   SYNTAX INTEGER
   ACCESS read-only
   STATUS mandatory
   DESCRIPTION
       "The identifier of the Circuit over which this
       destination is reachable. This object follows the index
       and manualOrAutomatic behaviours."
   ::= { xIsisRAEntry 2 }

xIsisRAIndex OBJECT-TYPE
   SYNTAX INTEGER
   ACCESS read-only
   STATUS mandatory
   DESCRIPTION
       "The identifier for this xIsisRAEntry. This value must be
       unique amongst all Reachable Addresses on the same parent
       Circuit. This object follows the index and
       manualOrAutomatic behaviours."
   ::= { xIsisRAEntry 3 }

xIsisRAExistState OBJECT-TYPE
   SYNTAX INTEGER {
                  off(1),
                  on(2)
                  }
   ACCESS read-write
   STATUS mandatory
   DESCRIPTION
       "The existence state of this Reachable Address. This
       object follows the ExistenceState and manualOrAutomatic
       behaviours."
   ::= { xIsisRAEntry 4 }

xIsisRAOperState OBJECT-TYPE
   SYNTAX INTEGER {
                  off(1),
                  on(2)
                  }
   ACCESS read-write
   STATUS mandatory
   DESCRIPTION
       "The operational state of the Reachable Address. This
       object follows the operationalState and manualOrAutomatic
       behaviours."
   ::= { xIsisRAEntry 5 }

xIsisRAAddrPrefix OBJECT-TYPE
   SYNTAX OCTET STRING
   ACCESS read-write
   STATUS mandatory
   DESCRIPTION
       "The destination of this Reachable Address. This is an
       Address Prefix. This object follows the
       replaceOnlyWhileDisabled and manualOrAutomatic
       behaviours."
   REFERENCE "ANSI {ISIS.aoi addressPrefix (98)}"
   ::= { xIsisRAEntry 6 }


xIsisRAMapType OBJECT-TYPE
   SYNTAX   INTEGER {
               none(1),
               explicit(2),
               extractIDI(3),
               extractDSP(4)
            }
   ACCESS read-write
   STATUS mandatory
   DESCRIPTION
       "The type of mapping to be employed to ascertain the SNPA
       Address which should be used in forwarding PDUs for this
       Reachable Address prefix. This object follows the
       manualOrAutomatic behaviour. The following values of
       mapping type are defined:

          none: The mapping is null because the neighbor SNPA is
          implicit by nature of the subnetwork (e.g. a
          point-to-point linkage).

          explicit: The subnetwork addresses in the object
          xIsisRASNPAAddress is to be used.

          extractIDI: The SNPA is embedded in the IDI of the
          destination NSAP Address. The mapping algorithm
          extracts the SNPA to be used according to the format
          and encoding rules of ISO8473/Add2. This SNPA
          extraction algorithm can be used in conjunction with
          Reachable Address prefixes from the X.121, F.69, E.163
          and E.164 addressing subdomains.

          extractDSP: All, or a suffix, of the SNPA is embedded
          in the DSP of the destination address. This SNPA
          extraction algorithm extracts the embedded subnetwork
          addressing information by performing a logical AND of
          the xIsisRASNPAMask object value with the destination
          address. The part of the SNPA extracted from the
          destination NSAP is appended to the xIsisRASNPAPrefix
          object value to form the next hop subnetwork
          addressing information."
   REFERENCE "ANSI {ISO10589-ISIS.aoi mappingType (107)}"
   ::= { xIsisRAEntry 7 }

xIsisRADefMetric OBJECT-TYPE
   SYNTAX INTEGER (1..63)
   ACCESS read-write
   STATUS mandatory
   DESCRIPTION
       "The default metric value for reaching the specified
       prefix over this circuit. This object follows the
       manualOrAutomatic behaviour."
   REFERENCE "ANSI {ISIS.aoi defaultMetric (99)}"
   ::= { xIsisRAEntry 8 }

xIsisRADelMetric OBJECT-TYPE
   SYNTAX INTEGER (0..63)
   ACCESS read-write
   STATUS mandatory
   DESCRIPTION
       "The delay metric for reaching the specified prefix over
       this circuit. This object follows the manualOrAutomatic
       behaviour. The value zero is reserved to indicate that
       this metric is not supported."
   REFERENCE "ANSI {ISIS.aoi delayMetric (100)}"
   ::= { xIsisRAEntry 9 }

xIsisRAExpMetric OBJECT-TYPE
   SYNTAX INTEGER (0..63)
   ACCESS read-write
   STATUS mandatory
   DESCRIPTION
       "The expense metric for reaching the specified prefix
       over this circuit. This object follows the
       manualOrAutomatic behaviour. The value zero is reserved
       to indicate that this metric is not supported."
   REFERENCE "ANSI {ISIS.aoi expenseMetric (101)}"
   ::= { xIsisRAEntry 10 }

xIsisRAErrMetric OBJECT-TYPE
   SYNTAX INTEGER (0..63)
   ACCESS read-write
   STATUS mandatory
   DESCRIPTION
       "The error metric for reaching the specified prefix over
       this circuit. This object follows the manualOrAutomatic
       behaviour. The value zero is reserved to indicate  that
       this metric is not supported."
   REFERENCE "ANSI {ISIS.aoi errorMetric (102)}"
   ::= { xIsisRAEntry 11 }

xIsisRADefMetricType OBJECT-TYPE
   SYNTAX INTEGER {
                  internal(1),
                  external(2)
                  }
   ACCESS read-write
   STATUS mandatory
   DESCRIPTION
       "Indicates whether the default metric is internal or
       external. This object follows the manualOrAutomatic
       behaviour."
   REFERENCE "ANSI {ISIS.aoi defaultMetricType (103)}"
   ::= { xIsisRAEntry 12 }

xIsisRADelMetricType OBJECT-TYPE
   SYNTAX INTEGER {
                  internal(1),
                  external(2)
                  }
   ACCESS read-write
   STATUS mandatory
   DESCRIPTION
       "Indicates whether the delay metric is internal or
       external. This object follows the manualOrAutomatic
       behaviour."
   REFERENCE "ANSI {ISO10589-ISIS.aoi delayMetricType (104)}"
   ::= { xIsisRAEntry 13 }

xIsisRAExpMetricType OBJECT-TYPE
   SYNTAX INTEGER {
                  internal(1),
                  external(2)
                  }
   ACCESS read-write
   STATUS mandatory
   DESCRIPTION
       "Indicates whether the expense metric is internal or
       external. This object follows the manualOrAutomatic
       behaviour."
   REFERENCE "ANSI {ISIS.aoi expenseMetricType (105)}"
   ::= { xIsisRAEntry 14 }

xIsisRAErrMetricType OBJECT-TYPE
   SYNTAX INTEGER {
                  internal(1),
                  external(2)
                  }
   ACCESS read-write
   STATUS mandatory
   DESCRIPTION
       "Indicates whether the error metric is internal or
       external. This object follows the manualOrAutomatic
       behaviour."
   REFERENCE "ANSI {ISIS.aoi errorMetricType (106)}"
   ::= { xIsisRAEntry 15 }

xIsisRASNPAAddress OBJECT-TYPE
   SYNTAX OCTET STRING
   ACCESS read-write
   STATUS mandatory
   DESCRIPTION
       "The SNPA Address to which a PDU may be forwarded in
       order to reach a destination which matches the address
       prefix of the Reachable Address. This object follows the
       manualOrAutomatic behaviour."
   REFERENCE "ANSI {ISIS.aoi sNPAAddresses (109)}"
-- note only one address may be specified per Reachable Address
-- in the MIB
   ::= { xIsisRAEntry 16 }

xIsisRASNPAMask OBJECT-TYPE
   SYNTAX OCTET STRING
   ACCESS read-write
   STATUS mandatory
   DESCRIPTION
       "A bit mask with 1 bits indicating the positions in the
       effective destination address from which embedded SNPA
       information is to be extracted. For the extraction the
       first octet of the xIsisRASNPAMask object value is aligned
       with the first octet (AFI) of the NSAP Address. If the
       xIsisRASNPAMask object value and NSAP Address are of
       different lengths, the shorter of the two is logically
       padded with zeros before performing the extraction. This
       object follows the manualOrAutomatic behaviour."
   REFERENCE "ANSI {ISIS.aoi sNPAMask (122)}"
   ::= { xIsisRAEntry 17 }

xIsisRASNPAPrefix OBJECT-TYPE
   SYNTAX OCTET STRING
   ACCESS read-write
   STATUS mandatory
   DESCRIPTION
       "A fixed SNPA prefix for use when the xIsisRAMapType is
       extractDSP. The SNPA Address to use is formed by
       concatenating the fixed SNPA prefix with a variable SNPA
       part that is extracted from the effective destination
       address. For Reachable Address prefixes in which the
       entire SNPA is embedded in the DSP the SNPA Prefix shall
       be null. This object follows the manualOrAutomatic
       behaviour."
   REFERENCE "ANSI {ISIS.aoi sNPAPrefix (123)}"
   ::= { xIsisRAEntry 18 }

xIsisRAType OBJECT-TYPE
    SYNTAX INTEGER {
    	manual(1),
	automatic(2)
    }
    ACCESS read-only
    STATUS mandatory
    DESCRIPTION
        "The type of Reachable address. Those of type 
        manual are created by the network manager. Those
        of type automatic are created through propogation
        of routing information from another routing
        protocol (eg. IDRP). "
    ::= { xIsisRAEntry 20 }

        
-- The Level 1 CLNP Destination Group

-- The Level 1 CLNP Destination Group is present if the system
-- supports Level 1 and forwards ISO 8473 packets.


-- The Level 1 CLNP Destination Table

-- The Level 1 CLNP Destination Table records information about
-- each end system ID destination known to the Intermediate
-- System in the system's level 1 forwarding database.

xIsisL1CLNPDestTable OBJECT-TYPE
   SYNTAX SEQUENCE OF XIsisL1CLNPDestEntry
   ACCESS not-accessible
   STATUS mandatory
   DESCRIPTION
       "The Level 1 CLNP Destination Table records information
       about each end system ID destination known to the
       Intermediate System."
   ::= { xIsisCLNPDest 1 }

xIsisL1CLNPDestEntry OBJECT-TYPE
   SYNTAX XIsisL1CLNPDestEntry
   ACCESS not-accessible
   STATUS mandatory
   DESCRIPTION
       "Each entry records information about one CLNP end system
       ID destination known to the Intermediate System."
   INDEX {  xIsisL1CLNPSysInstance, xIsisL1CLNPRouteMetricQOS, xIsisL1CLNPRouteDest, xIsisL1CLNPRouteForw }
   ::= { xIsisL1CLNPDestTable 1 }

XIsisL1CLNPDestEntry ::=
   SEQUENCE {
      xIsisL1CLNPRouteDest
         OCTET STRING,
      xIsisL1CLNPRouteMetricQOS
         INTEGER,
      xIsisL1CLNPRouteMetricType
         INTEGER,
      xIsisL1CLNPRouteMetricValue
         INTEGER,
      xIsisL1CLNPRouteForw
         OBJECT IDENTIFIER,
      xIsisL1CLNPRouteSource
         INTEGER,
      xIsisL1CLNPSysInstance
         INTEGER
   }


xIsisL1CLNPRouteDest OBJECT-TYPE
   SYNTAX OCTET STRING
   ACCESS read-only
   STATUS mandatory
   DESCRIPTION
       "The destination end system ID."
   ::= { xIsisL1CLNPDestEntry 2 }

xIsisL1CLNPRouteMetricQOS OBJECT-TYPE
   SYNTAX INTEGER {
                  default(1),
                  delay(2),
                  expense(3),
                  error(4)
                  }
   ACCESS read-only
   STATUS mandatory
   DESCRIPTION
       "The QOS metric for this destination."
   ::= { xIsisL1CLNPDestEntry 3 }

xIsisL1CLNPRouteMetricType OBJECT-TYPE
   SYNTAX   INTEGER  {
               internal(1),
               external(2)
            }
   ACCESS read-only
   STATUS mandatory
   DESCRIPTION
       "Indicates whether the metric has an external component
       or not"
   ::= { xIsisL1CLNPDestEntry 4 }

xIsisL1CLNPRouteMetricValue OBJECT-TYPE
   SYNTAX INTEGER (0..1023)
   ACCESS read-only
   STATUS mandatory
   DESCRIPTION
       "The path metric value for this destination."
   ::= { xIsisL1CLNPDestEntry 5 }

xIsisL1CLNPRouteForw OBJECT-TYPE
   SYNTAX OBJECT IDENTIFIER
   ACCESS read-only
   STATUS mandatory
   DESCRIPTION
       "The OBJECT IDENTIFIER for the first object in the table
       entry which corresponds to the entry used for forwarding
       packets to this destination. This value is an OBJECT
       IDENTIFIER for an instance of the object:
       xIsisESAdjSysInstance or xIsisISAdjSysInstance."
   ::= { xIsisL1CLNPDestEntry 6 }

xIsisL1CLNPRouteSource OBJECT-TYPE
   SYNTAX   INTEGER {
               manual(1),
               level1(2),
               esis(3)
            }
   ACCESS read-only
   STATUS mandatory
   DESCRIPTION
       "The source of the destination. Manual is used if the
       source is manually configured information on the system.
       Level1 is used if the source is Level 1 LSPs. Esis is
       used if the source is ES Hellos"
   ::= { xIsisL1CLNPDestEntry 7 }


xIsisL1CLNPSysInstance OBJECT-TYPE
   SYNTAX INTEGER
   ACCESS read-only
   STATUS mandatory
   DESCRIPTION
       "If the value of xIsisL1CLNPRouteSource is manual or
       level1 then this is the identifier of the Integrated
       IS-IS Level 1 instance from which this reachability
       information was learned, otherwise this value is zero."
   ::= { xIsisL1CLNPDestEntry 1 }

-- The Level 2 CLNP Destination Group

-- The Level 2 CLNP Destination Group is present if the system
-- supports Level 2 and forwards ISO 8473 packets.


-- The Level 2 CLNP Destination Table

-- The Level 2 CLNP Destination Table records information about
-- each NSAP Address Prefix known to the Intermediate
-- System

xIsisL2CLNPDestTable OBJECT-TYPE
   SYNTAX SEQUENCE OF XIsisL2CLNPDestEntry
   ACCESS not-accessible
   STATUS mandatory
   DESCRIPTION
       "The Level 2 CLNP Destination Table records information
       about each NSAP Address Prefix known to the Intermediate
       System."
   ::= { xIsisCLNPDest 2 }

xIsisL2CLNPDestEntry OBJECT-TYPE
   SYNTAX XIsisL2CLNPDestEntry
   ACCESS not-accessible
   STATUS mandatory
   DESCRIPTION
       "Each entry records information about one NSAP Address
       Prefix known to the Intermediate System."
   INDEX {  xIsisL2CLNPSysInstance, xIsisL2CLNPRouteMetricQOS, xIsisL2CLNPRouteDest, xIsisL2CLNPRouteForw }
   ::= { xIsisL2CLNPDestTable 1 }

XIsisL2CLNPDestEntry ::=
   SEQUENCE {
      xIsisL2CLNPRouteDest
         OCTET STRING,
      xIsisL2CLNPRouteMetricQOS
         INTEGER,
      xIsisL2CLNPRouteMetricType
         INTEGER,
      xIsisL2CLNPRouteMetricValue
         INTEGER,
      xIsisL2CLNPRouteForw
         OBJECT IDENTIFIER,
      xIsisL2CLNPRouteSource
         INTEGER,
      xIsisL2CLNPSysInstance
         INTEGER
   }

xIsisL2CLNPRouteDest OBJECT-TYPE
   SYNTAX OCTET STRING
   ACCESS read-only
   STATUS mandatory
   DESCRIPTION
       "The destination address prefix."
   ::= { xIsisL2CLNPDestEntry 2 }

xIsisL2CLNPRouteMetricQOS OBJECT-TYPE
   SYNTAX INTEGER {
                  default(1),
                  delay(2),
                  expense(3),
                  error(4)
                  }
   ACCESS read-only
   STATUS mandatory
   DESCRIPTION
       "The QOS metric for this destination."
   ::= { xIsisL2CLNPDestEntry 3 }

xIsisL2CLNPRouteMetricType OBJECT-TYPE
   SYNTAX   INTEGER  {
               internal(1),
               external(2)
            }
   ACCESS read-only
   STATUS mandatory
   DESCRIPTION
       "Indicates whether the metric has an external component
       or not"
   ::= { xIsisL2CLNPDestEntry 4 }

xIsisL2CLNPRouteMetricValue OBJECT-TYPE
   SYNTAX INTEGER (0..1023)
   ACCESS read-only
   STATUS mandatory
   DESCRIPTION
       "The path metric value for this destination."
   ::= { xIsisL2CLNPDestEntry 5 }

xIsisL2CLNPRouteForw OBJECT-TYPE
   SYNTAX OBJECT IDENTIFIER
   ACCESS read-only
   STATUS mandatory
   DESCRIPTION
       "The OBJECT IDENTIFIER for the first object in the table
       entry which corresponds to the entry used for forwarding
       packets to this destination. This value is an OBJECT
       IDENTIFIER for an instance of one of the following
       objects: isisVirtSysInstance, xIsisISAdjSysInstance,
       xIsisRASysInstance."
   ::= { xIsisL2CLNPDestEntry 6 }

xIsisL2CLNPRouteSource OBJECT-TYPE
   SYNTAX   INTEGER {
               manual(1),
               level2(2)
            }
   ACCESS read-only
   STATUS mandatory
   DESCRIPTION
       "The source of the destination. Manual is used if the
       source is manually configured information on the system.
       Level2 is used if the source is Level 2 LSPs."
   ::= { xIsisL2CLNPDestEntry 7 }

xIsisL2CLNPSysInstance OBJECT-TYPE
   SYNTAX INTEGER
   ACCESS read-only
   STATUS mandatory
   DESCRIPTION
       "The identifier of the Integrated IS-IS Level 2 instance
       from which this reachability information was learned."
   ::= { xIsisL2CLNPDestEntry 1 }


-- The Level 3 CLNP Destination Group

-- The Level 3 CLNP Destination Group is present if the system
-- supports reachable addresses
--  and forwards ISO 8473 packets.


-- The Level 3 CLNP Destination Table

-- The Level 3 CLNP Destination Table records information about
-- each Reachable Address Prefix known to the Intermediate
-- System

xIsisL3CLNPDestTable OBJECT-TYPE
   SYNTAX SEQUENCE OF XIsisL3CLNPDestEntry
   ACCESS not-accessible
   STATUS mandatory
   DESCRIPTION
       "The Level 3 CLNP Destination Table records information
       about each Reachable Address Prefix known to the Intermediate
       System."
   ::= { xIsisCLNPDest 3 }

xIsisL3CLNPDestEntry OBJECT-TYPE
   SYNTAX XIsisL3CLNPDestEntry
   ACCESS not-accessible
   STATUS mandatory
   DESCRIPTION
       "Each entry records information about one Address
       Prefix known to the Intermediate System."
   INDEX {  xIsisL3CLNPSysInstance, xIsisL3CLNPRouteMetricQOS, xIsisL3CLNPRouteDest, xIsisL3CLNPRouteForw }
   ::= { xIsisL3CLNPDestTable 1 }

XIsisL3CLNPDestEntry ::=
   SEQUENCE {
      xIsisL3CLNPRouteDest
        OCTET STRING,
      xIsisL3CLNPRouteMetricQOS
         INTEGER,
      xIsisL3CLNPRouteMetricType
         INTEGER,
      xIsisL3CLNPRouteMetricValue
         INTEGER,
      xIsisL3CLNPRouteForw
         OBJECT IDENTIFIER,
      xIsisL3CLNPRouteSource
         INTEGER,
      xIsisL3CLNPSysInstance
         INTEGER
   }

xIsisL3CLNPRouteDest OBJECT-TYPE
   SYNTAX OCTET STRING
   ACCESS read-only
   STATUS mandatory
   DESCRIPTION
       "The destination address prefix."
   ::= { xIsisL3CLNPDestEntry 2 }

xIsisL3CLNPRouteMetricQOS OBJECT-TYPE
   SYNTAX INTEGER {
                  default(1),
                  delay(2),
                  expense(3),
                  error(4)
                  }
   ACCESS read-only
   STATUS mandatory
   DESCRIPTION
       "The QOS metric for this destination."
   ::= { xIsisL3CLNPDestEntry 3 }

xIsisL3CLNPRouteMetricType OBJECT-TYPE
   SYNTAX   INTEGER  {
               internal(1),
               external(2)
            }
   ACCESS read-only
   STATUS mandatory
   DESCRIPTION
       "Indicates whether the metric has an external component
       or not"
   ::= { xIsisL3CLNPDestEntry 4 }

xIsisL3CLNPRouteMetricValue OBJECT-TYPE
   SYNTAX INTEGER (0..1023)
   ACCESS read-only
   STATUS mandatory
   DESCRIPTION
       "The path metric value for this destination."
   ::= { xIsisL3CLNPDestEntry 5 }

xIsisL3CLNPRouteForw OBJECT-TYPE
   SYNTAX OBJECT IDENTIFIER
   ACCESS read-only
   STATUS mandatory
   DESCRIPTION
       "The OBJECT IDENTIFIER for the first object in the table
       entry which corresponds to the entry used for forwarding
       packets to this destination. This value is an OBJECT
       IDENTIFIER for an instance of one of the following
       objects: isisVirtSysInstance, xIsisISAdjSysInstance,
       xIsisRASysInstance."
   ::= { xIsisL3CLNPDestEntry 6 }

xIsisL3CLNPRouteSource OBJECT-TYPE
   SYNTAX   INTEGER {
               manual(1),
               level2(2)
            }
   ACCESS read-only
   STATUS mandatory
   DESCRIPTION
       "The source of the destination. Manual is used if the
       source is manually configured information on the system.
       Level3 is used if the source is Level 3 LSPs."
   ::= { xIsisL3CLNPDestEntry 7 }

xIsisL3CLNPSysInstance OBJECT-TYPE
   SYNTAX INTEGER
   ACCESS read-only
   STATUS mandatory
   DESCRIPTION
       "The identifier of the Integrated IS-IS Level 3 instance
       from which this reachability information was learned."
   ::= { xIsisL3CLNPDestEntry 1 }

-- The Circuit CLNS Group

-- The Circuit IS Group is always present.


-- The Circuit CLNS Table

-- The Circuit CLNS Table contains objects controlling the
-- operation of the IS functions of the CLNS protocol
-- (ISO 8473) on each circuit over which ISIS is run.

xIsisCircClnsTable OBJECT-TYPE
   SYNTAX SEQUENCE OF XIsisCircClnsEntry
   ACCESS not-accessible
   STATUS mandatory
   DESCRIPTION
       "The set of objects controlling the operation of the
			  CLNS protocol (ISO 8473) on each
       circuit over which ISIS is run."
   ::= { xIsisCirc 3 }

xIsisCircClnsEntry OBJECT-TYPE
   SYNTAX XIsisCircClnsEntry
   ACCESS not-accessible
   STATUS mandatory
   DESCRIPTION
       "Each entry contains objects controlling the operation of
       the CLNS protocol (ISO 8473) on one
       circuit."
   INDEX {  xIsisCircClnsIndex }
   ::= { xIsisCircClnsTable 1 }

XIsisCircClnsEntry ::=
   SEQUENCE {
      xIsisCircClnsSysInstance
         INTEGER,
      xIsisCircClnsIndex
         INTEGER,
      xIsisCircClnsExistState
         INTEGER,
      xIsisCircClnsOperState
         INTEGER,
      xIsisCircClnsRxPDUs
         Counter,
      xIsisCircClnsTxPDUs
         Counter
   }
xIsisCircClnsSysInstance OBJECT-TYPE
   SYNTAX INTEGER
   ACCESS read-only
   STATUS mandatory
   DESCRIPTION            
       "The identifier of the Integrated IS-IS instance to which
       this row corresponds. This object follows the index and
       manualOrAutomatic behaviours."
   ::= { xIsisCircClnsEntry 1 }

xIsisCircClnsIndex OBJECT-TYPE
   SYNTAX INTEGER
   ACCESS read-only
   STATUS mandatory
   DESCRIPTION
       "The unique identifier of this row. This value is the
       same as the value of the ifIndex object which identifies
       the interface which corresponds to this circuit. This
       object follows the index behaviour."
   ::= { xIsisCircClnsEntry 2 }

xIsisCircClnsExistState OBJECT-TYPE
   SYNTAX INTEGER {
                  off(1),
                  on(2)
                  }
   ACCESS read-only
   STATUS mandatory
   DESCRIPTION
       "The existence state of this row. This object follows the
       ExistenceState behaviour."
   ::= { xIsisCircClnsEntry 3 }

xIsisCircClnsOperState OBJECT-TYPE
   SYNTAX INTEGER {
                  off(1),
                  on(2)
                  }
   ACCESS read-write
   STATUS mandatory
   DESCRIPTION
       "The operational state of the row. This object follows
       the operationalState behaviour."
   ::= { xIsisCircClnsEntry 4 }

xIsisCircClnsRxPDUs OBJECT-TYPE
   SYNTAX Counter
   ACCESS read-only
   STATUS mandatory
   DESCRIPTION
       "Counter of number of CLNS PDUs received on this
	circuit."
   ::= { xIsisCircClnsEntry 5 }

xIsisCircClnsTxPDUs OBJECT-TYPE
   SYNTAX Counter
   ACCESS read-only
   STATUS mandatory
   DESCRIPTION
       "Counter of number of CLNS PDUs transmitted on this
	circuit."
   ::= { xIsisCircClnsEntry 6 }


--
-- FILE: /users/sse/mibs/src/itouch/it-link-mib.mib
--

-- $Id: it-link-mib.mib,v 1.1 2000/07/25 14:34:31 sse Exp $


       xLink           OBJECT IDENTIFIER ::= { iTouch 24 }

       -- ITouch Link subgroups

       xLinkBasic      OBJECT IDENTIFIER ::= { xLink 1 }
       --                                    2 reserved for LAN
       xWan            OBJECT IDENTIFIER ::= { xLink 3 }




            -- This is a MIB module for all iTouch Communications systems
            -- that implement iTouch enhanced network communication links.

            -- Copyright 2000 iTouch Communications, Inc. All Rights Reserved.
            -- Reproduction of this document is authorized on
            -- condition that this copyright notice is included.
            -- This MIB document embodies iTouch Communications, Inc.'s 
            -- proprietary intellectual property.  iTouch Communications, Inc.
            -- retains all title and ownership in this MIB, including any
            -- revisions.
            --
            -- It is iTouch Communications, Inc.'s intent to encourage the
            -- widespread use of this MIB in connection with the management of
            -- iTouch Communications, Inc. products. iTouch Communications,
            -- Inc. grants vendors,end-users, and other interested parties a
            -- non-exclusive license to use this MIB in connection with the
            -- management of iTouch Communications, Inc. products.
            --
            -- This MIB document is supplied "AS IS," and iTouch 
            -- Communications, Inc. makes no warranty, either express or
            -- implied, as to the use operation, condition, or performance of
            -- the MIB.



       -- link group

       linkTable OBJECT-TYPE
           SYNTAX SEQUENCE OF LinkEntry
           ACCESS not-accessible
           STATUS mandatory
           DESCRIPTION
               "A list of links."
           ::= { xLinkBasic 1 }

       linkEntry OBJECT-TYPE
           SYNTAX LinkEntry
           ACCESS not-accessible
           STATUS mandatory
           DESCRIPTION
               "Link entry."
           INDEX { ifIndex }
           ::= { linkTable 1 }

       LinkEntry ::=
           SEQUENCE {
               linkNoBuffers
                   Counter,
               linkDelayExceeded
                   Counter,
               linkOutputQFull
                   Counter,
               linkDownTime
                   Counter,
               linkDownCount
                   Counter,
               linkDownLastStart
                   TimeTicks,
               linkStatus
                   INTEGER,
               linkLostBuffers
                   Counter
           }

       linkNoBuffers OBJECT-TYPE
           SYNTAX Counter
           ACCESS read-only
           STATUS mandatory
           DESCRIPTION
               "The number of packets discarded because of lack of 
               buffers."
           ::= { linkEntry 1 }

       linkDelayExceeded OBJECT-TYPE
           SYNTAX Counter
           ACCESS read-only
           STATUS mandatory
           DESCRIPTION
               "The number of packets discarded because they were 
               held to long."
           ::= { linkEntry 2 }

       linkOutputQFull OBJECT-TYPE
           SYNTAX Counter
           ACCESS read-only
           STATUS mandatory
           DESCRIPTION
               "The number of packets discarded because the output 
               queue was full."
           ::= { linkEntry 3 }

       linkDownTime OBJECT-TYPE
           SYNTAX Counter
           ACCESS read-only
           STATUS mandatory
           DESCRIPTION
               "Total number of seconds that the link has been 
               down."
           ::= { linkEntry 4 }

       linkDownCount OBJECT-TYPE
           SYNTAX Counter
           ACCESS read-only
           STATUS mandatory
           DESCRIPTION
               "Number of times that the link has been down."
           ::= { linkEntry 5 }

       linkDownLastStart OBJECT-TYPE
           SYNTAX TimeTicks
           ACCESS read-only
           STATUS mandatory
           DESCRIPTION
               "Value of sysUpTime when the link last went down.  
               If the link is up the value is 0."
           ::= { linkEntry 6 }

       linkStatus OBJECT-TYPE
           SYNTAX INTEGER { running1(7), initWaitDsr(128),
                            initWait(129), running2(130),
                            purgeWait(131), down(132),
                            purging(133), loop(138), 
                            testSend(139), testReceive(140),
                            testLoop(141), speedChange(143),
                            disabled(145), badQuality(146) }
           ACCESS read-only
           STATUS mandatory
           DESCRIPTION
               "The status of the link"
           ::= { linkEntry 7 }

       linkLostBuffers OBJECT-TYPE
           SYNTAX Counter
           ACCESS read-only
           STATUS mandatory
           DESCRIPTION
               "Number of packets discarded because of lost 
               buffers"
           ::= { linkEntry 8 }

       -- the Link Resource table

       linkResourceTable OBJECT-TYPE
           SYNTAX SEQUENCE OF LinkResourceEntry
           ACCESS not-accessible
           STATUS mandatory
           DESCRIPTION
               "A list of link resources."
           ::= { xLinkBasic 2 }

       linkResourceEntry OBJECT-TYPE
           SYNTAX LinkResourceEntry
           ACCESS not-accessible
           STATUS mandatory
           DESCRIPTION
               "link entry."
           INDEX { linkResourceType, ifIndex }
           ::= { linkResourceTable 1 }

       LinkResourceEntry ::=
           SEQUENCE {
               linkResourceType
                   INTEGER,
               linkResourceCurrent
                   Gauge,
               linkResourceHigh
                   Gauge,
               linkResourceAverage
                   Gauge
           }

       linkResourceType OBJECT-TYPE
           SYNTAX INTEGER { utilization(1), outputQueue(2) }
           ACCESS read-only
           STATUS mandatory
           DESCRIPTION
               "The resource type."
           ::= { linkResourceEntry 1 }

       linkResourceCurrent OBJECT-TYPE
           SYNTAX Gauge
           ACCESS read-only
           STATUS mandatory
           DESCRIPTION
               "The current percent of the resource used."
           ::= { linkResourceEntry 2 }

       linkResourceHigh OBJECT-TYPE
           SYNTAX Gauge
           ACCESS read-only
           STATUS mandatory
           DESCRIPTION
               "The highest percent of the resource used."
           ::= { linkResourceEntry 3 }

       linkResourceAverage OBJECT-TYPE
           SYNTAX Gauge
           ACCESS read-only
           STATUS mandatory
           DESCRIPTION
               "The average percent of the resource used."
           ::= { linkResourceEntry 4 }


       -- WAN group

       wanTable OBJECT-TYPE
           SYNTAX SEQUENCE OF WanEntry
           ACCESS not-accessible
           STATUS mandatory
           DESCRIPTION
               "A list of WANs."
           ::= { xWan 1 }

       wanEntry OBJECT-TYPE
           SYNTAX WanEntry
           ACCESS not-accessible
           STATUS mandatory
           DESCRIPTION
               "WAN entry."
           INDEX { ifIndex }
           ::= { wanTable 1 }

       WanEntry ::=
           SEQUENCE {
               wanProtocol
                   INTEGER,
               wanCompressionAdminStatus
                   INTEGER,
               wanMaxForwardDelay
                   INTEGER,
               wanMaxMultiForwardDelay
                   INTEGER,
               wanAdminSpeed
                   INTEGER,
               wanCompressionOperStatus
                   INTEGER
           }

       wanProtocol OBJECT-TYPE
           SYNTAX INTEGER { xcp(2), fr(3), ppp(4), frlmi(5),
                            fransi(6), frdcelmi(7), frdceansi(8),
                            x25(9) }
           ACCESS read-write
           STATUS mandatory
           DESCRIPTION
               "Controls the protocol run on the link, changes 
               ifType, typically to 'other'."
           DEFVAL { xcp }
           ::= { wanEntry 1 }

       wanCompressionAdminStatus OBJECT-TYPE
           SYNTAX INTEGER { noCompression(1), compress(2),
                            auto(256) }
           ACCESS read-write
           STATUS mandatory
           DESCRIPTION
               "Controls whether link compression will be run if 
               the link is running the xyplex protocol.  Auto will 
               enable compression for links slower than 67000."
           DEFVAL { auto }
           ::= { wanEntry 2 }

       wanMaxForwardDelay OBJECT-TYPE
       --  SYNTAX INTEGER ( 0 | 500..32000 )  (Preferred)
           SYNTAX INTEGER ( 0..32000 )
           ACCESS read-write
           STATUS mandatory
           DESCRIPTION
               "The number of milliseconds that a packet may be 
               held on the Wan link before it will be discarded.  
               The value 0 indicates no limit."
           DEFVAL { 1000 }
           ::= { wanEntry 3 }

       wanMaxMultiForwardDelay OBJECT-TYPE
       --  SYNTAX INTEGER ( 0 | 350..32000 )  (Preferred)
           SYNTAX INTEGER ( 0..32000 )
           ACCESS read-write
           STATUS mandatory
           DESCRIPTION
               "The number of milliseconds that a multicast packet 
               may  be held on the Wan link before it will be 
               discarded.  The value 0 indicates no delay."
           DEFVAL { 700 }
           ::= { wanEntry 4 }

       wanAdminSpeed OBJECT-TYPE
           SYNTAX INTEGER
           ACCESS read-write
           STATUS mandatory
           DESCRIPTION
               "The speed that the software should use for the wan 
               link. The value 0 indicates that the measured speed 
               should be used."
           DEFVAL { 0 }
           ::= { wanEntry 5 }

       wanCompressionOperStatus OBJECT-TYPE
           SYNTAX INTEGER { notCompressing(1), compressing(2) }
           ACCESS read-only
           STATUS mandatory
           DESCRIPTION
               "If the link is running the Xyplex protocol, 
               indicates whether link compression is running."
           ::= { wanEntry 6 }


--
-- FILE: /users/sse/mibs/src/itouch/it-param-client-mib.mib
--

-- $Id: it-param-client-mib.mib,v 1.2 2001/08/15 14:00:29 sse Exp $


            xParamClient    OBJECT IDENTIFIER ::= { iTouch 7 }

            --  This is the MIB module for clients of iTouch parameter
            --  service.

            -- Copyright 2000 iTouch Communications, Inc. All Rights Reserved.
            -- Reproduction of this document is authorized on
            -- condition that this copyright notice is included.
            -- This MIB document embodies iTouch Communications, Inc.'s 
            -- proprietary intellectual property.  iTouch Communications, Inc.
            -- retains all title and ownership in this MIB, including any
            -- revisions.
            --
            -- It is iTouch Communications, Inc.'s intent to encourage the
            -- widespread use of this MIB in connection with the management of
            -- iTouch Communications, Inc. products. iTouch Communications,
            -- Inc. grants vendors,end-users, and other interested parties a
            -- non-exclusive license to use this MIB in connection with the
            -- management of iTouch Communications, Inc. products.
            --
            -- This MIB document is supplied "AS IS," and iTouch 
            -- Communications, Inc. makes no warranty, either express or
            -- implied, as to the use operation, condition, or performance of
            -- the MIB.


            -- the Parameter Client group

            -- Implementation of this group is mandatory for all iTouch
            -- systems that use the iTouch parameter service

            paramClientLoaderName OBJECT-TYPE
                SYNTAX DisplayString
                ACCESS read-only
                STATUS mandatory
                DESCRIPTION
                    "The name of the system that most recently provided 
                    this system's stored parameters.  Corresponds 
                    directly to the name value labeled 'Loaded From:' in 
                    the PARAMETER SERVER display."
                ::= { xParamClient 1 }

            paramClientLoaderAddressType OBJECT-TYPE
                SYNTAX AddressType
                ACCESS read-only
                STATUS mandatory
                DESCRIPTION
                    "The type of network address contained in 
                    paramClientLoaderAddress.  'unknown' means no 
                    address has been defined.  'other' means no other 
                    type value applies.  'local' means there is no 
                    address and parameters were loaded from local 
                    storage.  'ip' is an Internet IP address.  
                    'ethernet' is an 802.3 MAC address.  Corresponds 
                    indirectly to the address value labeled 'Loaded 
                    From:' in the PARAMETER SERVER display."
                ::= { xParamClient 2 }

            paramClientLoaderAddress OBJECT-TYPE
                SYNTAX OCTET STRING
                ACCESS read-only
                STATUS mandatory
                DESCRIPTION
                    "The network address of the system that most 
                    recently provided this system's stored parameters.  
                    Corresponds directly to the address value labeled 
                    'Loaded From:' in the PARAMETER SERVER display."
                ::= { xParamClient 3 }

            paramClientParameterVersion OBJECT-TYPE
                SYNTAX INTEGER
                ACCESS read-write
                STATUS mandatory
                DESCRIPTION
                    "The version number of the parameters as stored in 
                    this system's local memory.  Corresponds directly to 
                    SERVER PARAMETER VERSION and the value labeled 'Last 
                    Update Version:' in the PARAMETER SERVER display."
                ::= { xParamClient 4 }

            paramClientUpdateTime OBJECT-TYPE
                SYNTAX DateTime
                ACCESS read-only
                STATUS mandatory
                DESCRIPTION
                    "This system's local date and time when it last 
                    attempted to store parameters with a parameter 
                    server.  Corresponds directly to the values labeled 
                    'Last Update Date:' and 'Last Update Time:' in the 
                    PARAMETER SERVER display."
                ::= { xParamClient 5 }

            paramClientServerCheck OBJECT-TYPE
                SYNTAX INTEGER { disabled(1), enabled(2) }
                ACCESS read-write
                STATUS mandatory
                DESCRIPTION
                    "Control over whether or not this system is allowed 
                    to check for additional parameter servers.  
                    'enabled' allows checking.  Corresponds directly to 
                    PARAMETER SERVER CHECK and the presence of PARAMETER 
                    POLLING under the label 'Enabled Characteristics' in 
                    the SERVER CHARACTERISTICS display."
                ::= { xParamClient 6 }

            paramClientCheckInterval OBJECT-TYPE
                SYNTAX INTEGER (1..120)
                ACCESS read-write
                STATUS mandatory
                DESCRIPTION
                    "The number of minutes between checks for additional 
                    parameter servers.  Corresponds directly to 
                    PARAMETER SERVER CHECK TIMER and the value labeled 
                    'Check Timer:' in the PARAMETER SERVER display."
                ::= { xParamClient 7 }

            paramClientCheckNow OBJECT-TYPE
                SYNTAX INTEGER { ready(1), execute(2) }
                ACCESS read-write
                STATUS mandatory
                DESCRIPTION
                    "Control to cause this system to immediately check 
                    for additional parameter servers.  The agent always 
                    returns 'ready' for this value.  Setting the value 
                    to 'ready' has no effect.  Setting it to 'execute' 
                    causes a check to be started.  Corresponds to the 
                    CHECK PARAMETER SERVER command."
                ::= { xParamClient 8 }

            paramClientServerLimit OBJECT-TYPE
                SYNTAX INTEGER (1..8)
                ACCESS read-write
                STATUS mandatory
                DESCRIPTION
                    "The maximum number of parameter servers this system 
                    is allowed to remember at the same time.  
                    Corresponds directly to PARAMETER SERVER LIMIT and 
                    the value labeled 'Parameter Server Limit:' in the 
                    PARAMETER SERVER display."
                ::= { xParamClient 9 }

            paramClientRetransmitInterval OBJECT-TYPE
                SYNTAX INTEGER (1..30)
                ACCESS read-write
                STATUS mandatory
                DESCRIPTION
                    "The number of minutes between this system's 
                    attempts to store new parameters with a server that 
                    has not acknowledged previous attempts.  Corresponds 
                    directly to PARAMETER SERVER RETRANSMIT TIMER and 
                    the value labeled 'Retransmit Timer: in the 
                    PARAMETER SERVER display."
                ::= { xParamClient 10 }

            paramClientRetransmitLimit OBJECT-TYPE
                SYNTAX INTEGER (1..100)
                ACCESS read-write
                STATUS mandatory
                DESCRIPTION
                    "The maximum number of attempts by this system to 
                    store new parameters with a server that has not 
                    acknowledged previous attempts.  Corresponds 
                    directly to PARAMETER SERVER RETRANSMIT LIMIT and 
                    the value labeled 'Retransmit Limit:' in the 
                    PARAMETER SERVER display."
                ::= { xParamClient 11 }

            paramClientState OBJECT-TYPE
                SYNTAX INTEGER { other(1), idle(2), internal1(3),
                                 internal2(4), internal3(5),
                                 internal4(6), internal5(7),
                                 internal6(8), internal7(9),
                                 internal8(10), hold(11),  retry(12)}
                ACCESS read-only
                STATUS mandatory
                DESCRIPTION
                    "This system's state with regard to update attempts.  
                    The value meanings are:

                    other       none of the following
                    idle        no update in progress
                    internal    internal state of no meaning to manager
                    hold        holding to keep from updating too often
                    retry       waiting to retry after failure

                    Corresponds directly to the value labeled 'Storage 
                    State:' in the PARAMETER SERVER display."
                ::= { xParamClient 12 }

            paramClientProtocolErrors OBJECT-TYPE
                SYNTAX Counter
                ACCESS read-only
                STATUS mandatory
                DESCRIPTION
                    "The number of invalid parameter service protocol 
                    messages received by this system.  Corresponds 
                    directly to the value labeled 'Bad Parameter 
                    Messages:' in the PARAMETER SERVER display."
                ::= { xParamClient 13 }

            paramClientServerRejects OBJECT-TYPE
                SYNTAX Counter
                ACCESS read-only
                STATUS mandatory
                DESCRIPTION
                    "The number of parameter servers this system 
                    rejected due to exceeding paramClientServerLimit.  
                    Corresponds directly to the value labeled 'Rejected 
                    Servers:' in the PARAMETER SERVER display."
                ::= { xParamClient 14 }

            paramClientServerNumber OBJECT-TYPE
                SYNTAX INTEGER
                ACCESS read-only
                STATUS mandatory
                DESCRIPTION
                    "The number of parameter servers known to this 
                    system, indicating the number of entries in 
                    serverTable.  Corresponds directly to the value 
                    labeled 'Parameter Servers:' in the PARAMETER SERVER 
                    display."
                ::= { xParamClient 15 }

            -- Further individual parameters follow the Parameter
            -- Server table


            -- the Parameter Server table

            paramServerTable OBJECT-TYPE
                SYNTAX SEQUENCE OF ParamServerEntry
                ACCESS not-accessible
                STATUS mandatory
                DESCRIPTION
                    "A list of parameter server entries.  The number of 
                    entries is given by the value of 
                    paramClientServerNumber."
                ::= { xParamClient 16 }

            paramServerEntry OBJECT-TYPE
                SYNTAX ParamServerEntry
                ACCESS not-accessible
                STATUS mandatory
                DESCRIPTION
                    "Status and parameter values for a parameter 
                    server."
                INDEX { paramServerName }
                ::= { paramServerTable 1 }

            ParamServerEntry ::=
                SEQUENCE {
                    paramServerName
                        DisplayString,
                    paramServerEntryStatus
                        INTEGER,
                    paramServerAddressType
                        AddressType,
                    paramServerAddress
                        OCTET STRING,
                    paramServerStoredVersion
                        INTEGER,
                    paramServerStoredTime
                        DateTime,
                    paramServerStoredStatus
                        INTEGER,
                    paramServerStoredFailure
                        INTEGER
                }

            paramServerName OBJECT-TYPE
                SYNTAX DisplayString (SIZE (16))
                ACCESS read-only
                STATUS mandatory
                DESCRIPTION
                    "The server's name, unique within this system.  
                    Always 16 characters, null padded on the end.  
                    Corresponds directly to the name used to create the 
                    entry and the value labeled 'Name' in the PARAMETER 
                    SERVER display."
                ::= { paramServerEntry 1 }

            paramServerEntryStatus OBJECT-TYPE
                SYNTAX INTEGER { invalid(1), valid(2) }
                ACCESS read-write
                STATUS mandatory
                DESCRIPTION
                    "The status of the entry.  Set to 'invalid' to 
                    remove the entry, which corresponds directly to the 
                    CLEAR/PURGE PARAMETER SERVER command.  Actual 
                    removal of the entry is implementation specific."
                DEFVAL { valid }
                ::= { paramServerEntry 2 }

            paramServerAddressType OBJECT-TYPE
                SYNTAX AddressType
                ACCESS read-write
                STATUS mandatory
                DESCRIPTION
                    "The type of network address contained in 
                    paramServerAddress.  'unknown' means no address has 
                    been defined.  'other' means no other type value 
                    applies.  'local' means there is no address and 
                    parameters were loaded from local storage.  'ip' is 
                    an Internet IP address.  'ethernet' is an 802.3 MAC 
                    address.  Corresponds indirectly to the value 
                    labeled 'Address' in the PARAMETER SERVER display."
                DEFVAL { unknown }
                ::= { paramServerEntry 3 }

            paramServerAddress OBJECT-TYPE
                SYNTAX OCTET STRING
                ACCESS read-write
                STATUS mandatory
                DESCRIPTION
                    "The server's network address.  Corresponds directly 
                    to the value labeled 'Address' in the PARAMETER 
                    SERVER display."
                DEFVAL { "" }  -- zero length
                ::= { paramServerEntry 4 }

            paramServerStoredVersion OBJECT-TYPE
                SYNTAX INTEGER
                ACCESS read-only
                STATUS mandatory
                DESCRIPTION
                    "Parameter version number currently stored at the 
                    server.  Corresponds directly to the value labeled 
                    'Version' in the PARAMETER SERVER display."
                DEFVAL { 0 }
                ::= { paramServerEntry 5 }

            paramServerStoredTime OBJECT-TYPE
                SYNTAX DateTime
                ACCESS read-only
                STATUS mandatory
                DESCRIPTION
                    "The server's date and time when it stored the 
                    parameters of version paramServerStoredVersion.  
                    Corresponds directly to the value labeled 'Date' in 
                    the PARAMETER SERVER display."
                DEFVAL { '00'h }
                ::= { paramServerEntry 6 }

            paramServerStoredStatus OBJECT-TYPE
                SYNTAX INTEGER { unknown(1), current(2), ahead(3),
                                 behind(4), failing(5), failed(6),
                                 query(7), noMemCard(8) }
                ACCESS read-only
                STATUS mandatory
                DESCRIPTION
                    "Status of this system's parameters with respect to 
                    the server.  Corresponds directly to the value 
                    labeled 'Status' in the PARAMETER SERVER display.  
                    The value meanings are:

                    ahead     server version newer than system's
                    behind    server version older than system's
                    current   up to date
                    failed    system no longer attempting update
                    failing   system trying to update but failing
                    query     attempting to determine version
                    noMemCard no memory card in card drive
                    unknown   version not known
                    "
                DEFVAL { unknown }
                ::= { paramServerEntry 7 }

            paramServerStoredFailure OBJECT-TYPE
                SYNTAX INTEGER { other(1), none(2), protocolOut(3),
                                 open(4), read(5), write(6), 
            resource(7),
                                 protocolIn(8), response(9),
                                 close(10), delete(11), rename(12),
                                 fileData(13) }
                ACCESS read-only
                STATUS mandatory
                DESCRIPTION
                    "When paramServerStoredStatus is 'failed' or 
                    'failing', the reason for the most recent failure.  
                    Corresponds directly to the value labeled 'Reason' 
                    in the PARAMETER SERVER display.  The value meanings 
                    are:

                    other        none of the following
                    none         no failure
                    protocolOut  invalid protocol message to server
                    open         file open error at server
                    read         file read error at server
                    write        file write error at server
                    resource     resource lack at server (e.g. disk)
                    protocolIn   invalid protocol message from server
                    response     no response from server
                    close        file close error at server
                    delete       file delete error at server
                    rename       file rename error at server
                    fileData     bad parameter data stored at server
                    "
                DEFVAL { none }
                ::= { paramServerEntry 8 }


            -- Additional individual parameters

            paramClientPath OBJECT-TYPE
                SYNTAX DisplayString (SIZE (0..40))
                ACCESS read-write
                STATUS mandatory
                DESCRIPTION
                    "The directory path to the parameter file on all 
                    servers.  Corresponds directly to PARAMETER SERVER 
                    PATH and the value labeled 'Path:' in the PARAMETER 
                    SERVER display."
                ::= { xParamClient 17 }

            paramClientChassisStorageState OBJECT-TYPE
                SYNTAX INTEGER { notApplicable(1), unknown(2),
                                 current(3), verifying(4),
                                 busBusy(5), retrying(6),
                                 failing(7), behind(8) }
                ACCESS read-only
                STATUS mandatory
                DESCRIPTION
                    "The status of the current attempt to update 
                    parameters in local chassis storage.  Corresponds 
                    directly to the value labeled 'Chassis 
                    Configuration:'."
                ::= { xParamClient 18 }

            paramClientTftpBroadcast OBJECT-TYPE
                SYNTAX INTEGER { disabled(1), enabled(2) }
                ACCESS read-write
                STATUS mandatory
                DESCRIPTION
                    "Control over whether or not this system is allowed 
                    to send out a TFTP read broadcast after sending
                    a BOOTP broadcast during the Parameter Check Function.
                    'enabled' allows TFTP broadcast.  Corresponds directly to 
                    the presence of PARAMETER TFTP BROADCAST
                    under the label 'Enabled Characteristics' in 
                    the SERVER CHARACTERISTICS display."
                DEFVAL { enabled }
                ::= { xParamClient 20 }

            paramClientWriteNow OBJECT-TYPE
                SYNTAX INTEGER { ready(1), execute(2) }
                ACCESS read-write
                STATUS mandatory
                DESCRIPTION
                   "Control to start saving parameters immediately in
                    response to an execute. Corresponds directly to the WRITE
                    PARAMETERS command. In response to a get-request or
                    get-next-request, the agent always returns 'ready' for
                    this value."
                ::= { xParamClient 21 }   



--
-- FILE: /users/sse/mibs/src/itouch/it-repeater-mib.mib
--

-- $Id: it-repeater-mib.mib,v 1.3 2001/07/25 15:14:53 sse Exp $


            hubDeprecated   OBJECT IDENTIFIER ::= { iTouch 9 }
            xRepeater       OBJECT IDENTIFIER ::= { iTouch 17 }

            -- MIB Groups

            xRepeaterInfo       OBJECT IDENTIFIER ::= { xRepeater 1 }
            xRepeaterGroupInfo  OBJECT IDENTIFIER ::= { xRepeater 2 }
            xRepeaterPortInfo   OBJECT IDENTIFIER ::= { xRepeater 3 }
            xRepeaterSlotInfo   OBJECT IDENTIFIER ::= { xRepeater 4 }
            xRepeaterSecurity   OBJECT IDENTIFIER ::= { xRepeater 5 }
            xRepeaterRepeater   OBJECT IDENTIFIER ::= { xRepeater 6 }
            xRepeaterRedundancy OBJECT IDENTIFIER ::= { xRepeater 7 }

            -- This is a MIB module for all iTouch Ethernet repeaters.

            -- Copyright 2000 iTouch Communications, Inc. All Rights Reserved.
            -- Reproduction of this document is authorized on
            -- condition that this copyright notice is included.
            -- This MIB document embodies iTouch Communications, Inc.'s 
            -- proprietary intellectual property.  iTouch Communications, Inc.
            -- retains all title and ownership in this MIB, including any
            -- revisions.
            --
            -- It is iTouch Communications, Inc.'s intent to encourage the
            -- widespread use of this MIB in connection with the management of
            -- iTouch Communications, Inc. products. iTouch Communications,
            -- Inc. grants vendors,end-users, and other interested parties a
            -- non-exclusive license to use this MIB in connection with the
            -- management of iTouch Communications, Inc. products.
            --
            -- This MIB document is supplied "AS IS," and iTouch 
            -- Communications, Inc. makes no warranty, either express or
            -- implied, as to the use operation, condition, or performance of
            -- the MIB.


            -- Textual Conventions

            Segment ::=
                INTEGER { a(1), b(2), c(3), d(4), e(5), f(6), g(7),
                          h(8), i(9), j(10), k(11), l(12), m(13),
                          n(14), o(15), p(16), q(17), r(18), s(19),
                          t(20), u(21), v(22), w(23), x(24), y(25),
                          z(26), disabled(27), notApplicable(28) }
            -- This data type is used in the ITouch Repeater MIB
            -- to identify a Network 9000 network segment.  Except
            -- for the final two values, it is the same as the
            -- ITouch Chassis MIB convention named Letter.

            Repeater ::=
                INTEGER { notApplicable(1), repeater1(2),
                                 repeater2(3), repeater3(4) }
            -- This data type is used in the ITouch Repeater MIB to
            -- identify a logical repeater in repeaters that implement
            -- non-proxy management for logical repeaters.


            -- the Repeater Basic Information group

            -- Implementation of this group is mandatory for all ITouch
            -- Ethernet repeaters that support SNMP management

            repeaterAccessViolation OBJECT-TYPE
                SYNTAX INTEGER { both(1), disable(2), trap(3) }
                ACCESS read-write
                STATUS mandatory
                DESCRIPTION
                    "Controls action to take when an access violation 
                    occurs."
                DEFVAL { disable }
                ::= { xRepeaterInfo 1 }

            repeaterMyGroup OBJECT-TYPE
                SYNTAX INTEGER
                ACCESS read-only
                STATUS mandatory
                DESCRIPTION
                    "The index value of the group that is directly 
                    associated with the agent.  The snmp support for the 
                    group associated with the agent is a superset of the 
                    support for other groups."
                ::= { xRepeaterInfo 2 }

            repeaterFifoOverflows OBJECT-TYPE
                SYNTAX Counter
                ACCESS read-only
                STATUS deprecated
                DESCRIPTION
                    "Deprecated, use repeaterRepeaterFifoOverflows in the
                     repeaterRepeater group for the desired repeater."
                ::= { xRepeaterInfo 3 }

            repeaterLEDDisplay OBJECT-TYPE
                SYNTAX INTEGER { activity(1), collisions(2) }
                ACCESS read-write
                STATUS mandatory
                DESCRIPTION
                    "Controls reason for flashing front panel LEDs."
                DEFVAL { activity }
                ::= { xRepeaterInfo 4 }

            repeaterReports OBJECT-TYPE
                SYNTAX INTEGER { disabled(1), enabled(2) }
                ACCESS read-write
                STATUS deprecated
                DESCRIPTION
                    "Deprecated, use repeaterRepeaterReports in the
                     repeaterRepeater group for the desired repeater on
                     which report generation is to be controlled."
                DEFVAL { enabled }
                ::= { xRepeaterInfo 5 }

            repeaterHealthTrap OBJECT-TYPE
                SYNTAX INTEGER { disabled(1), enabled(2) }
                ACCESS read-write
                STATUS mandatory
                DESCRIPTION
                    "Controls the generation of the repeater health trap."
                DEFVAL { enabled }
                ::= { xRepeaterInfo 6 }

            repeaterStatusChangeTrap OBJECT-TYPE
                SYNTAX INTEGER { disabled(1), enabled(2) }
                ACCESS read-write
                STATUS mandatory
                DESCRIPTION
                    "Controls the generation of the repeater status change
                    trap."
                DEFVAL { enabled }
                ::= { xRepeaterInfo 7 }

            repeaterAccessViolationTrap OBJECT-TYPE
                SYNTAX INTEGER { disabled(1), enabled(2) }
                ACCESS read-write
                STATUS mandatory
                DESCRIPTION
                    "Controls the generation of the repeater access
                    violation trap."
                DEFVAL { enabled }
                ::= { xRepeaterInfo 8 }

            repeaterIntegrityLossTrap OBJECT-TYPE
                SYNTAX INTEGER { disabled(1), enabled(2) }
                ACCESS read-write
                STATUS mandatory
                DESCRIPTION
                    "Controls the generation of the repeater integrity
                    loss trap."
                DEFVAL { disabled }
                ::= { xRepeaterInfo 9 }

            repeaterRedundancyPathChangeTrap OBJECT-TYPE
                SYNTAX INTEGER { disabled(1), enabled(2) }
                ACCESS read-write
                STATUS mandatory
                DESCRIPTION
                    "Controls the generation of the repeater redundancy
					path change trap."
                DEFVAL { enabled }
                ::= { xRepeaterInfo 10 }


            -- the Repeater Group group

            -- Implementation of this group is mandatory for all ITouch
            -- Ethernet repeaters that support SNMP management

            -- the Group table

            repeaterGroupTable OBJECT-TYPE
                SYNTAX SEQUENCE OF RepeaterGroupEntry
                ACCESS not-accessible
                STATUS mandatory
                DESCRIPTION
                    "Table of descriptive and status information about 
                    the groups."
                ::= { xRepeaterGroupInfo 1 }

            repeaterGroupEntry OBJECT-TYPE
                SYNTAX RepeaterGroupEntry
                ACCESS not-accessible
                STATUS mandatory
                DESCRIPTION
                    "An entry in the table, containing information about 
                    a group."
                INDEX { repeaterGroupIndex }
                ::= { repeaterGroupTable 1 }

            RepeaterGroupEntry ::=
                SEQUENCE {
                    repeaterGroupIndex
                        INTEGER,
                    repeaterGroupSQE
                        Counter,
                    repeaterGroupJabbers
                        Counter,
                    repeaterGroupSegment
                        Segment,
                    repeaterGroupSecurityLock
                        INTEGER,
                    repeaterGroupIOCardType
                        INTEGER,
                    repeaterGroupIOCardFirmwareVersion
                        INTEGER,
                    repeaterGroupIOCardOperStatus
                        INTEGER,
                    repeaterGroupManagement
                        INTEGER,
                    repeaterGroupRepeaterNumber
                        INTEGER,
                    repeaterGroupRepeaterHardwareVersion
                        INTEGER,
                    repeaterGroupManagerRepeater
                        Repeater,
                    repeaterGroupFifoErrors
                        Counter,
                    repeaterGroupCpuUtilization
                        INTEGER,
                    repeaterGroupMemoryUtilization
                        INTEGER,
                    repeaterGroupAlarmCount
                        INTEGER
                }

            repeaterGroupIndex OBJECT-TYPE
                SYNTAX INTEGER
                ACCESS read-only
                STATUS mandatory
                DESCRIPTION
                    "This variable identifies the group within the  
                    repeater for which this entry contains information.  
                    This value is the same as  rptrGroupIndex."
                ::= { repeaterGroupEntry 1 }

            repeaterGroupSQE OBJECT-TYPE
                SYNTAX Counter
                ACCESS read-only
                STATUS deprecated
                DESCRIPTION
                    "Deprecated, use repeaterRepeaterSQE in the
                     repeaterRepeaterGroup for the SQE count on the
                     desired repeater.  This object will always return
                     the count for repeater #1."
                ::= { repeaterGroupEntry 2 }

            repeaterGroupJabbers OBJECT-TYPE
                SYNTAX Counter
                ACCESS read-only
                STATUS deprecated
                DESCRIPTION
                    "Deprecated, use repeaterRepeaterJabbers in the
                     repeaterRepeaterGroup for the Jabber count on the
                     desired repeater.  This object will always return
                     the count for repeater #1."
                ::= { repeaterGroupEntry 3 }

            repeaterGroupSegment OBJECT-TYPE
                SYNTAX Segment
                ACCESS read-write
                STATUS deprecated
                DESCRIPTION
                    "Deprecated, use repeaterRepeaterSegment in the
                     repeaterRepeaterGroup to control the segment
                     mapping for the desired repeater.  This object will
                     always control the mapping for repeater #1."
                ::= { repeaterGroupEntry 4 }

            repeaterGroupSecurityLock OBJECT-TYPE
                SYNTAX INTEGER { unlocked(1), locked(2) }
                ACCESS read-write
                STATUS mandatory
                DESCRIPTION
                    "This variable indicates the state of security 
                    lockdown on an unmanaged repeater.  The only 
                    writable value is 'unlocked'."
                ::= { repeaterGroupEntry 5 }

            repeaterGroupIOCardType OBJECT-TYPE
                SYNTAX INTEGER
                ACCESS read-only
                STATUS mandatory
                DESCRIPTION
                    "The hardware type of the I/O card, as defined in 
                    ITouch Assigned Numbers."
                ::= { repeaterGroupEntry 6 }

            repeaterGroupIOCardFirmwareVersion OBJECT-TYPE
                SYNTAX INTEGER
                ACCESS read-only
                STATUS mandatory
                DESCRIPTION
                    "The firmware revision level of the I/O card ROM."
                ::= { repeaterGroupEntry 7 }

            repeaterGroupIOCardOperStatus OBJECT-TYPE
                SYNTAX INTEGER { loadRequested(1),
                                 loading(2),
                                 dumpRequested(3),
                                 dumping(4),
                                 paramRequested(5),
                                 paramLoading(6),
                                 running(7),
                                 initializing(8),     -- ROM wait
                                 attended(9),         -- in config menu
                                 internal10(10),      -- read chas info
                                 internal11(11),      -- read config
                                 inhibited(12),       -- run inhibited
                                 maxserverCard(13),
                                 invalidConfigStorage(14), -- suspended
                                 securityLockdown(15) }
                ACCESS read-only
                STATUS mandatory
                DESCRIPTION
                    "Relative to the chassis, the current operating 
                    status of the I/O card."
                ::= { repeaterGroupEntry 8 }

            repeaterGroupManagement OBJECT-TYPE
                SYNTAX INTEGER { minimal(1), full(2) }
                ACCESS read-only
                STATUS mandatory
                DESCRIPTION
                    "This variable indicates the level of management 
                    control and observation available."
                ::= { repeaterGroupEntry 9 }

            repeaterGroupRepeaterNumber OBJECT-TYPE
                SYNTAX INTEGER
                ACCESS read-only
                STATUS mandatory
                DESCRIPTION
                    "The number of logical repeaters visible via this 
                    repeater."
                ::= { repeaterGroupEntry 10 }

            repeaterGroupRepeaterHardwareVersion OBJECT-TYPE
                SYNTAX INTEGER
                ACCESS read-only
                STATUS mandatory
                DESCRIPTION
                    "The repeater chip set hardware revision level."
                ::= { repeaterGroupEntry 11 }

            repeaterGroupManagerRepeater OBJECT-TYPE
                SYNTAX Repeater
                ACCESS read-write
                STATUS mandatory
                DESCRIPTION
                    "The logical repeater to which the manager card, if 
                    present, is attached."
                ::= { repeaterGroupEntry 12 }

            repeaterGroupFifoErrors OBJECT-TYPE
                SYNTAX Counter
                ACCESS read-only
                STATUS mandatory
                DESCRIPTION
                    "This variable will reflect the number of times that the report
                    FIFO has gone out of synchronization."
                ::= { repeaterGroupEntry 13 }

            repeaterGroupCpuUtilization OBJECT-TYPE
                SYNTAX INTEGER (0..10000)
                ACCESS read-only
                STATUS mandatory
                DESCRIPTION
                    "The average CPU utilization for the processor which
                    maintains statistics and implements monitoring for the
                    group, expressed as percentage times 100."
                ::= { repeaterGroupEntry 14 }

            repeaterGroupMemoryUtilization OBJECT-TYPE
                SYNTAX INTEGER (0..10000)
                ACCESS read-only
                STATUS mandatory
                DESCRIPTION
                    "The current memory utilization for the processor which
                    maintains statistics and implements monitoring for the
                    group, expressed as percentage used times 100."
                ::= { repeaterGroupEntry 15 }

            repeaterGroupAlarmCount OBJECT-TYPE
                SYNTAX INTEGER
                ACCESS read-only
                STATUS mandatory
                DESCRIPTION
                    "The number of alarms currently being monitored by the
                    processor for comparison with RMON thresholds."
                ::= { repeaterGroupEntry 16 }


            -- the Repeater Port group

            -- Implementation of this group is mandatory for all ITouch
            -- Ethernet repeaters that support SNMP management

            -- the Port table

            repeaterPortTable OBJECT-TYPE
                SYNTAX SEQUENCE OF RepeaterPortEntry
                ACCESS not-accessible
                STATUS mandatory
                DESCRIPTION
                    "Table of descriptive and status information about 
                    the ports."
                ::= { xRepeaterPortInfo 1 }

            repeaterPortEntry OBJECT-TYPE
                SYNTAX RepeaterPortEntry
                ACCESS not-accessible
                STATUS mandatory
                DESCRIPTION
                    "An entry in the table, containing information about 
                    a port."
                INDEX { repeaterPortGroupIndex, repeaterPortIndex }
                ::= { repeaterPortTable 1 }

            RepeaterPortEntry ::=
                SEQUENCE {
                    repeaterPortGroupIndex
                        INTEGER,
                    repeaterPortIndex
                        INTEGER,
                    repeaterPortName
                        DisplayString,
                    repeaterPortAutoPolarity
                        INTEGER,
                    repeaterPortPolarityDirection
                        INTEGER,
                    repeaterPortPulse
                        INTEGER,
                    repeaterPortPulseStatus
                        INTEGER,
                    repeaterPortPulseLosses
                        Counter,
                    repeaterPortDistance
                        INTEGER,
                    repeaterPortSofMissing
                        Counter,
                    repeaterPortMCVs
                        Counter,
                    repeaterPortZero
                        INTEGER,
                    repeaterPortSinceZero
                        TimeTicks,
                    repeaterPortAccessAction
                        INTEGER,
                    repeaterPortAccessState
                        INTEGER,
                    repeaterPortAccessType
                        INTEGER,
                    repeaterPortAccessAllStatus
                        INTEGER,
                    repeaterPortPortLastViolationAddress
                        MacAddress,
                    repeaterPortPortAddressViolations
                        Counter,
                    repeaterPortSegment
                        Segment,
                    repeaterPortAccessLearn
                        INTEGER,
                    repeaterPortEthernetRepeater
                        INTEGER,
                    repeaterPortRepeatersAllowed
                        OCTET STRING,
                    repeaterPortGlobalSecurityAddress
                        MacAddress,
                    repeaterPortGlobalAddressChanges
                        Counter,
                    repeaterPortPercentUtilization
                        Gauge
                }

            repeaterPortGroupIndex OBJECT-TYPE
                SYNTAX INTEGER
                ACCESS read-only
                STATUS mandatory
                DESCRIPTION
                    "This variable identifies the group containing the 
                    port for which this entry contains infromation."
                ::= { repeaterPortEntry 1 }

            repeaterPortIndex OBJECT-TYPE
                SYNTAX INTEGER
                ACCESS read-only
                STATUS mandatory
                DESCRIPTION
                    "This variable identifies the port within the group 
                    within the repeater for which this entry contains 
                    management information.  This value can never be 
                    greater than rptrGroupPortCapacity for the 
                    associated group."
                ::= { repeaterPortEntry 2 }

            repeaterPortName OBJECT-TYPE
                SYNTAX DisplayString (SIZE (0..16))
                ACCESS read-write
                STATUS mandatory
                DESCRIPTION
                    "The port's display name."
                ::= { repeaterPortEntry 3 }

            repeaterPortAutoPolarity OBJECT-TYPE
                SYNTAX INTEGER { disabled(1), enabled(2) }
                ACCESS read-write
                STATUS mandatory
                DESCRIPTION
                    "Controls whether the port will automatically 
                    determine  its polarity."
                DEFVAL { enabled }
                ::= { repeaterPortEntry 4 }

            repeaterPortPolarityDirection OBJECT-TYPE
                SYNTAX INTEGER { reversed(1), normal(2), unknown(3) }
                ACCESS read-only
                STATUS mandatory
                DESCRIPTION
                    "If repeaterPortAutoPolarity is enabled, this is the 
                    current polarity of the port."
                ::= { repeaterPortEntry 5 }

            repeaterPortPulse OBJECT-TYPE
                SYNTAX INTEGER { disabled(1), enabled(2) }
                ACCESS read-write
                STATUS mandatory
                DESCRIPTION
                    "Controls whether the port will periodically 
                    generate a test pulse to determine the status of the 
                    port."
                DEFVAL { enabled }
                ::= { repeaterPortEntry 6 }

            repeaterPortPulseStatus OBJECT-TYPE
                SYNTAX INTEGER { notDetected(1), detected(2) }
                ACCESS read-only
                STATUS mandatory
                DESCRIPTION
                    "If repeaterPortPulse is enabled, this is indicates 
                    whether the test pulse response is being detected."
                ::= { repeaterPortEntry 7 }

            repeaterPortPulseLosses OBJECT-TYPE
                SYNTAX Counter
                ACCESS read-only
                STATUS mandatory
                DESCRIPTION
                    "The number of times that a test pulse has been sent  
                    and a response was not received."
                ::= { repeaterPortEntry 8 }

            repeaterPortDistance OBJECT-TYPE
                SYNTAX INTEGER { disabled(1), enabled(2) }
                ACCESS read-write
                STATUS mandatory
                DESCRIPTION
                    "Controls whether the port will support extended 
                    distances on the port."
                DEFVAL { enabled }
                ::= { repeaterPortEntry 9 }

            repeaterPortSofMissing OBJECT-TYPE
                SYNTAX Counter
                ACCESS read-only
                STATUS mandatory
                DESCRIPTION
                    "The number of times that alternating zero/one bits 
                    were seen after an inter-packet gap and were not 
                    followed by two one bits."
                ::= { repeaterPortEntry 10 }

            repeaterPortMCVs OBJECT-TYPE
                SYNTAX Counter
                ACCESS read-only
                STATUS mandatory
                DESCRIPTION
                    "The number of manchester violation errors detected 
                    on this port."
                ::= { repeaterPortEntry 11 }

            repeaterPortZero OBJECT-TYPE
                SYNTAX INTEGER { ready(1), execute(2) }
                ACCESS read-write
                STATUS mandatory
                DESCRIPTION
                    "Control to zero the hub port's counters.  The agent 
                    always returns 'ready' for this value.  Setting the 
                    value to 'ready' has no effect."
                ::= { repeaterPortEntry 12 }

            repeaterPortSinceZero OBJECT-TYPE
                SYNTAX TimeTicks
                ACCESS read-only
                STATUS mandatory
                DESCRIPTION
                    "Number of time ticks since the port's counters were 
                    zeroed."
                ::= { repeaterPortEntry 13 }

            repeaterPortAccessAction OBJECT-TYPE
                SYNTAX INTEGER { discard(1), accept(2) }
                ACCESS read-write
                STATUS mandatory
                DESCRIPTION
                    "Control whether packets will be accepted or 
                    discarded if they are in the access list.  The 
                    inverse action is applied to packets from all 
                    addresses not in the list."
                DEFVAL { discard }
                ::= { repeaterPortEntry 14 }

            repeaterPortAccessState OBJECT-TYPE
                SYNTAX INTEGER { disabled(1), notDisabled(2) }
                ACCESS read-only 
                STATUS mandatory
                DESCRIPTION
                    "Indicates whether the port was disabled due to 
                    receiving a frame from an invalid source address."
                ::= { repeaterPortEntry 15 }

            repeaterPortAccessType OBJECT-TYPE
                SYNTAX INTEGER { tenBaseT(1), aui(2), foirl(3),
                                 mac(4), lanbus(5), tenBase2(6),
                                 tenBaseFL(7) }
                ACCESS read-only 
                STATUS mandatory
                DESCRIPTION
                    "Indicates the type of the port."
                ::= { repeaterPortEntry 16 }

            repeaterPortAccessAllStatus OBJECT-TYPE
                SYNTAX INTEGER { invalid(1), valid(2) }
                ACCESS read-write
                STATUS mandatory
                DESCRIPTION
                    "Setting this field to invalid will delete all 
                    access addresses associated with this port. Setting 
                    this field to valid has no effect."
                ::= { repeaterPortEntry 17 }

            repeaterPortPortLastViolationAddress OBJECT-TYPE
                SYNTAX MacAddress
                ACCESS read-only
                STATUS mandatory
                DESCRIPTION
                    "Address that last caused an access violation."
                ::= { repeaterPortEntry 18 }

            repeaterPortPortAddressViolations OBJECT-TYPE
                SYNTAX Counter
                ACCESS read-only
                STATUS mandatory
                DESCRIPTION
                    "Number of access violations."
                ::= { repeaterPortEntry 19 }

            repeaterPortSegment OBJECT-TYPE
                SYNTAX Segment
                ACCESS read-only
                STATUS mandatory
                DESCRIPTION
                    "Returns the indirect mapping of the ethernet repeater
                     to which this port is connected."
                ::= { repeaterPortEntry 20 }

            repeaterPortAccessLearn OBJECT-TYPE
                SYNTAX INTEGER { disabled(1), single(2), continuous(3) }
                ACCESS read-write
                STATUS mandatory
                DESCRIPTION
                    "Controls how the port will learn the source 
                    addresses that can come in on the port."
                DEFVAL { disabled }
                ::= { repeaterPortEntry 21 }

            repeaterPortEthernetRepeater OBJECT-TYPE
                SYNTAX INTEGER { repeater1 (1), repeater2 (2), repeater3 (3) }
                ACCESS read-write
                STATUS mandatory
                DESCRIPTION
                    "For repeaters that implement non-proxy management 
                    of logical repeaters, this variable selects the 
                    logical Ethernet repeater to which the port is 
                    attached."
                ::= { repeaterPortEntry 22 }

            repeaterPortRepeatersAllowed OBJECT-TYPE
                SYNTAX OCTET STRING
                ACCESS read-only
                STATUS mandatory
                DESCRIPTION
                    "The list of repeaters to which this port can be 
                    attached.  The OCTET STRING contains a bitmap, with 
                    a bit for 'none' and one bit for each repeater, and 
                    enough octets for all the repeaters on the device.  
                    The high order bit of the first octet corresponds to 
                    'none', the following bits correspond to the 
                    repeaters, in order, beginning with 1."
                ::= { repeaterPortEntry 23 }

            repeaterPortGlobalSecurityAddress OBJECT-TYPE
                SYNTAX MacAddress
                ACCESS read-only
                STATUS mandatory
                DESCRIPTION
                    "This variable represents the global address which is
                    currently applied to the port."
                ::= { repeaterPortEntry 24 }

            repeaterPortGlobalAddressChanges OBJECT-TYPE
                SYNTAX    Counter
                ACCESS    read-only
                STATUS    mandatory
                DESCRIPTION
                    "This variable represents the number of times since
                    counters have been zeroed, that a global address
                    change occured on the port."
                ::= { repeaterPortEntry 25 }

            repeaterPortPercentUtilization OBJECT-TYPE
                SYNTAX Gauge
                ACCESS read-only
                STATUS mandatory
                DESCRIPTION
                    "This variable will reflect the percentage of a full
                    ethernet load that this port has received since last
                    zeroed.  The value is calculated as
                    '(8(bytesReceived + (20*framesReceived))) /107(time)'."
                ::= { repeaterPortEntry 26 }

            -- More scalars follow Port Access Table

            -- the Port Access table

            repeaterPortAccessTable OBJECT-TYPE
                SYNTAX SEQUENCE OF RepeaterPortAccessEntry
                ACCESS not-accessible
                STATUS mandatory
                DESCRIPTION
                    "Table of access control for the ports."
                ::= { xRepeaterPortInfo 2 }

            repeaterPortAccessEntry OBJECT-TYPE
                SYNTAX RepeaterPortAccessEntry
                ACCESS not-accessible
                STATUS mandatory
                DESCRIPTION
                    "An entry in the table, containing access 
                    information about a port."
                INDEX { repeaterPortAccessGroupIndex,
                        repeaterPortAccessPortIndex,
                        repeaterPortAccessAddress }
                ::= { repeaterPortAccessTable 1 }

            RepeaterPortAccessEntry ::=
                SEQUENCE {
                    repeaterPortAccessGroupIndex
                        INTEGER,
                    repeaterPortAccessPortIndex
                        INTEGER,
                    repeaterPortAccessAddress
                        MacAddress,
                    repeaterPortAccessStatus
                        INTEGER
                }

            repeaterPortAccessGroupIndex OBJECT-TYPE
                SYNTAX INTEGER
                ACCESS read-only
                STATUS mandatory
                DESCRIPTION
                    "This variable identifies the group containing the
                    access entry for which this entry contains information.
                    The group ID may only be that of the target agent.
                    Specifying a group ID of an agent in a different slot
                    will result in `badValue` being returned."
                ::= { repeaterPortAccessEntry 1 }

            repeaterPortAccessPortIndex OBJECT-TYPE
                SYNTAX INTEGER
                ACCESS read-only
                STATUS mandatory
                DESCRIPTION
                    "This variable identifies the port containing the
                    access entry for which this entry contains information."
                ::= { repeaterPortAccessEntry 2 }

            repeaterPortAccessAddress OBJECT-TYPE
                SYNTAX MacAddress
                ACCESS read-only
                STATUS mandatory
                DESCRIPTION
                    "This value will be compared to the source address of
                    all packets received on the port in applying the access
                    action"
                ::= { repeaterPortAccessEntry 3 }

            repeaterPortAccessStatus OBJECT-TYPE
                SYNTAX INTEGER { invalid(1), valid(2) }
                ACCESS read-write
                STATUS mandatory
                DESCRIPTION
                    "The status of the entry.  Set to 'invalid' to 
                    remove the rule."
                ::= { repeaterPortAccessEntry 4 }

            -- Additional Repeater Info scalars

            repeaterPortAccessGroupIndexShadow OBJECT-TYPE
                SYNTAX INTEGER
                ACCESS read-write
                STATUS mandatory
                DESCRIPTION
                    "This variable identifies the group which contains a
                    port to which an access address is to be assigned.  The
                    group ID may only be that of the target agent.  Specifying
                    a group ID of an agent in a different slot will result in
                    `badValue` being returned."
                ::= { xRepeaterPortInfo 3 }
            
            repeaterPortAccessPortIndexShadow OBJECT-TYPE
                SYNTAX INTEGER
                ACCESS read-write
                STATUS mandatory
                DESCRIPTION
                    "This variable identifies the port of a group to which
                    an access address is to be assigned."
                ::= { xRepeaterPortInfo 4 }
            
            repeaterPortAccessAddressShadow OBJECT-TYPE
                SYNTAX MacAddress
                ACCESS read-write
                STATUS mandatory
                DESCRIPTION
                    "This value contains the ethernet address which is to be
                    added to the access address table for the port specified
                    by repeaterPortAccessGroupIndexShadow and
                    repeaterPortAccessPortIndexShadow."
                ::= { xRepeaterPortInfo 5 }
            
            repeaterPortAccessStatusShadow OBJECT-TYPE
                SYNTAX INTEGER { ready(1), execute(2) }
                ACCESS read-write
                STATUS mandatory
                DESCRIPTION
                     "When read, this variable will always return 'ready'.  When
                     this variable is set to 'execute' the address specified by
                     repeaterPortAccessAddressShadow will be added to the access
                     address table for the port specified by
                     repeaterPortAccessGroupIndexShadow and
                     repeaterPortAccessPortIndexShadow.  If any of the above
                     variables are zero when this object is set to 'execute',
                     'bad value' will be returned."
                DEFVAL { ready }
                ::= { xRepeaterPortInfo 6 }

            -- extensions to the Port table

            repeaterPort2Table OBJECT-TYPE
                SYNTAX SEQUENCE OF RepeaterPort2Entry
                ACCESS not-accessible
                STATUS mandatory
                DESCRIPTION
                    "Table of more descriptive and status information
                     about the ports."
                ::= { xRepeaterPortInfo 7 }

            repeaterPort2Entry OBJECT-TYPE
                SYNTAX RepeaterPort2Entry
                ACCESS not-accessible
                STATUS mandatory
                DESCRIPTION
                    "An entry in the table, containing information about 
                    a port.  Index is identical to repeaterPortTable."
                INDEX { repeaterPortGroupIndex, repeaterPortIndex }
                ::= { repeaterPort2Table 1 }

            RepeaterPort2Entry ::=
                SEQUENCE {
                    repeaterPort2RmonOctets
                        Counter,
                    repeaterPort2RmonPkts
                        Counter,
                    repeaterPort2RmonBroadcastPkts
                        Counter,
                    repeaterPort2RmonMulticastPkts
                        Counter,
                    repeaterPort2RmonCRCAlignErrors
                        Counter,
                    repeaterPort2RmonPkts64Octets
                        Counter,
                    repeaterPort2RmonPkts65to127Octets
                        Counter,
                    repeaterPort2RmonPkts128to255Octets
                        Counter,
                    repeaterPort2RmonPkts256to511Octets
                        Counter,
                    repeaterPort2RmonPkts512to1023Octets
                        Counter,
                    repeaterPort2RmonPkts1024to1518Octets
                        Counter,
                    repeaterPort2TrafficRatio
                        INTEGER,
                    repeaterPort2CollisionRatio
                        INTEGER,
                    repeaterPort2ErrorRatio
                        INTEGER,
                    repeaterPort2BroadcastRatio
                        INTEGER,
                    repeaterPort2MulticastRatio
                        INTEGER,
                    repeaterPort2UnicastRatio
                        INTEGER
                }

            repeaterPort2RmonOctets OBJECT-TYPE
                SYNTAX Counter
                ACCESS read-only
                STATUS mandatory
                DESCRIPTION
                    "The total number of octets of data (including
                    those in bad packets) received on the port
                    (excluding framing bits but including FCS octets)."
                ::= { repeaterPort2Entry 1 }

            repeaterPort2RmonPkts OBJECT-TYPE
                  SYNTAX Counter
                  ACCESS read-only
                  STATUS mandatory
                  DESCRIPTION
                    "The total number of packets (including error packets)
                    received on the port."
                ::= { repeaterPort2Entry 2 }

            repeaterPort2RmonBroadcastPkts OBJECT-TYPE
                  SYNTAX Counter
                  ACCESS read-only
                  STATUS mandatory
                  DESCRIPTION
                    "The total number of good packets received on the port
                    that were directed to the broadcast address."
                ::= { repeaterPort2Entry 3 }

            repeaterPort2RmonMulticastPkts OBJECT-TYPE
                SYNTAX Counter
                ACCESS read-only
                STATUS mandatory
                DESCRIPTION
                    "The total number of good packets received on the port
                    that were directed to a multicast address.  Note that
                    this number does not include packets directed to the
                    broadcast address."
                ::= { repeaterPort2Entry 4 }

            repeaterPort2RmonCRCAlignErrors OBJECT-TYPE
                SYNTAX Counter
                ACCESS read-only
                STATUS mandatory
                DESCRIPTION
                    "The total number of packets received on the port that
                    had a length (excluding framing bits, but including
                    FCS octets) of between 64 and 1518 octets, inclusive,
                    but were not an integral number of octets in length or
                    had a bad Frame Check Sequence (FCS)."
                ::= { repeaterPort2Entry 5 }

            repeaterPort2RmonPkts64Octets OBJECT-TYPE
                SYNTAX Counter
                ACCESS read-only
                STATUS mandatory
                DESCRIPTION
                    "The total number of packets (including error packets)
                     received on the port that were 64 octets in length
                    (excluding framing bits but including FCS octets)."
                ::= { repeaterPort2Entry 6 }

            repeaterPort2RmonPkts65to127Octets OBJECT-TYPE
                SYNTAX Counter
                ACCESS read-only
                STATUS mandatory
                DESCRIPTION
                    "The total number of packets (including error packets)
                    received on the port that were between 65 and 127
                    octets in length inclusive (excluding framing bits but
                    including FCS octets)."
                ::= { repeaterPort2Entry 7 }

            repeaterPort2RmonPkts128to255Octets OBJECT-TYPE
                SYNTAX Counter
                ACCESS read-only
                STATUS mandatory
                DESCRIPTION
                    "The total number of packets (including error packets)
                    received on the port that were between 128 and 255
                    octets in length inclusive (excluding framing bits but
                    including FCS octets)."
                ::= { repeaterPort2Entry 8 }

            repeaterPort2RmonPkts256to511Octets OBJECT-TYPE
                SYNTAX Counter
                ACCESS read-only
                STATUS mandatory
                DESCRIPTION
                    "The total number of packets (including error packets)
                    received on the port that were between 256 and 511
                    octets in length inclusive (excluding framing bits but
                    including FCS octets)."
                ::= { repeaterPort2Entry 9 }

            repeaterPort2RmonPkts512to1023Octets OBJECT-TYPE
                SYNTAX Counter
                ACCESS read-only
                STATUS mandatory
                DESCRIPTION
                    "The total number of packets (including error packets)
                    received on the port that were between 512 and 1023
                    octets in length inclusive (excluding framing bits but
                    including FCS octets)."
                ::= { repeaterPort2Entry 10 }

            repeaterPort2RmonPkts1024to1518Octets OBJECT-TYPE
                SYNTAX Counter
                ACCESS read-only
                STATUS mandatory
                DESCRIPTION
                    "The total number of packets (including error packets)
                    received on the port that were between 1024 and 1518
                    octets in length inclusive (excluding framing bits but
                    including FCS octets)."
                ::= { repeaterPort2Entry 11 }

            repeaterPort2TrafficRatio OBJECT-TYPE
                SYNTAX INTEGER (0..10000)
                ACCESS read-only
                STATUS mandatory
                DESCRIPTION
                    "The portion of segment bandwidth used by the port
                    over a 5 second interval, expressed as percentage
                    times 100."
                ::= { repeaterPort2Entry 12 }

            repeaterPort2CollisionRatio OBJECT-TYPE
                SYNTAX INTEGER (0..10000)
                ACCESS read-only
                STATUS mandatory
                DESCRIPTION
                    "The ratio of collisions the port participated in
                    to total packets over a 5 second interval, expressed
                    as percentage times 100."
                ::= { repeaterPort2Entry 13 }

            repeaterPort2ErrorRatio OBJECT-TYPE
                SYNTAX INTEGER (0..10000)
                ACCESS read-only
                STATUS mandatory
                DESCRIPTION
                    "The ratio of total number of error frames on the
                    port to total packets over a 5 second interval,
                    expressed as percentage times 100."
                ::= { repeaterPort2Entry 14 }

            repeaterPort2BroadcastRatio OBJECT-TYPE
                SYNTAX INTEGER (0..10000)
                ACCESS read-only
                STATUS mandatory
                DESCRIPTION
                    "The ratio of good packets directed by the port to the
                    broadcast address to total packets over a 5 second
                    interval, expressed as percentage times 100."
                ::= { repeaterPort2Entry 15 }

            repeaterPort2MulticastRatio OBJECT-TYPE
                SYNTAX INTEGER (0..10000)
                ACCESS read-only
                STATUS mandatory
                DESCRIPTION
                    "The ratio of good packets directed by the port to any
                    multicast address (but not the broadcast address) to
                    total packets over a 5 second interval, expressed as
                    percentage times 100."
                ::= { repeaterPort2Entry 16 }

            repeaterPort2UnicastRatio OBJECT-TYPE
                SYNTAX INTEGER (0..10000)
                ACCESS read-only
                STATUS mandatory
                DESCRIPTION
                    "The ratio of good packets directed by the port to any
                    address other than a multicast or broadcast address to
                    total packets over a 5 second interval, expressed as
                    percentage times 100."
                ::= { repeaterPort2Entry 17 }


            -- the Repeater Slot group

            -- The slot group is deprecated, and there is no replacement
            -- group.

            -- the Slot Segment table

            repeaterSlotSegmentTable OBJECT-TYPE
                SYNTAX SEQUENCE OF RepeaterSlotSegmentEntry
                ACCESS not-accessible
                STATUS deprecated
                DESCRIPTION
                    "Deprecated, no replacement."
                ::= { xRepeaterSlotInfo 1 }

            repeaterSlotSegmentEntry OBJECT-TYPE
                SYNTAX RepeaterSlotSegmentEntry
                ACCESS not-accessible
                STATUS deprecated
                DESCRIPTION
                    "Deprecated, no replacement."
                INDEX { repeaterSlotIndex, repeaterSlotSegment }
                ::= { repeaterSlotSegmentTable 1 }

            RepeaterSlotSegmentEntry ::=
                SEQUENCE {
                    repeaterSlotIndex
                        INTEGER,
                    repeaterSlotSegment
                        Segment,
                    repeaterSlotSegmentStatus
                        INTEGER
                }

            repeaterSlotIndex OBJECT-TYPE
                SYNTAX INTEGER
                ACCESS read-only
                STATUS deprecated
                DESCRIPTION
                    "Deprecated, no replacement."
                ::= { repeaterSlotSegmentEntry 1 }

            repeaterSlotSegment OBJECT-TYPE
                SYNTAX Segment
                ACCESS read-only
                STATUS deprecated
                DESCRIPTION
                    "Deprecated, no replacement."
                ::= { repeaterSlotSegmentEntry 2 }

            repeaterSlotSegmentStatus OBJECT-TYPE
                SYNTAX INTEGER { disabled(1), enabled(2) }
                ACCESS read-write
                STATUS deprecated
                DESCRIPTION
                    "Deprecated, no replacement."
                ::= { repeaterSlotSegmentEntry 3 }


            -- the Repeater Security group

            -- Implementation of this group is mandatory for all ITouch
            -- Ethernet repeaters that support security

            repeaterSecurityState OBJECT-TYPE
                SYNTAX INTEGER { disabled(1), enabled(2) }
                ACCESS read-write
                STATUS mandatory
                DESCRIPTION
                    "Controls whether security operation will be applied 
                    to all ports on the repeater.  If security is not
                    supported by the device, 'badValue' will be returned
                    if the variable is set to 'enabled'."
                DEFVAL { disabled }
                ::= { xRepeaterSecurity 1 }

            -- the Security Port table

            repeaterSecurityPortTable OBJECT-TYPE
                SYNTAX SEQUENCE OF RepeaterSecurityPortEntry
                ACCESS not-accessible
                STATUS mandatory
                DESCRIPTION
                    "Table of descriptive and status information about 
                    the ports."
                ::= { xRepeaterSecurity 2 }

            repeaterSecurityPortEntry OBJECT-TYPE
                SYNTAX RepeaterSecurityPortEntry
                ACCESS not-accessible
                STATUS mandatory
                DESCRIPTION
                    "An entry in the table, containing information about 
                    a port."
                INDEX { repeaterPortGroupIndex, repeaterPortIndex }
                ::= { repeaterSecurityPortTable 1 }

            RepeaterSecurityPortEntry ::=
                SEQUENCE {
                    repeaterSecurityPortUnicast
                        INTEGER,
                    repeaterSecurityPortMulticast
                        INTEGER,
                    repeaterSecurityPortAllStatus
                        INTEGER,
                    repeaterSecurityPortSecurityLearn 
                        INTEGER
                }

            repeaterSecurityPortUnicast OBJECT-TYPE
                SYNTAX INTEGER { jam(1), allow(2) }
                ACCESS read-write
                STATUS mandatory
                DESCRIPTION
                    "The action to take when the destination address is 
                    unicast and does not have an entry in 
                    repeaterSecurityTable.  If repeaterPortGroupIndex is
                    equal to the group number of the agent, this object
                    is read-write, otherwise it is read-only."
                DEFVAL { jam }
                ::= { repeaterSecurityPortEntry 1 }

            repeaterSecurityPortMulticast OBJECT-TYPE
                SYNTAX INTEGER { jam(1), allow(2) }
                ACCESS read-write
                STATUS mandatory
                DESCRIPTION
                    "The action to take when the destination address is 
                    multicast and does not have an entry in 
                    repeaterSecurityTable.  If repeaterPortGroupIndex is
                    equal to the group number of the agent, this object
                    is read-write, otherwise it is read-only"
                DEFVAL { jam }
                ::= { repeaterSecurityPortEntry 2 }

            repeaterSecurityPortAllStatus OBJECT-TYPE
                SYNTAX INTEGER { invalid(1), valid(2) }
                ACCESS read-write
                STATUS mandatory
                DESCRIPTION
                    "Setting this field to invalid will delete all 
                    security addresses associated with this port. 
                    Setting this field to valid has no effect.  If
                    repeaterPortGroupIndex is equal to the group number
                    of the agent, this object is read-write, otherwise it
                    is read-only"
                DEFVAL { valid }
                ::= { repeaterSecurityPortEntry 3 }

            repeaterSecurityPortSecurityLearn OBJECT-TYPE
                SYNTAX INTEGER { disabled(1), single(2), continuous(3) }
                ACCESS read-write
                STATUS mandatory
                DESCRIPTION
                    "Controls how the port will learn the destination 
                    addresses that can be sent to the port.  If
                    repeaterPortGroupIndex is equal to the group number
                    of the agent, this object is read-write, otherwise
                    it is read-only"
                DEFVAL { disabled }
                ::= { repeaterSecurityPortEntry 4 }

            -- additional scalars follow the Security table

            -- the Security table

            repeaterSecurityTable OBJECT-TYPE
                SYNTAX SEQUENCE OF RepeaterSecurityEntry
                ACCESS not-accessible
                STATUS mandatory
                DESCRIPTION
                    "Table of security control for the ports."
                ::= { xRepeaterSecurity 3 }

            repeaterSecurityEntry OBJECT-TYPE
                SYNTAX RepeaterSecurityEntry
                ACCESS not-accessible
                STATUS mandatory
                DESCRIPTION
                    "An entry in the table, containing security 
                    information about a port."
                INDEX { repeaterSecurityGroupIndex,
                        repeaterSecurityPortIndex,
                        repeaterSecurityAddress }
                ::= { repeaterSecurityTable 1 }

            RepeaterSecurityEntry ::=
                SEQUENCE {
                    repeaterSecurityGroupIndex
                        INTEGER,
                    repeaterSecurityPortIndex
                        INTEGER,
                    repeaterSecurityAddress
                        MacAddress,
                    repeaterSecurityStatus
                        INTEGER,
                    repeaterSecurityAction
                        INTEGER
                }

            repeaterSecurityGroupIndex OBJECT-TYPE
                SYNTAX INTEGER
                ACCESS read-only
                STATUS mandatory
                DESCRIPTION
                    "This variable identifies the group containing the 
                    security entry for which this entry contains 
                    information.  The group ID may only be that of the
                    target agent.  Specifying a group ID of an agent in
                    a different slot will result in `badValue` being returned."
                ::= { repeaterSecurityEntry 1 }

            repeaterSecurityPortIndex OBJECT-TYPE
                SYNTAX INTEGER
                ACCESS read-only
                STATUS mandatory
                DESCRIPTION
                    "This variable identifies the port containing the  
                    security entry for which this entry contains 
                    infromation."
                ::= { repeaterSecurityEntry 2 }

            repeaterSecurityAddress OBJECT-TYPE
                SYNTAX MacAddress
                ACCESS read-only
                STATUS mandatory
                DESCRIPTION
                    "This value will be compared to the destination 
                    address of all packets received on the port in 
                    applying the security action."
                ::= { repeaterSecurityEntry 3 }

            repeaterSecurityStatus OBJECT-TYPE
                SYNTAX INTEGER { invalid(1), valid(2) }
                ACCESS read-write
                STATUS mandatory
                DESCRIPTION
                    "The status of the entry.  Set to 'invalid' to 
                    remove the rule."
                DEFVAL { valid }
                ::= { repeaterSecurityEntry 4 }

            repeaterSecurityAction OBJECT-TYPE
                SYNTAX INTEGER { jam(1), allow(2) }
                ACCESS read-write
                STATUS mandatory
                DESCRIPTION
                    "The action to take when the destination address 
                    matches."
                DEFVAL { jam }
                ::= { repeaterSecurityEntry 5 }

            -- additional security scalars

            repeaterSecurityGroupIndexShadow OBJECT-TYPE
                SYNTAX INTEGER
                ACCESS read-write
                STATUS mandatory
                DESCRIPTION
                    "This variable identifies the group containing a 
                    port to which a security address is to be assigned.  The
                    group ID may only be that of the target agent.  Specifying
                    a group ID of an agent in a different slot will result in
                    `badValue` being returned."
                ::= { xRepeaterSecurity 4 }
            
            repeaterSecurityPortIndexShadow OBJECT-TYPE
                SYNTAX INTEGER
                ACCESS read-write
                STATUS mandatory
                DESCRIPTION
                    "This variable identifies the port of a group to which
                    a security address is to be assigned."
                ::= { xRepeaterSecurity 5 }
            
            repeaterSecurityAddressShadow OBJECT-TYPE
                SYNTAX MacAddress
                ACCESS read-write
                STATUS mandatory
                DESCRIPTION
                    "This value contains the ethernet address which is to be
                    added to the security address table for the port specified
                    by repeaterSecurityGroupIndexShadow and
                    repeaterSecurityPortIndexShadow."
                ::= { xRepeaterSecurity 6 }
            
            repeaterSecurityStatusShadow OBJECT-TYPE
                SYNTAX INTEGER { ready(1), execute(2) }
                ACCESS read-write
                STATUS mandatory
                DESCRIPTION
                     "When read, this variable will always return 'ready'.  When
                     this variable is set to 'execute' the address specified by
                     repeaterSecurityAddressShadow will be added to the security
                     address table for the port specified by
                     repeaterSecurityGroupIndexShadow and
                     repeaterSecurityPortIndexShadow.  If any of the above variables
                     are zero when this object is set to 'execute', 'bad value' will
                     be returned."
                DEFVAL { ready }
                ::= { xRepeaterSecurity 7 }

            -- The global Security Table

            -- More scalars follow the global security table

            repeaterSecurityGlobalAddressTable OBJECT-TYPE
                SYNTAX SEQUENCE OF RepeaterSecurityGlobalAddressEntry
                ACCESS not-accessible
                STATUS mandatory
                DESCRIPTION
                    "Table of ethernet addresses which are applied globally
                    (intra Network 9000 chassis) to ports."
                ::= { xRepeaterSecurity 8 }

            repeaterSecurityGlobalAddressEntry OBJECT-TYPE
                SYNTAX RepeaterSecurityGlobalAddressEntry
                ACCESS not-accessible
                STATUS mandatory
                DESCRIPTION
                    "An entry in the table containing information about a
                    specific address."
                INDEX { repeaterSecurityGlobalAddress }
                ::= { repeaterSecurityGlobalAddressTable 1 }

            RepeaterSecurityGlobalAddressEntry ::=
                SEQUENCE {
                    repeaterSecurityGlobalAddress
                        MacAddress,
                    repeaterSecurityGlobalAddressStatus
                        INTEGER,
                    repeaterSecurityGlobalAddressAction
                        INTEGER
                }

            repeaterSecurityGlobalAddress OBJECT-TYPE
                SYNTAX MacAddress
                ACCESS read-only
                STATUS mandatory
                DESCRIPTION
                    "This variable identifies the address."
                ::= { repeaterSecurityGlobalAddressEntry 1 }

            repeaterSecurityGlobalAddressStatus OBJECT-TYPE
                SYNTAX INTEGER { invalid(1), valid(2) }
                ACCESS read-write
                STATUS mandatory
                DESCRIPTION
                    "This variable represents the status of the entry.
                    Setting this object (or any other writable object) to
                    'valid' will cause the row in the table to be created.
                    Setting this object to 'invalid' will cause the row to be
                    removed."
                ::= { repeaterSecurityGlobalAddressEntry 2 }

            repeaterSecurityGlobalAddressAction OBJECT-TYPE
                SYNTAX INTEGER { jam(1), allow(2) }
                ACCESS read-write
                STATUS mandatory
                DESCRIPTION
                    "This variable determines the action which is applied to
                    the packet in the event of an address match.  The packet is
                    either passed untouched when set to 'pass', or it is
                    forced to an alternating pattern of ones and zeros if
                    set to 'jam'."
                DEFVAL { allow }
                ::= { repeaterSecurityGlobalAddressEntry 3 }

            -- Additional Security group scalars

            repeaterSecurityGlobalDBID OBJECT-TYPE
                SYNTAX INTEGER
                ACCESS read-only
                STATUS mandatory
                DESCRIPTION
                    "This variable contains the current version number
                     of the global security database."
                ::= { xRepeaterSecurity 9 }

            repeaterSecurityGlobalSecurityAdminState OBJECT-TYPE
                SYNTAX INTEGER { disabled(1), enabled(2) } 
                ACCESS read-write
                STATUS mandatory
                DESCRIPTION
                    "This variable controls whether global security is
                     enabled or disabled.  Global security will not function
                     unless repeaterSecurityState and
                     this variable are both set to `enabled`."
                DEFVAL { disabled }
                ::= { xRepeaterSecurity 10 }

            repeaterSecurityGlobalSecurityOperState OBJECT-TYPE
                SYNTAX INTEGER { disabled(1), enabled(2), securityDisabled(3) } 
                ACCESS read-only
                STATUS mandatory
                DESCRIPTION
                    "This variable indicates the operational state of global
                     security.  If repeaterSecurityState is set to 'enabled'
                     this variable will reflect the value of
                     repeaterSecurityGlobalSecurityAdminState. if
                     repeaterSecurityState is set to 'disabled', this variable
                     will return 'securityDisabled'."
                ::= { xRepeaterSecurity 11 }

            -- Repeater Repeater table

            -- This table is for repeaters that implement non-proxy
            -- management of multiple logical repeaters.

            repeaterRepeaterTable OBJECT-TYPE
                SYNTAX SEQUENCE OF RepeaterRepeaterEntry
                ACCESS not-accessible
                STATUS mandatory
                DESCRIPTION
                    "For repeaters that implement non-proxy management 
                    of logical repeaters, a table of descriptive and 
                    status information about a logical Ethernet 
                    repeater."
                ::= { xRepeaterRepeater 1 }

                repeaterRepeaterEntry OBJECT-TYPE
                SYNTAX RepeaterRepeaterEntry
                ACCESS not-accessible
                STATUS mandatory
                DESCRIPTION
                    "An entry for a logical Ethernet repeater."
                INDEX { repeaterRepeaterGroupIndex,
                        repeaterRepeaterIndex }
                ::= { repeaterRepeaterTable 1 }

            RepeaterRepeaterEntry ::=
                SEQUENCE {
                    repeaterRepeaterGroupIndex
                        INTEGER,
                    repeaterRepeaterIndex
                        INTEGER,
                    repeaterRepeaterSegment
                        Segment,
                    repeaterRepeaterReports
                        INTEGER,
                    repeaterRepeaterCollisions
                        Counter,
                    repeaterRepeaterJabbers
                        Counter,
                    repeaterRepeaterSQE
                        Counter,
                    repeaterRepeaterFifoOverflows
                        Counter,
                    repeaterRepeaterZero
                        INTEGER,
                    repeaterRepeaterSinceZero
                        TimeTicks,
                    repeaterRepeaterSegmentsAllowed
                        OCTET STRING,
                    repeaterRepeaterTotalOctets
                        Counter,
                    repeaterRepeaterTotalFrames
                        Counter,
                    repeaterRepeaterPercentUtilization
                        Gauge
                }

            repeaterRepeaterGroupIndex OBJECT-TYPE
                SYNTAX INTEGER
                ACCESS read-only
                STATUS mandatory
                DESCRIPTION
                    "The slot of the chassis."
                ::= { repeaterRepeaterEntry 1 }

            repeaterRepeaterIndex OBJECT-TYPE
                SYNTAX INTEGER
                ACCESS read-only
                STATUS mandatory
                DESCRIPTION
                    "The logical Ethernet repeater within the group."
                ::= { repeaterRepeaterEntry 2 }

            repeaterRepeaterSegment OBJECT-TYPE
                SYNTAX Segment
                ACCESS read-write
                STATUS mandatory
                DESCRIPTION
                    "The Network 9000 Ethernet network segment to which 
                    the logical repeater is attached."
                ::= { repeaterRepeaterEntry 3 }

            repeaterRepeaterReports OBJECT-TYPE
                SYNTAX INTEGER { disabled(1), enabled(2) }
                ACCESS read-write
                STATUS mandatory
                DESCRIPTION
                    "Control for whether statistical reports will be 
                    collected for this logical repeater."
                DEFVAL { enabled }
                ::= { repeaterRepeaterEntry 4 }

            repeaterRepeaterCollisions OBJECT-TYPE
                SYNTAX Counter
                ACCESS read-only
                STATUS mandatory
                DESCRIPTION
                    "The number of packet collisions detected on the 
                    Ethernet network segment to which this logical 
                    repeater is attached."
                ::= { repeaterRepeaterEntry 5 }

            repeaterRepeaterJabbers OBJECT-TYPE
                SYNTAX Counter
                ACCESS read-only
                STATUS mandatory
                DESCRIPTION
                    "The number of Jabber events detected for this 
                    logical repeater."
                ::= { repeaterRepeaterEntry 6 }

            repeaterRepeaterSQE OBJECT-TYPE
                SYNTAX Counter
                    ACCESS read-only
                STATUS mandatory
                    DESCRIPTION
                    "The number of SQE failure events detected for this 
                    logical repeater."
                ::= { repeaterRepeaterEntry 7 }

            repeaterRepeaterFifoOverflows OBJECT-TYPE
                SYNTAX Counter
                ACCESS read-only
                STATUS mandatory
                DESCRIPTION
                    "The number of times the report FIFO was full when 
                    this logical repeater attemped to write a packet 
                    report."
                ::= { repeaterRepeaterEntry 8 }

            repeaterRepeaterZero OBJECT-TYPE
                SYNTAX INTEGER { ready(1), execute(2) }
                ACCESS read-write
                STATUS mandatory
                DESCRIPTION
                    "Control for zeroing the logical repeater's 
                    counters.  The agent always returns 'ready' for this 
                    value.  Setting the value to 'ready' has no effect.  
                    Setting the value to 'execute' will zero the 
                    counters for the logical repeater."
                ::= { repeaterRepeaterEntry 9 }

            repeaterRepeaterSinceZero OBJECT-TYPE
                SYNTAX TimeTicks
                ACCESS read-only
                STATUS mandatory
                DESCRIPTION
                    "The number of hundredths of a second since the 
                    counters for this logical repeater were last zeroed.  
                    This variable is set to zero when 
                    repeaterRepeaterZero is written with the value 
                    'execute'."
                ::= { repeaterRepeaterEntry 10 }

            repeaterRepeaterSegmentsAllowed OBJECT-TYPE
                SYNTAX OCTET STRING
                ACCESS read-only
                STATUS mandatory
                DESCRIPTION
                    "The list of segments to which this repeater can be 
                    attached.  The OCTET STRING contains a bitmap, with 
                    a bit for 'none' and one bit for each segment, and 
                    enough octets for all the Ethernet segments in the 
                    chassis.  The high order bit of the first octet 
                    corresponds to 'none', the following bits correspond 
                    to the segments, in order, beginning with A."
                ::= { repeaterRepeaterEntry 11 }

            repeaterRepeaterTotalOctets OBJECT-TYPE
                SYNTAX Counter
                ACCESS read-only
                STATUS mandatory
                DESCRIPTION
                    "This variable will reflect the total number of bytes that
                    the repeater both received from and sent to the segment.
                    Bytes in both good and error frames are counted."
                ::= { repeaterRepeaterEntry 12 }

            repeaterRepeaterTotalFrames OBJECT-TYPE
                SYNTAX Counter
                ACCESS read-only
                STATUS mandatory
                DESCRIPTION
                    "This variable will reflect the total number of frames that
                    the repeater both received from and sent to the segment.
                    Both good and error frames are counted."
                ::= { repeaterRepeaterEntry 13 }

            repeaterRepeaterPercentUtilization OBJECT-TYPE
                SYNTAX Gauge
                ACCESS read-only
                STATUS mandatory
                DESCRIPTION
                    "This variable will reflect the percentage of a full
                    ethernet load that this repeater has handled since last
                    zeroed.  The value is calculated as
                    `(8(totalBytes + (20*totalFrames)))/10 7(time)`."
                ::= { repeaterRepeaterEntry 14 }


            -- The Repeater Redundancy group

            -- Implementation of this group is mandatory for all ITouch
            -- Ethernet repeaters.
            -- The repeater Redundancy group contains:

            repeaterRedundancyState OBJECT-TYPE
                SYNTAX INTEGER { disabled(1), enabled(2) }
                ACCESS read-write
                STATUS mandatory
                DESCRIPTION
                    "This variable controls whether hub redundancy is enabled"
                DEFVAL { enabled }
                ::= { xRepeaterRedundancy 1 }
            -- The Redundancy Group table

            repeaterRedundancyGroupTable OBJECT-TYPE
                SYNTAX SEQUENCE OF RepeaterRedundancyGroupEntry
                ACCESS not-accessible
                STATUS mandatory
                DESCRIPTION
                    "Table of descriptive and status information
                    concerning hub redundancy groups."
                ::= { xRepeaterRedundancy 2 }

            repeaterRedundancyGroupEntry OBJECT-TYPE
                SYNTAX RepeaterRedundancyGroupEntry
                ACCESS not-accessible
                STATUS mandatory
                DESCRIPTION
                    "An entry in the table containing information about a
                    specific hub redundancy group."
                INDEX { repeaterRedundancyGroupGroupIndex }
                ::= { repeaterRedundancyGroupTable 1 }

            RepeaterRedundancyGroupEntry ::=
                SEQUENCE {
                    repeaterRedundancyGroupGroupIndex
                        INTEGER,
                    repeaterRedundancyGroupStatus
                        INTEGER,
                    repeaterRedundancyGroupName
                        DisplayString,
                    repeaterRedundancyGroupAdminState
                        INTEGER,
                    repeaterRedundancyGroupTestInterval
                        INTEGER,
                    repeaterRedundancyGroupRollbackAdminState
                        INTEGER,
                    repeaterRedundancyGroupRollbackInterval
                        INTEGER,
                    repeaterRedundancyGroupOperPath
                        INTEGER,
                    repeaterRedundancyGroupPathChanges
                        Counter,
                    repeaterRedundancyGroupRollbackAttempts
                        Counter,
                    repeaterRedundancyGroupZero
                        INTEGER,
                    repeaterRedundancyGroupSinceZero
                        TimeTicks,
                    repeaterRedundancyGroupConfigStatus
                        INTEGER
                }

            repeaterRedundancyGroupGroupIndex OBJECT-TYPE
                SYNTAX INTEGER
                ACCESS read-only
                STATUS mandatory
                DESCRIPTION
                    "This variable identifies the group."
                ::= { repeaterRedundancyGroupEntry 1 }

            repeaterRedundancyGroupStatus OBJECT-TYPE
                SYNTAX INTEGER { invalid(1), valid(2) }
                ACCESS read-write
                STATUS mandatory
                DESCRIPTION
                    "This variable represents the status of the entry.
                    Setting this object (or any other writable object) to
                    'valid' will cause the row in the table to be created.
                    Setting this object to 'invalid' will cause the row to be
                    removed.  If a row is removed from the group table, all
                    related rows in the path table and address table are
                    also removed."
                ::= { repeaterRedundancyGroupEntry 2 }

            repeaterRedundancyGroupName OBJECT-TYPE
                SYNTAX DisplayString (SIZE (0..16))
                ACCESS read-write
                STATUS mandatory
                DESCRIPTION
                    "This variable represents the definable name of the
                    group.  Prior to being set, this object will return
                    the default name 'Groupn' where n is the value of
                    repeaterRedundancyGroupIndex.  Setting this object to a zero
                    length string will cause the default name to be assumed."
                ::= { repeaterRedundancyGroupEntry 3 }

            repeaterRedundancyGroupAdminState OBJECT-TYPE
                SYNTAX INTEGER { disabled(1), enabled(2) }
                ACCESS read-write
                STATUS mandatory
                DESCRIPTION
                    "This variable represents the desired state of the
                    group.  When this variable is set to 'enabled', the group
                    will be activly monitored for integrity, and back-
                    up paths will be brought up as higher priority paths
                    disappear.  When set to 'disabled', the path will not be
                    tested for integrity."
                DEFVAL { enabled }
                ::= { repeaterRedundancyGroupEntry 4 }

            repeaterRedundancyGroupTestInterval OBJECT-TYPE
                SYNTAX INTEGER (250..180000)
                ACCESS read-write
                STATUS mandatory
                DESCRIPTION
                    "This variable determines the rate at which testing is
                    performed on the path which is currently active
                    (repeaterRedundancyGroupOperPath) in order to determine
                    integrity.  The value is in milliseconds."
                DEFVAL { 3000 }
                ::= { repeaterRedundancyGroupEntry 5 }

            repeaterRedundancyGroupRollbackAdminState OBJECT-TYPE
                SYNTAX INTEGER { disabled(1), enabled(2) }
                ACCESS read-write
                STATUS mandatory
                DESCRIPTION
                    "This variable represents the desired state of path
                    rollback.  Path rollback is defined as the automatic
                    testing and reactivation of higher priority
                    paths.  It should be noted that in order to test higher
                    priority paths, the currently enabled path will be
                    interrupted.  Setting this variable to 'enabled' will cause
                    rollback testing to occur every
                    repeaterRedundancyGroupRollbackInterval number of milliseconds.
                    Setting this variable to 'disabled' will force the group to
                    remain on lower priority paths, until they themselves fail."
                DEFVAL { enabled }
                ::= { repeaterRedundancyGroupEntry 6 }

            repeaterRedundancyGroupRollbackInterval OBJECT-TYPE
                SYNTAX INTEGER (500..180000)
                ACCESS read-write
                STATUS mandatory
                DESCRIPTION
                    "This variable determines the rate at which rollback
                    testing is performed. The value is in milliseconds."
                DEFVAL { 10000 }
                ::= { repeaterRedundancyGroupEntry 7 }

            repeaterRedundancyGroupOperPath OBJECT-TYPE
                SYNTAX INTEGER
                ACCESS read-only
                STATUS mandatory
                DESCRIPTION
                    "This variable represents the index of the path which is
                    currently being used as the active path. This value may be
                    used as the value for repeaterRedundancyPathIndex to index the
                    path table."
                ::= { repeaterRedundancyGroupEntry 8 }

            repeaterRedundancyGroupPathChanges OBJECT-TYPE
                SYNTAX Counter
                ACCESS read-only
                STATUS mandatory
                DESCRIPTION
                    "The value of this variable represents the number of times
                    that this group has changed paths."
                ::= { repeaterRedundancyGroupEntry 9 }

            repeaterRedundancyGroupRollbackAttempts OBJECT-TYPE
                SYNTAX Counter
                ACCESS read-only
                STATUS mandatory
                DESCRIPTION
                    "The value of this variable represents the number of times
                    that the current path has been interrupted in interest of
                    testing a higher priority path."
                ::= { repeaterRedundancyGroupEntry 10 }

            repeaterRedundancyGroupZero OBJECT-TYPE
                SYNTAX INTEGER { ready(1), execute(2) }
                ACCESS read-write
                STATUS mandatory
                DESCRIPTION
                    "This variable is used to zero all counters associated
                    with a group.  This variable when read will always read
                    'ready'.  When set to 'execute', all counters associated
                    with the group (group counters and path counters) will be set
                    to zero."
                ::= { repeaterRedundancyGroupEntry 11 }

            repeaterRedundancyGroupSinceZero OBJECT-TYPE
                SYNTAX TimeTicks
                ACCESS read-only
                STATUS mandatory
                DESCRIPTION
                    "The value of this variable represents the number of seconds
                    which have elapsed since the counters associated with the
                    group have been zeroed."
                ::= { repeaterRedundancyGroupEntry 12 }

            repeaterRedundancyGroupConfigStatus OBJECT-TYPE
				SYNTAX INTEGER { incomplete(1), complete(2) }
                ACCESS read-only
                STATUS mandatory
                DESCRIPTION
                    "In order for a particular redundancy group to be used by the
                    system, it must have at least one redundancy path defined.
                    This variable indicates whether a redundancy group has been
                    completely configured, and can therefore become active."
                ::= { repeaterRedundancyGroupEntry 13 }

            -- The Redundancy Path table

            repeaterRedundancyPathTable OBJECT-TYPE
                SYNTAX SEQUENCE OF RepeaterRedundancyPathEntry
                ACCESS not-accessible
                STATUS mandatory
                DESCRIPTION
                    "Table of descriptive and status information concerning hub
                    redundancy paths."
                ::= { xRepeaterRedundancy 3 }

            repeaterRedundancyPathEntry OBJECT-TYPE
                SYNTAX RepeaterRedundancyPathEntry
                ACCESS not-accessible
                STATUS mandatory
                DESCRIPTION
                    "An entry in the table containing information about a
                    specific hub redundancy path."
                INDEX { repeaterRedundancyPathGroupIndex,
                        repeaterRedundancyPathPathIndex }
                ::= { repeaterRedundancyPathTable 1 }

            RepeaterRedundancyPathEntry ::=
                SEQUENCE {
                    repeaterRedundancyPathGroupIndex
                        INTEGER,
                    repeaterRedundancyPathPathIndex
                        INTEGER,
                    repeaterRedundancyPathStatus
                        INTEGER,
                    repeaterRedundancyPathSlot
                        INTEGER,
                    repeaterRedundancyPathPort
                        INTEGER,
                    repeaterRedundancyPathPriority
                        INTEGER,
                    repeaterRedundancyPathActivate
                        INTEGER,
                    repeaterRedundancyPathTimeout
                        INTEGER,
                    repeaterRedundancyPathRetryCount
                        INTEGER,
                    repeaterRedundancyPathTestAttempts
                        Counter,
                    repeaterRedundancyPathLastTestStatus
                        INTEGER,
                    repeaterRedundancyPathDisposition
                        INTEGER,
                    repeaterRedundancyPathConfigStatus
                        INTEGER,
                    repeaterRedundancyPathAdminState
                        INTEGER
                }

            repeaterRedundancyPathGroupIndex OBJECT-TYPE
                SYNTAX INTEGER
                ACCESS read-only
                STATUS mandatory
                DESCRIPTION
                    "This variable identifies the group."
                ::= { repeaterRedundancyPathEntry 1 }

            repeaterRedundancyPathPathIndex OBJECT-TYPE
                SYNTAX INTEGER
                ACCESS read-only
                STATUS mandatory
                DESCRIPTION
                    "This variable identifies the path of the group."
                ::= { repeaterRedundancyPathEntry 2 }

            repeaterRedundancyPathStatus OBJECT-TYPE
                SYNTAX INTEGER { invalid(1), valid(2) }
                ACCESS read-write
                STATUS mandatory
                DESCRIPTION
                    "This variable represents the status of the entry.
                    Setting this object (or any other writable object) to
                    'valid' will cause the row in the table to be created.
                    Setting this object to 'invalid' will cause the row to be
                    removed.  If a row is removed from the path table, all related
                    rows in the address table are also removed."
                ::= { repeaterRedundancyPathEntry 3 }

            repeaterRedundancyPathSlot OBJECT-TYPE
                SYNTAX INTEGER
                ACCESS read-write
                STATUS mandatory
                DESCRIPTION
                    "This variable represents the slot of the Network 9000
                    chassis which contains the repeater on which the path
                    interface resides."
                ::= { repeaterRedundancyPathEntry 4 }

            repeaterRedundancyPathPort OBJECT-TYPE
                SYNTAX INTEGER
                ACCESS read-write
                STATUS mandatory
                DESCRIPTION
                    "This variable represents the port of the repeater to
                    which the path is connected."
                ::= { repeaterRedundancyPathEntry 5 }

            repeaterRedundancyPathPriority OBJECT-TYPE
                SYNTAX INTEGER
                ACCESS read-write
                STATUS mandatory
                DESCRIPTION
                    "This variable represents the order of preferred priority
                    for the path.  Lower numbed paths are preferred over higher
                    numbered paths."
                DEFVAL { 5 }
                ::= { repeaterRedundancyPathEntry 6 }

            repeaterRedundancyPathActivate OBJECT-TYPE
                SYNTAX INTEGER { ready(1), execute(2) }
                ACCESS read-write
                STATUS mandatory
                DESCRIPTION
                    "This variable is used to immediately make a specific path
                    active.  This variable when read will always read
                    'ready'.  When set to 'execute', the selected path will
                    become the active path for the group. Note that if rollback
                    is enabled and this path is lower in priority, the system
                    will attempt to restore the higher priority path."
                ::= { repeaterRedundancyPathEntry 7 }

            repeaterRedundancyPathTimeout OBJECT-TYPE
                SYNTAX INTEGER (250..10000)
                ACCESS read-write
                STATUS mandatory
                DESCRIPTION
                    "This variable represents the amount of time in
                    milliseconds that the syatem will wait for test responses from
                    targets on the path."
                DEFVAL { 3000 }
                ::= { repeaterRedundancyPathEntry 8 }

            repeaterRedundancyPathRetryCount OBJECT-TYPE
                SYNTAX INTEGER (1..50)
                ACCESS read-write
                STATUS mandatory
                DESCRIPTION
                    "This variable represents the number of times a test is
                    retried on the path in the event of a timeout before the
                    path is considered useless."
                DEFVAL { 3 }
                ::= { repeaterRedundancyPathEntry 9 }

            repeaterRedundancyPathTestAttempts OBJECT-TYPE
                SYNTAX Counter
                ACCESS read-only
                STATUS mandatory
                DESCRIPTION
                    "The value of this variable represents the number of times
                    that an integrity test was performed on the path."
                ::= { repeaterRedundancyPathEntry 10 }

            repeaterRedundancyPathLastTestStatus OBJECT-TYPE
                SYNTAX INTEGER { notTested(1),
                                 responded(2),
                                 timeout(3),
                                 noIntegrity(4) }
                ACCESS read-only
                STATUS mandatory
                DESCRIPTION
                    "This variable indicates the result of the last test of
                    the path. 'notTested' indicates that the path has yet
                    to be tested. 'responded' indicates that a target on the
                    path path has responded to the last test,  'timeout'
                    indicates that no target on the path responded to the last
                    test.  'integrity' indicates that a test was not performed on
                    the path due to an abscense of port integrity."
                ::= { repeaterRedundancyPathEntry 11 }

            repeaterRedundancyPathDisposition OBJECT-TYPE
                SYNTAX INTEGER { disable(1), null(2) }
                ACCESS read-write
                STATUS mandatory
                DESCRIPTION
                    "This variable controls the action that will be taken when
                    a path is considered bad.  'disable' indicates that the
                    path is to be disabled prior to switching to an alternate path.
                    'null' indicates that the failed path is to be left in its
                    current state prior to switching to an alternate path."
                DEFVAL { disable }
                ::= { repeaterRedundancyPathEntry 12 }

            repeaterRedundancyPathConfigStatus OBJECT-TYPE
				SYNTAX INTEGER { incomplete(1), complete(2) }
                ACCESS read-only
                STATUS mandatory
                DESCRIPTION
                    "In order for a particular redundancy path to be used by the
                    system, it must have at least one target address and the slot
                    and the port on which it originates defined.  This variable
                    indicates whether a redundancy path has been completely
                    configured, and can therefore become active."
                ::= { repeaterRedundancyPathEntry 13 }

            repeaterRedundancyPathAdminState OBJECT-TYPE
				SYNTAX INTEGER { disabled(1), enabled(2) }
                ACCESS read-write
                STATUS mandatory
                DESCRIPTION
                    "This variable represents the desired state of the path.
                    When this variable is set to 'disabled' the path will not
                    be used by the group.  When set to 'enabled', the path is
                    available as an alternate or primary path."
                DEFVAL { enabled }
                ::= { repeaterRedundancyPathEntry 14 }

            -- The Redundancy Target Address table

            repeaterRedundancyAddressTable OBJECT-TYPE
                SYNTAX SEQUENCE OF RepeaterRedundancyAddressEntry
                ACCESS not-accessible
                STATUS mandatory
                DESCRIPTION
                    "Table of descriptive and status information
                    concerning hub redundancy target addresses."
                ::= { xRepeaterRedundancy 4 }

            repeaterRedundancyAddressEntry OBJECT-TYPE
                SYNTAX RepeaterRedundancyAddressEntry
                ACCESS not-accessible
                STATUS mandatory
                DESCRIPTION
                    "An entry in the table containing information about a specific
                    target address associated with a hub redundancy path."
                INDEX { repeaterRedundancyAddressGroupIndex,
                        repeaterRedundancyAddressPathIndex,
                        repeaterRedundancyAddressAddress }
                ::= { repeaterRedundancyAddressTable 1 }

            RepeaterRedundancyAddressEntry ::=
                SEQUENCE {
                    repeaterRedundancyAddressGroupIndex
                        INTEGER,
                    repeaterRedundancyAddressPathIndex
                        INTEGER,
                    repeaterRedundancyAddressAddress
                        TypedAddress,
                    repeaterRedundancyAddressStatus
                        INTEGER,
                    repeaterRedundancyAddressResponses
                        Counter,
                    repeaterRedundancyAddressLastTestStatus
                        INTEGER
                }

            repeaterRedundancyAddressGroupIndex OBJECT-TYPE
                SYNTAX INTEGER
                ACCESS read-only
                STATUS mandatory
                DESCRIPTION
                    "This variable identifies the group."
                ::= { repeaterRedundancyAddressEntry 1 }

            repeaterRedundancyAddressPathIndex OBJECT-TYPE
                SYNTAX INTEGER
                ACCESS read-only
                STATUS mandatory
                DESCRIPTION
                    "This variable identifies the path of the group."
                ::= { repeaterRedundancyAddressEntry 2 }

            repeaterRedundancyAddressAddress OBJECT-TYPE
                SYNTAX TypedAddress
                ACCESS read-only
                STATUS mandatory
                DESCRIPTION
                    "This variable identifies the specific target address."
                ::= { repeaterRedundancyAddressEntry 3 }

            repeaterRedundancyAddressStatus OBJECT-TYPE
                SYNTAX INTEGER { invalid(1), valid(2) }
                ACCESS read-write
                STATUS mandatory
                DESCRIPTION
                    "This variable represents the status of the entry. Setting
                     this object (or any other writable object) to 'valid' will
                     cause the row in the table to be created.  Setting this 
                     object to 'invalid' will cause the row to be removed."
                ::= { repeaterRedundancyAddressEntry 4 }

            repeaterRedundancyAddressResponses OBJECT-TYPE
                SYNTAX Counter
                ACCESS read-only
                STATUS mandatory
                DESCRIPTION
                    "This value of this variable represents the number of times
                    this specific address has responded to a test attempt."
                ::= { repeaterRedundancyAddressEntry 5 }

            repeaterRedundancyAddressLastTestStatus OBJECT-TYPE
                SYNTAX INTEGER { notTested(1),
                                 responded(2),
                                 timeout(3) }
                ACCESS read-only
                STATUS mandatory
                DESCRIPTION
                    "This variable indicates whether this particular address responded to
                    the last test of the path.  'notTested' indicates that the
                    path has yet to be tested.  'responded' indicates that the
                    target responded to the last test, 'timeout' indicates
                    that the target responded to the last test."
                ::= { repeaterRedundancyAddressEntry 6 }

            -- Repeater traps

            accessViolation TRAP-TYPE
                ENTERPRISE xRepeater
                VARIABLES { 
                    repeaterPortIndex
                    }
                DESCRIPTION
                    "Access violation by connected system with Ethernet 
                    address not allowed by repeaterPortAccessTable and 
                    repeaterPortAccessAction."
                ::= 1

            integrityLoss TRAP-TYPE
                ENTERPRISE xRepeater
                VARIABLES { 
                    repeaterPortIndex,
                    repeaterPortGroupIndex
                    }
                DESCRIPTION
                    "This port has lost link integrity."
                ::= 2

            redundancyPathChange TRAP-TYPE
                ENTERPRISE xRepeater
                VARIABLES {  repeaterRedundancyGroupGroupIndex,
                            repeaterRedundancyGroupOperPath }
                DESCRIPTION
                    "This trap issued to indicate that a redundancy group has
                    experienced a path change.  The offending group and
                    the new path are included in the trap."
                ::= 3



--
-- FILE: /users/sse/mibs/src/itouch/it-rmon-mib.mib
--

-- $Id: it-rmon-mib.mib,v 1.3 2001/07/25 15:15:02 sse Exp $


        xRmon           OBJECT IDENTIFIER ::= { iTouch 31 }

        -- The individual Groups within the RMON MIB

        xRmonMonitor    OBJECT IDENTIFIER ::= { xRmon 1 }
        xRmonMB         OBJECT IDENTIFIER ::= { xRmon 2 }
        -- xRmonMapTable OBJECT IDENTIFIER ::= { xRmon 3 }

            -- This is a MIB module for all iTouch Communications systems
            -- that implement RMON.

            -- Copyright 2000 iTouch Communications, Inc. All Rights Reserved.
            -- Reproduction of this document is authorized on
            -- condition that this copyright notice is included.
            -- This MIB document embodies iTouch Communications, Inc.'s 
            -- proprietary intellectual property.  iTouch Communications, Inc.
            -- retains all title and ownership in this MIB, including any
            -- revisions.
            --
            -- It is iTouch Communications, Inc.'s intent to encourage the
            -- widespread use of this MIB in connection with the management of
            -- iTouch Communications, Inc. products. iTouch Communications,
            -- Inc. grants vendors,end-users, and other interested parties a
            -- non-exclusive license to use this MIB in connection with the
            -- management of iTouch Communications, Inc. products.
            --
            -- This MIB document is supplied "AS IS," and iTouch 
            -- Communications, Inc. makes no warranty, either express or
            -- implied, as to the use operation, condition, or performance of
            -- the MIB.

        -- DESCRIPTION fields for many objects are written in the
        -- form of 'help text', rather than as complete 'mib style'
        -- functional descriptions.

        -- The RMON Monitor group

        -- Implementation of this group is mandatory for all iTouch
        -- systems that implement RMON for fault management.

        xRmonMonitorRemote OBJECT-TYPE
            SYNTAX INTEGER (0..65535)
            ACCESS read-only
            STATUS mandatory
            DESCRIPTION "
                Once an alarm is 'completed', monitoring for that
                variable may be distributed within an enclosure to
                another processor.  Factors affecting this decision
                include variable type, slot number, and processor
                type.  Furthermore, alarms which have identical
                parameters (variable, interval, thresholds, etc.)
                are viewed by the monitoring processor as a single
                'object' to monitor.

                Alarm variables falling into this category are a
                subset of the repeater MIB and iTouch repeater MIB
                objects.

                This field represents the number of 'objects' this
                system CPU is monitoring on behalf of alarms which
                were distributed to it by a management processor."
            ::= { xRmonMonitor 1 }

        xRmonMonitorLocal OBJECT-TYPE
            SYNTAX INTEGER (0..65535)
            ACCESS read-only
            STATUS mandatory
            DESCRIPTION "
                Once an alarm is 'completed', monitoring for that
                variable may be distributed within an enclosure to
                another processor.  Factors affecting this decision
                include variable type, slot number, and processor
                type.  Furthermore, alarms which have identical
                parameters (variable, interval, thresholds, etc.)
                are viewed by the monitoring processor as a single
                'object' to monitor.

                Alarm variables falling into this category are a
                subset of the repeater MIB and iTouch repeater MIB
                objects.

                This field represents the number of 'objects' this
                system CPU is monitoring, objects it did not
                distribute to another processor."
            ::= { xRmonMonitor 2 }

        xRmonLogClear OBJECT-TYPE
            SYNTAX INTEGER { ready(1), execute(2) }
            ACCESS read-write
            STATUS mandatory
            DESCRIPTION "
                Set this field to 'execute' to delete all RMON log
                table entries.  Setting to 'ready' has no effect."
            ::= { xRmonMonitor 3 }

        xRmonLogTotal OBJECT-TYPE
            SYNTAX Counter
            ACCESS read-only
            STATUS mandatory
            DESCRIPTION "
                This field reports the total number of RMON log
                entries created since the system was initialized.
                Clearing the log table does not change this value."
            ::= { xRmonMonitor 4 }

        xRmonLogLastDateTime OBJECT-TYPE
            SYNTAX DateTime
            ACCESS read-only
            STATUS mandatory
            DESCRIPTION "
                The local date and time of the system at the time
                an RMON log entry was last created."
            ::= { xRmonMonitor 5 }

        xRmonTrapType OBJECT-TYPE
            SYNTAX INTEGER { standardFormat(1), iTouchFormat(2) }
            ACCESS read-write
            STATUS mandatory
            DESCRIPTION "
                Use this field to specify the type of SNMP trap to
                generate when an alarm event occurs.

                The value 'standardFormat' formats the trap as a
                standard, RMON-compliant rising and falling event
                trap.

                The value 'iTouchFormat' formats the trap as a
                DisplayString containing a human-readable summary
                of the event.  The text of the string is very
                similar to that of the log descriptions."
            DEFVAL { standardFormat }
            ::= { xRmonMonitor 6 }

        xRmonRepeaterManagement OBJECT-TYPE
            SYNTAX INTEGER { disabled(1), enabled(2) }
            ACCESS read-write
            STATUS mandatory
            DESCRIPTION "
                This field enables and disables RMON monitoring of
                certain repeater related variables in the chassis.

                Set this field to 'enabled' to allow this slot to
                activate alarms and report traps for variables from
                the standard repeater MIB (snmpDot3RptrMgt
                1.3.6.1.2.1.22) and the iTouch repeater MIB
                (xRepeater 1.3.6.1.4.1.33.17).

                When you set this field to 'disabled', alarms may
                still be created for these repeater variables, but
                no monitoring will take place for them.  The alarm
                state will be 'held' during this time.

                Only one slot in a chassis may have this field set
                to 'enabled' at any given time.  Setting 'enabled'
                in any one slot automatically sets it to 'disabled'
                in every other slot.  Repeater variable monitoring
                in those slots will cease and the corresponding
                alarm states will be 'held'."
            DEFVAL { disabled }
            ::= { xRmonMonitor 7 }

        xRmonAlarmActivate OBJECT-TYPE
            SYNTAX INTEGER {
                noAction(1),
                activateAll(2),
                deactivateAll(3)
            }
            ACCESS read-write
            STATUS mandatory
            DESCRIPTION "
                Use this field to change the states of all completed
                alarms to 'active' or 'inactive'.

                Select 'activateAll' to make all completed alarms
                not in the 'active' state become 'active' again.
                This is useful for alarms whose error states are not
                automatically cleared by the system.  Alarms whose
                error conditions have not cleared will remain in
                their current states.

                Select 'deactivateAll' to make all completed alarms
                that are in the 'active' state become 'inactive'.
                This is a convenient way to suppress alarm activity
                while making other configuration changes without
                actually deleting the alarms.

                Alarms which are incomplete (e.g., 'creating' state)
                are not affected by these actions.

                If you want to alter the state of a single alarm,
                modify the table entry for that alarm.

                Selecting noAction has no effect."
            ::= { xRmonMonitor 8 }

        xRmonAlarmClear OBJECT-TYPE
            SYNTAX INTEGER { noAction(1), deleteAll(2) }
            ACCESS read-write
            STATUS mandatory
            DESCRIPTION "
                Set this field to 'deleteAll' to delete all alarm
                table entries and their associated event entries.
                Setting to 'noAction' has no effect."
            ::= { xRmonMonitor 9 }

        -- The xRmonAlarmCount group

        -- These counters reflect the number of alarms in each of
        -- several different states.

        xRmonAlarmCount   OBJECT IDENTIFIER ::= { xRmonMonitor 10 }

        xRmonAlarmsIncomplete OBJECT-TYPE
            SYNTAX INTEGER
            ACCESS read-only
            STATUS mandatory
            DESCRIPTION "
                This value represents the number of alarms that are
                not completed.  Completing these alarms will make
                them active."
            ::= { xRmonAlarmCount 1 }

        xRmonAlarmsActive OBJECT-TYPE
            SYNTAX INTEGER
            ACCESS read-only
            STATUS mandatory
            DESCRIPTION "
                This value represents the number of alarms whose
                state is 'active'.  These are completed alarms
                which are actively monitored."
            ::= { xRmonAlarmCount 2 }

        xRmonAlarmsHeld OBJECT-TYPE
            SYNTAX INTEGER
            ACCESS read-only
            STATUS mandatory
            DESCRIPTION "
                This value represents the number of alarms whose
                state is 'held'.  These are completed alarms
                which will not be actively monitored because the
                Repeater Management feature for this processor is
                currently disabled.  Enabling the feature will
                activate all alarms in this state."
            ::= { xRmonAlarmCount 3 }

        xRmonAlarmsOther OBJECT-TYPE
            SYNTAX INTEGER
            ACCESS read-only
            STATUS mandatory
            DESCRIPTION "
                This value represents the number of completed alarms
                that are not 'active' and not 'held'.  Monitoring is
                not active for these alarms."
            ::= { xRmonAlarmCount 4 }

        xRmonAlarmInitAction OBJECT-TYPE
            SYNTAX INTEGER {
                activateUponInit(1),
                inactiveUponInit(2)
            }
            ACCESS read-write
            STATUS mandatory
            DESCRIPTION "
                Use this field to specify whether all alarms read
                from the parameter file should be placed in the
                'active' state or the 'inactive' state upon system
                initialization.

                Selecting 'activateUponInit' (the default) will
                activate all alarms read from the parameter file
                when the system initializes.

                Selecting 'inactiveUponInit' will place all alarms
                in the 'inactive' state when the system initializes.

                Modifying this value does not affect the present
                state of any alarm."
            ::= { xRmonMonitor 11 }

        -- The RMON MB group

        -- Implementation of the iTouch RMON MB group is optional.

        -- The MB group requires implementation of the RMON alarm
        -- and event groups.

        -- The MB group implements a more user-friendly interface to
        -- create RMON alarms and view alarm and log entries using
        -- applications that cannot interpret complex RMON tables.
        -- It offers an alternate interface for creating alarmTable
        -- and eventTable entries.  It also interprets the alarm and
        -- log tables, presenting them as more readable strings.


        -- The RMON MB Configuration Group

        -- The following objects provide access to the creation and
        -- viewing of a single, complete RMON alarmTable entry,
        -- including associated eventTable entries.  RMON alarms not
        -- created using these objects may also be viewed, within
        -- the limits stated below.

        -- Note that these objects, mbAlarmIndex in particular,
        -- cannot be shared among SNMP clients.  Only one such client
        -- should be attempting to create, modify, or view an alarm
        -- at any given time.  Failure to adhere to this convention
        -- may result in unexpected alarm parameter settings.

        -- Similarly, when creating a new alarm sets of these objects
        -- should not be combined in the same SET PDU with RMON alarm
        -- group objects for the same alarmIndex.

        xRmonMBConfig   OBJECT IDENTIFIER ::= { xRmonMB 1 }

        -- If the alarm specified by mbAlarmIndex is deleted through the
        -- standard RMON alarmStatus object, this entry becomes zero.
        -- Setting this object to 0 makes all remaining objects in this
        -- group invisible to SNMP.  GET-NEXT will skip over them and
        -- GET/SET return noSuchName errors.

        mbAlarmIndex OBJECT-TYPE
            SYNTAX INTEGER (0..65535)
            ACCESS read-write
            STATUS mandatory
            DESCRIPTION "
                This field can be either the index of an existing
                alarm (as seen in the alarm summary view) or a new
                number to create a new alarm.

                Specify the index of an existing alarm to fill the
                remaining fields with the corresponding settings
                from that alarm.  To modify the settings of a
                completed alarm, set its status to underCreation.

                Specify an index which does not exist to create a
                new alarm.  The initial settings of the remaining
                fields are taken from the alarm you were previously
                viewing, if any.  This makes it easier to 'copy' an
                alarm definition when you want to change only a few
                of the settings, such as the alarm variable or keys.

                Specify a value of 0 to clear the remaining fields."
            DEFVAL { 0 }
            ::= { xRmonMBConfig 1 }

        mbAlarmInterval OBJECT-TYPE
            SYNTAX INTEGER
            ACCESS read-write
            STATUS mandatory
            DESCRIPTION "
                The interval in seconds over which the variable is
                sampled and compared with the rising and falling
                thresholds.  If the monitored variable exceeds the
                limit 2^31-1 (4294967295), the alarm value field may
                roll over to 0 and cause or suppress the generation
                of an alarm event during that interval.

                You may not modify this field once the alarm is
                completed (see alarm status field)."
            DEFVAL { 10 }
            ::= { xRmonMBConfig 2 }

        mbAlarmVariable OBJECT-TYPE
            SYNTAX OBJECT IDENTIFIER
            ACCESS read-write
            STATUS mandatory
            DESCRIPTION "
                This value shows the SNMP object identifier of the
                variable being sampled.  Only variables that have an
                SNMP 'SYNTAX' of INTEGER, Counter, Gauge, or
                TimeTicks may be sampled.

                When you specify an object identifier in this field,
                the quick list, key prompt, and key value fields are
                filled for you with the appropriate values.  If you
                specify an object not found in the quick list, that
                field is set to 'unlistedAlarmVariable'.  The key
                values will be set to zero in this case.

                If you specify an alarm variable and keys using the
                quick list and key fields, an SNMP object identifier
                is built for you and placed in this field.

                You may not modify this field at the same time that
                you modify the quick list field or either of the
                key values.

                You may not modify this field once the alarm is
                completed (see alarm status field)."
            ::= { xRmonMBConfig 3 }

        mbAlarmInterpretation OBJECT-TYPE
            SYNTAX INTEGER {
                unlistedAlarmVariable(1),
                portReadableFrames(2),
                portReadableOctets(3),
                portTotalFrames(4),
                portTotalOctets(5),
                portBroadcastFrames(6),
                portMulticastFrames(7),
                portFrames64Octets(8),
                portFrames65to127Octets(9),
                portFrames128to255Octets(10),
                portFrames256to511Octets(11),
                portFrames512to1023Octets(12),
                portFrames1024to1518Octets(13),
                portPercentUtilization(14),
                portTrafficRatio(15),
                portCollisionRatio(16),
                portErrorRatio(17),
                portBroadcastRatio(18),
                portMulticastRatio(19),
                portUnicastRatio(20),
                 portAlignmentErrors(21),
                portAutoPartitions(22),
                portCollisions(23),
                portCRCAlignErrors(24),
                portCRCErrors(25),
                portDataRateMismatches(26),
                portFrameTooLongErrors(27),
                portLateCollisionErrors(28),
                portManchesterCodeViolations(29),
                portRunts(30),
                portShortPacketErrors(31),
                portStartOfFrameMissing(32),
                portVeryLongFrameErrors(33),
                portTotalErrors(34),
                portAccessState(35),
                portAccessAddressViolations(36),
                portGlobalAddressChanges(37),
                portSourceAddressChanges(38),
                portAdminStatus(39),
                portAutoPartitionState(40),
                portOperStatus(41),
                portPulseStatus(43),
                portPulseLosses(44),
                portSecondsSinceCountersZeroed(45),
                repeaterTotalFrames(46),
                repeaterTotalOctets(47),
                repeaterPercentUtilization(48),
                repeaterCollisions(49),
                repeaterFifoOverflows(50),
                repeaterJabbers(51),
                repeaterSQEErrors(52),
                repeaterSecondsSinceCountersZeroed(53),
                slotTotalFrames(54),
                slotTotalOctets(55),
                slotTotalErrors(56),
                slotCpuUtilization(57),
                slotMemoryUtilization(58),
                slotAlarmCount(59),
                slotFifoErrors(60),
                slotOperStatus(61),
                slotOperStatusChange(62),
                slotSecurityLockState(63),
                slotIOCardOperStatus(64),
                redundancyGroupPathChanges(67),
                redundancyGroupRollbackAttempts(68),
                redundancySecondsSinceCountersZeroed(69),
                redundancyPathTestAttempts(70),
                redundancyPathTestStatus(71),
                systemCurrentPctCPU(72),
                systemCurrentPctMemory(73),
                systemCurrentProcesses(74),
                systemCurrentTimers(75),
                systemCurrentPackets(76),
                systemCurrentIPCs(77),
                systemCurrentFreeMemory(78),
                systemWorstPctCPU(82),
                systemWorstPctMemory(83),
                systemWorstProcesses(84),
                systemWorstTimers(85),
                systemWorstPackets(86),
                systemWorstIPCs(87),
                systemWorstFreeMemory(88),
                systemUpTime(92),
                chassisSlotOperStatus(93),
                chassisSlotSecondsSinceReset(94),
                chassisSlotIOCardOperStatus(95),
                chassisSlotPlus5Status(96),
                chassisSlotPlus12Status(97),
                chassisSlotMinus12Status(98),
                chassisSlotPlus5Watts(99),
                chassisSlotPlus12Watts(100),
                chassisSlotMinus12Watts(101),
                powerSupplyRedundancyStatus(102),
                powerSupplyPlus5Status(103),
                powerSupplyPlus12Status(104),
                powerSupplyMinus12Status(105),
                powerSupplyThermalWarningStatus(106),
                powerSupplyThermalShutdownStatus(107),
                powerSupplyFanStatus(108),
                powerSupplyHardwareInhibitStatus(109),
                powerSupplyPlus5Volts(110),
                powerSupplyPlus12Volts(111),
                powerSupplyMinus12Volts(112),
                powerSupplyWatts(113),
                powerSupplyWattsMax(114),
                powerSupplyChassisWatts(115),
                powerSupplyChassisWattsMax(116),
                powerSupplyHardwareType(117)
            }
            ACCESS read-write
            STATUS mandatory
            DESCRIPTION "
                Use this field when you want to select an alarm
                variable without specifying its entire SNMP object
                identifier.  First, modify this field by selecting
                a variable from the list.  Then, read the key prompt
                fields.  They will direct you to specify key values
                appropriate to the selected variable.  The SNMP
                object identifier will be built for you when you
                are done.

                You may not modify this field at the same time that
                you modify the object identifier field.

                You may not modify this field once the alarm is
                completed (see alarm status field)."
            ::= { xRmonMBConfig 4 }

        mbAlarmKey1Meaning OBJECT-TYPE
            SYNTAX DisplayString (SIZE (0..47))
            ACCESS read-only
            STATUS mandatory
            DESCRIPTION "
                This field describes how its adjacent key value
                field will be interpreted when building a complete
                SNMP object identifier for the alarm variable.  The
                value of this field changes as you select different
                items from the quick list or specify different SNMP
                object identifiers.

                This object has the value 'not applicable' if its key
                value is not necessary or the object is unknown."
            ::= { xRmonMBConfig 5 }

        mbAlarmKey1 OBJECT-TYPE
            SYNTAX INTEGER
            ACCESS read-write
            STATUS mandatory
            DESCRIPTION "
                Specify a value here according the the instructions
                given in its adjacent prompt field.  That prompt
                explains how this field will be used.

                You may still modify this field even though the
                prompt field indicates that it is not applicable to
                the selected variable.  It will be ignored.

                You may not modify this field at the same time that
                you modify the object identifier field.

                You may not modify this field once the alarm is
                completed (see alarm status field)."
            ::= { xRmonMBConfig 6 }

        mbAlarmKey2Meaning OBJECT-TYPE
            SYNTAX DisplayString (SIZE (0..47))
            ACCESS read-only
            STATUS mandatory
            DESCRIPTION "
                This field describes how its adjacent key value
                field will be interpreted when building a complete
                SNMP object identifier for the alarm variable.  The
                value of this field changes as you select different
                items from the quick list or specify different SNMP
                object identifiers.

                This object has the value 'not applicable' if its key
                value is not necessary or the object is unknown."
            ::= { xRmonMBConfig 7 }

        mbAlarmKey2 OBJECT-TYPE
            SYNTAX INTEGER
            ACCESS read-write
            STATUS mandatory
            DESCRIPTION "
                Specify a value here according the the instructions
                given in its adjacent prompt field.  That prompt
                explains how this field will be used.

                In some cases, the value zero has a special meaning.
                This often occurs when you are prompted to enter a
                port number.  Zero indicates you want each port in
                the indicated slot to be monitored by this alarm.
                Only one alarm will exist, but it will generate an
                event each time any of the ports meets its criteria.

                You may still modify this field even though the
                prompt field indicates that it is not applicable to
                the selected variable.  It will be ignored.

                You may not modify this field at the same time that
                you modify the object identifier field.

                You may not modify this field once the alarm is
                completed (see alarm status field)."
            ::= { xRmonMBConfig 8 }

        mbAlarmSampleType OBJECT-TYPE
            SYNTAX INTEGER { absoluteValue(1), changeInValue(2) }
            ACCESS read-write
            STATUS mandatory
            DESCRIPTION "
                Use this field to select the method of calculating
                the value to be compared against the thresholds.

                When you set this to 'absoluteValue', the variable
                you specified is compared directly with the alarm
                thresholds at the end of each monitoring interval.

                When you set this to 'changeInValue', the change in
                the value of the variable over the interval is
                compared with the thresholds.  This is useful for
                detecting changes in rates of activity.

                You may not modify this field once the alarm is
                completed (see alarm status field)."
            ::= { xRmonMBConfig 9 }

        mbAlarmValue OBJECT-TYPE
            SYNTAX INTEGER
            ACCESS read-only
            STATUS mandatory
            DESCRIPTION "
                This field shows the value of the alarm variable at
                the end of the most recent monitoring interval.  If
                the alarm sample type is 'changeInValue', it instead
                shows the change in value over that interval.

                This field is zero any time the alarm is not active,
                or when the alarm is a wildcard (that is, a port or
                repeater number of 0 was specified for key 2 value).

                The value of this field has meaning after the alarm
                configuration is complete and monitoring begins."
            ::= { xRmonMBConfig 10 }

        -- The alarmStartupAlarm feature is not offered through this
        -- interface.  When creating alarms, risingOrFallingAlarm(3)
        -- is supplied.

        mbAlarmRisingThreshold OBJECT-TYPE
            SYNTAX INTEGER
            ACCESS read-write
            STATUS mandatory
            DESCRIPTION "
                This is the rising threshold value for the alarm.

                When the current alarm value, specified by the alarm
                sample type, is greater than or equal to this
                threshold, and the value at the previous sampling
                interval was less than this threshold, a single
                rising alarm event will be generated.

                Another rising alarm event will not be generated
                until the sampled value falls below the falling
                threshold value.

                You may not modify this field once the alarm is
                completed (see alarm status field)."
            ::= { xRmonMBConfig 11 }

        mbAlarmFallingThreshold OBJECT-TYPE
            SYNTAX INTEGER
            ACCESS read-write
            STATUS mandatory
            DESCRIPTION "
                This is the falling threshold value for the alarm.

                When the current alarm value, specified by the alarm
                sample type, is less than or equal to this
                threshold, and the value at the previous sampling
                interval was greater than this threshold, a single
                rising alarm event will be generated.

                Another rising alarm event will not be generated
                until the sampled value falls below the falling
                threshold value.

                You may not modify this field once the alarm is
                completed (see alarm status field)."
            ::= { xRmonMBConfig 12 }

        -- The alarmRisingEventIndex and alarmFallingEventIndex
        -- values are not accessible through this interface.  Instead,
        -- the value of mbAlarmRisingEventType indicates the event
        -- action.  A set to one of these entries will create an
        -- event entry unique to this alarm.  Choosing noAction(1)
        -- places a zero in the corresponding event index entry.
        -- Deleting an alarm will delete all of its event entries.

        mbAlarmRisingEventType OBJECT-TYPE
            SYNTAX INTEGER {
                noAction(1),
                logOnly(2),
                trapOnly(3),
                logAndTrap(4)
            }
            ACCESS read-write
            STATUS mandatory
            DESCRIPTION "
                Use this field to indicate the type of notification
                to make when the alarm variable exceeds its rising
                threshold.  The default action is to generate both
                a log entry and a trap.

                Set this field to noAction to suppress notification
                of rising threshold events.

                Set this field to logOnly to generate an RMON alarm
                log entry.  These log entries may be viewed through
                the RMON alarm log view.

                Set this field to trapOnly to generate an SNMP trap.
                Refer to the RMON alarm summary to specify whether
                traps are generated in standard RMON format or in
                iTouch format.

                Choosing logAndTrap invokes both these actions.

                You may not modify this field once the alarm is
                completed (see alarm status field)."
            DEFVAL { logAndTrap }
            ::= { xRmonMBConfig 13 }

        mbAlarmFallingEventType OBJECT-TYPE
            SYNTAX INTEGER {
                noAction(1),
                logOnly(2),
                trapOnly(3),
                logAndTrap(4)
            }
            ACCESS read-write
            STATUS mandatory
            DESCRIPTION "
                Use this field to indicate the type of notification
                to make when the alarm variable exceeds its falling
                threshold.  The default action is to generate both
                a log entry and a trap.

                Set this field to noAction to suppress notification
                of falling threshold events.

                Set this field to logOnly to generate an RMON alarm
                log entry.  These log entries may be viewed through
                the RMON alarm log view.

                Set this field to trapOnly to generate an SNMP trap.
                Refer to the RMON alarm summary to specify whether
                traps are generated in standard RMON format or in
                iTouch format.

                Choosing logAndTrap invokes both these actions.

                You may not modify this field once the alarm is
                completed (see alarm status field)."
            DEFVAL { logAndTrap }
            ::= { xRmonMBConfig 14 }

        -- The alarmOwner feature is not offered through this
        -- interface.  When creating alarms, a value of
        -- 'RMON monitor' is supplied.

        mbAlarmSummary OBJECT-TYPE
            SYNTAX DisplayString (SIZE (0..255))
            ACCESS read-only
            STATUS mandatory
            DESCRIPTION "
                As you make changes to the to alarm settings, this
                field is filled with an easily readable summary of
                the alarm parameters.  This is to make it easy for
                you to confirm that monitoring will behave as you
                expected once the alarm status is 'active'."
            ::= { xRmonMBConfig 15 }

        -- mbAlarmStatus is identical to mbAlarmCondition

        mbAlarmStatus OBJECT-TYPE
            SYNTAX INTEGER {
                underCreation(1),
                active(2),
                inactive(3),
                delete(4),
                held(5),
                noHubCard(6),
                oldFirmware(7),
                slotTimeout(8),
                slotFailed(9),
                monitorStopped(10),
                unknownVariable(11),
                keysMissing(12),
                noResources(13),
                loading(14),
                activating(15),
                deactivating(16),
                unsupported(17),
                unknownAlarm(18),
                inconsistency(19),
                invalidFlags(20),
                invalidSlot(21),
                inaccessible(22),
                otherError(23)
            }
            ACCESS read-write
            STATUS mandatory
            DESCRIPTION "
Describes the current operational state of the
alarm and allows you to make limited changes in
the state of the alarm for purposes of managing
its state.

You may set this field to one of: underCreation,
active, inactive, and delete.  All other values
report current status.

underCreation: Alarm configuration is incomplete.
You may modify alarm parameters.  No monitoring
is taking place for the alarm.  An alarm is saved
in a parameter file after configuration complete.
Select this state before changing a previously
completed alarm.

active: Alarm configuration is complete and active
monitoring of the alarm variable is in progress.
Select this state to complete an alarm or to begin
active monitioring of the alarm variable.

inactive: No monitoring of the alarm variable is
actively taking place.  Select this state when you
want to temporarily suppress monitoring for the
alarm.  Select 'active' to begin monitoring again.

delete: Select this state when you want to delete
this alarm and all log entries associated with it.

held: Active monitoring of the alarm variable is not
taking place because this system does not have RMON
Repeater Management set to 'enabled'.  Once you do
this, alarm monitoring begins automatically.

noHubCard: The target slot does not contain a
management card or repeater I/O card capable of
monitoring.  Monitoring will begin automatically
once the target slot is loaded with a supported
configuration.

oldFirmware: The I/O card in the target slot does
not contain monitoring firmware.  Monitoring will
begin automatically once that card has been loaded
with current scm firmware.

slotTimeout: The target slot did not respond to
attempts to activate the alarm.  May happen if the
management card in the target slot does not contain
monitoring software.  Monitoring begins automatically
once the target slot has been repaired or loaded
with current software.

slotFailed: Active monitoring of the alarm
variable stopped because the target slot was not
operating properly.  Monitoring automatically
resumes once the target slot has recovered.

monitorStopped: Active monitoring of the alarm
variable stopped due to some error.  This can
occur if the variable no longer exists because a
related configuration change has made it invalid.
Correct the condition and re-activate the alarm.

unknownVariable: The alarm variable specified by the
object ID is not recognized in the currently running
system.  Correct the entry.

keysMissing: One or more required key values are not
specified in the alarm variable object ID.  Correct
the entry.

noResources: Not enough system resources exist to
activate this alarm.  Reduce the use of packet buffers
or available memory and re-activate the alarm.

loading: The alarm is being read from a parameter
file and will soon be activated.  This condition
is transient.

activating: Monitoring of the alarm variable will
begin soon.  This condition is transient.

deactivating: Monitoring of the alarm variable will
stop soon.  This condition is transient.

unsupported: Monitoring for the alarm variable is
not supported by the target slot.  Monitoring will
begin once that card is loaded with current scm
firmware or software.

unknownAlarm: Monitoring stopped because the target
slot reset.  Monitoring will continue shortly.

inconsistency: Internal system error.

invalidFlags: Internal system error.

invalidSlot: Alarm specified for a slot which does
not exist in the chassis.  Modify and re-activate.

inaccessible: Monitoring of the alarm variable could
not begin.  This can occur if the key values are
invalid for the variable.  Correct and re-activate
the alarm.

otherError: An unspecified error has occurred."
            ::= { xRmonMBConfig 16 }

        -- The eventDescription field is set to contain a description
        -- of the alarm similar to the mbAlarmSummary field.

        -- The eventCommunity feature is not offered through this
        -- interface.  When creating events, a value of null is used.

        -- eventLastTimeSent is not reported through this interface
        -- because event entries created by it are shared among all
        -- alarms.

        -- The eventOwner feature is not offered through this
        -- interface.  When creating events, a value of
        -- 'RMON monitor' is supplied.

        -- The eventStatus feature is not offered through this
        -- interface.  Failure to create an event results in a
        -- mbAlarmRising/FallingEventType of noAction(1).


        -- The RMON MB Group Alarm View Table

        -- This table provides a human-readable interpretation of
        -- all RMON alarm group alarmTable entries, ordered by
        -- increasing value of alarmIndex.

        -- Though this table is indexed by alarmIndex, a separate
        -- index is supplied within the table to allow

        mbAlarmTable OBJECT-TYPE
            SYNTAX SEQUENCE OF MbAlarmEntry
            ACCESS not-accessible
            STATUS mandatory
            DESCRIPTION
                "A list of RMON alarms.  This table is indexed by
                alarmIndex to provide an intuitive mapping between
                alarms and descriptions."
            ::= { xRmonMB 2 }

        mbAlarmEntry OBJECT-TYPE
            SYNTAX MbAlarmEntry
            ACCESS not-accessible
            STATUS mandatory
            DESCRIPTION
                "A description of an RMON alarm which summarizes the
                actual RMON alarm and event parameters corresponding
                to this entry."
            INDEX { alarmIndex }
            ::= { mbAlarmTable 1 }

        MbAlarmEntry ::= SEQUENCE {
            mbAlarmCondition            INTEGER,
            mbAlarmDescription          DisplayString
        }

        -- mbAlarmCondition is identical to mbAlarmStatus

        mbAlarmCondition OBJECT-TYPE
            SYNTAX INTEGER {
                underCreation(1),
                active(2),
                inactive(3),
                delete(4),
                held(5),
                noHubCard(6),
                oldFirmware(7),
                slotTimeout(8),
                slotFailed(9),
                monitorStopped(10),
                unknownVariable(11),
                keysMissing(12),
                noResources(13),
                loading(14),
                activating(15),
                deactivating(16),
                unsupported(17),
                unknownAlarm(18),
                inconsistency(19),
                invalidFlags(20),
                invalidSlot(21),
                inaccessible(22),
                otherError(23)
            }
            ACCESS read-write
            STATUS mandatory
            DESCRIPTION "
Describes the current operational state of the
alarm and allows you to make limited changes in
the state of the alarm for purposes of managing
its state.

You may set this field to one of: underCreation,
active, inactive, and delete.  All other values
report current status.

underCreation: Alarm configuration is incomplete.
You may modify alarm parameters.  No monitoring
is taking place for the alarm.  An alarm is saved
in a parameter file after configuration complete.
Select this state before changing a previously
completed alarm.

active: Alarm configuration is complete and active
monitoring of the alarm variable is in progress.
Select this state to complete an alarm or to begin
active monitioring of the alarm variable.

inactive: No monitoring of the alarm variable is
actively taking place.  Select this state when you
want to temporarily suppress monitoring for the
alarm.  Select 'active' to begin monitoring again.

delete: Select this state when you want to delete
this alarm and all log entries associated with it.

held: Active monitoring of the alarm variable is not
taking place because this system does not have RMON
Repeater Management set to 'enabled'.  Once you do
this, alarm monitoring begins automatically.

noHubCard: The target slot does not contain a
management card or repeater I/O card capable of
monitoring.  Monitoring will begin automatically
once the target slot is loaded with a supported
configuration.

oldFirmware: The I/O card in the target slot does
not contain monitoring firmware.  Monitoring will
begin automatically once that card has been loaded
with current scm firmware.

slotTimeout: The target slot did not respond to
attempts to activate the alarm.  May happen if the
management card in the target slot does not contain
monitoring software.  Monitoring begins automatically
once the target slot has been repaired or loaded
with current software.

slotFailed: Active monitoring of the alarm
variable stopped because the target slot was not
operating properly.  Monitoring automatically
resumes once the target slot has recovered.

monitorStopped: Active monitoring of the alarm
variable stopped due to some error.  This can
occur if the variable no longer exists because a
related configuration change has made it invalid.
Correct the condition and re-activate the alarm.

unknownVariable: The alarm variable specified by the
object ID is not recognized in the currently running
system.  Correct the entry.

keysMissing: One or more required key values are not
specified in the alarm variable object ID.  Correct
the entry.

noResources: Not enough system resources exist to
activate this alarm.  Allocate more packet buffers
or increase free memory and re-activate the alarm.

loading: The alarm is being read from a parameter
file and will soon be activated.  This condition
is transient.

activating: Monitoring of the alarm variable will
begin soon.  This condition is transient.

deactivating: Monitoring of the alarm variable will
stop soon.  This condition is transient.

unsupported: Monitoring for the alarm variable is
not supported by the target slot.  Monitoring will
begin once that card is loaded with current scm
firmware or software.

unknownAlarm: Monitoring stopped because the target
slot reset.  Monitoring will continue shortly.

inconsistency: Internal system error.

invalidFlags: Internal system error.

invalidSlot: Alarm specified for a slot which does
not exist in the chassis.  Modify and re-activate.

inaccessible: Monitoring of the alarm variable could
not begin.  This can occur if the key values are
invalid for the variable.  Correct and re-activate
the alarm.

otherError: An unspecified error has occurred."
            ::= { mbAlarmEntry 1 }

        mbAlarmDescription OBJECT-TYPE
            SYNTAX DisplayString (SIZE (0..255))
            ACCESS read-only
            STATUS mandatory
            DESCRIPTION "
                An easily-readable summary of an RMON alarm.

                The general format is:  ' when 
                   is >=  or <= 
                .'

                 is from: 'Do nothing', 'Create log record',
                'Generate trap', 'Create log and trap', or 'Various
                actions', based on the alarm rising and falling
                event types.

                 is one of 'value of' or 'change in',
                according to the alarm sample type.

                , if recognized, describes the quick list
                selection.  If unlisted, the object identifier is
                substituted.

                 and  appear only if  is
                recognized and represent phrases like 'slot',
                'port', and 'any port'.

                 and  represent the rising and falling
                threshold values, respectively.

                The  phrase describes the units per N
                seconds or the length of the sample interval in
                seconds."
            ::= { mbAlarmEntry 2 }


        -- The RMON MB Group Log View Table

        -- This table provides a human-readable interpretation of
        -- all RMON event group logTable entries, ordered by time
        -- of creation, most recent first.

        mbLogTable OBJECT-TYPE
            SYNTAX SEQUENCE OF MbLogEntry
            ACCESS not-accessible
            STATUS mandatory
            DESCRIPTION
                "A list of RMON logTable entries."
            ::= { xRmonMB 3 }

        mbLogEntry OBJECT-TYPE
            SYNTAX MbLogEntry
            ACCESS not-accessible
            STATUS mandatory
            DESCRIPTION
                "A human-readable description of an RMON event."
            INDEX { mbLogIndex }
            ::= { mbLogTable 1 }

        MbLogEntry ::= SEQUENCE {
            mbLogIndex                INTEGER,
            mbLogDescription          DisplayString
        }

        mbLogIndex OBJECT-TYPE
            SYNTAX INTEGER
            ACCESS read-only
            STATUS mandatory
            DESCRIPTION "
                An index uniquely identifying an entry in this log
                table. Each such entry describes, in human-readable
                format, an RMON event occurring for an alarm.  All
                RMON log table entries are shown, ordered most
                recent first."
            ::= { mbLogEntry 1 }

        mbLogDescription OBJECT-TYPE
            SYNTAX DisplayString (SIZE (0..255))
            ACCESS read-only
            STATUS mandatory
            DESCRIPTION "
                An easily-readable summary of an RMON log entry.

                The general format is: ': alarm 
                    is
                 .'

                 is the date and time the entry was created.

                 is the alarm index causing the report.

                 is one of 'value of  for' or 'change
                of  for', according to the alarm sample type.
                 is the actual value triggering the report.

                , if recognized, describes the quick list
                selection.  If unlisted, the object identifier is
                substituted.

                 and  appear only if  is
                recognized and represent phrases like 'slot',
                'port', and 'any port'.

                 is one of '>= ' or '<= ' where  and
                 represent the rising and falling threshold
                values, respectively.

                The  phrase describes the units per N
                seconds or the length of the sample interval in
                seconds."
            ::= { mbLogEntry 2 }


        -- The RMON Resource Table

        -- Standard RMON does not place limits on the number of rows
        -- in its tables.  This table provides controls to specify
        -- and monitor the lengths of some RMON tables.

        mbResourceTable OBJECT-TYPE
            SYNTAX SEQUENCE OF MbResourceEntry
            ACCESS not-accessible
            STATUS mandatory
            DESCRIPTION
                "A list of RMON resource entries."
            ::= { xRmonMB 4 }

        mbResourceEntry OBJECT-TYPE
            SYNTAX MbResourceEntry
            ACCESS not-accessible
            STATUS mandatory
            DESCRIPTION
                "Values to control and monitor RMON resources."
            INDEX { mbResourceType }
            ::= { mbResourceTable 1 }

        MbResourceEntry ::= SEQUENCE {
            mbResourceType         INTEGER,
            mbResourceCurrent      Gauge,
            mbResourceWorst        Gauge,
            mbResourceMaximum      INTEGER,
            mbResourceOperMaximum  INTEGER
        }

        mbResourceType OBJECT-TYPE
            SYNTAX INTEGER { rmonAlarms(1),
                             rmonEvents(2),
                             rmonLogEntries(3),
                             rmonStatistics(4)
            }
            ACCESS read-only
            STATUS mandatory
            DESCRIPTION
                "Identification of an RMON resource type.  Typically
                each type corresponds to an RMON table whose size is
                to be controlled and monitored."
            ::= { mbResourceEntry 1 }

        mbResourceCurrent OBJECT-TYPE
            SYNTAX Gauge
            ACCESS read-only
            STATUS mandatory
            DESCRIPTION "
                The number of entries currently allocated by RMON."
            ::= { mbResourceEntry 2 }

        mbResourceWorst OBJECT-TYPE
            SYNTAX Gauge
            ACCESS read-only
            STATUS mandatory
            DESCRIPTION "
                The highest number of entries ever allocated by
                RMON since system initialization."
            ::= { mbResourceEntry 3 }

        mbResourceMaximum OBJECT-TYPE
            SYNTAX INTEGER
            ACCESS read-write
            STATUS mandatory
            DESCRIPTION "
                The desired maximum possible number of resources of
                this type RMON is permitted to use at any one time.

                Changes to alarm, event, and log entry resource
                settings take effect immediately.

                Changes to the statistics resource takes place after
                the system is initialized.

                For alarms and events, this value may not be set
                less than the current number of entries in use."
            ::= { mbResourceEntry 4 }

        mbResourceOperMaximum OBJECT-TYPE
            SYNTAX INTEGER
            ACCESS read-only
            STATUS mandatory
            DESCRIPTION "
                The actual maximum number of resources of this type
                RMON will attempt to use at any one time.  This is
                the limit in effect for the current system."
            ::= { mbResourceEntry 5 }


        -- The RMON Map Table

        -- This table is used to define RMON EtherStats tables
        -- for repeater ports.  ifTable entries are created that
        -- correspond to etherStatsTables for repeater ports.
        -- Entries created through this interface will have an
        -- owner string of 'RMON monitor'.

        xRmonMapTable OBJECT-TYPE
            SYNTAX SEQUENCE OF XRmonMapEntry
            ACCESS not-accessible
            STATUS mandatory
            DESCRIPTION
                "A list of RMON map entries."
            ::= { xRmon 3 }

        xRmonMapEntry OBJECT-TYPE
            SYNTAX XRmonMapEntry
            ACCESS not-accessible
            STATUS mandatory
            DESCRIPTION
                "Values to create RMON statistics tables for
                repeater ports."
            INDEX { etherStatsIndex }
            ::= { xRmonMapTable 1 }

        XRmonMapEntry ::= SEQUENCE {
            xRmonMapSlot           INTEGER,
            xRmonMapPort           INTEGER,
            xRmonMapIfIndex        INTEGER
        }

        xRmonMapSlot OBJECT-TYPE
            SYNTAX INTEGER
            ACCESS read-write
            STATUS mandatory
            DESCRIPTION "
                The slot the statistics will come from."
            ::= { xRmonMapEntry 1 }

        xRmonMapPort OBJECT-TYPE
            SYNTAX INTEGER
            ACCESS read-write
            STATUS mandatory
            DESCRIPTION "
                The port the statistics will come from."
            ::= { xRmonMapEntry 2 }

        xRmonMapIfIndex OBJECT-TYPE
            SYNTAX INTEGER
            ACCESS read-only
            STATUS mandatory
            DESCRIPTION "
                The interface index (ifIndex) corresponding to
                this statistics table."
            ::= { xRmonMapEntry 3 }

        -- ITouch RMON Traps

        iTouchAlarm TRAP-TYPE
            ENTERPRISE xRmon
            VARIABLES { mbLogDescription }
            DESCRIPTION
                "The SNMP trap that is generated when xRmonTrapType
                is set to iTouchFormat(2).  These traps, like the
                RMON standardFormat(1) traps, occur when an alarm
                variable crosses its rising or falling threshold
                and generates an event configured to send SNMP traps.

                The format of the DisplayString embodied by the
                trap PDU is identical to that of mbLogDescription.
                The actual object identifier is not significant."
            ::= 1



--
-- FILE: /users/sse/mibs/src/itouch/it-system-mib.mib
--

-- $Id: it-system-mib.mib,v 1.7 2001/08/17 14:28:38 sse Exp $


            xSystem         OBJECT IDENTIFIER ::= { iTouch 1 }

            -- This is a MIB module for all iTouch Communications systems.

            -- Copyright 2000 iTouch Communications, Inc. All Rights Reserved.
            -- Reproduction of this document is authorized on
            -- condition that this copyright notice is included.
            -- This MIB document embodies iTouch Communications, Inc.'s 
            -- proprietary intellectual property.  iTouch Communications, Inc.
            -- retains all title and ownership in this MIB, including any
            -- revisions.
            --
            -- It is iTouch Communications, Inc.'s intent to encourage the
            -- widespread use of this MIB in connection with the management of
            -- iTouch Communications, Inc. products. iTouch Communications,
            -- Inc. grants vendors,end-users, and other interested parties a
            -- non-exclusive license to use this MIB in connection with the
            -- management of iTouch Communications, Inc. products.
            --
            -- This MIB document is supplied "AS IS," and iTouch 
            -- Communications, Inc. makes no warranty, either express or
            -- implied, as to the use operation, condition, or performance of
            -- the MIB.


            -- the System group

            -- Implementation of this group is mandatory for all iTouch
            -- systems.

            sysIdent OBJECT-TYPE
                SYNTAX DisplayString (SIZE (0..50))
                ACCESS read-write
                STATUS mandatory
                DESCRIPTION
                    "An identification string for local and remote 
                    displays.  Corresponds directly to SERVER 
                    IDENTIFICATION and the value labeled 
                    'Identification:' on the SERVER CHARACTERISTICS 
                    display."
                ::= { xSystem 1 }

            sysDefineMode OBJECT-TYPE
                SYNTAX INTEGER { permOnly(1), operAndPerm(2) }
                ACCESS read-write
                STATUS mandatory
                DESCRIPTION
                    "The system's operation with regard to DEFINE 
                    commands.  'permOnly' indicates that DEFINE commands 
                    modify only the permanent data base.  'operAndPerm' 
                    indicates that DEFINE commands modify both 
                    operational and permanent data bases, unless 
                    specifically documented to the contrary.  
                    Corresponds to SERVER CHANGE and the presence of the 
                    label CHANGE in the SERVER CHARACTERISTICS 
                    display."
                ::= { xSystem 2 }

            sysDateTime OBJECT-TYPE
                SYNTAX DateTime
                ACCESS read-write
                STATUS mandatory
                DESCRIPTION
                    "The system's current local date and time.  
                    Corresponds directly to SERVER DATE and SERVER TIME 
                    and the value in various displays."
                ::= { xSystem 3 }

            sysTimeZone OBJECT-TYPE
                SYNTAX OCTET STRING (SIZE (2))
                ACCESS read-write
                STATUS mandatory
                DESCRIPTION
                    "The adjustment to apply to a universal (Greenwich) 
                    time received when down-line loaded, comprising two 
                    octets.  The first octet is the number of hours west 
                    of universal, the second is the number of minutes.  
                    Corresponds directly to SERVER TIMEZONE and the 
                    value labeled 'Timezone:' in the SERVER 
                    CHARACTERISTICS display."
                ::= { xSystem 4 }

            sysLoadSoftware OBJECT-TYPE
                SYNTAX DisplayString (SIZE (0..16))
                ACCESS read-write
                STATUS mandatory
                DESCRIPTION
                    "The software file name to request for down-line 
                    load of the server.  Corresponds directly to SERVER 
                    SOFTWARE, and the value labeled 'Software:' in the 
                    SERVER CHARACTERISTICS display."
                ::= { xSystem 5 }

            sysDump OBJECT-TYPE
                SYNTAX INTEGER { disabled(1), enabled(2) }
                ACCESS read-write
                STATUS mandatory
                DESCRIPTION
                    "Control for dumping the system's memory when the 
                    system crashes.  Corresponds directly to SERVER DUMP 
                    and the presence of 'Dump' under the label 'Enabled 
                    Characteristics' in the SERVER CHARACTERISTICS 
                    display."
                ::= { xSystem 6 }

            sysMaintenancePassword OBJECT-TYPE
                SYNTAX OCTET STRING (SIZE (0..8))
                ACCESS read-write
                STATUS mandatory
                DESCRIPTION
                    "The password a management system must supply to 
                    force the system to reboot or use the system's 
                    remote console via the Maintenance Operation 
                    Protocol (MOP).  Corresponds directly to SERVER 
                    MAINTENANCE PASSWORD.

                    When setting this value, the management system must 
                    supply eight octets, filling with zeros from the 
                    first octet.  That is, the value '1ab42' would be 
                    expressed as '0.0.0.0.0.1.ab.42'.  Setting the value 
                    to zero disables the password check.

                    When returning this value, the agent always returns 
                    a zero length OCTET STRING."
                ::= { xSystem 7 }

            sysLocalName OBJECT-TYPE
                SYNTAX DisplayString (SIZE (1..16))
                ACCESS read-write
                STATUS mandatory
                DESCRIPTION
                    "The system's local name.  Corresponds directly to 
                    SERVER NAME and the value labeled 'Name:' in the 
                    SERVER CHARACTERISTICS display."
                ::= { xSystem 8 }

            sysSoftwareVersionType OBJECT-TYPE
                SYNTAX INTEGER { alpha(1), beta(2),
                                 production(3), special(4) }
                ACCESS read-only
                STATUS mandatory
                DESCRIPTION
                    "The software version variant running in the system.  
                    Corresponds to the letter in the software version in 
                    the SERVER CHARACTERISTICS display.

                    alpha         'A':   alpha test
                    beta          'B':   beta test
                    production    null:  normal, production software
                    special       'S':   special, custom software
                    "
                ::= { xSystem 9 }

            sysSoftwareVersion OBJECT-TYPE
                SYNTAX OCTET STRING (SIZE (4))
                ACCESS read-only
                STATUS mandatory
                DESCRIPTION
                    "The software version running in the system.  In 
                    order, the octets contain major version, minor 
                    version, ECO, and pre-release number.  Corresponds 
                    to the numbers in the software version in the SERVER 
                    CHARACTERISTICS display.

                    For example, the version display for 
                    sysSoftwareVersionType 'production' and 
                    sysSoftwareVersion '2.2.0.0' is 'V2.2'.

                    The version display for sysSoftwareVersionType 
                    'beta' and sysSoftwareVersion '3.1.0.4' is 
                    'V3.1B4'."
                ::= { xSystem 10 }

            sysRomVersion OBJECT-TYPE
                SYNTAX INTEGER
                ACCESS read-only
                STATUS mandatory
                DESCRIPTION
                    "The firmware version of the bootstrap ROM installed 
                    in the system.  Corresponds directly to the value 
                    labeled 'Rom' in the SERVER CHARACTERISTICS 
                    display."
                ::= { xSystem 11 }

            sysHardwareType OBJECT-TYPE
                SYNTAX HardwareType
                ACCESS read-only
                STATUS mandatory
                DESCRIPTION
                    "The type of hardware on which the system is 
                    running.  Corresponds directly to the value labeled 
                    'Hardware Type:' in the UNIT display."
                ::= { xSystem 12 }

            sysHardwareVersion OBJECT-TYPE
                SYNTAX INTEGER
                ACCESS read-only
                STATUS mandatory
                DESCRIPTION
                    "This version of hardware on which the system is 
                    running.  Corresponds directly to part of the value 
                    labeled 'HW' in the SERVER CHARACTERISTICS 
                    display."
                ::= { xSystem 13 }

            sysChassisType OBJECT-TYPE
                SYNTAX ChassisType
                ACCESS read-only
                STATUS mandatory
                DESCRIPTION
                    "The type of chassis in which the system is running.  
                    Corresponds directly to part of the value labeled 
                    'HW' in the SERVER CHARACTERISTICS display."
                ::= { xSystem 14 }

            sysChassisVersion OBJECT-TYPE
                SYNTAX INTEGER
                ACCESS read-only
                STATUS mandatory
                DESCRIPTION
                    "This version of chassis in which the system is 
                    running.  Corresponds directly to part of the value 
                    labeled 'HW' in the SERVER CHARACTERISTICS 
                    display."
                ::= { xSystem 15 }

            sysCrash OBJECT-TYPE
                SYNTAX INTEGER { ready(1), execute(2) }
                ACCESS read-write
                STATUS mandatory
                DESCRIPTION
                    "Control to cause this system to crash.  In response 
                    to a get-request or get-next-request, the agent 
                    always returns 'ready' for this value.  Setting the 
                    value to 'ready' has no effect.  Setting it to 
                    'execute' causes an immediate crash.  Corresponds to 
                    the CRASH command."
            ::= { xSystem 16 }

            sysInitialize OBJECT-TYPE
                SYNTAX INTEGER { ready(1), conditionalExecute(2),
                                 unconditionalExecute(3), cancel(4) }
                ACCESS read-write
                STATUS mandatory
                DESCRIPTION
                    "Control to cause this system to reset its software 
                    to initial load values, typically by reloading.  
                    When executing an initialize command, the system 
                    observes the value of sysInitializeDelay as supplied 
                    anywhere in the same set request with sysInitialize. 
                     If this value is not included in the set request, 
                    the system uses its default value.

                    In response to a get-request or get-next-request, 
                    the agent always returns 'ready' for this value.  

                    Setting the value to 'ready' has no effect.  Setting 
                    it to 'conditionalExecute' causes initialization if 
                    the overall system state is acceptible (such as not 
                    needing to store permanent parameters).  Setting it 
                    to 'unconditionalExecute' causes initialization 
                    regardless of the overall system state.  Setting it 
                    to 'cancel' aborts an initialization that has not 
                    yet started.  According to standard SNMP operation, 
                    if the system is not in a proper state to accept a 
                    given set request for this value, it returns the 
                    standard SNMP error 'badValue'.

                    Corresponds to the INITIALIZE command."
                ::= { xSystem 17 }

            sysInitializeDelay OBJECT-TYPE
                SYNTAX INTEGER (0..32767)
                ACCESS read-write
                STATUS mandatory
                DESCRIPTION
                    "The number of minutes to delay before beginning the 
                    system initialization process as executed with 
                    sysInitialize.

                    This value cannot be set outside a set-request that 
                    contains the value 'execute' for sysInitialize.  If 
                    not included in such a set, the default value is 1.

                    Corresponds to the INITIALIZE command's DELAY 
                    parameter and to the value labeled 'Minutes to 
                    shutdown:' in the SYSTEM STATUS display."
                ::= { xSystem 18 }

            sysZeroAll OBJECT-TYPE
                SYNTAX INTEGER { ready(1), execute(2) }
                ACCESS read-write
                STATUS mandatory
                DESCRIPTION
                    "Control to zero all counters.  In response to a 
                    get-request or get-next-request, the agent always 
                    returns 'ready' for this value.  Setting the value 
                    to 'ready' has no effect.  Setting it to 'execute' 
                    causes all the system's counters to be zeroed.  
                    Corresponds to the ZERO ALL command."
                ::= { xSystem 19 }

            sysZeroBase OBJECT-TYPE
                SYNTAX INTEGER { ready(1), execute(2) }
                ACCESS read-write
                STATUS mandatory
                DESCRIPTION
                    "Control to zero all base counters.  In response to 
                    a get-request or get-next-request, the agent always 
                    returns 'ready' for this value.  Setting the value 
                    to 'ready' has no effect.  Setting it to 'execute' 
                    causes all the system's base counters to be zeroed.  
                    Examples of counters that are zeroed are the SNMP 
                    counters or the counters from the SYSTEM COUNTERS 
                    display.  Examples of counters that are not zeroed 
                    are Ethernet interface counters or port counters.  
                    Corresponds to the ZERO SYSTEM command."
                ::= { xSystem 20 }

            sysZeroBaseTime OBJECT-TYPE
                SYNTAX TimeTicks
                ACCESS read-only
                STATUS mandatory
                DESCRIPTION
                    "The number hundredths of a second since the most 
                    recent zeroing of the base counters, such as through 
                    execution of sysZeroAll or sysZeroBase.  Corresponds 
                    directly to the value labeled 'Seconds Since 
                    Zeroed:' in the SERVER COUNTERS display."
                ::= { xSystem 21 }

            sysLoaderName OBJECT-TYPE
                SYNTAX DisplayString (SIZE (0..40))
                ACCESS read-only
                STATUS mandatory
                DESCRIPTION
                    "The name of the system that provided this system's 
                    running software.  Corresponds directly to the value 
                    labeled 'Primary Host:' in the SERVER STATUS 
                    display."
                ::= { xSystem 22 }

            sysLoaderAddressType OBJECT-TYPE
                SYNTAX AddressType
                ACCESS read-only
                STATUS mandatory
                DESCRIPTION
                    "The type of network address contained in 
                    sysLoaderAddress.  'unknown' means no address has 
                    been defined.  'other' means no other type value 
                    applies.  'local' means there is no address and this 
                    system's software was loaded from local storage.  
                    'ip' is an Internet IP address.  'ethernet' is an 
                    802.3 MAC address.  Corresponds indirectly to the 
                    value labeled 'Load Address:' in the SERVER STATUS 
                    display."
                ::= { xSystem 23 }

            sysLoaderAddress OBJECT-TYPE
                SYNTAX OCTET STRING
                ACCESS read-only
                STATUS mandatory
                DESCRIPTION
                    "The network address of the system that provided 
                    this system's running software.  Corresponds 
                    directly to the value labeled 'Load Address:' in the 
                    SERVER STATUS display."
                ::= { xSystem 24 }

            sysDumperAddressType OBJECT-TYPE
                SYNTAX AddressType
                ACCESS read-only
                STATUS mandatory
                DESCRIPTION
                    "The type of network address contained in 
                    sysDumperAddress.  'unknown' means no address has 
                    been defined.  'other' means no other type value 
                    applies.  'local' means there is no address and this 
                    system's was dumped to local storage.  'ip' is an 
                    Internet IP address.  'ethernet' is an 802.3 MAC 
                    address.  Corresponds indirectly to the value 
                    labeled 'Dump Address:' in the SERVER STATUS 
                    display."
                ::= { xSystem 25 }

            sysDumperAddress OBJECT-TYPE
                SYNTAX OCTET STRING
                ACCESS read-only
                STATUS mandatory
                DESCRIPTION
                    "The network address of the system that most 
                    recently accepted a crash dump from this system.  
                    Corresponds directly to the value labeled 'Dump 
                    Address:' in the SERVER STATUS display."
                ::= { xSystem 26 }

            sysResourceLacks OBJECT-TYPE
                SYNTAX Counter
                ACCESS read-only
                STATUS mandatory
                DESCRIPTION
                    "The number of times a local resource allocation 
                    failed, for example due to lack of dynamic memory.  
                    Corresponds directly to the value labeled 'Resource 
                    Errors:' in the SERVER STATUS display."
                ::= { xSystem 27 }

            sysChassisState OBJECT-TYPE
                SYNTAX INTEGER { notApplicable(1), noFault(2), fault(3),
                                 loop(4) }
                ACCESS read-only
                STATUS mandatory
                DESCRIPTION
                    "For chassis-based systems, the state of the overall 
                    chassis.  'notApplicable' indicates the system is 
                    not chassis based.  'noFault' indicates no current 
                    chassis problem.  'fault' indicates a current 
                    chassis problem such as a card or power supply 
                    failure.  Corresponds directly to the value labeled 
                    'Crate Current State: in the SERVER ALTERNATE STATUS 
                    display."
                ::= { xSystem 28 }

            sysChassisFaultTransitions OBJECT-TYPE
                SYNTAX Counter
                ACCESS read-only
                STATUS mandatory
                DESCRIPTION
                    "The number of times this system has seen 
                    sysChassisState switch from 'noFault' to 'fault' or 
                    from 'fault' to 'noFault'.  Corresponds directly to 
                    the value labeled 'Crate Transition Count: in the 
                    SERVER ALTERNATE STATUS display."
                ::= { xSystem 29 }

            sysResourceNumber OBJECT-TYPE
                SYNTAX INTEGER
                ACCESS read-only
                STATUS mandatory
                DESCRIPTION
                    "The number of resource entries in the Resource 
                    table."
                ::= { xSystem 30 }

            sysFeatureNumber OBJECT-TYPE
                SYNTAX INTEGER
                ACCESS read-only
                STATUS mandatory
                DESCRIPTION
                    "The number of feature entries in the Feature 
                    table."
                ::= { xSystem 31 }

            -- more base objects following tables


            -- the Resource table

            resTable OBJECT-TYPE
                SYNTAX SEQUENCE OF ResEntry
                ACCESS not-accessible
                STATUS mandatory
                DESCRIPTION
                    "A list of resource entries.  The number of entries 
                    is given by the value of sysResourceNumber."
                ::= { xSystem 32 }

            resEntry OBJECT-TYPE
                SYNTAX ResEntry
                ACCESS not-accessible
                STATUS mandatory
                DESCRIPTION
                    "Status values for a system resource."
                INDEX { resType }
                ::= { resTable 1 }

            ResEntry ::=
                SEQUENCE {
                    resType
                        INTEGER,
                    resCurrent
                        Gauge,
                    resWorst
                        Gauge,
                    resAdminMaximum
                        INTEGER,
                    resLacks
                        Counter,
                    resLackTime
                        DateTime,
                    resOperMaximum
                        INTEGER
                }

            resType OBJECT-TYPE
                SYNTAX INTEGER { cpuPercent(1), memoryPercent(2),
                                 process(3), timer(4), packetBuffer(5),
                                 ipcMessage(6), textPool(7),
                                 freeMemory(8), globalMemoryPercent(9),
                                 phivDecnetRouteCache(10),
                                 ipFilterCache(11), ipRouteCache(12),
                                 ipxRouteCache(13), ipPolicyTable(14),
                                 ipFilterTable(15),
                                 phivDecnetPolicyTable(16),
                                 phivDecnetFilterTable(17),
                                 appleRouteCache(18),
                                 appleFilterTable(19),
                                 repeaterPortAccessTable(20),
                                 repeaterPortNameTable(21),
                                 ipxRipTable(22), ipxSapTable(23),
                                 repeaterPortSecurityTable(24),
                                 bridgeFilterTable(25),
                                 bridgeStaticFilters(26),
                                 bridgeSourceFilters(27),
                                 bridgeLearnedFilters(28),
                                 bridgeInactiveFilters(29),
                                 bridgeProtocolFilters(30),
                                 latAnnouncementCompressionTable(31),
                                 packetCompressionTable(32),
                                 ipFragmentTable(33),
                                 repeaterRedundancyTable(34),
                                 repeaterGlobalSecurityTable(35),
				 packetHeaders(36), interfaces(37),
				 circuits(38), ipIgmpTable(39),
				 ipMulticastTable(40), ipRouteTable(41),
				 ipxRipFilterTable(42), ipxSapFilterTable(43)
                               }
                ACCESS read-only
                STATUS mandatory
                DESCRIPTION
                    "Identification of a resource type.  Typically 
                    corresponds directly to a label such as 'Processes:' 
                    in the SERVER ALTERNATE STATUS display."
                ::= { resEntry 1 }

            resCurrent OBJECT-TYPE
                SYNTAX Gauge
                ACCESS read-only
                STATUS mandatory
                DESCRIPTION
                    "The number of resources currently in use on the 
                    system.  Typically corresponds directly to a value 
                    labeled 'Cur' in the SERVER ALTERNATE STATUS 
                    display."
                ::= { resEntry 2 }

            resWorst OBJECT-TYPE
                SYNTAX Gauge
                ACCESS read-only
                STATUS mandatory
                DESCRIPTION
                    "The highest or lowest value of resCurrent since 
                    system initialization.  Typically corresponds 
                    directly to a value labeled 'High' or 'Low' in the 
                    SERVER ALTERNATE STATUS display."
                ::= { resEntry 3 }

            resAdminMaximum OBJECT-TYPE
                SYNTAX INTEGER
                ACCESS read-write
                STATUS mandatory
                DESCRIPTION
                    "The desired maximum possible number of resources in 
                    the system.  In many cases, ACCESS to this object 
                    for a particular resType is read-only.  Typically 
                    corresponds directly to a value labeled 'Max' in the 
                    SERVER ALTERNATE STATUS display for desired, 
                    administrative values.  When the desired change 
                    takes effect is implementation specific, ranging 
                    from immediately to the next system initialization."
                ::= { resEntry 4 }

            resLacks OBJECT-TYPE
                SYNTAX Counter
                ACCESS read-only
                STATUS mandatory
                DESCRIPTION
                    "The number of times since system initialization 
                    that the system could not obtain the resource 
                    because none were available.  Typically corresponds 
                    directly to a value labeled 'Failure' in the SERVER 
                    ALTERNATE STATUS display.

                    If such failures do not apply to the particular 
                    resource, such as 'cpuPercent', the agent returns 
                    zero for this object."
                ::= { resEntry 5 }

            resLackTime OBJECT-TYPE
                SYNTAX DateTime
                ACCESS read-only
                STATUS mandatory
                DESCRIPTION
                    "The local system date and time when resLack last 
                    increased.  Typically corresponds directly to a 
                    value labeled 'Last Occurred' in the SERVER 
                    ALTERNATE STATUS display.

                    If such failures do not apply to the particular 
                    resource, such as 'cpuPercent', the agent returns 
                    all zeroes (unknown) for this object."
            ::= { resEntry 6 }

            resOperMaximum OBJECT-TYPE
                SYNTAX INTEGER
                ACCESS read-only
                STATUS mandatory
                DESCRIPTION
                    "The current maximum possible number of resources in 
                    the system.  Typically corresponds directly to a 
                    value labeled 'Max' in the SERVER ALTERNATE STATUS 
                    display for current operational values.  This value 
                    is based on current or previous value of 
                    resAdminMaximum."
                ::= { resEntry 7 }


            -- the Feature table

            featTable OBJECT-TYPE
                SYNTAX SEQUENCE OF FeatEntry
                ACCESS not-accessible
                STATUS mandatory
                DESCRIPTION
                    "A list of feature entries.  The number of entries 
                    is given by the value of sysFeatureNumber."
                ::= { xSystem 33 }

            featEntry OBJECT-TYPE
                SYNTAX FeatEntry
                ACCESS not-accessible
                STATUS mandatory
                DESCRIPTION
                    "Status values for a system feature."
                INDEX { featType }
                ::= { featTable 1 }

            FeatEntry ::=
                SEQUENCE {
                    featType
                        INTEGER,
                    featStatus
                        INTEGER,
                    featKey
                        DisplayString
                }

            featType OBJECT-TYPE
                SYNTAX INTEGER { help(1), snmp(2), xremote(3),
                                 tn3270(4), menu(5), multisessions(6),
                                 lat(7), eventLog(8),
                                 internetSecurity(9), slip(10),
                                 scriptServer(11), kerberos(12),
                                 telnet(13), rlogin(14), allPorts(15),
                                 xprinter(16), x25(17),
                                 frameRelay(18),
                                 ipMulticastSpecial(19),
                                 changeEthernetAddress(20),
                                 expanded800(21), lpDaemon(22),
                                 ppp(23), unixCommands(24),
                                 arap(25), fingerDaemon(26),
                                 routeDaemon(27), rwhoDaemon(28),
                                 securID(29), apd(30), ipxRouting(31),
                		 ipxFiltering(32), ipFiltering(33), 
                                 kerberos5(34), radius(35), 
                                 enviromentalManager(36), terminalServer(37),
                                 ssh(38), tl1(39) }
                ACCESS read-only
                STATUS mandatory
                DESCRIPTION
                    "Identification of a feature type.  Corresponds to a 
                    SERVER feature keyword."
                ::= { featEntry 1 }

            featStatus OBJECT-TYPE
                SYNTAX INTEGER { disabled(1), enabled(2), locked(3) }
                ACCESS read-write
                STATUS mandatory
                DESCRIPTION
                    "The status of the feature as of the next system 
                    initialization.  Corresponds to the presence of the 
                    feature's lable following the label 'Enabled 
                    Feature(s): in the UNIT display."
                ::= { featEntry 2 }

            featKey OBJECT-TYPE
                SYNTAX DisplayString (SIZE (8))
                ACCESS read-write
                STATUS mandatory
                DESCRIPTION
                    "The key a management system must supply to make a 
                    locked feature available.  When unlocking a feature 
                    and the management system does not supply a value 
                    for featStatus, that object's value is 
                    implementation dependent.

                    When returning this value, the agent always returns 
                    a zero length DisplayString."
                ::= { featEntry 3 }


            -- the Boot Control group

            -- The Boot Control group contains parameters to control
            -- how a system loads and dumps its runtime software and
            -- parameters.  Typically these parameters are kept for
            -- and used by system initialization firmware.

            -- This group is deprecated in favor of the Boot Control
            -- Record table, found later in this MIB.

            xBootControl OBJECT IDENTIFIER ::= { xSystem 34 }

            bootControlLoadInternetFile OBJECT-TYPE
                SYNTAX DisplayString (SIZE (0..64))
                ACCESS read-write
                STATUS deprecated
                DESCRIPTION
                    "The filename to request when loading an image via 
                    TFTP.  Corresponds directly to SERVER INTERNET LOAD 
                    FILE and the value labeled 'Internet Load File:' in 
                    the SERVER BOOT CHARACTERISTICS display."
                ::= { xBootControl 1 }

            bootControlLoadInternetServer OBJECT-TYPE
                SYNTAX IpAddress
                ACCESS read-write
                STATUS deprecated
                DESCRIPTION
                    "The internet address of the server to use when 
                    loading an image via TFTP.  Corresponds directly to 
                    SERVER INTERNET LOAD HOST and the value labeled 
                    'Internet Load Host:' in the SERVER BOOT 
                    CHARACTERISTICS display."
                ::= { xBootControl 2 }

            bootControlLoadInternetGateway OBJECT-TYPE
                SYNTAX IpAddress
                ACCESS read-write
                STATUS deprecated
                DESCRIPTION
                    "The internet address of the gateway to use when 
                    loading an image via TFTP.  Corresponds directly to 
                    SERVER INTERNET LOAD GATEWAY and the value labeled 
                    'Internet Load Gateway:' in the SERVER BOOT 
                    CHARACTERISTICS display."
                ::= { xBootControl 3 }

            bootControlLoadBootpTftp OBJECT-TYPE
                SYNTAX INTEGER { disabled(1), enabled(2) }
                ACCESS read-write
                STATUS deprecated
                DESCRIPTION
                    "Control for loading via the combination of BOOTP 
                    and TFTP.  Corresponds to SERVER LOAD PROTOCOL 
                    BOOTPTFTP and the presence of 'BOOTP/TFTP/' 
                    following the label 'Load Protocols Enabled:' in the 
                    SERVER BOOT CHARACTERISTICS display."
                ::= { xBootControl 4 }

            bootControlLoadTftpDirect OBJECT-TYPE
                SYNTAX INTEGER { disabled(1), enabled(2) }
                ACCESS read-write
                STATUS deprecated
                DESCRIPTION
                    "Control for loading via directed TFTP.  Corresponds 
                    to SERVER LOAD PROTOCOL TFTPDIRECT and the presence 
                    of 'TFTPDIRECT' following the label 'Load Protocols 
                    Enabled:' in the SERVER BOOT CHARACTERISTICS 
                    display."
                ::= { xBootControl 5 }

            bootControlLoadLocal OBJECT-TYPE
                SYNTAX INTEGER { disabled(1), enabled(2) }
                ACCESS read-write
                STATUS deprecated
                DESCRIPTION
                    "Control for loading from a local medium.  
                    Corresponds to SERVER LOAD PROTOCOL LOCAL and the 
                    presence of 'LOCAL' following the label 'Load 
                    Protocols Enabled:' in the SERVER BOOT 
                    CHARACTERISTICS display."
                ::= { xBootControl 6 }

            bootControlLoadMop OBJECT-TYPE
                SYNTAX INTEGER { disabled(1), enabled(2) }
                ACCESS read-write
                STATUS deprecated
                DESCRIPTION
                    "Control for loading via DEC MOP.  Corresponds to 
                    SERVER LOAD PROTOCOL MOP and the presence of 'MOP' 
                    following the label 'Load Protocols Enabled:' in the 
                    SERVER BOOT CHARACTERISTICS display."
                ::= { xBootControl 7 }

            bootControlLoadProprietary OBJECT-TYPE
                SYNTAX INTEGER { disabled(1), enabled(2) }
                ACCESS read-write
                STATUS deprecated
                DESCRIPTION
                    "Control for loading via ITouch-proprietary extended 
                    MOP.  Corresponds to SERVER LOAD PROTOCOL 
                    PROPRIETARY and the presence of 'Proprietary' 
                    following the label 'Load Protocols Enabled:' in the 
                    SERVER BOOT CHARACTERISTICS display."
                ::= { xBootControl 8 }

            bootControlLoadRarpTftp OBJECT-TYPE
                SYNTAX INTEGER { disabled(1), enabled(2) }
                ACCESS read-write
                STATUS deprecated
                DESCRIPTION
                    "Control for loading via the combination of RARP and 
                    TFTP.  Corresponds to SERVER LOAD PROTOCOL RARPTFTP 
                    and the presence of 'RARP/TFTP' following the label 
                    'Load Protocols Enabled:' in the SERVER BOOT 
                    CHARACTERISTICS display."
                ::= { xBootControl 9 }

            bootControlDumpBootpTftp OBJECT-TYPE
                SYNTAX INTEGER { disabled(1), enabled(2) }
                ACCESS read-write
                STATUS deprecated
                DESCRIPTION
                    "Control for dumping via the combination of BOOTP 
                    and TFTP.  Corresponds to SERVER DUMP PROTOCOL 
                    BOOTPTFTP and the presence of 'BOOTP/TFTP' following 
                    the label 'Dump Protocols Enabled:' in the SERVER 
                    BOOT CHARACTERISTICS display."
                ::= { xBootControl 10 }

            bootControlDumpLocal OBJECT-TYPE
                SYNTAX INTEGER { disabled(1), enabled(2) }
                ACCESS read-write
                STATUS deprecated
                DESCRIPTION
                    "Control for dumping to a local medium.  Corresponds 
                    to SERVER DUMP PROTOCOL LOCAL and the presence of 
                    'Local' following the label 'Dump Protocols 
                    Enabled:' in the SERVER BOOT CHARACTERISTICS 
                    display."
                ::= { xBootControl 11 }

            bootControlDumpMop OBJECT-TYPE
                SYNTAX INTEGER { disabled(1), enabled(2) }
                ACCESS read-write
                STATUS deprecated
                DESCRIPTION
                    "Control for dumping via DEC MOP.  Corresponds to 
                    SERVER DUMP PROTOCOL MOP and the presence of 'MOP' 
                    following the label 'Dump Protocols Enabled:' in the 
                    SERVER BOOT CHARACTERISTICS display."
                ::= { xBootControl 12 }

            bootControlDumpProprietary OBJECT-TYPE
                SYNTAX INTEGER { disabled(1), enabled(2) }
                ACCESS read-write
                STATUS deprecated
                DESCRIPTION
                    "Control for dumping via ITouch-proprietary extended 
                    MOP.  Corresponds to SERVER DUMP PROTOCOL 
                    PROPRIETARY and the presence of 'Proprietary' 
                    following the label 'Dump Protocols Enabled:' in the 
                    SERVER BOOT CHARACTERISTICS display."
                ::= { xBootControl 13 }

            bootControlDumpRarpTftp OBJECT-TYPE
                SYNTAX INTEGER { disabled(1), enabled(2) }
                ACCESS read-write
                STATUS deprecated
                DESCRIPTION
                    "Control for dumping via the combination of RARP and 
                    TFTP.  Corresponds to SERVER DUMP PROTOCOL RARPTFTP 
                    and the presence of 'RARP/TFTP' following the label 
                    'Dump Protocols Enabled:' in the SERVER BOOT 
                    CHARACTERISTICS display."
                ::= { xBootControl 14 }

            bootControlParamBootpTftp OBJECT-TYPE
                SYNTAX INTEGER { disabled(1), enabled(2) }
                ACCESS read-write
                STATUS deprecated
                DESCRIPTION
                    "Control for loading parameters via the combination 
                    of BOOTP and TFTP.  Corresponds to SERVER PARAMETER 
                    PROTOCOL MOP and the presence of 'BOOTP/TFTP' 
                    following the label 'Parameter Protocols Enabled:' 
                    in the SERVER BOOT CHARACTERISTICS display."
                ::= { xBootControl 15 }

            bootControlParamLocal OBJECT-TYPE
                SYNTAX INTEGER { disabled(1), enabled(2) }
                ACCESS read-write
                STATUS deprecated
                DESCRIPTION
                    "Control for loading parameters from a local medium.  
                    Corresponds to SERVER PARAMETER PROTOCOL LOCAL and 
                    the presence of 'LOCAL' following the label 
                    'Parameter Protocols Enabled:' in the SERVER BOOT 
                    CHARACTERISTICS display."
                ::= { xBootControl 16 }

            bootControlParamMop OBJECT-TYPE
                SYNTAX INTEGER { disabled(1), enabled(2) }
                ACCESS read-write
                STATUS deprecated
                DESCRIPTION
                    "Control for loading parameters via DEC MOP.  
                    Corresponds to SERVER PARAMETER PROTOCOL MOP and the 
                    presence of 'MOP' following the label 'Parameter 
                    Protocols Enabled:' in the SERVER BOOT 
                    CHARACTERISTICS display."
                ::= { xBootControl 17 }

            bootControlParamProprietary OBJECT-TYPE
                SYNTAX INTEGER { disabled(1), enabled(2) }
                ACCESS read-write
                STATUS deprecated
                DESCRIPTION
                    "Control for loading parameters via 
                    ITouch-proprietary extended MOP.  Corresponds to 
                    SERVER PARAMETER PROTOCOL PROPRIETARY and the 
                    presence of 'Proprietary' following the label 
                    'Parameter Protocols Enabled:' in the SERVER BOOT 
                    CHARACTERISTICS display."
                ::= { xBootControl 18 }

            bootControlParamRarpTftp OBJECT-TYPE
                SYNTAX INTEGER { disabled(1), enabled(2) }
                ACCESS read-write
                STATUS deprecated
                DESCRIPTION
                    "Control for loading parameters via the combination 
                    of RARP and TFTP.  Corresponds to SERVER PARAMETER 
                    PROTOCOL RARPTFTP and the presence of 'RARP/TFTP' 
                    following the label 'Parameter Protocols Enabled:' 
                    in the SERVER BOOT CHARACTERISTICS display."
                ::= { xBootControl 19 }


            -- the System group, basic parameters continued

            sysInstalledMemory OBJECT-TYPE
                SYNTAX Gauge
                ACCESS read-only
                STATUS mandatory
                DESCRIPTION
                    "The total number of bytes of main memory installed 
                    in the system.  Corresponds directly to the value 
                    labeled 'Installed' on the SERVER ALTERNATE STATUS 
                    display.  A value of 0 indicates standard memory for 
                    the particular hardware."
                ::= { xSystem 35 }

            sysTemperatureLevel OBJECT-TYPE
                SYNTAX INTEGER { unknown(1), normal(2), high(3) }
                ACCESS read-only
                STATUS mandatory
                DESCRIPTION
                    "The temperature level of the system.  'unknown' 
                    indicates the system does not support a temperature 
                    sensor.  'normal' indicates a normal temperature 
                    level.  'high' indicates an excessive temperature 
                    level.  Corresponds directly to the value labeled 
                    'Temperature Level:' in the SERVER ALTERNATE STATUS 
                    display."
                ::= { xSystem 36 }

            -- basic parameters continue after boot record table


            -- the Boot Control Record table

            -- The Boot Control Record table contains parameters to
            -- control how a system loads and dumps its runtime
            -- software and parameters.  Typically these parameters
            -- are kept for and used by system initialization firmware.

            -- This table is mandatory for systems that offer runtime
            -- control of these parameters, and empty in systems
            -- that do not.

            bootRecordTable OBJECT-TYPE
                SYNTAX SEQUENCE OF BootRecordEntry
                ACCESS not-accessible
                STATUS mandatory
                DESCRIPTION
                    "A list of boot control records."
                ::= { xSystem 37 }

            bootRecordEntry OBJECT-TYPE
                SYNTAX BootRecordEntry
                ACCESS not-accessible
                 STATUS mandatory
                DESCRIPTION
                    "Values for a boot record."
                INDEX { bootRecordIndex }
                ::= { bootRecordTable 1 }

            BootRecordEntry ::=
                SEQUENCE {
                    bootRecordIndex
                        INTEGER,
                    bootRecordLoadInternetFile
                        DisplayString,
                    bootRecordLoadInternetServer
                        IpAddress,
                    bootRecordLoadInternetGateway
                        IpAddress,
                    bootRecordLoadBootpTftp
                        INTEGER,
                    bootRecordLoadTftpDirect
                        INTEGER,
                    bootRecordLoadLocal
                        INTEGER,
                    bootRecordLoadMop
                        INTEGER,
                    bootRecordLoadProprietary
                        INTEGER,
                    bootRecordLoadRarpTftp
                        INTEGER,
                    bootRecordDumpBootpTftp
                        INTEGER,
                    bootRecordDumpLocal
                        INTEGER,
                    bootRecordDumpMop
                        INTEGER,
                    bootRecordDumpProprietary
                        INTEGER,
                    bootRecordDumpRarpTftp
                        INTEGER,
                    bootRecordParamBootpTftp
                        INTEGER,
                    bootRecordParamLocal
                        INTEGER,
                    bootRecordParamMop
                        INTEGER,
                    bootRecordParamProprietary
                        INTEGER,
                    bootRecordParamRarpTftp
                        INTEGER,
                    bootRecordStatus
                        INTEGER,
                    bootRecordMopFile
                        DisplayString,
                    bootRecordInternetAddress
                        IpAddress,
                    bootRecordParamTftpDirect
                        INTEGER,
                    bootRecordInternetDelimiter 
                        DisplayString 
                }

            bootRecordIndex OBJECT-TYPE
                SYNTAX INTEGER
                ACCESS read-only
                STATUS mandatory
                DESCRIPTION
                    "An index value that uniquely identifies a boot 
                    control record entry, from 1 to the number of 
                    entries for the system."
                ::= { bootRecordEntry 1 }

            bootRecordLoadInternetFile OBJECT-TYPE
                SYNTAX DisplayString (SIZE (0..64))
                ACCESS read-write
                STATUS mandatory
                DESCRIPTION
                    "The filename to request when loading an image via 
                    TFTP.  Corresponds directly to SERVER INTERNET LOAD 
                    FILE and the value labeled 'Internet Load File:' in 
                    the SERVER BOOT CHARACTERISTICS display."
                ::= { bootRecordEntry 2 }

            bootRecordLoadInternetServer OBJECT-TYPE
                SYNTAX IpAddress
                ACCESS read-write
                STATUS mandatory
                DESCRIPTION
                    "The internet address of the server to use when 
                    loading an image via TFTP.  Corresponds directly to 
                    SERVER INTERNET LOAD HOST and the value labeled 
                    'Internet Load Host:' in the SERVER BOOT 
                    CHARACTERISTICS display."
                ::= { bootRecordEntry 3 }

            bootRecordLoadInternetGateway OBJECT-TYPE
                SYNTAX IpAddress
                ACCESS read-write
                STATUS mandatory
                DESCRIPTION
                    "The internet address of the gateway to use when 
                    loading an image via TFTP.  Corresponds directly to 
                    SERVER INTERNET LOAD GATEWAY and the value labeled 
                    'Internet Load Gateway:' in the SERVER BOOT 
                    CHARACTERISTICS display."
                ::= { bootRecordEntry 4 }

            bootRecordLoadBootpTftp OBJECT-TYPE
                SYNTAX INTEGER { disabled(1), enabled(2) }
                ACCESS read-write
                STATUS mandatory
                DESCRIPTION
                    "Control for loading via the combination of BOOTP 
                    and TFTP.  Corresponds to SERVER LOAD PROTOCOL 
                    BOOTPTFTP and the presence of 'BOOTP/TFTP/' 
                    following the label 'Load Protocols Enabled:' in the 
                    SERVER BOOT CHARACTERISTICS display."
                ::= { bootRecordEntry 5 }

            bootRecordLoadTftpDirect OBJECT-TYPE
                SYNTAX INTEGER { disabled(1), enabled(2) }
                ACCESS read-write
                STATUS mandatory
                DESCRIPTION
                    "Control for loading via directed TFTP.  Corresponds 
                    to SERVER LOAD PROTOCOL TFTPDIRECT and the presence 
                    of 'TFTPDIRECT' following the label 'Load Protocols 
                    Enabled:' in the SERVER BOOT CHARACTERISTICS 
                    display."
                ::= { bootRecordEntry 6 }

            bootRecordLoadLocal OBJECT-TYPE
                SYNTAX INTEGER { disabled(1), enabled(2) }
                ACCESS read-write
                STATUS mandatory
                DESCRIPTION
                    "Control for loading from a local medium.  
                    Corresponds to SERVER LOAD PROTOCOL LOCAL and the 
                    presence of 'LOCAL' following the label 'Load 
                    Protocols Enabled:' in the SERVER BOOT 
                    CHARACTERISTICS display."
                ::= { bootRecordEntry 7 }

            bootRecordLoadMop OBJECT-TYPE
                SYNTAX INTEGER { disabled(1), enabled(2) }
                ACCESS read-write
                STATUS mandatory
                DESCRIPTION
                    "Control for loading via DEC MOP.  Corresponds to 
                    SERVER LOAD PROTOCOL MOP and the presence of 'MOP' 
                    following the label 'Load Protocols Enabled:' in the 
                    SERVER BOOT CHARACTERISTICS display."
                ::= { bootRecordEntry 8 }

            bootRecordLoadProprietary OBJECT-TYPE
                SYNTAX INTEGER { disabled(1), enabled(2) }
                ACCESS read-write
                STATUS mandatory
                DESCRIPTION
                    "Control for loading via ITouch-proprietary extended 
                    MOP.  Corresponds to SERVER LOAD PROTOCOL 
                    PROPRIETARY and the presence of 'Proprietary' 
                    following the label 'Load Protocols Enabled:' in the 
                    SERVER BOOT CHARACTERISTICS display."
                ::= { bootRecordEntry 9 }

            bootRecordLoadRarpTftp OBJECT-TYPE
                SYNTAX INTEGER { disabled(1), enabled(2) }
                ACCESS read-write
                STATUS mandatory
                DESCRIPTION
                    "Control for loading via the combination of RARP and 
                    TFTP.  Corresponds to SERVER LOAD PROTOCOL RARPTFTP 
                    and the presence of 'RARP/TFTP' following the label 
                    'Load Protocols Enabled:' in the SERVER BOOT 
                    CHARACTERISTICS display."
                ::= { bootRecordEntry 10 }

            bootRecordDumpBootpTftp OBJECT-TYPE
                SYNTAX INTEGER { disabled(1), enabled(2) }
                ACCESS read-write
                STATUS mandatory
                DESCRIPTION
                    "Control for dumping via the combination of BOOTP 
                    and TFTP.  Corresponds to SERVER DUMP PROTOCOL 
                    BOOTPTFTP and the presence of 'BOOTP/TFTP' following 
                    the label 'Dump Protocols Enabled:' in the SERVER 
                    BOOT CHARACTERISTICS display."
                ::= { bootRecordEntry 11 }

            bootRecordDumpLocal OBJECT-TYPE
                SYNTAX INTEGER { disabled(1), enabled(2) }
                ACCESS read-write
                STATUS mandatory
                DESCRIPTION
                    "Control for dumping to a local medium.  Corresponds 
                    to SERVER DUMP PROTOCOL LOCAL and the presence of 
                    'Local' following the label 'Dump Protocols 
                    Enabled:' in the SERVER BOOT CHARACTERISTICS 
                    display."
                ::= { bootRecordEntry 12 }

            bootRecordDumpMop OBJECT-TYPE
                SYNTAX INTEGER { disabled(1), enabled(2) }
                ACCESS read-write
                STATUS mandatory
                DESCRIPTION
                    "Control for dumping via DEC MOP.  Corresponds to 
                    SERVER DUMP PROTOCOL MOP and the presence of 'MOP' 
                    following the label 'Dump Protocols Enabled:' in the 
                    SERVER BOOT CHARACTERISTICS display."
                ::= { bootRecordEntry 13 }

            bootRecordDumpProprietary OBJECT-TYPE
                SYNTAX INTEGER { disabled(1), enabled(2) }
                ACCESS read-write
                STATUS mandatory
                DESCRIPTION
                    "Control for dumping via ITouch-proprietary extended 
                    MOP.  Corresponds to SERVER DUMP PROTOCOL 
                    PROPRIETARY and the presence of 'Proprietary' 
                    following the label 'Dump Protocols Enabled:' in the 
                    SERVER BOOT CHARACTERISTICS display."
                ::= { bootRecordEntry 14 }

            bootRecordDumpRarpTftp OBJECT-TYPE
                SYNTAX INTEGER { disabled(1), enabled(2) }
                ACCESS read-write
                STATUS mandatory
                DESCRIPTION
                    "Control for dumping via the combination of RARP and 
                    TFTP.  Corresponds to SERVER DUMP PROTOCOL RARPTFTP 
                    and the presence of 'RARP/TFTP' following the label 
                    'Dump Protocols Enabled:' in the SERVER BOOT 
                    CHARACTERISTICS display."
                ::= { bootRecordEntry 15 }

            bootRecordParamBootpTftp OBJECT-TYPE
                SYNTAX INTEGER { disabled(1), enabled(2) }
                ACCESS read-write
                STATUS mandatory
                DESCRIPTION
                    "Control for loading parameters via the combination 
                    of BOOTP and TFTP.  Corresponds to SERVER PARAMETER 
                    PROTOCOL MOP and the presence of 'BOOTP/TFTP' 
                    following the label 'Parameter Protocols Enabled:' 
                    in the SERVER BOOT CHARACTERISTICS display."
                ::= { bootRecordEntry 16 }

            bootRecordParamLocal OBJECT-TYPE
                SYNTAX INTEGER { disabled(1), enabled(2) }
                ACCESS read-write
                STATUS mandatory
                DESCRIPTION
                    "Control for loading parameters from a local medium.  
                    Corresponds to SERVER PARAMETER PROTOCOL LOCAL and 
                    the presence of 'LOCAL' following the label 
                    'Parameter Protocols Enabled:' in the SERVER BOOT 
                    CHARACTERISTICS display."
                ::= { bootRecordEntry 17 }

            bootRecordParamMop OBJECT-TYPE
                SYNTAX INTEGER { disabled(1), enabled(2) }
                ACCESS read-write
                STATUS mandatory
                DESCRIPTION
                    "Control for loading parameters via DEC MOP.  
                    Corresponds to SERVER PARAMETER PROTOCOL MOP and the 
                    presence of 'MOP' following the label 'Parameter 
                    Protocols Enabled:' in the SERVER BOOT 
                    CHARACTERISTICS display."
                ::= { bootRecordEntry 18 }

            bootRecordParamProprietary OBJECT-TYPE
                SYNTAX INTEGER { disabled(1), enabled(2) }
                ACCESS read-write
                STATUS mandatory
                DESCRIPTION
                    "Control for loading parameters via 
                    ITouch-proprietary extended MOP.  Corresponds to 
                    SERVER PARAMETER PROTOCOL PROPRIETARY and the 
                    presence of 'Proprietary' following the label 
                    'Parameter Protocols Enabled:' in the SERVER BOOT 
                    CHARACTERISTICS display."
                ::= { bootRecordEntry 19 }

            bootRecordParamRarpTftp OBJECT-TYPE
                SYNTAX INTEGER { disabled(1), enabled(2) }
                ACCESS read-write
                STATUS mandatory
                DESCRIPTION
                    "Control for loading parameters via the combination 
                    of RARP and TFTP.  Corresponds to SERVER PARAMETER 
                    PROTOCOL RARPTFTP and the presence of 'RARP/TFTP' 
                    following the label 'Parameter Protocols Enabled:' 
                    in the SERVER BOOT CHARACTERISTICS display."
                ::= { bootRecordEntry 20 }

            bootRecordStatus OBJECT-TYPE
                SYNTAX INTEGER { disabled(1), enabled(2) }
                ACCESS read-write
                STATUS mandatory
                DESCRIPTION
               "The status of the entry.  Set to 'disabled' to
               disable the entry."
                ::= { bootRecordEntry 21 }

            bootRecordMopFile OBJECT-TYPE
                SYNTAX DisplayString (SIZE (0..15))
                ACCESS read-write
                STATUS mandatory
                DESCRIPTION
                    "The software file name to request for down-line 
                    load of the server via MOP or XMOP."
                ::= { bootRecordEntry 22 }

            bootRecordInternetAddress OBJECT-TYPE
                SYNTAX IpAddress
                ACCESS read-write
                STATUS mandatory
                DESCRIPTION
                    "The internet address of the system is to use for 
                    itself when loading via TFTP.  The value 0.0.0.0 
                    indicates default action."
                ::= { bootRecordEntry 23 }

            bootRecordParamTftpDirect OBJECT-TYPE
                SYNTAX INTEGER { disabled(1), enabled(2) }
                ACCESS read-write
                STATUS mandatory
                DESCRIPTION
                    "Control for loading parameters via the protocol
                    DTFTP.  Corresponds to SERVER PARAMETER 
                    PROTOCOL DTFTP and the presence of 'DTFTP' 
                    following the label 'Parameter Protocols Enabled:' 
                    in the SERVER BOOT CHARACTERISTICS display."
                ::= { bootRecordEntry 24 }

            bootRecordInternetDelimiter OBJECT-TYPE 
                SYNTAX DisplayString (SIZE (0..1)) 
                ACCESS read-write 
                STATUS mandatory
                DESCRIPTION 
                    "The character separating the load file directory name
                    from the file name." 
                DEFVAL { '00'h }  -- the null string
                ::= { bootRecordEntry 25 }



            -- the System group, basic parameters continued

            sysLastAgentError OBJECT-TYPE
                SYNTAX INTEGER { noError(1), tooBig(2), noSuchName(3),
                                 badValue(4), readOnly(5), genErr(6),
                                 badCommunity(7), badVersion(8), badType(9),
                                 badClient(10) }
                ACCESS read-only
                STATUS mandatory
                DESCRIPTION
                    "The most recent error the agent encountered in 
                    attempting to satisfy an SNMP request.  Reading this 
                    value has the side effect of resetting it to 
                    'noError'."
                ::= { xSystem 38 }

             sysRcpMulticast OBJECT-TYPE
                SYNTAX INTEGER { disabled(1), enabled(2) }
                ACCESS read-write
                STATUS mandatory
                DESCRIPTION
                    "Control for sending of the MOP RCP system identifier
                    message.  Corresponds directly to the presence of 'RCP
                    Multicast' under the label 'Enabled Characteristics'
                    in the SERVER CHARACTERISTICS display."
                ::= { xSystem 40 }

            sysTimeServerAddress OBJECT-TYPE
                SYNTAX TypedAddress
                ACCESS read-only 
                STATUS mandatory 
                DESCRIPTION 
                    "The address of the time server, either an
                     IpAddr or an ethernet address."
                ::= { xSystem 41 }

            sysTimeServerConfiguredAddress OBJECT-TYPE
                SYNTAX TypedAddress
                ACCESS read-write
                STATUS mandatory
                DESCRIPTION
                      "The address of a configured time server (, either an
                          IpAddr or an ethernet address)."
                ::= { xSystem 46 }

            sysTimeServerConfiguredStatus OBJECT-TYPE
                SYNTAX INTEGER { disabled(1), enabled(2), required(3) }
                ACCESS read-write
                STATUS mandatory
                DESCRIPTION
                   "Control whether the sysTimeServerConfiguredAddress is
                    the only time server used to obtain the time (REQUIRED),
                    the first time server used to obtain the time (ENABLED),
                    or not used to obtain the time (DISABLED)."
                DEFVAL { disabled }
                ::= { xSystem 47 }
                 
            sysBootRecordOverrideDefinedAddress OBJECT-TYPE
                SYNTAX INTEGER { enabled(1), disabled(2) }
                ACCESS read-write
                STATUS mandatory
                DESCRIPTION
                   "Control to override the internally defined Internet address
                    with that obtained from the bootp loading protocol."
                DEFVAL { disabled  }
                ::= { xSystem 48 }

            sysBootRecordMessageEnable OBJECT-TYPE
                SYNTAX INTEGER { enabled(1), disabled(2) }
                ACCESS read-write
                STATUS mandatory
                DESCRIPTION
                    "Control to display load status messages during reboot.
                     Corresponds directly to the value labeled 'Status Message:'
                     in the SERVER LOADDUMP display."
                DEFVAL { enabled }
                ::= { xSystem 49 }
 
            sysBootRecordParamDefaults OBJECT-TYPE
                SYNTAX INTEGER { enabled(1), disabled(2) }
                ACCESS read-write
                STATUS mandatory
                DESCRIPTION
                    "Control to use default parameters upon the next reboot
                     after which time this control reverts to disabled. This
                     control only applies to stand-alone devices. Corresponds 
                     directly to the value labeled 'Default Parameters:'
                     in the SERVER LOADDUMP display."
                DEFVAL { disabled  }
                ::= { xSystem 50 }
 
            sysLoginAuthFailureTrapType OBJECT-TYPE
                SYNTAX INTEGER { none(1), loginPassword(2), pap(3),
                                 chap(4), kerberos(5), securId(6),
                                 radius(7), privilegedPassword(8),
                                 limitedPrivilegedPassword(9) }
                ACCESS read-only
                STATUS mandatory
                DESCRIPTION 
                    "Indicates the type of authentication failure which last
                     occurred."   
                
                ::= { xSystem 78 }

             sysLoginAuthTrapIdentity OBJECT-TYPE
                SYNTAX DisplayString (SIZE (0..16))
                ACCESS read-only
                STATUS mandatory
                DESCRIPTION
                    "An identification string for the circuit or port where an
                     authentication failure last occurred."
                ::= { xSystem 81 }

            sysLocalScriptServer OBJECT-TYPE
                SYNTAX INTEGER { disabled(1), enabled(2) }
                ACCESS read-write
                STATUS mandatory
                DESCRIPTION
                    "Control to allow script serving for this system
                     from a script residing in a local flash card."
                DEFVAL { disabled }
                ::= { xSystem 82 }

            sysInReachManagementSecurityStatus OBJECT-TYPE
                SYNTAX INTEGER { disabled(1), enabled(2) }
                ACCESS read-only
                STATUS mandatory
                DESCRIPTION
                    "Indicates whether per port authentication is in use. This
                     includes username, password, privilege level, and list of
                     power outlets controlled by that user, or console
                     connections allowed from that port."
                DEFVAL { disabled }
                ::= { xSystem 83 }

            sysProductName OBJECT-TYPE
                SYNTAX DisplayString
                ACCESS read-only
                STATUS mandatory
                DESCRIPTION
                    "Displays the product name of this system."
                ::= { xSystem 84 }

            sysModemPresent OBJECT-TYPE
                SYNTAX INTEGER { noModem(1), modem(2) }
                ACCESS read-only
                STATUS mandatory
                DESCRIPTION
                    "Indicates whether this system has a built-in 
                     modem."
                ::= { xSystem 85 }

            sysCauseAction  OBJECT-TYPE
                SYNTAX INTEGER { disabled(1), enabled(2) }
                ACCESS read-write
                STATUS mandatory
                DESCRIPTION
                    "A control for toggling the cause action feature.
                     Corresponds directly to the presence of 'Trigger/Action' 
                     under the label 'Enabled Characteristics:' in the SERVER
                     CHARACTERISTICS display. The desired change will not take
                     effect until the next system initialization."
                DEFVAL { disabled }
                ::= { xSystem 86 }                

            sysWebServerConfigAdminStatus  OBJECT-TYPE
                SYNTAX INTEGER { disabled(1), enabled(2) }
                ACCESS read-write
                STATUS mandatory
                DESCRIPTION
                    "A control for bring the web server up or down.
                     Corresponds directly to the presence of 'Web Server'
                     under the label 'Enabled Characteristics:' in the SERVER
                     CHARACTERISTICS display."
                DEFVAL { enabled }
                ::= { xSystem 87 }                

 	sysTl1SourceIdentifier OBJECT-TYPE
		SYNTAX DisplayString (SIZE (0..20))
		ACCESS read-write
		STATUS mandatory
		DESCRIPTION
		    "The source identifier (SID) is the server name used by
                     TL1 to identify the server."
		::= { xSystem 88 }

        sysInitializeDelayParameter OBJECT-TYPE
                SYNTAX INTEGER { ready(1), execute(2) }
                ACCESS read-write
                STATUS mandatory
                DESCRIPTION
                    "Control to begin the system initialization process
                    providing that at least one parameter server is
                    current. Corresponds directly to the INITIALIZE DELAY 
                    PARAMETER command. In response to a get-request or
                    get-next-request, the agent always returns 'ready' for
                    this value."
                ::= { xSystem 89 }


            -- System Traps
            -- resourceLack is deprecated, and replaced by resourceFailure.

            resourceLack TRAP-TYPE
                ENTERPRISE xSystem
                VARIABLES { 
                    resType
                    }
                DESCRIPTION
                    "Indication that the system incremented the 
                    corresponding value of resLacks."
                ::= 1

            resourceFailure TRAP-TYPE
                ENTERPRISE iTouch
                VARIABLES { 
                    resType,
		    sysLocation
                    }
                DESCRIPTION
                    "Indication that a system resource lack occurred of
                     the type resType."
                ::= 9


--
-- FILE: /users/sse/mibs/src/itouch/it-x25-mib.mib
--

-- $Id: it-x25-mib.mib,v 1.2 2000/07/24 19:34:11 sse Exp $


       xX25            OBJECT IDENTIFIER ::= { iTouch 20 }


            -- This is a MIB module for all iTouch Communications systems that
            -- implement X25.

            -- Copyright 2000 iTouch Communications, Inc. All Rights Reserved.
            -- Reproduction of this document is authorized on
            -- condition that this copyright notice is included.
            -- This MIB document embodies iTouch Communications, Inc.'s 
            -- proprietary intellectual property.  iTouch Communications, Inc.
            -- retains all title and ownership in this MIB, including any
            -- revisions.
            --
            -- It is iTouch Communications, Inc.'s intent to encourage the
            -- widespread use of this MIB in connection with the management of
            -- iTouch Communications, Inc. products. iTouch Communications,
            -- Inc. grants vendors,end-users, and other interested parties a
            -- non-exclusive license to use this MIB in connection with the
            -- management of iTouch Communications, Inc. products.
            --
            -- This MIB document is supplied "AS IS," and iTouch 
            -- Communications, Inc. makes no warranty, either express or
            -- implied, as to the use operation, condition, or performance of
            -- the MIB.
	
	
       -- X.25 Channel Table

       xX25ChannelTable OBJECT-TYPE
           SYNTAX SEQUENCE OF XX25ChannelEntry
           ACCESS not-accessible
           STATUS mandatory
           DESCRIPTION
               "Entries of xX25Channel Table."
           ::= { xX25 4 }

       xX25ChannelEntry OBJECT-TYPE
           SYNTAX XX25ChannelEntry
           ACCESS not-accessible
           STATUS mandatory
           DESCRIPTION
               "Entries of xX25ChannelTable."
           INDEX { xX25ChannelIndex }
           ::= { xX25ChannelTable 1 }

       XX25ChannelEntry ::=
           SEQUENCE {
               xX25ChannelIndex
                       INTEGER,
               xX25ChannelLowPVC
                       INTEGER,
               xX25ChannelHighPVC
                       INTEGER,
			   xX25ChannelNetwork
					   INTEGER,
			   xX25ChannelMaxPrecedence
					   INTEGER,
			   xX25ChannelStdVersion
					   INTEGER
           }

       xX25ChannelIndex OBJECT-TYPE
           SYNTAX INTEGER
           ACCESS read-only
           STATUS mandatory
           DESCRIPTION
               "The ifIndex value for the X.25 physical link."
           ::= { xX25ChannelEntry 1 }

       xX25ChannelLowPVC OBJECT-TYPE
           SYNTAX INTEGER (0..4095)
           ACCESS read-write
           STATUS mandatory
           DESCRIPTION
               "Lowest PVC channel.  Setting it to zero indicates 
               'none', and will also set the xX25ChannelHighPVC to 
               zero.  If set to a non-zero value and 
               xX25ChannelHighPVC is zero, xX25ChannelHighPVC will 
               be set to the same value.  Otherwise, 
               xX25ChannelLowPVC must be less than or equal to 
               xX25ChannelHighPVC."
           ::= { xX25ChannelEntry 2 }

       xX25ChannelHighPVC OBJECT-TYPE
           SYNTAX INTEGER (0..4095)
           ACCESS read-write
           STATUS mandatory
           DESCRIPTION
               "Highest PVC channel.  Setting it to 0 indicates 
               none, and will also set the xX25ChannelLowPVC to 0.  
               If set to a non-zero value and xX25ChannelLowPVC is 
               zero, xX25ChannelLowPVC will be set to the same 
               value.  Otherwise, xX25ChannelHighPVC must be less 
               than or equal to xX25ChannelLowPVC."
           ::= { xX25ChannelEntry 3 }

       xX25ChannelNetwork OBJECT-TYPE
           SYNTAX INTEGER { ccitt(1), ddnStandard(2) }
           ACCESS read-write
           STATUS mandatory
           DESCRIPTION
               "The type of network being run."
           ::= { xX25ChannelEntry 4 }

       xX25ChannelMaxPrecedence OBJECT-TYPE
           SYNTAX INTEGER ( 0..3 )
           ACCESS read-write
           STATUS mandatory
           DESCRIPTION
               "The maximum level of IP precedence supported."
           ::= { xX25ChannelEntry 5 }

       xX25ChannelStdVersion OBJECT-TYPE
           SYNTAX INTEGER
           ACCESS read-write
           STATUS mandatory
           DESCRIPTION
               "The standard year supported by x25.  Values are usually
			   1980 or 1984 (the default)."
           ::= { xX25ChannelEntry 6 }

       -- X.25 Virtual Circuit Configuration Table

       xX25VcCfgTable OBJECT-TYPE
           SYNTAX SEQUENCE OF XX25VcCfgEntry
           ACCESS not-accessible
           STATUS mandatory
           DESCRIPTION
               "These objects contain information about the virtual 
               circuit configuration in an X.25 PLE.  These values 
               are the configured values for circuits that  may or 
               may not be connected.  Unconfigured calls may be 
               added to this table as calls are accepted."
           ::= { xX25 6 }

       xX25VcCfgEntry OBJECT-TYPE
           SYNTAX XX25VcCfgEntry
           ACCESS not-accessible
           STATUS mandatory
           DESCRIPTION
               "Entries of the xX25VcCfgTable."
           INDEX { xX25VcCfgIndex }
           ::= { xX25VcCfgTable 1 }

       XX25VcCfgEntry ::=
           SEQUENCE {
               xX25VcCfgIndex
                   INTEGER,
               xX25VcCfgPartnerAddr
                   X121Address,
               xX25VcCfgInterfaceIndex
                   INTEGER,
               xX25VcCfgLinkIndex
                   INTEGER,
               xX25VcCfgProtocol
                   INTEGER,
               xX25VcCfgEncapsulation
                   INTEGER,
               xX25VcCfgPvc
                   INTEGER,
               xX25VcCfgPartnerIpAddress
                   IpAddress,
               xX25VcCfgClearFacilities
                   INTEGER,
               xX25VcCfgStatus
                   INTEGER
           }

       xX25VcCfgIndex OBJECT-TYPE
           SYNTAX INTEGER
           ACCESS read-only
           STATUS mandatory
           DESCRIPTION
               "An arbitrary index value for the virtual circuit."
           ::= { xX25VcCfgEntry 1 }

       xX25VcCfgPartnerAddr OBJECT-TYPE
           SYNTAX X121Address
           ACCESS read-write
           STATUS mandatory
           DESCRIPTION
               "Partner's X.121 Address."
           DEFVAL { "" }
           ::= { xX25VcCfgEntry 2 }

       xX25VcCfgInterfaceIndex OBJECT-TYPE
           SYNTAX INTEGER
           ACCESS read-write
           STATUS mandatory
           DESCRIPTION
               "ifIndex of ITouch logical interface associated with 
               this VC."
           DEFVAL { 0 } -- Actually lowest numbered WAN link
           ::= { xX25VcCfgEntry 3 }

       xX25VcCfgLinkIndex OBJECT-TYPE
           SYNTAX INTEGER
           ACCESS read-write
           STATUS mandatory
           DESCRIPTION
               "ifIndex of physical link on which this VC 
               resides."
           DEFVAL { 0 }  -- Actually lowest numbered WAN link
           ::= { xX25VcCfgEntry 4 }

       xX25VcCfgProtocol OBJECT-TYPE
           SYNTAX INTEGER { appleTalk(1),
                            bridged(2),
                            decnet(3),
                            ip(4),
                            ipx(5),
                            multiProtocol(6),
                            osi(7) }
           ACCESS read-write
           STATUS mandatory
           DESCRIPTION
               "Protocol which is being encapsulated by this VC."
           DEFVAL { ip }
           ::= { xX25VcCfgEntry 5 }

       xX25VcCfgEncapsulation OBJECT-TYPE
           SYNTAX INTEGER { null(1),
                            dedicated(2),
                            snap(3) }
           ACCESS read-write
           STATUS mandatory
           DESCRIPTION
               "Encapsulation method used by this VC."
           DEFVAL { dedicated }
           ::= { xX25VcCfgEntry 6 }

       xX25VcCfgPvc OBJECT-TYPE
           SYNTAX INTEGER (0..4095)
           ACCESS read-write
           STATUS mandatory
           DESCRIPTION
               "Channel number if VC is a PVC, else 0.  The value 
               must be in the range of xX25ChannelLowPVC to 
               xX25ChannelHighPVC"
           DEFVAL { 0 }
           ::= { xX25VcCfgEntry 7 }

       xX25VcCfgPartnerIpAddress OBJECT-TYPE
           SYNTAX IpAddress
           ACCESS read-write
           STATUS mandatory
           DESCRIPTION
               "IP address of the partner over this VC.  This must 
               be configured if IP packets will not be 
               MAC-encapsulated."
           DEFVAL { 0 }
           ::= { xX25VcCfgEntry 8 }

       xX25VcCfgClearFacilities OBJECT-TYPE
           SYNTAX INTEGER { ready(1), execute(2) }
           ACCESS read-write
           STATUS mandatory
           DESCRIPTION
               "Control to clear the VC call facilities string.  In 
               response to a get-request or get-next-request, the 
               agent always returns 'ready' for this value.  
               Setting the value to 'ready' has no effect.  Setting 
               it to 'execute' causes the string to be cleared."
           DEFVAL { ready }
           ::= { xX25VcCfgEntry 9 }

       xX25VcCfgStatus OBJECT-TYPE
           SYNTAX INTEGER { invalid(1), valid(2) }
           ACCESS read-write
           STATUS mandatory
           DESCRIPTION
               "Setting to 'invalid' removes this VC from the 
               table.  If 'valid', setting to 'valid' has no 
               effect, otherwise it creates an entry."
           DEFVAL { valid }
           ::= { xX25VcCfgEntry 10 }

       -- X.25 Physical Link Table

       xX25LinkTable OBJECT-TYPE
           SYNTAX SEQUENCE OF XX25LinkEntry
           ACCESS not-accessible
           STATUS mandatory
           DESCRIPTION
               "These objects contain information about the 
               configuration of the X.25 physical links necessary 
               for the ITouch Bridge/Router.  Unless otherwise 
               noted, changes to these objects require that the 
               X.25 physical link be restarted in order for the 
               changes to take effect."
           ::= { xX25 7 }

       xX25LinkEntry OBJECT-TYPE
           SYNTAX XX25LinkEntry
           ACCESS not-accessible
           STATUS mandatory
           DESCRIPTION
               "Entries of the xX25LinkTable."
           INDEX { xX25LinkIndex }
           ::= { xX25LinkTable 1 }

       XX25LinkEntry ::=
           SEQUENCE {
               xX25LinkIndex
                   INTEGER,
               xX25LinkRRDelay
                   INTEGER,
               xX25LinkIdleTimeout
                   INTEGER,
               xX25LinkHoldDownTimer
                   INTEGER,
               xX25LinkAccUncfgCalls
                   INTEGER,
               xX25LinkDefWindSize
                   INTEGER,
               xX25LinkMaxWindSize
                   INTEGER,
               xX25LinkDefPktSize
                   INTEGER,
               xX25LinkDefThrptClassIn
                   INTEGER,
               xX25LinkDefThrptClassOut
                   INTEGER,
               xX25LinkDefThrptClassInMsk
                   INTEGER,
               xX25LinkDefThrptClassOutMsk
                   INTEGER,
               xX25LinkFlowCtrlNeg
                   INTEGER,
               xX25LinkThrptClassNeg
                   INTEGER,
               xX25LinkICallBarred
                   INTEGER,
               xX25LinkOCallBarred
                   INTEGER,
               xX25LinkOneOut
                   INTEGER,
               xX25LinkOneIn
                   INTEGER,
               xX25LinkRevChargeAcc
                   INTEGER,
               xX25LinkLocalChargePrevent
                   INTEGER,
               xX25LinkRpoa
                   INTEGER,
               xX25LinkNui
                   INTEGER,
               xX25LinkMaxPacketSize
                   INTEGER,
               xX25LinkInsertCallingAddr
                   INTEGER,
               xX25LinkDefaultInterface
                   INTEGER
           }

       xX25LinkIndex OBJECT-TYPE
           SYNTAX INTEGER
           ACCESS read-only
           STATUS mandatory
           DESCRIPTION
               "The ifIndex value for a ITouch physical link."
           ::= { xX25LinkEntry 1 }

       xX25LinkRRDelay OBJECT-TYPE
           SYNTAX INTEGER (0..127)
           ACCESS read-write
           STATUS mandatory
           DESCRIPTION
               "Number of packets received before an RR will be 
               sent. The value must be less than the 
               xX25CallParmInWindowSize. Modifying this object does 
               not require the X.25 physical link to be 
               restarted. 0 indicates that RR will not be sent."
           ::= { xX25LinkEntry 2 }

       xX25LinkIdleTimeout OBJECT-TYPE
           SYNTAX INTEGER (0..255)
           ACCESS read-write
           STATUS mandatory
           DESCRIPTION
               "Length of time in minutes that a virtual circuit 
               may be idle before the circuit will be cleared.  
               Modifying this object does not require the X.25 
               physical link to be restarted."
           ::= { xX25LinkEntry 3 }

       xX25LinkHoldDownTimer OBJECT-TYPE
           SYNTAX INTEGER (0..255)
           ACCESS read-write
           STATUS mandatory
           DESCRIPTION
               "Length of time in minutes after a virtual circuit 
               has been cleared before it may make a call again.  
               Modifying this object does not require the X.25 
               physical link to be restarted."
           ::= { xX25LinkEntry 4 }

       xX25LinkAccUncfgCalls OBJECT-TYPE
           SYNTAX INTEGER { enabled(1), disabled(2) }
           ACCESS read-write
           STATUS mandatory
           DESCRIPTION
               "Indicates whether unconfigured, non-reverse charged 
               calls will be accepted.  Modifying this object does 
               not require the X.25 physical link to be 
               restarted."
           ::= { xX25LinkEntry 5 }

       xX25LinkDefWindSize OBJECT-TYPE
           SYNTAX INTEGER (1..127)
           ACCESS read-write
           STATUS mandatory
           DESCRIPTION
               "Default packet level window size for this link."
           ::= { xX25LinkEntry 6 }

       xX25LinkMaxWindSize OBJECT-TYPE
           SYNTAX INTEGER (1..127)
           ACCESS read-write
           STATUS mandatory
           DESCRIPTION
               "Maximum packet level window size for this link."
           ::= { xX25LinkEntry 7 }

       xX25LinkDefPktSize OBJECT-TYPE
           SYNTAX INTEGER { bytes16(16),
                            bytes32(32),
                            bytes64(64),
                            bytes128(128),
                            bytes256(256),
                            bytes512(512),
                            bytes1024(1024),
                            bytes2048(2048),
                            bytes4096(4096) }
           ACCESS read-write
           STATUS mandatory
           DESCRIPTION
               "Default packet size for this link."
           ::= { xX25LinkEntry 8 }

       xX25LinkDefThrptClassIn OBJECT-TYPE
           SYNTAX INTEGER { bps75(75),
                            bps150(150),
                            bps300(300),
                            bps600(600),
                            bps1200(1200),
                            bps2400(2400),
                            bps4800(4800),
                            bps9600(9600),
                            bps19200(19200),
                            bps48000(48000) }
           ACCESS read-write
           STATUS mandatory
           DESCRIPTION
               "Default input throughput class for this link."
           ::= { xX25LinkEntry 9 }

       xX25LinkDefThrptClassOut OBJECT-TYPE
           SYNTAX INTEGER { bps75(75),
                            bps150(150),
                            bps300(300),
                            bps600(600),
                            bps1200(1200),
                            bps2400(2400),
                            bps4800(4800),
                            bps9600(9600),
                            bps19200(19200),
                            bps48000(48000) }
           ACCESS read-write
           STATUS mandatory
           DESCRIPTION
               "Default output throughput class for this link."
           ::= { xX25LinkEntry 10 }

       xX25LinkDefThrptClassInMsk OBJECT-TYPE
           SYNTAX INTEGER { bps75(75),
                            bps150(150),
                            bps300(300),
                            bps600(600),
                            bps1200(1200),
                            bps2400(2400),
                            bps4800(4800),
                            bps9600(9600),
                            bps19200(19200),
                            bps48000(48000) }
           ACCESS read-write
           STATUS deprecated
           DESCRIPTION
               "Default incoming throughput class mask for this 
               link."
           ::= { xX25LinkEntry 11 }

       xX25LinkDefThrptClassOutMsk OBJECT-TYPE
           SYNTAX INTEGER { bps75(75),
                            bps150(150),
                            bps300(300),
                            bps600(600),
                            bps1200(1200),
                            bps2400(2400),
                            bps4800(4800),
                            bps9600(9600),
                            bps19200(19200),
                            bps48000(48000) }
           ACCESS read-write
           STATUS deprecated
           DESCRIPTION
               "Default outgoing throughput class mask for this 
               link."
           ::= { xX25LinkEntry 12 }

       xX25LinkFlowCtrlNeg OBJECT-TYPE
           SYNTAX INTEGER { enabled(1), disabled(2) }
           ACCESS read-write
           STATUS mandatory
           DESCRIPTION
               "Indicates whether flow control negotiation will be 
               performed on this link."
           ::= { xX25LinkEntry 13 }

       xX25LinkThrptClassNeg OBJECT-TYPE
           SYNTAX INTEGER { enabled(1), disabled(2) }
           ACCESS read-write
           STATUS mandatory
           DESCRIPTION
               "Indicates whether throughput class negotiation will 
               be performed on this link."
           ::= { xX25LinkEntry 14 }

       xX25LinkICallBarred OBJECT-TYPE
           SYNTAX INTEGER { enabled(1), disabled(2) }
           ACCESS read-write
           STATUS mandatory
           DESCRIPTION
               "Indicates whether incoming calls are barred on this 
               link."
           ::= { xX25LinkEntry 15 }

       xX25LinkOCallBarred OBJECT-TYPE
           SYNTAX INTEGER { enabled(1), disabled(2) }
           ACCESS read-write
           STATUS mandatory
           DESCRIPTION
               "Indicates whether outgoing calls are barred on this 
               link."
           ::= { xX25LinkEntry 16 }

       xX25LinkOneOut OBJECT-TYPE
           SYNTAX INTEGER { enabled(1), disabled(2) }
           ACCESS read-write
           STATUS mandatory
           DESCRIPTION
               "Indicates whether the link supports one way 
               outgoing channels."
           ::= { xX25LinkEntry 17 }

       xX25LinkOneIn OBJECT-TYPE
           SYNTAX INTEGER { enabled(1), disabled(2) }
           ACCESS read-write
           STATUS mandatory
           DESCRIPTION
               "Indicates whether the link supports one way 
               incoming channels."
           ::= { xX25LinkEntry 18 }

       xX25LinkRevChargeAcc OBJECT-TYPE
           SYNTAX INTEGER { enabled(1), disabled(2) }
           ACCESS read-write
           STATUS mandatory
           DESCRIPTION
               "Indicates whether reverse charge acceptance may be 
               configured on this link."
           ::= { xX25LinkEntry 19 }

       xX25LinkLocalChargePrevent OBJECT-TYPE
           SYNTAX INTEGER { enabled(1), disabled(2) }
           ACCESS read-write
           STATUS mandatory
           DESCRIPTION
               "Indicates whether local charge prevention may be 
               configured on the link."
           ::= { xX25LinkEntry 20 }

       xX25LinkRpoa OBJECT-TYPE
           SYNTAX INTEGER { enabled(1), disabled(2) }
           ACCESS read-write
           STATUS mandatory
           DESCRIPTION
               "Indicates whether RPOA may be configured on the 
               link."
           ::= { xX25LinkEntry 21 }

       xX25LinkNui OBJECT-TYPE
           SYNTAX INTEGER { enabled(1), disabled(2) }
           ACCESS read-write
           STATUS mandatory
           DESCRIPTION
               "Indicates whether NUI may be configured on the 
               link."
           ::= { xX25LinkEntry 22 }

       xX25LinkMaxPacketSize OBJECT-TYPE
           SYNTAX INTEGER { bytes16(16),
                            bytes32(32),
                            bytes64(64),
                            bytes128(128),
                            bytes256(256),
                            bytes512(512),
                            bytes1024(1024) }
           ACCESS read-write
           STATUS mandatory
           DESCRIPTION
               "Maximum size of packets on the link."
           ::= { xX25LinkEntry 23 }

       xX25LinkInsertCallingAddr OBJECT-TYPE
           SYNTAX INTEGER { enabled(1), disabled(2) }
           ACCESS read-write
           STATUS mandatory
           DESCRIPTION
               "Indicates whether the caller's X.121 address should 
               be inserted into the the call request packet."
           ::= { xX25LinkEntry 24 }

       xX25LinkDefaultInterface OBJECT-TYPE
           SYNTAX INTEGER
           ACCESS read-write
           STATUS mandatory
           DESCRIPTION
               "The ITouch logical ifIndex to which new SVCs should 
               be attached, when 'accept unconfigured calls' is 
               enabled.  A value of zero means 'create a new 
               interface'."
           ::= { xX25LinkEntry 25 }

END
