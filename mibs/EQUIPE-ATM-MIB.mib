EQUIPE-ATM-MIB DEFINITIONS ::= BEGIN

    --
    -- Equipe ATM MIB
    --

    IMPORTS
        enterprises    
            FROM RFC1155-SMI
        MODULE-IDENTITY, OBJECT-TYPE, Counter32, Counter64
            FROM SNMPv2-SMI
        TEXTUAL-CONVENTION
            FROM SNMPv2-TC;

    equipe        OBJECT IDENTIFIER ::= { enterprises 5022 }

    eqAtmMib MODULE-IDENTITY
        LAST-UPDATED "0009170000Z"
        ORGANIZATION ""
        CONTACT-INFO
            "Jas Parmar
            Equipe Communications
            100 Nagog Park
            Acton MA 01720"
        DESCRIPTION
            "This is the Equipe ATM MIB module."
        ::= { equipe 2 }

    --
    --  ATM Cause codes TC.
    --

    AtmCauseCode ::= TEXTUAL-CONVENTION
        STATUS    current
        DESCRIPTION
                "The atm last cause code values."
        SYNTAX    INTEGER {
                none(1),                    -- none 
                unallocNumber(2),           -- unallocated number
                noRouteToTransitNet(3),     -- no route to tansit net
                noRouteToDest(4),           -- no route to dest
                vccUnacceptable30(5),       -- VPI/VCI unacceptable (UNI 3.0)
                normalCallCleared31(6),     -- normal call cleared
                userBusy(7),                -- user busy
                noUserResponse(8),          -- no user response
                callRejected(9),            -- call rejected
                numberChanged(10),           -- number changed
                callRejectCLIR(11),         -- user rejects all calls with CLIR
                destOutOfOrder(12),         -- destn out of order
                invalidNumberFormat(13),    -- invalid number format
                respToStatusEnquiry(14),    -- response to status enquiry
                normalUnspecified(15),      -- normal unspecified
                reqVccUnavailable(16),      -- requested VPI/VCI unavailable
                vccFail31(17),              -- VPI/VCI assignment failure
                rateUnavailable31(18),      -- rate unavailable
                networkOutOfOrder(19),      -- network out of order
                tempFailure(20),            -- temp failure
                accessInfoDiscarded(21),    -- access info discarded
                resourcesUnavailable(22),   -- resource unavailable
                qosUnavailable(23),         -- QoS unavailable
                rateUnavailable(24),        -- call rate unavailable
                bcapNotAuthorised(25),      -- bearer caps not authorised
                bcapUnavailable(26),        -- bearer caps unavailable
                serviceUnavailable(27),     -- service or option unavailable
                bcapNotImplemented(28),     -- bearer cap not implemented
                combinationUnsupported(29), -- unsupported mix of traffic params
                aalParamsUnsupported31(30), -- unsupported aal params
                invalidCallReference(31),   -- invalid call reference
                noChannel(32),              -- channel does not exist
                destIncompatible(33),       -- incomptible destination
                invalidEndpointRef(34),     -- invalid endpoint
                invalidTransitNet(35),      -- invalid transit net
                tooManyAddPartyRequests(36),-- too many add party requests
                aalParamsUnsupported30(37), -- aal params unsupported
                infoELementMissing(38),     -- mandatory info element missing
                msgTypeNotImplemented(39),  -- msg type not implemented
                infoElementNotImplemented(40), -- info element not implemented
                invalidInfoElement(41),     -- invalid info element
                msgNotCompatible(42),       -- msg not comptaible with call state
                timerRecovery(43),          -- timer expired recovery
                invalidMsgLen(44),          -- invalid msg len
                protocolError(45),          -- protocol error
                opticalElementError(46),    -- optical element error 
                noRouteToNextNode(47),      -- no route to next node
                dtlNotMyNode(48)            -- not my node
        }

    --
    --  ATM Logical Port Stats Table.
    --

    eqAtmStatsTable OBJECT-TYPE
        SYNTAX      SEQUENCE OF EqAtmStatsEntry
        MAX-ACCESS  not-accessible
        STATUS      current
        DESCRIPTION
           "This table contains stats for an ATM logical port."
        ::= { eqAtmMib 1 }
        
    eqAtmStatsEntry OBJECT-TYPE
        SYNTAX      EqAtmStatsEntry
        MAX-ACCESS  not-accessible
        STATUS      current
        DESCRIPTION
                "An ATM logical port stats entry."
        INDEX    { eqAtmStatsIfIndex }
        ::= { eqAtmStatsTable 1 }

    EqAtmStatsEntry ::=
        SEQUENCE {
            eqAtmStatsIfIndex    
                    INTEGER,
            eqAtmStatsInCells        
                    Counter64,
            eqAtmStatsInCellsPerSecond        
                    Counter64,
            eqAtmStatsInBitsPerSecond        
                    Counter64,
            eqAtmStatsInCellsClp0        
                    Counter64,
            eqAtmStatsInCellsClp1
                    Counter64,
            eqAtmStatsInCellsTagged
                    Counter64,
            eqAtmStatsInCellsClp0Discards
                    Counter64,
            eqAtmStatsInCellsClp1Discards
                    Counter64,
            eqAtmStatsInCellsOam
                    Counter64,
            eqAtmStatsInCellsClp0Oam
                    Counter64,
            eqAtmStatsInCellsClp1Oam
                    Counter64,
            eqAtmStatsInCellsLoopback
                    Counter64,
            eqAtmStatsInCellsLoopbackOam
                    Counter64,
            eqAtmStatsOutCells        
                    Counter64,
            eqAtmStatsOutCellsPerSecond        
                    Counter64,
            eqAtmStatsOutBitsPerSecond        
                    Counter64,
            eqAtmStatsOutCellsClp0        
                    Counter64,
            eqAtmStatsOutCellsClp1
                    Counter64,
            eqAtmStatsOutCellsTagged
                    Counter64,
            eqAtmStatsOutCellsClp0Discards
                    Counter64,
            eqAtmStatsOutCellsClp1Discards
                    Counter64,
            eqAtmStatsOutCellsOam
                    Counter64,
            eqAtmStatsOutCellsClp0Oam
                    Counter64,
            eqAtmStatsOutCellsClp1Oam
                    Counter64,
            eqAtmStatsOutCellsLoopback
                    Counter64,
            eqAtmStatsOutCellsLoopbackOam
                    Counter64,
            eqAtmStatsCLR        
                    INTEGER
        }

    eqAtmStatsIfIndex OBJECT-TYPE
        SYNTAX      INTEGER (1..2147483647)
        MAX-ACCESS  read-only
        STATUS      current
        DESCRIPTION
            "The ifIndex for the corresponding atm logical port."
        ::= { eqAtmStatsEntry 1 }

    eqAtmStatsInCells OBJECT-TYPE
        SYNTAX      Counter64 
        MAX-ACCESS  read-only
        STATUS      current
        DESCRIPTION
            "The number of cells received."
        ::= { eqAtmStatsEntry 2 }

    eqAtmStatsInCellsPerSecond OBJECT-TYPE
        SYNTAX      Counter64 
        MAX-ACCESS  read-only
        STATUS      current
        DESCRIPTION
            "The number of cells received per second."
        ::= { eqAtmStatsEntry 3 }

    eqAtmStatsInBitsPerSecond OBJECT-TYPE
        SYNTAX      Counter64 
        MAX-ACCESS  read-only
        STATUS      current
        DESCRIPTION
            "The number of bits received per second."
        ::= { eqAtmStatsEntry 4 }

    eqAtmStatsInCellsClp0 OBJECT-TYPE
        SYNTAX      Counter64 
        MAX-ACCESS  read-only
        STATUS      current
        DESCRIPTION
            "The number of CLP-0 cells received."
        ::= { eqAtmStatsEntry 5 }

    eqAtmStatsInCellsClp1 OBJECT-TYPE
        SYNTAX      Counter64 
        MAX-ACCESS  read-only
        STATUS      current
        DESCRIPTION
            "The number of CLP-1 cells received."
        ::= { eqAtmStatsEntry 6 }

    eqAtmStatsInCellsTagged OBJECT-TYPE
        SYNTAX      Counter64 
        MAX-ACCESS  read-only
        STATUS      current
        DESCRIPTION
            "The number of tagged cells received."
        ::= { eqAtmStatsEntry 7 }

    eqAtmStatsInCellsClp0Discards OBJECT-TYPE
        SYNTAX      Counter64 
        MAX-ACCESS  read-only
        STATUS      current
        DESCRIPTION
            "The number of CLP-0 cells received and discarded."
        ::= { eqAtmStatsEntry 8 }

    eqAtmStatsInCellsClp1Discards OBJECT-TYPE
        SYNTAX      Counter64 
        MAX-ACCESS  read-only
        STATUS      current
        DESCRIPTION
            "The number of CLP-1 cells received and discarded."
        ::= { eqAtmStatsEntry 9 }

    eqAtmStatsInCellsOam OBJECT-TYPE
        SYNTAX      Counter64 
        MAX-ACCESS  read-only
        STATUS      current
        DESCRIPTION
            "The number of OAM cells received."
        ::= { eqAtmStatsEntry 10 }

    eqAtmStatsInCellsClp0Oam OBJECT-TYPE
        SYNTAX      Counter64 
        MAX-ACCESS  read-only
        STATUS      current
        DESCRIPTION
            "The number of CLP-0 OAM cells received."
        ::= { eqAtmStatsEntry 11 }

    eqAtmStatsInCellsClp1Oam OBJECT-TYPE
        SYNTAX      Counter64 
        MAX-ACCESS  read-only
        STATUS      current
        DESCRIPTION
            "The number of CLP-1 OAM cells received."
        ::= { eqAtmStatsEntry 12 }

    eqAtmStatsInCellsLoopback OBJECT-TYPE
        SYNTAX      Counter64 
        MAX-ACCESS  read-only
        STATUS      current
        DESCRIPTION
            "The number of loopback cells received."
        ::= { eqAtmStatsEntry 13 }

    eqAtmStatsInCellsLoopbackOam OBJECT-TYPE
        SYNTAX      Counter64 
        MAX-ACCESS  read-only
        STATUS      current
        DESCRIPTION
            "The number of loopback OAM cells received."
        ::= { eqAtmStatsEntry 14 }

    eqAtmStatsOutCells OBJECT-TYPE
        SYNTAX      Counter64 
        MAX-ACCESS  read-only
        STATUS      current
        DESCRIPTION
            "The number of cells transmitted."
        ::= { eqAtmStatsEntry 15 }

    eqAtmStatsOutCellsPerSecond OBJECT-TYPE
        SYNTAX      Counter64 
        MAX-ACCESS  read-only
        STATUS      current
        DESCRIPTION
            "The number of cells transmitted per second."
        ::= { eqAtmStatsEntry 16 }

    eqAtmStatsOutBitsPerSecond OBJECT-TYPE
        SYNTAX      Counter64 
        MAX-ACCESS  read-only
        STATUS      current
        DESCRIPTION
            "The number of bits transmitted per second."
        ::= { eqAtmStatsEntry 17 }

    eqAtmStatsOutCellsClp0 OBJECT-TYPE
        SYNTAX      Counter64 
        MAX-ACCESS  read-only
        STATUS      current
        DESCRIPTION
            "The number of CLP-0 cells transmitted."
        ::= { eqAtmStatsEntry 18 }

    eqAtmStatsOutCellsClp1 OBJECT-TYPE
        SYNTAX      Counter64 
        MAX-ACCESS  read-only
        STATUS      current
        DESCRIPTION
            "The number of CLP-1 cells transmitted."
        ::= { eqAtmStatsEntry 19 }

    eqAtmStatsOutCellsTagged OBJECT-TYPE
        SYNTAX      Counter64 
        MAX-ACCESS  read-only
        STATUS      current
        DESCRIPTION
            "The number of tagged cells transmitted."
        ::= { eqAtmStatsEntry 20 }

    eqAtmStatsOutCellsClp0Discards OBJECT-TYPE
        SYNTAX      Counter64 
        MAX-ACCESS  read-only
        STATUS      current
        DESCRIPTION
            "The number of CLP-0 cells discarded due to 
            lack of resources."
        ::= { eqAtmStatsEntry 21 }

    eqAtmStatsOutCellsClp1Discards OBJECT-TYPE
        SYNTAX      Counter64 
        MAX-ACCESS  read-only
        STATUS      current
        DESCRIPTION
            "The number of CLP-1 cells discarded due to 
            lack of resources."
        ::= { eqAtmStatsEntry 22 }

    eqAtmStatsOutCellsOam OBJECT-TYPE
        SYNTAX      Counter64 
        MAX-ACCESS  read-only
        STATUS      current
        DESCRIPTION
            "The number of OAM cells transmitted."
        ::= { eqAtmStatsEntry 23 }

    eqAtmStatsOutCellsClp0Oam OBJECT-TYPE
        SYNTAX      Counter64 
        MAX-ACCESS  read-only
        STATUS      current
        DESCRIPTION
            "The number of CLP-0 OAM cells transmitted."
        ::= { eqAtmStatsEntry 24 }

    eqAtmStatsOutCellsClp1Oam OBJECT-TYPE
        SYNTAX      Counter64 
        MAX-ACCESS  read-only
        STATUS      current
        DESCRIPTION
            "The number of CLP-1 OAM cells transmitted."
        ::= { eqAtmStatsEntry 25 }

    eqAtmStatsOutCellsLoopback OBJECT-TYPE
        SYNTAX      Counter64 
        MAX-ACCESS  read-only
        STATUS      current
        DESCRIPTION
            "The number of loopback cells transmitted."
        ::= { eqAtmStatsEntry 26 }

    eqAtmStatsOutCellsLoopbackOam OBJECT-TYPE
        SYNTAX      Counter64 
        MAX-ACCESS  read-only
        STATUS      current
        DESCRIPTION
            "The number of loopback OAM cells transmitted."
        ::= { eqAtmStatsEntry 27 }

    eqAtmStatsCLR OBJECT-TYPE
        SYNTAX      INTEGER (0..512)
        MAX-ACCESS  read-only
        STATUS      current
        DESCRIPTION
            "The cell loss ratio requirement, expressed as a negative
            exponent of 10. The default value of 512 indicates any
            cell loss ratio is acceptable."
        ::= { eqAtmStatsEntry 28 }


    --
    --  ATM Logical Port SVC Stats Table.
    --

    eqAtmSvcStatsTable OBJECT-TYPE
        SYNTAX      SEQUENCE OF EqAtmSvcStatsEntry
        MAX-ACCESS  not-accessible
        STATUS      current
        DESCRIPTION
           "This table contains svc stats for an ATM logical 
            port." 
        ::= { eqAtmMib 2 }
        
    eqAtmSvcStatsEntry OBJECT-TYPE
        SYNTAX      EqAtmSvcStatsEntry
        MAX-ACCESS  not-accessible
        STATUS      current
        DESCRIPTION
                "An ATM logical port svc stats entry."
        INDEX    { eqAtmSvcStatsIfIndex }
        ::= { eqAtmSvcStatsTable 1 }

    EqAtmSvcStatsEntry ::=
        SEQUENCE {
            eqAtmSvcStatsIfIndex    
                    INTEGER,
            eqAtmSvcTotal
                    Counter32,
            eqAtmSvcConnected
                    Counter32,
            eqAtmSvcFailures
                    Counter32,
            eqAtmSvcInLastCauseCode
                    AtmCauseCode,
            eqAtmSvcInSetupPdus
                    Counter32,
            eqAtmSvcInCallProceeding
                    Counter32,
            eqAtmSvcInPdusConnect
                    Counter32,
            eqAtmSvcInPdusConnectAck
                    Counter32,
            eqAtmSvcInPdusReleaseComplete
                    Counter32,
            eqAtmSvcInPdusAddParty
                    Counter32,
            eqAtmSvcInPdusAddPartyAck
                    Counter32,
            eqAtmSvcInPdusAddPartyReject
                    Counter32,
            eqAtmSvcInPdusDropParty
                    Counter32,
            eqAtmSvcInPdusDropPartyAck
                    Counter32,
            eqAtmSvcInPdusStatusEnquiry
                    Counter32,
            eqAtmSvcInPdusStatus
                    Counter32,
            eqAtmSvcInPdusRestart
                    Counter32,
            eqAtmSvcInPdusRestartAck
                    Counter32,
            eqAtmSvcInPdusNotify
                    Counter32,
            eqAtmSvcInPdusProgress
                    Counter32,
            eqAtmSvcInPdusAlerting
                    Counter32,
            eqAtmSvcInPdusPartyAlerting
                    Counter32,
            eqAtmSvcOutLastCauseCode
                    AtmCauseCode,
            eqAtmSvcOutSetupPdus
                    Counter32,
            eqAtmSvcOutCallProceeding
                    Counter32,
            eqAtmSvcOutPdusConnect
                    Counter32,
            eqAtmSvcOutPdusConnectAck
                    Counter32,
            eqAtmSvcOutPdusReleaseComplete
                    Counter32,
            eqAtmSvcOutPdusAddParty
                    Counter32,
            eqAtmSvcOutPdusAddPartyAck
                    Counter32,
            eqAtmSvcOutPdusAddPartyReject
                    Counter32,
            eqAtmSvcOutPdusDropParty
                    Counter32,
            eqAtmSvcOutPdusDropPartyAck
                    Counter32,
            eqAtmSvcOutPdusStatusEnquiry
                    Counter32,
            eqAtmSvcOutPdusStatus
                    Counter32,
            eqAtmSvcOutPdusRestart
                    Counter32,
            eqAtmSvcOutPdusRestartAck
                    Counter32,
            eqAtmSvcOutPdusNotify
                    Counter32,
            eqAtmSvcOutPdusProgress
                    Counter32,
            eqAtmSvcOutPdusAlerting
                    Counter32,
            eqAtmSvcOutPdusPartyAlerting
                    Counter32
        }

    eqAtmSvcStatsIfIndex OBJECT-TYPE
        SYNTAX      INTEGER (1..2147483647)
        MAX-ACCESS  read-only
        STATUS      current
        DESCRIPTION
            "The ifIndex for the corresponding atm logical port."
        ::= { eqAtmSvcStatsEntry 1 }

    eqAtmSvcTotal OBJECT-TYPE
        SYNTAX      Counter32 
        MAX-ACCESS  read-only
        STATUS      current
        DESCRIPTION
            "The total number of svc's established on this port."
        ::= { eqAtmSvcStatsEntry 2 }

    eqAtmSvcConnected OBJECT-TYPE
        SYNTAX      Counter32 
        MAX-ACCESS  read-only
        STATUS      current
        DESCRIPTION
            "The number of svc's currently active on this port."
        ::= { eqAtmSvcStatsEntry 3 }

    eqAtmSvcFailures OBJECT-TYPE
        SYNTAX      Counter32 
        MAX-ACCESS  read-only
        STATUS      current
        DESCRIPTION
            "The number of svc configuration failures on this port."
        ::= { eqAtmSvcStatsEntry 4 }

    eqAtmSvcInLastCauseCode OBJECT-TYPE
        SYNTAX      AtmCauseCode 
        MAX-ACCESS  read-only
        STATUS      current
        DESCRIPTION
            "The last cause code received on this port."
        ::= { eqAtmSvcStatsEntry 5 }

    eqAtmSvcInSetupPdus OBJECT-TYPE
        SYNTAX      Counter32 
        MAX-ACCESS  read-only
        STATUS      current
        DESCRIPTION
            "The number of setup pdu's received on this port."
        ::= { eqAtmSvcStatsEntry 6 }

    eqAtmSvcInCallProceeding OBJECT-TYPE
        SYNTAX      Counter32 
        MAX-ACCESS  read-only
        STATUS      current
        DESCRIPTION
            "The number of call proceeding pdu's received on this port."
        ::= { eqAtmSvcStatsEntry 7 }

    eqAtmSvcInPdusConnect OBJECT-TYPE
        SYNTAX      Counter32 
        MAX-ACCESS  read-only
        STATUS      current
        DESCRIPTION
            "The number of connect pdu's received on this port."
        ::= { eqAtmSvcStatsEntry 8 }

    eqAtmSvcInPdusConnectAck OBJECT-TYPE
        SYNTAX      Counter32 
        MAX-ACCESS  read-only
        STATUS      current
        DESCRIPTION
            "The number of connect ack pdu's received on this port."
        ::= { eqAtmSvcStatsEntry 9 }

    eqAtmSvcInPdusReleaseComplete OBJECT-TYPE
        SYNTAX      Counter32 
        MAX-ACCESS  read-only
        STATUS      current
        DESCRIPTION
            "The number of release complete pdu's received on this port."
        ::= { eqAtmSvcStatsEntry 10 }

    eqAtmSvcInPdusAddParty OBJECT-TYPE
        SYNTAX      Counter32 
        MAX-ACCESS  read-only
        STATUS      current
        DESCRIPTION
            "The number of add party pdu's received on this port."
        ::= { eqAtmSvcStatsEntry 11 }

    eqAtmSvcInPdusAddPartyAck OBJECT-TYPE
        SYNTAX      Counter32 
        MAX-ACCESS  read-only
        STATUS      current
        DESCRIPTION
            "The number of add party ack pdu's received on this port."
        ::= { eqAtmSvcStatsEntry 12 }

    eqAtmSvcInPdusAddPartyReject OBJECT-TYPE
        SYNTAX      Counter32 
        MAX-ACCESS  read-only
        STATUS      current
        DESCRIPTION
            "The number of add party reject pdu's received on this port."
        ::= { eqAtmSvcStatsEntry 13 }

    eqAtmSvcInPdusDropParty OBJECT-TYPE
        SYNTAX      Counter32 
        MAX-ACCESS  read-only
        STATUS      current
        DESCRIPTION
            "The number of drop party pdu's received on this port."
        ::= { eqAtmSvcStatsEntry 14 }

    eqAtmSvcInPdusDropPartyAck OBJECT-TYPE
        SYNTAX      Counter32 
        MAX-ACCESS  read-only
        STATUS      current
        DESCRIPTION
            "The number of drop party ack pdu's received on this port."
        ::= { eqAtmSvcStatsEntry 15 }

    eqAtmSvcInPdusStatusEnquiry OBJECT-TYPE
        SYNTAX      Counter32 
        MAX-ACCESS  read-only
        STATUS      current
        DESCRIPTION
            "The number of status enquiry pdu's received on this port."
        ::= { eqAtmSvcStatsEntry 16 }

    eqAtmSvcInPdusStatus OBJECT-TYPE
        SYNTAX      Counter32 
        MAX-ACCESS  read-only
        STATUS      current
        DESCRIPTION
            "The number of status pdu's received on this port."
        ::= { eqAtmSvcStatsEntry 17 }

    eqAtmSvcInPdusRestart OBJECT-TYPE
        SYNTAX      Counter32 
        MAX-ACCESS  read-only
        STATUS      current
        DESCRIPTION
            "The number of restart pdu's received on this port."
        ::= { eqAtmSvcStatsEntry 18 }

    eqAtmSvcInPdusRestartAck OBJECT-TYPE
        SYNTAX      Counter32 
        MAX-ACCESS  read-only
        STATUS      current
        DESCRIPTION
            "The number of restart ack pdu's received on this port."
        ::= { eqAtmSvcStatsEntry 19 }

    eqAtmSvcInPdusNotify OBJECT-TYPE
        SYNTAX      Counter32 
        MAX-ACCESS  read-only
        STATUS      current
        DESCRIPTION
            "The number of notify pdu's received on this port."
        ::= { eqAtmSvcStatsEntry 20 }

    eqAtmSvcInPdusProgress OBJECT-TYPE
        SYNTAX      Counter32 
        MAX-ACCESS  read-only
        STATUS      current
        DESCRIPTION
            "The number of progress pdu's received on this port."
        ::= { eqAtmSvcStatsEntry 21 }

    eqAtmSvcInPdusAlerting OBJECT-TYPE
        SYNTAX      Counter32 
        MAX-ACCESS  read-only
        STATUS      current
        DESCRIPTION
            "The number of alerting pdu's received on this port."
        ::= { eqAtmSvcStatsEntry 22 }

    eqAtmSvcInPdusPartyAlerting OBJECT-TYPE
        SYNTAX      Counter32 
        MAX-ACCESS  read-only
        STATUS      current
        DESCRIPTION
            "The number of party alerting pdu's received on this port."
        ::= { eqAtmSvcStatsEntry 23 }

    eqAtmSvcOutLastCauseCode OBJECT-TYPE
        SYNTAX      AtmCauseCode 
        MAX-ACCESS  read-only
        STATUS      current
        DESCRIPTION
            "The last cause code transmitted on this port."
        ::= { eqAtmSvcStatsEntry 24 }

    eqAtmSvcOutSetupPdus OBJECT-TYPE
        SYNTAX      Counter32 
        MAX-ACCESS  read-only
        STATUS      current
        DESCRIPTION
            "The number of setup pdu's transmitted on this port."
        ::= { eqAtmSvcStatsEntry 25 }

    eqAtmSvcOutCallProceeding OBJECT-TYPE
        SYNTAX      Counter32 
        MAX-ACCESS  read-only
        STATUS      current
        DESCRIPTION
            "The number of call proceeding pdu's transmitted on this port."
        ::= { eqAtmSvcStatsEntry 26 }

    eqAtmSvcOutPdusConnect OBJECT-TYPE
        SYNTAX      Counter32 
        MAX-ACCESS  read-only
        STATUS      current
        DESCRIPTION
            "The number of connect pdu's transmitted on this port."
        ::= { eqAtmSvcStatsEntry 27 }

    eqAtmSvcOutPdusConnectAck OBJECT-TYPE
        SYNTAX      Counter32 
        MAX-ACCESS  read-only
        STATUS      current
        DESCRIPTION
            "The number of connect ack pdu's transmitted on this port."
        ::= { eqAtmSvcStatsEntry 28 }

    eqAtmSvcOutPdusReleaseComplete OBJECT-TYPE
        SYNTAX      Counter32 
        MAX-ACCESS  read-only
        STATUS      current
        DESCRIPTION
            "The number of release complete pdu's transmitted on this port."
        ::= { eqAtmSvcStatsEntry 29 }

    eqAtmSvcOutPdusAddParty OBJECT-TYPE
        SYNTAX      Counter32 
        MAX-ACCESS  read-only
        STATUS      current
        DESCRIPTION
            "The number of add party pdu's transmitted on this port."
        ::= { eqAtmSvcStatsEntry 30 }

    eqAtmSvcOutPdusAddPartyAck OBJECT-TYPE
        SYNTAX      Counter32 
        MAX-ACCESS  read-only
        STATUS      current
        DESCRIPTION
            "The number of add party ack pdu's transmitted on this port."
        ::= { eqAtmSvcStatsEntry 31 }

    eqAtmSvcOutPdusAddPartyReject OBJECT-TYPE
        SYNTAX      Counter32 
        MAX-ACCESS  read-only
        STATUS      current
        DESCRIPTION
            "The number of add party reject pdu's transmitted on this port."
        ::= { eqAtmSvcStatsEntry 32 }

    eqAtmSvcOutPdusDropParty OBJECT-TYPE
        SYNTAX      Counter32 
        MAX-ACCESS  read-only
        STATUS      current
        DESCRIPTION
            "The number of drop party pdu's transmitted on this port."
        ::= { eqAtmSvcStatsEntry 33 }

    eqAtmSvcOutPdusDropPartyAck OBJECT-TYPE
        SYNTAX      Counter32 
        MAX-ACCESS  read-only
        STATUS      current
        DESCRIPTION
            "The number of drop party ack pdu's transmitted on this port."
        ::= { eqAtmSvcStatsEntry 34 }

    eqAtmSvcOutPdusStatusEnquiry OBJECT-TYPE
        SYNTAX      Counter32 
        MAX-ACCESS  read-only
        STATUS      current
        DESCRIPTION
            "The number of status enquiry pdu's transmitted on this port."
        ::= { eqAtmSvcStatsEntry 35 }

    eqAtmSvcOutPdusStatus OBJECT-TYPE
        SYNTAX      Counter32 
        MAX-ACCESS  read-only
        STATUS      current
        DESCRIPTION
            "The number of status pdu's transmitted on this port."
        ::= { eqAtmSvcStatsEntry 36 }

    eqAtmSvcOutPdusRestart OBJECT-TYPE
        SYNTAX      Counter32 
        MAX-ACCESS  read-only
        STATUS      current
        DESCRIPTION
            "The number of restart pdu's transmitted on this port."
        ::= { eqAtmSvcStatsEntry 37 }

    eqAtmSvcOutPdusRestartAck OBJECT-TYPE
        SYNTAX      Counter32 
        MAX-ACCESS  read-only
        STATUS      current
        DESCRIPTION
            "The number of restart ack pdu's transmitted on this port."
        ::= { eqAtmSvcStatsEntry 38 }

    eqAtmSvcOutPdusNotify OBJECT-TYPE
        SYNTAX      Counter32 
        MAX-ACCESS  read-only
        STATUS      current
        DESCRIPTION
            "The number of notify pdu's transmitted on this port."
        ::= { eqAtmSvcStatsEntry 39 }

    eqAtmSvcOutPdusProgress OBJECT-TYPE
        SYNTAX      Counter32 
        MAX-ACCESS  read-only
        STATUS      current
        DESCRIPTION
            "The number of progress pdu's transmitted on this port."
        ::= { eqAtmSvcStatsEntry 40 }

    eqAtmSvcOutPdusAlerting OBJECT-TYPE
        SYNTAX      Counter32 
        MAX-ACCESS  read-only
        STATUS      current
        DESCRIPTION
            "The number of alerting pdu's transmitted on this port."
        ::= { eqAtmSvcStatsEntry 41 }

    eqAtmSvcOutPdusPartyAlerting OBJECT-TYPE
        SYNTAX      Counter32 
        MAX-ACCESS  read-only
        STATUS      current
        DESCRIPTION
            "The number of party alerting pdu's transmitted on this port."
        ::= { eqAtmSvcStatsEntry 42 }


    --
    --  ATM Logical Port SAAL Stats Table.
    --

    eqAtmSaalStatsTable OBJECT-TYPE
        SYNTAX      SEQUENCE OF EqAtmSaalStatsEntry
        MAX-ACCESS  not-accessible
        STATUS      current
        DESCRIPTION
           "This table contains SAAL stats for an ATM logical 
            port." 
        ::= { eqAtmMib 3 }
        
    eqAtmSaalStatsEntry OBJECT-TYPE
        SYNTAX      EqAtmSaalStatsEntry
        MAX-ACCESS  not-accessible
        STATUS      current
        DESCRIPTION
                "An ATM logical port SAAL stats entry."
        INDEX    { eqAtmSaalStatsIfIndex }
        ::= { eqAtmSaalStatsTable 1 }

    EqAtmSaalStatsEntry ::=
        SEQUENCE {
            eqAtmSaalStatsIfIndex    
                    INTEGER,
            eqAtmSaalInErrors
                    Counter32,
            eqAtmSaalInDiscards
                    Counter32,
            eqAtmSaalInBeginPdus
                    Counter32,
            eqAtmSaalInBeginAckPdus
                    Counter32,
            eqAtmSaalInBeginRejectPdus
                    Counter32,
            eqAtmSaalInEndPdus
                    Counter32,
            eqAtmSaalInEndAckPdus
                    Counter32,
            eqAtmSaalInResyncPdus
                    Counter32,
            eqAtmSaalInResyncAckPdus
                    Counter32,
            eqAtmSaalInErrRecoveryPdus
                    Counter32,
            eqAtmSaalInSeqDataPdus
                    Counter32,
            eqAtmSaalInPollPdus
                    Counter32,
            eqAtmSaalInStatusPdus
                    Counter32,
            eqAtmSaalInUnsolicitedStatusPdus
                    Counter32,
            eqAtmSaalInUnsolicitedUserPdus
                    Counter32,
            eqAtmSaalInUnnumberedUserPdus
                    Counter32,
            eqAtmSaalInUnnumberedMgmtPdus
                    Counter32,
            eqAtmSaalInSignalOctets
                    Counter32,
            eqAtmSaalOutDiscards
                    Counter32,
            eqAtmSaalOutBeginPdus
                    Counter32,
            eqAtmSaalOutBeginAckPdus
                    Counter32,
            eqAtmSaalOutBeginRejectPdus
                    Counter32,
            eqAtmSaalOutEndPdus
                    Counter32,
            eqAtmSaalOutEndAckPdus
                    Counter32,
            eqAtmSaalOutResyncPdus
                    Counter32,
            eqAtmSaalOutResyncAckPdus
                    Counter32,
            eqAtmSaalOutErrRecoveryPdus
                    Counter32,
            eqAtmSaalOutSeqDataPdus
                    Counter32,
            eqAtmSaalOutPollPdus
                    Counter32,
            eqAtmSaalOutStatusPdus
                    Counter32,
            eqAtmSaalOutUnsolicitedStatusPdus
                    Counter32,
            eqAtmSaalOutUnsolicitedUserPdus
                    Counter32,
            eqAtmSaalOutUnnumberedUserPdus
                    Counter32,
            eqAtmSaalOutUnnumberedMgmtPdus
                    Counter32,
            eqAtmSaalOutSignalOctets
                    Counter32,
            eqAtmSaalOutWindowSize
                    INTEGER
        }

    eqAtmSaalStatsIfIndex OBJECT-TYPE
        SYNTAX      INTEGER (1..2147483647)
        MAX-ACCESS  read-only
        STATUS      current
        DESCRIPTION
            "The ifIndex for the corresponding atm logical port."
        ::= { eqAtmSaalStatsEntry 1 }

    eqAtmSaalInErrors OBJECT-TYPE
        SYNTAX      Counter32 
        MAX-ACCESS  read-only
        STATUS      current
        DESCRIPTION
            "The number of receive errors on this port."
        ::= { eqAtmSaalStatsEntry 2 }

    eqAtmSaalInDiscards OBJECT-TYPE
        SYNTAX      Counter32 
        MAX-ACCESS  read-only
        STATUS      current
        DESCRIPTION
            "The number of discards on this port."
        ::= { eqAtmSaalStatsEntry 3 }

    eqAtmSaalInBeginPdus OBJECT-TYPE
        SYNTAX      Counter32 
        MAX-ACCESS  read-only
        STATUS      current
        DESCRIPTION
            "The number of begin pdus received on this port."
        ::= { eqAtmSaalStatsEntry 4 }

    eqAtmSaalInBeginAckPdus OBJECT-TYPE
        SYNTAX      Counter32 
        MAX-ACCESS  read-only
        STATUS      current
        DESCRIPTION
            "The number of begin ack pdus received on this port."
        ::= { eqAtmSaalStatsEntry 5 }

    eqAtmSaalInBeginRejectPdus OBJECT-TYPE
        SYNTAX      Counter32 
        MAX-ACCESS  read-only
        STATUS      current
        DESCRIPTION
            "The number of begin reject pdus received on this port."
        ::= { eqAtmSaalStatsEntry 6 }

    eqAtmSaalInEndPdus OBJECT-TYPE
        SYNTAX      Counter32 
        MAX-ACCESS  read-only
        STATUS      current
        DESCRIPTION
            "The number of end pdus received on this port."
        ::= { eqAtmSaalStatsEntry 7 }

    eqAtmSaalInEndAckPdus OBJECT-TYPE
        SYNTAX      Counter32 
        MAX-ACCESS  read-only
        STATUS      current
        DESCRIPTION
            "The number of end ack pdus received on this port."
        ::= { eqAtmSaalStatsEntry 8 }

    eqAtmSaalInResyncPdus OBJECT-TYPE
        SYNTAX      Counter32 
        MAX-ACCESS  read-only
        STATUS      current
        DESCRIPTION
            "The number of resync pdus received on this port."
        ::= { eqAtmSaalStatsEntry 9 }

    eqAtmSaalInResyncAckPdus OBJECT-TYPE
        SYNTAX      Counter32 
        MAX-ACCESS  read-only
        STATUS      current
        DESCRIPTION
            "The number of resync ack pdus received on this port."
        ::= { eqAtmSaalStatsEntry 10 }

    eqAtmSaalInErrRecoveryPdus OBJECT-TYPE
        SYNTAX      Counter32 
        MAX-ACCESS  read-only
        STATUS      current
        DESCRIPTION
            "The number of error recovery pdus received on this port."
        ::= { eqAtmSaalStatsEntry 11 }

    eqAtmSaalInSeqDataPdus OBJECT-TYPE
        SYNTAX      Counter32 
        MAX-ACCESS  read-only
        STATUS      current
        DESCRIPTION
            "The number of sequence data pdus received on this port."
        ::= { eqAtmSaalStatsEntry 12 }

    eqAtmSaalInPollPdus OBJECT-TYPE
        SYNTAX      Counter32 
        MAX-ACCESS  read-only
        STATUS      current
        DESCRIPTION
            "The number of poll pdus received on this port."
        ::= { eqAtmSaalStatsEntry 13 }

    eqAtmSaalInStatusPdus OBJECT-TYPE
        SYNTAX      Counter32 
        MAX-ACCESS  read-only
        STATUS      current
        DESCRIPTION
            "The number of status pdus received on this port."
        ::= { eqAtmSaalStatsEntry 14 }

    eqAtmSaalInUnsolicitedStatusPdus OBJECT-TYPE
        SYNTAX      Counter32 
        MAX-ACCESS  read-only
        STATUS      current
        DESCRIPTION
            "The number of unsolicited status pdus received on this port."
        ::= { eqAtmSaalStatsEntry 15 }

    eqAtmSaalInUnsolicitedUserPdus OBJECT-TYPE
        SYNTAX      Counter32 
        MAX-ACCESS  read-only
        STATUS      current
        DESCRIPTION
            "The number of unsolicited user pdus received on this port."
        ::= { eqAtmSaalStatsEntry 16 }

    eqAtmSaalInUnnumberedUserPdus OBJECT-TYPE
        SYNTAX      Counter32 
        MAX-ACCESS  read-only
        STATUS      current
        DESCRIPTION
            "The number of unnumbered pdus received on this port."
        ::= { eqAtmSaalStatsEntry 17 }

    eqAtmSaalInUnnumberedMgmtPdus OBJECT-TYPE
        SYNTAX      Counter32 
        MAX-ACCESS  read-only
        STATUS      current
        DESCRIPTION
            "The number of unnumbered mgmt pdus received on this port."
        ::= { eqAtmSaalStatsEntry 18 }

    eqAtmSaalInSignalOctets OBJECT-TYPE
        SYNTAX      Counter32 
        MAX-ACCESS  read-only
        STATUS      current
        DESCRIPTION
            "The number of signal octets transmitted on this port."
        ::= { eqAtmSaalStatsEntry 19 }

    eqAtmSaalOutDiscards OBJECT-TYPE
        SYNTAX      Counter32 
        MAX-ACCESS  read-only
        STATUS      current
        DESCRIPTION
            "The number of begin pdus transmitted on this port."
        ::= { eqAtmSaalStatsEntry 20 }

    eqAtmSaalOutBeginPdus OBJECT-TYPE
        SYNTAX      Counter32 
        MAX-ACCESS  read-only
        STATUS      current
        DESCRIPTION
            "The number of begin pdus transmitted on this port."
        ::= { eqAtmSaalStatsEntry 21 }

    eqAtmSaalOutBeginAckPdus OBJECT-TYPE
        SYNTAX      Counter32 
        MAX-ACCESS  read-only
        STATUS      current
        DESCRIPTION
            "The number of begin ack pdus transmitted on this port."
        ::= { eqAtmSaalStatsEntry 22 }

    eqAtmSaalOutBeginRejectPdus OBJECT-TYPE
        SYNTAX      Counter32 
        MAX-ACCESS  read-only
        STATUS      current
        DESCRIPTION
            "The number of begin reject pdus transmitted on this port."
        ::= { eqAtmSaalStatsEntry 23 }

    eqAtmSaalOutEndPdus OBJECT-TYPE
        SYNTAX      Counter32 
        MAX-ACCESS  read-only
        STATUS      current
        DESCRIPTION
            "The number of end pdus transmitted on this port."
        ::= { eqAtmSaalStatsEntry 24 }

    eqAtmSaalOutEndAckPdus OBJECT-TYPE
        SYNTAX      Counter32 
        MAX-ACCESS  read-only
        STATUS      current
        DESCRIPTION
            "The number of end ack pdus transmitted on this port."
        ::= { eqAtmSaalStatsEntry 25 }

    eqAtmSaalOutResyncPdus OBJECT-TYPE
        SYNTAX      Counter32 
        MAX-ACCESS  read-only
        STATUS      current
        DESCRIPTION
            "The number of resync pdus transmitted on this port."
        ::= { eqAtmSaalStatsEntry 26 }

    eqAtmSaalOutResyncAckPdus OBJECT-TYPE
        SYNTAX      Counter32 
        MAX-ACCESS  read-only
        STATUS      current
        DESCRIPTION
            "The number of resync ack pdus transmitted on this port."
        ::= { eqAtmSaalStatsEntry 27 }

    eqAtmSaalOutErrRecoveryPdus OBJECT-TYPE
        SYNTAX      Counter32 
        MAX-ACCESS  read-only
        STATUS      current
        DESCRIPTION
            "The number of error recovery pdus transmitted on this port."
        ::= { eqAtmSaalStatsEntry 28 }

    eqAtmSaalOutSeqDataPdus OBJECT-TYPE
        SYNTAX      Counter32 
        MAX-ACCESS  read-only
        STATUS      current
        DESCRIPTION
            "The number of sequence data pdus transmitted on this port."
        ::= { eqAtmSaalStatsEntry 29 }

    eqAtmSaalOutPollPdus OBJECT-TYPE
        SYNTAX      Counter32 
        MAX-ACCESS  read-only
        STATUS      current
        DESCRIPTION
            "The number of poll pdus transmitted on this port."
        ::= { eqAtmSaalStatsEntry 30 }

    eqAtmSaalOutStatusPdus OBJECT-TYPE
        SYNTAX      Counter32 
        MAX-ACCESS  read-only
        STATUS      current
        DESCRIPTION
            "The number of status pdus transmitted on this port."
        ::= { eqAtmSaalStatsEntry 31 }

    eqAtmSaalOutUnsolicitedStatusPdus OBJECT-TYPE
        SYNTAX      Counter32 
        MAX-ACCESS  read-only
        STATUS      current
        DESCRIPTION
            "The number of unsolicited status pdus transmitted on this port."
        ::= { eqAtmSaalStatsEntry 32 }

    eqAtmSaalOutUnsolicitedUserPdus OBJECT-TYPE
        SYNTAX      Counter32 
        MAX-ACCESS  read-only
        STATUS      current
        DESCRIPTION
            "The number of unsolicited user pdus transmitted on this port."
        ::= { eqAtmSaalStatsEntry 33 }

    eqAtmSaalOutUnnumberedUserPdus OBJECT-TYPE
        SYNTAX      Counter32 
        MAX-ACCESS  read-only
        STATUS      current
        DESCRIPTION
            "The number of unnumbered pdus transmitted on this port."
        ::= { eqAtmSaalStatsEntry 34 }

    eqAtmSaalOutUnnumberedMgmtPdus OBJECT-TYPE
        SYNTAX      Counter32 
        MAX-ACCESS  read-only
        STATUS      current
        DESCRIPTION
            "The number of unnumbered mgmt pdus transmitted on this port."
        ::= { eqAtmSaalStatsEntry 35 }

    eqAtmSaalOutSignalOctets OBJECT-TYPE
        SYNTAX      Counter32 
        MAX-ACCESS  read-only
        STATUS      current
        DESCRIPTION
            "The number of signal octets transmitted on this port."
        ::= { eqAtmSaalStatsEntry 36 }

    eqAtmSaalOutWindowSize OBJECT-TYPE
        SYNTAX      INTEGER (1..4095) 
        MAX-ACCESS  read-only
        STATUS      current
        DESCRIPTION
            "The window size for SAAL on this port."
        ::= { eqAtmSaalStatsEntry 37 }



    --
    --  ATM Logical Port Stats Table.
    --

    eqAtmVcStatsTable OBJECT-TYPE
        SYNTAX      SEQUENCE OF EqAtmVcStatsEntry
        MAX-ACCESS  not-accessible
        STATUS      current
        DESCRIPTION
           "This table contains stats for an ATM logical port."
        ::= { eqAtmMib 4 }
        
    eqAtmVcStatsEntry OBJECT-TYPE
        SYNTAX      EqAtmVcStatsEntry
        MAX-ACCESS  not-accessible
        STATUS      current
        DESCRIPTION
                "An ATM logical port stats entry."
        INDEX    { eqAtmVcStatsIfIndex,
                   eqAtmVcStatsVpi,
                   eqAtmVcStatsVci }
        ::= { eqAtmVcStatsTable 1 }

    EqAtmVcStatsEntry ::=
        SEQUENCE {
            eqAtmVcStatsIfIndex    
                    INTEGER,
            eqAtmVcStatsVpi    
                    INTEGER,
            eqAtmVcStatsVci    
                    INTEGER,
            eqAtmVcStatsInCells        
                    Counter64,
            eqAtmVcStatsInCellsPerSecond        
                    Counter64,
            eqAtmVcStatsInBitsPerSecond        
                    Counter64,
            eqAtmVcStatsInCellsClp0        
                    Counter64,
            eqAtmVcStatsInCellsClp1
                    Counter64,
            eqAtmVcStatsInCellsTagged
                    Counter64,
            eqAtmVcStatsInCellsClp0Discards
                    Counter64,
            eqAtmVcStatsInCellsClp1Discards
                    Counter64,
            eqAtmVcStatsInCellsOam
                    Counter64,
            eqAtmVcStatsInCellsClp0Oam
                    Counter64,
            eqAtmVcStatsInCellsClp1Oam
                    Counter64,
            eqAtmVcStatsInCellsLoopback
                    Counter64,
            eqAtmVcStatsInCellsLoopbackOam
                    Counter64,
            eqAtmVcStatsOutCells        
                    Counter64,
            eqAtmVcStatsOutCellsPerSecond        
                    Counter64,
            eqAtmVcStatsOutBitsPerSecond        
                    Counter64,
            eqAtmVcStatsOutCellsClp0        
                    Counter64,
            eqAtmVcStatsOutCellsClp1
                    Counter64,
            eqAtmVcStatsOutCellsTagged
                    Counter64,
            eqAtmVcStatsOutCellsClp0Discards
                    Counter64,
            eqAtmVcStatsOutCellsClp1Discards
                    Counter64,
            eqAtmVcStatsOutCellsOam
                    Counter64,
            eqAtmVcStatsOutCellsClp0Oam
                    Counter64,
            eqAtmVcStatsOutCellsClp1Oam
                    Counter64,
            eqAtmVcStatsOutCellsLoopback
                    Counter64,
            eqAtmVcStatsOutCellsLoopbackOam
                    Counter64,
            eqAtmVcStatsCLR        
                    INTEGER
        }

    eqAtmVcStatsIfIndex OBJECT-TYPE
        SYNTAX      INTEGER (1..2147483647)
        MAX-ACCESS  read-only
        STATUS      current
        DESCRIPTION
            "The ifIndex for the corresponding atm logical port."
        ::= { eqAtmVcStatsEntry 1 }

    eqAtmVcStatsVpi OBJECT-TYPE
        SYNTAX      INTEGER (1..4095) 
        MAX-ACCESS  read-only
        STATUS      current
        DESCRIPTION
            "The Virtual Path Identifier."
        ::= { eqAtmVcStatsEntry 2 }

    eqAtmVcStatsVci OBJECT-TYPE
        SYNTAX      INTEGER (1..65535) 
        MAX-ACCESS  read-only
        STATUS      current
        DESCRIPTION
            "The Virtual Channel Identifier."
        ::= { eqAtmVcStatsEntry 3 }

    eqAtmVcStatsInCells OBJECT-TYPE
        SYNTAX      Counter64 
        MAX-ACCESS  read-only
        STATUS      current
        DESCRIPTION
            "The number of cells received."
        ::= { eqAtmVcStatsEntry 4 }

    eqAtmVcStatsInCellsPerSecond OBJECT-TYPE
        SYNTAX      Counter64 
        MAX-ACCESS  read-only
        STATUS      current
        DESCRIPTION
            "The number of cells received per second."
        ::= { eqAtmVcStatsEntry 5 }

    eqAtmVcStatsInBitsPerSecond OBJECT-TYPE
        SYNTAX      Counter64 
        MAX-ACCESS  read-only
        STATUS      current
        DESCRIPTION
            "The number of bits received per second."
        ::= { eqAtmVcStatsEntry 6 }

    eqAtmVcStatsInCellsClp0 OBJECT-TYPE
        SYNTAX      Counter64 
        MAX-ACCESS  read-only
        STATUS      current
        DESCRIPTION
            "The number of CLP-0 cells received."
        ::= { eqAtmVcStatsEntry 7 }

    eqAtmVcStatsInCellsClp1 OBJECT-TYPE
        SYNTAX      Counter64 
        MAX-ACCESS  read-only
        STATUS      current
        DESCRIPTION
            "The number of CLP-1 cells received."
        ::= { eqAtmVcStatsEntry 8 }

    eqAtmVcStatsInCellsTagged OBJECT-TYPE
        SYNTAX      Counter64 
        MAX-ACCESS  read-only
        STATUS      current
        DESCRIPTION
            "The number of tagged cells received."
        ::= { eqAtmVcStatsEntry 9 }

    eqAtmVcStatsInCellsClp0Discards OBJECT-TYPE
        SYNTAX      Counter64 
        MAX-ACCESS  read-only
        STATUS      current
        DESCRIPTION
            "The number of CLP-0 cells received and discarded."
        ::= { eqAtmVcStatsEntry 10 }

    eqAtmVcStatsInCellsClp1Discards OBJECT-TYPE
        SYNTAX      Counter64 
        MAX-ACCESS  read-only
        STATUS      current
        DESCRIPTION
            "The number of CLP-1 cells received and discarded."
        ::= { eqAtmVcStatsEntry 11 }

    eqAtmVcStatsInCellsOam OBJECT-TYPE
        SYNTAX      Counter64 
        MAX-ACCESS  read-only
        STATUS      current
        DESCRIPTION
            "The number of OAM cells received."
        ::= { eqAtmVcStatsEntry 12 }

    eqAtmVcStatsInCellsClp0Oam OBJECT-TYPE
        SYNTAX      Counter64 
        MAX-ACCESS  read-only
        STATUS      current
        DESCRIPTION
            "The number of CLP-0 OAM cells received."
        ::= { eqAtmVcStatsEntry 13 }

    eqAtmVcStatsInCellsClp1Oam OBJECT-TYPE
        SYNTAX      Counter64 
        MAX-ACCESS  read-only
        STATUS      current
        DESCRIPTION
            "The number of CLP-1 OAM cells received."
        ::= { eqAtmVcStatsEntry 14 }

    eqAtmVcStatsInCellsLoopback OBJECT-TYPE
        SYNTAX      Counter64 
        MAX-ACCESS  read-only
        STATUS      current
        DESCRIPTION
            "The number of loopback cells received."
        ::= { eqAtmVcStatsEntry 15 }

    eqAtmVcStatsInCellsLoopbackOam OBJECT-TYPE
        SYNTAX      Counter64 
        MAX-ACCESS  read-only
        STATUS      current
        DESCRIPTION
            "The number of loopback OAM cells received."
        ::= { eqAtmVcStatsEntry 16 }

    eqAtmVcStatsOutCells OBJECT-TYPE
        SYNTAX      Counter64 
        MAX-ACCESS  read-only
        STATUS      current
        DESCRIPTION
            "The number of cells transmitted."
        ::= { eqAtmVcStatsEntry 17 }

    eqAtmVcStatsOutCellsPerSecond OBJECT-TYPE
        SYNTAX      Counter64 
        MAX-ACCESS  read-only
        STATUS      current
        DESCRIPTION
            "The number of cells transmitted per second."
        ::= { eqAtmVcStatsEntry 18 }

    eqAtmVcStatsOutBitsPerSecond OBJECT-TYPE
        SYNTAX      Counter64 
        MAX-ACCESS  read-only
        STATUS      current
        DESCRIPTION
            "The number of bits transmitted per second."
        ::= { eqAtmVcStatsEntry 19 }

    eqAtmVcStatsOutCellsClp0 OBJECT-TYPE
        SYNTAX      Counter64 
        MAX-ACCESS  read-only
        STATUS      current
        DESCRIPTION
            "The number of CLP-0 cells transmitted."
        ::= { eqAtmVcStatsEntry 20 }

    eqAtmVcStatsOutCellsClp1 OBJECT-TYPE
        SYNTAX      Counter64 
        MAX-ACCESS  read-only
        STATUS      current
        DESCRIPTION
            "The number of CLP-1 cells transmitted."
        ::= { eqAtmVcStatsEntry 21 }

    eqAtmVcStatsOutCellsTagged OBJECT-TYPE
        SYNTAX      Counter64 
        MAX-ACCESS  read-only
        STATUS      current
        DESCRIPTION
            "The number of tagged cells transmitted."
        ::= { eqAtmVcStatsEntry 22 }

    eqAtmVcStatsOutCellsClp0Discards OBJECT-TYPE
        SYNTAX      Counter64 
        MAX-ACCESS  read-only
        STATUS      current
        DESCRIPTION
            "The number of CLP-0 cells discarded due to 
            lack of resources."
        ::= { eqAtmVcStatsEntry 23 }

    eqAtmVcStatsOutCellsClp1Discards OBJECT-TYPE
        SYNTAX      Counter64 
        MAX-ACCESS  read-only
        STATUS      current
        DESCRIPTION
            "The number of CLP-1 cells discarded due to 
            lack of resources."
        ::= { eqAtmVcStatsEntry 24 }

    eqAtmVcStatsOutCellsOam OBJECT-TYPE
        SYNTAX      Counter64 
        MAX-ACCESS  read-only
        STATUS      current
        DESCRIPTION
            "The number of OAM cells transmitted."
        ::= { eqAtmVcStatsEntry 25 }

    eqAtmVcStatsOutCellsClp0Oam OBJECT-TYPE
        SYNTAX      Counter64 
        MAX-ACCESS  read-only
        STATUS      current
        DESCRIPTION
            "The number of CLP-0 OAM cells transmitted."
        ::= { eqAtmVcStatsEntry 26 }

    eqAtmVcStatsOutCellsClp1Oam OBJECT-TYPE
        SYNTAX      Counter64 
        MAX-ACCESS  read-only
        STATUS      current
        DESCRIPTION
            "The number of CLP-1 OAM cells transmitted."
        ::= { eqAtmVcStatsEntry 27 }

    eqAtmVcStatsOutCellsLoopback OBJECT-TYPE
        SYNTAX      Counter64 
        MAX-ACCESS  read-only
        STATUS      current
        DESCRIPTION
            "The number of loopback cells transmitted."
        ::= { eqAtmVcStatsEntry 28 }

    eqAtmVcStatsOutCellsLoopbackOam OBJECT-TYPE
        SYNTAX      Counter64 
        MAX-ACCESS  read-only
        STATUS      current
        DESCRIPTION
            "The number of loopback OAM cells transmitted."
        ::= { eqAtmVcStatsEntry 29 }

    eqAtmVcStatsCLR OBJECT-TYPE
        SYNTAX      INTEGER (0..512)
        MAX-ACCESS  read-only
        STATUS      current
        DESCRIPTION
            "The cell loss ratio requirement, expressed as a negative
            exponent of 10. The default value of 512 indicates any
            cell loss ratio is acceptable."
        ::= { eqAtmVcStatsEntry 30 }



    --
    --  ATM OAM Performance Monitoring Table.
    --

    eqAtmOamPmTable OBJECT-TYPE
        SYNTAX      SEQUENCE OF EqAtmOamPmEntry
        MAX-ACCESS  not-accessible
        STATUS      current
        DESCRIPTION
           "This table contains OAM Performance Monitoring
            stats for an ATM OAM PM Session."
        ::= { eqAtmMib 5 }

    eqAtmOamPmEntry OBJECT-TYPE
        SYNTAX      EqAtmOamPmEntry
        MAX-ACCESS  not-accessible
        STATUS      current
        DESCRIPTION
                "An ATM logical port stats entry."
        INDEX    { eqAtmOamPmIfIndex,
                   eqAtmOamPmVpi,
                   eqAtmOamPmVci }
        ::= { eqAtmOamPmTable 1 }

    EqAtmOamPmEntry ::=
        SEQUENCE {
            eqAtmOamPmIfIndex
                    INTEGER,
            eqAtmOamPmVpi
                    INTEGER,
            eqAtmOamPmVci
                    INTEGER,
            eqAtmOamPmStatus
                    INTEGER,
            eqAtmOamPmSessionType
                    INTEGER,
            eqAtmOamPmSinkSource
                    INTEGER,
            eqAtmOamPmBlockSize
                    INTEGER,
            eqAtmOamPmEndPt
                    INTEGER,
            eqAtmOamPmFlow
                    INTEGER,
            eqAtmOamPmDirection
                    INTEGER,
            eqAtmOamPmTimeout
                    INTEGER,
            eqAtmOamPmRetryCount
                    INTEGER,
            eqAtmOamPmFwdTxUserCellsClp0
                    Counter32,
            eqAtmOamPmFwdTxUserCellsClp01
                    Counter32,
            eqAtmOamPmFwdTxLostCellsClp0
                    Counter32,
            eqAtmOamPmFwdTxLostCellsClp01
                    Counter32,
            eqAtmOamPmFwdSECBs
                    Counter32,
            eqAtmOamPmBwdTxUserCellsClp0
                    Counter32,
            eqAtmOamPmBwdTxUserCellsClp01
                    Counter32,
            eqAtmOamPmBwdTxLostCellsClp0
                    Counter32,
            eqAtmOamPmBwdTxLostCellsClp01
                    Counter32,
            eqAtmOamPmBwdSECBs
                    Counter32
        }

    eqAtmOamPmIfIndex OBJECT-TYPE
        SYNTAX      INTEGER (1..2147483647)
        MAX-ACCESS  read-only
        STATUS      current
        DESCRIPTION
            "The ifIndex for the corresponding atm logical port."
        ::= { eqAtmOamPmEntry 1 }

    eqAtmOamPmVpi OBJECT-TYPE
        SYNTAX      INTEGER (1..4095)
        MAX-ACCESS  read-only
        STATUS      current
        DESCRIPTION
            "The Virtual Path Identifier."
        ::= { eqAtmOamPmEntry 2 }

    eqAtmOamPmVci OBJECT-TYPE
        SYNTAX      INTEGER (1..65535)
        MAX-ACCESS  read-only
        STATUS      current
        DESCRIPTION
            "The Virtual Channel Identifier."
        ::= { eqAtmOamPmEntry 3 }

    eqAtmOamPmStatus OBJECT-TYPE
        SYNTAX      INTEGER {
                activating(1),
                connected(2),
                failConnect(3),
                failNoResource(4)
        }
        MAX-ACCESS  read-only
        STATUS      current
        DESCRIPTION
            "Indicates whether the activation process is in
             the middle of activating, has successfully
             connected, has failed to connect because the
             remote end did not respond, or couldn't setup
             the connection because of lack of local resources."
        ::= { eqAtmOamPmEntry 4 }

    eqAtmOamPmSessionType OBJECT-TYPE
        SYNTAX      INTEGER {
                contCheck(1),
                perfMonitoring(2)
        }
        MAX-ACCESS  read-only
        STATUS      current
        DESCRIPTION
            "Identifies the PM session to perform Continuity Check
             or Performance Monitoring."
        ::= { eqAtmOamPmEntry 5 }

    eqAtmOamPmSinkSource OBJECT-TYPE
        SYNTAX      INTEGER {
                sink(1),
                source(2),
                bidirectional(3)
        }
        MAX-ACCESS  read-only
        STATUS      current
        DESCRIPTION
            "Identifies the PM session to be sink, source, or both."
        ::= { eqAtmOamPmEntry 6 }

    eqAtmOamPmBlockSize OBJECT-TYPE
        SYNTAX      INTEGER {
                bytes128(1),
                bytes256(2),
                bytes512(3),
                bytes1K(4),
                bytes2K(5),
                bytes4K(6),
                bytes8K(7),
                bytes16K(8),
                bytes32K(9)
        }
        MAX-ACCESS  read-only
        STATUS      current
        DESCRIPTION
            "The Block Size of User cells transmitted before an
             OAM PM cell is transmitted."
        ::= { eqAtmOamPmEntry 7 }

    eqAtmOamPmEndPt OBJECT-TYPE
        SYNTAX      INTEGER {
                segment(1),
                endToEnd(2)
        }
        MAX-ACCESS  read-only
        STATUS      current
        DESCRIPTION
            "Identifies the PM Session as either a Segment Endpoint
             or an End-to-End Point"
        ::= { eqAtmOamPmEntry 8 }

    eqAtmOamPmFlow OBJECT-TYPE
        SYNTAX      INTEGER {
                f4(1),
                f5(2)
        }
        MAX-ACCESS  read-only
        STATUS      current
        DESCRIPTION
            "Identifies the Flow as either an F4 (Virtual Path)
             or F5 (Virtual Channel) flow."
        ::= { eqAtmOamPmEntry 9 }

    eqAtmOamPmDirection OBJECT-TYPE
        SYNTAX      INTEGER {
                segment(1),
                endToEnd(2)
        }
        MAX-ACCESS  read-only
        STATUS      current
        DESCRIPTION
            "Identifies the direction as either
                Forward (Egress, toward the outside netword)
             or
                Backward (Ingress, toward the switch fabric)"
        ::= { eqAtmOamPmEntry 10 }

    eqAtmOamPmTimeout OBJECT-TYPE
        SYNTAX      INTEGER (1..60)
        MAX-ACCESS  read-only
        STATUS      current
        DESCRIPTION
            "Identifies the Time Period in which to timeout an
             Activation/DeActivation Cell (in which case another
             cell may be sent depending on the Retry Count)."
        ::= { eqAtmOamPmEntry 11 }

    eqAtmOamPmRetryCount OBJECT-TYPE
        SYNTAX      INTEGER (1..10)
        MAX-ACCESS  read-only
        STATUS      current
        DESCRIPTION
            "Number of times to retry Activation in the event
             of a failure (no response)."
        ::= { eqAtmOamPmEntry 12 }

    eqAtmOamPmFwdTxUserCellsClp0 OBJECT-TYPE
        SYNTAX      Counter32
        MAX-ACCESS  read-only
        STATUS      current
        DESCRIPTION
            "The number of Clp0 cells transmitted."
        ::= { eqAtmOamPmEntry 13 }

    eqAtmOamPmFwdTxUserCellsClp01 OBJECT-TYPE
        SYNTAX      Counter32
        MAX-ACCESS  read-only
        STATUS      current
        DESCRIPTION
            "The number of Clp0 plus Clp1 cells transmitted."
        ::= { eqAtmOamPmEntry 14 }

    eqAtmOamPmFwdTxLostCellsClp0 OBJECT-TYPE
        SYNTAX      Counter32
        MAX-ACCESS  read-only
        STATUS      current
        DESCRIPTION
            "The number of Clp0 cells Lost."
        ::= { eqAtmOamPmEntry 15 }

    eqAtmOamPmFwdTxLostCellsClp01 OBJECT-TYPE
        SYNTAX      Counter32
        MAX-ACCESS  read-only
        STATUS      current
        DESCRIPTION
            "The number of Clp0 plus Clp1 cells Lost."
        ::= { eqAtmOamPmEntry 16 }

    eqAtmOamPmFwdSECBs OBJECT-TYPE
        SYNTAX      Counter32
        MAX-ACCESS  read-only
        STATUS      current
        DESCRIPTION
            "The number of Severely Errored Cell Blocks."
        ::= { eqAtmOamPmEntry 17 }

    eqAtmOamPmBwdTxUserCellsClp0 OBJECT-TYPE
        SYNTAX      Counter32
        MAX-ACCESS  read-only
        STATUS      current
        DESCRIPTION
            "The number of Clp0 cells transmitted."
        ::= { eqAtmOamPmEntry 18 }

    eqAtmOamPmBwdTxUserCellsClp01 OBJECT-TYPE
        SYNTAX      Counter32
        MAX-ACCESS  read-only
        STATUS      current
        DESCRIPTION
            "The number of Clp0 plus Clp1 cells transmitted."
        ::= { eqAtmOamPmEntry 19 }

    eqAtmOamPmBwdTxLostCellsClp0 OBJECT-TYPE
        SYNTAX      Counter32
        MAX-ACCESS  read-only
        STATUS      current
        DESCRIPTION
            "The number of Clp0 cells Lost."
        ::= { eqAtmOamPmEntry 20 }

    eqAtmOamPmBwdTxLostCellsClp01 OBJECT-TYPE
        SYNTAX      Counter32
        MAX-ACCESS  read-only
        STATUS      current
        DESCRIPTION
            "The number of Clp0 plus Clp1 cells Lost."
        ::= { eqAtmOamPmEntry 21 }

    eqAtmOamPmBwdSECBs OBJECT-TYPE
        SYNTAX      Counter32
        MAX-ACCESS  read-only
        STATUS      current
        DESCRIPTION
            "The number of Severely Errored Cell Blocks."
        ::= { eqAtmOamPmEntry 22 }


    --
    --  ATM OAM Loopback Table.
    --

    eqAtmOamLoopbackTable OBJECT-TYPE
        SYNTAX      SEQUENCE OF EqAtmOamLoopbackEntry
        MAX-ACCESS  not-accessible
        STATUS      current
        DESCRIPTION
           "This table contains OAM Performance Monitoring
            stats for an ATM OAM PM Session."
        ::= { eqAtmMib 6 }

    eqAtmOamLoopbackEntry OBJECT-TYPE
        SYNTAX      EqAtmOamLoopbackEntry
        MAX-ACCESS  not-accessible
        STATUS      current
        DESCRIPTION
                "An ATM logical port stats entry."
        INDEX    { eqAtmOamLoopbackIfIndex,
                   eqAtmOamLoopbackVpi,
                   eqAtmOamLoopbackVci }
        ::= { eqAtmOamLoopbackTable 1 }

    EqAtmOamLoopbackEntry ::=
        SEQUENCE {
            eqAtmOamLoopbackIfIndex
                    INTEGER,
            eqAtmOamLoopbackVpi
                    INTEGER,
            eqAtmOamLoopbackVci
                    INTEGER,
            eqAtmOamLoopbackStatus
                    INTEGER,
            eqAtmOamLoopbackSendCount
                    INTEGER,
            eqAtmOamLoopbackSendTrap
                    INTEGER,
            eqAtmOamLoopbackEndPoint
                    INTEGER,
            eqAtmOamLoopbackFlow
                    INTEGER,
            eqAtmOamLoopbackDirection
                    INTEGER,
            eqAtmOamLoopbackTimeout
                    INTEGER,
            eqAtmOamLoopbackCellsReceived
                    Counter32,
            eqAtmOamLoopbackCellsTimedOut
                    Counter32,
            eqAtmOamLoopbackAveCellTime
                    INTEGER,
            eqAtmOamLoopbackMinCellTime
                    INTEGER,
            eqAtmOamLoopbackMaxCellTime
                    INTEGER,
            eqAtmOamLoopbackTotalCellTime
                    INTEGER
        }

    eqAtmOamLoopbackIfIndex OBJECT-TYPE
        SYNTAX      INTEGER (1..2147483647)
        MAX-ACCESS  read-only
        STATUS      current
        DESCRIPTION
            "The ifIndex for the corresponding atm logical port."
        ::= { eqAtmOamLoopbackEntry 1 }

    eqAtmOamLoopbackVpi OBJECT-TYPE
        SYNTAX      INTEGER (1..4095)
        MAX-ACCESS  read-only
        STATUS      current
        DESCRIPTION
            "The Virtual Path Identifier."
        ::= { eqAtmOamLoopbackEntry 2 }

    eqAtmOamLoopbackVci OBJECT-TYPE
        SYNTAX      INTEGER (1..65535)
        MAX-ACCESS  read-only
        STATUS      current
        DESCRIPTION
            "The Virtual Channel Identifier."
        ::= { eqAtmOamLoopbackEntry 3 }

    eqAtmOamLoopbackStatus OBJECT-TYPE
        SYNTAX      INTEGER {
                inProgress(1),
                completed(2)
        }
        MAX-ACCESS  read-only
        STATUS      current
        DESCRIPTION
            "Indicates whether the Loopback request is being worked on
             or has completed."
        ::= { eqAtmOamLoopbackEntry 4 }

    eqAtmOamLoopbackSendCount OBJECT-TYPE
        SYNTAX      INTEGER (1..100)
        MAX-ACCESS  read-only
        STATUS      current
        DESCRIPTION
            "Indicates the number of Loopback Cells to send."
        ::= { eqAtmOamLoopbackEntry 5 }

    eqAtmOamLoopbackSendTrap OBJECT-TYPE
        SYNTAX      INTEGER {
                send(1),
                noAction(2)
        }
        MAX-ACCESS  read-only
        STATUS      current
        DESCRIPTION
            "Indicates whether or not to send an SNMP trap when finished."
        ::= { eqAtmOamLoopbackEntry 6 }

    eqAtmOamLoopbackEndPoint OBJECT-TYPE
        SYNTAX      INTEGER {
                segment(1),
                endToEnd(2)
        }
        MAX-ACCESS  read-only
        STATUS      current
        DESCRIPTION
            "Indicates whether the Loopback Cell to be sent is a Segment
             or End-to-End Point type cell."
        ::= { eqAtmOamLoopbackEntry 7 }

    eqAtmOamLoopbackFlow OBJECT-TYPE
        SYNTAX      INTEGER {
                f4(1),
                f5(2)
        }
        MAX-ACCESS  read-only
        STATUS      current
        DESCRIPTION
            "Identifies the Flow as either an F4 (Virtual Path)
             or F5 (Virtual Channel) flow."
        ::= { eqAtmOamLoopbackEntry 8 }

    eqAtmOamLoopbackDirection OBJECT-TYPE
        SYNTAX      INTEGER {
                segment(1),
                endToEnd(2)
        }
        MAX-ACCESS  read-only
        STATUS      current
        DESCRIPTION
            "Identifies the direction as either
                Forward (Egress, toward the outside netword)
             or
                Backward (Ingress, toward the switch fabric)"
        ::= { eqAtmOamLoopbackEntry 9 }

    eqAtmOamLoopbackTimeout OBJECT-TYPE
        SYNTAX      INTEGER (1..60)
        MAX-ACCESS  read-only
        STATUS      current
        DESCRIPTION
            "Indicates the Timeout (in seconds) to wait for a Loopback
             response before sending another (or finishing)."
        ::= { eqAtmOamLoopbackEntry 10 }

    eqAtmOamLoopbackCellsReceived OBJECT-TYPE
        SYNTAX      Counter32
        MAX-ACCESS  read-only
        STATUS      current
        DESCRIPTION
            "Count of the number of Loopback cell responses received
             succesfully."
        ::= { eqAtmOamLoopbackEntry 11 }

    eqAtmOamLoopbackCellsTimedOut OBJECT-TYPE
        SYNTAX      Counter32
        MAX-ACCESS  read-only
        STATUS      current
        DESCRIPTION
            "Count of the number of Loopback cell responses not received
             succesfully."
        ::= { eqAtmOamLoopbackEntry 12 }

    eqAtmOamLoopbackAveCellTime OBJECT-TYPE
        SYNTAX      INTEGER (1..2147483647)
        MAX-ACCESS  read-only
        STATUS      current
        DESCRIPTION
            "Average response time (in milliseconds) for the Loopback Cell."
        ::= { eqAtmOamLoopbackEntry 13 }

    eqAtmOamLoopbackMinCellTime OBJECT-TYPE
        SYNTAX      INTEGER (1..2147483647)
        MAX-ACCESS  read-only
        STATUS      current
        DESCRIPTION
            "Minimum response time (in milliseconds) for the Loopback Cell."
        ::= { eqAtmOamLoopbackEntry 14 }

    eqAtmOamLoopbackMaxCellTime OBJECT-TYPE
        SYNTAX      INTEGER (1..2147483647)
        MAX-ACCESS  read-only
        STATUS      current
        DESCRIPTION
            "Maximum response time (in milliseconds) for the Loopback Cell."
        ::= { eqAtmOamLoopbackEntry 15 }

    eqAtmOamLoopbackTotalCellTime OBJECT-TYPE
        SYNTAX      INTEGER (1..2147483647)
        MAX-ACCESS  read-only
        STATUS      current
        DESCRIPTION
            "Total response time (in milliseconds) for all Loopback Cells
             of the session."
        ::= { eqAtmOamLoopbackEntry 16 }



END
