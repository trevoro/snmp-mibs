ELFIQ-MODULE-COMMON-MIB DEFINITIONS ::= BEGIN

	IMPORTS
      MODULE-IDENTITY, OBJECT-TYPE, Integer32,
		NOTIFICATION-TYPE,TimeTicks			FROM SNMPv2-SMI
		TEXTUAL-CONVENTION, DisplayString, DateAndTime,
		RowStatus, VariablePointer			FROM SNMPv2-TC
		MODULE-COMPLIANCE, OBJECT-GROUP,
		NOTIFICATION-GROUP					FROM SNMPv2-CONF
		snmpTraps							FROM SNMPv2-MIB
		common,commonConformance     		FROM ELFIQ-INC-MIB;

--
-- A brief description and update information about this mib.
--
commonComponent                     MODULE-IDENTITY
    LAST-UPDATED "0902190000Z"            -- 09 Feb 2009, midnight
    ORGANIZATION "Elfiq Inc."
    CONTACT-INFO "
              Author:     Elfiq Network
              postal:     Montreal, QC H3B3A7
                                     CANADA
              email:      support@elfiq.com
              phone:      +1-514-667-0611
                        "
    DESCRIPTION  "This is the mib representing the common component of all your elfiq products"
    ::= { common 1 }


--
-- 3) This is the part for the component syst
--

systInfo		     		OBJECT IDENTIFIER ::= { commonComponent 1 }

--

SystIndex ::= TEXTUAL-CONVENTION
	DISPLAY-HINT	"d"
	STATUS 			current
	DESCRIPTION 
				" A unique value, greater than zero, for
					system functionality "
	SYNTAX		Integer32 (0..10)

systNumber		OBJECT-TYPE
	SYNTAX      Integer32 (0..10)
	MAX-ACCESS  read-only
	STATUS      current
	DESCRIPTION
           "The number of system configured"
	::= { systInfo 1 }

-- the syst table which contains information about its component details

systTable 		OBJECT-TYPE
	SYNTAX 		SEQUENCE OF SystEntry
	MAX-ACCESS	not-accessible
	STATUS		current
	DESCRIPTION	
				"This is a list of syst entries. The number of syst is 
				given by the value of systNumber."
	::= { systInfo 2 }

systEntry		OBJECT-TYPE
	SYNTAX		SystEntry
	MAX-ACCESS	not-accessible
	STATUS 		current
	DESCRIPTION	
				" An entry containing syst sub-component."
	INDEX	{ systIndex }
	::= { systTable 1 }
	
SystEntry ::=
	SEQUENCE {
			systIndex				SystIndex,
			systModel				DisplayString,
			systHostname			DisplayString,
			systVersion				Integer32,
			systRevision			Integer32,
			systRelease				Integer32,
			systBuild				Integer32,
			systTypeDesc			DisplayString,
			systTime				DateAndTime,
			systLicenceStatus		INTEGER,
			systLicenceType			INTEGER,
			systNbVfiActivated		Integer32,
			systCpuUsePct			Integer32,
			systRamUsePct			Integer32,
			systFanSpeed			Integer32,
			systCpuTemp				Integer32,
			systSmptSeverity		INTEGER,
			systSmtpReciptient1		DisplayString,
			systSmtpReciptient2		DisplayString,
			systSmtpReciptient3		DisplayString,
			systSmtpReciptient4		DisplayString,
			systSmtpReciptient5		DisplayString,
			systSmtpReciptient6		DisplayString,
			systSmtpReciptient7		DisplayString,
			systSmtpReciptient8		DisplayString

	}
	
systIndex		OBJECT-TYPE
	SYNTAX      SystIndex
	MAX-ACCESS  read-only
	STATUS      current
	DESCRIPTION
           "The syst index default is 1"
	::= { systEntry 1 }

systModel		OBJECT-TYPE
	SYNTAX      DisplayString (SIZE (0..255))
	MAX-ACCESS  read-only
	STATUS      current
	DESCRIPTION
           "The model of your elfiq product"
	::= { systEntry 2 }

systHostname	OBJECT-TYPE
	SYNTAX      DisplayString (SIZE (0..255))
	MAX-ACCESS  read-only
	STATUS      current
	DESCRIPTION
           "The hostname of your elfiq product"
	::= { systEntry 3 }

systVersion		OBJECT-TYPE
	SYNTAX      Integer32
	MAX-ACCESS  read-only
	STATUS      current
	DESCRIPTION
           "The version of your elfiq product"
	::= { systEntry 4 }

systRevision		OBJECT-TYPE
	SYNTAX      Integer32
	MAX-ACCESS  read-only
	STATUS      current
	DESCRIPTION
           "The revision of your elfiq product"
	::= { systEntry 5 }

systRelease		OBJECT-TYPE
	SYNTAX      Integer32
	MAX-ACCESS  read-only
	STATUS      current
	DESCRIPTION
           "The build number of your elfiq product"
	::= { systEntry 6 }

systBuild		OBJECT-TYPE
	SYNTAX      Integer32
	MAX-ACCESS  read-only
	STATUS      current
	DESCRIPTION
           "The sub build of your elfiq product"
	::= { systEntry 7 }

systTypeDesc	OBJECT-TYPE
	SYNTAX      DisplayString (SIZE (0..255))
	MAX-ACCESS  read-only
	STATUS      current
	DESCRIPTION
           "The type description of your elfiq product"
	::= { systEntry 8 }

systTime		OBJECT-TYPE
 	SYNTAX      DateAndTime
   	MAX-ACCESS  read-only
   	STATUS      current
	DESCRIPTION
        "The date and time configured in your elfiq product "
	::= { systEntry 9 }

systLicenceStatus 	OBJECT-TYPE
	SYNTAX	INTEGER { 
						ok(1),
						notVerified(2),
						keyActivated(3),
						readKeyFailed(4)
				}
   MAX-ACCESS  read-only
   STATUS      current
	DESCRIPTION
           "The status of our licence, Valid , No licence , Not verified etc..."
	::= { systEntry 10 }

systLicenceType 	OBJECT-TYPE
	SYNTAX   INTEGER { 
						endUser(1),
						demo(2),
						nfr(3),
						hrl(4),
						isp(5)
				}
   MAX-ACCESS  read-only
   STATUS      current
	DESCRIPTION
           "This is your type of licence. Is it for a user , a demonstration etc..."
	::= { systEntry 11 }

systNbVfiActivated 	OBJECT-TYPE
	SYNTAX   	Integer32
   MAX-ACCESS  read-only
   STATUS      current
	DESCRIPTION
           "This is the number of vfi you can activate with your licence"
	::= { systEntry 12 }

systCpuUsePct 	OBJECT-TYPE
	SYNTAX   	Integer32
   MAX-ACCESS  read-only
   STATUS      current
	DESCRIPTION
           "This is the per cent cpu usage of your elfiq product"
	::= { systEntry 13 }

systRamUsePct 	OBJECT-TYPE
	SYNTAX   	Integer32
   MAX-ACCESS  read-only
   STATUS      current
	DESCRIPTION
           "This is the per cent ram usage of your elfiq product"
	::= { systEntry 14 }

systFanSpeed 	OBJECT-TYPE
	SYNTAX   	Integer32
   MAX-ACCESS  read-only
   STATUS      current
	DESCRIPTION
           "This is the fan speed of your elfiq product
				Note: depending on your model this value could be not provided"
	::= { systEntry 15 }

systCpuTemp 	OBJECT-TYPE
	SYNTAX   	Integer32
   MAX-ACCESS  read-only
   STATUS      current
	DESCRIPTION
           "This is the current temperature of you elfiq product
				Note: depending on your model this value could be not provided"
	::= { systEntry 16 }

systSmptSeverity 	OBJECT-TYPE
	SYNTAX   	INTEGER { 
						alert(1),
						warning(2),
						notice(3),
						info(4)
				}
   MAX-ACCESS  read-only
   STATUS      current
	DESCRIPTION
           "This is the severity configured for the smtp messages sent"
	::= { systEntry 17 }

systSmtpReciptient1 	OBJECT-TYPE
	SYNTAX   	DisplayString (SIZE (0..255))
   MAX-ACCESS  read-only
   STATUS      current
	DESCRIPTION
           "This is the first smtp recipient"
	::= { systEntry 18 }

systSmtpReciptient2 	OBJECT-TYPE
	SYNTAX   	DisplayString (SIZE (0..255))
   MAX-ACCESS  read-only
   STATUS      current
	DESCRIPTION
           "This is the first smtp recipient"
	::= { systEntry 19 }

systSmtpReciptient3 	OBJECT-TYPE
	SYNTAX   	DisplayString (SIZE (0..255))
   MAX-ACCESS  read-only
   STATUS      current
	DESCRIPTION
           "This is the third smtp recipient"
	::= { systEntry 20 }

systSmtpReciptient4 	OBJECT-TYPE
	SYNTAX   	DisplayString (SIZE (0..255))
   MAX-ACCESS  read-only
   STATUS      current
	DESCRIPTION
           "This is the fourth smtp recipient"
	::= { systEntry 21 }

systSmtpReciptient5 	OBJECT-TYPE
	SYNTAX   	DisplayString (SIZE (0..255))
   MAX-ACCESS  read-only
   STATUS      current
	DESCRIPTION
           "This is the fifth smtp recipient"
	::= { systEntry 22 }

systSmtpReciptient6 	OBJECT-TYPE
	SYNTAX   	DisplayString (SIZE (0..255))
   MAX-ACCESS  read-only
   STATUS      current
	DESCRIPTION
           "This is the sixth smtp recipient"
	::= { systEntry 23 }

systSmtpReciptient7 	OBJECT-TYPE
	SYNTAX   	DisplayString (SIZE (0..255))
   MAX-ACCESS  read-only
   STATUS      current
	DESCRIPTION
           "This is the seventh smtp recipient"
	::= { systEntry 24 }

systSmtpReciptient8 	OBJECT-TYPE
	SYNTAX   	DisplayString (SIZE (0..255))
   MAX-ACCESS  read-only
   STATUS      current
	DESCRIPTION
           "This is the eighth smtp recipient"
	::= { systEntry 25 }



---
--- Notification event
---
commonNotification			OBJECT IDENTIFIER ::= { common 2 }

--

systNotification 		OBJECT IDENTIFIER ::= { commonNotification 1 }

--

systEOSStart 	NOTIFICATION-TYPE
    OBJECTS 		{ systHostname }
    STATUS    		current
    DESCRIPTION
        "This notification is sent every time your elfiq product starts"
    ::= { systNotification 1 }

systCPUTemp		 	NOTIFICATION-TYPE
    OBJECTS 		{ systHostname, 
							systCpuTemp
						 }
    STATUS    		current
    DESCRIPTION
        "This notification is sent when the temperature of your CPU is higher than 40�C"
    ::= { systNotification 2 }

systCPUUsage			NOTIFICATION-TYPE
    OBJECTS 		{ systHostname }
    STATUS    		current
    DESCRIPTION
        "This notification is sent when your CPU Usage is higher than 90%"
    ::= { systNotification 3 }

systCPUFan			NOTIFICATION-TYPE
    OBJECTS 		{ systHostname }
    STATUS    		current
    DESCRIPTION
        "This notification is sent when your CPU Fan speed is under 100 RPM"
    ::= { systNotification 4 }

---
-- Define object group conformance
---

systGroups	OBJECT IDENTIFIER ::= { commonConformance 1 }

	 systInfoGroup    OBJECT-GROUP
          OBJECTS {
			systNumber,
			systIndex,
			systModel,
			systHostname,
			systVersion,
			systRevision,
			systRelease,
			systBuild,
			systTypeDesc,
			systTime,
			systLicenceStatus,
			systLicenceType,
			systNbVfiActivated,
			systCpuUsePct,
			systFanSpeed,
			systCpuTemp,
			systRamUsePct,	
			systSmptSeverity,
			systSmtpReciptient1,
			systSmtpReciptient2,
			systSmtpReciptient3,
			systSmtpReciptient4,
			systSmtpReciptient5,
			systSmtpReciptient6,
			systSmtpReciptient7,
			systSmtpReciptient8			
       }
          STATUS     current
          DESCRIPTION
              "A collection of objects providing the syst information"
      ::= { systGroups 1 }

	systNotificationGroup    NOTIFICATION-GROUP
          NOTIFICATIONS {
             systEOSStart, systCPUTemp, systCPUUsage, systCPUFan
       }
          STATUS     current
          DESCRIPTION
              "A collection of objects notification corresponding to your products changes"
      ::= { systGroups 2 }


	
END
