QMS-MIB  --{ iso org(3) dod(6) internet(1) private(4) enterprises(1) 480 }
	DEFINITIONS ::= BEGIN
--	Copyright Minolta-QMS, Inc 1992-2000
--
--      External Release Revision      : 1.0.6
--      Component Software Label       : OIDG_03v18
--
--	History
-- 	  Original Version 0.1, November 19, 1992, TCP/IP NIC only
--
--        March 1994 TCP/IP NIC additions
--
--        April 1994, TCP/IP NIC additions
--
--        February 1997, Printer controller features additions
--
--        September 1997, added more enumerations for mediatype and consumable type
--
--        November 1997, added dpi2401 option to qmsENGResolution
--
--        June 1998, Added qmsCostPerPage(403) group, and qmsCPPSerialNumber(...480.1.403.2)
--
--        October 1998, Added qmsSYSMultiRes (...480.1.1.1011)
--
--        Nov 1998, Added qmsColorMatch(404) group, and six columnar objects in the group 
--
--        Nov 1998, Changed the OID numbers for qmsCMMProfileIndex, Description, and Type
--                  fixed appropriate enumeration for qmsCMMProfileType
--
--        Jan 1999, Added qmsClientColorMatching memory option handle.
--                  Added qmsENGOffsetStacking option handle.
-- 
--        Apr 1999, Added qmsClientHPEmulation memory option handle.
--                  Added qmsCMMICCHP color matching option handle.
--
--        Jun 2000, Changed corporate name to Minolta-QMS

--	MIB Descriptions

IMPORTS
       NetworkAddress, IpAddress, enterprises FROM RFC1155-SMI
		 OBJECT-TYPE               FROM RFC-1212
       DisplayString             FROM RFC1213-MIB
       snmp FROM RFC1158-MIB
       TRAP-TYPE FROM RFC-1215;

-- qmsInc MODULE-IDENTITY
--     LAST-UPDATED "000606"
--     ORGANIZATION "Minolta-QMS, Inc."
--     CONTACT-INFO
--             "    Engineering Division (Embedded Systems Dept)
--          Postal: Minolta-QMS Inc
--                  One Magnum Pass
--                  Mobile, AL, 36618
-- 
--                 Tel: 334-633-4300
--                 Fax: 334-639-3337
--              E-mail: mike.schlotterbeck@minolta-qms.com"
--     DESCRIPTION
--             "The MIB module for management of QMS printers."
--     ::= { enterprises 480 }
-- 
------------------------------------------------------------------------------
-- Define the QMS-MIB location
------------------------------------------------------------------------------
qmsInc		OBJECT IDENTIFIER ::= { enterprises 480 }
qmsUIH		OBJECT IDENTIFIER ::= { qmsInc 1 }

------------------------------------------------------------------------------
-- QMS UIH Groups
------------------------------------------------------------------------------
qmsSystem	OBJECT IDENTIFIER ::= {qmsUIH 1}
qmsMemory	OBJECT IDENTIFIER ::= {qmsUIH 5}

qmsIoCtl	OBJECT IDENTIFIER ::= {qmsUIH 101}
qmsHTTP         OBJECT IDENTIFIER ::= {qmsUIH 102}
qmsIoTimeOuts	OBJECT IDENTIFIER ::= {qmsUIH 103}
qmsIoPages	OBJECT IDENTIFIER ::= {qmsUIH 104}
qmsSerial	OBJECT IDENTIFIER ::= {qmsUIH 160}
qmsParallel	OBJECT IDENTIFIER ::= {qmsUIH 161}

qmsEngine	OBJECT IDENTIFIER ::= {qmsUIH 304}

qmsAccounting	OBJECT IDENTIFIER ::= {qmsUIH 401}
qmsScanner	OBJECT IDENTIFIER ::= {qmsUIH 402}
qmsCostPerPage	OBJECT IDENTIFIER ::= {qmsUIH 403}
qmsColorMatch   OBJECT IDENTIFIER ::= {qmsUIH 404} 


qmsPS	        OBJECT IDENTIFIER ::= {qmsUIH 520}
qmsHPGL		OBJECT IDENTIFIER ::= {qmsUIH 524}
qmsHPPCL	OBJECT IDENTIFIER ::= {qmsUIH 525}
qmsDECLN03	OBJECT IDENTIFIER ::= {qmsUIH 532}
qmsQUIC2	OBJECT IDENTIFIER ::= {qmsUIH 534}
qmsCCITT	OBJECT IDENTIFIER ::= {qmsUIH 538}
qmsLinePrinter	OBJECT IDENTIFIER ::= {qmsUIH 539}
qmsTIFF		OBJECT IDENTIFIER ::= {qmsUIH 541}
qmsCALS		OBJECT IDENTIFIER ::= {qmsUIH 542}
qmsCGM		OBJECT IDENTIFIER ::= {qmsUIH 544}

------------------------------------------------------------------------------
-- QMS System Option Handled
------------------------------------------------------------------------------

qmsSYSPageCount OBJECT-TYPE
	SYNTAX INTEGER
	ACCESS read-only
	STATUS mandatory
	DESCRIPTION
		"Value used to indicate the current number of pages printed to date."
	::= { qmsSystem 1001 }

qmsSYSSheetCount OBJECT-TYPE
	SYNTAX INTEGER
	ACCESS read-only
	STATUS mandatory
	DESCRIPTION
		"Flag used to indicate the current number of sheets printed to date."
	::= { qmsSystem 1002 }

qmsSYSPrinterModel OBJECT-TYPE
	SYNTAX DisplayString (SIZE(0..80))
	ACCESS read-only
	STATUS mandatory
	DESCRIPTION
		"Printer model name string."
	::= { qmsSystem 1003 }

qmsSYSPrinterVersion OBJECT-TYPE
	SYNTAX DisplayString (SIZE(0..80))
	ACCESS read-only
	STATUS mandatory
	DESCRIPTION
		"Value used to hold the current version of the printer software."
	::= { qmsSystem 1004 }

qmsSYSPrinterName OBJECT-TYPE
	SYNTAX DisplayString (SIZE(0..32))
	ACCESS read-write
	STATUS mandatory
	DESCRIPTION
		"Value used to hold the current printer name."
	::= { qmsSystem 1005 }

qmsSYSA3PageCount OBJECT-TYPE
	SYNTAX INTEGER
	ACCESS read-only
	STATUS mandatory
	DESCRIPTION
		"Value used to indicate the current number of A3 pages/faces printed to date."
	::= { qmsSystem 1006 }

qmsSYSA3SheetCount OBJECT-TYPE
	SYNTAX INTEGER
	ACCESS read-only
	STATUS mandatory
	DESCRIPTION
		"Value used to indicate the current number of A3 sheets printed to date."
	::= { qmsSystem 1007 }

qmsSYSFPA OBJECT-TYPE
	SYNTAX INTEGER {
		yes(2),
		no(1)
	}
	ACCESS  read-only
	STATUS      mandatory
	DESCRIPTION
		"Is FPA chip set installed in the system."
	::= { qmsSystem 1008 }

qmsSYSSystemImage OBJECT-TYPE
	SYNTAX INTEGER {
		flashSystem(2),
		diskSystem(1)
	}
	ACCESS  read-only
	STATUS      mandatory
	DESCRIPTION
		"What type of boot system is running."
	::= { qmsSystem 1009 }

qmsSYSDiskSwap OBJECT-TYPE
	SYNTAX INTEGER {
		diskSwapingDisabled(1),
		diskSwapingEnabled(2)
	}
	ACCESS read-only
	STATUS mandatory
	DESCRIPTION
		"Flag used to indicate the current state of disk swapping."
	::= { qmsSystem 1010 }

qmsSYSMultiRes OBJECT-TYPE
	SYNTAX INTEGER {
                notSupported(1),
		notPresent(2),
		lowMemory(3),
		disabled(4),
		optional(5),
		standard(6)
	}
	ACCESS  read-only
	STATUS      mandatory
	DESCRIPTION
		"Multi-Res is a mechanism which provides either
                 a printing resolution higher than the print engine's
                 native resolution or edge-smoothing at the native resolution.

                Current state of Multi-Res Option:
                notSupported(1) -> Feature is not available for this product
		notPresent(2)   -> Not Present in the Unit.
                                   Need to purchase this option separately
		lowMemory(3)    -> Feature installed or standard
                                   Insufficient memory to apply.
		disabled(4)     -> Feature installed or standard
                                   Feature disable by console option setting.
		optional(5)     -> Optional feature is present.
                                   System has sufficient memory to apply
		standard(6)     -> Standard feature is present.
                                   System has sufficient memory to apply"
	::= { qmsSystem 1011 }

------------------------------------------------------------------------------
-- QMS Memory Option Handles
------------------------------------------------------------------------------

qmsMEMPhysical OBJECT-TYPE
	SYNTAX	INTEGER
	ACCESS read-only
	STATUS mandatory
	DESCRIPTION
		"Size of the physical memory in MB."
	::= { qmsMemory 1 }

qmsMEMTotal OBJECT-TYPE
	SYNTAX	INTEGER
	ACCESS read-only
	STATUS mandatory
	DESCRIPTION
		"Size of the total virtual memory in MB.

		 Note: If no hard disk is installed, this will
		       be the size of physical memory."
	::= { qmsMemory 2 }

qmsClientSystem OBJECT-TYPE
	SYNTAX  INTEGER
	ACCESS  read-only
	STATUS mandatory
	DESCRIPTION
		"Also known as System Use, this non-configurable client is the amount
		of RAM used to run the printer's operating system. It's never
		increased or decreased. The system memory subtracted from the
		total amount of RAM identifies the amount of RAM available for all the
		other memory clients. Size is returned in Kilobytes."
	::= { qmsMemory 3 }

qmsClientSpool OBJECT-TYPE
	SYNTAX INTEGER
	ACCESS read-only
	STATUS mandatory
	DESCRIPTION
		"Also known as Host Input and K Mem for Spool, this memory client 
		stores incoming data from all the interfaces until the emulation can 
		process the print job. When enough memory is allocated to this client, 
		the host becomes free more quickly, and the number of jobs that the 
		printer can accept simultaneously is increased. You should consider 
		the amount of data being sent simultaneously when allocating mem-
		ory to the spool buffer. If available, a hard disk can supplement this 
		client with additional memory needed for spooling. Size is returned in
		Kilobytes.  

		Note: While increasing this client is beneficial in reducing network 
		      traffic, throughput is not necessarily increased. In addition, making 
		      this client too large could actually decrease throughput because of 
		      the overhead involved with managing a large spool."
	::= { qmsMemory 4 }

qmsClientEmulation OBJECT-TYPE
	SYNTAX INTEGER
	ACCESS read-only
	STATUS mandatory
	DESCRIPTION
		"Also known as K Mem Emulation, this client is used to store any 
		optional or loadable emulations, such as LN03 Plus or QUIC II. 
		Increasing this client's memory allows you to load more than one 
		optional emulation so that it doesn't have to be reloaded every time 
		the print job is sent.

		If an emulation is loaded to process a print job and there is not 
		enough memory in the emulation client, another emulation already 
		loaded may be unloaded automatically to obtain enough memory. If 
		you notice a delay in printing between jobs that have different nonres-
		ident emulations, it's possible that the emulations are having to reload 
		each time they're run. Adding to the emulation client may eliminate 
		the unloading and reloading of these emulations and, consequently, 
		increase throughput. It is recommended that you should add at least 
		1 MB of physical RAM to your printer and increase this memory client 
		by 1 MB for each additional emulation loaded. If your printer has an 
		optional hard disk and the disk swapping option is turned on then you 
		can increase the emulation memory client using this memory. 
		
		Size is returned in Kilobytes.

		Note: You should add at least 1 MB to the emulation memory client for 
		      each loadable emulation that your printer uses. Failure to add 
		      memory to this client may prevent the printer from loading and using 
		      the emulation. You should check the documentation accompanying 
		      your loadable emulation for information on additional resource 
		      requirements.

		Also increase the emulation client if you're printing complex non-Post-
		Script jobs that may require more memory to process correctly."
	::= { qmsMemory 5 }

qmsClientHeap OBJECT-TYPE
	SYNTAX INTEGER
	ACCESS read-only
	STATUS mandatory
	DESCRIPTION
		"Also known as K Mem PSHeap, Heap, PostScript VM, and Virtual 
		Memory, this client holds downloaded fonts, PostScript operators, and 
		forms.

		Inefficiently coded PostScript jobs can consume an extremely large 
		amount of virtual memory or leave objects in the PostScript Heap 
		after the print jobs are completed, leading to virtual memory errors. If 
		not enough memory is allocated to the PS Heap, the job cannot print. 

		Increasing the memory allocated to this client allows more complex 
		jobs to print and increases the number of fonts that can be down-
		loaded to virtual memory. 

		However, this client should be increased only if you receive a virtual 
		memory error when attempting to print a job or download a font, and 
		even then it should be increased only in small increments until the 
		error message goes away. Excess memory in the PS Heap is not 
		used."
	::= { qmsMemory 6 }

qmsClientFontCache OBJECT-TYPE
	SYNTAX INTEGER
	ACCESS read-only
	STATUS mandatory
	DESCRIPTION
		"Also known as K Mem PS Fonts and Font Cache, this memory client 
		stores bitmapped representations of previously scaled PostScript 
		fonts. This process reduces the number of times a font must be con-
		verted from outline form to bitmap form. Printing pages that have 
		characters already stored in the font cache is immensely faster than 
		printing characters not yet in the font cache.

		As the font cache memory fills, the printer makes room for new bit-
		mapped characters by erasing those that have been in the cache 
		longest without being used. Increasing the memory allocated to this 
		client, allows the printer to store more characters and spend less time 
		erasing and replacing characters in the cache. You should be careful 
		when increasing this client because the printer may spend more time 
		searching the cache than it would scaling the character. This client 
		has a limit to the maximum point size it will store.

		Normally, you don't need to change this memory client unless you 
		use a large number of fonts at various point sizes. If you do, you may 
		allocate additional memory to this client to improve printer perfor-
		mance. There's no specific formula to use in figuring the amount of 
		memory required by the font cache, but after a certain point, large font 
		caches cause the printer to take longer to print than smaller font 
		caches because of the search time through the cache. The recom-
		mended font cache size is in the following ranges:

			* 128-256 KB for 300x300 dpi printing
			* 256-512 KB for 600x600 dpi printing
			* 384-512 KB for 1200x1200 dpi printing

		You should experiment to see what font cache size works best for 
		you.

		Size is returned in Kilobytes."
	::= { qmsMemory 7 }

qmsClientDisplayList OBJECT-TYPE
	SYNTAX INTEGER
	ACCESS read-only
	STATUS mandatory
	DESCRIPTION
		"Also known as K Mem Display, this client stores compressed repre-
		sentations, or blocks, of the pages to be printed. It takes approxi-
		mately one compressed block for a normal 8.5'' x 11'' (215.9 mm x 
		279.4 mm) text page, four compressed blocks for an 8.5'' x 11''
		(215.9mm x 279.4 mm) page that includes some graphics, and as 
		many as 500 compressed blocks for an extremely complex page.

		Many pages of compressed blocks belonging to multiple print jobs 
		can be stored at the same time in the display list. If enough memory is 
		allocated to this memory client, a page can always be ready to print 
		as soon as another page has been imaged to the print engine.

        The amount of memory required for each compressed block is printer
        specific. See your printer specific manual for the amount of memory
        that a disply list will require for each compressed block. If a page 
		includes raster image data (for example, TIFF or bitmap data),
        each compressed block will require much more memory.

        Increasing the amount of memory in this client may improve printing
        throughput and minimize slowdowns due to collating or printing com-
        plex pages. If your Print System has a hard disk and the disk swap
        option is enabled, the memory added to this client is taken from virtual
        memory. If your printer does not have a hard disk then, the memory added
        to this client is taken from the amount of physical memory in your printer.
        It may be necessary to reduce memory added to another client before adding
        memory to the Display List. Check that the Frame Buffer still has the minimum
        amount of memory needed for your printing needs before reallocating this memory.
		
		Size is returned in Kilobytes."
	::= { qmsMemory 8 }

qmsClientFrameBuffer OBJECT-TYPE
	SYNTAX INTEGER
	ACCESS read-only
	STATUS mandatory
	DESCRIPTION
		"The Frame Buffer memory client holds rasterized or bitmapped 
		images of page faces which are ready to be sent to the print engine. A 
		frame holds the contents of each single page image. For example, a 
		600 dpi page printed on letter size paper would consume frame buffer 
		memory space as follows:
		  (600dpi x 600dpi x 8.5 in x 11 in) /8 = 4,207,500 bytes or 4.1 MB.

		Because the frame buffer memory is so critical to the actual printing 
		of a page, its allocation takes precedence over that of other memory 
		clients. The number of frames needed to print at engine speed is 
		engine specific and depends on the size media and resolution. For 
		example, printing at 600x600 dpi requires four times the amount of 
		memory in the frame buffer than does 300x300 dpi.

		If you are uncertain about how to configure your printer's memory, 
		use only the Administration/Memory/QuickConfig menu. This menu 
		appears if your printer does not have a hard disk attached or if the 
		disk swap option is disabled. Use this menu as a starting point before 
		trying manually to configure your printer's memory.

		It provides a simple method of defining how much memory should go 
		to each of the clients for the most complicated printing conditions in 
		your environment. Menu options allow you to specify the largest 
		media size at the resolution you plan to use. Memory is then automat-
		ically allocated to the clients.

		Size is returned in Kilobytes.

		Choices
			02200-variable depending on options installed"
	::= { qmsMemory 9 }

qmsClientEmulTemp OBJECT-TYPE
	SYNTAX  INTEGER
	ACCESS read-only
	STATUS mandatory
	DESCRIPTION
		"Also known as K Mem Emul Tmp and Emulation Temporary, this cli-
		ent sets the amount of system memory to be used by non-PostScript 
		emulations for storing downloaded many different non-Post Script 
		fonts, forms, or macros. By dedicating a portion of memory to this cli-
		ent, your printer can perform context switching, which is the ability to 
		retain downloaded fonts and forms even after the printer changes 
		from one emulation to another. Context switching prevents unneces-
		sary repetitive downloading and traffic congestion on networks. 

		Normally, this memory client doesn't need to be changed unless you 
		plan to download many different non-PostScript fonts, forms, or mac-
		ros.

		Size is returned in Kilobytes."
	::= { qmsMemory 10 }

qmsClientDisk OBJECT-TYPE
	SYNTAX INTEGER
	ACCESS read-only
	STATUS mandatory
	DESCRIPTION
		"This memory client stores frequently used data in system memory 
		instead of continually storing and retrieving it from a hard disk. If a 
		hard disk is used and a lot of disk access is required, adding memory 
		to the disk cache may increase the printer's performance.

		For example, if many fonts are stored on disk, faster access to these 
		fonts is achieved by increasing the disk cache size. Conversely, if no 
		hard disk is used, the disk cache will automatically be set to 0 KB until 
		a hard disk is installed and formatted. However, when one or more 
		hard disks are installed and formatted, disk cache is automatically 
		allocated 256 KB.

		The disk cache is a high-speed temporary buffer for data going to and 
		from the hard disk. It can speed up the printer in two ways:

		* Information such as frequently referenced fonts and logos may 
		  still be in the cache and may not have to be pulled off a hard disk 
		  each time they're needed.

		* Information being written to a hard disk can be held in the cache 
		  temporarily until a more convenient time to be written to disk.

		The amount of memory needed for the disk cache client is dependent 
		on the size of the disk, the number of disks, the number of subdirecto-
		ries on each disk, and the amount of memory dedicated to caching. 
		As long as the disk cache is enabled and there is enough memory in 
		the disk cache, all disks are accessible. If insufficient memory is allo-
		cated to the disk cache, some disks may be seen while others are 
		not.

		The recommended amount of memory for the disk cache client for all 
		hard disk is as follows:

		* 45 KB internal usage

		* 0.5 KB per MB of disk storage total for all disks

		* 100 KB of memory dedicated to caching

		For example, the recommended amount of memory for the disk cache 
		for a single 120 MB hard disk would be 208 KB, and for two 120 MB 
		hard disks it would be 268 KB.

		Size is returned in Kilobytes."
	::= { qmsMemory 11 }

qmsClientColorMatching OBJECT-TYPE
	SYNTAX INTEGER
	ACCESS read-only
	STATUS mandatory
	DESCRIPTION
		"The Color Matching memory client provides storage space for the
                control and operation of the Color Matching feature.  The available
                space is used to process the generation and management of printer 
                resident, custom ICC color matching profiles, as-well-as the 
                feature generated device link conversion maps.  These device link
                maps are ultimately used for RGB and CMYK device space color 
                conversion.

                By retaining the most frequently used profile and device link 
                information in primary storage, performance of the color matching
                operation is increased.  This increase comes from the ellimination of
                the time required to find and load the desired ICC profiles for a given 
                job, and to then generate the device link map used during color
                conversion by the printer's page description language.

                The size of ICC profiles used for color matching device link generation
                will affect the amount of free space remaining to the memory client
                for routine color matching operations.  The feature will routinely 
                unload unused profiles and device links as necessary to retain
                sufficient free space for operation.  However, if downloaded custom ICC
                profiles are overly large, excessive memory can be consumed for 
                device link generation, exhausting available client memory needed for
                other operations.  This will result in color matching processing errors
                being reported to the user.

                If color matching memory resource errors occur, the problem can be
                corrected by reducing the quality setting of the generated device link 
                maps via the operator panel, or by increasing the amount of memory
                available to the color matching client.

		If you are uncertain about how to configure your printer's memory, 
		use only the Administration/Memory/QuickConfig menu. This menu 
		appears if your printer does not have a hard disk attached or if the 
		disk swap option is disabled. Use this menu as a starting point before 
		attempting to manually configure your printer's memory.

		It provides a simple method of defining how much memory should go 
		to each of the clients for the most complicated printing conditions in 
		your environment. Menu options allow you to specify the largest 
		media size at the resolution you plan to use. Memory is then automat-
		ically allocated to the clients.

		Size is returned in Kilobytes.

		Choices: 8196KB default, or variable, depending on options installed"

	::= { qmsMemory 13 }

qmsClientHPStoragePool OBJECT-TYPE
	SYNTAX INTEGER
	ACCESS read-only
	STATUS mandatory
	DESCRIPTION
		"Also known as K Mem HP Pool, HP Heap, HP VM, and Virtual Memory, this 
                client holds downloaded fonts, and forms.

		Inefficiently coded PCL and XL jobs can consume an extremely large 
		amount of virtual memory or leave objects in the HP Heap after the 
                print jobs are completed, leading to virtual memory errors. If 
		not enough memory is allocated to the HP Heap, the job cannot print. 

		Increasing the memory allocated to this client allows more complex 
		jobs to print and increases the number of fonts that can be down-
		loaded to virtual memory. 

		However, this client should be increased only if you receive a virtual 
		memory error when attempting to print a job or download a font, and 
		even then it should be increased only in small increments until the 
		error message goes away. Excess memory in the HP Heap is not used.

		Size is returned in Kilobytes."

	::= { qmsMemory 14 }

------------------------------------------------------------------------------
-- QMS I/O Pages (Front End) Option Handles
------------------------------------------------------------------------------

qmsFEDoStartPage OBJECT-TYPE
	SYNTAX     INTEGER {
		yes(2),
		no(1)
	}
	ACCESS read-write
	STATUS mandatory
	DESCRIPTION
		"By default, the printer prints a start-up page when you turn it on.
                The start-up page lists basic information about the printer, such as
                its name, the PostScript version, and various printer settings. However,
                you can turn the start-up page off to conserve paper and toner.

		Choices
                    Yes: Print a start-up page each time the printer is 
                         turned on.

                    No: Don't print a start-up page each time the printer is 
                        turned on.

                Default
                    Yes"
	::= { qmsIoPages 5 }

qmsFEHeaderPage OBJECT-TYPE
	SYNTAX INTEGER {
		on(2),
		off(1)
	}
	ACCESS read-write
	STATUS mandatory
	DESCRIPTION
		"A header page is a separator page that prints before a print job
                to help users sort their jobs. The information on the header page
                can be customized. See the Document Option Commands manual
                for more information.

                Choices
                    On: Print a header page before each job.

                    Off: Don't print a header page before each job.

                Default
                    Off"
	::= { qmsIoPages 8 }

qmsFEHeaderInputbin OBJECT-TYPE
	SYNTAX INTEGER
	ACCESS read-write
	STATUS mandatory
	DESCRIPTION
		"You can select the input bin (tray or cassette) from which
                the printer pulls media when printing the header page.

		Choices
                    Printer specific; see your printer documentation.

                Notes
                    If you used the Administration/Engine/Inputbin x Name 
                    options to change the names of the input bins, these 
                    names replace Upper, Lower, and Multipurpose in the 
                    message window."
	::= { qmsIoPages 9 }

qmsFETrailerPage OBJECT-TYPE
	SYNTAX INTEGER {
		off(1),
		on(4),
		errorOnly(3),
		onError(5)
	}
	ACCESS read-write
	STATUS mandatory
	DESCRIPTION
		"A trailer page is a separator page that prints after a print
                job to help users sort out their jobs and, if requested, identify
                print job errors.

                Choices
                    Off: Don't print a trailer/error page for each print job.

                    On: Print a trailer/error page for each print job.

                    On Error: If any print job errors exist, print a trailer page that 
                               lists the errors as well as other trailer page information.

                    Errors Only: If any print job errors exist, print a trailer page
                                 that lists the errors but omits other trailer page information.

                Default
                    Off

                Notes
                    See the Document Option Commands 
                    manual for more information."
	::= { qmsIoPages 10 }

qmsFETrailerInputbin OBJECT-TYPE
	SYNTAX INTEGER
	ACCESS read-write
	STATUS mandatory
	DESCRIPTION
		"You can select the input bin (tray or cassette) from which
                the printer pulls media when printing the trailer page.

		Choices
                    Printer specific; see your printer documentation.

               Notes
                   If you used the Administration/Engine/Inputbin x Name 
                   options to change the names of the inputbins, these 
                   names replace Multipurpose in the message window."
	::= { qmsIoPages 11 }

qmsFEDoSysStart OBJECT-TYPE
	SYNTAX INTEGER {
		yes(2),
		no(1)
	}
	ACCESS read-write
	STATUS mandatory
	DESCRIPTION
		"If you have a hard disk and Do Sys Start is enabled, when
                the printer is turned on, the controller checks the hard
                disk for a PostScript file named SYS\START and executes this
                file. 

                Choices
                    Yes: Check the hard disk for and execute the 
                         SYS\START file when the printer is turned on.

                    No: Don't check the hard disk for a SYS/START file.

                Default
                    Yes

                Notes
                    This file does not print. Information on creating a 
                    SYS\START file is available in the Technical 
                    Reference Manual (shipped on disk with your printer) 
                    and also via Q-FAX (see appendix A, 'Minolta-QMS 
                    Customer Support,' for information on using Q-FAX)."
	::= { qmsIoPages 12 }

qmsFEStatusPageType OBJECT-TYPE
	SYNTAX INTEGER {
		advanced(2),
		standard(1)

	}
	ACCESS read-write
	STATUS mandatory
	DESCRIPTION
		"Status pages list printer hardware and software information.
                Two types of status pages are available.

                Choices
                    Standard: Lists printer identification information, paper 
                              source, current memory configuration, timeouts, 
                              communication settings, input buffer sizes, and all 
                              options.

                    Advanced: Contains the same information as the 
                              standard status page as well as configuration menu 
                              settings, fonts, and downloaded emulations.

                Default
                    Standard"
	::= { qmsIoPages 15 }

------------------------------------------------------------------------------
-- QMS I/O Control (Front End)  Option Handles
------------------------------------------------------------------------------

qmsFEEspEmul OBJECT-TYPE
	SYNTAX INTEGER {
		postscript(1),
		hpgl(5),
		hppcl(6),
		ln03(13),
		quic2(15),
		ccitt(19),
		lineprinter(20),
		tiff(22),
		cals(23),
		cgm(25)
	}
	ACCESS read-write
	STATUS mandatory
	DESCRIPTION
		"The ESP Default Emulation sets the ESP default emulation
                used when ESP is unable to identify the language of a
                print job. This allows the system administrator to select
                alternate default emulations.

                Default Choices
                    HPGL, Lineprinter, PCL5e, PostScript

                Default
                    PCL5e

               Note: Only the default and installed emulations
                     will be available to select from."
	::= { qmsIoCtl 7 }

qmsFECopies OBJECT-TYPE
    SYNTAX INTEGER (1..999)
    ACCESS read-write
    STATUS mandatory
    DESCRIPTION
        "While it is preferable to use your application to select
        the number of copies to print, you can change the default
        number of copies for all print jobs through the printer
        control panel.

        Choices
            1-999

        Default
            1

        Notes
            Sets the default number of copies for all subsequent 
            print jobs. When power is turned off and then back on 
            again, the number of copies is restored to the default 
            setting of 001."
    ::= { qmsIoCtl 17 }

------------------------------------------------------------------------------
-- QMS Front End Timeouts Option Handles
------------------------------------------------------------------------------

qmsFETmPSWait OBJECT-TYPE
	SYNTAX     INTEGER (0..99999)
	ACCESS read-write
	STATUS mandatory
	DESCRIPTION
		"The PostScript emulation timeout is the maximum number of seconds 
		the PostScript emulation waits for incoming data.

		Choices
			0-99999

		Default
			30 (30 sec.)

		Notes
			A value of 0 is the same as infinity (no timeout).

		The job is closed and the next job in the queue begins 
		if all of the following occur:

			* No additional data is received during the 
			  specified period of time.

			* The interface didn't time out.

			* An EOD (end-of-document commands) 
			  was not seen.

		When a print job is sent from a Macintosh, the PS 
		Wait timeout is automatically changed to 300 (5 
		min.).

		Large print jobs, such as those generated by graphics 
		or computer-aided design applications, require 
		timeouts of 00300 (5 min.)."
	::= { qmsIoTimeOuts 1 }

qmsFETmJob OBJECT-TYPE
	SYNTAX     INTEGER (0..99999)
	ACCESS read-write
	STATUS mandatory
	DESCRIPTION
		"The print job timeout is the maximum number of seconds the printer 
		processes a print job before it ends the job.

		Choices
			0-99999

		Default
			0 (infinity, no timeout)

		Notes
			A value of 0 is the same as infinity (no timeout)."
	::= { qmsIoTimeOuts 2 }

qmsFETmNonPSEmul OBJECT-TYPE
	SYNTAX     INTEGER (0..99999)
	ACCESS read-write
	STATUS mandatory
	DESCRIPTION
		"The emulation timeout is the maximum number of seconds emula-
		tions other than PostScript (such as HP-GL, HP PCL5e, and Line-
		printer) wait for incoming data.

		Choices
			0-99999

		Default
			5 (5 sec.)

		Notes
			A value of 000 is the same as infinity (no timeout)."
	::= { qmsIoTimeOuts 3 }	

qmsFETmEsp OBJECT-TYPE
	SYNTAX     INTEGER (0..99999)
	ACCESS read-write
	STATUS mandatory
	DESCRIPTION
		"The ESP timeout is the maximum number of seconds the printer waits 
		to match an emulation before printing the job in the default emulation.

		Choices
			0-99999

		Default
			3 (3 sec.)

		Notes
			A value of 00000 is the same as infinity (no timeout)."
	::= { qmsIoTimeOuts 4 }

------------------------------------------------------------------------------
-- QMS HTTP Option Handles
------------------------------------------------------------------------------

qmsHTTPContact OBJECT-TYPE
	SYNTAX DisplayString (SIZE(0..128))
	ACCESS read-write
	STATUS mandatory
	DESCRIPTION
		"Text string that contains the contact person for the printer."
	::= { qmsHTTP 1 }

qmsHTTPHelpURL OBJECT-TYPE
	SYNTAX DisplayString (SIZE(0..128))
	ACCESS read-write
	STATUS mandatory
	DESCRIPTION
		"Text string for the URL of the online help page."
	::= { qmsHTTP 2 }

qmsHTTPContactNumber OBJECT-TYPE
	SYNTAX DisplayString (SIZE(0..128))
	ACCESS read-write
	STATUS mandatory
	DESCRIPTION
		"Text string of the phone number of the contact person."
	::= { qmsHTTP 3 }

qmsHTTPCorpURL OBJECT-TYPE
	SYNTAX DisplayString (SIZE(0..128))
	ACCESS read-write
	STATUS mandatory
	DESCRIPTION
		"Text string for URL of the Minolta-QMS Corporate home page."
	::= { qmsHTTP 4 }

qmsHTTPSuppliesNumber OBJECT-TYPE
	SYNTAX DisplayString (SIZE(0..128))
	ACCESS read-write
	STATUS mandatory
	DESCRIPTION
		"Text string for phone number of the Supplies and Accessories contact."
	::= { qmsHTTP 5 }

------------------------------------------------------------------------------
-- QMS Serial Option Handles
------------------------------------------------------------------------------

qmsSerBufferSize OBJECT-TYPE
	SYNTAX INTEGER
	ACCESS read-only
	STATUS mandatory
	DESCRIPTION
		"Sets the minimum number of kilobytes of system memory
		allocated to the serial interface.

		Default
			15

		Notes
			This value must be less than K Mem For Spool.

			A 0 value does not turn off the spooling buffer for 
			the serial interface. If the value is set to 0, the 
			printer calculates the Min K Spool automatically at 
			initialization.

			The printer must be restarted for changes to the Min K 
			Spool menu to take effect. You can either let the printer 
			restart automatically after you save the change and exit 
			the Configuration menu, or you can wait for the change 
			to take effect the next time you manually turn on the 
			printer."
	::= { qmsSerial 104 }

qmsSerSpoolTimeout OBJECT-TYPE
	SYNTAX INTEGER (0..99999)
	ACCESS read-write
	STATUS mandatory
	DESCRIPTION
		"Sets the number of seconds the interface waits for data 
		from the host before terminating a spooled print job.

		Choices
			0-99999

		Default
			30"
	::= { qmsSerial 112 }

qmsSerMode OBJECT-TYPE
	SYNTAX INTEGER {
		disabled(1),
		interactive(3),
		noninteractive(4)
	}
	ACCESS read-write
	STATUS mandatory
	DESCRIPTION
		"Enables or disables the serial port.
		Choices
			Interactive: Establish two-way communication between
			             the host and the printer.

			Noninteractive: Establish one-way communication
			                from the host to the printer.

			Disabled: Turn off serial communication with the host.
			          The printer stops accepting print jobs over the
			          serial interface.

		Default
			Disabled

		Notes
			The printer must be restarted for changes to the Mode
			menu to take effect. You can either let the printer restart
			automatically after you save the change and exit the
			Configuration menu, or you can wait for the change to
			take effect the next time you manually turn on the
			printer."
	::= { qmsSerial 101 }

qmsSerEmulation OBJECT-TYPE
	SYNTAX INTEGER {
		postscript(1),		-- actual value should be 0 (zero).
		hpgl(5),
		hppcl(6),
		hexdump(7),
		ln03(13),
		quic2(15),
		ccitt(19),
		lineprinter(20),
		tiff(22),
		cals(23),
		cgm(25),
		esp(201)
	}
	ACCESS read-write
	STATUS mandatory
	DESCRIPTION
		"Sets the serial interface emulation.

		Choices
			PostScript, HPGL, HPPCL, HEXDUMP, LN03, QUIC2
			CCITT, Line Printer, TIFF, CALS, CGM, ESP

		Default
			ESP

        Note: Only the installed emulations will be available to select
              from."
	::= { qmsSerial 102 }

qmsSerEndDocumentMode OBJECT-TYPE
	SYNTAX INTEGER {
		none(1),
		qmseod(2),
		hpeod(3)
	}
	ACCESS read-write
	STATUS mandatory
	DESCRIPTION
		"Enables (and identifies an end-of-job sequence) or 
		disables data stream sensing for the end-of-document
		(EOD) command.

		Choices
			None-The printer recognizes only the PostScript ^D 
			command.

			DOC EOD-The printer recognizes only the 
			Minolta-QMS %%EndOfDocument command.

			HP EOD-The printer recognizes only the HP 
			<ESC>%12345X command.

		Default
			None"
	::= { qmsSerial 111 }

qmsSerPriority OBJECT-TYPE
	SYNTAX INTEGER (1..100)
	ACCESS read-write
	STATUS mandatory
	DESCRIPTION
		"Allows you to specify which jobs are printed first, according to the 
		interface through which they are received, when jobs are received 
		simultaneously. For example, you can give jobs received via the serial 
		interface priority over jobs received via the parallel and Ethernet inter-
		faces.

		Choices
			001-100 (lowest-highest priority)

		Default
			001 (lowest priority)"
	::= { qmsSerial 103 }

qmsSerPSProtocol OBJECT-TYPE
	SYNTAX INTEGER {
		normal(1),
		normalfixed(2),
		binary(3),
		binaryfixed(4)
	}
	ACCESS read-write
	STATUS mandatory
	DESCRIPTION
		"Sets the binary communications protocol (BCP) for 
		communicating over a serial interface to a PostScript
		printer.

		Choices
			Normal: Enables standard, ASCII (7-bit) hex protocol. 
			        Data is sent and received in ASCII format. This mode is 
			        recommended if you do not print binary data. It was 
			        designed for data in the printable ASCII range. Print 
			        jobs can change this setting through PostScript 
			        operators.

			Normal Fixed: Enables standard, ASCII (7-bit) hex 
			              protocol. Print jobs cannot change this setting
			              through PostScript operators.

			Binary: Enables binary communications protocol 
			        (BCP). Print jobs can change this setting through 
			        PostScript operators. Data in the printable ASCII range 
			        also prints. 

			Binary Fixed: Enables binary fixed communications 
			              protocol (BCP). Print jobs cannot alter change this 
			              setting through PostScript operators. Data in the 
			              printable ASCII range also prints.

			Default
				Normal"
	::= { qmsSerial 100 }

qmsSerBaudRate OBJECT-TYPE
	SYNTAX INTEGER{
		bps38400(38401),
		bps19200(19201),
		bps9600(9601),
		bps4800(4801),
		bps2400(2401),
		bps1200(1201),
		bps600(601),
		bps300(301)
	}
	ACCESS read-write
	STATUS mandatory
	DESCRIPTION
		"Sets the rate data is transmitted (bits per second) over 
		the serial interface.

		Choices
			300, 600, 1200, 2400, 4800, 9600, 19200, 38400

		Default
			9600

		Notes
			Baud rates of 19200 and 38400 require hardware flow 
			control."
	::= { qmsSerial 201 }

qmsSerHwDSRPOL OBJECT-TYPE
	SYNTAX INTEGER {
		reverse(1),
		normal(2)
	}
	ACCESS read-write
	STATUS mandatory
	DESCRIPTION
		"Controls the flow of data between the printer and the host.

		Choices
			Reverse, Normal
	
		Default
			Normal

		Notes
			If the host uses hardware flow control, set this option to 
			match the type used by the host.

			However, to download printer system software to flash 
			ROM via the serial port, RTS and CTS must be set to 
			On, and the cable pinouts must be connected as shown 
			in the printer documentation."
	::= { qmsSerial 213 }

qmsSerHwDSR OBJECT-TYPE
	SYNTAX INTEGER {
		off(1),
		on(2)
	}
	ACCESS read-write
	STATUS mandatory
	DESCRIPTION
		"Controls the flow of data between the printer and the host.

		Choices
			Off, On

		Default
			Off

		Notes
			If the host uses hardware flow control, set this option to 
			match the type used by the host.

			However, to download printer system software to flash 
			ROM via the serial port, RTS and CTS must be set to 
			On, and the cable pinouts must be connected as shown 
			in the printer documentation."
	::= { qmsSerial 212 }

qmsSerHwDTRPOL OBJECT-TYPE
	SYNTAX INTEGER {
		reverse(1),
		normal(2)
	}
	ACCESS read-write
	STATUS mandatory
	DESCRIPTION
		"Controls the flow of data between the printer and the host.

		Choices
			Reverse, Normal

		Default
			Normal

		Notes
			If the host uses hardware flow control, set this option to 
			match the type used by the host.

			However, to download printer system software to flash 
			ROM via the serial port, RTS and CTS must be set to 
			On, and the cable pinouts must be connected as shown 
			in the printer documentation."
	::= { qmsSerial 211 }

qmsSerHwDTR OBJECT-TYPE
	SYNTAX INTEGER {
		off(1),
		on(2)
	}
	ACCESS read-write
	STATUS mandatory
	DESCRIPTION
		"Controls the flow of data between the printer and the host.

		Choices
			Off, On

		Default
			On

		Notes
			If the host uses hardware flow control, set this option to 
			match the type used by the host.

			However, to download printer system software to flash 
			ROM via the serial port, RTS and CTS must be set to 
			On, and the cable pinouts must be connected as shown 
			in the printer documentation."
	::= { qmsSerial 210 }

qmsSerHwRTS OBJECT-TYPE
	SYNTAX INTEGER {
		off(1),
		on(2)
	}
	ACCESS read-write
	STATUS mandatory
	DESCRIPTION
		"Controls the flow of data between the printer and the host.

		Choices
			Off, On

		Default
			Off

		Notes
			If the host uses hardware flow control, set this option to 
			match the type used by the host.

			However, to download printer system software to flash 
			ROM via the serial port, RTS and CTS must be set to 
			On, and the cable pinouts must be connected as shown 
			in the printer documentation."
	::= { qmsSerial 209 }

qmsSerHwCTS OBJECT-TYPE
	SYNTAX INTEGER{
		off(1),
		on(2)
	}
	ACCESS read-write
	STATUS mandatory
	DESCRIPTION
		"Controls the flow of data between the printer and the host.

		Choices
			Off, On

		Default
			Off

		Notes
			If the host uses hardware flow control, set this option to 
			match the type used by the host.

			However, to download printer system software to flash 
			ROM via the serial port, RTS and CTS must be set to 
			On, and the cable pinouts must be connected as shown 
			in the printer documentation."
	::= { qmsSerial 208 }

qmsSerStopBits OBJECT-TYPE
	SYNTAX INTEGER {
		onebit(1),
		twobits(2),
                oneandhalf(3)
	}
	ACCESS read-write
	STATUS mandatory
	DESCRIPTION
		"Sets the number of stop bits transmitted per character.

		Choices
			1 Bit, 2 Bits, 1 1/2 Bits

		Default
			One Bit"
	::= { qmsSerial 207 }

qmsSerDataBits OBJECT-TYPE
	SYNTAX INTEGER {
		bits8(1),
		bits7(2),
                bits6(3),
                bits5(4)
	}
	ACCESS read-write
	STATUS mandatory
	DESCRIPTION
		"Sets the number of data bits transmitted per character. 

		Choices
			5 Bits, 6 Bits, 7 Bits, 8 Bits

		Default
			8 Bits"
	::= { qmsSerial 206 }

qmsSerTxSWFlow OBJECT-TYPE
	SYNTAX INTEGER {
		none(1),
		xonxoff(2),
		etxack(3)
	}
	ACCESS read-write
	STATUS mandatory
	DESCRIPTION
		"Sets the software communication protocol used by the
		host computer to control communication with the printer.

		Choices
			ETX/ACK, None, XON/XOFF

		Default
			None"
	::= { qmsSerial 205 }

qmsSerRxSWFlow OBJECT-TYPE
	SYNTAX INTEGER {
		none(1),
		xonxoff(2),
		etxack(3),
		robustxonxoff(4)
	}
	ACCESS read-write
	STATUS mandatory
	DESCRIPTION
		"Sets the software communication protocol used by the 
		printer to control communication from the host computer. 

		Choices
			ETX/ACK, Robust XON/XOFF, None, XON/XOFF

		Default
			XON/XOFF"
	::= { qmsSerial 204 }

qmsSerIgnoreParity OBJECT-TYPE
	SYNTAX INTEGER{
		off(1),
		on(2)
	}
	ACCESS read-write
	STATUS mandatory
	DESCRIPTION
		"Specifies how the printer should handle parity errors.

		Choices
			Off: Ignore parity errors. The printer prints its best 
			     interpretation of the character(s) affected by the error.

			On: Don't ignore parity errors. The printer replaces the 
			    character(s) affected by the error with a question mark.

		Default
			Off

		Notes
			Use the qmsCOM0Parity to set parity."
	::= { qmsSerial 203 }

qmsSerParity OBJECT-TYPE
	SYNTAX INTEGER{
		none(1),
		odd(4),
		even(5)
	}
	ACCESS read-write
	STATUS mandatory
	DESCRIPTION
		"Sets the check bit used to identify data transmission errors. 

		Choices:
			None, Odd, Even

		Default:
			None

		Note:
			The printer's parity setting must match that of the host 
			or application.

			Use the qmsSerIgnoreParity to specify how the printer
			handles parity errors."
	::= { qmsSerial 202 }

------------------------------------------------------------------------------
-- QMS Parallel Option Handles
------------------------------------------------------------------------------

qmsParBufferSize OBJECT-TYPE
	SYNTAX INTEGER
	ACCESS read-only
	STATUS mandatory
	DESCRIPTION
		"Sets the minimum number of kilobytes of system memory
		allocated to the parallel interface.

		Default
			15

		Notes
			This value must be less than K Mem for Spool in the 
			Administration/Memory submenu.

			A 0 value does not turn off the spooling buffer for 
			the parallel interface. If the value is set to 0, the 
			printer calculates the Min K Spool automatically at 
			initialization.

			The printer must be restarted for changes to the Min K 
			Spool menu to take effect. You can either let the printer 
			restart automatically after you save the change and exit 
			the configuration menu, or you can wait for the change 
			to take effect the next time you manually turn on the 
			printer."
	::= { qmsParallel 104}

qmsParSpoolTimeout OBJECT-TYPE
	SYNTAX     INTEGER (0..99999)
	ACCESS read-write
	STATUS mandatory
	DESCRIPTION
		"Sets the number of seconds the interface waits for data 
		from the host before terminating a spooled print job.

		Choices
			0-99999

		Default
			30"
	::= { qmsParallel 111 }

qmsParMode OBJECT-TYPE
	SYNTAX INTEGER {
		interactive(3),
		noninteractive(4),
		disabled(1)
	}
	ACCESS read-write
	STATUS mandatory
	DESCRIPTION
		"The parallel interface supports Centronics parallel
		communication as well as IEEE 1284 bidirectional parallel
		communication.

		Choices
			Interactive-Establish two-way communication between 
			the host and the printer.


			Noninteractive-Establish one-way communication 
			from the host to the printer.

			Disabled-Turn off parallel communication with the 
			host. The printer stops accepting print jobs over the 
			parallel interface.

		Default
			Noninteractive

		Notes
			The printer must be restarted for changes to the menu 
			to take effect. You can either let the printer restart 
			automatically after you save the change and exit from 
			the Configuration menu, or you can wait for the change 
			to take effect the next time you manually turn on the 
			printer."
	::= { qmsParallel 101 }

qmsParEmulation OBJECT-TYPE
	SYNTAX INTEGER {
		postscript(1),
		hpgl(5),
		hppcl(6),
		hexdump(7),
		ln03(13),
		quic2(15),
		ccitt(19),
		lineprinter(20),
		tiff(22),
		cals(23),
		cgm(25),
		esp(201)
	}
	ACCESS read-write
	STATUS mandatory
	DESCRIPTION
		"Sets the parallel interface emulation.
		Choices
			PostScript, HPGL, HPPCL, HEXDUMP, LN03, QUIC2
			CCITT, Line Printer, TIFF, CALS, CGM, ESP

		Default
			ESP

        Note: Only the installed emulations will be available to select
	      from."
	::= { qmsParallel 102 }

qmsParDataBits OBJECT-TYPE
	SYNTAX INTEGER {
		bits8(1),
		bits7(2)
	}
	ACCESS read-write
	STATUS mandatory
	DESCRIPTION
		"Sets the number of data bits transmitted per character.

		Choices
			7 Bits, 8 Bits

		Default
			8 Bits"
	::= { qmsParallel 113 }

qmsParEndDocumentMode OBJECT-TYPE
	SYNTAX INTEGER {
		none(1),
		qmseod(2),
		hpeod(3)
	}
	ACCESS read-write
	STATUS mandatory
	DESCRIPTION
		"Enables (and identifies an end-of-job sequence) or disables
		data stream sensing for the end-of-document (EOD) command. 

		Choices
			None: The printer recognizes only the PostScript ^D 
			      command.

			DOC EOD: The printer recognizes only the Minolta-QMS 
			         %%EndOfDocument command.

			HP EOD: The printer recognizes only the HP 
			        <ESC>%12345X command.

		Default
			None"
	::= { qmsParallel 112 }

qmsParPriority OBJECT-TYPE
	SYNTAX	INTEGER (1..100)
	ACCESS read-write
	STATUS mandatory
	DESCRIPTION
		"Allows you to specify which jobs are printed first, 
		according to the interface through which they are received,
		when jobs are received simultaneously. 

		Choices
			1-100 (lowest-highest priority)

		Default
			1 (lowest priority)

		Notes
			For example, you can give jobs received via the parallel 
			interface priority over jobs received via the Ethernet 
			interface."
	::= { qmsParallel 103 }

qmsParPSProtocol OBJECT-TYPE
	SYNTAX INTEGER {
		normal(1),
		normalfixed(2),
		binary(3),
		binaryfixed(4)
	}
	ACCESS read-write
	STATUS mandatory
	DESCRIPTION
		"Sets the binary communications protocol (BCP) for
		communicating over a parallel interface to a PostScript
		printer.

		Choices
			Normal: Enables standard, ASCII (7-bit) hex protocol. 
			        Data is sent and received in ASCII format. This mode is 
			        recommended if you do not print binary data. It was 
			        designed for data in the printable ASCII range. Print 
			        jobs can change this setting through PostScript 
			        operators.

			Normal Fixed: Enables standard, ASCII (7-bit) hex 
			              protocol. Print jobs cannot change this setting through 
			              PostScript operators.

			Binary: Enables quoted binary communications 
			        protocol (BCP). Print jobs can change this setting 
			        through PostScript operators. Data in the printable 
			        ASCII range also prints. 

			Binary Fixed: Enables binary communications protocol 
			              (BCP). Print jobs cannot alter change this setting 
			              through PostScript operators. Data in the printable 
			              ASCII range also prints.

		Default
			Normal"
	::= { qmsParallel 100 }

------------------------------------------------------------------------------
-- QMS Engine Option Handles
------------------------------------------------------------------------------

qmsENGTopOffset OBJECT-TYPE
	SYNTAX INTEGER (0..300)
	ACCESS  read-write
	STATUS mandatory
	DESCRIPTION
		"This option allows you to adjust the vertical placement of printed images.

		To check image alignment, print a standard status page (Print Status 
		key). When the printer is placing images properly, the alignment angle 
		bar in the lower-left corner of the status page is 0.5''/12.7 mm from 
		the left and bottom edges of the page. If the angle bar is off, use the 
		Administration/Engine/Image Alignment option to align the image vertically
		in pixel increments (1/300'' or 0.08 mm). 

		Note: Engine constraints may limit the accuracy of pixel alignment.

		Choices
			000-300 (0.00''-1.00'')

		Default
			100 (0.33''/.84 mm)

		Notes
			Values above 100 move the image right.
			Values below 100 move the image left."
	::= { qmsEngine 1 }

qmsENGLeftOffset OBJECT-TYPE
	SYNTAX INTEGER (0..300)
	ACCESS  read-write
	STATUS mandatory
	DESCRIPTION
		"This option allows you to adjust the horizontal placement of
		printed images.

		To check image alignment, print a standard status page (Print Status 
		key). When the printer is placing images properly, the alignment angle 
		bar in the lower-left corner of the status page is 0.5''/12.7 mm from 
		the left and bottom edges of the page. If the angle bar is off, use the 
		Administration/Engine/Image Alignment option to align the image hor-
		izontally in pixel increments (1/300'' or 0.08 mm). 

		Note: Engine constraints may limit the accuracy of pixel alignment.

		Choices
			000-300 (0.00''/0 mm-1.00''/25.4 mm)

		Default
			100 (0.33''/.84 mm)

		Notes
			Values above 100 move the image to the right.
			Values below 100 move the image to the left."
	::= { qmsEngine 2 }

qmsENGTopOffsetDuplex OBJECT-TYPE
	SYNTAX INTEGER (0..300)
	ACCESS  read-write
	STATUS mandatory
	DESCRIPTION
		"This option allows you to adjust the duplex vertical placement of printed images.

		To check image alignment, print a standard status page (Print Status 
		key). When the printer is placing images properly, the alignment angle 
		bar in the lower-left corner of the status page is 0.5''/12.7 mm from 
		the left and bottom edges of the page. If the angle bar is off, use the 
		Administration/Engine/Image Alignment option to align the image vertically
		in pixel increments (1/300'' or 0.08 mm). 

		Note: Engine constraints may limit the accuracy of pixel alignment.

		Choices
			000-300 (0.00''-1.00'')

		Default
			100 (0.33''/.84 mm)

		Notes
			Values above 100 move the image down.
			Values below 100 move the image up."
	::= { qmsEngine 4 }

qmsENGLeftOffsetDuplex OBJECT-TYPE
	SYNTAX INTEGER (0..300)
	ACCESS  read-write
	STATUS mandatory
	DESCRIPTION
		"This option allows you to adjust the duplex horizontal placement of
		printed images.

		To check image alignment, print a standard status page (Print Status 
		key). When the printer is placing images properly, the alignment angle 
		bar in the lower-left corner of the status page is 0.5''/12.7 mm from 
		the left and bottom edges of the page. If the angle bar is off, use the 
		Administration/Engine/Image Alignment option to align the image hor-
		izontally in pixel increments (1/300'' or 0.08 mm). 

		Note: Engine constraints may limit the accuracy of pixel alignment.

		Choices
			000-300 (0.00''/0 mm-1.00''/25.4 mm)

		Default
			100 (0.33''/.84 mm)

		Notes
			Values above 100 move the image to the right.
			Values below 100 move the image to the left."
	::= { qmsEngine 6 }

qmsENGResolution OBJECT-TYPE
	SYNTAX INTEGER {
		dpi300(301),
		dpi600(601),
		dpi1200(1201),
		dpi2401(2401)
	}
	ACCESS  read-write
	STATUS mandatory
	DESCRIPTION
		"This option sets the print engine's default resolution.

		Choices
			300 dpi-300x300 dpi resolution
			600 dpi-600x600 dpi resolution
			1200 dpi-1200x1200 dpi resolution
			2400 dpi-2400x600 dpi resolution

		Default
			600 dpi

                Note: The 1200x1200 dpi resolution option is 
                      available only when the optional 1200x1200 dpi 
                      daughterboard is installed. See your Minolta-QMS 
                      product supplier for availability of this option.

                      If your printer is configured for duplex printing and has 
                      less than 16 MB RAM, 600x600 dpi isn't available on all 
                      media sizes. Duplexing using 600x600 or 1200x1200 
                      resolution requires additional memory. 

                      The 1200 dpi option will not show up in this menu until 
                      the multires board is installed and the frame buffer has 
                      sufficient memory to support 1200 dpi. Restoring 
                      defaults or selecting Quick Config should re-configure 
                      the frame buffer memory client

                      The 2400 dpi option is specific to certain products only.
                      We do not need multi-res board. Currently only 2400x600
                      is supported. Duplexing needs additional memory."

	::= { qmsEngine 8 }

qmsENGDefaultPaper OBJECT-TYPE
	SYNTAX INTEGER {
		letter(1),
		a4(2)
	}
	ACCESS  read-write
	STATUS mandatory
	DESCRIPTION
		"Default Paper is used when the default media is requested but the 
		default input bin is missing from the engine. There's no way to sense 		
		the media size automatically. This only applies to system that can have
		all input bin removed.

		Choices
			Letter, A4

		Default
			Letter"
	::= { qmsEngine 11 }

qmsENGDuplex OBJECT-TYPE
	SYNTAX INTEGER {
		off(1),
		longedge(2),
		shortedge(3)
	}
	ACCESS  read-write
	STATUS mandatory
	DESCRIPTION
		"Current duplexing setting on printers for which the feature
                 is supported.
                 
                 Choices
                     Off:           Prints simplex pages.

                     Long Edge:     Duplexes each page of each job so they can
                                    be bound at the long edge of the page.

                     Short Edge:    Duplexes each page so they can be bound at
                                    the short edge of the page.

                     Default:       Off"
	::= { qmsEngine 12 }

qmsENGOrientation OBJECT-TYPE
	SYNTAX INTEGER {
		portrait(1),	
		landscape(2)
	}
	ACCESS  read-write
	STATUS mandatory
	DESCRIPTION
		"While you can usually specify the orientation of a print job in your 
		application, if you consistently use a certain media orientation, you 
		can set this option.

		Choices
			Portrait: Vertical
			Landscape: Horizontal

		Default
			Portrait"
	::= { qmsEngine 14 }

qmsENGInputbin OBJECT-TYPE
	SYNTAX INTEGER
	ACCESS  read-write
	STATUS mandatory
	DESCRIPTION
		"Default inputbin number."
	::= { qmsEngine 15 }

qmsENGOutputbin OBJECT-TYPE
	SYNTAX INTEGER
	ACCESS  read-write
	STATUS mandatory
	DESCRIPTION
		"Default outputbin number."
	::= { qmsEngine 16 }

qmsENGCollation OBJECT-TYPE
	SYNTAX INTEGER {	
		off(1),
		on(2)
	}
	ACCESS  read-write
	STATUS mandatory
	DESCRIPTION
		"Collation is one of your printer's features. It is the printing of sets of 
		multiple copies of a document in numeric order. Your printer is capa-
		ble of delivering multiple copies of your files in collated order to the 
		output tray. The following figure shows the collated and uncollated 
		stacking for two copies of a four-page file.

		The main advantage of collation is convenience and the time savings 
		derived from not having to separate and sort individual copies of a 
		document. Each copy of the document exists as a whole unless 
		chunk collation has occurred.

		Choices
			On: Enable collation.
			Off: Disable collation.

		Default
			Off

		Working with Chunk Collation
			For a multiple copy document with collation On, there must be 
			enough display list memory to hold the display list blocks for
                        all pages in the collation range. See the 'Memory' section in 
			Chapter 5, for more information on the Display List compressed 
			blocks. If there is not enough memory, then a chunk collation 
			boundary is forced after the last compiled page of the collation 
			range."
	::= { qmsEngine 17 }

qmsENGErrorRecovery OBJECT-TYPE
	SYNTAX INTEGER {
		on(2),
		off(1)
	}
	ACCESS  read-write
	STATUS mandatory
	DESCRIPTION
		"When a media jam or other similar error occurs, the printer can reprint 
		the job starting from the page on which the jam occurred.

		Choices
			On: Reprints a print job from the page on which the jam 
			    or error occurred.

			Off: Don't reprint a print job when a jam or error occurs.
			     
		Default
			Off"
	::= { qmsEngine 19 }

qmsENGManualTrayMedia OBJECT-TYPE
	SYNTAX INTEGER {
			letter(1),
			legal(2),
			executive(3),
			sz11x17(4),
			a3(5),
			a4(6),
			a5(7),
			b4(8),
			b5(9),
			statement(10),
			universal(11),
			com10(12),
			dl(13),
			monarch(14),
			c5(15),
			envelope(16)
	}
	ACCESS  read-write
	STATUS mandatory
	DESCRIPTION
		"Need description and values."
	::= { qmsEngine 20 }

qmsENGToneroutAction OBJECT-TYPE
	SYNTAX INTEGER {
		stop(1),
		continue(2)
	}
	ACCESS  read-write
	STATUS mandatory
	DESCRIPTION
		"You can configure the printer to stop or to continue printing when a 
		TONER LOW ACT. error message is displayed in the message window.

		Choices
			Continue: Continue printing when a TONER LOW ACT 
			          message displays.

			Stop: Stop printing when a TONER LOW ACT 
			      message displays.

		Default
			Continue"
	::= { qmsEngine 21 }

qmsENGLetterheadMode OBJECT-TYPE
	SYNTAX INTEGER {
		off(1),
		duplexPath(2),
		rotateSimplex(3)
	}
	ACCESS  read-write
	STATUS mandatory
	DESCRIPTION
		"This option appears only if the duplexing unit is installed 
                on the printer. The letterhead option allows you to print both
                simplex and duplex jobs on letterhead paper from the same input
                bin (cassette) without having to sort the pages manually.

		Choices
			Off

			DuplexPath
				Rotate the simplex images to match the output
				produced for duplex jobs. You may notice a decrease
				in the printing speed depending on the mix of simplex
				and duplex pages.

			RotateSimplex
				When Rotate Simplex is enabled it rotates the simplex
				impage 180 degrees from normal. This option allows the
				user to insert 3-hole punched paper backwards permitting
				it to print. If installed the opposite way the engine
				sensors cause a error thinking the paper is shorter than
				full size.

		Default
			Off

		Notes
			Letterhead paper must be loaded face down in the input 
                        bin with the bottom edge inserted first into the printer. 
                        You may notice a decrease in the printing speed depending
                        on the mix of simplex and duplex pages. See printer manual
                        for loading 3-hole or letterhead paper."
	::= { qmsEngine 23 }

qmsENGManualFeedTimeout OBJECT-TYPE
	SYNTAX INTEGER (0..300)
	ACCESS  read-write
	STATUS mandatory
	DESCRIPTION
		"This option allows you to set the amount of time the printer waits for 
		paper to be inserted into the multipurpose tray before it cancels the 
		job.

		Choices
			0 - 300 seconds

		Default
			60 seconds

		Notes
			A value of 0 sets the timeout to infinity."
	::= { qmsEngine 24 }

qmsENGOffsetStacking OBJECT-TYPE
	SYNTAX INTEGER {
		off(1),
		on(2)
	}
	ACCESS  read-write
	STATUS mandatory
	DESCRIPTION
		"This option appears only if the printer is capable of offset
                stacking.

		Choices: Off - Stacking of each output set is aligned with the
                               previous set.
                         On  - Stacking of each output set is offset from the
                               previous set.
		Default: Off"

	::= { qmsEngine 26 }

qmsENGEnergyStar OBJECT-TYPE
	SYNTAX INTEGER {
        	off(1),
		min15(16),
		min30(31),
		hour1(61),
		hour2(121),
		hour3(181)
	}
	ACCESS  read-write
	STATUS mandatory
	DESCRIPTION
		"The Energy Saver option specifies whether the printer changes to a 
		low-power state (the engine remains on, but the fuser turns off) after 
		the printer is inactive for a user-defined length of time. When a print 
		job is received, the printer returns to normal power within 90 seconds.

		Choices
			15 minutes, 30 minutes, 
			1 hour, 2 hours, 
			3 hours - Idle time before activation of low-power state.

			Off-Use normal power all of the time.

		Default
			1 hour"
	::= { qmsEngine 27 }

qmsENGPageOrder OBJECT-TYPE
	SYNTAX INTEGER {
		reverse(1),
		normal(2)
	}
	ACCESS  read-write
	STATUS mandatory
	DESCRIPTION
		"Need input on this....is this new?"
	::= { qmsEngine 40 }

qmsENGEnvelopeTrayMedia OBJECT-TYPE
	SYNTAX INTEGER {
		com10(12),
		dl(13),
		monarch(14),
		c5(15),
		envelope(16)
	}
	ACCESS  read-write
	STATUS mandatory
	DESCRIPTION
		"The envelope feeder can be adjusted to accept different envelope 
		sizes. See chapter 7, of the Options manual, the 'Selecting Enve-
		lopes'  section, for more information on envelope sizes.

		Use the Operator Control/Envelope menu to identify and select the 
		size envelope for the envelope feeder (inputbin 4). Your printer sup-
		ports the following media sizes via the multipurpose tray:

		Choices
			C5, Com10, DL
			Envelope, Monarch

		Default
			Envelope"
	::= { qmsEngine 41 }

qmsENGDensity OBJECT-TYPE
	SYNTAX INTEGER
	ACCESS  read-write
	STATUS mandatory
	DESCRIPTION
		"The Toner Density option adjusts the density of the toner that is laid 
		down on the paper.

		Note: 
			See your Minolta-QMS documentation for printer specific values."
	::= { qmsEngine 42 }

qmsENGColorModel OBJECT-TYPE
	SYNTAX INTEGER {
		gray(2),
		cmy(3),
		rgb(4),
		cmyk(5)
	}
	ACCESS  read-only
	STATUS mandatory
	DESCRIPTION
		"Use this option to select between full-color and
		 monochrome printing.

               Choices
                   Gray, CMY, RGB, CMYK"
	::= { qmsEngine 43 }

qmsENGColorSeparation OBJECT-TYPE
	SYNTAX INTEGER {
		on(2),
		off(1)
	}
	ACCESS  read-only
	STATUS mandatory
	DESCRIPTION
		"Use this option to turn color separation on or off.

                Choices
                    On, Off

                Default
                    Off"
	::= { qmsEngine 44 }

qmsENGUnderColor OBJECT-TYPE
	SYNTAX INTEGER {
		on(2),
		off(1)
	}
	ACCESS  read-only
	STATUS mandatory
	DESCRIPTION
		"Need input on this....is this new?"
	::= { qmsEngine 45 }

qmsENGQuality OBJECT-TYPE
	SYNTAX INTEGER {
		normal(1),
		conserveToner(2),
		smooth600dpi(3),
                fineMode(5)
	}
	ACCESS  read-write
	STATUS mandatory
	DESCRIPTION
		"The Print Quality option allows the printer to operate at a lower 
		rate of toner consumption and extend the life of your toner cartridges. 
		This option also allows you to enable other installed quality features.

		Choices
			Normal: Normal toner use.
			Conserve Toner: Toner use is lowered.
			Smooth(600dpi): Requires MultiRes board.
                        Fine Mode: Reduces chassis vibration during image processing.

		Default
			Normal

		Notes
			When Conserve Toner is selected the Toner Density 
			option can be adjusted for the best acceptable print 
			quality. Toner Density can be set from 1 to 15.

			Smoothing alters the size and position of dots that lie 
			on the outer edges of an object by reducing the width of 
			the laser pulse to a fraction of the full pulse width. This 
			smooths jagged-edges in text, lines, and graphics and 
			generally improves their print quality.

                        Fine Mode reduces the media feed rate, allowing each sheet
                        to complete the image transfer process before the next sheet
                        is fed to the media path.  This reduces chassis vibration 
                        that occurs during paper movement to a minimum level during
                        image processing.

		Note: When printing halftones, smoothing is not recommended 
		      because it may introduce artifacts in the halftone or 
		      scanned image.  For better results if smoothing is 
		      required for your documents in text and line art, use 
		      the basic option for halftone types."
	::= { qmsEngine 48 }

qmsENGConsumeNameMulti OBJECT-TYPE
    SYNTAX     SEQUENCE OF QmsENGConsumeNameEntry
    ACCESS not-accessible
    STATUS mandatory
    DESCRIPTION
        "A table of the engine's consumable names."
	::= { qmsEngine 1000 }

QmsENGConsumeNameEntry ::= SEQUENCE {
    qmsENGConsumeName           DisplayString
}

qmsENGConsumeName OBJECT-TYPE
	SYNTAX DisplayString (SIZE(0..80))
	ACCESS read-only
	STATUS mandatory
	DESCRIPTION
		"Consumable name for engine."
	::= { qmsENGConsumeNameMulti 1 }

qmsENGConsumeLevelMulti OBJECT-TYPE
    SYNTAX SEQUENCE OF QmsENGConsumeLevelEntry
    ACCESS not-accessible
    STATUS mandatory
    DESCRIPTION
        "A table of the engine's consumable levels."
	::= { qmsEngine 1001 }

QmsENGConsumeLevelEntry ::= SEQUENCE {
    qmsENGConsumeLevel           INTEGER
}

qmsENGConsumeLevel OBJECT-TYPE
	SYNTAX INTEGER
	ACCESS read-only
	STATUS mandatory
	DESCRIPTION
		"Specific consumable level."
	::= { qmsENGConsumeLevelMulti 1 }

qmsENGConsumeMaxMulti OBJECT-TYPE
    SYNTAX SEQUENCE OF QmsENGConsumeMaxEntry
    ACCESS not-accessible
    STATUS mandatory
    DESCRIPTION
        "A table of the engine's consumable maximum levels."
	::= { qmsEngine 1002 }

QmsENGConsumeMaxEntry ::= SEQUENCE {
    qmsENGConsumeMax           INTEGER
}

qmsENGConsumeMax OBJECT-TYPE
	SYNTAX INTEGER
	ACCESS read-only
	STATUS mandatory
	DESCRIPTION
		"Specific consumable maximum level."
	::= { qmsENGConsumeMaxMulti 1 }

qmsENGConsumeUnitsMulti OBJECT-TYPE
    SYNTAX SEQUENCE OF QmsENGConsumeUnitsEntry
    ACCESS not-accessible
    STATUS mandatory
    DESCRIPTION
        "A table of the engine's consumable units."
	::= { qmsEngine 1003 }

QmsENGConsumeUnitsEntry ::= SEQUENCE {
    qmsENGConsumeUnits           DisplayString
}

qmsENGConsumeUnits OBJECT-TYPE
	SYNTAX DisplayString (SIZE(0..80))
	ACCESS read-only
	STATUS mandatory
	DESCRIPTION
		"Specific consumable unit type."
	::= { qmsENGConsumeUnitsMulti 1 }

qmsENGConsumeTypeMulti OBJECT-TYPE
	SYNTAX SEQUENCE OF QmsENGConsumeTypeEntry
	ACCESS not-accessible
	STATUS mandatory
	DESCRIPTION
        	"A table of the engine's consumable types."
	::= { qmsEngine 1004 }

QmsENGConsumeTypeEntry ::= SEQUENCE {
    qmsENGConsumeType           INTEGER
}

qmsENGConsumeType OBJECT-TYPE
	SYNTAX INTEGER {
		invalid(1),
		inputBin(2),
		outputBin(3),
		toner(4),
		wasteToner(5),
		opc(6),
		fuserUnit(7),
		fuserCRoller(8),
		fuserOil(9),
		pmService(10)
	}
	ACCESS read-only
	STATUS mandatory
	DESCRIPTION
		"Specific consumable type."
	::= { qmsENGConsumeTypeMulti 1 }

qmsENGConsumeNote1Multi OBJECT-TYPE
    SYNTAX SEQUENCE OF QmsENGConsumeNote1Entry
    ACCESS not-accessible
    STATUS mandatory
    DESCRIPTION
        "A table of the first note applicable to each of the
	 engines consumable."
	::= { qmsEngine 1005 }

QmsENGConsumeNote1Entry ::= SEQUENCE {
    qmsENGConsumeNote1           DisplayString
}

qmsENGConsumeNote1 OBJECT-TYPE
	SYNTAX DisplayString (SIZE(0..80))
	ACCESS read-only
	STATUS mandatory
	DESCRIPTION
		"Specific consumable note e.g. the kind of
		 paper in an input tray."
	::= { qmsENGConsumeNote1Multi 1 }

qmsENGConsumeNote2Multi OBJECT-TYPE
    SYNTAX SEQUENCE OF QmsENGConsumeNote2Entry
    ACCESS not-accessible
    STATUS mandatory
    DESCRIPTION
        "A table of the second note applicable to each of the engine's consumables."
	::= { qmsEngine 1006 }

QmsENGConsumeNote2Entry ::= SEQUENCE {
    qmsENGConsumeNote2           DisplayString
}

qmsENGConsumeNote2 OBJECT-TYPE
	SYNTAX DisplayString (SIZE(0..80))
	ACCESS read-only
	STATUS mandatory
	DESCRIPTION
		"Specific consumable note."
	::= { qmsENGConsumeNote2Multi 1 }

qmsENGConsumeIndexMulti OBJECT-TYPE
    SYNTAX SEQUENCE OF QmsENGConsumeIndexEntry
    ACCESS not-accessible
    STATUS mandatory
    DESCRIPTION
        "Index into OID table."
	::= { qmsEngine 1007 }

QmsENGConsumeIndexEntry ::= SEQUENCE {
    qmsENGConsumeIndex           INTEGER
}

qmsENGConsumeIndex OBJECT-TYPE
	SYNTAX INTEGER
	ACCESS  read-only
	STATUS mandatory
	DESCRIPTION
		"Specific consumable index."
	::= { qmsENGConsumeIndexMulti 1 }

qmsENGNumConsumables OBJECT-TYPE
	SYNTAX INTEGER
	ACCESS read-only
	STATUS     mandatory
	DESCRIPTION
		"Number of engine-related consumables that exist within the system."
	::= { qmsEngine 1010 }

qmsENGChainInputBins OBJECT-TYPE
	SYNTAX INTEGER {	
		off(1),
		on(2),
		onAny(3)
	}
	ACCESS  read-write
	STATUS  mandatory
	DESCRIPTION
		"An option in the Operator Control menu allows you to 'chain' input-
		bins (tray and cassettes) so that when the first inputbin empties, the 
		printer will automatically draw media from another inputbin with either 
		the same or any size and type of media (dependent on the choice 
		selected).

		Choices
			On: Switch to the next inputbin with the same size and 
			    type of media when the default inputbin is empty.
			    Note: Make sure the two trays/cassettes use the 
			          same size paper.

			Off: Don't switch inputbins; use only the default 
			     inputbin.

            On Any: Switch to the next inputbin with any size and
                    type of media when the default inputbin is empty.

		Default
			On

		Notes
			Use the Operator 'qmsENGInputbin' OID to set the 
			default inputbin. Make sure that the two inputbins use 
			the same size media."
	::= { qmsEngine 1011 }

qmsENGChainOutputbinMulti OBJECT-TYPE
    SYNTAX SEQUENCE OF QmsENGChainOutputbinEntry
    ACCESS not-accessible
    STATUS mandatory
    DESCRIPTION
        "A table of the engine's default input chaining setting."
    ::= { qmsEngine 1012 }

QmsENGChainOutputbinEntry ::= SEQUENCE {
    qmsENGChainOutputbin           INTEGER
}

qmsENGChainOutputbin OBJECT-TYPE
	SYNTAX INTEGER {
		off(1),
		on(2)
	}
	ACCESS read-write
	STATUS mandatory
	DESCRIPTION
		"Flag used to indicate if output bin chaining should be active."
	::= { qmsENGChainOutputbinMulti 1 }

qmsENGInputbinMediatypeMulti OBJECT-TYPE
    SYNTAX SEQUENCE OF QmsENGInputbinMediatypeEntry
    ACCESS not-accessible
    STATUS mandatory
    DESCRIPTION
        "A table of the engine's default media type setting."
    ::= { qmsEngine 1013 }

QmsENGInputbinMediatypeEntry ::= SEQUENCE {
    qmsENGInputbinMediatype           INTEGER
}

qmsENGInputbinMediatype OBJECT-TYPE
	SYNTAX INTEGER {
		plainPaper(1),
		transparency(2),
		thermal(3),
		prePrinted(4),
		letterhead(5),
		prePunched(6),
		labels(7),
		bond(8),
		recycled(9),
		color(10),
		cardStock(11),
		thinStock(12),
		automatic(13),
		thickStock(14)
	}
	ACCESS read-only
	STATUS mandatory
	DESCRIPTION
		"A table of the engine's default media type settings."
	::= { qmsENGInputbinMediatypeMulti 1 }

qmsENGChainInputbinMulti OBJECT-TYPE
    SYNTAX SEQUENCE OF QmsENGChainInputbinEntry
    ACCESS not-accessible
    STATUS mandatory
    DESCRIPTION
        "A table of the engine's default input chaining setting."
    ::= { qmsEngine 1014 }

QmsENGChainInputbinEntry ::= SEQUENCE {
    qmsENGChainInputbin           INTEGER
}

qmsENGChainInputbin OBJECT-TYPE
	SYNTAX INTEGER {	
		off(1),
		on(2)
	}
	ACCESS read-write
	STATUS mandatory
	DESCRIPTION
		"An option in the Operator Control menu allows you to 'chain' input-
		bins (tray and cassettes) so that when the first inputbin empties, the 
		printer will automatically draw media from another inputbin with either 
		the same or any size and type of media (dependent on the choice 
		selected).

		Choices
			On: Switch to the next inputbin with the same size and 
			    type of media when the default inputbin is empty.
			    Note: Make sure the two trays/cassettes use the 
			          same size paper.

			Off: Don't switch inputbins; use only the default 
			     inputbin.

		Default
			On

		Notes
			Use the Operator 'qmsENGInputbin' OID to set the 
			default inputbin. Make sure that the two inputbins use 
			the same size media."
	::= { qmsENGChainInputbinMulti 1 }

qmsENGStaplePosition OBJECT-TYPE
	SYNTAX INTEGER {
		off(1),
		frontCorner(2),
		backCorner(3),
		center(4),
		offsetStacking(5)
	}
	ACCESS  read-write
	STATUS mandatory
	DESCRIPTION
		"This option identifies the location of the staple when stapling 
         is enabled.

                Choices
                    Off, Front corner, Back corner, Center, Offset Stacking

                Default
                    Off"
	::= { qmsEngine 1015 }

------------------------------------------------------------------------------
-- QMS Accounting Option Handles
------------------------------------------------------------------------------

qmsACCMode OBJECT-TYPE
	SYNTAX INTEGER {
		enabled(2),
		disabled(1)
	}
	ACCESS read-only
	STATUS mandatory
	DESCRIPTION
		""
	::= { qmsAccounting 1 }

qmsACCDiskSpace OBJECT-TYPE
	SYNTAX INTEGER
	ACCESS read-only
	STATUS mandatory
	DESCRIPTION
		"Size of the accounting file in KB.

		 The normal limits on this value are 50K to 10240K at the
		 present time."
	::= { qmsAccounting 2 }

qmsACCFileSegment OBJECT-TYPE
	SYNTAX INTEGER {
		single(2),
		multiple(3)
	}
	ACCESS read-only
	STATUS mandatory
	DESCRIPTION
		"How the accounting information will be created on the disk
 		 in a single or in multiple file."
	::= { qmsAccounting 3 }

------------------------------------------------------------------------------
-- QMS Scanner Option Handles
------------------------------------------------------------------------------

qmsSCColorAdjust OBJECT-TYPE
	SYNTAX INTEGER
	ACCESS read-write
        STATUS mandatory
        DESCRIPTION
		"Use this option to adjust brightness in copies.

		It allows you to adjust the brightness of halftone images. 
		This setting is enabled by the:
		        Copier/Copy Mode/Select Mode/Halftone B/W 

		Choices
			15 brightness settings (1-15); each setting makes an 
			incremental brightness change of about 2%

			D-Moving the setting in this direction decreases 
			brightness. It darkens the overall image making light 
			and dark areas appear darker.

			L-Moving the setting in this direction increases 
			brightness. It lightens the overall image making light 
			and dark areas appear lighter.

		Default
			The middle setting

		Notes
			Use the Previous key to move the message-window 
			cursor from the center towards the left to a darker (less 
			bright) setting or use the Next key to move the cursor 
			towards the right to a lighter (brighter) setting.

			Each increment of change in the brightness setting is 
			significant in output quality. Therefore, we recommend 
			that you change the setting by only one level, print out a 
			test copy, and then determine if further modification is 
			necessary."
	::= { qmsScanner 3 }

qmsSCScanResolution OBJECT-TYPE
	SYNTAX INTEGER {
		dpi100(101),
		dpi150(151),
		dpi200(201),
		dpi300(301)
	}
	ACCESS read-write
	STATUS mandatory
	DESCRIPTION
		"Use this menu to specify what resolution the scanner 
		should use.

		Choices
			100, 150, 200, or 300 dpi

		    Choose a scan resolution that is at least half of the 
		    printer resolution being used. The higher the scan 
		    resolution, the more detailed the copy output (as long 
		    as the printer resolution being used is double the scan 
		    resolution). Also, a higher scan resolution increases 
		    copying time, because of the increased amount of data 
		    that must be scanned and sent to the printer for 
		    processing. (Each time scan resolution is doubled, the 
		    amount of information that is scanned and printed is 
		    quadrupled.)

		Default
			200 dpi

		Note
			In order to change the default scan resolution, you must 
			choose the Custom Gray option in the Copier/Copy 
			Mode/Select Mode menu."
	::= { qmsScanner 4 }

qmsSCSizeHorizontal OBJECT-TYPE
	SYNTAX INTEGER (1..850)
	ACCESS read-write
	STATUS mandatory
	DESCRIPTION
		"Use this to scan only part of the scannable area in 
                order to copy only part of an image or to reduce copying
                time for images smaller than letter or A4."
	::= { qmsScanner 8 }

qmsSCSizeVertical OBJECT-TYPE
	SYNTAX INTEGER (1..1400)
	ACCESS read-write
	STATUS mandatory
	DESCRIPTION
		"Use this to scan only part of the scannable area in 
                order to copy only part of an image or to reduce copying
                time for images smaller than letter or A4."
	::= { qmsScanner 12 }

qmsSCOffsetHorizontal OBJECT-TYPE
	SYNTAX INTEGER (0..850)
	ACCESS read-write
	STATUS mandatory
	DESCRIPTION
		"Use this menu to specify where the copy is to print on the 
                selected media (in 0.01'' increments).

                Choices
                    0-850

                Default
                    0

                Notes
                    This option assigns the top-left corner of the image, so 
                    printing with the defaults places the image at the top-leftmost 
                    corner of the page."
	::= { qmsScanner 16 }

qmsSCOffsetVertical OBJECT-TYPE
	SYNTAX INTEGER (0..1100)
	ACCESS read-write
	STATUS mandatory
	DESCRIPTION
		"Use this menu to specify where the copy is to print on the 
                selected media (in 0.01'' increments).

                Choices
                    0-1100

                Default
                    0

                Notes
                    This option assigns the top-left corner of the image, so 
                    printing with the defaults places the image at the top-leftmost 
                    corner of the page."
	::= { qmsScanner 20 }

qmsSCCopyMode OBJECT-TYPE
	SYNTAX INTEGER {
		automaticColor(8),
		customColor(9),
		binaryColor(10),
		halftoneColor(11),
		automaticGray(4),
		customGray(5),
		binaryBandW(6),
		halftoneBandW(7)
	}
	ACCESS read-write
	STATUS mandatory
	DESCRIPTION
		"Use this menu to specify what type of copy is being made so 
                the printer can optimize for this type output.

                Choices
                    Automatic Gray, Custom Gray, Binary B/W, Halftone B/W

                Notes
                    Automatic Gray-Sets color depth to 8-bit gray and scan 
                    resolution to 200 dpi. Use this option when copying 
                    documents that are black and white or shades of gray. Best 
                    quality output for images.

                    Custom Gray-Allows you to adjust grayscale values.

                    Binary B/W-Allows you to adjust binary thresholds. Good for 
                    text. 

                    Halftone B/W-Allows you to adjust the brightness of halftone 
                    images. 

                Note
                    In order to change the default grayscale value, you must 
                    choose the Custom Gray option in this menu."
	::= { qmsScanner 24 }

qmsSCRedGammaFunction OBJECT-TYPE
	SYNTAX INTEGER
	ACCESS read-write
	STATUS mandatory
	DESCRIPTION
		""
	::= { qmsScanner 26 }

qmsSCGreenGammaFunction OBJECT-TYPE
	SYNTAX INTEGER
	ACCESS read-write
	STATUS mandatory
	DESCRIPTION
		""
	::= { qmsScanner 27 }

qmsSCBlueGammaFunction OBJECT-TYPE
	SYNTAX INTEGER
	ACCESS read-write
	STATUS mandatory
	DESCRIPTION
		""
	::= { qmsScanner 28 }

qmsSCGrayGammaFunction OBJECT-TYPE
	SYNTAX INTEGER {
		none(1),
		photoGraphic(2),
		reverseImage(3)
	}
	ACCESS read-write
	STATUS mandatory
	DESCRIPTION
		"Need description"
	::= { qmsScanner 29 }

qmsSCBinaryAdjustment OBJECT-TYPE
	SYNTAX INTEGER
	ACCESS read-write
	STATUS mandatory
	DESCRIPTION
		""
	::= { qmsScanner 31 }

qmsSCTrans OBJECT-TYPE
	SYNTAX INTEGER {
		disabled(1),
		enabled(2)
	}
	ACCESS read-write
	STATUS mandatory
	DESCRIPTION
		"Use this option to specify how you want the 
                Transparency Adapter (an optional accessory) to work.

                Choices
                    Enabled: Specifies transparency document copying. 
                             Enables the transparency adapter's backlighting
                             feature, which optimizes transparency copying. 

                             Note: The Transparency Adapter option must be 
                                   installed before you can enable this option.

                    Disabled: Specifies paper document copying. Turns off 
                              the transparency adapter's backlighting feature, which 
                              optimizes paper document copying.

                Default
                    Disabled"
	::= { qmsScanner 35 }

qmsSCContrast OBJECT-TYPE
	SYNTAX INTEGER
	ACCESS read-write
	STATUS mandatory
	DESCRIPTION
		"Use this option to adjust contrast in copies.

                Choices
                    15 contrast settings (1-15); each makes an incremental 
                    contrast change of about 2%

                    d-Moving the setting in this direction increases 
                      contrast. It makes light areas appear lighter and dark 
                      areas appear darker.

                    l-Moving the setting in this direction decreases 
                      contrast by making dark areas appear lighter and light 
                      areas appear darker.

                Default
                    The middle setting

                Notes
                    Each increment of change in the contrast setting is 
                    significant in output quality. Therefore, we recommend 
                    that you change the setting by only one level, print out a 
                    test copy, and then determine if further modification to 
                    the contrast setting is necessary.

                    See chapter 'Copy Quality' for more information on 
                    these options."
	::= { qmsScanner 36 }

------------------------------------------------------------------------------
-- QMS CostPerPage Option Handles
------------------------------------------------------------------------------

qmsCPPSerialNumber OBJECT-TYPE
	SYNTAX DisplayString (SIZE(0..32))
	ACCESS read-only
	STATUS mandatory
	DESCRIPTION
		"Cost per page reference serial number"
	::= { qmsCostPerPage 2 }

------------------------------------------------------------------------------
-- QMS ColorMatch Option Handles
------------------------------------------------------------------------------

-- The Minolta-QMS Color Matching Profile Group 
--
-- Implementation of this group is optional for the qms systems
-- The Color matching group is useful for identifying the color profiles 
-- loaded in the printer whether it may be native or user installed
-- International Color Consortium (ICC) profiles. 
--

qmsCMMICCColorMatch OBJECT-TYPE
	SYNTAX INTEGER {
		disabled(1),
		enabled(2)
	}
	ACCESS read-write
	STATUS mandatory
	DESCRIPTION
		"ICC Color Matching master control for activation and 
		deactivation of the feature on the printer

		Choices
			Disabled: Color conversion is not performed 
			Enabled: Color conversion is performed
		Default
			Disabled"
	::= { qmsColorMatch 1 }

qmsCMMICCRGBSource OBJECT-TYPE
	SYNTAX INTEGER
	ACCESS read-write
	STATUS mandatory
	DESCRIPTION
		"the RGB color space source profile to be used for the
		job in progress. Installed source profiles are registered with
		the color matching feature and are assigned a sequential ID at 
		power-on time. The ID field is used to locate the profile in
		secondary storage and identify the source profile element of 
		any color matching device link that may be created and ultimately 
		saved in secondary storage. Internal to the color matching
		component, the ID values range from 1 to 127. The ID value of '0' 
                is reserved, indicating that a default, resident device link
                will automatically be selected when processing this color space.  
		Any RGB profile files encountered during registration, after the 
                ID has incremented to 127, will not be registered with the system 
                and an error messaage will be displayed.

		Choices
			(1, 2, ... 128)
		Default
			(1 = None selected)"
	::= { qmsColorMatch 2 }

qmsCMMICCSimulation OBJECT-TYPE
	SYNTAX INTEGER
	ACCESS read-write
	STATUS mandatory
	DESCRIPTION
		"the ICC CMYK color space simulation profile to be used 
		for the job in progress. Installed simulation profiles are
		registered with the color matching feature and are assigned a 
		sequential ID at power-on time. The ID field is used to 
		locate the profile in secondary storage and identify the simulation 
		profile element of any color matching device link that may be 
		created and ultimately saved in secondary storage. Internal 
		to the color matching component, the ID values range from 1 to 
		127. The ID value of '0' is reserved, indicating that a default, 
                resident device link will automatically be selected when processing 
                this color space.  Any simulation files encountered during 
                registration after the ID has incremented to 127, will not be 
                registered with the system and an error messaage will be displayed. 

		Choices
			(1, 2, ... 128) 
		Default
			(1 = None selected)"
	::= { qmsColorMatch 4 }

qmsCMMICCDestination OBJECT-TYPE
	SYNTAX INTEGER
	ACCESS read-write
	STATUS mandatory
	DESCRIPTION
		"the ICC destination color profile to be used for the job in
		progress. Installed destination profiles are registered with
		the color matching feature and are assigned a sequential ID at 
		power-on time. The ID field is used to locate the profile in 
		secondary storage, and to identify the destination profile
		element of any color matching device link that may be created 
		and ultimately saved in secondary storage.

		Internal to the color matching component, the IDs range from 0 
		to 127. The ID values '0' to 'm' are reserved for factory supplied
		destination profiles associated with each available print
		resolution. The number of factory supplied profiles can vary 
		from engine to engine based on the number of supported print
		resolutions. Any destination profile files encountered during 
		registration, after the ID has incremented to 127, will not be 
		registered with the system and an error message will be
		displayed.

		All factory supplied profiles in the range of '0' to 'm' are 
		grouped into a single setting designated 'Automatic.' In the
		Automatic setting, destination profile selection is determined
		by the print resolution currently selected, screentype, and
                mediatype, depending on resident destination profiles. Any 
                settings in the range of 'm+1' to 127 require that the user 
                ensure that the correct resolution is selected before printing 
                occurs. 

		Choices
			(1, 2, ... 128) 
		Default
			(1 = Automatic)"
	::= { qmsColorMatch 6 }

qmsCMMICCHP OBJECT-TYPE
	SYNTAX INTEGER {
		disabled(1),
		srgb(2)
	}
	ACCESS read-write
	STATUS mandatory
	DESCRIPTION
		"default ICC CMY color space profile to be used for the PCL/XL
                job in progress.  The available CMY profiles are registered 
                with the color matching feature, and assigned a sequential ID
                at power-on time.  The ID field is used to locate the profile
                in primary or secondary storage for when creating ICC device
                links.  The ID values for these profiles range from 1 to 2.
                The ID value of 1 indicates that color matching is disabled 
                for the PCL/XL job in progress.

		Choices
			(1 or 2)
		Default
			(1 = PCL/XL color matching is disabled)
                        (2 = sRGB is selected for PCL/XL color matching)"

	::= { qmsColorMatch 12 }

qmsCMMLinkQuality OBJECT-TYPE
	SYNTAX INTEGER {
		low(1),
		medium(2),
		high(3)
	}
	ACCESS read-write
	STATUS mandatory
	DESCRIPTION
		"Color Matching device link quality to be used for any ICC 
		device links created during execution of the current job.
		Three quality settings are available: low, medium, and high.
		The higher the quality setting, the greater the amount of
		client memory consumed when creating the device link. 

		Choices
			1 = Low quality
			2 = Medium quality 
			3 = High quality

		Default
			3"
	::= { qmsColorMatch 8 }

qmsCMMSimInRGBLinks OBJECT-TYPE
	SYNTAX INTEGER {
		no(1),
		yes(2)
	}
	ACCESS read-write
	STATUS mandatory
	DESCRIPTION
		"Determines if the Simulation profile selection should be used 
		with the RGB source profile to construct the color matching
		device links used in RGB color space processing. When set to 
		(No), this has the same effect as setting the Simulation 
		profile value to (None) when RGB color space device links are created. 
		This setting has no effect on device links created for use in 
		CMYK color space processing. RGB color space Device Link
		construction may be visualized as follows: 

		RGB Profile + Simulation Profile + Destination Profile -
		Device Link

		where the Simulation Profile parameter is optional. 

		Choices
			No:  Device links used for RGB color space processing are 
			     constructed without any Simulation profiles.
			Yes: The current Simulation profile selection will be included
			     in the construction of RGB color space device links.

		Default
			(No)"
	::= { qmsColorMatch 10 }

qmsCMMProfileTable OBJECT-TYPE
	SYNTAX SEQUENCE OF QmsCMMProfileEntry
	ACCESS not-accessible 
	STATUS mandatory
	DESCRIPTION
		"A table of color profiles in the printer. The user will 
		query the printer to get all the available profiles.
		The profiles when read will normally be arranged in contiguous 
		order based on the type"
	::= { qmsColorMatch 1000 }

qmsCMMProfileEntry OBJECT-TYPE
	SYNTAX QmsCMMProfileEntry 
	ACCESS not-accessible
	STATUS mandatory
	DESCRIPTION
		"Information describing ICC color profile entries. The number 
		of entries returned is dynamic, changing based on the addition 
		or deletion of profiles by remote users."
	INDEX { qmsCMMProfileIndex } 
	::= { qmsCMMProfileTable 1 } 

QmsCMMProfileEntry ::= SEQUENCE {
	qmsCMMProfileIndex INTEGER,
	qmsCMMProfileDescription DisplayString,
	qmsCMMProfileType INTEGER
	}

qmsCMMProfileIndex OBJECT-TYPE
	SYNTAX INTEGER
	ACCESS read-only
	STATUS mandatory
	DESCRIPTION
		"A value used by the printer to identify the color profile. 
		There may be three sequence of index number corresponding
		to the RGBSource, Simulation and Destination Profiles.
		These values may change due to user reconfiguration of the
		device (e.g. the addition and deletion of new profile files to 
		the printer)"
	::= { qmsCMMProfileEntry 1000 } 

qmsCMMProfileDescription OBJECT-TYPE
	SYNTAX DisplayString (SIZE(0..32)) 
	ACCESS read-only
	STATUS mandatory
	DESCRIPTION
		"profile description field. This field is loaded from
		the ICC profile header information contained in each installed 
		profile for the profile type and ID selected. The first 15
		characters are reserved for the profile's name. The remaining
		characters are available for the display of additional 
		information about the profile. The complete description of the
		ICC profile header is documented in the ICC Profile Specification
		Version 3.0.1 approved in August, 1995. Refer to the
		qmsCMMRGBSource, qmsCMMSimulation, and qmsCMMDestination
		object type descriptions for more information.

		Example: Trin G1.8 D50 Sony Trinitron D50 
			where
				Trin G1.8 D50 - (positions 1 through 15) is used
						internally as the profile name, and 
				Sony Trinitron D50 - is additional information
						provided by the profile author." 
	::= { qmsCMMProfileEntry 1001 }

	qmsCMMProfileType OBJECT-TYPE 
	SYNTAX INTEGER {
		source(1),
		destination(2),
		simulation(3)
	}
	ACCESS read-only
	STATUS mandatory
	DESCRIPTION
		"ICC defined Profile Type. Typically, there will be more than one 
		profile registered for each type"
	::= { qmsCMMProfileEntry 1002 }

------------------------------------------------------------------------------
-- QMS PostScript (R) Emulation Option Handles
------------------------------------------------------------------------------

qmsPSErrorHandler	OBJECT-TYPE
	SYNTAX	INTEGER {
		yes(2),
		no(1)
	}
	ACCESS read-write
	STATUS mandatory
	DESCRIPTION
	"Error Handler is a diagnostic tool that identifies PostScript errors
         encountered during a print job.

        Choices
            Yes: Load the Error Handler at power on.

            No: Don't load the Error Handler.

        Default
            No

        Notes
            Refer to the PostScript Language Reference Manual 
            (Adobe Systems Incorporated, Reading, PA: Addison-
            Wesley, 1990, ISBN 0-201-18127-4) for more 
            information on PostScript errors."
	::= { qmsPS 5 }

qmsPSOutputPositioning	OBJECT-TYPE
	SYNTAX	INTEGER {
		on(2),
		off(1)
	}
	ACCESS read-only
	STATUS mandatory
	DESCRIPTION
	"PS Flag to enable or disable output positioning."
	::= { qmsPS 6 }

qmsPSDefaultHalftone	OBJECT-TYPE
	SYNTAX INTEGER {
			basic(1),
			standard(2),
			advanced(3)
	}
	ACCESS read-write
	STATUS mandatory
	DESCRIPTION
		"Sets the default PostScript halftone type.
	
		Choices
			Basic
			Standard
			Advanced

		Default
			Standard

		Notes
			Consult your printer documentation for more information.
		    These values are specific to each printer."
	::= { qmsPS 138 }

qmsPSDefaultBlackOverPrint	OBJECT-TYPE
	SYNTAX	INTEGER {
		on(2),
		off(1)
	}
	ACCESS read-only
	STATUS mandatory
	DESCRIPTION
	"PS value...."
	::= { qmsPS 139 }

qmsPSDefaultCRD	OBJECT-TYPE
	SYNTAX	INTEGER (0..15)
	ACCESS	read-only
	STATUS mandatory
	DESCRIPTION
	"PS value for the default color rendering dictionary."
	::= { qmsPS 140 }

qmsPSDefaultDither	OBJECT-TYPE
	SYNTAX	INTEGER {
		on(2),
		off(1)
	}
	ACCESS	read-only
	STATUS mandatory
	DESCRIPTION
	"PS value for the default dither."
	::= { qmsPS 141 }

qmsPSDefaultGamma	OBJECT-TYPE
	SYNTAX	INTEGER {
		on(2),
		off(1)
	}
	ACCESS	read-write
	STATUS mandatory
	DESCRIPTION
	"PS value for the default gamma correction to use."
	::= { qmsPS 152 }

qmsPSIntensity  OBJECT-TYPE      
    SYNTAX  INTEGER {
        darkest(1),
        darker(2),
        normal(3),
        lighter(4), 
        lightest(5) 
    }  
    ACCESS  read-write
    STATUS mandatory
    DESCRIPTION     
    "Intensity uses the PostScript settrasfer operator's
	 functionality to make the print lighter or darker while
	 maintaining the linearity of the grayscale.

	 Choices:
	     Darkest, Darker, Normal, Lighter, Lightest

	 Default:
		 Normal"
    ::= { qmsPS 154 }

------------------------------------------------------------------------------
-- QMS HPGL Emulation Option Handles
------------------------------------------------------------------------------

qmsHPGLPaperType OBJECT-TYPE
	SYNTAX	INTEGER {
		a(1),
		a4(2),
		b(3),
		a3(4),
		c(5),
		d(6),
		e(7),
		cArch(8),
		dArch(9),
		eArch(10),
		a2(11),
		a1(12),
		a0(13),
		scaleToPaper(14)
	}
	ACCESS  read-write
	STATUS mandatory
	DESCRIPTION
		"Identifies the original image's paper size.

		Choices
			A-(8.5''x 11''-216 x 279 mm),
			A0-(33.11'' x 46.81''-841 x 1189 mm)
			A1-(23.39'' x 3.11''-594 x 1189 mm)
			A2-(16.54'' x 23.29''-420 x 594 mm)
			A3-(11.69'' x 16.54''-297 x 420 mm)
			A4-(8.27'' x 11.69''-210 x 297 mm)
			B-(11'' x 17''-279 x 432 mm)
			C-(17'' x 22''-431.80 x 558.80 mm)
			D-(22'' x 34''-558.80 x 863.60 mm)
			E-(34'' x 44''-863.60 x 1117.60 mm)
			C ARCH
			D ARCH
			E ARCH
			Scale to Paper

		Default
			Scale to Paper

		Note: These paper sizes describe a mapping to 
		      the physical paper. This mapping is a scaling 
		      factor (or a size ratio) between the chosen paper 
		      size and the physical paper size in the default 
		      inputbin. For example if A3 is selected (size 
		      11.69'' x 16.54'') for paper size and the physical 
		      paper size in the default inputbin is A4 (8.27'' x 
		      11.69''), then the plot is scaled by a factor of 2."
	::= { qmsHPGL 2 }

qmsHPGLPlotter OBJECT-TYPE
	SYNTAX	INTEGER {
		plotter7475A(1),
		plotter7470A(2),
		colorpro(3),
		plotter7550A(4),
		draftmaster(5)
	}
	ACCESS  read-write
	STATUS mandatory
	DESCRIPTION
		"Identifies the HP-GL plotter type.

		Choices
			7475A
			7470A
			Colorpro
			7550A
			DraftMaster: Supports architectural and engineering 
			             paper sizes (for example, A to E and Arch A to Arch E). 

		Default
			7550A"
	::= { qmsHPGL 12 }

qmsHPGLScalingPercent OBJECT-TYPE
	SYNTAX INTEGER (1..150)
	ACCESS read-write
	STATUS mandatory
	DESCRIPTION
		"Identifies the percentage to reduce or enlarge an image.

		Choices
			001-150 (1-150%)

		Default
			100 (100%)

		Note: To scale plots, select the paper size originally used for the plot 
		      in the Paper Type menu and then enter the reduction or enlargement 
		      needed to fit the plot on the new page in the Scaling Percent menu."
	::= { qmsHPGL 13 }

qmsHPGLEnhancedMode OBJECT-TYPE
	SYNTAX	INTEGER {
		off(1),
		on(2)
	}
	ACCESS read-write
	STATUS mandatory
	DESCRIPTION
		"Increases the resolution of the grid for downloaded characters. The 
		HP-GL UC (User-defined Character) command allows you to down-
		load and draw characters using an encoding scheme consisting of 
		sequences of pen control movements and coordinate sequences. 
		The characters are drawn on a grid that is superimposed on the 
		character plot cell.

		Choices
			On: Standard resolution for fixed- and variable-spaced 
			    fonts (4x8 grid).

			Off: Enhanced resolution for variable-spaced fonts 
			     (26x36 grid).

		Default
			Off"
	::= { qmsHPGL 14 }

qmsHPGLExpandMode OBJECT-TYPE
	SYNTAX	INTEGER {
		off(1),
		on(2)
	}
	ACCESS read-write
	STATUS mandatory
	DESCRIPTION
		"Defines a larger imageable area which affects the default placement 
		of the scaling points P1 and P2. 

		Choices
			On: Turn on expand mode

			Off: Use default scaling points, plotting range, and 
			     plotting area.

		Default
			Off

		Notes
			The available range of plotter units for a particular 
			media size is only partially determined by setting the 
			Expand Mode to On. When the printer/plotter senses 
			the media size it automatically sets the hard clip limit to 
			15mm on three sides and 39 mm on the fourth. If 
			Expand Mode is On, then the hard clip limits are set to 
			5mm on three sides and 29 mm on the fourth side. This 
			is what allows you to define a larger imageable area.

			The HP-GL emulation senses the media type if the 
			paper type is set to Scale to Paper. It is also possible to 
			have the HP-GL emulation use a particular media size 
			by setting Original Paper Type through the control panel 
			or by using a Document Option Command."
	::= { qmsHPGL 15 }

qmsHPGLPenWidth1 OBJECT-TYPE
	SYNTAX INTEGER (0..60)
	ACCESS read-write
	STATUS mandatory
	DESCRIPTION
		"Sets the width for pen 1. Each pen has a 
		width option available.

		Choices
			0-60 (0.0-6.0 mm)

		Default
			Pen 1-7 (0.7 mm)

		Note
			A choice of 0 defaults to a pixel of '1'."
	::= { qmsHPGL 16 }

qmsHPGLPenWidth2 OBJECT-TYPE
	SYNTAX INTEGER (0..60)
	ACCESS read-write
	STATUS mandatory
	DESCRIPTION
		"Sets the width for pen 2. Each pen has a 
		width option available.

		Choices
			0-60 (0.0-6.0 mm)

		Default
			Pen 2-3 (0.3 mm)

		Note
			A choice of 0 defaults to a pixel of '1'."
	::= { qmsHPGL 17 }

qmsHPGLPenWidth3 OBJECT-TYPE
	SYNTAX INTEGER (0..60)
	ACCESS read-write
	STATUS mandatory
	DESCRIPTION
		"Sets the width for pen 3. Each pen has a 
		width option available.

		Choices
			0-60 (0.0-6.0 mm)

		Default
			Pen 3-3 (0.3 mm)

		Note
			A choice of 0 defaults to a pixel of '1'."
	::= { qmsHPGL 18 }

qmsHPGLPenWidth4 OBJECT-TYPE
	SYNTAX INTEGER (0..60)
	ACCESS read-write
	STATUS mandatory
	DESCRIPTION
		"Sets the width for pen 4. Each pen has a 
		width option available.

		Choices
			0-60 (0.0-6.0 mm)

		Default
			Pen 4-3 (0.3 mm)

		Note
			A choice of 0 defaults to a pixel of '1'."
	::= { qmsHPGL 19 }

qmsHPGLPenWidth5 OBJECT-TYPE
	SYNTAX INTEGER (0..60)
	ACCESS read-write
	STATUS mandatory
	DESCRIPTION
		"Sets the width for pen 5. Each pen has a 
		width option available.

		Choices
			0-60 (0.0-6.0 mm)

		Default
			Pen 5-3 (0.3 mm)

		Note
			A choice of 0 defaults to a pixel of '1'."
	::= { qmsHPGL 20 }

qmsHPGLPenWidth6 OBJECT-TYPE
	SYNTAX INTEGER (0..60)
	ACCESS read-write
	STATUS mandatory
	DESCRIPTION
		"Sets the width for pen 6. Each pen has a 
		width option available.

		Choices
			0-60 (0.0-6.0 mm)

		Default
			Pen 6-3 (0.3 mm)

		Note
			A choice of 0 defaults to a pixel of '1'."
	::= { qmsHPGL 21 }

qmsHPGLPenWidth7 OBJECT-TYPE
	SYNTAX INTEGER (0..60)
	ACCESS read-write
	STATUS mandatory
	DESCRIPTION
		"Sets the width for pen 7. Each pen has a 
		width option available.

		Choices
			0-60 (0.0-6.0 mm)

		Default
			Pen 7-3 (0.3 mm)

		Note
			A choice of 0 defaults to a pixel of '1'."
	::= { qmsHPGL 22 }

qmsHPGLPenWidth8 OBJECT-TYPE
	SYNTAX INTEGER (0..60)
	ACCESS read-write
	STATUS mandatory
	DESCRIPTION
		"Sets the width for pen 8. Each pen has a 
		width option available.

		Choices
			0-60 (0.0-6.0 mm)

		Default
			Pen 8-3 (0.3 mm)

		Note
			A choice of 0 defaults to a pixel of '1'."
	::= { qmsHPGL 23 }

qmsHPGLPenColor1 OBJECT-TYPE
	SYNTAX	INTEGER {
		red(2),
		orange(3),
		yellow(4),
		green(5),
		blue(6),
		cyan(7),
		magenta(8),
		black(9),
		violet(10),
		brown(11),
		gray25Percent(12),
		gray50Percent(13),
		gray75Percent(14)
	}
	ACCESS read-write
	STATUS mandatory
	DESCRIPTION
		"Sets color for pen 1. Each pen has a color option available.

		Choices
			Black, Blue, Brown, Cyan, Gray-25%, Gray-50%, Gray-
			75%, Green, Magenta, Orange, Red, Violet, Yellow

		Default
			Pen 1-Black (100% black)"
	::= { qmsHPGL 24 }

qmsHPGLPenColor2 OBJECT-TYPE
	SYNTAX	INTEGER {
		red(2),
		orange(3),
		yellow(4),
		green(5),
		blue(6),
		cyan(7),
		magenta(8),
		black(9),
		violet(10),
		brown(11),
		gray25Percent(12),
		gray50Percent(13),
		gray75Percent(14)
	}
	ACCESS read-write
	STATUS mandatory
	DESCRIPTION
		"Sets color for pen 2. Each pen has a 
		color option available.

		Choices
			Black, Blue, Brown, Cyan, Gray-25%, Gray-50%, Gray-
			75%, Green, Magenta, Orange, Red, Violet, Yellow

		Default
			Pen 2-Black (100% black)"
	::= { qmsHPGL 25 }

qmsHPGLPenColor3 OBJECT-TYPE
	SYNTAX	INTEGER {
		red(2),
		orange(3),
		yellow(4),
		green(5),
		blue(6),
		cyan(7),
		magenta(8),
		black(9),
		violet(10),
		brown(11),
		gray25Percent(12),
		gray50Percent(13),
		gray75Percent(14)
	}
	ACCESS read-write
	STATUS mandatory
	DESCRIPTION
		"Sets color for pen 3. Each pen has a color option available.

		Choices
			Black, Blue, Brown, Cyan, Gray-25%, Gray-50%, Gray-
			75%, Green, Magenta, Orange, Red, Violet, Yellow

		Default
			Pen 3-Red (70% black)"
	::= { qmsHPGL 26 }

qmsHPGLPenColor4 OBJECT-TYPE
	SYNTAX	INTEGER {
		red(2),
		orange(3),
		yellow(4),
		green(5),
		blue(6),
		cyan(7),
		magenta(8),
		black(9),
		violet(10),
		brown(11),
		gray25Percent(12),
		gray50Percent(13),
		gray75Percent(14)
	}
	ACCESS read-write
	STATUS mandatory
	DESCRIPTION
		"Sets color for pen 4. Each pen has a color option available.

		Choices
			Black, Blue, Brown, Cyan, Gray-25%, Gray-50%, Gray-
			75%, Green, Magenta, Orange, Red, Violet, Yellow

		Default
			Pen 4-Green (41% black)"
	::= { qmsHPGL 27 }

qmsHPGLPenColor5 OBJECT-TYPE
	SYNTAX	INTEGER {
		red(2),
		orange(3),
		yellow(4),
		green(5),
		blue(6),
		cyan(7),
		magenta(8),
		black(9),
		violet(10),
		brown(11),
		gray25Percent(12),
		gray50Percent(13),
		gray75Percent(14)
	}
	ACCESS read-write
	STATUS mandatory
	DESCRIPTION
		"Sets color for pen 5. Each pen has a color option available.

		Choices
			Black, Blue, Brown, Cyan, Gray-25%, Gray-50%, Gray-
			75%, Green, Magenta, Orange, Red, Violet, Yellow

		Default
			Pen 5-Blue (89% black)"
	::= { qmsHPGL 28 }

qmsHPGLPenColor6 OBJECT-TYPE
	SYNTAX	INTEGER {
		red(2),
		orange(3),
		yellow(4),
		green(5),
		blue(6),
		cyan(7),
		magenta(8),
		black(9),
		violet(10),
		brown(11),
		gray25Percent(12),
		gray50Percent(13),
		gray75Percent(14)
	}
	ACCESS read-write
	STATUS mandatory
	DESCRIPTION
		"Sets color for pen 6. Each pen has a color option available.

		Choices
			Black, Blue, Brown, Cyan, Gray-25%, Gray-50%, Gray-
			75%, Green, Magenta, Orange, Red, Violet, Yellow

		Default
			Pen 6-Violet (59% black)"
	::= { qmsHPGL 29 }

qmsHPGLPenColor7 OBJECT-TYPE
	SYNTAX	INTEGER {
		red(2),
		orange(3),
		yellow(4),
		green(5),
		blue(6),
		cyan(7),
		magenta(8),
		black(9),
		violet(10),
		brown(11),
		gray25Percent(12),
		gray50Percent(13),
		gray75Percent(14)
	}
	ACCESS read-write
	STATUS mandatory
	DESCRIPTION
		"Sets color for pen 7. Each pen has a color option available.

		Choices
			Black, Blue, Brown, Cyan, Gray-25%, Gray-50%, Gray-
			75%, Green, Magenta, Orange, Red, Violet, Yellow

		Default
			Pen 7-Orange (25.8% black)"
	::= { qmsHPGL 30 }

qmsHPGLPenColor8 OBJECT-TYPE
	SYNTAX	INTEGER {
		red(2),
		orange(3),
		yellow(4),
		green(5),
		blue(6),
		cyan(7),
		magenta(8),
		black(9),
		violet(10),
		brown(11),
		gray25Percent(12),
		gray50Percent(13),
		gray75Percent(14)
	}
	ACCESS read-write
	STATUS mandatory
	DESCRIPTION
		"Sets color for pen 8. Each pen has a color option available.

		Choices
			Black, Blue, Brown, Cyan, Gray-25%, Gray-50%, Gray-
			75%, Green, Magenta, Orange, Red, Violet, Yellow

		Default
			Pen 8-Brown (50% black)"
	::= { qmsHPGL 31 }

------------------------------------------------------------------------------
-- QMS HPPCL Option Handles
------------------------------------------------------------------------------

qmsHPPCLLineTermination OBJECT-TYPE
	SYNTAX	INTEGER {
		crEQcr-lfEQlf(1),
		crEQcrANDlf-lfEQlf(2),
		crEQcr-lfEQcrANDlf(3),
		crORlfEQcrANDlf(4)
	}
	ACCESS read-write
	STATUS mandatory
	DESCRIPTION
		"Indicates the default line termination mode. This setting specifies
		the treatment of line feeds and carriage returns.

		Choices
			CR=CR LF=LF
			CR=CR+LF LF=LF
			CR=CR LF=CR+LF
			CR or LF=CR+LF

		Default
			CR=CR LF=LF"
	::= { qmsHPPCL 2 }

qmsHPPCLFontNumber OBJECT-TYPE
	SYNTAX	INTEGER {
		courier12(1),
		courier12Bold(2),
		courier12Italic(3),
		courier10(4),
		courier10Bold(5),
		courier10Italic(6),
		lineprinter(7),
		times(8),
		timesItalic(9),
		timesBold(10),
		timesBldItalic(11),
		univ(12),
		univItalic(13),
		univBold(14),
		univBoldItalic(15),
		univcond(16),
		univcondItalic(17),
		univcondBold(18),
		univcondBldItlc(19),
		selectByIndex(20)
	}
	ACCESS read-write
	STATUS mandatory
	DESCRIPTION
		"Sets the printer's default font.

		Choices
			Courier12, Courier12bold, Courier12italic, Courier10, 
			Courier10bold, Courier10italic, Lineprinter, Times*, 
			Times*Italic, Times*Bold, Times*BldItalic, Univ*, 
			Univ*Italic, Univ*Bold, Univ*BldItalic, Univcond*, 
			Univcond*Italic, Univcond*Bold, Univcond*BldItlc, 
			Select By Index 

		Default
			Courier12

		Notes
			Fonts with an asterisk `*` in their names are scalable. 
			Their default point size is set by the Point Size X100 
			option. Choosing Selectbyindex as the default font 
			selects the font by the index number printed on the 
			advanced status page and is set through the Default 
			Font Index option. 

			Note: You must used the selectbying value to 
		              select an Intellifont.

		All courier fonts (courier10 and courier12) and 
		lineprinter are bitmap fonts, so they have a fixed point 
		size. Selecting a bound, bitmap font overrides the 
		default settings for symbol set and point size. An 
		unbound font uses the specified default symbol set if 
		possible, and a scalable font uses the default font size."
	::= { qmsHPPCL 4 }

qmsHPPCLLinesPerInch OBJECT-TYPE
	SYNTAX INTEGER (100..4800)
	ACCESS read-write
	STATUS mandatory
	DESCRIPTION
		"Sets the default lines printed per inch in PCL jobs, regardless 
		of page size.

		Choices
			100 to 4800

		Default
			600

		Notes
			You must enter the number of lines per inch times 100. 
			For example, 6 lines per inch is entered as 600; 
			6.6 lines per inch is entered as 660."
	::= { qmsHPPCL 6 }

qmsHPPCLDefaultSymbolSet OBJECT-TYPE
	SYNTAX	INTEGER {
		roman8(278),
		isoLatin1(15),
		isoLatin2(79),
		isoLatin5(175),
		pc8US(342),
		pc8DN(374),
		pc850(406),
		pc852Latin2(566),
		pc8TK(309),
		win31Latin1(630),
		win31Latin2(294),
		win31Latin5(181),
		desktop(235),
		psText(331),
		venturaIntl(427),
		venturaUS(459),
		microsoftPub(203),
		math8(270),
		psMath(174),
		ventura-Math(206),
		piFont(502),
		legal(54),
		iso4UK(38),
		iso6ASCII(22),
		iso11SWED(20),
		iso15ITAL(10),
		iso17SPAN(84),
		iso21GERM(40),
		iso60NORW(5),
		iso69FREN(39),
		win30Latin1(310),
		mcText(395)
	}
	ACCESS read-write
	STATUS mandatory
	DESCRIPTION
		"Selects the default symbol set for the emulation. Not all symbol sets 
		are available with certain resident fonts. In particular, the Desktop, PS 
		Math, Math 8, Microsoft Pub, Pi Font, PS Text, Ventura Intl, Ventura 
		Math, Ventura US, and Windows symbol sets cannot be used with the 
		resident bitmap fonts: courier10, courier10bold, courier10italic, 
		courier12, courier12bold, courier12italic, and lineprinter. 

		Choices
			Roman-8, PC-850, PC8-US, PC8-DN, Legal, ISO-4, 
			ISO-6, ISO-11, ISO-15, ISO-17, ISO-21, ISO-60,
			ISO-69, Desktop, PS Math, Math-8, Microsoft-Pub, Pi - 
			font, PS-Text, Ventura-Intl, Ventura-Math, Ventura-US, 
			Windows , ISO-Latin-1, ISO-Latin-2, ISO-Latin-5, 
			PC-852, PC-8tk, Windows 3.1-1, Windows 3.1-2, 
			Windows 3.1-3, MC-Text

		Default
			Roman-8

		Notes
			If a mismatch between symbol set and fonts occurs, the 
			standard PCL font selection mechanism is used to 
			locate a font that matches the selected symbol set. With 
			the standard set of fonts distributed for your printer, this 
			matches the Times* font, but other user-installed fonts 
			could change this result."
	::= { qmsHPPCL 8 }

qmsHPPCLPreJobReset OBJECT-TYPE
	SYNTAX INTEGER {
		off(1),
		on(2),
		oncompatibility(3)
	}
	ACCESS read-write
	STATUS mandatory
	DESCRIPTION
		"Allows you to control the PCL 5e print environment across print jobs. 

		Choices
			Off: Resets PCL to its default state at the end of each 
			     PCL print job, executes an implicit <ESC>E at the 
			     start and end of the job, and deletes any temporary 
			     fonts, macros, and patterns.

			On: Resets PCL to its default state at the end of each 
			    PCL print job. Temporary fonts, macros, and patterns 
			    from previous PCL jobs are retained in memory after 
			    the print job has completed. You can recall these 
			    downloaded fonts, macros, or patterns from within 
			    your PCL file without having to download them again.

			On Compatibility: Retains the entire state of PCL as 
			                  well as the temporary macros, fonts, 
			                  and patterns from previous PCL jobs.

		Default
			Off

		Notes
			A retained state is cleared if you do any of the following:

			* Explicitly clear the PCL state by sending an 
			  <ESC>E or Printer Job Language.

			* Turn off the printer. (Note that if Retain Temporary 
			  is set to On or On Compatibility and power is turned 
			  off and back on again, all temporary objects on the 
			  disk's standard resource will become permanent. 
			  RAM-based temporary objects are lost).

			* Change any PCL front panel option.

			* Send any PCL-specific DOC commands (except 
			  the DOC emulation command).

			* Send a PCL job from a different communications 
			  port. For example, the state set up by a PCL job 
			  using the parallel port is cleared if a subsequent 
			  PCL job arrives at the serial port)."
	::= { qmsHPPCL 10 }

qmsHPPCLPointSize OBJECT-TYPE
	SYNTAX INTEGER (25..99975)
	ACCESS read-write
	STATUS mandatory
	DESCRIPTION
		"Sets the point size for scalable default fonts in units of hundreths of a 
		point. For example, a 24 point default point size is selected by enter-
		ing 2400. 

		The smallest increment allowed in point size is .25 point (for example, 
		8.5 point and 8.75 point fonts are allowed, but 8.6 point is not).

		Choices
			00025-99975 (0.25-999.75 points)

		Default
			01200 (12 points)

		Notes
			If the font is not scalable or if a bitmap font is specified, 
			the setting is ignored."
	::= { qmsHPPCL 12 }

qmsHPPCLDefaultFontID OBJECT-TYPE
	SYNTAX INTEGER (0..32767)
	ACCESS read-write
	STATUS mandatory
	DESCRIPTION
		"Sets the Default Font Index when the Default Font is set to 
		selectbyindex.

		Choices
			0 to 32767

		Default
			0

		Note
			The index number can be obtained by the listing printed 
			on the advanced status page."
	::= { qmsHPPCL 16 }

qmsHPPCLGL2Plotter OBJECT-TYPE
	SYNTAX	INTEGER {
		off(1),
		on(2)
	}
	ACCESS read-write
	STATUS mandatory
	DESCRIPTION
		"Allows your printer to emulate a monochrome or color plotter.

		Choices
			On: Sets the printer to monochrome (2 pen).

			Off: Sets the printer to color (8 pen). 

		Note: Since a monochrome print system has two 
		      pen colors only (black and white), grayscale 
		      patterns are substituted for other colors.

		      The printer maps each pen to its assigned color, then 
		      converts the color to a grayscale using the National 
		      Television System Committee (NTSC) color standard 
		      for luminosity coefficients (Additive System):

				Y = .3R + .59G + .11B

		      Examples on How to Use the Color Standard Formula

			White	Y = [(1*0.3) + (1*0.59) + (1*0.11)]-100% gray
			Black	Y = [(0*0.3) + (0*0.59) + (0*0.11)]-0% gray
			Red	Y = [(1*0.3) + (0*0.59) + (0*0.11)]-30% gray
			Green	Y = [(0*0.3) + (1*0.59) + (0*0.11)]-59% gray
			Yellow	Y = [(1*0.3) + (1*0.59) + (0*0.11)]-89% gray
			Blue	Y = [(0*0.3) + (0*0.59) + (1*0.11)]-11% gray
			Magenta	Y = [(1*0.3) + (0*0.59) + (1*0.11)]-41% gray
			Cyan	Y = [(0*0.3) + (1*0.59) + (1*0.11)]-70% gray

		Default
			On

		Pen Color Defaults:
			Pen 1 = White
			Pen 2 = Black
			Pen 3 = Red
			Pen 4 = Green
			Pen 5 = Yellow
			Pen 6 = Blue
			Pen 7 = Magenta
			Pen 8 = Cyan"
	::= { qmsHPPCL 18 }

qmsHPPCLDiskOrRam OBJECT-TYPE
	SYNTAX	INTEGER {
		memory(1),
		disk(2)
	}
	ACCESS read-only
	STATUS mandatory
	DESCRIPTION
		"Controls the default storage location of PCL objects (fonts, macros, 
		and patterns) when it is not otherwise specified through DOC com-
		mands.

		Choices
			Disk: All downloaded PCL objects are stored in the 
			      default disk resource, if present.

			Memory: All downloaded PCL objects are stored in 
			        temporary storage in RAM.

		Default
			Disk

		Notes
			Note: Before downloading any fonts, macros, or 
			      patterns ensure that the printer has enough 
			      memory to do the download. 

			DOC commands specifying resources override this 
			option on a per-job basis.


			If this option is set to Disk and no hard disk is installed, 
			memory is used as the default storage location.


			If the printer has both a hard disk and a large amount of 
			memory, setting this option to Memory enhances printer 
			performance."
	::= { qmsHPPCL 24 }

------------------------------------------------------------------------------
-- QMS DEC LN03 Emulation Option Handles
------------------------------------------------------------------------------

qmsDECLN03ProductID OBJECT-TYPE
	SYNTAX	INTEGER {
		ln03(1),
		lqp02(2),
		la100(3)
	}
        ACCESS read-write
        STATUS mandatory
        DESCRIPTION
        	"This is the emulation printer model. If your host 
			sends a Device Attributes request to the printer, the 
			printer responds with the Product ID.

			Choices
			    LN03, LQP02, and LA100

		    Default
			    LN03"
        ::= { qmsDECLN03 4 }

qmsDECLN03AutowrapMode OBJECT-TYPE
	SYNTAX	INTEGER {
		off(1),
		on(2)
	}
        ACCESS read-write
        STATUS mandatory
        DESCRIPTION
        	"Determines whether text that exceeds the right 
			margin wraps to the next line.

			Choices
			    Off and On

		    Default
			    On"
        ::= { qmsDECLN03 5 }

qmsDECLN03PaperSize OBJECT-TYPE
	SYNTAX	INTEGER {
		letter(1),
		a4(2),
		legal(3),
		sz11x17(4)
	}
        ACCESS read-write
        STATUS mandatory
        DESCRIPTION
        	"Specifies the paper size used at power-up or when 
			no paper size is specified.

			Choices
			    Letter, A4, Legal, and 11x17

			Default
			    Letter"
        ::= { qmsDECLN03 6 }

qmsDECLN03PaperSizeOverride OBJECT-TYPE
	SYNTAX	INTEGER {
		off(1),
		on(2)
	}
        ACCESS  read-write
        STATUS mandatory
        DESCRIPTION
        	"Controls the paper selection. If Paper Size Override 
		    is disabled, the emulation uses the transformation 
		    point for the size of paper selected and uses the 
		    current paper size (does not change paper trays). If 
		    Paper Size Override is enabled, the transformation 
    		is the same as above, and the specified paper size 
		    is selected.

		    Choices
			    Off and On

		    Default
			    Off"
        ::= { qmsDECLN03 7 }

qmsDECLN03Xorigin OBJECT-TYPE
	SYNTAX INTEGER
        ACCESS read-write
        STATUS mandatory
        DESCRIPTION
        	"Moves the lower left corner of the image to the right 
		    from 0 to 300 dots (1 inch at a resolution of 300 
		    dpi). Use this option to eliminate clipping of the 
		    right edge of the image on some systems.

		    Range
			    0-300

		    Default
			    75"
        ::= { qmsDECLN03 8 }

qmsDECLN03Yorigin OBJECT-TYPE
	SYNTAX INTEGER
        ACCESS read-write
        STATUS mandatory
        DESCRIPTION
        	"Moves the lower left corner of the image downward 
		    from 0 to 300 dots (1 inch at a resolution of 300 
		    dpi). Use this option to eliminate clipping of the top 
		    edge of the image on some systems.

		    Range
			    0-300

		    Default
			    75"
        ::= { qmsDECLN03 10 }

qmsDECLN03Reset OBJECT-TYPE
	SYNTAX	INTEGER {
		off(1),
		on(2)
	}
        ACCESS read-write
        STATUS mandatory
        DESCRIPTION
        	"Determines whether the printer automatically resets to the 
			initial power-up configuration before every print job or 
			whether it retains the configuration from the previous print 
			job.

			Choices
			    Off and On

			Default
			    Off"
        ::= { qmsDECLN03 12 }

qmsDECLN03Orientation OBJECT-TYPE
	SYNTAX	INTEGER {
		portrait(1),
		landscape(2)
	}
        ACCESS read-write
        STATUS mandatory
        DESCRIPTION
        	"Sets the printing direction of the print media.

		    Choices
			    Portrait: Prints the Y axis parallel to the long edge of 
			              the page.

			    Landscape: Prints the Y axis parallel to the short 
			               edge of the page.

		    Default
			    Portrait"
        ::= { qmsDECLN03 14 }

------------------------------------------------------------------------------
-- QMS QUIC2 Emulation Option Handles
------------------------------------------------------------------------------

qmsQUIC2CommandCharacter OBJECT-TYPE
	SYNTAX INTEGER (32..255)
	ACCESS read-write
	STATUS mandatory
	DESCRIPTION
		"This option specifies the default command character. 
		Enter the decimal value of the QUIC II command character. 
		The options range from 32 to 255 with the exception of 
		78 (N) and 110 (n). The default is 94 (^)."
	::= { qmsQUIC2 4 }

qmsQUIC2TopMargin OBJECT-TYPE
	SYNTAX INTEGER (0..9999)
	ACCESS read-write
	STATUS mandatory
	DESCRIPTION
		"This option specifies the default top page margin in 
		dots. The available range of options is from 0000 to 9999.
		The default is 0060."
	::= { qmsQUIC2 6 }

qmsQUIC2BottomMargin OBJECT-TYPE
	SYNTAX INTEGER (0..9999)
	ACCESS read-write
	STATUS mandatory
	DESCRIPTION
		"This option specifies in dots the default bottom page
		margin. The available range of options is from 0000 to 
		9999. The default is 0060. The status page displays it 
		as the displacement from the top of the page."
	::= { qmsQUIC2 8 }

qmsQUIC2LeftMargin OBJECT-TYPE
	SYNTAX INTEGER (0..9999)
	ACCESS read-write
	STATUS mandatory
	DESCRIPTION
		"This option specifies the default left page margin in 
		dots. The available range of options is from 0000 to 
		9999. The default is 0060."
	::= { qmsQUIC2 10 }

qmsQUIC2RightMargin OBJECT-TYPE
	SYNTAX INTEGER (0..9999)
	ACCESS read-write
	STATUS mandatory
	DESCRIPTION
		"This option specifies the default right page margin in 
		dots. The available range of options is from 0000 to 9999. 
		The default is 0060.  The status page displays it as the 
		displacement from the top of the page."
	::= { qmsQUIC2 12 }

qmsQUIC2IfParam OBJECT-TYPE
	SYNTAX	INTEGER {
		immediateErase(1),
		immediateEject(2),
		onPageEject(3)
	}
	ACCESS read-write
	STATUS mandatory
	DESCRIPTION
		"This option determines when the printer pulls paper from a 
		different input tray when the ^IF Paper Handling command is 
		used.  
		
		The options are 
			* Immediate/Erase (when the ^IF command is encountered, 
			  the input tray is immediately selected, and any 
			  images on the current page prior to the ^IF command 
			  are not printed) 

			* Immediate/Eject (when the ^IF command is encountered, 
			  the current page is immediately ejected using current 
			  input tray, and subsequent pages are printed using the 
			  newly requested input tray)

			* On Page Eject (when the ^IF command is encountered, 
			  the current page is printed using the current input 
			  tray, and when a page ejection is encountered, such as 
			  a Form Feed command or exceeding the bottom margin, 
			  the subsequent pages print from the newly requested 
			  input tray). The default is On Page Eject."
	::= { qmsQUIC2 14 }

qmsQUIC2CReqCRLF OBJECT-TYPE
	SYNTAX	INTEGER {
		crEQcrANDlf(2),
		crEQcr(1)
	}
	ACCESS read-write
	STATUS mandatory
	DESCRIPTION
		"This option determines whether a line feed is added to 
		each carriage return received by the printer. The 
		selection affects system carriage return control mode 
		(0D) as well as QUIC II Carriage Return commands 
		(^-). The options are CR and CR+LF. The default is CR."
	::= { qmsQUIC2 15 }

qmsQUIC2LFeqLFCR OBJECT-TYPE
	SYNTAX	INTEGER {
		lfEQlfANDcr(2),
		lfEQlf(1)
	}
	ACCESS read-write
	STATUS mandatory
	DESCRIPTION
		"This option determines whether or not a carriage return 
		is added to each line feed received by the printer. The 
		selection affects system Line Feed Control commands 
		as well as QUIC II Line Feed Control commands. The options 
		are LF and LF+CR. The default is LF+CR."
	::= { qmsQUIC2 16 }

qmsQUIC2Decimal OBJECT-TYPE
	SYNTAX	INTEGER {
		implicitLeft(1),
		implicitRight(2),
		explicit(3)
	}
	ACCESS read-write
	STATUS mandatory
	DESCRIPTION
		"This option selects whether implicit decimal values are 
		interpreted as left- or right-justified or whether explicit 
		decimals are inserted in QUIC II commands. Refer to the 
		QUICII documentation for information about left- and 
		right-justified implicit decimal values and inserting 
		explicit decimals in QUIC II commands. The options are 
		Implicit/Left (interpret implicit decimal values as 
		left-justified), Implicit/Right (interpret implicit decimal 
		values as right-justified), and Explicit (use explicit decimals 
		in values). The default is Implicit/Left."
	::= { qmsQUIC2 17 }

qmsQUIC2Dimensions OBJECT-TYPE
	SYNTAX	INTEGER {
		dots(1),
		centimeters(2),
		inches(3)
	}
	ACCESS read-write
	STATUS mandatory
	DESCRIPTION
		"This option determines whether dimensions in QUIC 
		II commands are interpreted as inches, centimeters, or 
		dots. Refer to the QUICII documentation for information. 
		The options are Centimeters, Inches, and Dots. The default 
		is Inches."
	::= { qmsQUIC2 18 }

qmsQUIC2EDPMode OBJECT-TYPE
	SYNTAX	INTEGER {
		on(2),
		off(1)
	}
	ACCESS read-write
	STATUS mandatory
	DESCRIPTION
		"This option specifies the lines-per-inch setting used in 
		QUIC II Line Printer mode. The default uses the setting 
		of the Lines Per Inch option. The options are On (66 
		lines/page regardless of page orientation) and Off (use 
		default lines-per-inch setting). The default is Off."
	::= { qmsQUIC2 19 }

qmsQUIC2DefaultFont OBJECT-TYPE
	SYNTAX INTEGER (0..32767)
	ACCESS read-write
	STATUS mandatory
	DESCRIPTION
		"This option specifies a default font to be active when 
		QUIC II is entered. It also is the default font for QUIC 
		II Line Printer mode. Refer the QUICII documentation for 
		additional information about fonts. Enter the font number 
		for default font. The range is from 00000 to 32767. The 
		default font is number 0938 (Q-Format)."
	::= { qmsQUIC2 20 }

qmsQUIC2LineSpacing OBJECT-TYPE
	SYNTAX	INTEGER {
		lpi6(1),
		lpi8(2)
	}
	ACCESS read-write
	STATUS mandatory
	DESCRIPTION
		"This option selects the lines-per-inch setting to be used 
		for printing. Refer to the QUICII documentation for information. 
		The options are 6 (6 lines/inch) and 8 (8 lines/inch). The 
		default is 8."
	::= { qmsQUIC2 22 }

qmsQUIC2Orientation OBJECT-TYPE
	SYNTAX	INTEGER {
		portrait(1),
		landscape(2)
	}
	ACCESS read-write
	STATUS mandatory
	DESCRIPTION
		"This option controls the direction of printing on the 
		page. Portrait orientation is 0 deg. rotation and landscape 
		orientation is 270 deg. rotation. Refer to the QUICII 
		documentation for information about page orientation. 
		The options are Portrait and Landscape. The default is Portrait."
	::= { qmsQUIC2 23 }

qmsQUIC2Scan OBJECT-TYPE
	SYNTAX	INTEGER {
		on(2),
		off(1)
	}
	ACCESS read-write
	STATUS mandatory
	DESCRIPTION
		""
	::= { qmsQUIC2 24 }

qmsQUIC2Spaces OBJECT-TYPE
	SYNTAX	INTEGER {
		on(2),
		off(1)
	}
	ACCESS read-write
	STATUS mandatory
	DESCRIPTION
		"This option allow you to ignore leading/trailing spaces 
		in numeric values. The options are On (absorb leading/
		trailing spaces) and Off (do not absorb leading/trailing 
		spaces). The default is Off."
	::= { qmsQUIC2 25 }

qmsQUIC2AllowDataRepeats OBJECT-TYPE
	SYNTAX	INTEGER {
		on(2),
		off(1)
	}
	ACCESS read-write
	STATUS mandatory
	DESCRIPTION
		"This option enables or disables the ^DR Data Repeat 
		command. Refer to the QUICII documentation for 
		information about this command. The options are On 
		(allow Data Repeat commands) and Off (ignore Data 
		Repeat commands). The default is On."
	::= { qmsQUIC2 26 }

qmsQUIC2AllowOverlays OBJECT-TYPE
	SYNTAX	INTEGER {
		on(2),
		off(1)
	}
	ACCESS read-write
	STATUS mandatory
	DESCRIPTION
		"This option enables or disables all Overlay commands. 
		Refer to the QUICII documentation for information about 
		overlays. The options are On (allow Overlay commands) 
		and Off (do not allow Overlay commands). The default is On."
	::= { qmsQUIC2 27 }

qmsQUIC2AllowPageCopies OBJECT-TYPE
	SYNTAX	INTEGER {
		on(2),
		off(1)
	}
	ACCESS read-write
	STATUS mandatory
	DESCRIPTION
		"This option enables or disables the Multiple Copy 
		command. Refer to the QUICII documentation for additional 
		information. The options are On (allow multiple or continuous 
		copies) and Off (do not allow multiple or continuous 
		copies). The default is On."
	::= { qmsQUIC2 28 }

qmsQUIC2SaveDLF OBJECT-TYPE
	SYNTAX	INTEGER {
		on(2),
		off(1)
	}
	ACCESS read-write
	STATUS mandatory
	DESCRIPTION
		"This option allows you to choose whether or not all 
		downloaded fonts are retained on disk. If this option is 
		not enabled and the power is turned off, the fonts are 
		lost. Refer to the QUICII documentation for information 
		about downloaded fonts. The options are On (save downloaded 
		fonts) or Off (do not save downloaded fonts). The default is Off."
	::= { qmsQUIC2 29 }

qmsQUIC2SaveOverlays OBJECT-TYPE
	SYNTAX	INTEGER {
		on(2),
		off(1)
	}
	ACCESS read-write
	STATUS mandatory
	DESCRIPTION
		"This option allows you to choose whether or not all 
		overlays are retained on disk. If this option is not 
		enabled and the power is turned off, the overlays are 
		lost. Refer to the QUICII documentation for information 
		about overlays. The options are On (save overlays) or 
		Off (do not save overlays). The default is Off."
	::= { qmsQUIC2 30 }

qmsQUIC2DefaultMode OBJECT-TYPE
	SYNTAX	INTEGER {
		linePrinter(1),
		commandFree(2),
		commandNoFree(3)
	}
	ACCESS read-write
	STATUS mandatory
	DESCRIPTION
		"This option selects QUIC II Line Printer mode or QUIC 
		II command mode with or without Free Format. Refer to 
		the QUICII documentation for information on the two 
		modes and on Free Format. The options are Line Printer 
		(enter QUIC II Line Printer mode), Command/
		Free, (enter QUIC II mode with Free Format on), or 
		Command/No Free (enter QUIC II mode with Free 
		Format off). The default is Line Printer."
	::= { qmsQUIC2 31 }

qmsQUIC2RebuildFontTable OBJECT-TYPE
	SYNTAX	INTEGER {
		on(2),
		off(1)
	}
	ACCESS read-write
	STATUS mandatory
	DESCRIPTION
		"This option determines whether or not characters that 
		have been inserted into downloaded fonts with a Font 
		Definition command (^DFA) are erased or retained when 
		QUIC II is entered. Refer to the QUICII documentation 
		for information about inserted characters in downloaded 
		fonts. The options are On (retain inserted characters) 
		or Off (do not retain inserted characters). The default 
		is Off."
	::= { qmsQUIC2 32 }

qmsQUIC2TrayMap1 OBJECT-TYPE
	SYNTAX INTEGER (1..5)
	ACCESS read-write
	STATUS mandatory
	DESCRIPTION
		"Map Tray 1 To:"
	::= { qmsQUIC2 33 }

qmsQUIC2TrayMap2 OBJECT-TYPE
	SYNTAX INTEGER (1..5)
	ACCESS read-write
	STATUS mandatory
	DESCRIPTION
		"Map Tray 2 To:"
	::= { qmsQUIC2 34 }

qmsQUIC2TrayMap3 OBJECT-TYPE
	SYNTAX INTEGER (1..5)
	ACCESS read-write
	STATUS mandatory
	DESCRIPTION
		"Map Tray 3 To:"
	::= { qmsQUIC2 35 }

qmsQUIC2TrayMap4 OBJECT-TYPE
	SYNTAX INTEGER (1..5)
	ACCESS read-write
	STATUS mandatory
	DESCRIPTION
		"Map Tray 4 To:"
	::= { qmsQUIC2 36 }

qmsQUIC2TrayMap5 OBJECT-TYPE
	SYNTAX      INTEGER (1..5)
	ACCESS  read-write
	STATUS mandatory
	DESCRIPTION
		"Map Tray 5 To:"
	::= { qmsQUIC2 37 }

qmsQUIC2PatternType OBJECT-TYPE
	SYNTAX	INTEGER {
		opaque(1),
		transparent(2)
	}
	ACCESS  read-write
	STATUS mandatory
	DESCRIPTION
		"This option allows the patterns to be either opaque or transparent. The
		default value is opaque."
	::= { qmsQUIC2 38 }

------------------------------------------------------------------------------
-- QMS Lineprinter Emulation Option Handles
------------------------------------------------------------------------------

qmsLPFont OBJECT-TYPE
        SYNTAX DisplayString (SIZE (0..32))
        ACCESS read-write
        STATUS mandatory
        DESCRIPTION
        	"Sets the printer fonts for the current print job. Any PostScript fonts 
			available on the printer can be used. To see a list of available Post-
			Script fonts, print an advanced status page through the printer config-
			uration menu.

			Choices
			    All printer-resident PostScript fonts.

			Default
			    Courier"
        ::= { qmsLinePrinter 46 }

qmsLPPointSize OBJECT-TYPE
	SYNTAX INTEGER (0..99999)
        ACCESS read-write
        STATUS mandatory
        DESCRIPTION
	        "Sets the five-digit value used to specify the point size of the font for 
			the current print job.

			Choices
			    00000-99999 

			Default
			    00880 (8.8 points)"
        ::= { qmsLinePrinter 4 }

qmsLPAsciiMap OBJECT-TYPE
        SYNTAX INTEGER {
		ascii(2),
		ebcdic(1)
	}
        ACCESS read-write
        STATUS mandatory
        DESCRIPTION
		"Specifies the type of character map to be used.

		Choices
			ASCII, EBCDIC, PC ASCII, PC Multilingual

		Default
			ASCII

		Note
			If you select the PC ASCII or PC Multilingual character 
			map, special PostScript fonts will be substituted for the 
			lineprinter character map."
        ::= { qmsLinePrinter 32 }

qmsLPLineNumbering OBJECT-TYPE
        SYNTAX INTEGER {
		on(2),
		off(1)
	}
        ACCESS read-write
        STATUS mandatory
        DESCRIPTION
		"Specifies that a five-digit number is to be prefixed to each 
		line.

		Choices
			On: Number all lines.
			Off: Don't number lines.

		Default
			Off"
        ::= { qmsLinePrinter 34 }

qmsLPTabStops OBJECT-TYPE
	SYNTAX INTEGER (0..256)
        ACCESS read-write
        STATUS mandatory
        DESCRIPTION
        	"Specifies the number of spaces between tab stops.

		Choices
			0-256

		Default
			8"
        ::= { qmsLinePrinter 8 }

qmsLPLFisCRLF OBJECT-TYPE
        SYNTAX INTEGER {
		on(2),
		off(1)
	}
        ACCESS read-write
        STATUS mandatory
        DESCRIPTION
	        "Stipulates whether each line feed (LF) in the print job is translated
		to a carriage return/line feed (CRLF) combination.

		Choices
			On: Translate all line feeds to carriage return/line feed 
			    combinations.

			Off: Use line feeds only as line feeds.

		Default
			On"
        ::= { qmsLinePrinter 36 }

qmsLPCRisCRLF OBJECT-TYPE
        SYNTAX INTEGER {
		on(2),
		off(1)
	}
        ACCESS  read-write
        STATUS mandatory
        DESCRIPTION
        	"Stipulates whether each carriage return (CR) in the print job is trans-
		lated to a carriage return/line feed (CRLF) combination.

		Choices
			On: Translate all carriage returns to line feeds.
			Off: Use carriage returns only as carriage returns.

	Default
		Off"
        ::= { qmsLinePrinter 38 }

qmsLPFFisCRFF OBJECT-TYPE
        SYNTAX INTEGER {
		on(2),
		off(1)
	}
        ACCESS  read-write
        STATUS mandatory
        DESCRIPTION
        	"Stipulates whether each form feed (FF) in the print job is translated to 
		a carriage return/form feed (CRFF) combination.

		Choices
			On: Translate all form feeds to carriage return/form 
			    feed combinations.

			Off: Use form feeds only as form feeds.

		Default
			On"
        ::= { qmsLinePrinter 40 }

qmsLPOrientation OBJECT-TYPE
        SYNTAX INTEGER {
		portrait(1),
		landscape(2)
	}
        ACCESS  read-write
        STATUS mandatory
        DESCRIPTION
        	"Specifies whether text and graphics are placed on the page in a por-
		trait or landscape orientation.

		Choices
			Landscape
		Portrait

		Default
			Portrait"
        ::= { qmsLinePrinter 42 }

qmsLPLineWrap OBJECT-TYPE
        SYNTAX INTEGER {
		on(2),
		off(1)
	}
        ACCESS  read-write
        STATUS mandatory
        DESCRIPTION
		"Indicates whether long lines are to be wrapped to the next line instead 
		of being truncated.

		Choices
			On: Wrap long lines.
			Off: Truncate long lines.

		Default
			On"
        ::= { qmsLinePrinter 44 }

qmsLPLinesPerPage OBJECT-TYPE
	SYNTAX      INTEGER (1..128)
        ACCESS  read-write
        STATUS mandatory
        DESCRIPTION
        	"Specifies the number of lines printed on a page before an automatic 
		page eject. Interline spacing is set to the selected point size. Logical 
		pages consisting of more lines than specified are split into multiple 
		pages.

		Choices
			1-128

		Default
			87"
        ::= { qmsLinePrinter 12 }

qmsLPLeftMargin OBJECT-TYPE
	SYNTAX      INTEGER (0..79200)
        ACCESS  read-write
        STATUS mandatory
        DESCRIPTION
	        "Defines the left margin in 1/7200'' increments.

		Choices
			Left    0-79200 (0''-11.00'') 

		Default
			Left    0

		Note
			The margins are in 1/7200 increments (79200 is 11.00'' 
			in 1/7200'' increments."
        ::= { qmsLinePrinter 16 }

qmsLPRightMargin OBJECT-TYPE
	SYNTAX      INTEGER (0..79200)
        ACCESS  read-write
        STATUS mandatory
        DESCRIPTION
        	"Defines the right margin in 1/7200'' increments.

		Choices
			Right    0-79200 (0''-11.00'')

		Default
			Right    0

		Note
			The margins are in 1/7200 increments (79200 is 11.00'' 
			in 1/7200'' increments."
        ::= { qmsLinePrinter 20 }

qmsLPTopMargin OBJECT-TYPE
	SYNTAX      INTEGER (0..79200)
        ACCESS  read-write
        STATUS mandatory
        DESCRIPTION
        	"Defines the top margin in 1/7200'' increments.

		Choices
			Top    0-79200 (0''-11.00'')

		Default
			Top    0

		Note
			The margins are in 1/7200 increments (79200 is 11.00'' 
			in 1/7200'' increments."
        ::= { qmsLinePrinter 24 }

qmsLPBottomMargin OBJECT-TYPE
	SYNTAX      INTEGER (0..79200)
        ACCESS  read-write
        STATUS mandatory
        DESCRIPTION
        	"Defines the bottom margin in 1/7200'' increments.

		Choices
			Bottom    0-79200 (0''-11.00'') 

		Default
			Bottom    0

		Note
			The margins are in 1/7200 increments (79200 is 11.00'' 
			in 1/7200'' increments."
        ::= { qmsLinePrinter 28 }

------------------------------------------------------------------------------
-- QMS TIFF Emulation Option Handles
------------------------------------------------------------------------------

qmsTIFFAutoRotation OBJECT-TYPE
	SYNTAX	INTEGER {
		off(1),
		rot90(2),
		rot270(3),
	        rot180(4)
	}
	ACCESS  read-write
	STATUS mandatory
	DESCRIPTION
		"Allows you to specify whether the TIFF image should be automatically 
		rotated 90 degrees if this would result in a better fit on the 
		currently selected paper size.

		Choices
			Off, 90, 270, 180

		Default
			90"
	::= { qmsTIFF 1 }

qmsTIFFScratchFileSize OBJECT-TYPE
        SYNTAX INTEGER (0..255)
	ACCESS  read-write
	STATUS mandatory
	DESCRIPTION
		"Allows you to define the size of the scratch file (in MB) that is 
		created on the printer's hard disk to contain the image during 
		processing.

		Choices
			0: No scratch file is created, and the data is 
			   processed from the host input spool buffer as 
			   it is received.

			1-255: The data is written to the scratch file if there 
			       is not enough room in the host input spool 
			       buffer to hold it.

		Default
			0"
	::= { qmsTIFF 2 }

qmsTIFFPaperToImage OBJECT-TYPE
	SYNTAX	INTEGER {
		on(2),
		off(1)
	}
	ACCESS  read-write
	STATUS mandatory
	DESCRIPTION
		"Allows you to specify whether the TIFF emulation should 
		automatically select the paper size closest to the image 
		size rather than using the default paper size.

		Choices
			Off, On

		Default
			On"
	::= { qmsTIFF 3 }

qmsTIFFAnnotationState OBJECT-TYPE
	SYNTAX	INTEGER {
		disabled(1),
		enabled(2)
	}
	ACCESS  read-write
	STATUS mandatory
	DESCRIPTION
		"Allows you to enable or disable annotation.

		 Choices
			Enabled, Disabled

		Default
			Disabled"
	::= { qmsTIFF 4 }

qmsTIFFAnnotationTag OBJECT-TYPE
        SYNTAX INTEGER (0..65000)
	ACCESS  read-write
	STATUS mandatory
	DESCRIPTION
		"Identifies the annotation tag number. 

		Choices
			0-65000

		Default
			1000"
	::= { qmsTIFF 5 }

qmsTIFFReverseImage OBJECT-TYPE
	SYNTAX INTEGER {
		off(1),
		on(2)
	}
	ACCESS  read-write
	STATUS mandatory
	DESCRIPTION
		"Allows you to turn reverse image 'on' or 'off'.

		 Choices
			on, off

		Default
			off"
	::= { qmsTIFF 7 }

qmsTIFFAutoScaling OBJECT-TYPE
	SYNTAX	INTEGER {
 		off(1),
 		upANDdown(2),
 		upOnly(3),
 		downOnly(4)
 	}
 	ACCESS  read-write
 	STATUS mandatory
 	DESCRIPTION
 		"Allows you to specify whether the TIFF image should be scaled 
 		(up or down) to fit on the currently selected paper size.
 
 		Choices
 			Off, Down Only, Up Only, Up & Down
 
 		Default
 			Up & Down"
 	::= { qmsTIFF 50 }

------------------------------------------------------------------------------
-- QMS CALS Emulation Option Handles
------------------------------------------------------------------------------

qmsCALSAutoRotation OBJECT-TYPE
	SYNTAX	INTEGER {
	        off(1),
        	rot90(2),
	        rot270(3),
        	rot180(4)
	}
	ACCESS  read-write
	STATUS mandatory
	DESCRIPTION
		"Allows you to specify whether the CALS image should be automatically 
		rotated 90 degrees if this would result in a better fit on the 
		currently selected paper size

		Choices
			Off, 90, 270, 180

		Default
			90"
	::= { qmsCALS 1 }

qmsCALSAutoScaling OBJECT-TYPE
	SYNTAX	INTEGER {
	        off(1),
        	upANDdown(2),
	        upOnly(3),
        	downOnly(4)
 	}
 	ACCESS  read-write
 	STATUS mandatory
 	DESCRIPTION
 		"Allows you to specify whether the CALS image should be 
 		automatically scaled (up or down) to fit on the currently selected 
 		paper size.
 
 		Choices
 			Off,  Up & Down, Up Only, Down Only
 
 		Default
 			Up & Down"
 	::= { qmsCALS 50 }

------------------------------------------------------------------------------
-- QMS CGM Emulation Option Handles
------------------------------------------------------------------------------

qmsCGMSuppressScale OBJECT-TYPE
	SYNTAX INTEGER {
		yes(2),
		no(1)
	}
        ACCESS read-write
        STATUS mandatory
        DESCRIPTION
        "Specifies whether the file should be scaled.

        Choices
            No:  The file is scaled.
            Yes: The file is NOT scaled. 

        Default
            No

        Notes
            If yes is Selected and a file with metric scaling is printed, the file 
            will not be scaled."
        ::= { qmsCGM 1 }

qmsCGMMono OBJECT-TYPE
	SYNTAX INTEGER {
		on(2),
		off(1)
	}
        ACCESS read-write
        STATUS mandatory
        DESCRIPTION
        "Specifies whether the file should be printed in monochrome or 
        color.

        Choices
            On:  The file prints in monochrome.
            Off: The file prints in color.

        Default
            Off

        Notes
            Off (color printing) is not available on monochrome printers."
        ::= { qmsCGM 2 }

qmsCGMIgnoreBorder OBJECT-TYPE
	SYNTAX INTEGER {
		yes(2),
		no(1)
	}
	ACCESS read-write
	STATUS mandatory
	DESCRIPTION
		"Causes the non-printable area of a page to be ignored.

                Choices
                    Yes, No

                Default
                    No

                Notes
                    If the non-printable area is ignored, the image is shifted up and to 
                    the right."
	::= { qmsCGM 3 }

qmsCGMOriginX OBJECT-TYPE
	SYNTAX INTEGER (0..1700)
        ACCESS read-write
        STATUS mandatory
        DESCRIPTION
        "The viewport origin, along with the viewport size, determines the paper size selected.
        The image is scaled to fit within the specified viewport.
        Specifies the X origin of the CGM viewport in .01'' increments.

        Choices
            0-1700 (0''-17.00'')

        Default
            100 (1'')"
        ::= { qmsCGM 4 }

qmsCGMOriginY OBJECT-TYPE
	SYNTAX INTEGER (0..1700)
        ACCESS read-write
        STATUS mandatory
        DESCRIPTION
        "The viewport origin, along with the viewport size, determines the paper size selected.
        The image is scaled to fit within the specified viewport.
        Specifies the Y origin of the CGM viewport in .01'' increments.

        Choices
            0-1700 (0''-17.00'')

        Default
            100 (1'')"
        ::= { qmsCGM 8 }

qmsCGMPrintErrors OBJECT-TYPE
	SYNTAX INTEGER {
		yes(2),
		no(1)
	}
	ACCESS read-write
	STATUS mandatory
	DESCRIPTION
	"Causes an additional page, listing errors encountered, to print if 
        a CGM job contains errors.

        Choices
            Yes, No

        Default
            No"
	::= { qmsCGM 12 }

-- END
qmsRel		OBJECT IDENTIFIER ::= { qmsInc 2 }

------------------------------------------------------------------------------
-- QMS REL Groups
------------------------------------------------------------------------------
qmsPrinter	OBJECT IDENTIFIER ::= { qmsRel 1 }
qmsIF 		OBJECT IDENTIFIER ::= { qmsRel 9 }
qmsConfig	OBJECT IDENTIFIER ::= { qmsRel 10}

-- Groups in the QMS-MIB

qmsPtrSys	OBJECT IDENTIFIER ::= { qmsPrinter 1 }
qmsPtrEmu	OBJECT IDENTIFIER ::= { qmsPrinter 2 }
qmsPtrJobs	OBJECT IDENTIFIER ::= { qmsPrinter 3 }

qmsIFAdmin	OBJECT IDENTIFIER ::= { qmsIF 1 }
qmsIFSetup	OBJECT IDENTIFIER ::= { qmsIF 2 }

qmsIFConfig        OBJECT IDENTIFIER ::= { qmsIFSetup 1 }
qmsIFNetware       OBJECT IDENTIFIER ::= { qmsIFSetup 5 }
qmsIFApple         OBJECT IDENTIFIER ::= { qmsIFSetup 6 }
qmsIFSnmpcontrol   OBJECT IDENTIFIER ::= { qmsIFSetup 8 }
qmsIFLservlmgr     OBJECT IDENTIFIER ::= { qmsIFSetup 9 }

qmsCfgUser	OBJECT IDENTIFIER ::= {qmsConfig 10}
qmsCfgAdmin	OBJECT IDENTIFIER ::= {qmsConfig 20}
qmsCfgSecurity	OBJECT IDENTIFIER ::= {qmsConfig 30}

-- The System Group

qmsPtrSysStatus OBJECT-TYPE
	SYNTAX	DisplayString (SIZE (0..255))
	ACCESS	read-only
	STATUS	mandatory
	DESCRIPTION
			"A text string indicating the current printer status."
	::= { qmsPtrSys 1 }

qmsPtrSysNamePrinter OBJECT-TYPE
	SYNTAX	DisplayString (SIZE (0..255))
	ACCESS	read-only
	STATUS	optional
	DESCRIPTION
			"A text string indicating the current printer name."
	::= { qmsPtrSys 2 }

-- The Interfaces Table

qmsPtrIfTable OBJECT-TYPE
	SYNTAX	SEQUENCE OF QMSPtrIfEntry
	ACCESS	not-accessible
	STATUS	mandatory
	DESCRIPTION
			"A list of interfaces supported by this printer and
			their currently selected default emulations."
	::= { qmsPtrSys 3 }

qmsPtrIfEntry OBJECT-TYPE
	SYNTAX	QMSPtrIfEntry
	ACCESS	not-accessible
	STATUS	mandatory
	DESCRIPTION
			"An interface entry containing an interface and it
			currently selected dafault emulation."
	INDEX	{ qmsPtrIfIndex }
	::= { qmsPtrIfTable 1 }

QMSPtrIfEntry ::=
	SEQUENCE {
		qmsPtrIfIndex
			INTEGER,
		qmsPtrIfName
			DisplayString (SIZE (0..255)),
		qmsPtrIfDefEmu
			INTEGER
	}

qmsPtrIfIndex OBJECT-TYPE
	SYNTAX	INTEGER
	ACCESS	read-only
	STATUS	mandatory
	DESCRIPTION
			"A unique value for each interface.  Its value ranges between 1
			and the number of intrfaces, qmsPtrIfNumber.  This value must
			remain the same between successive printer power cycles."
	::= { qmsPtrIfEntry 1 }

qmsPtrIfName OBJECT-TYPE
	SYNTAX	DisplayString (SIZE (0..255))
	ACCESS	read-only
	STATUS	mandatory
	DESCRIPTION
			"The name of the interface."
	::= { qmsPtrIfEntry 2 }

qmsPtrIfDefEmu OBJECT-TYPE
	SYNTAX	INTEGER {
				ultrascript(1),		--  following values have been incremented by one in
				ibm-proprinter(2),	--  observance of the rule against using an OID of 0.
				diablo-630(3),
				ti-855(4),
				hp-gl(5),
				hp-pcl(6),
				hex-dump(7),
				ti-855-dp(8),
				ti-810(9),
				epson-fx(10),
				dec-ansi(11),
				ibm-ext-ascii(12),
				ln03(13),
				tektronix-4014(14),
				quic-2(15),
				impress(16),
				code-v(17),
				r1(18),
				ccitt(19),
				line-printer(20),
				hp-pcl-5(21),
				esp(201),
				not-supported(65534),	--  Special case, this variable not supported by the printer.
				wild-card(65535)		--  Left at original value to stay within a word.
			}
	ACCESS	read-only
	STATUS	mandatory
	DESCRIPTION
			"The name of the currently selected default emulation
			for this interface."
	::= { qmsPtrIfEntry 3 }

-- The Input/Output Bins Table

qmsPtrBinTable OBJECT-TYPE
	SYNTAX	SEQUENCE OF QMSPtrBinEntry
	ACCESS	not-accessible
	STATUS	mandatory
	DESCRIPTION
			"A list of input/output paper trays supported by
			this printer and their currently selected paper sizes
			and bin names.  Note: paper sizes are not assigned to
			output paper trays."
	::= { qmsPtrSys 4 }

qmsPtrBinEntry OBJECT-TYPE
	SYNTAX	QMSPtrBinEntry
	ACCESS	not-accessible
	STATUS	mandatory
	DESCRIPTION
			"A paper tray entry containing its currently selected
			default paper size and paper tray name."
	INDEX	{ qmsPtrBinIndex }
	::= { qmsPtrBinTable 1 }

QMSPtrBinEntry ::=
	SEQUENCE {
		qmsPtrBinIndex		INTEGER,
		qmsPtrBinType		INTEGER,
		qmsPtrBinId			INTEGER,
		qmsPtrBinPaper		DisplayString (SIZE (0..255)),
		qmsPtrBinName		DisplayString (SIZE (0..255))
	}

qmsPtrBinIndex OBJECT-TYPE
	SYNTAX	INTEGER
	ACCESS	read-only
	STATUS	mandatory
	DESCRIPTION
			"A unique value for each input/output bin.  Its value ranges
			between 1 and the number of input/output bins, qmsPtrBinNumber.
			This value must remain the same between successive printer power
			cycles."
	::= { qmsPtrBinEntry 1 }

qmsPtrBinType OBJECT-TYPE
	SYNTAX	INTEGER {
			output(1),	-- must use as passed by the MB.
			input(2)	-- was "output(0), input(1)"
			}
	ACCESS	read-only
	STATUS	mandatory
	DESCRIPTION
			"The input/output tray designator (input=1, output=0)."
	::= { qmsPtrBinEntry 2 }

qmsPtrBinId OBJECT-TYPE
	SYNTAX	INTEGER
	ACCESS	read-only
	STATUS	mandatory
	DESCRIPTION
			"The input tray designator."
	::= { qmsPtrBinEntry 3 }

qmsPtrBinPaper OBJECT-TYPE
	SYNTAX	DisplayString (SIZE (0..255))
	ACCESS	read-only
	STATUS	mandatory
	DESCRIPTION
			"The name of the currently selected paper size for this
			paper tray (applies to input paper trays only)."
	::= { qmsPtrBinEntry 4 }

qmsPtrBinName OBJECT-TYPE
	SYNTAX	DisplayString (SIZE (0..255))
	ACCESS	read-only
	STATUS	mandatory
	DESCRIPTION
			"The name currently assigned to this paper tray."
	::= { qmsPtrBinEntry 5 }

-- The Emulations Group

-- The Jobs Group
-- The Current Job

qmsPtrJobsCurStatus OBJECT-TYPE
	SYNTAX	INTEGER {
					spooling(1),
					interpreting(2),
					rasterizing(4),
					printing(8),
					terminating(16),
					waiting(32),
					spooled(64),
                                        printed(128),
                                        canceled(256),
					internal(32768)
				}
		ACCESS	read-only
		STATUS	mandatory
		DESCRIPTION
				"The current job entries status."
		::= { qmsPtrJobs 1 }

	qmsPtrJobsCurSheet OBJECT-TYPE
		SYNTAX	INTEGER
		ACCESS	read-only
		STATUS	mandatory
		DESCRIPTION
				"The sheet being imaged for the current job."
		::= { qmsPtrJobs 2 }

	qmsPtrJobsCurPage OBJECT-TYPE
		SYNTAX	INTEGER
		ACCESS	read-only
		STATUS	mandatory
		DESCRIPTION
				"The page being imaged for the current job."
		::= { qmsPtrJobs 3 }

-- The Jobs Table
-- (includes all jobs currently being processed by the printer)

qmsPtrJobsTable OBJECT-TYPE
	SYNTAX	SEQUENCE OF QMSPtrJobsEntry
	ACCESS	not-accessible
	STATUS	mandatory
	DESCRIPTION
			"A list of the status, byte size, emulation, page number,
			sheet number, channel number, comment string, job title,
			and job originator string for all jobs currently being
			processed by the printer."
	::= { qmsPtrJobs 4 }

qmsPtrJobsEntry OBJECT-TYPE
	SYNTAX	QMSPtrJobsEntry
	ACCESS	not-accessible
	STATUS	mandatory
	DESCRIPTION
			"The current job entry containing its current status, sheet
			number, and page number."
	INDEX	{ qmsPtrJobsIndex }
	::= { qmsPtrJobsTable 1 }

QMSPtrJobsEntry ::=
	SEQUENCE {
		qmsPtrJobsIndex				INTEGER,
		qmsPtrJobsStatus			INTEGER,
		qmsPtrJobsEmulation			INTEGER,
		qmsPtrJobsPage				INTEGER,
		qmsPtrJobsSheet				INTEGER,
		qmsPtrJobsChannel			INTEGER,
		qmsPtrJobsComment			DisplayString (SIZE (0..255)),
		qmsPtrJobsTitle				DisplayString (SIZE (0..255)),
		qmsPtrJobsOwner				DisplayString (SIZE (0..255))
	}

qmsPtrJobsIndex OBJECT-TYPE
	SYNTAX	INTEGER
	ACCESS	read-only
	STATUS	mandatory
	DESCRIPTION
			"A unique value for each currently active job.  Its value ranges
			between 1 and the number of currently active jobs,
			qmsPtrJobsNumber.  This value must remain the same between
			successive printer power cycles."
	::= { qmsPtrJobsEntry 1 }

qmsPtrJobsStatus OBJECT-TYPE
	SYNTAX	INTEGER {
				spooling(1),
				interpreting(2),
				rasterizing(4),
				printing(8),
				terminating(16),
				waiting(32),
				spooled(64),
                                printed(128),
                                canceled(256),
				internal(32768)
			}
	ACCESS	read-only
	STATUS	mandatory
	DESCRIPTION
			"The job status."
	::= { qmsPtrJobsEntry 2 }

qmsPtrJobsEmulation OBJECT-TYPE
	SYNTAX	INTEGER {
				ultrascript(1),		-- actual value should be 0 (zero).
				ibm-proprinter(2),
				diablo-630(3),
				ti-855(4),
				hp-gl(5),
				hp-pcl(6),
				hex-dump(7),
				ti-855-dp(8),
				ti-810(9),
				epson-fx(10),
				dec-ansi(11),
				ibm-ext-ascii(12),
				ln03(13),
				tektronix-4014(14),
				quic-2(15),
				impress(16),
				code-v(17),
				r1(18),
				ccitt(19),
				line-printer(20),
				hp-pcl-5(21),
                                tiff(22),
                                cals(23),
                                cgm(25),
                                hp-pcl-xl(26),
				esp(201),
				wild-card(65536)
			}
	ACCESS	read-only
	STATUS	mandatory
	DESCRIPTION
			"The emulation selected for the processing of this job."
	::= { qmsPtrJobsEntry 4 }

qmsPtrJobsPage OBJECT-TYPE
	SYNTAX	INTEGER
	ACCESS	read-only
	STATUS	mandatory
	DESCRIPTION
			"The number of pages defined for this job.  Note: Sheets
			are defined as the physical sheet of paper as opposed to
			the number of logical page images appearing on the physical
			sheet of paper."
	::= { qmsPtrJobsEntry 5 }

qmsPtrJobsSheet OBJECT-TYPE
	SYNTAX	INTEGER
	ACCESS	read-only
	STATUS	mandatory
	DESCRIPTION
			"The number of sheets defined for this job.  Note: Sheets
			are defined as the physical sheet of paper as opposed to
			the number of logical page images appearing on the physical
			sheet of paper."
	::= { qmsPtrJobsEntry 6 }

qmsPtrJobsChannel OBJECT-TYPE
	SYNTAX	INTEGER {
				other(1),	-- was "other(0)"
				rs-232(12),
				parallel(13),
				appletalk(14),
				optional-io(16)
			}
	ACCESS	read-only
	STATUS	mandatory
	DESCRIPTION
			"The interface over which this job was communicated to
			the printer."
	::= { qmsPtrJobsEntry 7 }

qmsPtrJobsComment OBJECT-TYPE
	SYNTAX	DisplayString (SIZE (0..255))
	ACCESS	read-only
	STATUS	mandatory
	DESCRIPTION
			"A user defined text string sent with this job."
	::= { qmsPtrJobsEntry 8 }

qmsPtrJobsTitle OBJECT-TYPE
	SYNTAX	DisplayString (SIZE (0..255))
	ACCESS	read-only
	STATUS	mandatory
	DESCRIPTION
			"A user defined text string, usually the name of the job."
	::= { qmsPtrJobsEntry 9 }

qmsPtrJobsOwner OBJECT-TYPE
	SYNTAX	DisplayString (SIZE (0..255))
	ACCESS	read-only
	STATUS	mandatory
	DESCRIPTION
			"A user defined text string, usually the username of the
			person originating the job."
	::= { qmsPtrJobsEntry 10 }

-- The Job Completion Statistics
--     Accumulation of all jobs processed by the printer since the
--     last power-up.

qmsPtrJobsStatPages OBJECT-TYPE
	SYNTAX	INTEGER
	ACCESS	read-only
	STATUS	mandatory
	DESCRIPTION
			"The total number of pages printed for all jobs processed
			by the printer since the last power cycle.  Note: Sheets
			are defined as the physical sheet of paper as opposed to
			the number of logical page images appearing on the physical
			sheet of paper."
	::= { qmsPtrJobs 6 }

qmsPtrJobsStatSheets OBJECT-TYPE
	SYNTAX	INTEGER
	ACCESS	read-only
	STATUS	mandatory
	DESCRIPTION    
			"The total number of sheets printed for all jobs processed
			by the printer since the last power cycle.  Note: Sheets
			are defined as the physical sheet of paper as opposed to
			the number of logical page images appearing on the physical
			sheet of paper."
	::= { qmsPtrJobs 7 }



--- The Optional I/O Administration group

QmsIFAdminMenu ::= SEQUENCE {
        qmsIFAdminUnitStatus           INTEGER,
        qmsIFAdminConfigStatus         INTEGER,
        qmsIFAdminOldIntAddr           IpAddress
}

qmsIFAdminUnitStatus OBJECT-TYPE
        SYNTAX  INTEGER {
                running(1),
                resetOnNoClient(2),
                hardReset(3)
        }
        ACCESS  read-write
        STATUS  mandatory
        DESCRIPTION
        "The units's operational status.  A value other
		than (1) will reset the unit."
        ::= { qmsIFAdmin 1 }

qmsIFAdminConfigStatus OBJECT-TYPE
        SYNTAX  INTEGER {
                configUnknown1(1),
                configUnknown2(2),
                configLoadRequest(3),
                configSaveRequest(4),
                configDefaultRequest(5)
        }
        ACCESS  read-write
        STATUS  mandatory
        DESCRIPTION
        "The units's configuration status.
         read-only values:
           (1) reserved for future use.
           (2) reserved for future use.
         write-only values :
           (3) will load permanent values .
           (4) will save current configuration permanently.
           (5) load default configuration."
        ::= { qmsIFAdmin 2 }


qmsIFAdminOldIntAddr OBJECT-TYPE
        SYNTAX  IpAddress
        ACCESS  read-write
        STATUS  mandatory
        DESCRIPTION
        "The Internet Address at power-on or before change by
         RARP or 'arp -s'."
        ::= { qmsIFAdmin 3 }



--- The Optional I/O Configuration group
--- These objects correspond to the parameters of the product.

    -- The Configuration Menu

QmsIFConfigMenu ::= SEQUENCE {
        intAddr			IpAddress,
        ethAddr			NetworkAddress,
        defRout			IpAddress,
        netMask			IpAddress,
        tcpEnb			INTEGER,
        tftpEnb			INTEGER,
        tnPort			INTEGER,
        rtnOpt			INTEGER,
        trP1            INTEGER,
        bootP           INTEGER,
        rarp            INTEGER
}


intAddr OBJECT-TYPE
        SYNTAX  IpAddress
        ACCESS  read-write
        STATUS  mandatory
        DESCRIPTION
        "The Internet Address."
        ::= { qmsIFConfig 1 }

ethAddr OBJECT-TYPE
        SYNTAX  NetworkAddress
        ACCESS  read-only
        STATUS  mandatory
        DESCRIPTION
        "The Ethernet Address."
        ::= { qmsIFConfig 2 }

defRout OBJECT-TYPE
        SYNTAX  IpAddress
        ACCESS  read-write
        STATUS  mandatory
        DESCRIPTION
        "The Default Router."
        ::= { qmsIFConfig 3 }

netMask OBJECT-TYPE
        SYNTAX  IpAddress
        ACCESS  read-write
        STATUS  mandatory
        DESCRIPTION
        "The Net Mask."
        ::= { qmsIFConfig 4 }

tcpEnb  OBJECT-TYPE
        SYNTAX  INTEGER {
                no(1),
                yes(2)
        }
        ACCESS  read-write
        STATUS  mandatory
        DESCRIPTION
        "The TCP protocol stack enable switch."
        ::= { qmsIFConfig 5 }


tftpEnb OBJECT-TYPE
        SYNTAX  INTEGER {
                no(1),
                yes(2)
        }
        ACCESS  read-write
        STATUS  mandatory
        DESCRIPTION
        "The TFTP protocol enable switch."
        ::= { qmsIFConfig 13 }

tnPort  OBJECT-TYPE
        SYNTAX  INTEGER
        ACCESS  read-write
        STATUS  obsolete
        DESCRIPTION
        "The Telnet TCP Port.

        This object is obsolete."
        ::= { qmsIFConfig 16 }

rtnOpt  OBJECT-TYPE
        SYNTAX  INTEGER {
                no(1),
                yes(2)
        }
        ACCESS  read-write
        STATUS  obsolete
        DESCRIPTION
        "The Reverse Telnet option handling switch.

        This object is obsolete."
        ::= { qmsIFConfig 18 }

trP1  OBJECT-TYPE
        SYNTAX  INTEGER
        ACCESS  read-write
        STATUS  mandatory
        DESCRIPTION
        "The Transport 1 Port."
        ::= { qmsIFConfig 30 }

bootP  OBJECT-TYPE
        SYNTAX  INTEGER {
			yes(2),
			no(1)
        }
        ACCESS  read-write
        STATUS  mandatory
        DESCRIPTION
        "Boot Strap protocal enable/disable."
        ::= { qmsIFConfig 698 }

rarp  OBJECT-TYPE
        SYNTAX  INTEGER {
			yes(2),
			no(1)
        }
        ACCESS  read-write
        STATUS  mandatory
        DESCRIPTION
        "Reverse address resolution enable/disable."
        ::= { qmsIFConfig 699 }

spooling OBJECT-TYPE
        SYNTAX  INTEGER {
			on(1),
			onInputIdle(2),
			onIdle(3)
        }
        ACCESS  read-write
        STATUS  mandatory
        DESCRIPTION
        "Job spooling option."
        ::= { qmsIFConfig 9000 }
	

    -- The Netware Menu

QmsIFNetwareMenu ::= SEQUENCE {
        netwEnb           INTEGER,
        psName           DisplayString,
        confServ           DisplayString,
        msgLog           INTEGER,
        nwMode           INTEGER,
        psPoll           INTEGER,
        fr-802-3           INTEGER,
        fr-eth-2           INTEGER,
        fr-802-2           INTEGER,
        fr-snap           INTEGER,
        login1           DisplayString,
        login2           DisplayString,
        login3           DisplayString,
        login4           DisplayString,
        login5           DisplayString,
        login6           DisplayString,
        login7           DisplayString,
        login8           DisplayString,
        login9           DisplayString,
        login10           DisplayString,
        login11           DisplayString,
        login12           DisplayString,
        login13           DisplayString,
        login14           DisplayString,
        login15           DisplayString,
        login16           DisplayString,
        rprinter1           DisplayString,
        rprinter2           DisplayString,
        rprinter3           DisplayString,
        rprinter4           DisplayString,
        rprinter5           DisplayString,
        rprinter6           DisplayString,
        rprinter7           DisplayString,
        rprinter8           DisplayString
}


netwEnb OBJECT-TYPE
       SYNTAX INTEGER {
                no(1),
                yes(2)
        }
        ACCESS  read-write
        STATUS  mandatory
        DESCRIPTION
        "The NetWare protocol stack enable switch."
        ::= { qmsIFNetware 400 }

psName  OBJECT-TYPE
        SYNTAX DisplayString
        ACCESS  read-write
        STATUS  mandatory
        DESCRIPTION
        "The NetWare print server name."
        ::= { qmsIFNetware 401 }

confServ OBJECT-TYPE
        SYNTAX DisplayString
        ACCESS  read-write
        STATUS  mandatory
        DESCRIPTION
        "The NetWare configuration file server name."
        ::= { qmsIFNetware 402 }

msgLog  OBJECT-TYPE
        SYNTAX INTEGER {
                none(1),
                console(2),
                netlog(3),
                both(4)
        }
        ACCESS  read-write
        STATUS  mandatory
        DESCRIPTION
        "The NetWare message log mode."
        ::= { qmsIFNetware 403 }

nwMode  OBJECT-TYPE
        SYNTAX INTEGER {
                off(1),
                pserver(2),
                rprinter(3),
                both(4)
        }
        ACCESS  read-write
        STATUS  mandatory
        DESCRIPTION
        "The NetWare print mode."
        ::= { qmsIFNetware 404 }

psPoll  OBJECT-TYPE
        SYNTAX INTEGER (1..255)
        ACCESS  read-write
        STATUS  mandatory
        DESCRIPTION
        "The NetWare print server poll time."
        ::= { qmsIFNetware 405 }

fr8023 OBJECT-TYPE
        SYNTAX INTEGER {
                no(1),
                yes(2)
        }
        ACCESS  read-write
        STATUS  mandatory
        DESCRIPTION
        "The 802.3 frame support switch for NetWare."
        ::= { qmsIFNetware 420 }

freth2 OBJECT-TYPE
        SYNTAX INTEGER {
                no(1),
                yes(2)
        }
        ACCESS  read-write
        STATUS  mandatory
        DESCRIPTION
        "The Ethernet-2 frame support switch for NetWare."
        ::= { qmsIFNetware 421 }

fr8022 OBJECT-TYPE
        SYNTAX INTEGER {
                no(1),
                yes(2)
        }
        ACCESS  read-write
        STATUS  mandatory
        DESCRIPTION
        "The 802.2 frame support switch for NetWare."
        ::= { qmsIFNetware 422 }

frSnap OBJECT-TYPE
        SYNTAX INTEGER {
                no(1),
                yes(2)
        }
        ACCESS  read-write
        STATUS  mandatory
        DESCRIPTION
        "The SNAP frame support switch for NetWare."
        ::= { qmsIFNetware 423 }

login1  OBJECT-TYPE
        SYNTAX DisplayString
        ACCESS  read-write
        STATUS  mandatory
        DESCRIPTION
        "File server, print queue and logical printer def. ."
        ::= { qmsIFNetware 432 }

login2  OBJECT-TYPE
        SYNTAX DisplayString
        ACCESS  read-write
        STATUS  mandatory
        DESCRIPTION
        "File server, print queue and logical printer def. ."
        ::= { qmsIFNetware 433 }

login3  OBJECT-TYPE
        SYNTAX DisplayString
        ACCESS  read-write
        STATUS  mandatory
        DESCRIPTION
        "File server, print queue and logical printer def. ."
        ::= { qmsIFNetware 434 }

login4  OBJECT-TYPE
        SYNTAX DisplayString
        ACCESS  read-write
        STATUS  mandatory
        DESCRIPTION
        "File server, print queue and logical printer def. ."
        ::= { qmsIFNetware 435 }

login5  OBJECT-TYPE
        SYNTAX DisplayString
        ACCESS  read-write
        STATUS  mandatory
        DESCRIPTION
        "File server, print queue and logical printer def. ."
        ::= { qmsIFNetware 436 }

login6  OBJECT-TYPE
        SYNTAX DisplayString
        ACCESS  read-write
        STATUS  mandatory
        DESCRIPTION
        "File server, print queue and logical printer def. ."
        ::= { qmsIFNetware 437 }

login7  OBJECT-TYPE
        SYNTAX DisplayString
        ACCESS  read-write
        STATUS  mandatory
        DESCRIPTION
        "File server, print queue and logical printer def. ."
        ::= { qmsIFNetware 438 }

login8  OBJECT-TYPE
        SYNTAX DisplayString
        ACCESS  read-write
        STATUS  mandatory
        DESCRIPTION
        "File server, print queue and logical printer def. ."
        ::= { qmsIFNetware 439 }

login9  OBJECT-TYPE
        SYNTAX DisplayString
        ACCESS  read-write
        STATUS  mandatory
        DESCRIPTION
        "File server, print queue and logical printer def. ."
        ::= { qmsIFNetware 440 }

login10 OBJECT-TYPE
        SYNTAX DisplayString
        ACCESS  read-write
        STATUS  mandatory
        DESCRIPTION
        "File server, print queue and logical printer def. ."
        ::= { qmsIFNetware 441 }

login11 OBJECT-TYPE
        SYNTAX DisplayString
        ACCESS  read-write
        STATUS  mandatory
        DESCRIPTION
        "File server, print queue and logical printer def. ."
        ::= { qmsIFNetware 442 }

login12 OBJECT-TYPE
        SYNTAX DisplayString
        ACCESS  read-write
        STATUS  mandatory
        DESCRIPTION
        "File server, print queue and logical printer def. ."
        ::= { qmsIFNetware 443 }

login13 OBJECT-TYPE
        SYNTAX DisplayString
        ACCESS  read-write
        STATUS  mandatory
        DESCRIPTION
        "File server, print queue and logical printer def. ."
        ::= { qmsIFNetware 444 }

login14 OBJECT-TYPE
        SYNTAX DisplayString
        ACCESS  read-write
        STATUS  mandatory
        DESCRIPTION
        "File server, print queue and logical printer def. ."
        ::= { qmsIFNetware 445 }

login15 OBJECT-TYPE
        SYNTAX DisplayString
        ACCESS  read-write
        STATUS  mandatory
        DESCRIPTION
        "File server, print queue and logical printer def. ."
        ::= { qmsIFNetware 446 }

login16 OBJECT-TYPE
        SYNTAX DisplayString
        ACCESS  read-write
        STATUS  mandatory
        DESCRIPTION
        "File server, print queue and logical printer def. ."
        ::= { qmsIFNetware 447 }

rprinter1 OBJECT-TYPE
        SYNTAX DisplayString
        ACCESS  read-write
        STATUS  mandatory
        DESCRIPTION
        "Pserver name and printer number on pserver."
        ::= { qmsIFNetware 470 }

rprinter2 OBJECT-TYPE
        SYNTAX DisplayString
        ACCESS  read-write
        STATUS  mandatory
        DESCRIPTION
        "Pserver name and printer number on pserver."
        ::= { qmsIFNetware 471 }

rprinter3 OBJECT-TYPE
        SYNTAX DisplayString
        ACCESS  read-write
        STATUS  mandatory
        DESCRIPTION
        "Pserver name and printer number on pserver."
        ::= { qmsIFNetware 472 }

rprinter4 OBJECT-TYPE
        SYNTAX DisplayString
        ACCESS  read-write
        STATUS  mandatory
        DESCRIPTION
        "Pserver name and printer number on pserver."
        ::= { qmsIFNetware 473 }

rprinter5 OBJECT-TYPE
        SYNTAX DisplayString
        ACCESS  read-write
        STATUS  mandatory
        DESCRIPTION
        "Pserver name and printer number on pserver."
        ::= { qmsIFNetware 474 }

rprinter6 OBJECT-TYPE
        SYNTAX DisplayString
        ACCESS  read-write
        STATUS  mandatory
        DESCRIPTION
        "Pserver name and printer number on pserver."
        ::= { qmsIFNetware 475 }

rprinter7 OBJECT-TYPE
        SYNTAX DisplayString
        ACCESS  read-write
        STATUS  mandatory
        DESCRIPTION
        "Pserver name and printer number on pserver."
        ::= { qmsIFNetware 476 }

rprinter8 OBJECT-TYPE
        SYNTAX DisplayString
        ACCESS  read-write
        STATUS  mandatory
        DESCRIPTION
        "Pserver name and printer number on pserver."
        ::= { qmsIFNetware 477 }

        -- The Appletalk Menu

QmsIFAppletalkMenu ::= SEQUENCE {
        atlkEnb           INTEGER,
        atlkZone           DisplayString,
        atlkZonerEnb           INTEGER,
        atlkLWEnb           INTEGER,
        atlkQMSRemConEnb           INTEGER,
        atlkConnType           INTEGER
}

atlkEnb OBJECT-TYPE
        SYNTAX INTEGER {
                no(1),
                yes(2)
        }
        ACCESS  read-write
        STATUS  mandatory
        DESCRIPTION
        "The AppleTalk protocol stack enable switch."
        ::= { qmsIFApple 500 }


atlkZone OBJECT-TYPE
        SYNTAX DisplayString
        ACCESS  read-write
        STATUS  mandatory
        DESCRIPTION
        "The AppleTalk zone name."
        ::= { qmsIFApple 502 }

atlkZonerEnb OBJECT-TYPE
        SYNTAX INTEGER {
                no(1),
                yes(2)
        }
        ACCESS  read-write
        STATUS  mandatory
        DESCRIPTION
        "The AppleTalk HP Zoner support enable switch."
        ::= { qmsIFApple 503 }


atlkLWEnb OBJECT-TYPE
        SYNTAX INTEGER {
                no(1),
                yes(2)
        }
        ACCESS  read-write
        STATUS  mandatory
        DESCRIPTION
        "The AppleTalk LaserWriter support enable switch."
        ::= { qmsIFApple 560 }


atlkQMSRemConEnb OBJECT-TYPE
        SYNTAX INTEGER {
                no(1),
                yes(2)
        }
        ACCESS  read-write
        STATUS  mandatory
        DESCRIPTION
        "The AppleTalk QMS Remote Console support enable switch."
        ::= { qmsIFApple 561 }


atlkConnType OBJECT-TYPE
        SYNTAX INTEGER {
                conventional(1),
                spooling(2),
                both(3)
        }
        ACCESS  read-write
        STATUS  mandatory
        DESCRIPTION
        "The AppleTalk connection type."
        ::= { qmsIFApple 562 }


        -- The SNMP Menu

QmsIFSnmpMenu ::= SEQUENCE {
        enableAuthenTraps           INTEGER,
        enablePrinterTraps           INTEGER,
        nms1Address           IpAddress,
        nms1Community           DisplayString,
        nms1Access           INTEGER,
        nms2Address           IpAddress,
        nms2Community           DisplayString,
        nms2Access           INTEGER,
        nms3Address           IpAddress,
        nms3Community           DisplayString,
        nms3Access           INTEGER,
        nms4Address           IpAddress,
        nms4Community           DisplayString,
        nms4Access           INTEGER,
        nms5Address           IpAddress,
        nms5Community           DisplayString,
        nms5Access           INTEGER
}


enableAuthenTraps OBJECT-TYPE
        SYNTAX  INTEGER {
                enabled(1),
                disabled(2)
        }
        ACCESS  read-write
        STATUS  mandatory
        DESCRIPTION
        "Same as snmpEnableAuthenTraps in MIB-II."
        ::= { qmsIFSnmpcontrol 715 }

enablePrinterTraps OBJECT-TYPE
        SYNTAX  INTEGER {
                enabled(1),
                disabled(2)
        }
        ACCESS  read-write
        STATUS  mandatory
        DESCRIPTION
        "Enables the enterprise specific 'trapPrinter' traps."
        ::= { qmsIFSnmpcontrol 716 }

nms1Address OBJECT-TYPE
        SYNTAX  IpAddress
        ACCESS  read-write
        STATUS  mandatory
        DESCRIPTION
        "The IP address of NMS 1 definition."
        ::= { qmsIFSnmpcontrol 730 }

nms1Community OBJECT-TYPE
        SYNTAX  DisplayString
        ACCESS  read-write
        STATUS  mandatory
        DESCRIPTION
        "The community of NMS 1 definition."
        ::= { qmsIFSnmpcontrol 731 }

nms1Access OBJECT-TYPE
        SYNTAX INTEGER {
                none(1),
                trap(2),
                read(3),
                readtrap(4),
                write(5),
                writetrap(6)
        }
        ACCESS  read-write
        STATUS  mandatory
        DESCRIPTION
        "The access priviledge of NMS 1."
        ::= { qmsIFSnmpcontrol 732 }

nms2Address OBJECT-TYPE
        SYNTAX  IpAddress
        ACCESS  read-write
        STATUS  mandatory
        DESCRIPTION
        "The IP address of NMS 2 definition."
        ::= { qmsIFSnmpcontrol 735 }

nms2Community OBJECT-TYPE
        SYNTAX  DisplayString
        ACCESS  read-write
        STATUS  mandatory
        DESCRIPTION
        "The community of NMS 2 definition."
        ::= { qmsIFSnmpcontrol 736 }

nms2Access OBJECT-TYPE
        SYNTAX INTEGER {
                none(1),
                trap(2),
                read(3),
                readtrap(4),
                write(5),
                writetrap(6)
        }
        ACCESS  read-write
        STATUS  mandatory
        DESCRIPTION
        "The access priviledge of NMS 2."
        ::= { qmsIFSnmpcontrol 737 }

nms3Address OBJECT-TYPE
        SYNTAX  IpAddress
        ACCESS  read-write
        STATUS  mandatory
        DESCRIPTION
        "The IP address of NMS 3 definition."
        ::= { qmsIFSnmpcontrol 740 }

nms3Community OBJECT-TYPE
        SYNTAX  DisplayString
        ACCESS  read-write
        STATUS  mandatory
        DESCRIPTION
        "The community of NMS 3 definition."
        ::= { qmsIFSnmpcontrol 741 }

nms3Access OBJECT-TYPE
        SYNTAX INTEGER {
                none(1),
                trap(2),
                read(3),
                readtrap(4),
                write(5),
                writetrap(6)
        }
        ACCESS  read-write
        STATUS  mandatory
        DESCRIPTION
        "The access priviledge of NMS 3."
        ::= { qmsIFSnmpcontrol 742 }

nms4Address OBJECT-TYPE
        SYNTAX  IpAddress
        ACCESS  read-write
        STATUS  mandatory
        DESCRIPTION
        "The IP address of NMS 4 definition."
        ::= { qmsIFSnmpcontrol 745 }

nms4Community OBJECT-TYPE
        SYNTAX  DisplayString
        ACCESS  read-write
        STATUS  mandatory
        DESCRIPTION
        "The community of NMS 4 definition."
        ::= { qmsIFSnmpcontrol 746 }

nms4Access OBJECT-TYPE
        SYNTAX INTEGER {
                none(1),
                trap(2),
                read(3),
                readtrap(4),
                write(5),
                writetrap(6)
        }
        ACCESS  read-write
        STATUS  mandatory
        DESCRIPTION
        "The access priviledge of NMS 4."
        ::= { qmsIFSnmpcontrol 747 }


nms5Address OBJECT-TYPE
        SYNTAX  IpAddress
        ACCESS  read-write
        STATUS  mandatory
        DESCRIPTION
        "The IP address of NMS 5 definition."
        ::= { qmsIFSnmpcontrol 750 }

nms5Community OBJECT-TYPE
        SYNTAX  DisplayString
        ACCESS  read-write
        STATUS  mandatory
        DESCRIPTION
        "The community of NMS 5 definition."
        ::= { qmsIFSnmpcontrol 751 }

nms5Access OBJECT-TYPE
        SYNTAX INTEGER {
                none(1),
                trap(2),
                read(3),
                readtrap(4),
                write(5),
                writetrap(6)
        }
        ACCESS  read-write
        STATUS  mandatory
        DESCRIPTION
        "The access priviledge of NMS 5."
        ::= { qmsIFSnmpcontrol 752 }

        -- The LAN Server / LAN Manager Menu


QmsIFLServLMgrMenu ::= SEQUENCE {
        lslmEnb           INTEGER
}

lslmEnb OBJECT-TYPE
        SYNTAX INTEGER {
                no(1),
                yes(2)
        }
        ACCESS  read-write
        STATUS  mandatory
        DESCRIPTION
        "The Lan Serv/Lan Mgr protocol stack enable switch."
        ::= { qmsIFLservlmgr 800 }


--- The Standard Traps

coldStart TRAP-TYPE
        ENTERPRISE  snmp
        DESCRIPTION
        "A coldStart trap signifies that the sending
         protocol entity is reinitializing itself such
         that the agent's configuration or the protocol
         entity implementation may be altered."
        ::= 0

authenticationFailure TRAP-TYPE
        ENTERPRISE  snmp
        DESCRIPTION
        "An authenticationFailure trap signifies that
         the sending protocol entity is the addressee
         of a protocol message that is not properly
         authenticated.  While implementations of the
         SNMP must be capable of generating this trap,
         they must also be capable of suppressing the
         emission of such traps via an implementation-
         specific mechanism."
        ::= 4



--- The Private Enterprise Traps


qmsPtrErrorMsg TRAP-TYPE
		ENTERPRISE	qmsInc
		VARIABLES	{ qmsPtrSysStatus }
		DESCRIPTION    
		"The variable used to relay the current printer error
		or informaitional message."
		::= 1

trapNewIPaddr TRAP-TYPE
        ENTERPRISE qmsInc
        VARIABLES  { qmsIFAdminOldIntAddr }
        DESCRIPTION
        "The IP address has been changed by RARP or an 'arp -s'."
        ::= 2

-- END
END
