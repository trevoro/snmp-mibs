-- COPYRIGHT NOTICE
-- Copyright (c) Alteon Networks, Inc. 2002 
-- All rights reserved
-- 
-- 
-- HISTORY
-- $Log: cheetahtrap.mib $
-- Revision submit_cheetah_385/1 2002/07/18 17:19:37 rrekha
-- Added Mike's descriptions for some of the traps.
-- 
-- Revision ch_1_0_0_dev/4 2002/05/13 23:55:31 rrekha
-- Changed the altswitchtrap to alttrap.
-- 
-- Revision ch_1_0_0_dev/3 2002/04/23 21:49:32 smiao
-- Renamed node cheetah to aws-switches.
-- 
-- Revision ch_1_0_0_dev/2 2002/03/11 19:12:07 smiao
-- Changed altswitchTraps to be cheetah 7.
-- 
-- Revision ch_1_0_0_dev/1 2002/03/07 19:01:59 smiao
-- Removed unnecssary MIB objects for CHEEATH.
-- 
-- Revision ch10latest_smiao/2 2002/02/13 01:41:50 smiao
-- 	Initial checked in for cheetah MIB files.
-- 
-- $EndLog$

CHEETAH-TRAP-MIB DEFINITIONS ::= BEGIN

IMPORTS
	OBJECT-TYPE FROM RFC1155-SMI
    TRAP-TYPE
        FROM RFC-1215
    sysName, sysLocation, sysContact, DisplayString
        FROM RFC1213-MIB
    aws-switch 
        FROM ALTEON-ROOT-MIB
    ipCurCfgGwIndex, ipCurCfgGwAddr, 
    vrrpCurCfgVirtRtrIndx, vrrpCurCfgVirtRtrAddr,
    vrrpCurCfgIfIndx, vrrpCurCfgIfPasswd
        FROM ALTEON-CHEETAH-NETWORK-MIB
    slbCurCfgRealServerIndex, slbCurCfgRealServerIpAddr,
    slbCurCfgRealServerName, fltCurCfgIndx, fltCurCfgPortIndx, 
    slbCurCfgVirtServiceRealPort, fltCurCfgSrcIp
        FROM ALTEON-CHEETAH-LAYER4-MIB;

altTraps		OBJECT IDENTIFIER ::= { aws-switch 7 }

-- SECTION 2:  Temporary Object Definitions Used In Traps
 
altSwTrapDisplayString OBJECT-TYPE
        SYNTAX  DisplayString (SIZE(0..255))
        ACCESS  read-only
        STATUS  mandatory
        DESCRIPTION
                "Temporary string object used to store information being sent
                 in an Alteon Switch trap."
        ::= { altTraps 1000 }

altSwTrapRate OBJECT-TYPE
    SYNTAX  INTEGER
    ACCESS  read-only
    STATUS  mandatory
    DESCRIPTION
        "Temporary integer object used to store information being sent
         in an Alteon Switch trap."
    ::= { altTraps 1001 }

-- SECTION 3:  Trap Definitions

-- Many of the following traps include sysName, sysLocation and sysContact. 
-- These variables are all defined in the rfc1213 MIB.  
--
-- sysName is the administratively-assigned name for this managed node. By  
-- convention, this is the node's fully-qualified domain name. 
--
-- sysLocation is the physical location of this node (e.g., 'telephone closet,  
-- 3rd floor'). 
--
-- sysContact is textual identification of the contact person for this managed  
-- node, together with information on how to contact this person. 

altSwPrimaryPowerSupplyFailure TRAP-TYPE
        ENTERPRISE      altTraps
        DESCRIPTION
                "A altSwPrimaryPowerSupplyFailure trap signifies that the 
		 primary power supply failed."
        ::= 1   -- 0x01

altSwDefGwUp TRAP-TYPE
        ENTERPRISE      altTraps
        VARIABLES       { ipCurCfgGwIndex,
                          ipCurCfgGwAddr,
                          sysName, sysLocation, sysContact }
        DESCRIPTION
                "A altSwDefGwUp trap signifies that the default gateway is alive.
                 ipCurCfgGwIndex is the index of the Gateway in ipCurCfgGwTable.
                 The range for ipCurCfgGwIndex is from 1 to ipGatewayTableMax.
                 ipCurCfgGwAddr is the IP address of the default gateway."
        ::= 2   -- 0x02

altSwDefGwDown TRAP-TYPE
        ENTERPRISE      altTraps
        VARIABLES       { ipCurCfgGwIndex,
                          ipCurCfgGwAddr,
                          sysName, sysLocation, sysContact }
        DESCRIPTION
                "A altSwDefGwDown trap signifies that the default gateway is down.
                 ipCurCfgGwIndex is the index of the Gateway in ipCurCfgGwTable. 
                 The range for ipCurCfgGwIndex is from 1 to ipGatewayTableMax.
                 ipCurCfgGwAddr is the IP address of the default gateway."
        ::= 3   -- 0x03

altSwDefGwInService TRAP-TYPE
        ENTERPRISE      altTraps
        VARIABLES       { ipCurCfgGwIndex,
                          ipCurCfgGwAddr,
                          sysName, sysLocation, sysContact }
        DESCRIPTION
                "A altSwDefGwEnabled trap signifies that the default gateway is up
                 and in service. ipCurCfgGwIndex is the index of the Gateway in 
                 ipCurCfgGwTable. The range for ipCurCfgGwIndex is from 
                 1 to ipGatewayTableMax. ipCurCfgGwAddr is the IP address of the 
                 default gateway."
        ::= 4   -- 0x04

altSwDefGwNotInService TRAP-TYPE
        ENTERPRISE      altTraps
        VARIABLES       { ipCurCfgGwIndex,
                          ipCurCfgGwAddr,
                          sysName, sysLocation, sysContact }
        DESCRIPTION
                "A altSwDefGwDisabled trap signifies that the default gateway is 
                 alive but not in service. ipCurCfgGwIndex is the index of the 
                 Gateway in ipCurCfgGwTable. The range for ipCurCfgGwIndex is 
                 from 1 to ipGatewayTableMax. ipCurCfgGwAddr is the IP address of 
                 the default gateway."
        ::= 5   -- 0x05

altSwSlbRealServerUp TRAP-TYPE
        ENTERPRISE      altTraps
        VARIABLES       { slbCurCfgRealServerIndex,
                          slbCurCfgRealServerIpAddr,
                          slbCurCfgRealServerName,
                          sysName, sysLocation, sysContact }
        DESCRIPTION
                "A altSwSlbRealServerUp trap signifies that the real
                 server (which had gone down )is back up and operational now.
                 slbCurCfgRealServerIndex is the affected Real Server Number.
                 The range is from 1 to slbRealServerMaxSize.
                 slbCurCfgRealServerIpAddr is the IP address of the affected 
                 Real Server.
                 slbCurCfgRealServerName is the optional Name given to the 
                 affected Real Server."
        ::= 6   -- 0x06

altSwSlbRealServerDown TRAP-TYPE
        ENTERPRISE      altTraps
        VARIABLES       { slbCurCfgRealServerIndex,
                          slbCurCfgRealServerIpAddr,
                          slbCurCfgRealServerName,
                          sysName, sysLocation, sysContact }
        DESCRIPTION
                "A altSwSlbRealServerDown trap signifies that the real
                 server has gone down and is out of service.
                 slbCurCfgRealServerIndex is the affected Real Server Number.
                 The range is from 1 to slbRealServerMaxSize.
                 slbCurCfgRealServerIpAddr is the IP address of the affected 
                 Real Server.
                 slbCurCfgRealServerName is the optional Name given to the 
                 affected Real Server."
        ::= 7   -- 0x07

altSwSlbRealServerMaxConnReached TRAP-TYPE
        ENTERPRISE      altTraps
        VARIABLES       { slbCurCfgRealServerIndex,
                          slbCurCfgRealServerIpAddr,
                          slbCurCfgRealServerName,
                          sysName, sysLocation, sysContact }
        DESCRIPTION
                "A altSwSlbRealServerMaxConnReached trap signifies that the 
		 real server has reached maximum connections. The Real server 
                 will not be sent any more traffic from the switch until the 
                 number of connections drops below the maximum. If a backup 
                 server has been specified, it will be used to service 
                 additional requests, which is referred to as an Overflow server.
                 slbCurCfgRealServerIndex is the affected Real Server Number.
                 The range is from 1 to slbRealServerMaxSize.
                 slbCurCfgRealServerIpAddr is the IP address of the affected 
                 Real Server.
                 slbCurCfgRealServerName is the optional Name given to the 
                 affected Real Server."
        ::= 8   -- 0x08

altSwSlbBkupRealServerAct TRAP-TYPE
        ENTERPRISE      altTraps
        VARIABLES       { slbCurCfgRealServerIndex,
                          slbCurCfgRealServerIpAddr,
                          slbCurCfgRealServerName,
                          sysName, sysLocation, sysContact }
        DESCRIPTION
                "A altSwSlbBkupRealServerAct trap signifies that this 
		 backup real server has been activated because the Real server
		 that it backs up went down.One might expect that a 
                 altSwSlbRealServerDown trap with the primary real server 
                 specified would preceded this one.
                 slbCurCfgRealServerIndex is the affected Real Server Number.
                 The range is from 1 to slbRealServerMaxSize.
                 slbCurCfgRealServerIpAddr is the IP address of the affected 
                 Real Server.
                 slbCurCfgRealServerName is the optional Name given to the 
                 affected Real Server."
        ::= 9   -- 0x09

altSwSlbBkupRealServerDeact TRAP-TYPE
        ENTERPRISE      altTraps
        VARIABLES       { slbCurCfgRealServerIndex,
                          slbCurCfgRealServerIpAddr,
                          slbCurCfgRealServerName,
                          sysName, sysLocation, sysContact }
        DESCRIPTION
                "A altSwSlbBkupRealServerDeact trap signifies that the 
		 backup real server is deactivated because the primary real 
		 server has become available.One might expect that a 
                 altSwSlbRealServerUp trap with the primary real server specified 
                 would preceded this one.
                 slbCurCfgRealServerIndex is the affected Real Server Number.
                 The range is from 1 to slbRealServerMaxSize.
                 slbCurCfgRealServerIpAddr is the IP address of the affected 
                 Real Server.
                 slbCurCfgRealServerName is the optional Name given to the 
                 affected Real Server."
        ::= 10   -- 0x0A

altSwSlbBkupRealServerActOverflow TRAP-TYPE
        ENTERPRISE      altTraps
        VARIABLES       { slbCurCfgRealServerIndex,
                          slbCurCfgRealServerIpAddr,
                          slbCurCfgRealServerName,
                          sysName, sysLocation, sysContact }
        DESCRIPTION
                "A altSwSlbBkupRealServerActOverflow trap signifies 
		 that the backup real server is activated because the primary 
		 real server has reached the maximum allowed connections and 
                 is considered to be  is in the Overflow state.One would expect 
                 an altSwSlbRealServerMaxConnReached trap from the Real 
                 server that just entered Overflow would preceded this one. 
                 slbCurCfgRealServerIndex is the affected Real Server Number.
                 The range is from 1 to slbRealServerMaxSize.
                 slbCurCfgRealServerIpAddr is the IP address of the affected 
                 Real Server.
                 slbCurCfgRealServerName is the optional Name given to the 
                 affected Real Server."
        ::= 11   -- 0x0B

altSwSlbBkupRealServerDeactOverflow TRAP-TYPE
        ENTERPRISE      altTraps
        VARIABLES       { slbCurCfgRealServerIndex,
                          slbCurCfgRealServerIpAddr,
                          slbCurCfgRealServerName,
                          sysName, sysLocation, sysContact }
        DESCRIPTION
                "A altSwSlbBkupRealServerDeactOverflow trap signifies 
		 that the backup real server is deactivated because the 
                 primary real server is no longer in Overflow. The number of 
                 connections to the real server has fallen below the maximum 
                 allowed. The backup/overflow server is no longer needed.
                 slbCurCfgRealServerIndex is the affected Real Server Number.
                 The range is from 1 to slbRealServerMaxSize.
                 slbCurCfgRealServerIpAddr is the IP address of the affected 
                 Real Server.
                 slbCurCfgRealServerName is the optional Name given to the 
                 affected Real Server."
        ::= 12   -- 0x0C

altSwfltFilterFired TRAP-TYPE
        ENTERPRISE      altTraps
        VARIABLES       { fltCurCfgIndx, fltCurCfgPortIndx,
                          sysName, sysLocation, sysContact }
        DESCRIPTION
                "A altSwfltFilterFired trap signifies that the packet 
		 received on a switch port matches the filter rule.
                 on a switch port matches the filter rule.
                 fltCurCfgIndx is the affected filter index, referenced in 
                 fltCurCfgTable. The range is from 1 to fltCfgTableMaxSize.
                 fltCurCfgPortIndx is the affected port index, referenced in 
                 fltCurCfgPortTable. The range is from 1 to agPortTableMaxEnt."
        ::= 13   -- 0x0D

altSwSlbRealServerServiceUp TRAP-TYPE
        ENTERPRISE      altTraps
        VARIABLES       { slbCurCfgRealServerIndex,
                          slbCurCfgRealServerIpAddr,
                          slbCurCfgRealServerName,
                          slbCurCfgVirtServiceRealPort,
                          sysName, sysLocation, sysContact }
        DESCRIPTION    
                "A altSwSlbRealServerServiceUp trap signifies that the service 
                 port of the real server is up and operational.
                 slbCurCfgRealServerIndex is the affected Real Server Number.
                 The range is from 1 to the value return from slbRealServerMaxSize.
                 slbCurCfgRealServerIpAddr is the IP address of the affected 
                 Real Server.
                 slbCurCfgRealServerName is the optional Name given to the 
                 affected Real Server.
                 slbCurCfgVirtualServiceRealPort referenced in 
                 slbCurCfgVirtServicesTable.  
                 This is the layer 4 real port number of the service."
        ::= 14   -- 0x0E
 
altSwSlbRealServerServiceDown TRAP-TYPE
        ENTERPRISE      altTraps
        VARIABLES       { slbCurCfgRealServerIndex,
                          slbCurCfgRealServerIpAddr,
                          slbCurCfgRealServerName,
                          slbCurCfgVirtServiceRealPort,
                          sysName, sysLocation, sysContact }
        DESCRIPTION    
                "A altSwSlbRealServerServiceDown trap signifies that the 
                 service port of the real server is down and out of service.
                 slbCurCfgRealServerIndex is the affected Real Server Number.
                 The range is from 1 to the value return from slbRealServerMaxSize.
                 slbCurCfgRealServerIpAddr is the IP address of the affected 
                 Real Server.
                 slbCurCfgRealServerName is the optional Name given to the 
                 affected Real Server.
                 slbCurCfgVirtualServiceRealPort referenced in 
                 slbCurCfgVirtServicesTable.  
                 This is the layer 4 real port number of the service."
        ::= 15   -- 0x0F

altSwVrrpNewMaster TRAP-TYPE
        ENTERPRISE      altTraps
        VARIABLES       { vrrpCurCfgVirtRtrIndx,
                          vrrpCurCfgVirtRtrAddr,
                          sysName, sysLocation, sysContact }
        DESCRIPTION    
                "The altSwVrrpNewMaster trap indicates that the sending agent
		 has transitioned to 'Master' state.
                 vrrpCurCfgVirtRtrIndx is the VRRP virtual router table index 
                 referenced in vrrpCurCfgVirtRtrTable. The range is from 
                 1 to vrrpVirtRtrTableMaxSize.
                 vrrpCurCfgVirtRtrAddr is the VRRP virtual router IP address."
        ::= 16 -- 0x10
 
altSwVrrpNewBackup TRAP-TYPE
        ENTERPRISE      altTraps
        VARIABLES       { vrrpCurCfgVirtRtrIndx,
                          vrrpCurCfgVirtRtrAddr,
                          sysName, sysLocation, sysContact }
        DESCRIPTION    
                "The altSwVrrpNewBackup trap indicates that the sending agent
		 has transitioned to 'Backup' state.
                 vrrpCurCfgVirtRtrIndx is the VRRP virtual router table index 
                 referenced in vrrpCurCfgVirtRtrTable. The range is from 
                 1 to vrrpVirtRtrTableMaxSize.
                 vrrpCurCfgVirtRtrAddr is the VRRP virtual router IP address."
        ::= 17 -- 0x11
 
altSwVrrpAuthFailure TRAP-TYPE
        ENTERPRISE      altTraps
        VARIABLES       { vrrpCurCfgIfIndx,
                          vrrpCurCfgIfPasswd,
                          sysName, sysLocation, sysContact }
        DESCRIPTION    
                "A altSwVrrpAuthFailure trap signifies that a packet has
		 been received from a router whose authentication key
		 or authentication type conflicts with this router's
		 authentication key or authentication type. Implementation
		 of this trap is optional.
                 vrrpCurCfgIfIndx is the VRRP interface index. This is equivalent 
                 to IfIndex in RFC 1213 mib. The range is from 1 to 
                 vrrpIfTableMaxSize.
                 vrrpCurCfgIfPasswd is the password for authentication. It is a 
                 DisplayString of 0 to 7 characters."
        ::= 18 -- 0x12

altSwLoginFailure TRAP-TYPE
        ENTERPRISE      altTraps
        VARIABLES       { altSwTrapDisplayString,
                          sysName, sysLocation, sysContact }
        DESCRIPTION
                "A altSwLoginFailure trap signifies that someone failed to
                 enter a valid username/password combination. 
                 altSwTrapDisplayString specifies whether the login attempt was
                 from CONSOLE or TELNET. In case of TELNET login it also specifies 
                 the IP address of the host from which the attempt was made."
        ::= 19 -- 0x13

altSwSlbSynAttack TRAP-TYPE
    ENTERPRISE     altTraps
    VARIABLES      { altSwTrapRate,
                     sysName, sysLocation, sysContact }
    DESCRIPTION
        "A altSwSlbSynAttack trap signifies that a SYN attack has been 
         detected.
         altSwTrapRate specifies the number of new half-open sessions per second."
    ::= 20   -- 0x14

altSwTcpHoldDown TRAP-TYPE
    ENTERPRISE     altTraps
    VARIABLES      { fltCurCfgSrcIp,
                     altSwTrapRate,
                     sysName, sysLocation, sysContact }
    DESCRIPTION
        "A altSwTcpHoldDown trap signifies that new TCP connection requests
         from a particular client will be blocked for a pre-determined amount
         of time since the rate of new TCP connections from that client has
         reached a pre-determined threshold. 
         The fltCurCfgSrcIp is the client source IP address for which new TCP 
         connection requests will be blocked. 
         The altSwTrapRate specifies the amount of time in minutes that the 
         particular client will be blocked."
    ::= 21   -- 0x15

altSwTempExceedThreshold TRAP-TYPE
    ENTERPRISE      altTraps
    VARIABLES       { altSwTrapDisplayString,
                      sysName, sysLocation, sysContact }
    DESCRIPTION
        "A altSwTempExceedThreshold trap signifies that the
         switch temperature has exceeded maximum safety limits. 
         altSwTrapDisplayString specifies the sensor, the current sensor 
         temperature and the threshold for the particular sensor."
    ::= 22   -- 0x16
END
