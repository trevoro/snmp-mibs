--
--      Title:  Appian Physical Port Common MIB
--
--      Dated:  03/04/2k
--      Author: D. Theriault
--
--      Description:
--
--      This MIB file contains the definitions and support for the Appian
--      Optical Services Access Platform(s).
-- 
--      The Appian physical port common MIB supports tables which are
--      common to all physical interface ports.
--
--
APPIAN-PPORT-COMMON-MIB DEFINITIONS ::= BEGIN
    IMPORTS
        AcAdminStatus, AcOpStatus,
        AcNodeId, AcSlotNumber, AcPortNumber,
        acPport                                     FROM APPIAN-SMI-MIB 
            
        MODULE-IDENTITY, OBJECT-TYPE                FROM SNMPv2-SMI

        DisplayString                               FROM SNMPv2-TC;


acPportCommon       MODULE-IDENTITY
    LAST-UPDATED    "0003040000Z"
    ORGANIZATION    "Appian Communications, Inc."
    CONTACT-INFO    "Douglas Theriault"
    
    DESCRIPTION     "Appian physical port common MIB provides configuration
                    information common to all physical interfaces."
                    
    REVISION        "0003040000Z"

    DESCRIPTION     "Engineering draft version, not for release."

    ::= { acPport 1 }

--
-- Common Interface Table
--
acInterfaceTable  OBJECT-TYPE
    SYNTAX  SEQUENCE OF AcInterfaceEntry
    MAX-ACCESS  not-accessible
    STATUS  current
    DESCRIPTION
    "A table which will map a physical ports instance ID with a subscriber
    and reseller along with the interface name and mapping to MIB-II's 
    ifIndex value."
    
    ::= { acPportCommon 1 }
    
acInterfaceEntry  OBJECT-TYPE
    SYNTAX  AcInterfaceEntry
    MAX-ACCESS  not-accessible
    STATUS  current
    DESCRIPTION
    "A single row which identifies a physical interface."
    
    INDEX { acInterfaceNodeId, acInterfaceSlot, acInterfacePort }
    
    ::= { acInterfaceTable 1 }
    
    AcInterfaceEntry ::=
        SEQUENCE {
            acInterfaceNodeId                        AcNodeId,
            acInterfaceSlot                          AcSlotNumber,
            acInterfacePort                          AcPortNumber,
            acInterfaceType                          INTEGER,
            acInterfaceChannel                       INTEGER,
            acInterfaceIfIndex                       INTEGER,
            acInterfaceAdminStatus                   AcAdminStatus,
            acInterfaceOpStatus                      AcOpStatus,
            acInterfaceInterfaceName                 DisplayString,
            acInterfaceSubscriberId                  INTEGER,
            acInterfaceSubscriberName                 DisplayString,
            acInterfaceResellerId                    INTEGER,
            acInterfaceResellerName                  DisplayString
        }
        

--
-- acInterfaceEntry
--

acInterfaceNodeId  OBJECT-TYPE
    SYNTAX  AcNodeId
    MAX-ACCESS accessible-for-notify
    STATUS  current
    DESCRIPTION
    "A unique number assigned to this node within an Appian Ring."
    
    ::= { acInterfaceEntry 1 }
    
acInterfaceSlot  OBJECT-TYPE
    SYNTAX  AcSlotNumber
    MAX-ACCESS accessible-for-notify
    STATUS  current
    DESCRIPTION
    "The physical slot number where this physical interface is 
    located."
    
    ::= { acInterfaceEntry 2 }
        
acInterfacePort  OBJECT-TYPE
    SYNTAX  AcPortNumber
    MAX-ACCESS accessible-for-notify
    STATUS  current
    DESCRIPTION
    "The physical port number on the slot where this interface is
    located."
    
    ::= { acInterfaceEntry 3 }

acInterfaceType   OBJECT-TYPE
    SYNTAX  INTEGER {
                unknown(0),  -- the payload type is unknown
                enet(1),     -- an ETHERNET port (access card)
                ds1(2),      -- a DS1 port (access card)
                ds3(3),      -- a DS3 port (access card)
                sonet(4)     -- a SONET port (sonet card)
            }
    MAX-ACCESS      read-write
    STATUS          current
    DESCRIPTION
    "The type of physical interface (port)"
        
    DEFVAL { unknown }
    ::= { acInterfaceEntry 4 }

acInterfaceChannel  OBJECT-TYPE
    SYNTAX  INTEGER
    MAX-ACCESS read-write
    STATUS  current
    DESCRIPTION
    "If the physical interface can be channelized, this attribute is
    the channel associated with a specific subscriber and reseller."
    
    ::= { acInterfaceEntry 5 }

acInterfaceIfIndex  OBJECT-TYPE
    SYNTAX  INTEGER
    MAX-ACCESS read-only
    STATUS  current
    DESCRIPTION
    "The associated MIB-II IfIndex value which corresponds to this
    physical interface.  The agent will calculate this value in a
    deterministic manner and is here as an easy means to map the
    heirarchical slot.port.channel index to a linear ifIndex value."
    
    ::= { acInterfaceEntry 6 }
    
acInterfaceAdminStatus  OBJECT-TYPE
    SYNTAX  AcAdminStatus
    MAX-ACCESS read-write
    STATUS  current
    DESCRIPTION
    "Appian Administrative Status attribute used to set the provisioning
    state as either activate(1), inactivate(2) or delete(3).  Refer to
    the Appian-SMI.mib file for additional information."

    DEFVAL { inactivate }
    
    ::= { acInterfaceEntry 7 }

acInterfaceOpStatus  OBJECT-TYPE
    SYNTAX  AcOpStatus
    MAX-ACCESS read-only
    STATUS  current
    DESCRIPTION
    "The current operational status of this physical interface.  Refer
    to the appian_smi.mib file for enumeration details."
    
    ::= { acInterfaceEntry 8 }

acInterfaceInterfaceName  OBJECT-TYPE
    SYNTAX  DisplayString (SIZE(0..64))
    MAX-ACCESS read-only
    STATUS  current
    DESCRIPTION
    "A user defined name which is used to identify this physical interface.
    The string is in readable ASCII and can be up to 64 characters in length.
    This name is configured in each of the physical port interface MIB's and
    is a read-only attribute here."
    
    ::= { acInterfaceEntry 9 }

acInterfaceSubscriberId  OBJECT-TYPE
    SYNTAX  INTEGER
    MAX-ACCESS read-write
    STATUS  current
    DESCRIPTION
    "A unique number assigned by the EMS that uniquely identifies the
    subscriber who is using this physical interface."
    
    ::= { acInterfaceEntry 10 }
    
acInterfaceSubscriberName  OBJECT-TYPE
    SYNTAX  DisplayString (SIZE(0..64))
    MAX-ACCESS read-write
    STATUS  current
    DESCRIPTION
    "An ASCII string which represents the subscriber in a readable form. The
    string can be up to 64 characters in length."
    
    ::= { acInterfaceEntry 11 }
    
acInterfaceResellerId  OBJECT-TYPE
    SYNTAX  INTEGER
    MAX-ACCESS read-write
    STATUS  current
    DESCRIPTION
    "A unique number assigned by the EMS that uniquely identifies the reseller
    for which service is supplied by this physical interface."
    
    ::= { acInterfaceEntry 12 }

acInterfaceResellerName  OBJECT-TYPE
    SYNTAX  DisplayString (SIZE(0..64))
    MAX-ACCESS read-write
    STATUS  current
    DESCRIPTION
    "An ASCII string which represents the reseller in a readable form. The
    string can be up to 64 characters in length."    

    ::= { acInterfaceEntry 13 }
    
END
