-- *****************************************************************************
-- Juniper-SMDS-CONF
--
-- SNMP Agent Capabilities definitions for the Smds MIB.
--
-- Copyright (c) 2001 Unisphere Networks, Inc.
-- Copyright (c) 2002, 2003 Juniper Networks, Inc.
--   All rights reserved.
-- *****************************************************************************

Juniper-SMDS-CONF  DEFINITIONS ::= BEGIN

IMPORTS
    MODULE-IDENTITY
        FROM SNMPv2-SMI
    AGENT-CAPABILITIES
        FROM SNMPv2-CONF
    juniAgents
        FROM Juniper-Agents;

juniSmdsAgent  MODULE-IDENTITY
    LAST-UPDATED "200209061654Z"  -- 06-Sep-02 12:54 PM EDT
    ORGANIZATION "Juniper Networks, Inc."
    CONTACT-INFO
        "       Juniper Networks, Inc.
        Postal: 10 Technology Park Drive
                Westford, MA  01886-3146
                USA
        Tel:    +1 978 589 5800
        E-mail: mib@Juniper.net"
    DESCRIPTION
        "The agent capabilities definitions for the Switched Multimegabit Data
        Service (SMDS) management component of the SNMP agent in the Juniper
        E-series family of products."
    -- Revision History
    REVISION    "200209061654Z"  -- 06-Sep-02 12:54 PM EDT  - JUNOSe 5.0
    DESCRIPTION
        "Replaced Unisphere names with Juniper names."
    REVISION    "200109201457Z"  -- 20-Sep-01 10:57 AM EDT  - JUNOSe 4.0
    DESCRIPTION
        "Added support for major and sub interfaces."
    REVISION    "200103301430Z"  -- 30-Mar-01 09:30 AM EST  - JUNOSe 3.2
    DESCRIPTION
        "The initial release of this management information module."
    ::= { juniAgents 46 }


-- *****************************************************************************
-- SMDS SNMP Agent Capabilities definitions
-- *****************************************************************************
juniSmdsAgentV1  AGENT-CAPABILITIES
    PRODUCT-RELEASE
        "Version 1 of the Switched Multimegabit Data Service (SMDS) management
        component of the JUNOSe SNMP agent.  This version of the SMDS component
        was supported in JUNOSe 3.1 and subsequent 3.x system releases."
    STATUS      obsolete
    DESCRIPTION
        "The MIB supported by the SNMP agent for the SMDS application in JUNOSe.
        These capabilities became obsolete when support was added for major and
        sub interfaces"
    SUPPORTS    Juniper-SMDS-MIB
        INCLUDES {
            juniSmdsGroup }
    ::= { juniSmdsAgent 1 }

juniSmdsAgentV2  AGENT-CAPABILITIES
    PRODUCT-RELEASE
        "Version 2 of the Switched Multimegabit Data Service (SMDS) management
        component of the JUNOSe SNMP agent.  This version of the SMDS component
        is supported in JUNOSe 4.0 and subsequent system releases."
    STATUS      current
    DESCRIPTION
        "The MIB supported by the SNMP agent for the SMDS application in
        JUNOSe."
    SUPPORTS    Juniper-SMDS-MIB
        INCLUDES {
            juniSmdsGroup2 }
    ::= { juniSmdsAgent 2 }

END
