-- *****************************************************************
-- Moxa Active Ethernet I/O Server MIB
--
-- 01-03-2013
--
-- Copyright (c) 2013 by Moxa Automation Co., Ltd.
-- All rights reserved.
-- *****************************************************************

MOXA-IO-E1242-MIB DEFINITIONS ::= BEGIN
    IMPORTS
        enterprises, Unsigned32, Integer32, MODULE-IDENTITY, OBJECT-TYPE FROM SNMPv2-SMI;
   
-- 1.3.6.1.4.1.8691.10.1242
    e1242   MODULE-IDENTITY
    LAST-UPDATED "201302211400Z"
    ORGANIZATION "Moxa Automation,Inc."
    CONTACT-INFO
            "Postal: Moxa Automation,Inc.
             Fl.4, No.135,Lane 235,Pao-Chiao Rd.
             Shing Tien City,Taipei,Taiwan,R.O.C
             Tel: +866-2-89191230 "
    DESCRIPTION
            "The MIB module for Moxa ioLogik Remote Ethernet I/O specific information." 
    REVISION "201302211400Z"
    DESCRIPTION
            "First version of this MIB."
           ::= { ioLogik 1242 }    -- 1.3.6.1.4.1.8691.10.1242

-- 1.3.6.1.4.1.8691
    moxa OBJECT IDENTIFIER ::= { enterprises 8691 }

-- 1.3.6.1.4.1.8691.10
    ioLogik OBJECT IDENTIFIER ::= { moxa 10 }

-- 1.3.6.1.4.1.8691.10.1242.1
    totalChannelNumber OBJECT-TYPE
        SYNTAX Integer32 (1..16)
        MAX-ACCESS read-only
        STATUS current
        DESCRIPTION
            "Total I/O channels."
        ::= { e1242 1 }

-- 1.3.6.1.4.1.8691.10.1242.2
    serverModel OBJECT-TYPE
        SYNTAX OCTET STRING
        MAX-ACCESS read-only
        STATUS current
        DESCRIPTION
            "The I/O server model."
        ::= { e1242 2 }

-- 1.3.6.1.4.1.8691.10.1242.3
    systemTime OBJECT-TYPE
        SYNTAX Integer32
        MAX-ACCESS read-only
        STATUS current
        DESCRIPTION
            "I/O server up time (in seconds)."
        ::= { e1242 3 }

-- 1.3.6.1.4.1.8691.10.1242.4
    firmwareVersion OBJECT-TYPE
        SYNTAX OCTET STRING
        MAX-ACCESS read-only
        STATUS current
        DESCRIPTION
            "The firmware version."
        ::= { e1242 4 }


----------------------------------------------------------------
-- I/O
-- 1.3.6.1.4.1.8691.10.1242.10          
    e1242monitor OBJECT IDENTIFIER ::= { e1242 10 }
----------------------------------------------------------------
-- DI channel
diTable OBJECT-TYPE
        SYNTAX          SEQUENCE OF DIEntry
        MAX-ACCESS      not-accessible
        STATUS          current
        DESCRIPTION     
            "The DI channel monitor table"
        ::= { e1242monitor 1 }

diEntry OBJECT-TYPE
        SYNTAX          DIEntry
        MAX-ACCESS      not-accessible
        STATUS          current
        DESCRIPTION     
            "The DI channel monitor item"
        INDEX { diIndex }
        ::= { diTable 1 }

DIEntry ::= SEQUENCE {
                diIndex     Integer32,
                diType      Integer32,
                diMode      Integer32,
                diStatus    Integer32,
                diFilter    Integer32,
                diTrigger   Integer32,
                diCntStart  Integer32   
                 }

diIndex OBJECT-TYPE
        SYNTAX          Integer32  (0..7)
        MAX-ACCESS      read-only
        STATUS          current
        DESCRIPTION     
            "The channel DI index."
        ::= { diEntry 1 }   
        
diType OBJECT-TYPE
        SYNTAX          Integer32  (0..1)
        MAX-ACCESS      read-only
        STATUS          current
        DESCRIPTION     "The channel DI type. 0=DI, 1=DO"
        ::= { diEntry 2 }
        
diMode OBJECT-TYPE
        SYNTAX          Integer32  (0..1)
        MAX-ACCESS      read-write
        STATUS          current
        DESCRIPTION     "The channel DI mode. 0=DI, 1=Event Counter"
        ::= { diEntry 3 }
 
diStatus OBJECT-TYPE
        SYNTAX          Integer32 (0..4294967295)
        MAX-ACCESS      read-only
        STATUS          current
        DESCRIPTION     "The channel DI status. 0=Off, 1=On in DI mode or N=Count in counter mode"
        ::= { diEntry 4 }
        
diFilter OBJECT-TYPE
        SYNTAX          Integer32  (1..65535)
        MAX-ACCESS      read-write
        STATUS          current
        DESCRIPTION     "The channel DI counter filter. unit=1ms"
        ::= { diEntry 5 }

diTrigger OBJECT-TYPE
        SYNTAX          Integer32  (0..2)
        MAX-ACCESS      read-write
        STATUS          current
        DESCRIPTION     "The channel DI counter trigger level. 0=L2H, 1=H2L, 2=Both"
        ::= { diEntry 6 }

diCntStart OBJECT-TYPE
        SYNTAX          Integer32 (0..1)
        MAX-ACCESS      read-write
        STATUS          current
        DESCRIPTION     "The channel DI counter start/stop. 0=stop, 1=start"
        ::= { diEntry 7 }
      
----------------------------------------------------------------
---------------------------------------------------------------- 
-- DIO channel
dioTable OBJECT-TYPE
		SYNTAX 			SEQUENCE OF DIOEntry
		MAX-ACCESS 		not-accessible
		STATUS 			current
		DESCRIPTION		"The DIO channel monitor table"
		::= { e1242monitor 3 }

dioEntry OBJECT-TYPE
		SYNTAX 			DIOEntry
		MAX-ACCESS 		not-accessible
		STATUS 			current
		DESCRIPTION		"The DIO channel monitor item"
		INDEX { dioIndex }
		::= { dioTable 1 }

DIOEntry ::= SEQUENCE { 
        dioIndex		Integer32,
		dioType			Integer32,
		dioMode			Integer32,
		dioStatus		Integer32,
		dioDIFilter		Integer32,
		dioDITrigger        Integer32,
		dioDICntStart    	Integer32,
		dioDOPulsONWidth   	Integer32,
		dioDOPulsOFFWidth  	Integer32,
   		dioDOPulseStart	    Integer32
		}                       
			
dioIndex OBJECT-TYPE
		SYNTAX 			Integer32(0..7)
		MAX-ACCESS 		read-only
		STATUS 			current
		DESCRIPTION		"The channel DI/DO index."
		::= { dioEntry 1}

dioType OBJECT-TYPE
		SYNTAX 			Integer32(0..1)
		MAX-ACCESS 		read-only
		STATUS 			current
		DESCRIPTION		"The channel DIO type. 0=DI, DO=1"
		::= { dioEntry 2 }
		
dioMode OBJECT-TYPE
		SYNTAX 			Integer32(0..1)
		MAX-ACCESS 		read-write
		STATUS 			current
		DESCRIPTION		"The channel DI Type(0=DI, 1=Event Counter),DO Type(0=DO, 1=Pulse Output)."
		::= { dioEntry 3 }
		
dioStatus OBJECT-TYPE
		SYNTAX 			Integer32(0..4294967295) 
		MAX-ACCESS 		read-write
		STATUS 			current
		DESCRIPTION		"The channel DI status.(0=Off, 1=On in DI mode or N=Count in counter mode),DO status(0=Off, 1=On in DO mode or N=Count in pulse mode)"
		::= { dioEntry 4 }
		
dioDIFilter OBJECT-TYPE
		SYNTAX 			Integer32(1..65535)
		MAX-ACCESS 		read-write
		STATUS 			current
		DESCRIPTION		"The channel DI counter filter. unit=1ms"
		::= { dioEntry 5 }

dioDITrigger OBJECT-TYPE
		SYNTAX 			Integer32(0..2)
		MAX-ACCESS 		read-write
		STATUS 			current
		DESCRIPTION		"The channel DI counter trigger level. 0=L2H, 1=H2L, 2=Both"
		::= { dioEntry 6 } 
dioDICntStart OBJECT-TYPE
		SYNTAX 			Integer32(0..1)
		MAX-ACCESS 		read-write
		STATUS 			current
		DESCRIPTION		"The channel DI counter start/stop. 0=stop, 1=start"
		::= { dioEntry 7 }


dioDOPulsONWidth 	OBJECT-TYPE
		SYNTAX 			Integer32(1..65535)
		MAX-ACCESS 		read-write
		STATUS 			current
		DESCRIPTION		"The channel DO signal ON width. unit=1ms"
		::= { dioEntry 8 }
		
dioDOPulsOFFWidth	OBJECT-TYPE
		SYNTAX 			Integer32(1..65535)
		MAX-ACCESS 		read-write
		STATUS 			current
		DESCRIPTION		"The channel DO signal OFF width. unit=1ms"
		::= { dioEntry 9}


dioDOPulseStart OBJECT-TYPE
		SYNTAX 			Integer32(0..1)
		MAX-ACCESS 		read-write
		STATUS 			current
		DESCRIPTION		"The channel DO pulse start/stop. 0=stop, 1=start"
		::= { dioEntry 10}
     
----------------------------------------------------------------
---------------------------------------------------------------- 
-- ai
aiTable OBJECT-TYPE
		SYNTAX 			SEQUENCE OF AIEntry
		MAX-ACCESS 		not-accessible
		STATUS 			current
		DESCRIPTION		"The ai channel monitor table"
		::= { e1242monitor 4 }

aiEntry OBJECT-TYPE
		SYNTAX			AIEntry
		MAX-ACCESS 		not-accessible
		STATUS 			current
		DESCRIPTION		"The ai channel monitor item"
		INDEX { aiIndex }
		::= { aiTable 1 }

AIEntry ::=	SEQUENCE {
		aiIndex		Integer32,
		aiEnable	Integer32, 
		aiMode 		Integer32,
		aiValue		Integer32,
		aiMin		Integer32,
		aiMax		Integer32
}
-------------------------------------------
aiIndex OBJECT-TYPE
		SYNTAX 			Integer32(0..3)
		MAX-ACCESS 		read-only
		STATUS 			current
		DESCRIPTION		"The ai channel index."
		::= { aiEntry 1 }
aiEnable OBJECT-TYPE
		SYNTAX 			Integer32(0..1)
		MAX-ACCESS 		read-write
		STATUS 			current
		DESCRIPTION		"The ai channel Enable/Disable. Disable=0, Enable=1"
		::= { aiEntry 2 }

aiMode OBJECT-TYPE
		SYNTAX 			Integer32(0..4)
		MAX-ACCESS 		read-write
		STATUS 			current
		DESCRIPTION		"The ai channel Mode. 0-10V=0, 4-20mA=1, 0-20mA=2, 4-20mA Burnout=4"
		::= { aiEntry 3 }

aiValue OBJECT-TYPE
		SYNTAX 			Integer32(0..65535)
		MAX-ACCESS 		read-only
		STATUS 			current
		DESCRIPTION		"The ai channel value (RAW)."
		::= { aiEntry 4 }
		
aiMin OBJECT-TYPE
		SYNTAX 			Integer32(0..65535)
		MAX-ACCESS 		read-only
		STATUS 			current
		DESCRIPTION		"The ai channel minimum value (RAW)."
		::= { aiEntry 5 }
		
aiMax OBJECT-TYPE
		SYNTAX 			Integer32(0..65535)
		MAX-ACCESS 		read-only
		STATUS 			current
		DESCRIPTION		"The ai channel maximum value (RAW)."
		::= { aiEntry 6 }




----------------------------------------------------------------
-- AI TRAP Greater
-- 1.3.6.1.4.1.8691.10.1242.22
    aiTrap-Greater OBJECT IDENTIFIER ::= { e1242 22 }

----------------------------------------------------------------
aiTrapG0 TRAP-TYPE
	ENTERPRISE 		aiTrap-Greater
	DESCRIPTION 		"The ai channel-00 Greater Trap."
	::= 1

aiTrapG1 TRAP-TYPE
	ENTERPRISE 		aiTrap-Greater
	DESCRIPTION 		"The ai channel-01 Greater Trap."
	::= 2

aiTrapG2 TRAP-TYPE
	ENTERPRISE 		aiTrap-Greater
	DESCRIPTION 		"The ai channel-02 Greater Trap."
	::= 3

aiTrapG3 TRAP-TYPE       
	ENTERPRISE 		aiTrap-Greater
	DESCRIPTION 		"The ai channel-03 Greater Trap."
	::= 4


----------------------------------------------------------------
-- AI TRAP Smaller
-- 1.3.6.1.4.1.8691.10.1242.23
    aiTrap-Smaller OBJECT IDENTIFIER ::= { e1242 23 }

----------------------------------------------------------------
aiTrapS0 TRAP-TYPE
	ENTERPRISE 		aiTrap-Smaller
	DESCRIPTION 		"The ai channel-00 Smaller Trap."
	::= 1

aiTrapS1 TRAP-TYPE
	ENTERPRISE 		aiTrap-Smaller
	DESCRIPTION 		"The ai channel-01 Smaller Trap."
	::= 2

aiTrapS2 TRAP-TYPE
	ENTERPRISE 		aiTrap-Smaller
	DESCRIPTION 		"The ai channel-02 Smaller Trap."
	::= 3

aiTrapS3 TRAP-TYPE       
	ENTERPRISE 		aiTrap-Smaller
	DESCRIPTION 		"The ai channel-03 Smaller Trap."
	::= 4



----------------------------------------------------------------
-- Message TRAP
-- 1.3.6.1.4.1.8691.10.1242.30
	messageTrap OBJECT IDENTIFIER ::= { e1242 30 }

----------------------------------------------------------------
activeMessageTrap TRAP-TYPE
	ENTERPRISE 		messageTrap
	DESCRIPTION 	"The SNMP trap with active message"
	::= 1

END
