Nortel-Magellan-Passport-StateSummaryMIB
DEFINITIONS ::= BEGIN

IMPORTS

      TimeTicks,
--   FROM RFC1155-SMI

      MODULE-IDENTITY, OBJECT-TYPE, Gauge32
   FROM SNMPv2-SMI

      DisplayString
   FROM SNMPv2-TC

      components, passportMIBs
   FROM Nortel-Magellan-Passport-UsefulDefinitionsMIB;

stateSummaryMIB MODULE-IDENTITY
  LAST-UPDATED "9707150000Z"
  ORGANIZATION "Nortel"
  CONTACT-INFO "
         Nortel Magellan Network Management

         Postal: P.O. Box 5080, Station F
                 Ottawa, Ontario
                 Canada  K2C 3T1

         Email:  nm_plm@nt.com"
 DESCRIPTION
    "This MIB module specifies the variables used to implement
     the Nortel Magellan Passport state summary functionality."
::= { passportMIBs 7 }

--stateSummaryMIB OBJECT IDENTIFIER  ::= { passportMIBs 7 }

stateSummary OBJECT IDENTIFIER ::= { components 5 }

-- the timeOfLastTableChange group

-- STATUS       current
-- DESCRIPTION
--    " This group contains the variables (timestamps) indicating
--      when a change has occurred in one of the state summary tables.
--      There is one timestamp per table."
timeOfLastTableChange   OBJECT IDENTIFIER ::= { stateSummary 1 }

timeOfLastStateSummTableChange OBJECT-TYPE
   SYNTAX       TimeTicks
   MAX-ACCESS   read-only
   STATUS       current
   DESCRIPTION
        "The value of sysUpTime at the time that an entry in the
         compClassTable detected a change."
   ::= { timeOfLastTableChange 1 }

compClassTable OBJECT-TYPE
    SYNTAX  SEQUENCE OF CompClassEntry
    MAX-ACCESS  not-accessible
    STATUS  current
    DESCRIPTION
            "A list of component classes that have state
             information summaries."
    ::= { stateSummary 2 }

compClassEntry OBJECT-TYPE
    SYNTAX  CompClassEntry
    MAX-ACCESS  not-accessible
    STATUS  current
    DESCRIPTION
            "A component class entry."
    INDEX   { compClass }
    ::= { compClassTable 1 }

CompClassEntry ::=
    SEQUENCE {
        compClass
            OBJECT IDENTIFIER,
        compName
            DisplayString,
        timeOfLastStateStatusChange
            TimeTicks,
        numberDown
            Gauge32,
        numberTroubled
            Gauge32
             }

compClass OBJECT-TYPE
    SYNTAX  OBJECT IDENTIFIER
    MAX-ACCESS  read-only
    STATUS  current
    DESCRIPTION
            "An object identifier which points to the SNMP Mib Arc for
             that particular component class. For example, a
             replication of 1.3.6.1.4.1.562.2.4.1.12 (iso.org.dod.
             internet.private.enterprises.nortel.magellan.passport.
             components.lp) corresponds to the Lp  component class."
    ::= { compClassEntry 1 }

compName OBJECT-TYPE
    SYNTAX  DisplayString
    MAX-ACCESS  read-only
    STATUS  current
      DESCRIPTION
            "The string representation of the component class object
             identifier.  For example, 1.3.6.1.4.1.562.2.4.1.12 (iso.org.
             dod.internet.private.enterprises.nortel.magellan.passport.
             components.lp) is represented as the string, LogicalProcessor."
    ::= { compClassEntry 2 }

timeOfLastStateStatusChange OBJECT-TYPE
    SYNTAX  TimeTicks
    MAX-ACCESS  read-only
    STATUS  current
      DESCRIPTION
            "The value of sysUpTime when an OsiState or OsiStateStatus
             change was detected for the component class.  Currently
             monitored attributes include: AdminState, OperationalState,
             AvailabilityStatus and AlarmStatus."
    ::= { compClassEntry 3 }

numberDown OBJECT-TYPE
    SYNTAX  Gauge32
    MAX-ACCESS  read-only
    STATUS  current
      DESCRIPTION
            "The number of component instances that are down.  A component
             is considered down when its administrative state is locked
             or its operational state is disabled. "
    ::= { compClassEntry 4 }

numberTroubled OBJECT-TYPE
    SYNTAX  Gauge32
    MAX-ACCESS  read-only
    STATUS  current
      DESCRIPTION
            "The number of component instances that are troubled. A component
             is considered troubled when its administrative status is
             shuttingDown or its alarm status is not empty or its availability
             status is degraded."
    ::= { compClassEntry 5 }

--
-- Version and Compliance statements
--


-- Object-Group Statement:

-- OBJECTS   { ifRowPointer }
-- STATUS     current
-- DESCRIPTION
--       "A list of all current accessible leaf objects."

stateSummaryGroupBE00A OBJECT IDENTIFIER
::= { stateSummaryMIB
      stateSummaryGroup(1)
      stateSummaryGroupBE(3)
      stateSummaryGroupBE00(2)  2 }


-- Agent-Capabilities Statement:

-- PRODUCT-RELEASE "Passport Release 5.0 State Summary ."
-- STATUS          current
-- DESCRIPTION
--    "State Summary : MIB Version BE00A."
-- SUPPORTS        Nortel-Magellan-Passport-StateSummaryMIB
-- INCLUDES        { stateSummaryGroupBE00A }

stateSummaryCapabilitiesBE00A OBJECT IDENTIFIER
::= { stateSummaryMIB
      stateSummaryCapabilities(3)
      stateSummaryCapabilitiesBE(3)
      stateSummaryCapabilitiesBE00(2)  2 }

END
