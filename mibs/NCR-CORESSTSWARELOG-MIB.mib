NCR-CORESSTSWARELOG-MIB DEFINITIONS ::= BEGIN

--
-- NCR SST Software Log MIB
--

IMPORTS
    enterprises, Counter
        FROM RFC1155-SMI
    OBJECT-TYPE
        FROM RFC-1212
    DisplayString
        FROM RFC1213-MIB
    TruthValue
    FROM RFC1253-MIB;
        
        ncr                     OBJECT IDENTIFIER ::= { enterprises 191 }
        sst                     OBJECT IDENTIFIER ::= { ncr 39 }
        sstCore                 OBJECT IDENTIFIER ::= { sst 1 }
        sstProduct              OBJECT IDENTIFIER ::= { sst 13 }
        sstObjs                 OBJECT IDENTIFIER ::= { sstProduct 2}
        sstGeneral              OBJECT IDENTIFIER ::= { sstObjs 1 }    
        sstDevice               OBJECT IDENTIFIER ::= { sstObjs 2 }
        sstApplic               OBJECT IDENTIFIER ::= { sstObjs 3 }
        sstLogs                 OBJECT IDENTIFIER ::= { sstObjs 4 }

-----------------------------------------------------------
-- Software Log Table
-----------------------------------------------------------

sstSWareLogTable OBJECT-TYPE
    SYNTAX  SEQUENCE OF SstSWareLogEntry
    ACCESS  not-accessible
    STATUS  mandatory
    DESCRIPTION                        
    "This group defines the attributes of event entries in the 
    SST software log."
    ::= { sstLogs 9 }

sstSWareLogEntry OBJECT-TYPE
    SYNTAX SstSWareLogEntry
    ACCESS  not-accessible
    STATUS  mandatory
        DESCRIPTION
        "This defines the contents of the table."
    INDEX   { sstSWareLogIndex }
    ::= { sstSWareLogTable 1 }

SstSWareLogEntry ::=
    SEQUENCE { 
                    sstSWareLogIndex           INTEGER,
                    sstSWareLogLineNumber      INTEGER,
                    sstSWareLogSourceName      DisplayString,
                    sstSWareLogProcName        DisplayString,
                    sstSWareLogThrdName        DisplayString,
                    sstSWareLogDLLName         DisplayString,
                    sstSWareLogEventId         INTEGER,
                    sstSWareLogLevel           INTEGER,
                    sstSWareLogReason          INTEGER,
                    sstSWareLogBinaryType         INTEGER,
                    sstSWareLogBinaryData         OCTET STRING,
                    sstSWareLogStrData         DisplayString                    
                }

sstSWareLogIndex OBJECT-TYPE
    SYNTAX INTEGER
    ACCESS read-only
    STATUS mandatory    
    DESCRIPTION 
    "A unique number for every entry in the software log."
    ::= { sstSWareLogEntry 1 }

sstSWareLogLineNumber OBJECT-TYPE
    SYNTAX INTEGER
    ACCESS read-only
    STATUS mandatory    
    DESCRIPTION 
    "The line number in the source file where the event occurred."
    ::= { sstSWareLogEntry 2 }

sstSWareLogSourceName OBJECT-TYPE
    SYNTAX DisplayString
    ACCESS read-only
    STATUS mandatory    
    DESCRIPTION 
    "The name of the source file where the event occurred."
    ::= { sstSWareLogEntry 3 }

sstSWareLogProcName OBJECT-TYPE
    SYNTAX DisplayString
    ACCESS read-only
    STATUS mandatory    
    DESCRIPTION 
    "The name of the process that generated the event."
    ::= { sstSWareLogEntry 4 }

sstSWareLogThrdName OBJECT-TYPE
    SYNTAX DisplayString
    ACCESS read-only
    STATUS mandatory    
    DESCRIPTION 
    "The name of the thread that generated the event."
    ::= { sstSWareLogEntry 5 }

sstSWareLogDLLName OBJECT-TYPE
    SYNTAX DisplayString
    ACCESS read-only
    STATUS mandatory    
    DESCRIPTION 
    "The name of the DLL that generated the event."
    ::= { sstSWareLogEntry 6 }

sstSWareLogEventId OBJECT-TYPE
    SYNTAX INTEGER
    ACCESS read-only
    STATUS mandatory    
    DESCRIPTION 
    "The identifier for the event."
    ::= { sstSWareLogEntry 7 }

sstSWareLogLevel OBJECT-TYPE
    SYNTAX INTEGER
    ACCESS read-only
    STATUS mandatory    
    DESCRIPTION 
    "The level of the log entry: information, warning or error."
    ::= { sstSWareLogEntry 8 }

sstSWareLogReason OBJECT-TYPE
    SYNTAX INTEGER
    ACCESS read-only
    STATUS mandatory    
    DESCRIPTION 
    "The category of the event: a normal event, a system escape or a 
    critical error."
    ::= { sstSWareLogEntry 9 }

sstSWareLogBinaryType OBJECT-TYPE
    SYNTAX INTEGER
    ACCESS read-only
    STATUS mandatory    
    DESCRIPTION 
    "This indicates the type of binary data."
    ::= { sstSWareLogEntry 10 }

sstSWareLogBinaryData OBJECT-TYPE
    SYNTAX OCTET STRING
    ACCESS read-only
    STATUS mandatory    
    DESCRIPTION 
    "A description of the event in binary data format."
    ::= { sstSWareLogEntry 11 }

sstSWareLogStrData OBJECT-TYPE
    SYNTAX DisplayString
    ACCESS read-only
    STATUS mandatory    
    DESCRIPTION 
    "Information about the cause of the event."
    ::= { sstSWareLogEntry 12 }

END
