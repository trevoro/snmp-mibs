-- Each module definition could be in its own file.
-- They have been concatenated and placed in this file.
-- They can be separated if this file grows too big.
--
-- This document should be viewed using tab-stops 4 spaces wide.
-- When updating this document, please use tabs, not spaces, for indents.

-- ========================================================================
-- Start - PERIBIT-GLOBAL-REG Module

-- Peribit OID infrastructure layout.
--
-- The convention described in "Understanding SNMP MIBs"
-- (David Perkins, Evan McGinnis), Chapter 8, has generally been followed.

PERIBIT-GLOBAL-REG DEFINITIONS ::= BEGIN

	IMPORTS
		MODULE-IDENTITY, OBJECT-IDENTITY,
		enterprises
			FROM SNMPv2-SMI;

	pnGlobalRegModule MODULE-IDENTITY
		LAST-UPDATED			"200107292200Z"
		ORGANIZATION			"Peribit Networks, Inc"
		CONTACT-INFO			"
					Customer Support
					Peribit Networks, Inc.
					2300 Central Expressway
					Santa Clara, CA 95050

					+1 866-PERIBIT
					support@peribit.com"

		DESCRIPTION				"
			A MIB module containing top-level OID definitions
			for various sub-trees for Peribit Networks' enterprise MIB modules."

		REVISION				"200403151400Z"
		DESCRIPTION				"
			Add sr100 product OID."

		REVISION				"200306262000Z"
		DESCRIPTION				"
			Add sr80 product OID."

		REVISION				"200107292200Z"
		DESCRIPTION				"
			Rev 1.0
			Initial version of MIB module PERIBIT-GLOBAL-REG."

		::= { pnModules 1 }

	peribitRoot OBJECT-IDENTITY
		STATUS					current
		DESCRIPTION				"
			The root of the OID sub-tree assigned to Peribit Networks assigned by
			the Internet Assigned Numbers Authority (IANA)."
		::= { enterprises 8239 }

	pnReg OBJECT-IDENTITY
		STATUS					current
		DESCRIPTION				"
			Sub-tree for registrations - identification of modules and logical and
			physical components."
		::= { peribitRoot 1 }

	pnModules OBJECT-IDENTITY
		STATUS					current
		DESCRIPTION				"
			Sub-tree for module registrations."
		::= { pnReg 1 }

	pnMibs OBJECT-IDENTITY
		STATUS					current
		DESCRIPTION				"
			Sub-tree for all Peribit object and event definitions."
		::= { peribitRoot 2 }

	pnCaps OBJECT-IDENTITY
		STATUS					current
		DESCRIPTION				"
			Sub-tree for agent profiles."
		::= { peribitRoot 3 }

	pnReqs OBJECT-IDENTITY
		STATUS					current
		DESCRIPTION				"
			Sub-tree for management application requirements."
		::= { peribitRoot 4 }

	pnExpr OBJECT-IDENTITY
		STATUS					current
		DESCRIPTION				"
			Sub-tree for experimental definitions."
		::= { peribitRoot 5 }

	-- Sub-trees for Peribit managed objects

	pnCommonMib OBJECT-IDENTITY
		STATUS					current
		DESCRIPTION				"
			Sub-tree for common Peribit object and event definitions.
			These would be implemented by all Peribit products."
		::= { pnMibs 1 }

	pnSpecificMib OBJECT-IDENTITY
		STATUS					current
		DESCRIPTION				"
			Sub-tree for specific Peribit object and event definitions."
		::= { pnMibs 2 }

	-- OID registrations for Peribit product lines
	-- These OIDs are never queried by management stations.
	-- They can be returned as product identifiers in responses.

	pnProductSr OBJECT-IDENTITY
		STATUS					current
		DESCRIPTION				"
			The Sequence Reducer product family."
		::= { pnReg 2 }

		pnProductSr50 OBJECT-IDENTITY
			STATUS					current
			DESCRIPTION				"
				Sequence Reducer Model 50"
			::= { pnProductSr 1 }

		pnProductSr55 OBJECT-IDENTITY
			STATUS					current
			DESCRIPTION				"
				Sequence Reducer Model 55"
			::= { pnProductSr 2 }

		pnProductSr20 OBJECT-IDENTITY
			STATUS					current
			DESCRIPTION				"
				Sequence Reducer Model 20"
			::= { pnProductSr 3 }

		pnProductSr80 OBJECT-IDENTITY
			STATUS					current
			DESCRIPTION				"
				Sequence Reducer Model 80"
			::= { pnProductSr 4 }

		pnProductSr100 OBJECT-IDENTITY
			STATUS					current
			DESCRIPTION				"
				Sequence Reducer Model 100"
			::= { pnProductSr 5 }

		pnProductSm500 OBJECT-IDENTITY
			STATUS					current
			DESCRIPTION				"
				Sequence Mirror Model 500"
			::= { pnProductSr 6 }

		pnProductSr15 OBJECT-IDENTITY
			STATUS					current
			DESCRIPTION				"
				Sequence Reducer Model 15"
			::= { pnProductSr 7 }
END

-- End - PERIBIT-GLOBAL-REG Module

-- ========================================================================
-- Start - PERIBIT-GLOBAL-TC Module

-- Peribit Global Textual Conventions
--
-- The convention described in "Understanding SNMP MIBs"
-- (David Perkins, Evan McGinnis), Chapter 8, has generally been followed.
