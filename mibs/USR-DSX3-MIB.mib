USR-DSX3-MIB DEFINITIONS ::= BEGIN
	IMPORTS
        OBJECT-TYPE
            FROM SNMPv2-SMI
        DisplayString, usrDsx3, UsrConfigStatus
            FROM USR-DEFINITIONS-MIB;
	usrDsx3ConfigFileName OBJECT-TYPE
		SYNTAX      DisplayString
		MAX-ACCESS  read-only
		STATUS      current
		DESCRIPTION		
		  "The name of a ConfigFile to read/write permanent
		   database records. If the value of this object is an
                   empty string, then the NMBA process uses the
                   default name `@file://Dsx3.cfg'. "
	::= { usrDsx3 1 }
	usrDsx3CFMStatusFlag  OBJECT-TYPE
	 	SYNTAX	  UsrConfigStatus
		MAX-ACCESS      read-write
		STATUS      current
		DESCRIPTION
		  "Setting the value of this object to `save' causes the values
		   of the Dsx3SlotTable to be written out to the
                   current config file, which is stored in the 
                   usrDsx3ConfigFileName object. While the new
                   ConfigFile is being written, the NMBA process
		   will set the value of this flag to `saving''. Any
		   attempts to set the value while it is not `normal'
		   (i.e. the file is currently being written to the
		   ConfigFile) while result in a badValue error being
		   returned. Setting the value to `normal' will result in no
		   action."
	::= { usrDsx3 2 }
    usrDsx3ConfigTable OBJECT-TYPE
        SYNTAX  SEQUENCE OF UsrDsx3ConfigEntry
        MAX-ACCESS  not-accessible
        STATUS  current
        DESCRIPTION
                "USR Specific variable Config table."
        ::= { usrDsx3 3 }
    usrDsx3ConfigEntry OBJECT-TYPE
        SYNTAX  UsrDsx3ConfigEntry
        MAX-ACCESS  not-accessible
        STATUS  current
        DESCRIPTION
                "An entry in the DSX3/E3 Configuration table."
        INDEX   { usrDsx3LineIndex }
        ::= { usrDsx3ConfigTable 1 }
    UsrDsx3ConfigEntry ::=
        SEQUENCE {
            usrDsx3LineIndex
                INTEGER,
            usrDsx3CableLength
                INTEGER,
            usrDsx3FrameType
                INTEGER,
            usrDsx3PayloadScrambling
                INTEGER,
            usrDsx3TransmitCells
                INTEGER,
            usrDsx3RecieveCells
                INTEGER
        }
    usrDsx3LineIndex OBJECT-TYPE
        SYNTAX  INTEGER (1..65535)
        MAX-ACCESS  read-only
        STATUS  current
        DESCRIPTION
        "This object is the identifier of a DSX3/E3
        Interface on a managed device.  If there is an
        ifEntry that is directly associated with this
        and only this DSX3/E3 interface, it should have
        the same value as ifIndex.  Otherwise, number
        the dsx3LineIndices with an unique identifier
        following the rules of choosing a number that
        is greater than ifNumber and numbering the
        inside interfaces (e.g., equipment side) with
        even numbers and outside interfaces (e.g,
        network side) with odd numbers."
	::= { usrDsx3ConfigEntry 1 }
	usrDsx3CableLength  OBJECT-TYPE
		SYNTAX   INTEGER {
         usrDsx3ShortHaul(1),
         usrDsx3LongHaul(2)
			}
		MAX-ACCESS  read-write
		STATUS      current
		DESCRIPTION
                  "This variable indicates which compensation 
                  measures are to be used with varying cable
                  lengths.
                  usrDsx3ShortHaul refers to cable lengths
                  shorter than xx meters. atmDsx3LongHaul handles
                  cable lengths longer than that."
	        --CONFIGURABLE
	::= { usrDsx3ConfigEntry 2 }
	usrDsx3FrameType  OBJECT-TYPE
		SYNTAX   INTEGER {
         usrDsx3Adm(1),
         usrDsx3Plcp(2)
			}
		MAX-ACCESS  read-write
		STATUS      current
		DESCRIPTION
                "This variable indicates which frame type
                 to use in transmission.
                 usrDsx3Adm sets the Phy to use Direct Mapping
                 on transmit , and usrDsx3Plcp uses the PLCP
                 framing format."
	        --CONFIGURABLE
	::= { usrDsx3ConfigEntry 3 }
	usrDsx3PayloadScrambling OBJECT-TYPE
		SYNTAX   INTEGER {
			enabled(1),
			disabled(2)
			}
      MAX-ACCESS      read-write
      STATUS      current
      DESCRIPTION
            "An indicator that tells if this interface is using
             Payload Scrambling.  Setting the variable to enabled
             sets the Phy interface allow scrambling."
	        --CONFIGURABLE
   ::= { usrDsx3ConfigEntry 4 }
    usrDsx3TransmitCells OBJECT-TYPE
        SYNTAX  INTEGER (1..65535)
        MAX-ACCESS  read-only
        STATUS  current
        DESCRIPTION
        "This object contains the number of cells
        transmitted in the current valid interval. At
        the end of each interval the count is reset."
	::= { usrDsx3ConfigEntry 5 }
    usrDsx3RecieveCells OBJECT-TYPE
        SYNTAX  INTEGER (1..65535)
        MAX-ACCESS  read-only
        STATUS  current
        DESCRIPTION
        "This object contains the number of cells
        received in the current valid interval. At
        the end of each interval the count is reset."
	::= { usrDsx3ConfigEntry 6 }
END         -- End usrDsx3 MIB definitions
-- ************************************************************************
--
--	usr_atm_1483_pvc.mib - A MIB file for the Netserver ATM
--                             RFC1483 PVC MIB. 
--
-- Author:         Mike Redden
--
