-- A MIB to define nortel and dialaccess

CPM-NORTEL-MIB DEFINITIONS ::= BEGIN

IMPORTS
         enterprises       FROM SNMPv2-SMI
         MODULE-IDENTITY   FROM SNMPv2-SMI;

nortel MODULE-IDENTITY
       LAST-UPDATED "9906231337Z"    -- June 23, 1999 08:37 EST
       ORGANIZATION "Nortel Networks"
       CONTACT-INFO
               "Nortel Customer Support 
                Nortel Networks 
                E-Mail: joedev@nortel.ca"
       DESCRIPTION
               ""
       ::= { enterprises 562 }


dialaccess OBJECT IDENTIFIER ::= { nortel 14 }

END
