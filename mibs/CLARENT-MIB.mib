CLARENT-MIB DEFINITIONS ::= BEGIN
 
	  --
	  -- Clarent Corporation
	  -- 850 Chesapeake Corporation
	  -- Redwood City, CA 94063
	  -- Version 4.0(alpha)

	  IMPORTS
		  enterprises, NetworkAddress, IpAddress
			  FROM RFC1155-SMI
		  OBJECT-TYPE
			  FROM RFC-1212
		  DisplayString
			  FROM RFC1213-MIB
		TRAP-TYPE
			FROM RFC-1215;
 
 
	  clarent       OBJECT IDENTIFIER ::= { enterprises 2858 }
	  gateway       OBJECT IDENTIFIER ::= { clarent 1 }
	  ccreadvars   OBJECT IDENTIFIER ::= { clarent 2 }
	  rdc           OBJECT IDENTIFIER ::= { clarent 3 }
	  clarent-traps OBJECT IDENTIFIER ::= { clarent 4 }
	  clearinghouse OBJECT IDENTIFIER ::= { clarent 5 }
	  gwControl    OBJECT IDENTIFIER ::= { clarent 6 }
	  ccControl    OBJECT IDENTIFIER ::= { clarent 7 }
	  gatewayports  OBJECT IDENTIFIER ::= { clarent 8 }     
	  gatewaytable  OBJECT IDENTIFIER ::= { clarent 9 }
	  gwtrafficstats  OBJECT IDENTIFIER ::= { clarent 10 }
	  trap-Parameters OBJECT IDENTIFIER ::= { clarent 48 }
	 
	 
	  mgt						OBJECT IDENTIFIER	::= { clarent 100 }
	  packageManagement			OBJECT IDENTIFIER 	::=	{ mgt 1 }
	  gwStatisticsManagement	OBJECT IDENTIFIER 	::=	{ mgt 2 }

	  throughPacket				OBJECT IDENTIFIER	::= { mgt 3 }
		  tpStatus					OBJECT IDENTIFIER	::= { throughPacket 1 }
		  tpConfig 					OBJECT IDENTIFIER	::= { throughPacket 2 }
		  tpStatisticsManagement	OBJECT IDENTIFIER	::= { throughPacket 3 }

	  procManagement			OBJECT IDENTIFIER	::= { mgt 4 }

	  versionManagement			OBJECT IDENTIFIER	::= { mgt 5 }

	  cSysManagement				OBJECT IDENTIFIER	::= { mgt 6 }
		  cSysStatus				OBJECT IDENTIFIER	::= { cSysManagement 1 }
		  cSysControl				OBJECT IDENTIFIER	::= { cSysManagement 2 }


	 cGatekeeper	OBJECT IDENTIFIER	::= { mgt 20 }
	 cGkStatus		OBJECT IDENTIFIER 	::= { cGatekeeper 1 }
	 cGkConfig		OBJECT IDENTIFIER 	::= { cGatekeeper 2 }
	 cGkStatisticsManagement		OBJECT IDENTIFIER 	::= { cGatekeeper 3 }
	 clarent-gktraps				OBJECT IDENTIFIER 	::= { cGatekeeper 100 }


	  -- gateway MIB
 
	  gatewayStatus OBJECT-TYPE
	      SYNTAX  DisplayString
	      ACCESS  read-only
	      STATUS  mandatory
	      DESCRIPTION
		  "The number of ports currently in use, as well as the 
		   number of calls, call time, and hold time for each port
		   (# sign-delimited string)"
	      ::= { gateway 1 }
 

	  portInUseCount OBJECT-TYPE
	      SYNTAX  INTEGER
	      ACCESS  read-only
	      STATUS  mandatory
	      DESCRIPTION
		      "Number of ports currently in use"
	      ::= { gateway 2 }
 
	  gwnumberOfCalls OBJECT-TYPE
	      SYNTAX  DisplayString
	      ACCESS  read-only
	      STATUS  mandatory
	      DESCRIPTION
		      "Number of calls per port (comma-delimited string)"
	      ::= { gateway 3 }
 
	  portCallTime OBJECT-TYPE
	      SYNTAX  DisplayString
	      ACCESS  read-only
	      STATUS  mandatory
	      DESCRIPTION
		      "Call time per port (comma-delimited string)"
	      ::= { gateway 4 }
 
	  portHoldTime OBJECT-TYPE
	      SYNTAX  DisplayString
	      ACCESS  read-only
	      STATUS  mandatory
	      DESCRIPTION
		      "Hold time per port (comma-delimited string) "
	      ::= { gateway 5 }
 
	  trafficStatus OBJECT-TYPE
	      SYNTAX  DisplayString
	      ACCESS  read-only
	      STATUS  mandatory
	      DESCRIPTION
		      "Traffic information: idle, ingress, egress, fax, and out of service time"
	      ::= { gateway 6 }
 
	  gwOperState OBJECT-TYPE
	      SYNTAX  INTEGER {
			  enabled(0),
			  disabled(1)
		      }
	      ACCESS  read-only
	      STATUS  mandatory
	      DESCRIPTION
		      "State of the GW, enabled means running, disabled means not running"
	      ::= { gateway 7 }
 
	  gwBoardType OBJECT-TYPE
	      SYNTAX  INTEGER {
			  noBoard(0),
			  quad-T1(1),
			  quad-E1(2),
			  wti8(3),
			  wti16(4),
			  wti24(5),
			  wti32(6),
			  quad-T1-ISDN(7),
			  quad-E1-ISDN(8),
			  t1-ISDN(9),
			  e1-ISDN(10),
			  quad-T1-SS7(11),
			  quad-E1-SS7(12),
			  t1-SS7(13),
			  e1-SS7(14),
			  ag2000(15),
			  ag8(16),
			  t1(17),
			  e1(18)
		      }
	      ACCESS  read-only
	      STATUS  mandatory
	      DESCRIPTION
		      "Type of boards loaded in Gateway"
	      ::= { gateway 8 }
 
	  gwNumBoards OBJECT-TYPE
	      SYNTAX  INTEGER 
	      ACCESS  read-only
	      STATUS  mandatory
	      DESCRIPTION
		      "Number of boards loaded in Gateway"
	      ::= { gateway 9 }
 
	  gwPortsPerFirstSpan OBJECT-TYPE
	      SYNTAX  INTEGER 
	      ACCESS  read-only
	      STATUS  mandatory
	      DESCRIPTION
		      "number of ports on the first span in a multi-span board"
	      ::= { gateway 10 }
		  
	  gwPortsPerSpan OBJECT-TYPE
	      SYNTAX  INTEGER 
	      ACCESS  read-only
	      STATUS  mandatory
	      DESCRIPTION
		      "number of ports on a span in a multi-span board"
	      ::= { gateway 11 }

	  gwSpansPerBoard OBJECT-TYPE
	      SYNTAX  INTEGER 
	      ACCESS  read-only
	      STATUS  mandatory
	      DESCRIPTION
		      "number of spans on a board"
	      ::= { gateway 12 }


	  gwPortStatusList OBJECT-TYPE
	      SYNTAX  OCTET STRING 
	      ACCESS  read-only
	      STATUS  mandatory
	      DESCRIPTION
		      "returns an OCTET string of length equal to the number of ports
			 in the system. Each byte indicates the status of the port at that
			 offset. That values are identical to the portStatus Value defined 
			 in the Port Table below "
	      ::= { gateway 13 }

	  gwControlVal OBJECT-TYPE
	      SYNTAX  DisplayString
	      ACCESS  read-write
	      STATUS  mandatory
	      DESCRIPTION
		      "Controls Clarent Gateway"
	      ::= { gwControl 1 }
 
	  trapParm1 OBJECT-TYPE
	      SYNTAX  INTEGER
	      ACCESS  read-write
	      STATUS  mandatory
	      DESCRIPTION
		      "Allows traps to have integer parameters"
	      ::= { gwControl 2 }


	  trapParm2 OBJECT-TYPE
	      SYNTAX  INTEGER
	      ACCESS  read-write
	      STATUS  mandatory
	      DESCRIPTION
		      "Allows traps to have integer parameters"
	      ::= { gwControl 3 }

	  trapParm3 OBJECT-TYPE
	      SYNTAX  INTEGER
	      ACCESS  read-write
	      STATUS  mandatory
	      DESCRIPTION
		      "Allows traps to have integer parameters"
	      ::= { gwControl 4 }


	  trapParm4 OBJECT-TYPE
	      SYNTAX  DisplayString
	      ACCESS  read-write
	      STATUS  mandatory
	      DESCRIPTION
		      "Allows traps to have string parameters"
	      ::= { gwControl 5 }

	  clarentcfg OBJECT-TYPE
	      SYNTAX  DisplayString
	      ACCESS  read-write
	      STATUS  mandatory
	      DESCRIPTION
		      "Private control field"
	      ::= { gwControl 6 }

	  enablePort OBJECT-TYPE
	      SYNTAX  INTEGER
	      ACCESS  read-write
	      STATUS  mandatory
	      DESCRIPTION
		      "Enable the port passed in the varbind. For example, to enable port 9, 
			set the value of this variable to 9.  Setting the value of this variable
			to -1 enables all ports."
	      ::= { gwControl 7 }

	  disablePort OBJECT-TYPE
	      SYNTAX  INTEGER
	      ACCESS  read-write
	      STATUS  mandatory
	      DESCRIPTION
		      "Disable the port passed in the varbind. For example, to disable port 11,
			set the value of this variable to 11. Setting the value of this variable
			to -1 disables all ports."
	      ::= { gwControl 8 }

	  hangupPort OBJECT-TYPE
	      SYNTAX  INTEGER
	      ACCESS  read-write
	      STATUS  mandatory
	      DESCRIPTION
		      "Hang up the port passed in the varbind. For example, to hang up port 10,
			set the value of this variable to 10. Setting the value of this variable
			to -1 hangs up all ports."
	      ::= { gwControl 9 }		

	  -- cmdcentre MIB
 
	  ccStatus OBJECT-TYPE
	      SYNTAX  DisplayString
	      ACCESS  read-only
	      STATUS  mandatory
	      DESCRIPTION
		      "Clarent Command Center status"
	      ::= { ccreadvars 1 }

	  ccOperState OBJECT-TYPE
	      SYNTAX  INTEGER {
			  enabled(0),
			  disabled(1)
		      }
	      ACCESS  read-only
	      STATUS  mandatory
	      DESCRIPTION
		      "State of the CC, enabled means running, disabled means not running"
	      ::= { ccreadvars 2 }
 
	  ccControlval OBJECT-TYPE
	      SYNTAX  DisplayString
	      ACCESS  read-write
	      STATUS  mandatory
	      DESCRIPTION
		      "Controls Clarent Command Center"
	      ::= { ccControl 1 }
 
	  -- rdc MIB
 
	  rdcStatus OBJECT-TYPE
	      SYNTAX  DisplayString
	      ACCESS  read-only
	      STATUS  mandatory
	      DESCRIPTION
		      "Roaming Domain Controller status"
	      ::= { rdc 1 }



	  -- the GatewayPorts group


	  gwNumPhysicalPorts OBJECT-TYPE
	      SYNTAX  INTEGER
	      ACCESS  read-only
	      STATUS  mandatory
	      DESCRIPTION
		      "Number of physical gateway ports present on this system (regardless of
		      their current states)"
	      ::= { gatewayports 1 }


	  -- the GatewayPorts table

	  -- The GatewayPorts table contains information about the 
	  -- licensed ports in the Gateway. The number of licensed ports
	  -- can be less than the number of physical ports.
	  -- A value of -1 for the portStatus of any port indicates that the
	  -- port is not licensed and cannot be used.

	  gwPortTable OBJECT-TYPE
	      SYNTAX  SEQUENCE OF GWPortEntry
	      ACCESS  not-accessible
	      STATUS  mandatory
	      DESCRIPTION
		      "A list of gateway port entries.  The number of
		      usable ports is governed by the number of licensed ports."
	      ::= { gatewayports 2 }

	  gwPortEntry OBJECT-TYPE
	      SYNTAX  GWPortEntry
	      ACCESS  not-accessible
	      STATUS  mandatory
	      DESCRIPTION
		      "The status of a port"
	      INDEX   { portIndex }
	      ::= { gwPortTable 1 }

	  GWPortEntry ::=
	      SEQUENCE {
		portIndex
			INTEGER,
		portStatus
			INTEGER,
		numberOfCalls
			INTEGER,
		avgHoldTime
			INTEGER,
		xmitCount
			INTEGER,
		recvCount
			INTEGER,
		ingressTime
			INTEGER,
		ingressCount
			INTEGER,
		egressTime
			INTEGER,
		egressCount
			INTEGER,
		clarentreserved
			INTEGER,
		totalVoiceUsage
			INTEGER,
		voicecount
			INTEGER,
		totalFaxUsage
			INTEGER,
		faxcount
			INTEGER,
		totalDataUsage
			INTEGER,
		datacount
			INTEGER,
		linePortState
			INTEGER,
		linePortLocMState
			INTEGER,
		linePortRemMState
			INTEGER,
		ipPortState
			INTEGER,
		ipPortLocMState
			INTEGER,
		ipPortRemMState
			INTEGER,
		connectedCalls
			INTEGER,
		remoteChannel
			INTEGER,
		remoteGWId
			INTEGER,
		currentHoldTime
			INTEGER,
		currentAni 
			DisplayString, 
		currentDnis  
			DisplayString
	      }

	portIndex OBJECT-TYPE
	      SYNTAX  INTEGER
	      ACCESS  read-only
	      STATUS  mandatory
	      DESCRIPTION
		      "A unique number for each port, ranging from 0 (zero) to the
		      number of physical ports"
		::= { gwPortEntry 1 }

	portStatus OBJECT-TYPE
	      SYNTAX  INTEGER {
			kVoiceOnHook (0),
			kVoiceOffHook (1),
			kVoiceOutOfService ( 2 ),
			kVoiceBusyOutOfService (3),
			kFaxOffHook (4),
			kFaxByPassOffHook (5),
			kDataOffHook (6),
			kVoiceMakeBusyOutCall (7),
			kPortDisabled (8),
			kUnknownState (9),
			kVoiceOffHookIngress (10),
			kVoiceOffHookEgress (11),
			kFaxOffHookIngress (12),
			kFaxOffHookEgress (13),
			kDataOffHookIngress (14),
			kDataOffHookEgress (15)
		      }
	      ACCESS  read-only
	      STATUS  mandatory
	      DESCRIPTION
		      "Port state"
		::= { gwPortEntry 2 }



	numberOfCalls OBJECT-TYPE
		SYNTAX INTEGER
		ACCESS read-only
		STATUS mandatory
		DESCRIPTION 
			"Number of calls made on the port"
		::= { gwPortEntry 3 }

	avgHoldTime OBJECT-TYPE
		SYNTAX INTEGER
		ACCESS read-only
			STATUS mandatory
			DESCRIPTION 
			"Average time per call on the port"
		::= { gwPortEntry 4 }

	xmitCount OBJECT-TYPE
		SYNTAX INTEGER
		ACCESS read-only
			STATUS mandatory
			DESCRIPTION "   "
		::= { gwPortEntry 5 }

	recvCount OBJECT-TYPE
		SYNTAX INTEGER
		ACCESS read-only
			STATUS mandatory
			DESCRIPTION "   "
		::= { gwPortEntry  6 }

	ingressTime OBJECT-TYPE
		SYNTAX INTEGER
		ACCESS read-only
			STATUS mandatory
			DESCRIPTION 
			"Total ingress time, in seconds, on the port"
		::= { gwPortEntry 7 }

	ingressCount OBJECT-TYPE
		SYNTAX INTEGER
		ACCESS read-only
			STATUS mandatory
			DESCRIPTION 
			"Total number of ingress calls on the port"
		::= { gwPortEntry 8 }

	egressTime OBJECT-TYPE
		SYNTAX INTEGER
		ACCESS read-only
			STATUS mandatory
			DESCRIPTION "Total egress time, in seconds, on the port"
		::= { gwPortEntry 9 }

	egressCount OBJECT-TYPE
		SYNTAX INTEGER
		ACCESS read-only
			STATUS mandatory
			DESCRIPTION "Total number of egress calls on the port"
		::= { gwPortEntry 10 }

	clarentreserved OBJECT-TYPE
		SYNTAX INTEGER
		ACCESS read-only
			STATUS mandatory
			DESCRIPTION "Reserved"
		::= { gwPortEntry 11 }

	totalVoiceUsage OBJECT-TYPE
		SYNTAX INTEGER
		ACCESS read-only
			STATUS mandatory
			DESCRIPTION "Time, in seconds, used for voice calls on the port"
		::= { gwPortEntry 12 }

	voicecount OBJECT-TYPE
		SYNTAX INTEGER
		ACCESS read-only
			STATUS mandatory
			DESCRIPTION "Total number of voice calls on the port"
		::= { gwPortEntry 13 }

	totalFaxUsage OBJECT-TYPE
		SYNTAX INTEGER
		ACCESS read-only
			STATUS mandatory
			DESCRIPTION "Time, in seconds, used for fax calls on the port"
		::= { gwPortEntry 14 }

	faxcount OBJECT-TYPE
		SYNTAX INTEGER
		ACCESS read-only
			STATUS mandatory
			DESCRIPTION "Total number of fax calls on the port"
		::= { gwPortEntry 15 }

	totalDataUsage OBJECT-TYPE
		SYNTAX INTEGER
		ACCESS read-only
			STATUS mandatory
			DESCRIPTION "Time, in seconds, used for data transfer/modem calls on the port"
		::= { gwPortEntry 16 }

	datacount OBJECT-TYPE
		SYNTAX INTEGER
		ACCESS read-only
			STATUS mandatory
			DESCRIPTION 
			"Number of data events on the port"
		::= { gwPortEntry 17 }

	linePortState OBJECT-TYPE
	      SYNTAX  INTEGER {
			  idle(0),
			  callInitiated(1),  
			  overlapsend(2),
			  outcallproceding(3),
			  outcallalerting(4),
			  creserved1(5),
			  callpresented(6),
			  callreceived(7),
			  connectrequested(8),
			  creserved2(9),
			  connected(10),
			  disconnectind(11),
			  disconnreq(12),
			
			  notopened(50),
			  portopening(51),
			  portopend(52),
			  startingprot(53),
			  openfailed(54),
			  portclosing(55),
			  portclosed(56)
		      }
	      ACCESS  read-only
	      STATUS  mandatory
	      DESCRIPTION
		      "Line port state"
		::= { gwPortEntry 18 }

	linePortLocMState OBJECT-TYPE
	      SYNTAX  INTEGER {
			  inService(0),
			  ooSMaint(1),  
			  ooSHardware(2)
		      }
	      ACCESS  read-only
	      STATUS  mandatory
	      DESCRIPTION
		      "Local maintenance state of the telephone line to the port"
		::= { gwPortEntry 19 }

	linePortRemMState OBJECT-TYPE
	      SYNTAX  INTEGER {
			  inService(0),
			  ooSMaint(1),  
			  ooSHardware(2)
		      }
	      ACCESS  read-only
	      STATUS  mandatory
	      DESCRIPTION
		      "Remote maintenance state of the telephone line to the port"
		::= { gwPortEntry 20 }

	ipPortState OBJECT-TYPE
	      SYNTAX  INTEGER {
			  idle(0),
			  callInitiated(1),  
			  overlapsend(2),
			  outcallproceding(3),
			  outcallalerting(4),
			  creserved1(5),
			  callpresented(6),
			  callreceived(7),
			  connectrequested(8),
			  creserved2(9),
			  connected(10),
			  disconnectind(11),
			  disconnreq(12),
			
			  notopened(50),
			  portopening(51),
			  portopend(52),
			  startingprot(53),
			  openfailed(54),
			  portclosing(55),
			  portclosed(56)
		      }
	      ACCESS  read-only
	      STATUS  mandatory
	      DESCRIPTION
		      "IP port state"
		::= { gwPortEntry 21 }

	ipPortLocMState OBJECT-TYPE
	      SYNTAX  INTEGER {
			  inService(0),
			  ooSMaint(1),  
			  ooSHardware(2)
		      }
	      ACCESS  read-only
	      STATUS  mandatory
	      DESCRIPTION
		      "Local maintenance state of the IP connection between gateways"
		::= { gwPortEntry 22 }

	ipPortRemMState OBJECT-TYPE
	      SYNTAX  INTEGER {
			  inService(0),
			  ooSMaint(1),  
			  ooSHardware(2)
		      }
	      ACCESS  read-only
	      STATUS  mandatory
	      DESCRIPTION
		      "Remote maintenance state of the IP connection between gateways."
		::= { gwPortEntry 23 }

	connectedCalls OBJECT-TYPE
		SYNTAX INTEGER
		ACCESS read-only
			STATUS mandatory
			DESCRIPTION "Number of calls answered"
		::= { gwPortEntry 24 }

	remoteChannel OBJECT-TYPE
		SYNTAX INTEGER
		ACCESS read-only
			STATUS mandatory
			DESCRIPTION "Port number on the remote gateway, if the port is connected"
		::= { gwPortEntry 25 }

	remoteGWId OBJECT-TYPE
		SYNTAX INTEGER
		ACCESS read-only
			STATUS mandatory
			DESCRIPTION "ID of the remote gateway, if the port is connected"
		::= { gwPortEntry 26 }


	currentHoldTime OBJECT-TYPE
		SYNTAX INTEGER
		ACCESS read-only
			STATUS mandatory
			DESCRIPTION "Current hold time, in seconds, if the port is connected"
		::= { gwPortEntry 27 }


	currentAni OBJECT-TYPE
		SYNTAX DisplayString
		ACCESS read-only
			STATUS mandatory
			DESCRIPTION "Current ANI, if the port is connected"
		::= { gwPortEntry 28 }


	currentDnis OBJECT-TYPE
		SYNTAX DisplayString
		ACCESS read-only
			STATUS mandatory
			DESCRIPTION "Current DNIS, if the port is connected"
		::= { gwPortEntry 29 }



	  -- This table is read from the Command Center and
	  -- provides information about the number of gateways connected to the Command Center

	  gwNumAttached OBJECT-TYPE
	      SYNTAX  INTEGER
	      ACCESS  read-only
	      STATUS  mandatory
	      DESCRIPTION
		      "The number of Clarent Gateways currently connected to the Command Center"
	      ::= { gatewaytable 1 }


	  -- the Clarent Gateway table

	  -- The Clarent Gateway table contains information about the 
	  -- gateways currently connected to the Command Center.
	  -- The number of rows in the table corresponds to the number
	  -- of gateways connected at a given point in time.

	  gwTable OBJECT-TYPE
	      SYNTAX  SEQUENCE OF GWEntry
	      ACCESS  not-accessible
	      STATUS  mandatory
	      DESCRIPTION
		      "A list of Clarent Gateway entries" 
	      ::= { gatewaytable 2 }

	  gwEntry OBJECT-TYPE
	      SYNTAX  GWEntry
	      ACCESS  not-accessible
	      STATUS  mandatory
	      DESCRIPTION
		      "Clarent Gateway entry"
	      INDEX   { gwId }
	      ::= { gwTable 1 }

	  GWEntry ::=
	      SEQUENCE {
		gwId
			INTEGER,
		serverIpAddr
			INTEGER,
		inServerTable   
			INTEGER
	  }

	gwId OBJECT-TYPE
	      SYNTAX  INTEGER
	      ACCESS  read-only
	      STATUS  mandatory
	      DESCRIPTION
		      "A unique number for each Clarent Gateway"
		::= { gwEntry 1 }

	serverIpAddr OBJECT-TYPE
	      SYNTAX  IpAddress
	      ACCESS  read-only
	      STATUS  mandatory
	      DESCRIPTION
		      "IP Address of the Clarent Gateway"
	      ::= { gwEntry 2 }
		  
	inServerTable OBJECT-TYPE
	      SYNTAX  INTEGER {
			  no(0),
			  yes(1)  
		      }
	      ACCESS  read-only
	      STATUS  mandatory
	      DESCRIPTION
		      "Whether the gateway is in the SERVER-INFO table" 
		::= { gwEntry 3 }


	-- Traffic Stats Group

	  totalInterval OBJECT-TYPE
	      SYNTAX  INTEGER
	      ACCESS  read-only
	      STATUS  mandatory
	      DESCRIPTION
		      "Time, in seconds, since any member of the Traffic Stats group was last read"
	      ::= { gwtrafficstats 1 }
 
	  totalEventCount OBJECT-TYPE
	      SYNTAX  INTEGER
	      ACCESS  read-only
	      STATUS  mandatory
	      DESCRIPTION
		      "Total number of events in gateway"
	      ::= { gwtrafficstats 2 }
 
	  totalIngressTime OBJECT-TYPE
	      SYNTAX  INTEGER
	      ACCESS  read-only
	      STATUS  mandatory
	      DESCRIPTION
		      "Total time, in seconds, for ingress traffic"
	      ::= { gwtrafficstats 3 }
 
	  totalIngressCount OBJECT-TYPE
	      SYNTAX  INTEGER
	      ACCESS  read-only
	      STATUS  mandatory
	      DESCRIPTION
		      "Total number of ingress events" 
	      ::= { gwtrafficstats 4 }

	  totalEgressTime OBJECT-TYPE
	      SYNTAX  INTEGER
	      ACCESS  read-only
	      STATUS  mandatory
	      DESCRIPTION
		      "Total time, in seconds, for egress traffic"
	      ::= { gwtrafficstats 5 }
 
	  totalEgressCount OBJECT-TYPE
	      SYNTAX  INTEGER
	      ACCESS  read-only
	      STATUS  mandatory
	      DESCRIPTION
		      "Total number of egress events" 
	      ::= { gwtrafficstats 6 }

	  totalFaxTime OBJECT-TYPE
	      SYNTAX  INTEGER
	      ACCESS  read-only
	      STATUS  mandatory
	      DESCRIPTION
		      "Total time, in seconds, for fax traffic"
	      ::= { gwtrafficstats 7 }
 
	  totalFaxCount OBJECT-TYPE
	      SYNTAX  INTEGER
	      ACCESS  read-only
	      STATUS  mandatory
	      DESCRIPTION
		      "Total number of fax events" 
	      ::= { gwtrafficstats 8 }

	  totalOutSvcTime OBJECT-TYPE
	      SYNTAX  INTEGER
	      ACCESS  read-only
	      STATUS  mandatory
	      DESCRIPTION
		      "Total time, in seconds, that the gateway has been out of service :: Reserved; Not Implemented"
	      ::= { gwtrafficstats 9 }
 
	  totalOutSvcCount OBJECT-TYPE
	      SYNTAX  INTEGER
	      ACCESS  read-only
	      STATUS  mandatory
	      DESCRIPTION
		      "Total number of egress events :: Reserved; Not Implemented" 
	      ::= { gwtrafficstats 10 }

	  totalDataTime OBJECT-TYPE
	      SYNTAX  INTEGER
	      ACCESS  read-only
	      STATUS  mandatory
	      DESCRIPTION
		      "Total time, in seconds, for data traffic"
	      ::= { gwtrafficstats 11 }
 
	  totalDataCount OBJECT-TYPE
	      SYNTAX  INTEGER
	      ACCESS  read-only
	      STATUS  mandatory
	      DESCRIPTION
		      "Total number of data events" 
	      ::= { gwtrafficstats 12 }

	  totalVoiceTime OBJECT-TYPE
	      SYNTAX  INTEGER
	      ACCESS  read-only
	      STATUS  mandatory
	      DESCRIPTION
		      "Total time, in seconds, for voice traffic"
	      ::= { gwtrafficstats 13 }
 
	  totalVoiceCount OBJECT-TYPE
	      SYNTAX  INTEGER
	      ACCESS  read-only
	      STATUS  mandatory
	      DESCRIPTION
		      "Total number of voice events" 
	      ::= { gwtrafficstats 14 }

	  totalConnectCall OBJECT-TYPE
	      SYNTAX  INTEGER
	      ACCESS  read-only
	      STATUS  mandatory
	      DESCRIPTION
		      "Total number of ingress calls that were terminated at a remote gateway"
	      ::= { gwtrafficstats 15 }

	-- Clarent Trap Error Parameters

	  trapSeverity OBJECT-TYPE
	      SYNTAX  INTEGER {
			  critical(0),
			  major(1),  
			  minor(2),
			  warning(3),
			  information(4)
		  }
	      ACCESS  read-only
	      STATUS  mandatory
	      DESCRIPTION
		      "Trap severity"
	      ::= { trap-Parameters 1 }

	  trapClass OBJECT-TYPE
	      SYNTAX  INTEGER {
			  configuration(0),
			  hardware(1),  
			  software(2)
		  }
	      ACCESS  read-only
	      STATUS  mandatory
	      DESCRIPTION
		      "Trap class"
	      ::= { trap-Parameters 2 }

	  trapNumber OBJECT-TYPE
	      SYNTAX  INTEGER
	      ACCESS  read-only
	      STATUS  mandatory
	      DESCRIPTION
		      "Class-specific trap number"
	      ::= { trap-Parameters 3 }

	  trapText OBJECT-TYPE
	      SYNTAX  DisplayString
	      ACCESS  read-only
	      STATUS  mandatory
	      DESCRIPTION
		      "Text on a per trap Basis"
	      ::= { trap-Parameters 4 }

	  trapCount OBJECT-TYPE
	      SYNTAX  INTEGER 
	      ACCESS  read-only
	      STATUS  mandatory
	      DESCRIPTION
		      "Number of specific traps sent from the agent"
	      ::= { trap-Parameters 5 }
		
		
	  trapAppName OBJECT-TYPE
	      SYNTAX  DisplayString
	      ACCESS  read-only
	      STATUS  mandatory
	      DESCRIPTION
		      "Name of the Clarent Application issuing the Trap"
	      ::= { trap-Parameters 6 }

	  threshHoldName OBJECT-TYPE
	      SYNTAX  DisplayString 
	      ACCESS  read-only
	      STATUS  mandatory
	      DESCRIPTION
		      "Name of the Threshold Package being reported on in a ThreshHold Trap"
	      ::= { trap-Parameters 7 }
		
	  threshHoldValue OBJECT-TYPE
	      SYNTAX  INTEGER 
	      ACCESS  read-only
	      STATUS  mandatory
	      DESCRIPTION
		      "The ThreshHoldValue That is being exceeded or rearmed"
	      ::= { trap-Parameters 8 }
		
	  currentValue OBJECT-TYPE
	      SYNTAX  INTEGER 
	      ACCESS  read-only
	      STATUS  mandatory
	      DESCRIPTION
		      "The current value of the paramater that has exceeded or rearmed the
			  threshHold in the ThreshHold Trap"
	      ::= { trap-Parameters 9 }
		
	  threshHoldAction  OBJECT-TYPE
	      SYNTAX  INTEGER {
			  exceeded(0),
			  rearmed(1)  
		  }
	      ACCESS  read-only
	      STATUS  mandatory
	      DESCRIPTION
		      "ThreshHold Action"
	      ::= { trap-Parameters 10 }


	-- Clarent Traps

	gatewayIsDown TRAP-TYPE
		ENTERPRISE clarent-traps
		DESCRIPTION

		"Clarent Gateway is down"
		::= 9901

	restartGWSuccess TRAP-TYPE
		ENTERPRISE clarent-traps
		DESCRIPTION

		"Clarent Gateway restarted successfully"
		::= 9902

	restartGWFailed TRAP-TYPE
		ENTERPRISE clarent-traps
		DESCRIPTION

		"Clarent Gateway failed to restart"
		::= 9903

	ccIsDown TRAP-TYPE
		ENTERPRISE clarent-traps
		DESCRIPTION

		"Clarent Command Center is down"
		::= 9904

	restartCCSuccess TRAP-TYPE
		ENTERPRISE clarent-traps
		DESCRIPTION

		"Clarent Command Center restarted successfully"
		::= 9905

	restartCCFailed TRAP-TYPE
		ENTERPRISE clarent-traps
		DESCRIPTION

		"Clarent Command Center failed to restart"
		::= 9906

	lostCC TRAP-TYPE
		ENTERPRISE clarent-traps
		VARIABLES { serverIpAddr }
		DESCRIPTION

		"Clarent Gateway lost its connection to the specified Command Center"
		::= 9907

	connectCCFailed TRAP-TYPE
		ENTERPRISE clarent-traps
		VARIABLES { serverIpAddr }
		DESCRIPTION

		"Clarent Gateway cannot connect to the specified Command Center"
		::= 9908

		-- Traps 9909 and 9910 Reserved

	portOutOfService TRAP-TYPE
		ENTERPRISE clarent-traps
		VARIABLES { portIndex }
		DESCRIPTION

		"Clarent Gateway port is out of service"
		::= 9911

	portInService TRAP-TYPE
		ENTERPRISE clarent-traps
		VARIABLES { portIndex }
		DESCRIPTION

		"Clarent Gateway port is back in service"
		::= 9912

	dialUpNoVoicePort TRAP-TYPE
		ENTERPRISE clarent-traps
		DESCRIPTION

		"Clarent Gateway cannot dial number; no voice port is available"
		::= 9913

	connectNoVoicePort TRAP-TYPE
		ENTERPRISE clarent-traps
		DESCRIPTION

		"Clarent Gateway cannot connect to another gateway; not responding"

		::= 9914

	gatewayConnect TRAP-TYPE
		ENTERPRISE clarent-traps
		VARIABLES { serverIpAddr }
		DESCRIPTION

		"Clarent Gateway, at the specified IP address, connected to Command Center"
		::= 9915

	gatewayDisconnect TRAP-TYPE
		ENTERPRISE clarent-traps
		VARIABLES { serverIpAddr }
		DESCRIPTION

		"Clarent Gateway, at the specified IP address, disconnected from Command Center"
		::= 9916

	gwNotRegistered TRAP-TYPE
		ENTERPRISE clarent-traps
		VARIABLES { gwId }
		DESCRIPTION

		"Clarent Gateway is  not registered"
		::= 9917

	callRatingFailed TRAP-TYPE
		ENTERPRISE clarent-traps
		VARIABLES { trapText }
		DESCRIPTION

		"Call rating failed"
		::= 9918

	invalidCCLicense TRAP-TYPE
		ENTERPRISE clarent-traps
		DESCRIPTION

		"Invalid Command Center license"
		::= 9919

	validCCTmpLicense TRAP-TYPE
		ENTERPRISE clarent-traps
		DESCRIPTION

		"Valid temporary Command Center license"
		::= 9920

	ss7LinkUp TRAP-TYPE
		ENTERPRISE clarent-traps
		DESCRIPTION

		"SS7 link is up"
		::= 9921

	ss7LinkDown TRAP-TYPE
		ENTERPRISE clarent-traps
		DESCRIPTION

		"SS7 link is down"
		::= 9922

	-- Traps 9923-9926 reserved for Future

	gwAppShutdown TRAP-TYPE
		ENTERPRISE clarent-traps
		VARIABLES { trapText }
		DESCRIPTION

		"Clarent Gateway shut down"
		::= 9927

	resettingDSPBrd TRAP-TYPE
		ENTERPRISE clarent-traps
		VARIABLES { trapText }
		DESCRIPTION

		"Resetting DSP board"
		::= 9928

	clrHseCreditSChg TRAP-TYPE
		ENTERPRISE clarent-traps
		VARIABLES { trapText }
		DESCRIPTION

		"Clarent Connect clearinghouse credit status changed"
		::= 9929

	ccCreditSChg TRAP-TYPE
		ENTERPRISE clarent-traps
		VARIABLES { trapText }
		DESCRIPTION

		"Clarent Connect credit status changed"
		::= 9930

	validateEGErr  TRAP-TYPE
		ENTERPRISE clarent-traps
		VARIABLES { trapText }
		DESCRIPTION

		"Clarent Gateway validate egress error"

		::= 9931
		
	licRollBack  TRAP-TYPE
		ENTERPRISE clarent-traps
		DESCRIPTION

		"Clarent Command Center license key change rolled back" 

		::= 9932
		
	clarentInfo  TRAP-TYPE
		ENTERPRISE clarent-traps
		VARIABLES { trapSeverity, trapClass, trapNumber, trapCount, trapText }
		DESCRIPTION

		"Generic Clarent error trap: 
			Severity:
				Critical(0), Major(1), Minor(2), Warning(3), or Information(4)
			Class:
				Configuration(0), Hardware(1), or Software(2)
			Number of trap
			Count of total number of traps per class
			Descriptive text string"

		::= 9933

	softwareUpdate  TRAP-TYPE
		ENTERPRISE clarent-traps
		VARIABLES { packageName, packageOperation, packageStatus /*, errorCount */}
		DESCRIPTION
		"Software update:
			Name of package
			Package operation: Download(0), Unpack(1), Install(2), Prepare(3), Commit(4), Abort(5), Delete(8)
			Package operation status
			Error count"

		::= 9934


	numberIntercept  TRAP-TYPE
		ENTERPRISE clarent-traps
		VARIABLES { trapText }
		DESCRIPTION
		"Call placed to the intercept number"

		::= 9935
		
	tpIsDown  TRAP-TYPE
		ENTERPRISE clarent-traps
		DESCRIPTION

		"Clarent ThroughPacket server is down"

		::= 9936
		
	restartTPFailed  TRAP-TYPE
		ENTERPRISE clarent-traps
		DESCRIPTION

		"Clarent ThroughPacket server failed to restart"

		::= 9937
		
	tpRestarted  TRAP-TYPE
		ENTERPRISE clarent-traps
		DESCRIPTION

		"Clarent ThroughPacket server restarted successfully"

		::= 9938
		
	threshHoldTrap  TRAP-TYPE
		ENTERPRISE clarent-traps
		VARIABLES { trapSeverity, trapAppName, threshHoldName, 
					threshHoldValue , currentValue , threshHoldAction }
		DESCRIPTION
		"Clarent ThreshHold Trap, indicates that a particular Threshold
		has been exceeded or rearmed by the named Application. This trap contains
		1) The Severity of the Threshold (Critical, Major, Minor, Warning, Information)
		2) the name of the Application (e.g. ThroughPacket)
		3) the ThreshHold Name (e.g. PacketsperSecond, BytesPerSecond )
		4) the ThreshHold Value that was exceeded/rearmed ( e.g. 350000 )
		5) the current value of the variable being sampled. ( e.g. BytesPerSecond 355043 )
		6) the Action, Exceeded or Rearmed. Thresholds are rearmed when the moving
		   average of the variable being measured is at 75% of the ThreshHold.
		"
		::= 9939

	systemReboot  TRAP-TYPE
		ENTERPRISE clarent-traps
		VARIABLES { trapText }
		DESCRIPTION

		"The system is rebooting in response to a startShutdown command"

		::= 9940
		
	rebootCommand  TRAP-TYPE
		ENTERPRISE clarent-traps
		VARIABLES { trapText }
		DESCRIPTION

		"The system has been enabled to receive a startShutdown command"

		::= 9941
		
	cDiskSpaceLow  TRAP-TYPE
		ENTERPRISE clarent-traps
		VARIABLES { trapText }
		DESCRIPTION

		"Drive has less than 50MB of free space available. This trap is issued on an hourly basis
		if the condition persists."
		::= 9942
		
	cNoConnectRoute  TRAP-TYPE
		ENTERPRISE clarent-traps
		VARIABLES { trapText }
		DESCRIPTION

		"Clarent Connect partner does not have a route for this call. This trap is issued
no more than once every 5 minutes."

		::= 9943
		
		
	dbError  TRAP-TYPE
		ENTERPRISE clarent-traps
		VARIABLES { trapSeverity, trapNumber, trapText, trapCount }
		DESCRIPTION

		"Clarent DB error trap contains the following information
			Severity:
				Critical(0), Major(1), Minor(2), Warning(3), or Information(4)
			Database error number 
			Descriptive error text string
			Count of total number of database error traps sent since machine power up"

		::= 9944

	dbClerkStarted TRAP-TYPE
		ENTERPRISE clarent-traps
		VARIABLES { trapNumber }
		DESCRIPTION

		"A new database clerk was started. The value of trapNumber represents the total number of 
clerks running."

		::= 9945

	restartDMFailed  TRAP-TYPE
		ENTERPRISE clarent-traps
		DESCRIPTION

		"Clarent Distribution Service failed to restart"

		::= 9946
		
	dmRestarted  TRAP-TYPE
		ENTERPRISE clarent-traps
		DESCRIPTION

		"Clarent Distribution Service restarted successfully"

		::= 9947

	dmIsDown  TRAP-TYPE
		ENTERPRISE clarent-traps
		DESCRIPTION

		"Clarent Distribution Service is down"

		::= 9948


	sigGWMTPPause  TRAP-TYPE
		ENTERPRISE clarent-traps
		VARIABLES { trapText }
		DESCRIPTION
		"The Message Transfer Protocol paused"
		::= 9949
		
	sigGWMTPResume  TRAP-TYPE
		ENTERPRISE clarent-traps
		VARIABLES { trapText }
		DESCRIPTION
		"The Message Transfer Protocol resumed"
		::= 9950
		
	sigGWTaskActive  TRAP-TYPE
		ENTERPRISE clarent-traps
		VARIABLES { trapText }
		DESCRIPTION
		"A signaling task started"
		::= 9951

	pinSuspended  TRAP-TYPE
		ENTERPRISE clarent-traps
		VARIABLES { trapText }
		DESCRIPTION
		"An account was suspended"
		::= 9952
		

	  -- the Package table

	  numPackages OBJECT-TYPE
	      SYNTAX  INTEGER
	      ACCESS  read-only
	      STATUS  mandatory
	      DESCRIPTION
		      "Number of packages on a Clarent Network Element."
	      ::= { packageManagement 1 }

	  -- The Package table contains information about the 
	  -- software packages that have been loaded onto a Clarent network element. 
	  -- The number of rows in the table corresponds to the number
	  -- of packages loaded.

	  packageTable OBJECT-TYPE
	      SYNTAX  SEQUENCE OF PackageEntry
	      ACCESS  not-accessible
	      STATUS  mandatory
	      DESCRIPTION
		      "A list of package entries" 
	      ::= { packageManagement 2 }

	  packageEntry OBJECT-TYPE
	      SYNTAX  PackageEntry
	      ACCESS  not-accessible
	      STATUS  mandatory
	      DESCRIPTION
		      "Package status entry"
	      INDEX   { packageName }
	      ::= { packageTable 1 }
		

	  PackageEntry ::=
	      SEQUENCE {
		packageName 
			DisplayString,
		packageStatus 
			INTEGER,
		downloadStatus 
			INTEGER,
		downloadMessage 
			DisplayString,
		downloadError
			INTEGER,
		unpackStatus 
			INTEGER,
		unpackMessage 
			DisplayString,
		unpackError
			INTEGER,
		installStatus 
			INTEGER,
		installMessage 
			DisplayString,
		installError
			INTEGER,
		prepareStatus 
			INTEGER,
		prepareMessage 
			DisplayString,
		prepareError
			INTEGER,
		commitStatus 
			INTEGER,
		commitMessage 
			DisplayString,
		commitError
			INTEGER,
		abortStatus 
			INTEGER,
		abortMessage 
			DisplayString,
		abortError
			INTEGER,
		loadStatus 
			INTEGER,
		loadMessage 
			DisplayString,
		loadError
			INTEGER,
		deleteStatus 
			INTEGER,
		deleteMessage 
			DisplayString,
		deleteError
			INTEGER,
		commitLevel 
			INTEGER
	  }


	packageName OBJECT-TYPE
	      SYNTAX  DisplayString
	      ACCESS  read-only
	      STATUS  mandatory
	      DESCRIPTION
		      "Unique name of the package"
		::= { packageEntry 1 }

	packageStatus OBJECT-TYPE
	      SYNTAX  INTEGER {
			  phaseComplete(0),
			  phaseError(1),
			  phaseStarted(2),
			  phaseNotStarted(3)  
		      }
	      ACCESS  read-only
	      STATUS  mandatory
	      DESCRIPTION
		      "Package status"
	      ::= { packageEntry 2 }
		  
	downloadStatus OBJECT-TYPE
	      SYNTAX  INTEGER {
			  phaseComplete(0),
			  phaseError(1),
			  phaseStarted(2),
			  phaseNotStarted(3)  
		      }
	      ACCESS  read-only
	      STATUS  mandatory
	      DESCRIPTION
		      "Package download status"
	      ::= { packageEntry 3 }

	downloadMessage OBJECT-TYPE
	      SYNTAX  DisplayString
	      ACCESS  read-only
	      STATUS  mandatory
	      DESCRIPTION
			"Package download status message"
		::= { packageEntry 4 }

	downloadError OBJECT-TYPE
	      SYNTAX  INTEGER 
	      ACCESS  read-only
	      STATUS  mandatory
	      DESCRIPTION
		      "Package download error"
	      ::= { packageEntry 5 }

	unpackStatus OBJECT-TYPE
	      SYNTAX  INTEGER {
			  phaseComplete(0),
			  phaseError(1),  
			  phaseStarted(2),
			  phaseNotStarted(3)  
		      }
	      ACCESS  read-only
	      STATUS  mandatory
	      DESCRIPTION
		      "Package unpack status"
	      ::= { packageEntry 6 }

	unpackMessage OBJECT-TYPE
	      SYNTAX  DisplayString
	      ACCESS  read-only
	      STATUS  mandatory
	      DESCRIPTION
			  "Package unpack status message"
		::= { packageEntry 7 }

	unpackError OBJECT-TYPE
	      SYNTAX  INTEGER 
	      ACCESS  read-only
	      STATUS  mandatory
	      DESCRIPTION
		      "Package unpack error"
	      ::= { packageEntry 8 }

	installStatus OBJECT-TYPE
	      SYNTAX  INTEGER {
			  phaseComplete(0),
			  phaseError(1),  
			  phaseStarted(2),
			  phaseNotStarted(3)  
		      }
	      ACCESS  read-only
	      STATUS  mandatory
	      DESCRIPTION
		      "Package install status"
	      ::= { packageEntry 9 }

	installMessage OBJECT-TYPE
	      SYNTAX  DisplayString
	      ACCESS  read-only
	      STATUS  mandatory
	      DESCRIPTION
			  "Package install status message"
		::= { packageEntry 10 }

	installError OBJECT-TYPE
	      SYNTAX  INTEGER 
	      ACCESS  read-only
	      STATUS  mandatory
	      DESCRIPTION
		      "Package install error"
	      ::= { packageEntry 11 }

	prepareStatus OBJECT-TYPE
	      SYNTAX  INTEGER {
			  phaseComplete(0),
			  phaseError(1),  
			  phaseStarted(2),
			  phaseNotStarted(3)  
		      }
	      ACCESS  read-only
	      STATUS  mandatory
	      DESCRIPTION
		      "Package prepare status"
	      ::= { packageEntry 12 }

	prepareMessage OBJECT-TYPE
	      SYNTAX  DisplayString
	      ACCESS  read-only
	      STATUS  mandatory
	      DESCRIPTION
			  "Package prepare status message"
		::= { packageEntry 13 }

	prepareError OBJECT-TYPE
	      SYNTAX  INTEGER 
	      ACCESS  read-only
	      STATUS  mandatory
	      DESCRIPTION
		      "Package prepare error"
	      ::= { packageEntry 14 }

	commitStatus OBJECT-TYPE
	      SYNTAX  INTEGER {
			  phaseComplete(0),
			  phaseError(1),  
			  phaseStarted(2),
			  phaseNotStarted(3)  
		      }
	      ACCESS  read-only
	      STATUS  mandatory
	      DESCRIPTION
			  "Package commit status"
	      ::= { packageEntry 15 }

	commitMessage OBJECT-TYPE
	      SYNTAX  DisplayString
	      ACCESS  read-only
	      STATUS  mandatory
	      DESCRIPTION
			  "Package commit status message"
		::= { packageEntry 16 }

	commitError OBJECT-TYPE
	      SYNTAX  INTEGER 
	      ACCESS  read-only
	      STATUS  mandatory
	      DESCRIPTION
		      "Package commit error"
	      ::= { packageEntry 17 }

	abortStatus OBJECT-TYPE
	      SYNTAX  INTEGER {
			  phaseComplete(0),
			  phaseError(1),  
			  phaseStarted(2),
			  phaseNotStarted(3)  
		      }
	      ACCESS  read-only
	      STATUS  mandatory
	      DESCRIPTION
			  "Package abort status"
	      ::= { packageEntry 18 }

	abortMessage OBJECT-TYPE
	      SYNTAX  DisplayString
	      ACCESS  read-only
	      STATUS  mandatory
	      DESCRIPTION
			  "Package abort status message"
		::= { packageEntry 19 }

	abortError OBJECT-TYPE
	      SYNTAX  INTEGER 
	      ACCESS  read-only
	      STATUS  mandatory
	      DESCRIPTION
		      "Package abort error"
	      ::= { packageEntry 20 }

	loadStatus OBJECT-TYPE
	      SYNTAX  INTEGER {
			  phaseComplete(0),
			  phaseError(1),  
			  phaseStarted(2),
			  phaseNotStarted(3)  
		      }
	      ACCESS  read-only
	      STATUS  mandatory
	      DESCRIPTION
			  "Package load status"
	      ::= { packageEntry 21 }

	loadMessage OBJECT-TYPE
	      SYNTAX  DisplayString
	      ACCESS  read-only
	      STATUS  mandatory
	      DESCRIPTION
			  "Package load status message"
		::= { packageEntry 22 }

	loadError OBJECT-TYPE
	      SYNTAX  INTEGER 
	      ACCESS  read-only
	      STATUS  mandatory
	      DESCRIPTION
		      "Package load error"
	      ::= { packageEntry 23 }

	deleteStatus OBJECT-TYPE
	      SYNTAX  INTEGER {
			  phaseComplete(0),
			  phaseError(1),  
			  phaseStarted(2),
			  phaseNotStarted(3)  
		      }
	      ACCESS  read-only
	      STATUS  mandatory
	      DESCRIPTION
			  "Package delete status"
	      ::= { packageEntry 24 }

	deleteMessage OBJECT-TYPE
	      SYNTAX  DisplayString
	      ACCESS  read-only
	      STATUS  mandatory
	      DESCRIPTION
			  "Package delete status message"
		::= { packageEntry 25 }

	deleteError OBJECT-TYPE
	      SYNTAX  INTEGER 
	      ACCESS  read-only
	      STATUS  mandatory
	      DESCRIPTION
		      "Package delete error"
	      ::= { packageEntry 26 }

	commitLevel OBJECT-TYPE
	      SYNTAX  INTEGER {
			  single(0),
			  multi(1)  
		      }
	      ACCESS  read-write
	      STATUS  mandatory
	      DESCRIPTION
		      "Mode of operation in which the package was installed"
	      ::= { packageEntry 27 }

--		Commands we can send to the Package Distributor.
--		Once the base URL is set, setting any of the command variables 
--		will make the Distribution Manager take the specified action.	

	  downLoadCommand OBJECT-TYPE
	      SYNTAX  DisplayString
	      ACCESS  read-write
	      STATUS  mandatory
	      DESCRIPTION
		      "Initiate a DOWNLOAD command.  In the SET command, specify
		      the package name."
	      ::= { packageManagement 3 }

	  unpackCommand OBJECT-TYPE
	      SYNTAX  DisplayString
	      ACCESS  read-write
	      STATUS  mandatory
	      DESCRIPTION
		      "Initiate an UNPACK command.  In the SET command, specify
		      the package name."
	      ::= { packageManagement 4 }

	  installCommand OBJECT-TYPE
	      SYNTAX  DisplayString
	      ACCESS  read-write
	      STATUS  mandatory
	      DESCRIPTION
		      "Initiate an INSTALL command. In the SET command, specify
		      the package name."
	      ::= { packageManagement 5 }



	  prepareCommand OBJECT-TYPE
	      SYNTAX  DisplayString
	      ACCESS  read-write
	      STATUS  mandatory
	      DESCRIPTION
		      "Initiate a PREPARE command. In the SET command, specify
		      the package name."
	      ::= { packageManagement 6 }


	  commitCommand OBJECT-TYPE
	      SYNTAX  DisplayString
	      ACCESS  read-write
	      STATUS  mandatory
	      DESCRIPTION
		      "Initiate a COMMIT command. In the SET command, specify
		      the package name."
	      ::= { packageManagement 7 }

	  abortCommand OBJECT-TYPE
	      SYNTAX  DisplayString
	      ACCESS  read-write
	      STATUS  mandatory
	      DESCRIPTION
		      "Initiate an ABORT command. In the SET command, specify
		      the package name."
	      ::= { packageManagement 8 }


	  loadCommand OBJECT-TYPE
	      SYNTAX  DisplayString
	      ACCESS  read-write
	      STATUS  mandatory
	      DESCRIPTION
		      "Initiate a LOAD command. In the SET command, specify
			the package name."
	      ::= { packageManagement 9 }


	  baseURL OBJECT-TYPE
	      SYNTAX  DisplayString
	      ACCESS  read-write
	      STATUS  mandatory
	      DESCRIPTION
		      "Use this variable to set/get the BASE URL, which is a well-known URL
			identifying the location from which packages are downloaded."
	      ::= { packageManagement 10 }

	  deleteCommand OBJECT-TYPE
	      SYNTAX  DisplayString
	      ACCESS  read-write
	      STATUS  mandatory
	      DESCRIPTION
		      "Initiate a DELETE command. In the SET command, specify
			the package name."
	      ::= { packageManagement 11 }


--	  Used only in TRAP to give Trap Syntax.
	packageOperation OBJECT-TYPE
	      SYNTAX  INTEGER {
			  download(0),
			  unpack(1),
			  install(2),
			  prepare(3),
			  commit(4),
			  abort(5),
			  load (6),
			  delete(8)
		      }
	      ACCESS  read-write
	      STATUS  mandatory
	      DESCRIPTION
		      "List of allowed package operations"
	      ::= { packageManagement 99999 }

	  -- the gwstatisticsManagement Group

	  gwEnableStats	OBJECT-TYPE
	      SYNTAX  INTEGER
	      ACCESS  read-write
	      STATUS  mandatory
	      DESCRIPTION
		      "Enables statistics messages from the gateway to the Command Center.
			Specify a value of 1 to enable statistics. The default value is 0 (zero),
			which disables statistics."
	      ::= { gwStatisticsManagement 1 }

	  gwStatsInterval	OBJECT-TYPE
	      SYNTAX  INTEGER
	      ACCESS  read-write
	      STATUS  mandatory
	      DESCRIPTION
		      "Interval, in minutes, between gateway statistic messages from the gateway
			to the Command Center"
	      ::= { gwStatisticsManagement 2 }

	--	Clarent ThroughPacket tpStatus group

	  tpstatus OBJECT-TYPE
	      SYNTAX  INTEGER {
			  inService(0),
			  outofService(1),
			  inError(2)
			  }
	      ACCESS  read-only
	      STATUS  mandatory
	      DESCRIPTION
		  "Current status of the Clarent ThroughPacket server" 
	      ::= { tpStatus  1 }
 
	  tpstatusCode OBJECT-TYPE
	      SYNTAX  INTEGER 
	      ACCESS  read-only
	      STATUS  mandatory
	      DESCRIPTION
		  "If tpstatus is inError, interrogate this variable for more information."
	      ::= { tpStatus  2 }
 
	  tpOperState OBJECT-TYPE
	      SYNTAX  INTEGER {
			  enabled(0),
			  disabled(1)
		      }
	      ACCESS  read-only
	      STATUS  mandatory
	      DESCRIPTION
		      "State of the TP, enabled means running, disabled means not running"
	      ::= { tpStatus 3 }
 

	  -- the tpConfig Group
 
	  priCCIPAddress OBJECT-TYPE
	      SYNTAX  DisplayString
	      ACCESS  read-write
	      STATUS  mandatory
	      DESCRIPTION
		      "IP address of the primary Command Center for the Clarent ThroughPacket server"
	      ::= { tpConfig 1 }

	  ccPortNumber OBJECT-TYPE 
	      SYNTAX  INTEGER
	      ACCESS  read-write
	      STATUS  mandatory
	      DESCRIPTION
		      "Port number of the Command Center for the Clarent ThroughPacket server"
	      ::= { tpConfig 2 }

	  secCCIPAddress OBJECT-TYPE
	      SYNTAX  DisplayString
	      ACCESS  read-write
	      STATUS  mandatory
	      DESCRIPTION
		      "IP address of the secondary Command Center for the Clarent ThroughPacket server"
	      ::= { tpConfig 3 }

	  tpConfigCommand OBJECT-TYPE
	      SYNTAX  DisplayString
	      ACCESS  read-write
	      STATUS  mandatory
	      DESCRIPTION
		      "Use this variable to issue commands to the Clarent ThroughPacket server"
	      ::= { tpConfig 4 }

	  tpRunTimeCtrl OBJECT-TYPE
	      SYNTAX  INTEGER {
			  stop(0)
		  }
	      ACCESS  read-write
	      STATUS  mandatory
	      DESCRIPTION
		  "Start or stop the Clarent ThroughPacket server"
	      ::= { tpConfig  5 }


	  -- the tpstatisticsManagement Group

	  tpEnableStats	OBJECT-TYPE
	      SYNTAX  INTEGER
	      ACCESS  read-write
	      STATUS  mandatory
	      DESCRIPTION
		      "Enables statistics messages from Clarent ThroughPacket to the 
			  Command Center.
			Specify a value of 1 to enable statistics. The default value is 0 (zero),
			which disables statistics."
	      ::= { tpStatisticsManagement 1 }

	  tpStatsInterval	OBJECT-TYPE
	      SYNTAX  INTEGER
	      ACCESS  read-write
	      STATUS  mandatory
	      DESCRIPTION
		      "Interval, in minutes, between statistics messages from Clarent ThroughPacket
			to the Command Center"
	      ::= { tpStatisticsManagement 2 }

	  -- The Process Management Group
	  -- use to control the auto restart of applications

	  autoGWRestart OBJECT-TYPE
	      SYNTAX  INTEGER {
			  disable(0),
			  enable(1)
		      }
	      ACCESS  read-write
	      STATUS  mandatory
	      DESCRIPTION
		      "Enable SNMP Agent to automatically restart the GW"
	      ::= { procManagement 1  }
 
	  autoCCRestart OBJECT-TYPE
	      SYNTAX  INTEGER {
			  disable(0),
			  enable(1)
		      }
	      ACCESS  read-write
	      STATUS  mandatory
	      DESCRIPTION
		      "Enable SNMP Agent to automatically restart the GW"
	      ::= { procManagement 2  }
 
	  autoTPRestart OBJECT-TYPE
	      SYNTAX  INTEGER {
			  disable(0),
			  enable(1)
		      }
	      ACCESS  read-write
	      STATUS  mandatory
	      DESCRIPTION
		      "Enable SNMP Agent to automatically restart the GW"
	      ::= { procManagement 3  }

	  autoDMRestart OBJECT-TYPE
	      SYNTAX  INTEGER {
			  disable(0),
			  enable(1)
		      }
	      ACCESS  read-write
	      STATUS  mandatory
	      DESCRIPTION
		      "Enable SNMP Agent to automatically restart the DM"
	      ::= { procManagement 4  }

	  autoGKRestart OBJECT-TYPE
	      SYNTAX  INTEGER {
			  disable(0),
			  enable(1)
		      }
	      ACCESS  read-write
	      STATUS  mandatory
	      DESCRIPTION
		      "Enable SNMP Agent to automatically restart the GK"
	      ::= { procManagement 5  }


	  autoCAMRestart OBJECT-TYPE
	      SYNTAX  INTEGER {
			  disable(0),
			  enable(1)
		      }
	      ACCESS  read-write
	      STATUS  mandatory
	      DESCRIPTION
		      "Enable SNMP Agent to automatically restart the CAM"
	      ::= { procManagement 6  }


	  -- The Version Management Group
	  -- used to list the Versions of all Clarent Software Components
	  -- The Clarent Agent interrogate the Clarent components for
	  -- version information and presents the extracted information in this table.
	  -- The components must be running in order for the information to be found.

	  versionTable OBJECT-TYPE
	      SYNTAX  SEQUENCE OF VersionEntry
	      ACCESS  not-accessible
	      STATUS  mandatory
	      DESCRIPTION
		      "A list of Version entries" 
	      ::= { versionManagement 1 }

	  versionEntry OBJECT-TYPE
	      SYNTAX  VersionEntry
	      ACCESS  not-accessible
	      STATUS  mandatory
	      DESCRIPTION
		      "Version Table Entry containing version component information"
	      INDEX   { component }
	      ::= { versionTable 1 }
		

	  VersionEntry ::=
	      SEQUENCE {
		component 
			DisplayString,
		majorVersion 
			INTEGER,
		minorVersion 
			INTEGER,
		buildMajorVersion 
			DisplayString,
		buildMinorVersion
			INTEGER,
		versionString 
			DisplayString
	  }

	  component OBJECT-TYPE
	      SYNTAX   DisplayString
	      ACCESS  read-only
	      STATUS  mandatory
	      DESCRIPTION
		      "Name of Clarent Component that is versioned"
	      ::= { versionEntry 1  }

	  majorVersion OBJECT-TYPE
	      SYNTAX  INTEGER 
	      ACCESS  read-only
	      STATUS  mandatory
	      DESCRIPTION
		      "Major Release Version Number"
	      ::= { versionEntry 2 }

	  minorVersion OBJECT-TYPE
	      SYNTAX  INTEGER 
	      ACCESS  read-only
	      STATUS  mandatory
	      DESCRIPTION
		      "Minor Release Version Number"
	      ::= { versionEntry 3}


	  buildMajorVersion OBJECT-TYPE
	      SYNTAX  INTEGER 
	      ACCESS  read-only
	      STATUS  mandatory
	      DESCRIPTION
		      "Build Major Release Version Number"
	      ::= { versionEntry 4 }

	  buildMinorVersion OBJECT-TYPE
	      SYNTAX  INTEGER 
	      ACCESS  read-only
	      STATUS  mandatory
	      DESCRIPTION
		      "Major Release Version Number"
	      ::= { versionEntry 5 }

	  versionString OBJECT-TYPE
	      SYNTAX   DisplayString
	      ACCESS  read-only
	      STATUS  mandatory
	      DESCRIPTION
		      " Version in String Format"
	      ::= { versionEntry 6  }

	--	Clarent cSysManageMent Group

	  cSystemStatus OBJECT-TYPE
	      SYNTAX  INTEGER {
			  available(0),
			  shutdownAllowed(1),
			  shutdownPending(2),
			  opError(3)
			  }
	      ACCESS  read-only
	      STATUS  mandatory
	      DESCRIPTION
		  "Current status of the Clarent Network Element, if state is shutdownAllowed
		  it means that an enableShutdown down operation has been received. At this point
		  a startShutdown operation would start the shutdown process, if opError then the
		  csystemError will contain an error code"
	      ::= { cSysStatus  1 }

	  cSystemError OBJECT-TYPE
	      SYNTAX  INTEGER 
	      ACCESS  read-only
	      STATUS  mandatory
	      DESCRIPTION
		  " Error Code reflected from system"
	      ::= { cSysStatus  2 }

	
	  cSysOperation OBJECT-TYPE
	      SYNTAX  INTEGER  {
			  enableShutdown(0),
			  disableShutdown(1),
			  startShutdown(2)
			}
	      ACCESS  read-write
	      STATUS  mandatory
	      DESCRIPTION
		  "User can reboot the system by issuing an enableShutdown operation followed
		   by a startShutdown operation. When the system is enabled for shutdown
		   the clarent shutdowntrap is emitted, disableShutdown inhibits shutdown
		   until an enableShutdown is received. Default state is Shutdown disabled"
	      ::= { cSysControl  1 }
 

-- Clarent Gk Extended MIB Section

	gkPortInUseCount OBJECT-TYPE
	      SYNTAX  INTEGER 
	      ACCESS  read-only
	      STATUS  mandatory
	      DESCRIPTION
		  "Number of ports currently in use"
	      ::= { cGkStatus  1 }

	gkOpState OBJECT-TYPE
	      SYNTAX  INTEGER {
			disabled(0),
			enabled(1)
		  }
	      ACCESS  read-only
	      STATUS  mandatory
	      DESCRIPTION
		  "Clarent Gatekeeper operational state"
	      ::= { cGkStatus  2 }

	gkAltGKList OBJECT-TYPE
	      SYNTAX  DisplayString 
	      ACCESS  read-only
	      STATUS  mandatory
	      DESCRIPTION
		  "Alternate gatekeeper list"
	      ::= { cGkStatus  3 }

	gkLoadState OBJECT-TYPE
	      SYNTAX  INTEGER  {
			  kGatekeeperOpStateMinimal(0),
			  kGatekeeperOpStateLight(1),
			  kGatekeeperOpStateMedium(2),
			  kGatekeeperOpStateHeavy(3),
			  kGatekeeperOpStateDangerouslyHeavy(4),
			  kGatekeeperOpStateCritical(5)

			}
	      ACCESS  read-only
	      STATUS  mandatory
	      DESCRIPTION
		  "Clarent Gatekeeper load state"
	      ::= { cGkStatus  4 }

	gkCCConnState OBJECT-TYPE
	      SYNTAX  INTEGER  {
			  notRegistered(0),
			  connected(1)
			}
	      ACCESS  read-only
	      STATUS  mandatory
	      DESCRIPTION
		  "Gatekeeper-to-Command Center connection state"
	      ::= { cGkStatus  5 }

	-- Table for Call Times/Call Counts.


	  gkCallStatsTable OBJECT-TYPE
	      SYNTAX  SEQUENCE OF GkCallStatsEntry
	      ACCESS  not-accessible
	      STATUS  mandatory
	      DESCRIPTION
		      "List of call statistics for all call port types"
	      ::= { cGkStatus 6 }

	  gkCallStatsEntry OBJECT-TYPE
	      SYNTAX  GkCallStatsEntry
	      ACCESS  not-accessible
	      STATUS  mandatory
	      DESCRIPTION
		      "Entry in the CallStatsTable for a given call port type"
	      INDEX   { gkCallPortType }
	      ::= { gkCallStatsTable 1 }
		

	  GkCallStatsEntry ::=
	      SEQUENCE {
		gkCallPortType
			INTEGER,
		gkNumberOfCalls 
			INTEGER,
		gkCallTime 
			INTEGER,
		gkAverageHoldTime 
			INTEGER,
		gkNumberOfConnectedCalls
			INTEGER
	  }

	  gkCallPortType OBJECT-TYPE
	      SYNTAX  INTEGER {
			total(1),
			h323none(2),
			h323h323(3),
			h323clarent (4),
			clarent2none(5),
			clarent2h323(6),
			clarent2clarent(7)
		  }

	      ACCESS  read-only
	      STATUS  mandatory
	      DESCRIPTION
		      "List of call port types. 
		      Call port types are: 
		      TOTAL, a call from any combination of call port types 
		      H323H323, an H.323 gateway-to-H.323 gateway call 
			  H323CLARENT, an H.323 gateway-to IP
		      H323NONE , an H.323 gateway call that was not successfully routed 
		      CLARENT2H323, a Clarent Gateway-to-H.323 gateway call 
		      CLARENT2CLARENT, a Clarent Gateway-Clarent Gateway call 
		      CLARENT2CLARENT, a Clarent Gateway call that was not successfully routed."

	      ::= { gkCallStatsEntry 1 }

	  gkNumberOfCalls OBJECT-TYPE
	      SYNTAX  INTEGER 
	      ACCESS  read-only
	      STATUS  mandatory
	      DESCRIPTION
		      "Number of call attempts for a given call port type"
	      ::= { gkCallStatsEntry 2 }

	  gkCallTime OBJECT-TYPE
	      SYNTAX  INTEGER 
	      ACCESS  read-only
	      STATUS  mandatory
	      DESCRIPTION
		      "Amount of time, in seconds, for calls of a given call port type"
	      ::= { gkCallStatsEntry 3 }

	  gkAverageHoldTime OBJECT-TYPE
	      SYNTAX  INTEGER 
	      ACCESS  read-only
	      STATUS  mandatory
	      DESCRIPTION
		      "Average hold time for calls of a given call port type"
	      ::= { gkCallStatsEntry 4 }

	  gkNumberOfConnectedCalls OBJECT-TYPE
	      SYNTAX  INTEGER 
	      ACCESS  read-only
	      STATUS  mandatory
	      DESCRIPTION
		      "Number of call completions for a given call port type"
	      ::= { gkCallStatsEntry 5 }


	-- Configuration Group for GK

	gkName OBJECT-TYPE
	      SYNTAX  DisplayString 
	      ACCESS  read-write
	      STATUS  mandatory
	      DESCRIPTION
		  "Clarent Gatekeeper name"
	      ::= { cGkConfig  1 }

	gkIPAddr OBJECT-TYPE
	      SYNTAX  IpAddress
	      ACCESS  read-write
	      STATUS  mandatory
	      DESCRIPTION
		  "IP address of Clarent Gatekeeper"
	      ::= { cGkConfig  2 }

	gkExternalIPAddr OBJECT-TYPE
	      SYNTAX  IpAddress 
	      ACCESS  read-write
	      STATUS  mandatory
	      DESCRIPTION
		  "IP address by which Clarent Gatekeeper is known to outside entities"
	      ::= { cGkConfig  3 }

	gkCCUDPPort OBJECT-TYPE
	      SYNTAX  INTEGER 
	      ACCESS  read-write
	      STATUS  mandatory
	      DESCRIPTION
		  "UDP port through which Clarent Command Center communicates 
		  with Clarent Gatekeeper"
	      ::= { cGkConfig  4 }


	gkPrimaryCCCIPAddr OBJECT-TYPE
	      SYNTAX  IpAddress 
	      ACCESS  read-write
	      STATUS  mandatory
	      DESCRIPTION
		  "IP address of primary Command Center"
	      ::= { cGkConfig  5 }

	gkSecCCCIPAddr OBJECT-TYPE
	      SYNTAX  IpAddress 
	      ACCESS  read-write
	      STATUS  mandatory
	      DESCRIPTION
		  "IP address of secondary Command Center"
	      ::= { cGkConfig  6 }



	gkServiceLpdFilePath OBJECT-TYPE
	      SYNTAX  DisplayString 
	      ACCESS  read-write
	      STATUS  mandatory
	      DESCRIPTION
		  "Location of telephone user interface, or Line Port Director (LPD) file"
	      ::= { cGkConfig  7 }


	gkDebugFilePath OBJECT-TYPE
	      SYNTAX  DisplayString 
	      ACCESS  read-write
	      STATUS  mandatory
	      DESCRIPTION
		  "Path to Clarent Gatekeeper trace configuration file"
	      ::= { cGkConfig  8 }

	gkLogFileEnable OBJECT-TYPE
	      SYNTAX  INTEGER {
			disabled(0),
			enabled(1)
		  }
	      ACCESS  read-write
	      STATUS  mandatory
	      DESCRIPTION
		  "Enable or disable file logging"
	      ::= { cGkConfig  9 }

	gkLogFileDir OBJECT-TYPE
	      SYNTAX  DisplayString 
	      ACCESS  read-write
	      STATUS  mandatory
	      DESCRIPTION
		  "Directory in which Clarent Gatekeeper saves log files"
	      ::= { cGkConfig  10 }

	gkLogFileAppendString OBJECT-TYPE
	      SYNTAX  DisplayString 
	      ACCESS  read-write
	      STATUS  mandatory
	      DESCRIPTION
		  "Character string to append to Clarent Gatekeeper log file names"
	      ::= { cGkConfig  11 }

	gkLogFileRolloverSize OBJECT-TYPE
	      SYNTAX  INTEGER 
	      ACCESS  read-write
	      STATUS  mandatory
	      DESCRIPTION
		  "Size, in kilobytes, to which Clarent Gatekeeper allows a 
		  log file to grow before closing a log and starting another"
	      ::= { cGkConfig  12 }

	gkLogFileMaxNumFiles OBJECT-TYPE
	      SYNTAX  INTEGER 
	      ACCESS  read-write
	      STATUS  mandatory
	      DESCRIPTION
		  "Maximum number of log files Clarent Gatekeeper creates before 
		  overwriting existing logs"
	      ::= { cGkConfig  13 }

	gkSysLogEnable OBJECT-TYPE
	      SYNTAX  INTEGER {
			disabled(0),
			enabled(1)
		  }
	      ACCESS  read-write
	      STATUS  mandatory
	      DESCRIPTION
		  "Enable or disable logging to a system logging (syslog) daemon 
		  process running on another computer"
	      ::= { cGkConfig  14 }

	gkSysLogIpAddr OBJECT-TYPE
	      SYNTAX  IpAddress 
	      ACCESS  read-write
	      STATUS  mandatory
	      DESCRIPTION
		  "IP address of a system logging (syslog) daemon server"
	      ::= { cGkConfig  15 }

	gkGroup OBJECT-TYPE
	      SYNTAX  DisplayString 
	      ACCESS  read-write
	      STATUS  mandatory
	      DESCRIPTION
		  "Group to which Clarent Gatekeeper belongs"
	      ::= { cGkConfig  16 }

	gkPriority OBJECT-TYPE
	      SYNTAX  INTEGER 
	      ACCESS  read-write
	      STATUS  mandatory
	      DESCRIPTION
		  "Priority of this Clarent Gatekeeper in the alternate gatekeeper list"
	      ::= { cGkConfig  17 }

	gkRasKeepAliveTimer OBJECT-TYPE
	      SYNTAX  INTEGER 
	      ACCESS  read-write
	      STATUS  mandatory
	      DESCRIPTION
		  "Amount of time, in seconds, that an H.323 gateway must 
		  register with Clarent Gatekeeper. Default = 25, miniumum = 0, maximum = 120."
	      ::= { cGkConfig  18 }

	gkCCCKeepAliveTimer OBJECT-TYPE
	      SYNTAX  INTEGER 
	      ACCESS  read-write
	      STATUS  mandatory
	      DESCRIPTION
		  "How often, in seconds, Clarent Gatekeeper checks its 
		  connection with the Command Center. Default = 10, minimum = 5, maximum = 120"
	      ::= { cGkConfig  19 }

	gkAdminState OBJECT-TYPE
	      SYNTAX  INTEGER {
		    locked(0),
			unlocked(1),
			shuttingDown(2)
		  }
	      ACCESS  read-write
	      STATUS  mandatory
	      DESCRIPTION
		  "Command object to shut down Gatekeeper gracefully or forcefully"
	      ::= { cGkConfig  20 }

	gkGracefulShutdownPeriod OBJECT-TYPE
	      SYNTAX  INTEGER 
	      ACCESS  read-write
	      STATUS  mandatory
	      DESCRIPTION
		  "Number of minutes to wait before shutting down Clarent Gatekeeper gracefully"
	      ::= { cGkConfig  21 }
-- Clarent GateKeeper Traps

	gkIsDown  TRAP-TYPE
		ENTERPRISE clarent-gktraps
		VARIABLES { trapSeverity, trapText, trapCount }
		DESCRIPTION

		"Clarent Gatekeeper is down"
		::= 1

	gkRestartFailed  TRAP-TYPE
		ENTERPRISE clarent-gktraps
		VARIABLES { trapSeverity, trapText, trapCount }
		DESCRIPTION

		"Clarent Gatekeeper failed to restart"
		::= 2

	gkRestarted  TRAP-TYPE
		ENTERPRISE clarent-gktraps
		VARIABLES { trapSeverity, trapText, trapCount }
		DESCRIPTION

		"Clarent Gatekeeper restarted successfully"
		::= 3


	gkNotRegistered  TRAP-TYPE
		ENTERPRISE clarent-gktraps
		VARIABLES { trapSeverity, trapText, trapCount }
		DESCRIPTION

		"Clarent Gatekeeper cannot register with the Command Center"
		::= 4

	gkOpStateChg  TRAP-TYPE
		ENTERPRISE clarent-gktraps
		VARIABLES { trapSeverity, trapText, gkOpState, trapCount }
		DESCRIPTION

		"Clarent Gatekeeper changed operational state. Operational states are: 
		disabled (0), enabled (1)."
		::= 5

	gkLoadStateCritical  TRAP-TYPE
		ENTERPRISE clarent-gktraps
		VARIABLES { trapSeverity, trapText, trapCount }
		DESCRIPTION

		"Clarent Gatekeeper load state is critical. Load states are: 
		Minimal (0), Light (1), Medium (2), Heavy (3), 
		Dangerously Heavy (4), and Critical (5)."
		::= 6


	gkIsRejectingRasMsg  TRAP-TYPE
		ENTERPRISE clarent-gktraps
		VARIABLES { trapSeverity, trapText, trapCount }
		DESCRIPTION

		"Clarent Gatekeeper started rejecting H.225 RAS messages.
	Clarent::For Future Release"
		::= 7


	gkEndpointUnreachable  TRAP-TYPE
		ENTERPRISE clarent-gktraps
		VARIABLES { trapSeverity, trapText, serverIpAddr , trapCount}
		DESCRIPTION

		"Endpoint stopped sending keepalive messages to Clarent Gatekeeper"
		::= 8

	gkEndPointURQFailed  TRAP-TYPE
		ENTERPRISE clarent-gktraps
		VARIABLES { trapSeverity, trapText, serverIpAddr, trapCount }
		DESCRIPTION

		"Endpoint attempted to unregister but has active calls"
		::= 9


	 END
