-- Request For Comments
     
H320MCU-MIB DEFINITIONS ::= BEGIN
        IMPORTS
             Counter32, Integer32, OBJECT-TYPE, MODULE-IDENTITY
                 FROM SNMPv2-SMI
             DisplayString, TruthValue
                 FROM SNMPv2-TC
             OBJECT-GROUP, MODULE-COMPLIANCE
                 FROM SNMPv2-CONF
             MmGlobalIdentifier,
             mmH320Root
                 FROM MULTI-MEDIA-MIB-TC;

         -- Define the top of this MIB.
   
     
        -- This MIB module describes H.320 MCU devices in ASN.1 as applicable to
        -- and for use with SNMP.  It describes the hardware elements within
        -- the device and the H.320 MCU information abstracted as conferences and
        -- terminals within conferences.
        -- This is the MIB module for the H.320 MCU objects

         h320Mcu MODULE-IDENTITY
             LAST-UPDATED "9812222253Z"      -- Tuesday December 22, 1998
             ORGANIZATION "ITU-T"
             CONTACT-INFO
             "ITU-T SG 16 "
             DESCRIPTION
                " "
          ::= { mmH320Root 3 }

         --groups in h320 Mcu

        h320McuSystem          OBJECT IDENTIFIER ::= { h320Mcu 1 }
        h320McuConference      OBJECT IDENTIFIER ::= { h320Mcu 2 }
        h320McuTerminal        OBJECT IDENTIFIER ::= { h320Mcu 3 }
        h320McuControls        OBJECT IDENTIFIER ::= { h320Mcu 4 } 
        h320McuMIBConformance  OBJECT IDENTIFIER ::= { h320Mcu 5 }     


        h320McuSysDescr OBJECT-TYPE
             SYNTAX  DisplayString 
             MAX-ACCESS  read-only
             STATUS  current
             DESCRIPTION
               " Multipoint Control Unit , 
                 which interconnects H.320 and T.120 -compliant conferencing 
                 systems. "
                 ::= { h320McuSystem 1 }

        h320McuSysSoftwareVersion OBJECT-TYPE
             SYNTAX INTEGER (1..65535)
             MAX-ACCESS read-only
             STATUS current
             DESCRIPTION
                "This  data element is used to describe the H.320 software
                 revision."
                ::= { h320McuSystem 2 }

        h320McuSysG728 OBJECT-TYPE
               SYNTAX TruthValue
               MAX-ACCESS read-only
               STATUS current
               DESCRIPTION
                 "This value identifies whether the system is enabled for
                  G728 audio codec.An ITU-T Recommendation for the encoding of
                  128-kbps companded PCM data to 16-kbps LD-CFLP code word"
                   ::= {h320McuSystem 3}

        h320McuSysChairControl OBJECT-TYPE
               SYNTAX TruthValue
               MAX-ACCESS read-only
               STATUS current
               DESCRIPTION
                  "This value identifies whether the system is enabled for a 
                   video-switching method (using ITU-T Recommendation H.243) 
                   in which a participant at a conference site selects the 
                   current broadcaster from the controls provided by the
                   conferencing system."
                   ::= {h320McuSystem 4}

        h320McuSysConferencePassword OBJECT-TYPE
               SYNTAX TruthValue
               MAX-ACCESS read-only
               STATUS current
               DESCRIPTION
                  "H320 Conference Password Supported."
                   ::= {h320McuSystem 5}

        h320McuSysH243Cascading OBJECT-TYPE
               SYNTAX TruthValue
               MAX-ACCESS read-only
               STATUS current
               DESCRIPTION
                  "Connecting two or more MCSs together to increase the number
                   of terminals included in a multipoint conference"
                   ::= {h320McuSystem 6}

        h320McuConfStatusTable OBJECT-TYPE
             SYNTAX SEQUENCE OF H320McuConfStatusTableEntry
             MAX-ACCESS not-accessible
             STATUS current
             DESCRIPTION
                "This table contains information about entities that provide 
                 status information for a conference. It is a list of 
                 conference entries.
                 The number of entries equals to the number of conferences."
             ::= { h320McuConference 1 }

         h320McuConfStatusTableEntry OBJECT-TYPE
             SYNTAX H320McuConfStatusTableEntry
             MAX-ACCESS not-accessible
             STATUS current
             DESCRIPTION 
                 "It contains objects that describe a conference."
             INDEX { h320McuConfId }
             ::= { h320McuConfStatusTable 1 }

         H320McuConfStatusTableEntry ::=
              SEQUENCE {
                  h320McuConfId
                     MmGlobalIdentifier,
                  h320McuConfName
                     OCTET STRING, 
                  h320McuConfVideoSrc
                     TruthValue,
                  h320McuConfLsdSrc
                     TruthValue,
                  h320McuConfHsdSrc
                     TruthValue,
                  h320McuConfConferenceChair
                     TruthValue,
                  h320McuConfLsdChannelOpen
                     TruthValue,
                  h320McuConfHsdChannelOpen
                     TruthValue,
                  h320McuConfVideoMode
                     TruthValue,
                  h320McuConfSelectedCaps
                      DisplayString,
                  h320McuConfTransferRate
                      INTEGER,
                  h320McuConfNetworkSpeed
                      INTEGER       
                            
           }

         h320McuConfId OBJECT-TYPE
               SYNTAX MmGlobalIdentifier
               MAX-ACCESS  not-accessible
               STATUS current
               DESCRIPTION
                  "The conference ID of the conference whose status you requested."
                   ::= { h320McuConfStatusTableEntry 1 }

         h320McuConfName OBJECT-TYPE
             SYNTAX OCTET STRING (SIZE (0..29))
             MAX-ACCESS read-only
             STATUS current
             DESCRIPTION
                "The name of the conference whose status you requested."
                 ::= { h320McuConfStatusTableEntry 2 }

         h320McuConfVideoSrc OBJECT-TYPE
             SYNTAX TruthValue 
             MAX-ACCESS read-only
             STATUS current
             DESCRIPTION
                "The terminal number for the current conference video source. terminal 
                 numbers are assigned when a terminal is added to the conference. "
                 ::= { h320McuConfStatusTableEntry 3}

         h320McuConfLsdSrc OBJECT-TYPE
              SYNTAX TruthValue 
              MAX-ACCESS read-only
              STATUS current
              DESCRIPTION
                 "The terminal number of the current conference low-speed data source."
                 ::= { h320McuConfStatusTableEntry 4 }

         h320McuConfHsdSrc OBJECT-TYPE
              SYNTAX TruthValue (1..65535)
              MAX-ACCESS read-only
              STATUS current
              DESCRIPTION
                 "The terminal number of the current conference high-speed data 
                  source."
                  ::= { h320McuConfStatusTableEntry 5 }

         h320McuConfConferenceChair OBJECT-TYPE
              SYNTAX TruthValue
              MAX-ACCESS read-only
              STATUS current
              DESCRIPTION
                 "The terminal number of the H.243 chairl controller for the 
                  current conference"
                  ::= { h320McuConfStatusTableEntry 6 }

         h320McuConfHsdChannelOpen OBJECT-TYPE
              SYNTAX TruthValue 
              MAX-ACCESS read-only
              STATUS current
              DESCRIPTION
                 "The current status for the high-speed data channel in this conference"
                  ::= { h320McuConfStatusTableEntry 7 }

         h320McuConfLsdChannelOpen OBJECT-TYPE
              SYNTAX TruthValue 
              MAX-ACCESS read-only
              STATUS current
              DESCRIPTION
                 "The current status for the low-speed data channel in this conference"
                  ::= { h320McuConfStatusTableEntry 8 }

         h320McuConfVideoMode  OBJECT-TYPE
              SYNTAX TruthValue 
              MAX-ACCESS read-only
              STATUS current
              DESCRIPTION
                 "The current conference video switching mode:
                     0=Voice-Activated, No Chair
                     1=User-controlled (MCV)
                     2=Chair Controlled (VCB)
                     3=Director Selected
                     4=Voice-Activated With Chair "
                  ::= { h320McuConfStatusTableEntry 9 }

         h320McuConfSelectedCaps OBJECT-TYPE
              SYNTAX DisplayString
              MAX-ACCESS read-only
              STATUS current
              DESCRIPTION
                 "The capabilities that were selected for the current 
                  conference. "
                 ::= { h320McuConfStatusTableEntry 10}

         h320McuConfTransferRate OBJECT-TYPE
              SYNTAX INTEGER (1..65535)
              MAX-ACCESS read-only
              STATUS current
              DESCRIPTION
                 "Conferemce transfer rate. "
                  ::= { h320McuConfStatusTableEntry 11 }

         h320McuConfNetworkSpeed OBJECT-TYPE
              SYNTAX INTEGER { restricted (1), unrestricted (2)}
              MAX-ACCESS read-only
              STATUS current
              DESCRIPTION
                 "Network type used by this conference:
                    1 - RESTRICTED=56 kbps channels
                    2 - UNRESTRICTED=64 kbps channels"
                  ::= { h320McuConfStatusTableEntry 12 }

         h320McuTerminalStatusTable OBJECT-TYPE
             SYNTAX SEQUENCE OF H320McuTerminalStatusTableEntry
             MAX-ACCESS not-accessible
             STATUS current
             DESCRIPTION
                "This table contains information about entities that provide status
                 information for h320McuTerminals.
                 The number of entries equals to the number of terminals."
             ::= { h320McuTerminal 1 }

         h320McuTerminalStatusTableEntry OBJECT-TYPE
             SYNTAX H320McuTerminalStatusTableEntry
             MAX-ACCESS not-accessible
             STATUS current
             DESCRIPTION 
                 "It contains objects that describe a terminal."
             INDEX { h320McuTerminalId }
             ::= { h320McuTerminalStatusTable 1 }

         H320McuTerminalStatusTableEntry ::=
              SEQUENCE {
                  h320McuTerminalId
                      Integer32,
                  h320McuTerminalConfId
                      MmGlobalIdentifier, 
                  h320McuTerminalConfName
                     OCTET STRING ,
                  h320McuTerminalAudioFrom
                     TruthValue ,
                  h320McuTerminalVideoFrom
                     TruthValue ,
                  h320McuTerminalLsdChannelStatus
                     INTEGER ,
                  h320McuTerminalHsdChannelStatus
                     INTEGER ,
                  h320McuTerminalCapabilities
                      DisplayString,
                  h320McuTerminalStatus
                     INTEGER,
                  h320McuTerminalPhoneNumber
                       OCTET STRING ,
                  h320McuTerminalMCUPhoneNumber
                       OCTET STRING
              }

          h320McuTerminalId OBJECT-TYPE
               SYNTAX Integer32
               MAX-ACCESS  not-accessible
               STATUS current
               DESCRIPTION
                  "The terminal id number given at the time of registration."
                   ::= { h320McuTerminalStatusTableEntry 1 }

          h320McuTerminalConfId OBJECT-TYPE
               SYNTAX MmGlobalIdentifier
               MAX-ACCESS read-only
               STATUS current
               DESCRIPTION
                  "The conference id for this terminal. "
                   ::= { h320McuTerminalStatusTableEntry 2 }

          h320McuTerminalConfName OBJECT-TYPE
               SYNTAX OCTET STRING (SIZE (0..29))
               MAX-ACCESS read-only
               STATUS current
               DESCRIPTION
                  "The conference name for this terminal."
                   ::= { h320McuTerminalStatusTableEntry 3 }

          h320McuTerminalAudioFrom OBJECT-TYPE
               SYNTAX TruthValue
               MAX-ACCESS read-only
               STATUS current
               DESCRIPTION
                  "0 - no audio from the terminal 
                   1 - audio from the terminal ok. "
                   ::= { h320McuTerminalStatusTableEntry 4 }

          h320McuTerminalVideoFrom OBJECT-TYPE
               SYNTAX TruthValue
               MAX-ACCESS read-only
               STATUS current
               DESCRIPTION
                  "0 - no video from the terminal 
                   1 - video from the terminal ok. "
                   ::= { h320McuTerminalStatusTableEntry 5 }

          h320McuTerminalLsdChannelStatus OBJECT-TYPE
               SYNTAX INTEGER { channelOpen (1), channelClosed (2)}
               MAX-ACCESS read-only
               STATUS current
               DESCRIPTION
                  "2 - low-speed data channel is closed
                   1 - low-speed data channel is open. "
                   ::= { h320McuTerminalStatusTableEntry 6 }

          h320McuTerminalHsdChannelStatus OBJECT-TYPE
               SYNTAX INTEGER  { channelOpen (1), channelClosed (2)}
               MAX-ACCESS read-only
               STATUS current
               DESCRIPTION
                  "2 - high-speed data channel is closed
                   1 - high-speed data channel is open.    "
                   ::= { h320McuTerminalStatusTableEntry 7 }

          h320McuTerminalCapabilities OBJECT-TYPE
               SYNTAX DisplayString
               MAX-ACCESS read-only
               STATUS current
               DESCRIPTION
                  "Capabilities for this terminal. "
                   ::= { h320McuTerminalStatusTableEntry 8 }

          h320McuTerminalStatus OBJECT-TYPE
               SYNTAX INTEGER {notConnected (1), connectionInprogress (2), connected (3), h320Framed (4)}
               MAX-ACCESS read-only
               STATUS current
               DESCRIPTION
                  "    "
                   ::= { h320McuTerminalStatusTableEntry 9 }

          h320McuTerminalPhoneNumber OBJECT-TYPE
               SYNTAX OCTET STRING (SIZE (0..25))
               MAX-ACCESS read-only
               STATUS current
               DESCRIPTION
                  "The phone number for this terminal. "
                   ::= { h320McuTerminalStatusTableEntry 10 }

          h320McuTerminalMCUPhoneNumber OBJECT-TYPE
               SYNTAX OCTET STRING (SIZE (0..25))
               MAX-ACCESS read-only
               STATUS current
               DESCRIPTION
                  "The MCU phone number."
                   ::= { h320McuTerminalStatusTableEntry 11 }

        h320McuTerminalStatsTable OBJECT-TYPE
               SYNTAX SEQUENCE OF H320McuTerminalStatsTableEntry
               MAX-ACCESS not-accessible
               STATUS current
               DESCRIPTION
                  "This table contains information about entities that are
                   connected to the MCU. It is a list of connected terminals.
                   The number of entries equals to the number of terminals."
                   ::= { h320McuTerminal 2 }

          h320McuTerminalStatsTableEntry OBJECT-TYPE
               SYNTAX H320McuTerminalStatsTableEntry
               MAX-ACCESS not-accessible
               STATUS current
               DESCRIPTION
                  "It contains objects that describe a terminal."
               INDEX { h320McuTerminalId }
                   ::= { h320McuTerminalStatsTable 1 }

         H320McuTerminalStatsTableEntry ::=
              SEQUENCE {
                  h320McuTerminalStatsTerminalId
                      Integer32,
                  h320McuTerminalStatsConfId
                      MmGlobalIdentifier, 
                  h320McuTerminalStatsConfName
                      OCTET STRING,
                  h320McuTerminalStatsRxMultiframes 
                      Integer32,
                  h320McuTerminalStatsFALossAtTerminal
                      Integer32,
                  h320McuTerminalStatsMCUCrcErrors
                      Counter32,
                  h320McuTerminalStatsTerminalCrcErrors
                      Counter32,
                  h320McuTerminalStatsStatsRequests
                      Counter32
                }


          h320McuTerminalStatsTerminalId OBJECT-TYPE
               SYNTAX Integer32
               MAX-ACCESS read-only
               STATUS current
               DESCRIPTION
                  "The terminal id number assigned during terminal registration."
                   ::= { h320McuTerminalStatsTableEntry 1 }

          h320McuTerminalStatsConfId OBJECT-TYPE
               SYNTAX MmGlobalIdentifier
               MAX-ACCESS read-only
               STATUS current
               DESCRIPTION
                  "The conference id for this terminal. "
                   ::= { h320McuTerminalStatsTableEntry 2 }

          h320McuTerminalStatsConfName OBJECT-TYPE
               SYNTAX OCTET STRING (SIZE (0..29))
               MAX-ACCESS read-only
               STATUS current
               DESCRIPTION
                  "The conference name for this terminal."
                   ::= { h320McuTerminalStatsTableEntry 3 }  

          h320McuTerminalStatsRxMultiframes OBJECT-TYPE
               SYNTAX Integer32
               MAX-ACCESS read-only
               STATUS current
               DESCRIPTION
                  "The number of received multiframes."
                   ::= { h320McuTerminalStatsTableEntry 4 }

          h320McuTerminalStatsFALossAtTerminal OBJECT-TYPE
               SYNTAX Integer32 
               MAX-ACCESS read-only
               STATUS current
               DESCRIPTION
                  "The number of H.221 frame alignment loss errors."
                   ::= { h320McuTerminalStatsTableEntry 5 }

          h320McuTerminalStatsMCUCrcErrors OBJECT-TYPE
               SYNTAX Counter32
               MAX-ACCESS read-only
               STATUS current
               DESCRIPTION
                  "The number of MCU CRC errors."
                   ::= { h320McuTerminalStatsTableEntry 6 }

          h320McuTerminalStatsTerminalCrcErrors OBJECT-TYPE
               SYNTAX Counter32
               MAX-ACCESS read-only
               STATUS current
               DESCRIPTION
                  "The number of terminal CRC errors."
                   ::= { h320McuTerminalStatsTableEntry 7 }

          h320McuTerminalStatsStatsRequests OBJECT-TYPE
               SYNTAX Counter32
               MAX-ACCESS read-only
               STATUS current
               DESCRIPTION
                  "The number of stats requests. "
                   ::= { h320McuTerminalStatsTableEntry 8 }

          h320McuControlsCommands OBJECT-TYPE 
               SYNTAX INTEGER { 
                       other(1),
                       abruptRestart(2),
                       gracefulRestart (3),
                       abruptShutdown(4),
                       gracefulShutdown (5),
                       enterQuiescence (6),
                       exitQuiescence (7),
                       startLog(8), 
                       stopLog(9),
                       resetStatistics(10), 
                       runDiagnostic(11)
              } 
               MAX-ACCESS read-write 
               STATUS current 
               DESCRIPTION 
          "A value that represents a command for the H.320 MCU.
           1. Other             (for proprietary extensions)
           2. Abrupt Restart    (Drastic Restart)
           3. Graceful Restart  (Restart after all calls have terminated. 
                                 Meanwhile, accept no calls) 
           4. Abrupt Shutdown   (Drastic Restart)
           5. Graceful Shutdown (Shutdown after all calls have terminated.
                                 Meanwhile, accept no calls) 
           6. Enter Quiescence Mode (Disable receiving of calls)
           7. Exit  Quiescence Mode (Enable  receiving of calls)
           8. Start Error/Log Reporting
           9. Stop Error/Log Reporting
          10. Reset Statistics
          11. Run Diagnostic"
                ::= { h320McuControls 1}   
   
--
-- CONFORMANCE
--
h320McuMIBGroups  OBJECT IDENTIFIER ::= { h320McuMIBConformance 1 }

--
-- Groups for Conformance 
--

h320McuSystemGroup OBJECT-GROUP
    OBJECTS {
            h320McuSysDescr,
            h320McuSysSoftwareVersion,
            h320McuSysG728,
            h320McuSysChairControl,
            h320McuSysConferencePassword,
            h320McuSysH243Cascading
       }
    STATUS  current
    DESCRIPTION
       "."
    ::= { h320McuMIBGroups 1 }

h320McuConferenceGroup OBJECT-GROUP
    OBJECTS {
            h320McuConfName,
            h320McuConfVideoSrc,
            h320McuConfLsdSrc,
            h320McuConfHsdSrc,
            h320McuConfConferenceChair,
            h320McuConfLsdChannelOpen,
            h320McuConfHsdChannelOpen,
            h320McuConfVideoMode,
            h320McuConfSelectedCaps,
            h320McuConfTransferRate,
            h320McuConfNetworkSpeed
       }
    STATUS  current
    DESCRIPTION
       "."
    ::= { h320McuMIBGroups 2 }

h320McuTerminalGroup OBJECT-GROUP
    OBJECTS {

            h320McuTerminalConfId,
            h320McuTerminalConfName,
            h320McuTerminalAudioFrom,
            h320McuTerminalVideoFrom,
            h320McuTerminalLsdChannelStatus,
            h320McuTerminalHsdChannelStatus,
            h320McuTerminalCapabilities,
            h320McuTerminalStatus,
            h320McuTerminalPhoneNumber,
            h320McuTerminalMCUPhoneNumber,
--
            h320McuTerminalStatsTerminalId,
            h320McuTerminalStatsConfId,
            h320McuTerminalStatsConfName,
            h320McuTerminalStatsRxMultiframes, 
            h320McuTerminalStatsFALossAtTerminal,
            h320McuTerminalStatsMCUCrcErrors,
            h320McuTerminalStatsTerminalCrcErrors,
            h320McuTerminalStatsStatsRequests
       }
    STATUS  current
    DESCRIPTION
       "."
    ::= { h320McuMIBGroups 3 }

h320McuControlsGroup OBJECT-GROUP
    OBJECTS {
            h320McuControlsCommands
       }
    STATUS  current
    DESCRIPTION
       "."
    ::= { h320McuMIBGroups 4 }

h320McuMIBCompliance        MODULE-COMPLIANCE
    STATUS      current
    DESCRIPTION
        "The set of objects required for compliance."
    MODULE
        MANDATORY-GROUPS { h320McuSystemGroup,
                           h320McuConferenceGroup,
                           h320McuTerminalGroup,
                           h320McuControlsGroup 
                         }
   ::= { h320McuMIBConformance  2 }

END
