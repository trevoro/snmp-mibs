--			Ascend mibdialmod MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBDIALMOD-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibdialModifierProfile  OBJECT IDENTIFIER ::= { configuration 74}

	-- The mibdialModifierProfile table
	--
	-- This table contains parameters for the mibdialModifierProfile profile
	--

    mibdialModifierProfileTable	OBJECT-TYPE
	SYNTAX		SEQUENCE OF MibdialModifierProfileEntry
	ACCESS		not-accessible
	STATUS		mandatory
	DESCRIPTION	"A list of mibdialModifierProfile profile entries."
	::= { mibdialModifierProfile 1 }

    mibdialModifierProfileEntry	OBJECT-TYPE
	SYNTAX		MibdialModifierProfileEntry
	ACCESS		not-accessible
	STATUS		mandatory
	DESCRIPTION	"A mibdialModifierProfile entry containing objects that
			 maps to the parameters of mibdialModifierProfile profile."
	INDEX		{ dialModifierProfile-Name }
	::= { mibdialModifierProfileTable 1 }

    MibdialModifierProfileEntry ::=
	SEQUENCE {
	    dialModifierProfile-Name
		DisplayString,
	    dialModifierProfile-Active
		INTEGER,
	    dialModifierProfile-UserSuppliedTg
		INTEGER,
	    dialModifierProfile-TrunkGroupFilter
		INTEGER,
	    dialModifierProfile-SlotFilter
		INTEGER,
	    dialModifierProfile-PortTypeFilter
		INTEGER,
	    dialModifierProfile-PrefixFilter
		DisplayString,
	    dialModifierProfile-LengthFilter
		INTEGER,
	    dialModifierProfile-DialPlan
		INTEGER,
	    dialModifierProfile-NewTrunkGroup
		INTEGER,
	    dialModifierProfile-Action-o
		INTEGER
	}

    dialModifierProfile-Name	OBJECT-TYPE
	SYNTAX	DisplayString
	ACCESS	read-only
	STATUS	mandatory
	DESCRIPTION	""
	::= { mibdialModifierProfileEntry 1 }

    dialModifierProfile-Active	OBJECT-TYPE
	SYNTAX	INTEGER {
		    no (1),
		    yes (2)
		}
	ACCESS	read-write
	STATUS	mandatory
	DESCRIPTION	"TRUE to allow use of this profile, FALSE otherwise."
	::= { mibdialModifierProfileEntry 2 }

    dialModifierProfile-UserSuppliedTg	OBJECT-TYPE
	SYNTAX	INTEGER {
		    no (1),
		    yes (2)
		}
	ACCESS	read-write
	STATUS	mandatory
	DESCRIPTION	"TRUE if dial string contains the trunk group."
	::= { mibdialModifierProfileEntry 3 }

    dialModifierProfile-TrunkGroupFilter	OBJECT-TYPE
	SYNTAX	INTEGER
	ACCESS	read-write
	STATUS	mandatory
	DESCRIPTION	"Trunk group filter (0 for any)"
	::= { mibdialModifierProfileEntry 4 }

    dialModifierProfile-SlotFilter	OBJECT-TYPE
	SYNTAX	INTEGER
	ACCESS	read-write
	STATUS	mandatory
	DESCRIPTION	"Slot filter (0 for any)"
	::= { mibdialModifierProfileEntry 5 }

    dialModifierProfile-PortTypeFilter	OBJECT-TYPE
	SYNTAX	INTEGER {
		    any (1),
		    maxpots (2)
		}
	ACCESS	read-write
	STATUS	mandatory
	DESCRIPTION	"Port-type filter."
	::= { mibdialModifierProfileEntry 6 }

    dialModifierProfile-PrefixFilter	OBJECT-TYPE
	SYNTAX	DisplayString
	ACCESS	read-write
	STATUS	mandatory
	DESCRIPTION	"Dial prefix filter"
	::= { mibdialModifierProfileEntry 7 }

    dialModifierProfile-LengthFilter	OBJECT-TYPE
	SYNTAX	INTEGER
	ACCESS	read-write
	STATUS	mandatory
	DESCRIPTION	"Dial string length filter"
	::= { mibdialModifierProfileEntry 8 }

    dialModifierProfile-DialPlan	OBJECT-TYPE
	SYNTAX	INTEGER
	ACCESS	read-write
	STATUS	mandatory
	DESCRIPTION	"Use dial plan (0 for none)"
	::= { mibdialModifierProfileEntry 9 }

    dialModifierProfile-NewTrunkGroup	OBJECT-TYPE
	SYNTAX	INTEGER
	ACCESS	read-write
	STATUS	mandatory
	DESCRIPTION	"Change trunk group to (0 for don't change"
	::= { mibdialModifierProfileEntry 10 }

    dialModifierProfile-Action-o	OBJECT-TYPE
	SYNTAX	INTEGER {
		    noAction (1),
		    createProfile (2),
		    deleteProfile (3)
		}
	ACCESS	read-write
	STATUS	mandatory
	DESCRIPTION	""
	::= { mibdialModifierProfileEntry 11 }

END
