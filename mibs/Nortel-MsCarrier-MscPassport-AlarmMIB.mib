Nortel-MsCarrier-MscPassport-AlarmMIB 
DEFINITIONS ::= BEGIN

IMPORTS

      OBJECT-TYPE 
   FROM RFC-1212

      TRAP-TYPE
   FROM RFC-1215

      DisplayString, DateAndTime, RowPointer, Unsigned32
   FROM Nortel-MsCarrier-MscPassport-StandardTextualConventionsMIB

      Hex, AsciiString, HexString, DigitString
   FROM Nortel-MsCarrier-MscPassport-TextualConventionsMIB

      mscPassportMIBs, mscPassportTraps
   FROM Nortel-MsCarrier-MscPassport-UsefulDefinitionsMIB;
		

-- LAST-UPDATED    "9907300000Z"
-- ORGANIZATION    "Nortel Networks"
-- CONTACT-INFO    "
--         Nortel Carrier Data Network Management
--
--         Postal:       P.O. Box 3511, Station C 
--                       Ottawa, Ontario
--                       Canada  K1Y 4H7
--
--	   via the WEB:  http://www.nortelnetworks.com
--                       select 'Contact Us' from the menu
--
--	   via phone:    1-800-4NORTEL"

-- DESCRIPTION
--    "This MIB module specifies the variables and notifications
--    used to implement the MsCarrier MscPassport Alarms reporting
--    facility. The Passport 6400, 7400, 8700, 15000 Alarms 
--    NTP 241-5701-500 describes the Alarm generation philosophy."

alarmMIB     OBJECT IDENTIFIER ::= { mscPassportMIBs 4 }

mscAlarmTrap    OBJECT IDENTIFIER ::= { mscPassportTraps 2 }

-- the mscMandatoryAlarmInfo group

-- STATUS     	current
-- DESCRIPTION
--    " This group contains the mandatory variables representing information 
--      pertinent to all alarms: mscComponentRowPointer, mscComponentName, 
--      mscEventTime, mscActiveListStatus, mscSeverity, mscAlarmType, 
--      mscProbableCause, mscNtpIndex, and mscCommentData"
mscMandatoryAlarmInfo   OBJECT IDENTIFIER ::= { mscAlarmTrap 7 }

mscComponentRowPointer OBJECT-TYPE
   SYNTAX	RowPointer
   ACCESS	not-accessible  
   STATUS	mandatory
   DESCRIPTION
   	" A pointer to the RowStatus variable of the component emitting 
          the alarm."
   ::= { mscMandatoryAlarmInfo 1 }

mscComponentName OBJECT-TYPE
   SYNTAX	DisplayString
   ACCESS	not-accessible 
   STATUS	mandatory
   DESCRIPTION
      " The textual name of the component emitting the alarm in a format
        suitable for use in commands entered on the `console'.  It 
        includes the name of the node from which the alarm was 
        sent, as specified in `ModuleData nodeName'."
   ::= { mscMandatoryAlarmInfo 2 }

mscEventTime OBJECT-TYPE
   SYNTAX	DateAndTime
   ACCESS	not-accessible
   STATUS	mandatory
   DESCRIPTION
      " The date and time at which the alarmed event occurred."
   ::= { mscMandatoryAlarmInfo 3 }

mscActiveListStatus OBJECT-TYPE
   SYNTAX	INTEGER { message(0), set(1), clear(2) }
   ACCESS	not-accessible
   STATUS	mandatory
   DESCRIPTION
      " The active alarm list status. This may be used by the
        Manager to add (on receiving a set) and delete (on 
        receiving a clear) alarms from the alarm displays."
   ::= { mscMandatoryAlarmInfo 4 }

mscSeverity OBJECT-TYPE
   SYNTAX	INTEGER { indeterminate(0), critical(1), major(2), minor(3), 
                          warning(4), cleared(5) }
   ACCESS	not-accessible
   STATUS	mandatory
   DESCRIPTION
      " The severity of the alarm which should indicate what
        priority that fixing this problem should be given.  All
        values are OSI-defined; refer to CCITT X.733/ISO 10164-4
        for a more complete description."
   ::= { mscMandatoryAlarmInfo 5 }

mscAlarmType OBJECT-TYPE
   SYNTAX	INTEGER { communications(0), qualityOfService(1),
		          processing(2), equipment(3), environmental(4),
			  security(5), operator(6), debug(7), unknown(8) }
   ACCESS	not-accessible
   STATUS	mandatory
   DESCRIPTION
      " The alarm type field as defined by OSI which is
        used to indicate a broad category of what is wrong. The 
        first 6 values are OSI-defined; refer to CCITT X.733/ISO 10164-4
        (for the first 5)  and CCITT X.736/ISO 10164-4 (for the last) 
        for a more complete description.

   	The value 'operator' is used when an alarm is issued due to an 
        operator command. The values 'debug' and 'unknown' are for 
        compatibility with older switches and are used for debugging alarms and 
        for those which do not fit any of the above, respectively."
   ::= { mscMandatoryAlarmInfo 6}

mscProbableCause OBJECT-TYPE
   SYNTAX	INTEGER {
		-- Start of OSI-defined values
                -- (see X.733/ ISO 10165-3)

		lossOfSignal(0),
		lossOfFrame(1),
		framingError(2),
		localTransmissionError(3),
		remoteTransmissionError(4),
		callEstablishmentError(5),
		degradedSignal(6),
		commSubsystemFailure(7),
		commProtocolError(8),
		lanError(9),
		dteDceInterfaceError(10),
		
		responseTimeExcessive(20),
		queueSizeExceeded(21),
		bandwidthReduced(22),
		retransmissionRateReduced(23),
		thresholdCrossed(24),
		performanceDegraded(25),
		congestion(26),
		atOrNearCapacity(27),
		
		storageCapacityProblem(40),
		versionMismatch(41),
		corruptData(42),
		cpuCyclesLimitExceeded(43),
		softwareError(44),
		softwareProgramError(45),
		softwareProgramTermination(46),
		fileError(47),
		outOfMemory(48),
		underlyingResourceUnavail(49),
		applicationSubsystemFailure(50),
		configurationError(51),
		
		powerProblem(60),
		timingProblem(61),
		processorProblem(62),
		datasetModemError(63),
		multiplexorProblem(64),
		receiverFailure(65),
		transmitterFailure(66),
		outputDeviceError(67),
		inputDeviceError(68),
		ioDeviceError(69),
		equipmentFailure(70),
		adapterError(71),
		
		-- OSI-defined values continued (see X.736)
		duplicateInfo(80),
		infoMissing(81),
		infoModification(82),
		infoOutOfSequence(83),
		unexpectedInfo(84),
		
		denialOfService(90),
		outOfService(91),
		proceduralError(92),
		otherOperational(93),
		
		cableTamper(100),
		intrusionDetection(101),
		otherPhysical(102),
		
		authenticationFailure(110),
		breachOfConfidence(111),
		nonRepudiationFailure(112),
		unauthorizedAccess(113),
		otherSecurityService(114),
		
		delayedInfo(120),
		keyExpired(121),
		outOfHoursActivity(122),
		
		-- Start of non-OSI defined values
		operationalCondition(200),
		debugging(201),
		unknown(202),
		inactiveVirtualCircuit(203),
		networkServerIntervention(204)
	}
   ACCESS	not-accessible
   STATUS	mandatory
   DESCRIPTION
      " The probable cause for the alarm which usually qualifies
        the Alarm Type field. Most values are OSI-defined; refer
        refer to CCITT X.733 and X.736 (ISO 10164-4 and 10164-7) for a more 
        complete description."
   ::= { mscMandatoryAlarmInfo 7}

mscNtpIndex OBJECT-TYPE
   SYNTAX	DigitString (SIZE(8))
   ACCESS	not-accessible
   STATUS	mandatory
   DESCRIPTION
      " An 8-digit code which is an index into an NTP to 
        provide more description of the alarm and possible actions to 
        take. The first 4 digits indicate a 'group' of alarms 
        (belonging to a particular subsystem or component, etc.). The last 
   	4 digits are a subindex arbitrarily assigned by the application 
        which is responsible for them."
   ::= { mscMandatoryAlarmInfo 8 }

mscCommentData	OBJECT-TYPE
   SYNTAX	AsciiString (SIZE(0..750))
   ACCESS	not-accessible
   STATUS	mandatory
   DESCRIPTION
      " Additional textual information for the network operator to use. 
        It contains only ASCII characters. 
        Note: The total number of bytes in mscCommentData, mscOperatorData, 
        and mscInternalData may not exceed 750 bytes."
   ::= { mscMandatoryAlarmInfo 9}

-- the mscOptionalAlarmInfo group

-- STATUS	current
-- DESCRIPTION
--    " This group contains optional variables representing information 
--      pertinent to all alarms: mscNotificationID, mscLpForHierClear,
-- 	mscOperatorData, mscPid, mscFileName, mscFileLineNumber, mscFileVersion, 
--      and mscInternalData."
mscOptionalAlarmInfo   OBJECT IDENTIFIER ::= { mscAlarmTrap 8}

mscNotificationID	OBJECT-TYPE
   SYNTAX	Hex
   ACCESS	not-accessible
   STATUS	mandatory
   DESCRIPTION
      " The notification Id of the alarm. The high-order byte is
        the card number of the card from which this alarm originated. 
        The low-order 24 bits contain a sequence number which increases each 
        time an alarm is generated. Thus, this id provides a simple way of 
        uniquely identifying an alarm as well as the order in which alarms 
        are generated on a card. For cross-card ordering, one 
	would have to look at the time stamp (see dateAndTime)."
   ::= { mscOptionalAlarmInfo 1 }

mscLpForHierClear	OBJECT-TYPE
   SYNTAX	RowPointer
   ACCESS	not-accessible
   STATUS	mandatory
   DESCRIPTION
      " A pointer to the RowStatus variable of the Logical Processor 
        the component generating the alarm is running on. A component
        generating an Alarm with `mscActiveListStatus = set' can include
        this variable in the Alarm.  If the identified Logical Processor 
        generates a Hierarchical Clear Alarm, then it will clear the 
        Set Alarm."
   ::= { mscOptionalAlarmInfo 2 }

mscOperatorData	OBJECT-TYPE
   SYNTAX	HexString (SIZE(0..750))
   ACCESS	not-accessible
   STATUS	mandatory
   DESCRIPTION
      " Additional hexadecimal information for the network operator to 
        use. Note: The total number of bytes in mscCommentData, mscOperatorData, 
        and mscInternalData may not exceed 750 bytes."
   ::= { mscOptionalAlarmInfo 3 }

mscPid		OBJECT-TYPE
   SYNTAX	DisplayString (SIZE (0..25))
   ACCESS	not-accessible
   STATUS	mandatory
   DESCRIPTION
      " A string representation of the internal process id (Pid) 
        of the process which generated the alarm (for 
        internal use only). Note that it may or may not map to the 
        mscComponentName field. "
   ::= { mscOptionalAlarmInfo 4 }

mscFileName	OBJECT-TYPE
   SYNTAX 	DisplayString
   ACCESS	not-accessible
   STATUS	mandatory
   DESCRIPTION
      " An internal filename (for internal use only)."
   ::= { mscOptionalAlarmInfo 5 }

mscFileLineNumber	OBJECT-TYPE
   SYNTAX	Unsigned32
   ACCESS	not-accessible
   STATUS	mandatory
   DESCRIPTION
      " An internal line number in the file (see filename) 
        referred to above (for internal use only)."
   ::= { mscOptionalAlarmInfo 6 }

mscFileVersion	OBJECT-TYPE
   SYNTAX	DisplayString
   ACCESS	not-accessible
   STATUS	mandatory
   DESCRIPTION
      " A version indicator of the file (filename) referred
        to above (for internal use only)."
   ::= { mscOptionalAlarmInfo 7}

mscInternalData	OBJECT-TYPE
   SYNTAX	HexString (SIZE(0..750))
   ACCESS	not-accessible
   STATUS	mandatory
   DESCRIPTION
      " An additional internal hexadecimal information for
        internal use only. Note: The total number of bytes in comment, 
        operator, and internal data may not exceed 750 bytes."
   ::= { mscOptionalAlarmInfo 8 }

-- the mscProvisionalAlarmInfo group

--   STATUS       current
--   DESCRIPTION
--      " This group contains provisional variables representing information
--        pertinent to all alarms: mscCid"
mscProvisionalAlarmInfo OBJECT IDENTIFIER ::= { mscAlarmTrap 9 }
mscCid    OBJECT-TYPE
   SYNTAX       Unsigned32
   ACCESS       not-accessible
   STATUS       mandatory
   DESCRIPTION
      " This is a Custom Identifier(CID) of the component which generated
        the alarm"
   ::= { mscProvisionalAlarmInfo 1 }

-- The following notifications are defined. Note that the structure and content
-- of each notification is identical.

-- The notification types are defined (one for each type of Alarm severity)
-- to accomodate simple Trap monitoring tools which assign severity
-- to a Trap based on the Specific Trap Number as opposed to the value
-- of a variable bind in the trap.

-- A Carrier Passport alarm with mscSeverity = critical will be mapped into the
-- mscCriticalAlarm notification.  A Carrier Passport alarm with mscSeverity = 
-- cleared will be mapped into the mscClearedAlarm notification, etc.
-- Note that the Trap number corresponds to the severity variable bind's
-- enumerated value, with the exception of an mscIndeterminateAlarm, which
-- has a number of 6, and a severity variable bind value of 0 to correspond
-- to the OSI-defined value.

mscCriticalAlarm TRAP-TYPE
   ENTERPRISE mscAlarmTrap
   VARIABLES { mscComponentRowPointer, mscComponentName, mscEventTime, 
	     mscActiveListStatus, mscSeverity, mscAlarmType, mscProbableCause, 
	     mscNtpIndex, mscCommentData } 
   DESCRIPTION		
      " This trap is used to provide a real time indication of a critical Alarm
        condition.  The variables listed in the VARIABLES clause,
        defined in the `mscMandatoryAlarmInfo' group are present 
        in all critical alarms. Additional variables as defined in
        the 'mscOptionalAlarmInfo' group may be included if appropriate. "
::= 1

mscMajorAlarm TRAP-TYPE
   ENTERPRISE mscAlarmTrap
   VARIABLES { mscComponentRowPointer, mscComponentName, mscEventTime, 
             mscActiveListStatus, mscSeverity, mscAlarmType, mscProbableCause, 
	     mscNtpIndex, mscCommentData } 
   DESCRIPTION		
      " This trap is used to provide a real time indication of a major Alarm
        condition.  The variables listed in the VARIABLES clause,
        defined in the `mscMandatoryAlarmInfo' group are present 
        in all major alarms. Additional variables as defined in
        the 'mscOptionalAlarmInfo' group may be included if appropriate. "
::= 2

mscMinorAlarm TRAP-TYPE
   ENTERPRISE mscAlarmTrap
   VARIABLES { mscComponentRowPointer, mscComponentName, mscEventTime, 
               mscActiveListStatus, mscSeverity, mscAlarmType, mscProbableCause, 
               mscNtpIndex, mscCommentData } 
   DESCRIPTION		
      " This trap is used to provide a real time indication of a minor Alarm
        condition.  The variables listed in the VARIABLES clause,
        defined in the `mscMandatoryAlarmInfo' group are present 
        in all minor alarms. Additional variables as defined in
        the 'mscOptionalAlarmInfo' group may be included if appropriate. "
::= 3

mscWarningAlarm TRAP-TYPE
   ENTERPRISE mscAlarmTrap
   VARIABLES { mscComponentRowPointer, mscComponentName, mscEventTime, 
	     mscActiveListStatus, mscSeverity, mscAlarmType, mscProbableCause, 
	     mscNtpIndex, mscCommentData } 
   DESCRIPTION		
      " This trap is used to provide a real time indication of a warning Alarm
        condition.  The variables listed in the VARIABLES clause,
        defined in the `mscMandatoryAlarmInfo' group are present 
        in all warning alarms. Additional variables as defined in
        the 'mscOptionalAlarmInfo' group may be included if appropriate. "
::= 4

mscClearedAlarm TRAP-TYPE
   ENTERPRISE mscAlarmTrap
   VARIABLES { mscComponentRowPointer, mscComponentName, mscEventTime, 
	     mscActiveListStatus, mscSeverity, mscAlarmType, mscProbableCause, 
	     mscNtpIndex, mscCommentData } 
   DESCRIPTION		
      " This trap is used to provide a real time indication of a cleared
        Alarm.  The variables listed in the VARIABLES clause,
        defined in the `mscMandatoryAlarmInfo' group are present 
        in all cleared alarms. Additional variables as defined in
        the 'mscOptionalAlarmInfo' group may be included if appropriate. "
::= 5

mscIndeterminateAlarm TRAP-TYPE
   ENTERPRISE mscAlarmTrap
   VARIABLES { mscComponentRowPointer, mscComponentName, mscEventTime, 
	     mscActiveListStatus, mscSeverity, mscAlarmType, mscProbableCause, 
	     mscNtpIndex, mscCommentData } 
   DESCRIPTION		
      " This trap is used to provide a real time indication of an indeterminate
        Alarm condition.  The variables listed in the VARIABLES clause,
        defined in the `mscMandatoryAlarmInfo' group are present 
        in all indeterminate alarms. Additional variables as defined in
        the 'mscOptionalAlarmInfo' group may be included if appropriate. "
::= 6


--
-- Version and Compliance statements
--
 
 
-- Object-Group Statement:
 
-- OBJECTS   { mscComponentRowPointer, mscComponentName, mscEventTime, 
--             mscActiveListStatus, mscSeverity, mscAlarmType, mscProbableCause,  
--             mscNtpIndex, mscCommentData, mscNotificationID, mscLpForHierClear, 
-- 	       mscOperatorData, mscPid, mscFileName, mscFileLineNumber, 
--	       mscFileVersion, mscInternalData }
-- STATUS     current
-- DESCRIPTION
--       "A list of all current accessible leaf objects."

alarmGroup OBJECT IDENTIFIER ::= { alarmMIB 1 }
alarmGroupCA OBJECT IDENTIFIER ::= { alarmGroup 1 }
alarmGroupCA01 OBJECT IDENTIFIER ::= { alarmGroupCA 2 }
alarmGroupCA01A OBJECT IDENTIFIER ::= { alarmGroupCA01 2 }



-- Notification Group:

-- NOTIFICATIONS   { mscCriticalAlarm, mscMajorAlarm, mscMinorAlarm, 
--                   mscWarningAlarm, mscClearedAlarm, mscIndeterminateAlarm }
-- STATUS          current
-- DESCRIPTION
--    "A list of all current notifications defined in this Module."

alarmNotifications OBJECT IDENTIFIER ::= { alarmMIB 2 }
alarmNotificationsGroupCA01A OBJECT IDENTIFIER ::= { alarmNotifications 1 }



-- Agent-Capabilities Statement:

-- PRODUCT-RELEASE "Passport Carrier Release 1.1 Alarms."
-- STATUS          current
-- DESCRIPTION
--    "Carrier Passport Alarms MIB: MIB Version CA01A."
-- SUPPORTS        Nortel-MsCarrier-MscPassport-AlarmMIB
-- INCLUDES        { alarmGroupCA01A, 
--                   alarmNotificationsGroupCA01A }

alarmCapabilities OBJECT IDENTIFIER ::= { alarmMIB 3 }
alarmCapabilitiesCA OBJECT IDENTIFIER ::= { alarmCapabilities 1 }
alarmCapabilitiesCA01 OBJECT IDENTIFIER ::= { alarmCapabilitiesCA 2 }
alarmCapabilitiesCA01A OBJECT IDENTIFIER ::= { alarmCapabilitiesCA01 2 }


END
