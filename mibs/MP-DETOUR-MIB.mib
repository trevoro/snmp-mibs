-- ***************************************************************************
-- FileName    :mpDetourMib.my
-- Description :Detour Private MIB
-- Revision History     :
--   Ver.     mark   date      
--   01.01    @001   08/14/2001
-- ***************************************************************************

MP-DETOUR-MIB DEFINITIONS ::= BEGIN

   IMPORTS
      mgmt, NetworkAddress, IpAddress, Counter, Gauge, TimeTicks
      FROM RFC1155-SMI

      ifIndex
      FROM RFC1213-MIB

      OBJECT-TYPE
      FROM RFC-1212

      TRAP-TYPE
      FROM RFC-1215;

   DisplayString ::= OCTET STRING


-- The following definition is privately defined for IX5000 Private MIB

   org               OBJECT IDENTIFIER ::= { iso 3 }
   dod               OBJECT IDENTIFIER ::= { org 6 }
   internet          OBJECT IDENTIFIER ::= { dod 1 }
   private           OBJECT IDENTIFIER ::= { internet 4 }
   enterprises       OBJECT IDENTIFIER ::= { private 1 }
   nec               OBJECT IDENTIFIER ::= { enterprises 119}

   necProduct        OBJECT IDENTIFIER ::= { nec 1 }
   datax             OBJECT IDENTIFIER ::= { necProduct 3 }
   mmpf              OBJECT IDENTIFIER ::= { datax 13 }
   mmn9110           OBJECT IDENTIFIER ::= { mmpf 1 }
   mmn9120           OBJECT IDENTIFIER ::= { mmpf 2 }

   nec-mib           OBJECT IDENTIFIER ::= { nec 2 }
   necProductDepend  OBJECT IDENTIFIER ::= { nec-mib 3 }
   datax-mib         OBJECT IDENTIFIER ::= { necProductDepend 3 }
   mmpf-mib          OBJECT IDENTIFIER ::= { datax-mib 13 }

   mpDetour                 OBJECT IDENTIFIER ::= { mmpf-mib 130 }


-- Detour Private MIB


--
-- 迂回管理情報
--

       mpDetourTable OBJECT-TYPE
               SYNTAX  SEQUENCE OF MpDetourEntry
               ACCESS  not-accessible
               STATUS  mandatory
               DESCRIPTION 
			"This is the table type object of Detour infomation" 
               ::= { mpDetour 1 }

       mpDetourEntry OBJECT-TYPE
               SYNTAX  MpDetourEntry
               ACCESS  not-accessible
               STATUS  mandatory
               DESCRIPTION 
			"This is the table entry of mpDetourTable."
               INDEX   { mpDetourID }
               ::= { mpDetourTable 1 }


       MpDetourEntry ::=
               SEQUENCE {
                   mpDetourID
                       INTEGER,
                   mpObservationIfindex
                       INTEGER,
                   mpObservationIfType
                       INTEGER,
                   mpObservationIfNumber
                       INTEGER,
                   mpDetourIfindex
                       INTEGER,
                   mpDetourIfType
                       INTEGER,
                   mpDetourIfNumber
                       INTEGER,
                   mpObservationAdminStatus
                       INTEGER,
                   mpObservationOperStatus
                       INTEGER,
                   mpDiscardIfindex
                       INTEGER, 
                   mpDiscardIfType
                       INTEGER,
                   mpDiscardIfNumber
                       INTEGER,
                   mpDetourAdminStatus
                       INTEGER,
                   mpDetourOperStatus
                       INTEGER,
                   mpDiscardAdminStatus
                       INTEGER,
                   mpDiscardOperStatus
                       INTEGER,
                   mpRouteStatus
                       INTEGER,
                   mpInhibitMode
                       INTEGER,
                   mpWatchMode
                       INTEGER 
               }

--Detour ID
mpDetourID OBJECT-TYPE
	SYNTAX	INTEGER
	ACCESS	read-only
	STATUS	mandatory
	DESCRIPTION
		"This object is ifIndex of observation route."
--迂回管理識別子：迂回管理ブロックが監視ルートを監視するためび識別子
	::= { mpDetourEntry 1 }

--迂回元　ifindex
mpObservationIfindex OBJECT-TYPE
	SYNTAX	INTEGER
	ACCESS	read-only
	STATUS	mandatory
	DESCRIPTION
		"This object is ifIndex of observation route."
	::= { mpDetourEntry 2 }

--迂回元仮想インタフェースタイプ
mpObservationIfType OBJECT-TYPE
	SYNTAX  INTEGER {
			atmpp(1),
			vlan(2),
			lis(3),
			outband(4),
			trunk(5),
			ppp(6),
			frpp(7),
			vlantrap(8),
			mplspp(9)
			}
	ACCESS  read-only
	STATUS  mandatory
	DESCRIPTION
		"This object is interface type of observation route."
	::= { mpDetourEntry 3 }

--迂回元仮想インタフェース番号
mpObservationIfNumber   OBJECT-TYPE
	SYNTAX  INTEGER
	ACCESS  read-only
	STATUS  mandatory
	DESCRIPTION
		"This object is interface number of observation route."
	::= { mpDetourEntry 4 }

--迂回先　ifindex
mpDetourIfindex OBJECT-TYPE
	SYNTAX	INTEGER
	ACCESS	read-only
	STATUS	mandatory
	DESCRIPTION
		"This object is ifIndex of detour route."
	::= { mpDetourEntry 5 }

--迂回先仮想インタフェースタイプ
mpDetourIfType OBJECT-TYPE
	SYNTAX  INTEGER {
			atmpp(1),
			vlan(2),
			lis(3),
			outband(4),
			trunk(5),
			ppp(6),
			frpp(7),
			vlantrap(8),
			mplspp(9)
			}
	ACCESS  read-only
	STATUS  mandatory
	DESCRIPTION
		"This object is interface type of detour route."
	::= { mpDetourEntry 6 }

--迂回先仮想インタフェース番号
mpDetourIfNumber   OBJECT-TYPE
	SYNTAX  INTEGER
	ACCESS  read-only
	STATUS  mandatory
	DESCRIPTION
		"This object is interface number of detour route."
	::= { mpDetourEntry 7 }

--迂回元インタフェースの内部設定状態
mpObservationAdminStatus  OBJECT-TYPE
	SYNTAX  INTEGER {
			up(1),
			down(2)
			}
	ACCESS	read-write
	STATUS  mandatory
	DESCRIPTION
		"The value of this object identifies the desired
                 administer status of this observation route."
	::= { mpDetourEntry 8 }

--迂回元インタフェースの内部状態
mpObservationOperStatus  OBJECT-TYPE
	SYNTAX  INTEGER {
			up(1),
			down(2)
			}
	ACCESS  read-only
	STATUS  mandatory
	DESCRIPTION
		"The value of this object identifies the desired
                 operational status of this observation route."
	::= { mpDetourEntry 9 }

--パケット廃棄用　ifindex                    @001追加
mpDiscardIfindex OBJECT-TYPE
	SYNTAX	INTEGER
	ACCESS	read-only
	STATUS	mandatory
	DESCRIPTION
		"This object is ifIndex of discard route."
	::= { mpDetourEntry 10 }

--パケット廃棄用仮想インタフェースタイプ     @001追加
mpDiscardIfType OBJECT-TYPE
	SYNTAX  INTEGER {
			atmpp(1),
			vlan(2),
			lis(3),
			outband(4),
			trunk(5),
			ppp(6),
			frpp(7),
			vlantrap(8),
			mplspp(9)
			}
	ACCESS  read-only
	STATUS  mandatory
	DESCRIPTION
		"This object is interface type of discard route."
	::= { mpDetourEntry 11 }

--パケット廃棄用仮想インタフェース番号       @001追加
mpDiscardIfNumber   OBJECT-TYPE
	SYNTAX  INTEGER
	ACCESS  read-only
	STATUS  mandatory
	DESCRIPTION
		"This object is interface number of discard route."
	::= { mpDetourEntry 12 }

--迂回先インタフェースの内部設定状態         @001追加
mpDetourAdminStatus  OBJECT-TYPE
	SYNTAX  INTEGER {
			up(1),
			down(2)
			}
	ACCESS	read-write
	STATUS  mandatory
	DESCRIPTION
		"The value of this object identifies the desired
                 administer status of this detour route."
	::= { mpDetourEntry 13 }

--迂回先インタフェースの内部状態             @001追加
mpDetourOperStatus  OBJECT-TYPE
	SYNTAX  INTEGER {
			up(1),
			down(2)
			}
	ACCESS  read-only
	STATUS  mandatory
	DESCRIPTION
		"The value of this object identifies the desired
                 operational status of this detour route."
	::= { mpDetourEntry 14 }

--パケット廃棄用インタフェースの内部設定状態   @001追加
mpDiscardAdminStatus  OBJECT-TYPE
	SYNTAX  INTEGER {
			up(1),
			down(2)
			}
	ACCESS	read-write
	STATUS  mandatory
	DESCRIPTION
		"The value of this object identifies the desired
                 administer status of this discard route."
	::= { mpDetourEntry 15 }

--パケット廃棄用インタフェースの内部状態      @001追加
mpDiscardOperStatus  OBJECT-TYPE
	SYNTAX  INTEGER {
			up(1),
			down(2)
			}
	ACCESS  read-only
	STATUS  mandatory
	DESCRIPTION
		"The value of this object identifies the desired
                 operational status of this discard route."
	::= { mpDetourEntry 16 }

--監視ルートの状態                           @001追加
mpRouteStatus  OBJECT-TYPE
	SYNTAX  INTEGER {
			up(1),
			down(2)
			}
	ACCESS  read-only
	STATUS  mandatory
	DESCRIPTION
		"The value of this object identifies the desired
                 operational status of this observe route."
	::= { mpDetourEntry 17 }

--迂回抑止設定/解除                         @001追加
mpInhibitMode  OBJECT-TYPE
	SYNTAX  INTEGER {
			on(1),
			off(2)
			}
	ACCESS  read-write
	STATUS  mandatory
	DESCRIPTION
		"This object is inhibit mode data."
	::= { mpDetourEntry 18 }

--迂回監視モード                           @001追加
mpWatchMode  OBJECT-TYPE
	SYNTAX  INTEGER {
			on(1),
			off(2)
			}
	ACCESS  read-only
	STATUS  mandatory
	DESCRIPTION
		"This object is watch mode data."
	::= { mpDetourEntry 19 }

--
-- 迂回管理構成変化
--
mpDetourConfigChangeTimeStamp  OBJECT IDENTIFIER ::= { mpDetour 2 }

mpDetourConfigLastChange   OBJECT-TYPE
     SYNTAX       TimeTicks
     ACCESS       read-only
     STATUS       mandatory
     DESCRIPTION   "This object indicates the the time which configuration of the Detour data
                    is changed."
--構成に関する状態変化が発生した時刻。
--迂回管理のConfigデータが設定又は削除された時
--変化時点のTimeTicksが設定される。

	::= { mpDetourConfigChangeTimeStamp 1 }

--
-- 迂回管理状態変化
--
mpDetourStatusTimeStamp  OBJECT IDENTIFIER ::= { mpDetour 3 }

mpDetourStatusLastChange    OBJECT-TYPE
     SYNTAX       TimeTicks
     ACCESS       read-only
     STATUS       mandatory
     DESCRIPTION   "This object indicates the the time which configuration of 
                    the operational status is changed."
--迂回元の内部Oper　Statusの状態変化が発生した時刻。
--変化時点のTimeTicksが設定される。

 	::= { mpDetourStatusTimeStamp 1 }


END
