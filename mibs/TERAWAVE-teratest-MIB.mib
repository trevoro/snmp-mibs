TERAWAVE-teratest-MIB DEFINITIONS ::= BEGIN
        -- Created by sml2mib compiler 
        IMPORTS

 enterprises,  OBJECT-TYPE,  Counter,  Gauge,  TimeTicks
        FROM RFC1155-SMI
	Counter32 FROM SNMPv2-SMI
	;

terawave OBJECT IDENTIFIER ::=  { enterprises 4513 }

teraTestGroup OBJECT IDENTIFIER ::=  { terawave 14 }

     -- teraTestTable

teraTestTable OBJECT-TYPE
     SYNTAX SEQUENCE OF TeraTestTableEntryType
     ACCESS not-accessible
     STATUS mandatory
     DESCRIPTION
          " table teraTestTable"
     ::= { teraTestGroup 1 }

teraTestTableEntry OBJECT-TYPE
          SYNTAX TeraTestTableEntryType
          ACCESS not-accessible
          STATUS mandatory
          DESCRIPTION
               " table entry teraTestTableEntry "
          INDEX {                   teraTestSourceSlot,                  teraTestIndex }
     ::= { teraTestTable 1 }

TeraTestTableEntryType ::= SEQUENCE {
          teraTestSourceSlot   
             INTEGER (1..7),
          teraTestIndex   
             Counter32 (1..4294967295),
          teraTestTargetIfIndex   
             INTEGER,
          teraTestTargetVpi   
             INTEGER,
          teraTestTargetVci   
             INTEGER,
          teraTestTargetDirection   
             INTEGER,
          teraTestType   
             OBJECT IDENTIFIER,
          teraTestMoreInfo   
             OCTET STRING,
          teraTestResultTimeStamp   
             TimeTicks,
          teraTestResult   
             INTEGER,
          teraTestCode   
             INTEGER,
          teraTestRowStatus   
             INTEGER,
          teraTestAction   
             INTEGER
}

teraTestSourceSlot OBJECT-TYPE
          SYNTAX INTEGER (1..7)
          ACCESS read-only
          STATUS mandatory
          DESCRIPTION
               ""
          ::= { teraTestTableEntry 1 }

teraTestIndex OBJECT-TYPE
          SYNTAX Counter32 (1..4294967295)
          ACCESS read-only
          STATUS mandatory
          DESCRIPTION
               ""
          ::= { teraTestTableEntry 2 }

teraTestTargetIfIndex OBJECT-TYPE
          SYNTAX INTEGER
          ACCESS read-write
          STATUS mandatory
          DESCRIPTION
               ""
          ::= { teraTestTableEntry 3 }

teraTestTargetVpi OBJECT-TYPE
          SYNTAX INTEGER
          ACCESS read-write
          STATUS mandatory
          DESCRIPTION
               ""
          ::= { teraTestTableEntry 4 }

teraTestTargetVci OBJECT-TYPE
          SYNTAX INTEGER
          ACCESS read-write
          STATUS mandatory
          DESCRIPTION
               ""
          ::= { teraTestTableEntry 5 }

teraTestTargetDirection OBJECT-TYPE
          SYNTAX INTEGER
                  {
                  upstream(1),
                  downstream(2)
                  }
          ACCESS read-write
          STATUS mandatory
          DESCRIPTION
               ""
          ::= { teraTestTableEntry 6 }

teraTestType OBJECT-TYPE
          SYNTAX OBJECT IDENTIFIER
          ACCESS read-write
          STATUS mandatory
          DESCRIPTION
               ""
          ::= { teraTestTableEntry 7 }

teraTestMoreInfo OBJECT-TYPE
          SYNTAX OCTET STRING
          ACCESS read-write
          STATUS mandatory
          DESCRIPTION
               ""
          ::= { teraTestTableEntry 8 }

teraTestResultTimeStamp OBJECT-TYPE
          SYNTAX TimeTicks
          ACCESS read-only
          STATUS mandatory
          DESCRIPTION
               ""
          ::= { teraTestTableEntry 9 }

teraTestResult OBJECT-TYPE
          SYNTAX INTEGER
                  {
                  none(1),
                  success(2),
                  inProgress(3),
                  notSupported(4),
                  unAbleToRun(5),
                  aborted(6),
                  failed(7)
                  }
          ACCESS read-only
          STATUS mandatory
          DESCRIPTION
               ""
          ::= { teraTestTableEntry 10 }

teraTestCode OBJECT-TYPE
          SYNTAX INTEGER
                  {
                  none(1),
                  unkown(2),
                  timeout(3),
                  manualStop(4),
                  portFail(5),
                  invalidTarget(6)
                  }
          ACCESS read-only
          STATUS mandatory
          DESCRIPTION
               ""
          ::= { teraTestTableEntry 11 }

teraTestRowStatus OBJECT-TYPE
          SYNTAX INTEGER
                  {
                  notInService(1),
                  active(2),
                  inProgress(3),
                  destroy(4)
                  }
          ACCESS read-write
          STATUS mandatory
          DESCRIPTION
               ""
          ::= { teraTestTableEntry 12 }

teraTestAction OBJECT-TYPE
          SYNTAX INTEGER
                  {
                  none(1),
                  send(2)
                  }
          ACCESS read-write
          STATUS mandatory
          DESCRIPTION
               ""
          ::= { teraTestTableEntry 13 }

     -- teraTestCapabilityTable

teraTestCapabilityTable OBJECT-TYPE
     SYNTAX SEQUENCE OF TeraTestCapabilityTableEntryType
     ACCESS not-accessible
     STATUS mandatory
     DESCRIPTION
          " table teraTestCapabilityTable"
     ::= { teraTestGroup 2 }

teraTestCapabilityTableEntry OBJECT-TYPE
          SYNTAX TeraTestCapabilityTableEntryType
          ACCESS not-accessible
          STATUS mandatory
          DESCRIPTION
               " table entry teraTestCapabilityTableEntry "
          INDEX {                   teraTestSourceSlot }
     ::= { teraTestCapabilityTable 1 }

TeraTestCapabilityTableEntryType ::= SEQUENCE {
          teraTestIndexNext   
             Counter32,
          teraTestTableMaxSize   
             Counter32 (10..4294967295),
          teraTestCapabilityTypeBits   
             INTEGER
}

teraTestIndexNext OBJECT-TYPE
          SYNTAX Counter32
          ACCESS read-only
          STATUS mandatory
          DESCRIPTION
               ""
          ::= { teraTestCapabilityTableEntry 1 }

teraTestTableMaxSize OBJECT-TYPE
          SYNTAX Counter32 (10..4294967295)
          ACCESS read-only
          STATUS mandatory
          DESCRIPTION
               ""
          ::= { teraTestCapabilityTableEntry 2 }

teraTestCapabilityTypeBits OBJECT-TYPE
          SYNTAX INTEGER
          ACCESS read-only
          STATUS mandatory
          DESCRIPTION
               ""
          ::= { teraTestCapabilityTableEntry 3 }

END
