NETBOTZ-PRD-BOT-MIB DEFINITIONS ::= BEGIN

IMPORTS
   OBJECT-TYPE FROM RFC-1212
   TRAP-TYPE FROM RFC-1215
   netBotz-ismetric FROM NETBOTZ-DEVICE-MIB
   netBotz-prd-bot FROM NETBOTZ-PRODUCTS-MIB
   netBotz-products FROM NETBOTZ-MIB
   DisplayString FROM RFC1213-MIB
   IpAddress FROM RFC1155-SMI;

netBotz-prd-bot-temp OBJECT-TYPE
	SYNTAX		INTEGER
	ACCESS		read-only
	STATUS		mandatory
	DESCRIPTION	"The reading of the temperature probe, in degrees F or degrees C (depends on netBotz-ismetric)."
	REFERENCE 	"NetBotz Temperature Probe"
	::= { netBotz-prd-bot 1 }

netBotz-prd-bot-humidity     OBJECT-TYPE
	SYNTAX		INTEGER
	ACCESS		read-only
	STATUS		mandatory
	DESCRIPTION	"The reading of the humidity probe, in percent."
	REFERENCE 	"NetBotz Humidity Probe"
	::= { netBotz-prd-bot 2 }

netBotz-prd-bot-airflow      OBJECT-TYPE
	SYNTAX		INTEGER
	ACCESS		read-only
	STATUS		mandatory
	DESCRIPTION	"The reading of the airflow probe.  Each unit represents approximately 40 feet/minute or
            13 meters/minute of airflow velocity."
	REFERENCE 	"NetBotz Airflow Probe"
	::= { netBotz-prd-bot 3 }

netBotz-prd-bot-audio   OBJECT-TYPE
	SYNTAX		INTEGER
	ACCESS		read-only
	STATUS		mandatory
	DESCRIPTION	"The reading of the audio alarm probe on/off."
	REFERENCE 	"NetBotz Audio Probe"
	::= { netBotz-prd-bot 4 }

netBotz-prd-bot-doorajar     OBJECT-TYPE
	SYNTAX		INTEGER
	ACCESS		read-only
	STATUS		mandatory
	DESCRIPTION	"The reading of the door switch probe open(0) or closed(1)."
	REFERENCE 	"NetBotz Door Switch Probe"
	::= { netBotz-prd-bot 5 }

netBotz-prd-bot-temp-min OBJECT-TYPE
	SYNTAX		INTEGER
	ACCESS		read-write
	STATUS		mandatory
	DESCRIPTION	"The temperature probe minimum, from 35 to 120 degrees F, or 1 to 50 degrees C (depends on netBotz-ismetric)."
	REFERENCE 	"NetBotz Temperature Probe Minimum"
	::= { netBotz-prd-bot 6 }

netBotz-prd-bot-temp-max OBJECT-TYPE
	SYNTAX		INTEGER
	ACCESS		read-write
	STATUS		mandatory
	DESCRIPTION	"The temperature probe maximum, from 35 to 120 degrees F, or 1 to 50 degrees C (depends on netBotz-ismetric)."
	REFERENCE 	"NetBotz Temperature Probe Maximum"
	::= { netBotz-prd-bot 7 }

netBotz-prd-bot-humidity-min OBJECT-TYPE
	SYNTAX		INTEGER
	ACCESS		read-write
	STATUS		mandatory
	DESCRIPTION	"The humidity probe minimum, from 10 to 90 percent."
	REFERENCE 	"NetBotz Humidity Probe Minimum"
	::= { netBotz-prd-bot 8 }

netBotz-prd-bot-humidity-max OBJECT-TYPE
	SYNTAX		INTEGER
	ACCESS		read-write
	STATUS		mandatory
	DESCRIPTION	"The humidity probe maximum, from 10 to 90 percent."
	REFERENCE 	"NetBotz Humidity Probe Maximum"
	::= { netBotz-prd-bot 9 }

netBotz-prd-bot-airflow-mins OBJECT-TYPE
	SYNTAX		INTEGER
	ACCESS		read-write
	STATUS		mandatory
	DESCRIPTION	"Minutes without airflow before alarm set."
	REFERENCE 	"NetBotz|Airflow minutes"
	::= { netBotz-prd-bot 10 }

netBotz-prd-bot-audio-secs OBJECT-TYPE
	SYNTAX		INTEGER
	ACCESS		read-write
	STATUS		mandatory
	DESCRIPTION	"Seconds of alarm audio before alarm set."
	REFERENCE 	"NetBotz|Audio seconds"
	::= { netBotz-prd-bot 11 }

netBotz-prd-bot-temp-enabled OBJECT-TYPE
	SYNTAX		INTEGER
	ACCESS		read-write
	STATUS		mandatory
	DESCRIPTION	"Temperature probe alarm enabled(1) or disabled(0)."
	REFERENCE 	"NetBotz|Temperature Probe Enabled"
	::= { netBotz-prd-bot 12 }

netBotz-prd-bot-hum-enabled OBJECT-TYPE
	SYNTAX		INTEGER
	ACCESS		read-write
	STATUS		mandatory
	DESCRIPTION	"Humidity probe alarm enabled(1) or disabled(0)."
	REFERENCE 	"NetBotz|Humidity Probe Enabled"
	::= { netBotz-prd-bot 13 }

netBotz-prd-bot-air-enabled OBJECT-TYPE
	SYNTAX		INTEGER
	ACCESS		read-write
	STATUS		mandatory
	DESCRIPTION	"Airflow probe alarm enabled(1) or disabled(0)."
	REFERENCE 	"NetBotz|Airflow Probe Enabled"
	::= { netBotz-prd-bot 14 }

netBotz-prd-bot-audio-enabled OBJECT-TYPE
	SYNTAX		INTEGER
	ACCESS		read-write
	STATUS		mandatory
	DESCRIPTION	"Audio probe alarm enabled(1) or disabled(0)."
	REFERENCE 	"NetBotz|Audio Probe Enabled"
	::= { netBotz-prd-bot 15 }

netBotz-prd-bot-switch-state OBJECT-TYPE
	SYNTAX		INTEGER
	ACCESS		read-write
	STATUS		mandatory
	DESCRIPTION	
	"Switch state setting. The state controls which
	condition of the door switch indicates an alarm.
	If set to 0, alarm is set when the switch is closed.
	If set to 1, alarm is set when the switch is open."
	REFERENCE 	"NetBotz|Switch state setting"
	::= { netBotz-prd-bot 16 }

netBotz-prd-bot-switch-enabled OBJECT-TYPE
	SYNTAX		INTEGER
	ACCESS		read-write
	STATUS		mandatory
	DESCRIPTION	"Door switch enabled(1) or disabled(0)."
	REFERENCE 	"NetBotz|Door Switch Enabled"
	::= { netBotz-prd-bot 17 }

netBotz-prd-bot-audio-level	OBJECT-TYPE
	SYNTAX		INTEGER
	ACCESS		read-write
	STATUS		mandatory
	DESCRIPTION	"Audio level setting.  This is the relative audio level, from 0-11, 
            above which an alarm will be sent."
	REFERENCE 	"NetBotz|Audio Level"
	::= { netBotz-prd-bot 18 }

netBotz-prd-bot-doorpic-delay	OBJECT-TYPE
	SYNTAX		INTEGER
	ACCESS		read-write
	STATUS		mandatory
	DESCRIPTION	"Number of seconds between door alert and first picture."
	REFERENCE 	"NetBotz|Door Picture Delay"
	::= { netBotz-prd-bot 19 }

netBotz-prd-bot-trap-index OBJECT-TYPE
	SYNTAX		INTEGER
	ACCESS		read-only
	STATUS		mandatory
	DESCRIPTION	"The crawler ID of the last trap."
	REFERENCE 	"NetBotz Last Trap Index"
	::= { netBotz-prd-bot 20 }

netBotz-prd-bot-trap-address OBJECT-TYPE
	SYNTAX		IpAddress
	ACCESS		read-only
	STATUS		mandatory
	DESCRIPTION	"The IP address of the last trap."
	REFERENCE 	"NetBotz Last Trap Address"
	::= { netBotz-prd-bot 21 }                 

netBotz-prd-bot-trap-oid OBJECT-TYPE
	SYNTAX		OBJECT IDENTIFIER
	ACCESS		read-only
	STATUS		mandatory
	DESCRIPTION	"The object id of the last trap."
	REFERENCE 	"NetBotz Last Trap OID"
	::= { netBotz-prd-bot 22 }                 

netBotz-prd-bot-trap-value OBJECT-TYPE
	SYNTAX		INTEGER
	ACCESS		read-only
	STATUS		mandatory
	DESCRIPTION	"The value of the last object trap."
	REFERENCE 	"NetBotz Last Trap Value"
	::= { netBotz-prd-bot 23 }

netBotz-prd-bot-trap-date OBJECT-TYPE
	SYNTAX		INTEGER
	ACCESS		read-only
	STATUS		mandatory
	DESCRIPTION	
	"The date and time of a specific trap. This field
	contains the number of seconds elapsed since 
	midnight (00:00:00), January 1, 1970"
	REFERENCE 	"NetBotz Trap Date"
	::= { netBotz-prd-bot 24 }

netBotz-prd-bot-refresh	OBJECT-TYPE
	SYNTAX		INTEGER
	ACCESS		read-write
	STATUS		mandatory
	DESCRIPTION	"Rate of web page refresh, in seconds.  This must be greater than 5 seconds."
	REFERENCE 	"NetBotz|Web Refresh"
	::= { netBotz-prd-bot 26 }


netBotz-prd-bot-airflow-level	OBJECT-TYPE
	SYNTAX		INTEGER
	ACCESS		read-write
	STATUS		mandatory
	DESCRIPTION	"Airflow alert level.  This is the relative level of airflow below which
	an alarm will be sent.  The range is 1-11.  Each unit is approximately 40 feet/second or 13 meters/second of
        airflow velocity."
	REFERENCE 	"NetBotz|Airflow Alert Level"
	::= { netBotz-prd-bot 27 }

netBotz-prd-bot-doorpic-count	OBJECT-TYPE
	SYNTAX		INTEGER
	ACCESS		read-write
	STATUS		mandatory
	DESCRIPTION	"Number of pictures to take when door activated.
        These pictures will be sent as attachments to the door alert e-mail.
	The range is from 0 to 5 pictures."
	REFERENCE 	"NetBotz|Door Picture Count"
	::= { netBotz-prd-bot 28 }

netBotz-prd-bot-amps1 OBJECT-TYPE
	SYNTAX		INTEGER
	ACCESS		read-only
	STATUS		mandatory
	DESCRIPTION	"The reading of the first amperage probe, in milliamps."
	REFERENCE 	"NetBotz Amperage[1] Probe"
	::= { netBotz-prd-bot 29 }

netBotz-prd-bot-amps1-enabled OBJECT-TYPE
	SYNTAX		INTEGER
	ACCESS		read-write
	STATUS		mandatory
	DESCRIPTION	"Amperage[1] probe alarm enabled(1) or disabled(0)."
	REFERENCE 	"NetBotz|Amperage[1] Probe Enabled"
	::= { netBotz-prd-bot 30 }

netBotz-prd-bot-amps1-min OBJECT-TYPE
	SYNTAX		INTEGER
	ACCESS		read-write
	STATUS		mandatory
	DESCRIPTION	"The amperage[1] probe minimum, from 0 to 30000 milliamps."
	REFERENCE 	"NetBotz Amperage[1] Probe Minimum"
	::= { netBotz-prd-bot 31 }

netBotz-prd-bot-amps1-max OBJECT-TYPE
	SYNTAX		INTEGER
	ACCESS		read-write
	STATUS		mandatory
	DESCRIPTION	"The amperage[1] probe maximum, from 0 to 30000 milliamps."
	REFERENCE 	"NetBotz Amperage[1] Probe Maximum"
	::= { netBotz-prd-bot 32 }

netBotz-prd-bot-amps2 OBJECT-TYPE
	SYNTAX		INTEGER
	ACCESS		read-only
	STATUS		mandatory
	DESCRIPTION	"The reading of the second amperage probe, in milliamps."
	REFERENCE 	"NetBotz Amperage[2] Probe"
	::= { netBotz-prd-bot 34 }

netBotz-prd-bot-amps2-enabled OBJECT-TYPE
	SYNTAX		INTEGER
	ACCESS		read-write
	STATUS		mandatory
	DESCRIPTION	"Amperage[2] probe alarm enabled(1) or disabled(0)."
	REFERENCE 	"NetBotz|Amperage[2] Probe Enabled"
	::= { netBotz-prd-bot 35 }

netBotz-prd-bot-amps2-min OBJECT-TYPE
	SYNTAX		INTEGER
	ACCESS		read-write
	STATUS		mandatory
	DESCRIPTION	"The amperage[2] probe minimum, from 0 to 30000 milliamps."
	REFERENCE 	"NetBotz Amperage[2] Probe Minimum"
	::= { netBotz-prd-bot 36 }

netBotz-prd-bot-amps2-max OBJECT-TYPE
	SYNTAX		INTEGER
	ACCESS		read-write
	STATUS		mandatory
	DESCRIPTION	"The amperage[2] probe maximum, from 0 to 30000 milliamps."
	REFERENCE 	"NetBotz Amperage[2] Probe Maximum"
	::= { netBotz-prd-bot 37 }

netBotz-prd-bot-amps3 OBJECT-TYPE
	SYNTAX		INTEGER
	ACCESS		read-only
	STATUS		mandatory
	DESCRIPTION	"The reading of the third amperage probe, in milliamps."
	REFERENCE 	"NetBotz Amperage[3] Probe"
	::= { netBotz-prd-bot 39 }

netBotz-prd-bot-amps3-enabled OBJECT-TYPE
	SYNTAX		INTEGER
	ACCESS		read-write
	STATUS		mandatory
	DESCRIPTION	"Amperage[3] probe alarm enabled(1) or disabled(0)."
	REFERENCE 	"NetBotz|Amperage[3] Probe Enabled"
	::= { netBotz-prd-bot 40 }

netBotz-prd-bot-amps3-min OBJECT-TYPE
	SYNTAX		INTEGER
	ACCESS		read-write
	STATUS		mandatory
	DESCRIPTION	"The amperage[3] probe minimum, from 0 to 30000 milliamps."
	REFERENCE 	"NetBotz Amperage[3] Probe Minimum"
	::= { netBotz-prd-bot 41 }

netBotz-prd-bot-amps3-max OBJECT-TYPE
	SYNTAX		INTEGER
	ACCESS		read-write
	STATUS		mandatory
	DESCRIPTION	"The amperage[3] probe maximum, from 0 to 30000 milliamps."
	REFERENCE 	"NetBotz Amperage[3] Probe Maximum"
	::= { netBotz-prd-bot 42 }

netBotz-prd-bot-amps-total OBJECT-TYPE
	SYNTAX		INTEGER
	ACCESS		read-only
	STATUS		mandatory
	DESCRIPTION	"The total of the readings of all amperage probes, in milliamps."
	REFERENCE 	"NetBotz Total Amperage Probe"
	::= { netBotz-prd-bot 44 }

netBotz-prd-bot-amps-total-enabled OBJECT-TYPE
	SYNTAX		INTEGER
	ACCESS		read-write
	STATUS		mandatory
	DESCRIPTION	"Total amperage alarm enabled(1) or disabled(0)."
	REFERENCE 	"NetBotz|Total Amperage Enabled"
	::= { netBotz-prd-bot 45 }

netBotz-prd-bot-amps-total-min OBJECT-TYPE
	SYNTAX		INTEGER
	ACCESS		read-write
	STATUS		mandatory
	DESCRIPTION	"The total amperage minimum, from 0 to 90000 milliamps."
	REFERENCE 	"NetBotz Total Amperage Minimum"
	::= { netBotz-prd-bot 46 }

netBotz-prd-bot-amps-total-max OBJECT-TYPE
	SYNTAX		INTEGER
	ACCESS		read-write
	STATUS		mandatory
	DESCRIPTION	"The total amperage maximum, from 0 to 90000 milliamps."
	REFERENCE 	"NetBotz Total Amperage Maximum"
	::= { netBotz-prd-bot 47 }

netBotz-prd-bot-amps-total-support-enabled OBJECT-TYPE
	SYNTAX		DisplayString
	ACCESS		read-write
	STATUS		mandatory
	DESCRIPTION	"Total Amperage Support enabled(Y) or disabled(N)."
	REFERENCE 	"NetBotz|Total Amperage Support Enabled"
	::= { netBotz-prd-bot 48 }

netBotz-prd-bot-amps1-uV-per-10mA OBJECT-TYPE
	SYNTAX		INTEGER
	ACCESS		read-write
	STATUS		mandatory
	DESCRIPTION	"The scaling factor used for the first amperage probe to convert microvolts measured from the
        Amp Detect into 10s of milliamps of current.  Needs to be set based on the type of Amp Detect module installed."
	REFERENCE 	"NetBotz uVolts To 10 mAmps 1"
	::= { netBotz-prd-bot 49 }

netBotz-prd-bot-amps2-uV-per-10mA OBJECT-TYPE
	SYNTAX		INTEGER
	ACCESS		read-write
	STATUS		mandatory
	DESCRIPTION	"The scaling factor used for the second amperage probe to convert microvolts measured from the
        Amp Detect into 10s of milliamps of current.  Needs to be set based on the type of Amp Detect module installed."
	REFERENCE 	"NetBotz uVolts To 10 mAmps 2"
	::= { netBotz-prd-bot 50 }

netBotz-prd-bot-amps3-uV-per-mA OBJECT-TYPE
	SYNTAX		INTEGER
	ACCESS		read-write
	STATUS		mandatory
	DESCRIPTION	"The scaling factor used for the third amperage probe to convert microvolts measured from the
        Amp Detect into 10s of milliamps of current.  Needs to be set based on the type of Amp Detect module installed."
	REFERENCE 	"NetBotz uVolts To 10 mAmps 3"
	::= { netBotz-prd-bot 51 }

netBotz-prd-bot-amps1-max-range OBJECT-TYPE
	SYNTAX		INTEGER
	ACCESS		read-write
	STATUS		mandatory
	DESCRIPTION	"The maximum RMS milliamps measureable by the first Amp Detect."
	REFERENCE 	"NetBotz Max milliAmps 1"
	::= { netBotz-prd-bot 52 }

netBotz-prd-bot-amps2-max-range OBJECT-TYPE
	SYNTAX		INTEGER
	ACCESS		read-write
	STATUS		mandatory
	DESCRIPTION	"The maximum RMS milliamps measureable by the second Amp Detect."
	REFERENCE 	"NetBotz Max milliAmps 2"
	::= { netBotz-prd-bot 53 }

netBotz-prd-bot-amps3-max-range OBJECT-TYPE
	SYNTAX		INTEGER
	ACCESS		read-write
	STATUS		mandatory
	DESCRIPTION	"The maximum RMS milliamps measureable by the third Amp Detect."
	REFERENCE 	"NetBotz Max milliAmps 3"
	::= { netBotz-prd-bot 54 }

netBotz-prd-bot-amps4 OBJECT-TYPE
	SYNTAX		INTEGER
	ACCESS		read-only
	STATUS		mandatory
	DESCRIPTION	"The reading of the fourth amperage probe, in milliamps."
	REFERENCE 	"NetBotz Amperage[4] Probe"
	::= { netBotz-prd-bot 55 }

netBotz-prd-bot-amps4-enabled OBJECT-TYPE
	SYNTAX		INTEGER
	ACCESS		read-write
	STATUS		mandatory
	DESCRIPTION	"Amperage[4] probe alarm enabled(1) or disabled(0)."
	REFERENCE 	"NetBotz|Amperage[4] Probe Enabled"
	::= { netBotz-prd-bot 56 }

netBotz-prd-bot-amps4-min OBJECT-TYPE
	SYNTAX		INTEGER
	ACCESS		read-write
	STATUS		mandatory
	DESCRIPTION	"The amperage[4] probe minimum, in milliamps."
	REFERENCE 	"NetBotz Amperage[4] Probe Minimum"
	::= { netBotz-prd-bot 57 }

netBotz-prd-bot-amps4-max OBJECT-TYPE
	SYNTAX		INTEGER
	ACCESS		read-write
	STATUS		mandatory
	DESCRIPTION	"The amperage[4] probe maximum, in milliamps."
	REFERENCE 	"NetBotz Amperage[4] Probe Maximum"
	::= { netBotz-prd-bot 58 }

netBotz-prd-bot-amps4-uV-per-10mA OBJECT-TYPE
	SYNTAX		INTEGER
	ACCESS		read-write
	STATUS		mandatory
	DESCRIPTION	"The scaling factor used for the fourth amperage probe to convert microvolts measured from the
        Amp Detect into 10s of milliamps of current.  Needs to be set based on the type of Amp Detect module installed."
	REFERENCE 	"NetBotz uVolts To 10 mAmps 4"
	::= { netBotz-prd-bot 60 }

netBotz-prd-bot-amps4-max-range OBJECT-TYPE
	SYNTAX		INTEGER
	ACCESS		read-write
	STATUS		mandatory
	DESCRIPTION	"The maximum RMS milliamps measureable by the fourth Amp Detect."
	REFERENCE 	"NetBotz Max milliAmps 4"
	::= { netBotz-prd-bot 61 }

netBotz-prd-bot-ext-temp1 OBJECT-TYPE
	SYNTAX		INTEGER
	ACCESS		read-only
	STATUS		mandatory
	DESCRIPTION	"The reading of the external temperature probe on port 1, in degrees F or degrees C (depends on netBotz-ismetric)."
	REFERENCE 	"NetBotz External Temperature Probe 1"
	::= { netBotz-prd-bot 62 }

netBotz-prd-bot-ext-temp2 OBJECT-TYPE
	SYNTAX		INTEGER
	ACCESS		read-only
	STATUS		mandatory
	DESCRIPTION	"The reading of the external temperature probe on port 2, in degrees F or degrees C (depends on netBotz-ismetric)."
	REFERENCE 	"NetBotz External Temperature Probe 2"
	::= { netBotz-prd-bot 63 }

netBotz-prd-bot-ext-temp3 OBJECT-TYPE
	SYNTAX		INTEGER
	ACCESS		read-only
	STATUS		mandatory
	DESCRIPTION	"The reading of the external temperature probe on port 3, in degrees F or degrees C (depends on netBotz-ismetric)."
	REFERENCE 	"NetBotz External Temperature Probe 3"
	::= { netBotz-prd-bot 64 }

netBotz-prd-bot-ext-temp4 OBJECT-TYPE
	SYNTAX		INTEGER
	ACCESS		read-only
	STATUS		mandatory
	DESCRIPTION	"The reading of the external temperature probe on port 4, in degrees F or degrees C (depends on netBotz-ismetric)."
	REFERENCE 	"NetBotz External Temperature Probe 4"
	::= { netBotz-prd-bot 65 }

netBotz-prd-bot-ext-temp1-enabled OBJECT-TYPE
	SYNTAX		INTEGER
	ACCESS		read-write
	STATUS		mandatory
	DESCRIPTION	"External temperature probe on port 1 alarm enabled(1) or disabled(0)."
	REFERENCE 	"NetBotz|Ext Temp[1] Probe Enabled"
	::= { netBotz-prd-bot 66 }

netBotz-prd-bot-ext-temp1-min OBJECT-TYPE
	SYNTAX		INTEGER
	ACCESS		read-write
	STATUS		mandatory
	DESCRIPTION	"The external temperature probe on port 1 probe minimum, in degrees F or degrees C (depends on netBotz-ismetric)."
	REFERENCE 	"NetBotz Ext Temp[1] Probe Minimum"
	::= { netBotz-prd-bot 67 }

netBotz-prd-bot-ext-temp1-max OBJECT-TYPE
	SYNTAX		INTEGER
	ACCESS		read-write
	STATUS		mandatory
	DESCRIPTION	"The external temperature probe on port 1 probe maximum, in degrees F or degrees C (depends on netBotz-ismetric)."
	REFERENCE 	"NetBotz Ext Temp[1] Probe Maximum"
	::= { netBotz-prd-bot 68 }

netBotz-prd-bot-ext-temp2-enabled OBJECT-TYPE
	SYNTAX		INTEGER
	ACCESS		read-write
	STATUS		mandatory
	DESCRIPTION	"External temperature probe on port 2 alarm enabled(1) or disabled(0)."
	REFERENCE 	"NetBotz|Ext Temp[2] Probe Enabled"
	::= { netBotz-prd-bot 69 }

netBotz-prd-bot-ext-temp2-min OBJECT-TYPE
	SYNTAX		INTEGER
	ACCESS		read-write
	STATUS		mandatory
	DESCRIPTION	"The external temperature probe on port 2 probe minimum, in degrees F or degrees C (depends on netBotz-ismetric)."
	REFERENCE 	"NetBotz Ext Temp[2] Probe Minimum"
	::= { netBotz-prd-bot 70 }

netBotz-prd-bot-ext-temp2-max OBJECT-TYPE
	SYNTAX		INTEGER
	ACCESS		read-write
	STATUS		mandatory
	DESCRIPTION	"The external temperature probe on port 2 probe maximum, in degrees F or degrees C (depends on netBotz-ismetric)."
	REFERENCE 	"NetBotz Ext Temp[2] Probe Maximum"
	::= { netBotz-prd-bot 71 }

netBotz-prd-bot-ext-temp3-enabled OBJECT-TYPE
	SYNTAX		INTEGER
	ACCESS		read-write
	STATUS		mandatory
	DESCRIPTION	"External temperature probe on port 3 alarm enabled(1) or disabled(0)."
	REFERENCE 	"NetBotz|Ext Temp[3] Probe Enabled"
	::= { netBotz-prd-bot 72 }

netBotz-prd-bot-ext-temp3-min OBJECT-TYPE
	SYNTAX		INTEGER
	ACCESS		read-write
	STATUS		mandatory
	DESCRIPTION	"The external temperature probe on port 3 probe minimum, in degrees F or degrees C (depends on netBotz-ismetric)."
	REFERENCE 	"NetBotz Ext Temp[3] Probe Minimum"
	::= { netBotz-prd-bot 73 }

netBotz-prd-bot-ext-temp3-max OBJECT-TYPE
	SYNTAX		INTEGER
	ACCESS		read-write
	STATUS		mandatory
	DESCRIPTION	"The external temperature probe on port 3 probe maximum, in degrees F or degrees C (depends on netBotz-ismetric)."
	REFERENCE 	"NetBotz Ext Temp[3] Probe Maximum"
	::= { netBotz-prd-bot 74 }

netBotz-prd-bot-ext-temp4-enabled OBJECT-TYPE
	SYNTAX		INTEGER
	ACCESS		read-write
	STATUS		mandatory
	DESCRIPTION	"External temperature probe on port 4 alarm enabled(1) or disabled(0)."
	REFERENCE 	"NetBotz|Ext Temp[4] Probe Enabled"
	::= { netBotz-prd-bot 75 }

netBotz-prd-bot-ext-temp4-min OBJECT-TYPE
	SYNTAX		INTEGER
	ACCESS		read-write
	STATUS		mandatory
	DESCRIPTION	"The external temperature probe on port 4 probe minimum, in degrees F or degrees C (depends on netBotz-ismetric)."
	REFERENCE 	"NetBotz Ext Temp[4] Probe Minimum"
	::= { netBotz-prd-bot 76 }

netBotz-prd-bot-ext-temp4-max OBJECT-TYPE
	SYNTAX		INTEGER
	ACCESS		read-write
	STATUS		mandatory
	DESCRIPTION	"The external temperature probe on port 4 probe maximum, in degrees F or degrees C (depends on netBotz-ismetric)."
	REFERENCE 	"NetBotz Ext Temp[4] Probe Maximum"
	::= { netBotz-prd-bot 77 }

netBotz-prd-bot-ext-temp1-uV-per-degreeC OBJECT-TYPE
	SYNTAX		INTEGER
	ACCESS		read-write
	STATUS		mandatory
	DESCRIPTION	"The scaling factor used for the external temperature probe on port 1 to convert microvolts measured from the
        temperature sensor into degrees C.  Needs to be set based on the type of temperature sensor module installed."
	REFERENCE 	"NetBotz uVolts To degrees C - 1"
	::= { netBotz-prd-bot 78 }

netBotz-prd-bot-ext-temp1-uV-at-0-degreeC OBJECT-TYPE
	SYNTAX		INTEGER
	ACCESS		read-write
	STATUS		mandatory
	DESCRIPTION	"The offset used for the external temperature probe on port 1 of microvolts measured from the
        temperature sensor at zero degrees C.  Needs to be set based on the type of temperature sensor module installed."
	REFERENCE 	"NetBotz uVolts at 0 degrees C - 1"
	::= { netBotz-prd-bot 79 }

netBotz-prd-bot-ext-temp1-max-range OBJECT-TYPE
	SYNTAX		INTEGER
	ACCESS		read-write
	STATUS		mandatory
	DESCRIPTION	"The maximum temperature measureable by the temperature sensor installed on port 1, in tenths of a degree C.
        Needs to be set based on the type of temperature sensor module installed."
	REFERENCE 	"NetBotz Max temperature supported - 1"
	::= { netBotz-prd-bot 81 }

netBotz-prd-bot-ext-temp1-min-range OBJECT-TYPE
	SYNTAX		INTEGER
	ACCESS		read-write
	STATUS		mandatory
	DESCRIPTION	"The minimum temperature measureable by the temperature sensor installed on port 1, in tenths of a degree C.
        Needs to be set based on the type of temperature sensor module installed."
	REFERENCE 	"NetBotz min temperature supported - 1"
	::= { netBotz-prd-bot 80 }

netBotz-prd-bot-ext-temp2-uV-per-degreeC OBJECT-TYPE
	SYNTAX		INTEGER
	ACCESS		read-write
	STATUS		mandatory
	DESCRIPTION	"The scaling factor used for the external temperature probe on port 2 to convert microvolts measured from the
        temperature sensor into degrees C.  Needs to be set based on the type of temperature sensor module installed."
	REFERENCE 	"NetBotz uVolts To degrees C - 2"
	::= { netBotz-prd-bot 82 }

netBotz-prd-bot-ext-temp2-uV-at-0-degreeC OBJECT-TYPE
	SYNTAX		INTEGER
	ACCESS		read-write
	STATUS		mandatory
	DESCRIPTION	"The offset used for the external temperature probe on port 2 of microvolts measured from the
        temperature sensor at zero degrees C.  Needs to be set based on the type of temperature sensor module installed."
	REFERENCE 	"NetBotz uVolts at 0 degrees C - 2"
	::= { netBotz-prd-bot 83 }

netBotz-prd-bot-ext-temp2-max-range OBJECT-TYPE
	SYNTAX		INTEGER
	ACCESS		read-write
	STATUS		mandatory
	DESCRIPTION	"The maximum temperature measureable by the temperature sensor installed on port 2, in tenths of a degree C.
        Needs to be set based on the type of temperature sensor module installed."
	REFERENCE 	"NetBotz Max temperature supported - 2"
	::= { netBotz-prd-bot 85 }

netBotz-prd-bot-ext-temp2-min-range OBJECT-TYPE
	SYNTAX		INTEGER
	ACCESS		read-write
	STATUS		mandatory
	DESCRIPTION	"The minimum temperature measureable by the temperature sensor installed on port 2, in tenths of a degree C.
        Needs to be set based on the type of temperature sensor module installed."
	REFERENCE 	"NetBotz min temperature supported - 2"
	::= { netBotz-prd-bot 84 }

netBotz-prd-bot-ext-temp3-uV-per-degreeC OBJECT-TYPE
	SYNTAX		INTEGER
	ACCESS		read-write
	STATUS		mandatory
	DESCRIPTION	"The scaling factor used for the external temperature probe on port 3 to convert microvolts measured from the
        temperature sensor into degrees C.  Needs to be set based on the type of temperature sensor module installed."
	REFERENCE 	"NetBotz uVolts To degrees C - 3"
	::= { netBotz-prd-bot 86 }

netBotz-prd-bot-ext-temp3-uV-at-0-degreeC OBJECT-TYPE
	SYNTAX		INTEGER
	ACCESS		read-write
	STATUS		mandatory
	DESCRIPTION	"The offset used for the external temperature probe on port 3 of microvolts measured from the
        temperature sensor at zero degrees C.  Needs to be set based on the type of temperature sensor module installed."
	REFERENCE 	"NetBotz uVolts at 0 degrees C - 3"
	::= { netBotz-prd-bot 87 }

netBotz-prd-bot-ext-temp3-max-range OBJECT-TYPE
	SYNTAX		INTEGER
	ACCESS		read-write
	STATUS		mandatory
	DESCRIPTION	"The maximum temperature measureable by the temperature sensor installed on port 3, in tenths of a degree C.
        Needs to be set based on the type of temperature sensor module installed."
	REFERENCE 	"NetBotz Max temperature supported - 3"
	::= { netBotz-prd-bot 89 }

netBotz-prd-bot-ext-temp3-min-range OBJECT-TYPE
	SYNTAX		INTEGER
	ACCESS		read-write
	STATUS		mandatory
	DESCRIPTION	"The minimum temperature measureable by the temperature sensor installed on port 3, in tenths of a degree C.
        Needs to be set based on the type of temperature sensor module installed."
	REFERENCE 	"NetBotz min temperature supported - 3"
	::= { netBotz-prd-bot 88 }

netBotz-prd-bot-ext-temp4-uV-per-degreeC OBJECT-TYPE
	SYNTAX		INTEGER
	ACCESS		read-write
	STATUS		mandatory
	DESCRIPTION	"The scaling factor used for the external temperature probe on port 4 to convert microvolts measured from the
        temperature sensor into degrees C.  Needs to be set based on the type of temperature sensor module installed."
	REFERENCE 	"NetBotz uVolts To degrees C - 4"
	::= { netBotz-prd-bot 90 }

netBotz-prd-bot-ext-temp4-uV-at-0-degreeC OBJECT-TYPE
	SYNTAX		INTEGER
	ACCESS		read-write
	STATUS		mandatory
	DESCRIPTION	"The offset used for the external temperature probe on port 4 of microvolts measured from the
        temperature sensor at zero degrees C.  Needs to be set based on the type of temperature sensor module installed."
	REFERENCE 	"NetBotz uVolts at 0 degrees C - 4"
	::= { netBotz-prd-bot 91 }

netBotz-prd-bot-ext-temp4-max-range OBJECT-TYPE
	SYNTAX		INTEGER
	ACCESS		read-write
	STATUS		mandatory
	DESCRIPTION	"The maximum temperature measureable by the temperature sensor installed on port 4, in tenths of a degree C.
        Needs to be set based on the type of temperature sensor module installed."
	REFERENCE 	"NetBotz Max temperature supported - 4"
	::= { netBotz-prd-bot 93 }

netBotz-prd-bot-ext-temp4-min-range OBJECT-TYPE
	SYNTAX		INTEGER
	ACCESS		read-write
	STATUS		mandatory
	DESCRIPTION	"The minimum temperature measureable by the temperature sensor installed on port 4, in tenths of a degree C.
        Needs to be set based on the type of temperature sensor module installed."
	REFERENCE 	"NetBotz min temperature supported - 4"
	::= { netBotz-prd-bot 92 }

netBotz-prd-bot-ext-port1-module-id OBJECT-TYPE
	SYNTAX		DisplayString
	ACCESS		read-write
	STATUS		mandatory
	DESCRIPTION	"The module ID of the sensor module installed on port 1.  Blank string indicates that no module is installed."
	REFERENCE 	"NetBotz module ID port 1"
	::= { netBotz-prd-bot 94 }

netBotz-prd-bot-ext-port1-module-type OBJECT-TYPE
	SYNTAX		DisplayString
	ACCESS		read-write
	STATUS		mandatory
	DESCRIPTION	"The type of sensor module installed on port 1.  NONE=no module, AMP=AmpDetect module, TEMP=temperature sensor, DRY=dry contact sensor."
	REFERENCE 	"NetBotz module type port 1"
	::= { netBotz-prd-bot 95 }

netBotz-prd-bot-ext-port2-module-id OBJECT-TYPE
	SYNTAX		DisplayString
	ACCESS		read-write
	STATUS		mandatory
	DESCRIPTION	"The module ID of the sensor module installed on port 2.  Blank string indicates that no module is installed."
	REFERENCE 	"NetBotz module ID port 2"
	::= { netBotz-prd-bot 96 }

netBotz-prd-bot-ext-port2-module-type OBJECT-TYPE
	SYNTAX		DisplayString
	ACCESS		read-write
	STATUS		mandatory
	DESCRIPTION	"The type of sensor module installed on port 2.  NONE=no module, AMP=AmpDetect module, TEMP=temperature sensor, DRY=dry contact sensor."
	REFERENCE 	"NetBotz module type port 2"
	::= { netBotz-prd-bot 97 }

netBotz-prd-bot-ext-port3-module-id OBJECT-TYPE
	SYNTAX		DisplayString
	ACCESS		read-write
	STATUS		mandatory
	DESCRIPTION	"The module ID of the sensor module installed on port 3.  Blank string indicates that no module is installed."
	REFERENCE 	"NetBotz module ID port 3"
	::= { netBotz-prd-bot 98 }

netBotz-prd-bot-ext-port3-module-type OBJECT-TYPE
	SYNTAX		DisplayString
	ACCESS		read-write
	STATUS		mandatory
	DESCRIPTION	"The type of sensor module installed on port 3.  NONE=no module, AMP=AmpDetect module, TEMP=temperature sensor, DRY=dry contact sensor."
	REFERENCE 	"NetBotz module type port 3"
	::= { netBotz-prd-bot 99 }

netBotz-prd-bot-ext-port4-module-id OBJECT-TYPE
	SYNTAX		DisplayString
	ACCESS		read-write
	STATUS		mandatory
	DESCRIPTION	"The module ID of the sensor module installed on port 4.  Blank string indicates that no module is installed."
	REFERENCE 	"NetBotz module ID port 4"
	::= { netBotz-prd-bot 100 }

netBotz-prd-bot-ext-port4-module-type OBJECT-TYPE
	SYNTAX		DisplayString
	ACCESS		read-write
	STATUS		mandatory
	DESCRIPTION	"The type of sensor module installed on port 4.  NONE=no module, AMP=AmpDetect module, TEMP=temperature sensor, DRY=dry contact sensor."
	REFERENCE 	"NetBotz module type port 4"
	::= { netBotz-prd-bot 101 }

netBotz-prd-bot-amp1-total-amp-seconds OBJECT-TYPE
	SYNTAX		INTEGER
	ACCESS		read-only
	STATUS		mandatory
	DESCRIPTION	"The accumulated total of amp-seconds on the AmpDetect on port 1."
	REFERENCE 	"NetBotz Total Amp-Seconds - 1"
	::= { netBotz-prd-bot 102 }

netBotz-prd-bot-amp1-total-amp-seconds-since-time OBJECT-TYPE
	SYNTAX		INTEGER
	ACCESS		read-write
	STATUS		mandatory
	DESCRIPTION	"The UTC time (seconds since 1/1/1970) of the beginning of the accumulated total of amp-seconds on the AmpDetect on port 1.
        Writing a value to this attribute resets the accumulated total amp-seconds and sets this time to the current time."
	REFERENCE 	"NetBotz Total Amp-Seconds reset time - 1"
	::= { netBotz-prd-bot 103 }

netBotz-prd-bot-amp2-total-amp-seconds OBJECT-TYPE
	SYNTAX		INTEGER
	ACCESS		read-only
	STATUS		mandatory
	DESCRIPTION	"The accumulated total of amp-seconds on the AmpDetect on port 2."
	REFERENCE 	"NetBotz Total Amp-Seconds - 2"
	::= { netBotz-prd-bot 104 }

netBotz-prd-bot-amp2-total-amp-seconds-since-time OBJECT-TYPE
	SYNTAX		INTEGER
	ACCESS		read-write
	STATUS		mandatory
	DESCRIPTION	"The UTC time (seconds since 1/1/1970) of the beginning of the accumulated total of amp-seconds on the AmpDetect on port 2.
        Writing a value to this attribute resets the accumulated total amp-seconds and sets this time to the current time."
	REFERENCE 	"NetBotz Total Amp-Seconds reset time - 2"
	::= { netBotz-prd-bot 105 }

netBotz-prd-bot-amp3-total-amp-seconds OBJECT-TYPE
	SYNTAX		INTEGER
	ACCESS		read-only
	STATUS		mandatory
	DESCRIPTION	"The accumulated total of amp-seconds on the AmpDetect on port 3."
	REFERENCE 	"NetBotz Total Amp-Seconds - 3"
	::= { netBotz-prd-bot 106 }

netBotz-prd-bot-amp3-total-amp-seconds-since-time OBJECT-TYPE
	SYNTAX		INTEGER
	ACCESS		read-write
	STATUS		mandatory
	DESCRIPTION	"The UTC time (seconds since 1/1/1970) of the beginning of the accumulated total of amp-seconds on the AmpDetect on port 3.
        Writing a value to this attribute resets the accumulated total amp-seconds and sets this time to the current time."
	REFERENCE 	"NetBotz Total Amp-Seconds reset time - 3"
	::= { netBotz-prd-bot 107 }

netBotz-prd-bot-amp4-total-amp-seconds OBJECT-TYPE
	SYNTAX		INTEGER
	ACCESS		read-only
	STATUS		mandatory
	DESCRIPTION	"The accumulated total of amp-seconds on the AmpDetect on port 4."
	REFERENCE 	"NetBotz Total Amp-Seconds - 4"
	::= { netBotz-prd-bot 108 }

netBotz-prd-bot-amp4-total-amp-seconds-since-time OBJECT-TYPE
	SYNTAX		INTEGER
	ACCESS		read-write
	STATUS		mandatory
	DESCRIPTION	"The UTC time (seconds since 1/1/1970) of the beginning of the accumulated total of amp-seconds on the AmpDetect on port 4.
        Writing a value to this attribute resets the accumulated total amp-seconds and sets this time to the current time."
	REFERENCE 	"NetBotz Total Amp-Seconds reset time - 4"
	::= { netBotz-prd-bot 109 }

netBotz-prd-bot-amptotal-total-amp-seconds OBJECT-TYPE
	SYNTAX		INTEGER
	ACCESS		read-only
	STATUS		mandatory
	DESCRIPTION	"The accumulated total of amp-seconds on the total of all AmpDetects."
	REFERENCE 	"NetBotz Total Amp-Seconds - total"
	::= { netBotz-prd-bot 110 }

netBotz-prd-bot-amptotal-total-amp-seconds-since-time OBJECT-TYPE
	SYNTAX		INTEGER
	ACCESS		read-write
	STATUS		mandatory
	DESCRIPTION	"The UTC time (seconds since 1/1/1970) of the beginning of the accumulated total of amp-seconds for all AmpDetects.
        Writing a value to this attribute resets the accumulated total amp-seconds and sets this time to the current time."
	REFERENCE 	"NetBotz Total Amp-Seconds reset time - total"
	::= { netBotz-prd-bot 111 }

netBotz-prd-bot-ext-dry1 OBJECT-TYPE
	SYNTAX		INTEGER
	ACCESS		read-only
	STATUS		mandatory
	DESCRIPTION	"The current value of the external dry contact sensor on Ext1: 0=Open, 1=Closed, -1=N/A"
	REFERENCE 	"NetBotz Ext Dry 1"
	::= { netBotz-prd-bot 112 }

netBotz-prd-bot-ext-dry2 OBJECT-TYPE
	SYNTAX		INTEGER
	ACCESS		read-only
	STATUS		mandatory
	DESCRIPTION	"The current value of the external dry contact sensor on Ext2: 0=Open, 1=Closed, -1=N/A"
	REFERENCE 	"NetBotz Ext Dry 2"
	::= { netBotz-prd-bot 113 }

netBotz-prd-bot-ext-dry3 OBJECT-TYPE
	SYNTAX		INTEGER
	ACCESS		read-only
	STATUS		mandatory
	DESCRIPTION	"The current value of the external dry contact sensor on Ext3: 0=Open, 1=Closed, -1=N/A"
	REFERENCE 	"NetBotz Ext Dry 3"
	::= { netBotz-prd-bot 114 }

netBotz-prd-bot-ext-dry4 OBJECT-TYPE
	SYNTAX		INTEGER
	ACCESS		read-only
	STATUS		mandatory
	DESCRIPTION	"The current value of the external dry contact sensor on Ext4: 0=Open, 1=Closed, -1=N/A"
	REFERENCE 	"NetBotz Ext Dry 4"
	::= { netBotz-prd-bot 115 }

netBotz-prd-bot-ext-dry1-alarm-value OBJECT-TYPE
	SYNTAX		INTEGER
	ACCESS		read-write
	STATUS		mandatory
	DESCRIPTION	"The value to generate alarms on for the external dry contact sensor on Ext1: 0=Open, 1=Closed"
	REFERENCE 	"NetBotz Ext Dry 1 Alarm Value"
	::= { netBotz-prd-bot 116 }

netBotz-prd-bot-ext-dry1-enabled OBJECT-TYPE
	SYNTAX		INTEGER
	ACCESS		read-write
	STATUS		mandatory
	DESCRIPTION	"External dry contact sensor on Ext1 alarm enabled(1) or disabled(0)."
	REFERENCE 	"NetBotz Ext Dry 1 Alarm Enabled"
	::= { netBotz-prd-bot 117 }

netBotz-prd-bot-ext-dry2-alarm-value OBJECT-TYPE
	SYNTAX		INTEGER
	ACCESS		read-write
	STATUS		mandatory
	DESCRIPTION	"The value to generate alarms on for the external dry contact sensor on Ext2: 0=Open, 1=Closed"
	REFERENCE 	"NetBotz Ext Dry 2 Alarm Value"
	::= { netBotz-prd-bot 118 }

netBotz-prd-bot-ext-dry2-enabled OBJECT-TYPE
	SYNTAX		INTEGER
	ACCESS		read-write
	STATUS		mandatory
	DESCRIPTION	"External dry contact sensor on Ext2 alarm enabled(1) or disabled(0)."
	REFERENCE 	"NetBotz Ext Dry 2 Alarm Enabled"
	::= { netBotz-prd-bot 119 }

netBotz-prd-bot-ext-dry3-alarm-value OBJECT-TYPE
	SYNTAX		INTEGER
	ACCESS		read-write
	STATUS		mandatory
	DESCRIPTION	"The value to generate alarms on for the external dry contact sensor on Ext3: 0=Open, 1=Closed"
	REFERENCE 	"NetBotz Ext Dry 3 Alarm Value"
	::= { netBotz-prd-bot 120 }

netBotz-prd-bot-ext-dry3-enabled OBJECT-TYPE
	SYNTAX		INTEGER
	ACCESS		read-write
	STATUS		mandatory
	DESCRIPTION	"External dry contact sensor on Ext3 alarm enabled(1) or disabled(0)."
	REFERENCE 	"NetBotz Ext Dry 3 Alarm Enabled"
	::= { netBotz-prd-bot 121 }

netBotz-prd-bot-ext-dry4-alarm-value OBJECT-TYPE
	SYNTAX		INTEGER
	ACCESS		read-write
	STATUS		mandatory
	DESCRIPTION	"The value to generate alarms on for the external dry contact sensor on Ext4: 0=Open, 1=Closed"
	REFERENCE 	"NetBotz Ext Dry 4 Alarm Value"
	::= { netBotz-prd-bot 122 }

netBotz-prd-bot-ext-dry4-enabled OBJECT-TYPE
	SYNTAX		INTEGER
	ACCESS		read-write
	STATUS		mandatory
	DESCRIPTION	"External dry contact sensor on Ext4 alarm enabled(1) or disabled(0)."
	REFERENCE 	"NetBotz Ext Dry 4 Alarm Enabled"
	::= { netBotz-prd-bot 123 }

netBotz-prd-bot-ext-dry1-label OBJECT-TYPE
	SYNTAX		DisplayString
	ACCESS		read-write
	STATUS		mandatory
	DESCRIPTION	"The sensor name/label for the dry contact sensor on Ext1"
	REFERENCE 	"NetBotz Ext Dry 1 Label"
	::= { netBotz-prd-bot 124 }

netBotz-prd-bot-ext-dry1-open-label OBJECT-TYPE
	SYNTAX		DisplayString
	ACCESS		read-write
	STATUS		mandatory
	DESCRIPTION	"The sensor name/label for the open(0) state for the dry contact sensor on Ext1"
	REFERENCE 	"NetBotz Ext Dry 1 Open Label"
	::= { netBotz-prd-bot 125 }

netBotz-prd-bot-ext-dry1-closed-label OBJECT-TYPE
	SYNTAX		DisplayString
	ACCESS		read-write
	STATUS		mandatory
	DESCRIPTION	"The sensor name/label for the closed(0) state for the dry contact sensor on Ext1"
	REFERENCE 	"NetBotz Ext Dry 1 Closed Label"
	::= { netBotz-prd-bot 126 }

netBotz-prd-bot-ext-dry1-open-to-close-millis OBJECT-TYPE
	SYNTAX		INTEGER
	ACCESS		read-write
	STATUS		mandatory
	DESCRIPTION	"The minimum number of milliseconds that the dry contact sensor on Ext1
			must read closed before the state is changed from open to closed."
	REFERENCE 	"NetBotz Ext Dry 1 Open-to-Closed Millis"
	::= { netBotz-prd-bot 127 }

netBotz-prd-bot-ext-dry1-close-to-open-millis OBJECT-TYPE
	SYNTAX		INTEGER
	ACCESS		read-write
	STATUS		mandatory
	DESCRIPTION	"The minimum number of milliseconds that the dry contact sensor on Ext1
			must read openbefore the state is changed from closed to open."
	REFERENCE 	"NetBotz Ext Dry 1 Closed-to-Open Millis"
	::= { netBotz-prd-bot 128 }

netBotz-prd-bot-ext-dry1-response OBJECT-TYPE
	SYNTAX		DisplayString
	ACCESS		read-write
	STATUS		mandatory
	DESCRIPTION	"The type of alert response for the dry contact sensor on Ext1: ALERT=e-mail with no
		pictures, CAMERA=e-mail with pictures from camera."
	REFERENCE 	"NetBotz Ext Dry 1 Response"
	::= { netBotz-prd-bot 129 }

netBotz-prd-bot-ext-dry2-label OBJECT-TYPE
	SYNTAX		DisplayString
	ACCESS		read-write
	STATUS		mandatory
	DESCRIPTION	"The sensor name/label for the dry contact sensor on Ext2"
	REFERENCE 	"NetBotz Ext Dry 2 Label"
	::= { netBotz-prd-bot 130 }

netBotz-prd-bot-ext-dry2-open-label OBJECT-TYPE
	SYNTAX		DisplayString
	ACCESS		read-write
	STATUS		mandatory
	DESCRIPTION	"The sensor name/label for the open(0) state for the dry contact sensor on Ext2"
	REFERENCE 	"NetBotz Ext Dry 2 Open Label"
	::= { netBotz-prd-bot 131 }

netBotz-prd-bot-ext-dry2-closed-label OBJECT-TYPE
	SYNTAX		DisplayString
	ACCESS		read-write
	STATUS		mandatory
	DESCRIPTION	"The sensor name/label for the closed(0) state for the dry contact sensor on Ext2"
	REFERENCE 	"NetBotz Ext Dry 2 Closed Label"
	::= { netBotz-prd-bot 132 }

netBotz-prd-bot-ext-dry2-open-to-close-millis OBJECT-TYPE
	SYNTAX		INTEGER
	ACCESS		read-write
	STATUS		mandatory
	DESCRIPTION	"The minimum number of milliseconds that the dry contact sensor on Ext2
			must read closed before the state is changed from open to closed."
	REFERENCE 	"NetBotz Ext Dry 2 Open-to-Closed Millis"
	::= { netBotz-prd-bot 133 }

netBotz-prd-bot-ext-dry2-close-to-open-millis OBJECT-TYPE
	SYNTAX		INTEGER
	ACCESS		read-write
	STATUS		mandatory
	DESCRIPTION	"The minimum number of milliseconds that the dry contact sensor on Ext2
			must read openbefore the state is changed from closed to open."
	REFERENCE 	"NetBotz Ext Dry 2 Closed-to-Open Millis"
	::= { netBotz-prd-bot 134 }

netBotz-prd-bot-ext-dry2-response OBJECT-TYPE
	SYNTAX		DisplayString
	ACCESS		read-write
	STATUS		mandatory
	DESCRIPTION	"The type of alert response for the dry contact sensor on Ext2: ALERT=e-mail with no
		pictures, CAMERA=e-mail with pictures from camera."
	REFERENCE 	"NetBotz Ext Dry 2 Response"
	::= { netBotz-prd-bot 135 }

netBotz-prd-bot-ext-dry3-label OBJECT-TYPE
	SYNTAX		DisplayString
	ACCESS		read-write
	STATUS		mandatory
	DESCRIPTION	"The sensor name/label for the dry contact sensor on Ext3"
	REFERENCE 	"NetBotz Ext Dry 3 Label"
	::= { netBotz-prd-bot 136 }

netBotz-prd-bot-ext-dry3-open-label OBJECT-TYPE
	SYNTAX		DisplayString
	ACCESS		read-write
	STATUS		mandatory
	DESCRIPTION	"The sensor name/label for the open(0) state for the dry contact sensor on Ext3"
	REFERENCE 	"NetBotz Ext Dry 3 Open Label"
	::= { netBotz-prd-bot 137 }

netBotz-prd-bot-ext-dry3-closed-label OBJECT-TYPE
	SYNTAX		DisplayString
	ACCESS		read-write
	STATUS		mandatory
	DESCRIPTION	"The sensor name/label for the closed(0) state for the dry contact sensor on Ext3"
	REFERENCE 	"NetBotz Ext Dry 3 Closed Label"
	::= { netBotz-prd-bot 138 }

netBotz-prd-bot-ext-dry3-open-to-close-millis OBJECT-TYPE
	SYNTAX		INTEGER
	ACCESS		read-write
	STATUS		mandatory
	DESCRIPTION	"The minimum number of milliseconds that the dry contact sensor on Ext3
			must read closed before the state is changed from open to closed."
	REFERENCE 	"NetBotz Ext Dry 3 Open-to-Closed Millis"
	::= { netBotz-prd-bot 139 }

netBotz-prd-bot-ext-dry3-close-to-open-millis OBJECT-TYPE
	SYNTAX		INTEGER
	ACCESS		read-write
	STATUS		mandatory
	DESCRIPTION	"The minimum number of milliseconds that the dry contact sensor on Ext3
			must read openbefore the state is changed from closed to open."
	REFERENCE 	"NetBotz Ext Dry 3 Closed-to-Open Millis"
	::= { netBotz-prd-bot 140 }

netBotz-prd-bot-ext-dry3-response OBJECT-TYPE
	SYNTAX		DisplayString
	ACCESS		read-write
	STATUS		mandatory
	DESCRIPTION	"The type of alert response for the dry contact sensor on Ext3: ALERT=e-mail with no
		pictures, CAMERA=e-mail with pictures from camera."
	REFERENCE 	"NetBotz Ext Dry 3 Response"
	::= { netBotz-prd-bot 141 }

netBotz-prd-bot-ext-dry4-label OBJECT-TYPE
	SYNTAX		DisplayString
	ACCESS		read-write
	STATUS		mandatory
	DESCRIPTION	"The sensor name/label for the dry contact sensor on Ext4"
	REFERENCE 	"NetBotz Ext Dry 4 Label"
	::= { netBotz-prd-bot 142 }

netBotz-prd-bot-ext-dry4-open-label OBJECT-TYPE
	SYNTAX		DisplayString
	ACCESS		read-write
	STATUS		mandatory
	DESCRIPTION	"The sensor name/label for the open(0) state for the dry contact sensor on Ext4"
	REFERENCE 	"NetBotz Ext Dry 4 Open Label"
	::= { netBotz-prd-bot 143 }

netBotz-prd-bot-ext-dry4-closed-label OBJECT-TYPE
	SYNTAX		DisplayString
	ACCESS		read-write
	STATUS		mandatory
	DESCRIPTION	"The sensor name/label for the closed(0) state for the dry contact sensor on Ext4"
	REFERENCE 	"NetBotz Ext Dry 4 Closed Label"
	::= { netBotz-prd-bot 144 }

netBotz-prd-bot-ext-dry4-open-to-close-millis OBJECT-TYPE
	SYNTAX		INTEGER
	ACCESS		read-write
	STATUS		mandatory
	DESCRIPTION	"The minimum number of milliseconds that the dry contact sensor on Ext4
			must read closed before the state is changed from open to closed."
	REFERENCE 	"NetBotz Ext Dry 4 Open-to-Closed Millis"
	::= { netBotz-prd-bot 145 }

netBotz-prd-bot-ext-dry4-close-to-open-millis OBJECT-TYPE
	SYNTAX		INTEGER
	ACCESS		read-write
	STATUS		mandatory
	DESCRIPTION	"The minimum number of milliseconds that the dry contact sensor on Ext4
			must read openbefore the state is changed from closed to open."
	REFERENCE 	"NetBotz Ext Dry 4 Closed-to-Open Millis"
	::= { netBotz-prd-bot 146 }

netBotz-prd-bot-ext-dry4-response OBJECT-TYPE
	SYNTAX		DisplayString
	ACCESS		read-write
	STATUS		mandatory
	DESCRIPTION	"The type of alert response for the dry contact sensor on Ext4: ALERT=e-mail with no
		pictures, CAMERA=e-mail with pictures from camera."
	REFERENCE 	"NetBotz Ext Dry 4 Response"
	::= { netBotz-prd-bot 147 }

netBotz-prd-bot-traps OBJECT IDENTIFIER
                     ::= { netBotz-products 100 }

netBotz-prd-bot-temperature-traps OBJECT IDENTIFIER
                     ::= { netBotz-prd-bot-traps 1 }

netBotz-prd-bot-humidity-traps OBJECT IDENTIFIER
                     ::= { netBotz-prd-bot-traps 2 }

netBotz-prd-bot-airflow-traps OBJECT IDENTIFIER
                     ::= { netBotz-prd-bot-traps 3 }

netBotz-prd-bot-audio-traps OBJECT IDENTIFIER
                     ::= { netBotz-prd-bot-traps 4 }

netBotz-prd-bot-door-traps OBJECT IDENTIFIER
                     ::= { netBotz-prd-bot-traps 5 }

netBotz-prd-bot-amp1-traps OBJECT IDENTIFIER
                     ::= { netBotz-prd-bot-traps 6 }

netBotz-prd-bot-amp2-traps OBJECT IDENTIFIER
                     ::= { netBotz-prd-bot-traps 7 }

netBotz-prd-bot-amp3-traps OBJECT IDENTIFIER
                     ::= { netBotz-prd-bot-traps 8 }

netBotz-prd-bot-amp4-traps OBJECT IDENTIFIER
                     ::= { netBotz-prd-bot-traps 9 }

netBotz-prd-bot-amp-total-traps OBJECT IDENTIFIER
                     ::= { netBotz-prd-bot-traps 10 }

netBotz-prd-bot-ext-temp1-traps OBJECT IDENTIFIER
                     ::= { netBotz-prd-bot-traps 11 }

netBotz-prd-bot-ext-temp2-traps OBJECT IDENTIFIER
                     ::= { netBotz-prd-bot-traps 12 }

netBotz-prd-bot-ext-temp3-traps OBJECT IDENTIFIER
                     ::= { netBotz-prd-bot-traps 13 }

netBotz-prd-bot-ext-temp4-traps OBJECT IDENTIFIER
                     ::= { netBotz-prd-bot-traps 14 }

netBotz-prd-bot-ext-dry1-traps OBJECT IDENTIFIER
                     ::= { netBotz-prd-bot-traps 15 }

netBotz-prd-bot-ext-dry2-traps OBJECT IDENTIFIER
                     ::= { netBotz-prd-bot-traps 16 }

netBotz-prd-bot-ext-dry3-traps OBJECT IDENTIFIER
                     ::= { netBotz-prd-bot-traps 17 }

netBotz-prd-bot-ext-dry4-traps OBJECT IDENTIFIER
                     ::= { netBotz-prd-bot-traps 18 }

netBotz-prd-bot-temperature-low-trap TRAP-TYPE
	ENTERPRISE netBotz-prd-bot-temperature-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz Temperature Low Trap. This trap indicates that the lower
	limit for temperature has been exceeded."
	REFERENCE 	"NetBotz Temperature Low Trap"
	::= 1

netBotz-prd-bot-temperature-high-trap TRAP-TYPE
	ENTERPRISE netBotz-prd-bot-temperature-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz Temperature High Trap. This trap indicates that the upper
	limit for temperature has been exceeded."
	REFERENCE 	"NetBotz Temperature High Trap"
	::= 2

netBotz-prd-bot-temperature-trap-clear TRAP-TYPE
	ENTERPRISE netBotz-prd-bot-temperature-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz Temperature Cleared Trap. The trap has been cleared because
	the temperature value has returned to acceptable limits."
	REFERENCE 	"NetBotz Temperature Cleared Trap"
	::= 3

netBotz-prd-bot-humidity-low-trap TRAP-TYPE
	ENTERPRISE netBotz-prd-bot-humidity-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz Humidity Low Trap. This trap indicates that the lower
	limit for humidity has been exceeded."
	REFERENCE 	"NetBotz Humidity Low Trap"
	::= 1

netBotz-prd-bot-humidity-high-trap TRAP-TYPE
	ENTERPRISE netBotz-prd-bot-humidity-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz Humidity High Trap. This trap indicates that the upper
	limit for humidity has been exceeded."
	REFERENCE 	"NetBotz Humidity High Trap"
	::= 2

netBotz-prd-bot-humidity-trap-clear TRAP-TYPE
	ENTERPRISE netBotz-prd-bot-humidity-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz Humidity Cleared Trap. The trap has been cleared because
	the humidity value has returned to acceptable limits."
	REFERENCE 	"NetBotz Humidity Cleared Trap"
	::= 3

netBotz-prd-bot-airflow-low-trap TRAP-TYPE
	ENTERPRISE netBotz-prd-bot-airflow-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz Airflow Low Trap. This trap indicates that the lower
	limit for airflow has been exceeded."
	REFERENCE 	"NetBotz Airflow Low Trap"
	::= 1

netBotz-prd-bot-airflow-trap-clear TRAP-TYPE
	ENTERPRISE netBotz-prd-bot-airflow-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz Airflow Cleared Trap. The trap has been cleared because
	the airflow value has returned to acceptable limits."
	REFERENCE 	"NetBotz Airflow Cleared Trap"
	::= 3

netBotz-prd-bot-audio-high-trap TRAP-TYPE
	ENTERPRISE netBotz-prd-bot-audio-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz Audio High Trap. This trap indicates that the upper
	limit for audio has been exceeded."
	REFERENCE 	"NetBotz Audio High Trap"
	::= 2

netBotz-prd-bot-audio-trap-clear TRAP-TYPE
	ENTERPRISE netBotz-prd-bot-audio-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz Audio Cleared Trap. The trap has been cleared because
	the audio value has returned to acceptable limits."
	REFERENCE 	"NetBotz Audio Cleared Trap"
	::= 3

netBotz-prd-bot-door-trap-tripped TRAP-TYPE
	ENTERPRISE netBotz-prd-bot-door-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz Door Sensor Tripped Trap. This trap indicates that the door sensor
	has been triggered (i.e. opened, if the thresdhold has been set to trip on open, closed if otherwise)."
	REFERENCE 	"NetBotz Door Tripped Trap"
	::= 2

netBotz-prd-bot-door-trap-clear TRAP-TYPE
	ENTERPRISE netBotz-prd-bot-door-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz Door Cleared Trap. The trap has been cleared because
	the door sensor has returned to normal (i.e. been closed, if the threshold has been set to trip on open)."
	REFERENCE 	"NetBotz Door Cleared Trap"
	::= 3

netBotz-prd-bot-amp1-low-trap TRAP-TYPE
	ENTERPRISE netBotz-prd-bot-amp1-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz Amp1 Low Trap. This trap indicates that the lower
	limit for the first amp detect has been exceeded."
	REFERENCE 	"NetBotz Amp1 Low Trap"
	::= 1

netBotz-prd-bot-amp1-high-trap TRAP-TYPE
	ENTERPRISE netBotz-prd-bot-amp1-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz Amp1 High Trap. This trap indicates that the upper
	limit for the first amp detect has been exceeded."
	REFERENCE 	"NetBotz Amp1 High Trap"
	::= 2

netBotz-prd-bot-amp1-trap-clear TRAP-TYPE
	ENTERPRISE netBotz-prd-bot-amp1-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz Amp1 Cleared Trap. The trap has been cleared because
	the first amp detect value has returned to acceptable limits."
	REFERENCE 	"NetBotz Amp1 Cleared Trap"
	::= 3

netBotz-prd-bot-amp1-sensor-unplugged TRAP-TYPE
	ENTERPRISE netBotz-prd-bot-amp1-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz Amp 1 Sensor Unplugged Trap. The sensor for the first AmpDetect is unplugged or malfunctioning."
	REFERENCE 	"NetBotz Amp 1 Unplugged Trap"
	::= 6

netBotz-prd-bot-amp1-sensor-replugged TRAP-TYPE
	ENTERPRISE netBotz-prd-bot-amp1-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz Amp 1 Sensor Replugged Trap. The sensor for the first AmpDetect was unplugged, but has been reconnected."
	REFERENCE 	"NetBotz Amp 1 Replugged Trap"
	::= 7

netBotz-prd-bot-amp2-low-trap TRAP-TYPE
	ENTERPRISE netBotz-prd-bot-amp2-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz Amp2 Low Trap. This trap indicates that the lower
	limit for the second amp detect has been exceeded."
	REFERENCE 	"NetBotz Amp2 Low Trap"
	::= 1

netBotz-prd-bot-amp2-high-trap TRAP-TYPE
	ENTERPRISE netBotz-prd-bot-amp2-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz Amp2 High Trap. This trap indicates that the upper
	limit for the second amp detect has been exceeded."
	REFERENCE 	"NetBotz Amp2 High Trap"
	::= 2

netBotz-prd-bot-amp2-trap-clear TRAP-TYPE
	ENTERPRISE netBotz-prd-bot-amp2-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz Amp2 Cleared Trap. The trap has been cleared because
	the second amp detect value has returned to acceptable limits."
	REFERENCE 	"NetBotz Amp2 Cleared Trap"
	::= 3

netBotz-prd-bot-amp2-sensor-unplugged TRAP-TYPE
	ENTERPRISE netBotz-prd-bot-amp2-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz Amp 2 Sensor Unplugged Trap. The sensor for the second AmpDetect is unplugged or malfunctioning."
	REFERENCE 	"NetBotz Amp 2 Unplugged Trap"
	::= 6

netBotz-prd-bot-amp2-sensor-replugged TRAP-TYPE
	ENTERPRISE netBotz-prd-bot-amp2-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz Amp 2 Sensor Replugged Trap. The sensor for the second AmpDetect was unplugged, but has been reconnected."
	REFERENCE 	"NetBotz Amp 2 Replugged Trap"
	::= 7

netBotz-prd-bot-amp3-low-trap TRAP-TYPE
	ENTERPRISE netBotz-prd-bot-amp3-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz Amp3 Low Trap. This trap indicates that the lower
	limit for the third amp detect has been exceeded."
	REFERENCE 	"NetBotz Amp3 Low Trap"
	::= 1

netBotz-prd-bot-amp3-high-trap TRAP-TYPE
	ENTERPRISE netBotz-prd-bot-amp3-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz Amp3 High Trap. This trap indicates that the upper
	limit for the third amp detect has been exceeded."
	REFERENCE 	"NetBotz Amp3 High Trap"
	::= 2

netBotz-prd-bot-amp3-trap-clear TRAP-TYPE
	ENTERPRISE netBotz-prd-bot-amp3-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz Amp3 Cleared Trap. The trap has been cleared because
	the third amp detect value has returned to acceptable limits."
	REFERENCE 	"NetBotz Amp3 Cleared Trap"
	::= 3

netBotz-prd-bot-amp3-sensor-unplugged TRAP-TYPE
	ENTERPRISE netBotz-prd-bot-amp3-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz Amp 3 Sensor Unplugged Trap. The sensor for the third AmpDetect is unplugged or malfunctioning."
	REFERENCE 	"NetBotz Amp 3 Unplugged Trap"
	::= 6

netBotz-prd-bot-amp3-sensor-replugged TRAP-TYPE
	ENTERPRISE netBotz-prd-bot-amp3-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz Amp 3 Sensor Replugged Trap. The sensor for the third AmpDetect was unplugged, but has been reconnected."
	REFERENCE 	"NetBotz Amp 3 Replugged Trap"
	::= 7

netBotz-prd-bot-amp4-low-trap TRAP-TYPE
	ENTERPRISE netBotz-prd-bot-amp4-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz Amp4 Low Trap. This trap indicates that the lower
	limit for the fourth amp detect has been exceeded."
	REFERENCE 	"NetBotz Amp4 Low Trap"
	::= 1

netBotz-prd-bot-amp4-high-trap TRAP-TYPE
	ENTERPRISE netBotz-prd-bot-amp4-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz Amp4 High Trap. This trap indicates that the upper
	limit for the fourth amp detect has been exceeded."
	REFERENCE 	"NetBotz Amp4 High Trap"
	::= 2

netBotz-prd-bot-amp4-trap-clear TRAP-TYPE
	ENTERPRISE netBotz-prd-bot-amp4-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz Amp4 Cleared Trap. The trap has been cleared because
	the fourth amp detect value has returned to acceptable limits."
	REFERENCE 	"NetBotz Amp4 Cleared Trap"
	::= 3

netBotz-prd-bot-amp4-sensor-unplugged TRAP-TYPE
	ENTERPRISE netBotz-prd-bot-amp4-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz Amp 4 Sensor Unplugged Trap. The sensor for the fourth AmpDetect is unplugged or malfunctioning."
	REFERENCE 	"NetBotz Amp 4 Unplugged Trap"
	::= 6

netBotz-prd-bot-amp4-sensor-replugged TRAP-TYPE
	ENTERPRISE netBotz-prd-bot-amp4-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz Amp 4 Sensor Replugged Trap. The sensor for the fourth AmpDetect was unplugged, but has been reconnected."
	REFERENCE 	"NetBotz Amp 4 Replugged Trap"
	::= 7

netBotz-prd-bot-amp-total-low-trap TRAP-TYPE
	ENTERPRISE netBotz-prd-bot-amp-total-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz Total Amps Low Trap. This trap indicates that the lower
	limit for the total amperage has been exceeded."
	REFERENCE 	"NetBotz Total Amps Low Trap"
	::= 1

netBotz-prd-bot-amp-total-high-trap TRAP-TYPE
	ENTERPRISE netBotz-prd-bot-amp-total-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz Total Amps High Trap. This trap indicates that the upper
	limit for the total amperage has been exceeded."
	REFERENCE 	"NetBotz Total Amps High Trap"
	::= 2

netBotz-prd-bot-amp-total-trap-clear TRAP-TYPE
	ENTERPRISE netBotz-prd-bot-amp-total-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz Total Amps Cleared Trap. The trap has been cleared because
	the total amperage value has returned to acceptable limits."
	REFERENCE 	"NetBotz Total Amps Cleared Trap"
	::= 3

netBotz-prd-bot-low-trap TRAP-TYPE
	ENTERPRISE netBotz-prd-bot
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz Low Trap. This trap indicates that a lower
	limit has been exceeded."
	REFERENCE 	"NetBotz Low Trap"
	::= 1

netBotz-prd-bot-high-trap TRAP-TYPE
	ENTERPRISE netBotz-prd-bot
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz High Trap. This trap indicates that an upper
	limit has been exceeded."
	REFERENCE 	"NetBotz High Trap"
	::= 2

netBotz-prd-bot-trap-clear TRAP-TYPE
	ENTERPRISE netBotz-prd-bot
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz Cleared Trap. The trap has been cleared because
	the value has returned to acceptable limits."
	REFERENCE 	"NetBotz Cleared Trap"
	::= 3

netBotz-prd-bot-offline-trap TRAP-TYPE
	ENTERPRISE netBotz-prd-bot
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz Device Offline Trap. This trap indicates that a device or function 
	has been determined to be offline."
	REFERENCE 	"NetBotz Offline Trap"
	::= 4

netBotz-prd-bot-online-trap TRAP-TYPE
	ENTERPRISE netBotz-prd-bot
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz Device Online Trap. This trap indicates that a device or function 
	has been determined to be online."
	REFERENCE 	"NetBotz Online Trap"
	::= 5

netBotz-prd-bot-ext-temp1-low-trap TRAP-TYPE
	ENTERPRISE netBotz-prd-bot-ext-temp1-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz External Temperature 1 Low Trap. This trap indicates that the lower
	limit for external temperature probe on port 1 has been exceeded."
	REFERENCE 	"NetBotz Ext Temperature 1 Low Trap"
	::= 1

netBotz-prd-bot-ext-temp1-high-trap TRAP-TYPE
	ENTERPRISE netBotz-prd-bot-ext-temp1-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz External Temperature 1 High Trap. This trap indicates that the upper
	limit for external temperature probe on port 1 has been exceeded."
	REFERENCE 	"NetBotz Ext Temperature 1 High Trap"
	::= 2

netBotz-prd-bot-ext-temp1-trap-clear TRAP-TYPE
	ENTERPRISE netBotz-prd-bot-ext-temp1-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz External Temperature 1 Cleared Trap. The trap has been cleared because
	the temperature value for the temperature probe on port 1 has returned to acceptable limits."
	REFERENCE 	"NetBotz Ext Temperature 1 Cleared Trap"
	::= 3

netBotz-prd-bot-ext-temp1-sensor-unplugged TRAP-TYPE
	ENTERPRISE netBotz-prd-bot-ext-temp1-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz External Temperature 1 Sensor Unplugged Trap. The sensor is unplugged or malfunctioning."
	REFERENCE 	"NetBotz Ext Temperature 1 Unplugged Trap"
	::= 6

netBotz-prd-bot-ext-temp1-sensor-replugged TRAP-TYPE
	ENTERPRISE netBotz-prd-bot-ext-temp1-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz External Temperature 1 Sensor Replugged Trap. The sensor was unplugged, but has been reconnected."
	REFERENCE 	"NetBotz Ext Temperature 1 Replugged Trap"
	::= 7

netBotz-prd-bot-ext-temp2-low-trap TRAP-TYPE
	ENTERPRISE netBotz-prd-bot-ext-temp2-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz External Temperature 2 Low Trap. This trap indicates that the lower
	limit for external temperature probe on port 2 has been exceeded."
	REFERENCE 	"NetBotz Ext Temperature 2 Low Trap"
	::= 1

netBotz-prd-bot-ext-temp2-high-trap TRAP-TYPE
	ENTERPRISE netBotz-prd-bot-ext-temp2-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz External Temperature 2 High Trap. This trap indicates that the upper
	limit for external temperature probe on port 2 has been exceeded."
	REFERENCE 	"NetBotz Ext Temperature 2 High Trap"
	::= 2

netBotz-prd-bot-ext-temp2-trap-clear TRAP-TYPE
	ENTERPRISE netBotz-prd-bot-ext-temp2-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz External Temperature 2 Cleared Trap. The trap has been cleared because
	the temperature value for the temperature probe on port 2 has returned to acceptable limits."
	REFERENCE 	"NetBotz Ext Temperature 2 Cleared Trap"
	::= 3

netBotz-prd-bot-ext-temp2-sensor-unplugged TRAP-TYPE
	ENTERPRISE netBotz-prd-bot-ext-temp2-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz External Temperature 2 Sensor Unplugged Trap. The sensor is unplugged or malfunctioning."
	REFERENCE 	"NetBotz Ext Temperature 2 Unplugged Trap"
	::= 6

netBotz-prd-bot-ext-temp2-sensor-replugged TRAP-TYPE
	ENTERPRISE netBotz-prd-bot-ext-temp2-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz External Temperature 2 Sensor Replugged Trap. The sensor was unplugged, but has been reconnected."
	REFERENCE 	"NetBotz Ext Temperature 2 Replugged Trap"
	::= 7

netBotz-prd-bot-ext-temp3-low-trap TRAP-TYPE
	ENTERPRISE netBotz-prd-bot-ext-temp3-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz External Temperature 3 Low Trap. This trap indicates that the lower
	limit for external temperature probe on port 3 has been exceeded."
	REFERENCE 	"NetBotz Ext Temperature 3 Low Trap"
	::= 1

netBotz-prd-bot-ext-temp3-high-trap TRAP-TYPE
	ENTERPRISE netBotz-prd-bot-ext-temp3-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz External Temperature 3 High Trap. This trap indicates that the upper
	limit for external temperature probe on port 3 has been exceeded."
	REFERENCE 	"NetBotz Ext Temperature 3 High Trap"
	::= 2

netBotz-prd-bot-ext-temp3-trap-clear TRAP-TYPE
	ENTERPRISE netBotz-prd-bot-ext-temp3-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz External Temperature 3 Cleared Trap. The trap has been cleared because
	the temperature value for the temperature probe on port 3 has returned to acceptable limits."
	REFERENCE 	"NetBotz Ext Temperature 3 Cleared Trap"
	::= 3

netBotz-prd-bot-ext-temp3-sensor-unplugged TRAP-TYPE
	ENTERPRISE netBotz-prd-bot-ext-temp3-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz External Temperature 3 Sensor Unplugged Trap. The sensor is unplugged or malfunctioning."
	REFERENCE 	"NetBotz Ext Temperature 3 Unplugged Trap"
	::= 6

netBotz-prd-bot-ext-temp3-sensor-replugged TRAP-TYPE
	ENTERPRISE netBotz-prd-bot-ext-temp3-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz External Temperature 3 Sensor Replugged Trap. The sensor was unplugged, but has been reconnected."
	REFERENCE 	"NetBotz Ext Temperature 3 Replugged Trap"
	::= 7

netBotz-prd-bot-ext-temp4-low-trap TRAP-TYPE
	ENTERPRISE netBotz-prd-bot-ext-temp4-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz External Temperature 4 Low Trap. This trap indicates that the lower
	limit for external temperature probe on port 4 has been exceeded."
	REFERENCE 	"NetBotz Ext Temperature 4 Low Trap"
	::= 1

netBotz-prd-bot-ext-temp4-high-trap TRAP-TYPE
	ENTERPRISE netBotz-prd-bot-ext-temp4-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz External Temperature 4 High Trap. This trap indicates that the upper
	limit for external temperature probe on port 4 has been exceeded."
	REFERENCE 	"NetBotz Ext Temperature 4 High Trap"
	::= 2

netBotz-prd-bot-ext-temp4-trap-clear TRAP-TYPE
	ENTERPRISE netBotz-prd-bot-ext-temp4-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz External Temperature 4 Cleared Trap. The trap has been cleared because
	the temperature value for the temperature probe on port 4 has returned to acceptable limits."
	REFERENCE 	"NetBotz Ext Temperature 4 Cleared Trap"
	::= 3

netBotz-prd-bot-ext-temp4-sensor-unplugged TRAP-TYPE
	ENTERPRISE netBotz-prd-bot-ext-temp4-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz External Temperature 4 Sensor Unplugged Trap. The sensor is unplugged or malfunctioning."
	REFERENCE 	"NetBotz Ext Temperature 4 Unplugged Trap"
	::= 6

netBotz-prd-bot-ext-temp4-sensor-replugged TRAP-TYPE
	ENTERPRISE netBotz-prd-bot-ext-temp4-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz External Temperature 4 Sensor Replugged Trap. The sensor was unplugged, but has been reconnected."
	REFERENCE 	"NetBotz Ext Temperature 4 Replugged Trap"
	::= 7

netBotz-prd-bot-ext-dry1-triggered-trap TRAP-TYPE
	ENTERPRISE netBotz-prd-bot-ext-dry1-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz External Dry Contact 1 Triggered Trap. This trap indicates that the state of the
	dry contact sensor on Ext1 matches the alarm value."
	REFERENCE 	"NetBotz Ext Dry 1 Triggered Trap"
	::= 2

netBotz-prd-bot-ext-dry1-trap-clear TRAP-TYPE
	ENTERPRISE netBotz-prd-bot-ext-dry1-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz External Dry Contact 1 Cleared Trap. The trap has been cleared because
	the state of the dry contact sensor on Ext1 no longer matches the alarm value."
	REFERENCE 	"NetBotz Ext Dry 1 Cleared Trap"
	::= 3

netBotz-prd-bot-ext-dry2-triggered-trap TRAP-TYPE
	ENTERPRISE netBotz-prd-bot-ext-dry2-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz External Dry Contact 2 Triggered Trap. This trap indicates that the state of the
	dry contact sensor on Ext2 matches the alarm value."
	REFERENCE 	"NetBotz Ext Dry 2 Triggered Trap"
	::= 2

netBotz-prd-bot-ext-dry2-trap-clear TRAP-TYPE
	ENTERPRISE netBotz-prd-bot-ext-dry2-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz External Dry Contact 2 Cleared Trap. The trap has been cleared because
	the state of the dry contact sensor on Ext2 no longer matches the alarm value."
	REFERENCE 	"NetBotz Ext Dry 2 Cleared Trap"
	::= 3

netBotz-prd-bot-ext-dry3-triggered-trap TRAP-TYPE
	ENTERPRISE netBotz-prd-bot-ext-dry3-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz External Dry Contact 3 Triggered Trap. This trap indicates that the state of the
	dry contact sensor on Ext3 matches the alarm value."
	REFERENCE 	"NetBotz Ext Dry 3 Triggered Trap"
	::= 2

netBotz-prd-bot-ext-dry3-trap-clear TRAP-TYPE
	ENTERPRISE netBotz-prd-bot-ext-dry3-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz External Dry Contact 3 Cleared Trap. The trap has been cleared because
	the state of the dry contact sensor on Ext3 no longer matches the alarm value."
	REFERENCE 	"NetBotz Ext Dry 3 Cleared Trap"
	::= 3

netBotz-prd-bot-ext-dry4-triggered-trap TRAP-TYPE
	ENTERPRISE netBotz-prd-bot-ext-dry4-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz External Dry Contact 4 Triggered Trap. This trap indicates that the state of the
	dry contact sensor on Ext4 matches the alarm value."
	REFERENCE 	"NetBotz Ext Dry 4 Triggered Trap"
	::= 2

netBotz-prd-bot-ext-dry4-trap-clear TRAP-TYPE
	ENTERPRISE netBotz-prd-bot-ext-dry4-traps
	VARIABLES {
		netBotz-prd-bot-trap-index,
		netBotz-prd-bot-trap-address,
		netBotz-prd-bot-trap-oid,
		netBotz-prd-bot-trap-value,
		netBotz-prd-bot-trap-date,
		netBotz-ismetric
		}
	DESCRIPTION 
	"Netbotz External Dry Contact 4 Cleared Trap. The trap has been cleared because
	the state of the dry contact sensor on Ext4 no longer matches the alarm value."
	REFERENCE 	"NetBotz Ext Dry 4 Cleared Trap"
	::= 3

END
