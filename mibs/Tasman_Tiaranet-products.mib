-- *****************************************************************
-- tiaranet-products.mib:  Tiara Networks Product Object Identifier 
-- Assignments
--
-- April,1st 1998, Shyla
--
--
-- Copyright (c) 1998-2005 by Tiara Networks, Inc.
-- All rights reserved.
-- 
-- *****************************************************************


TIARA-NETWORKS-PRODUCTS-MIB DEFINITIONS ::= BEGIN

IMPORTS
            MODULE-IDENTITY 
                    FROM SNMPv2-SMI
	    tiaraModules,
	    tiaraProducts
		    FROM TIARA-NETWORKS-SMI;

tiaraProductsMIB MODULE-IDENTITY 
  	LAST-UPDATED	"9904230000Z"
  	ORGANIZATION	"Tiara Networks, Inc."
  	CONTACT-INFO
                "       Tiara Networks
                        Customer Service

                Postal: 525 Race Street, Suite 100,
                        San Jose, CA 95126
                        USA

                   Tel: +1 408-216-4700
                   Fax: +1 408-216-4701

                E-mail: support@tiaranetworks.com"

  	DESCRIPTION
  		"This module defines the object identifiers that are
  		assigned to various hardware platforms, and hence are
  		returned as values for sysObjectID"
   	REVISION	"9904230000Z"
    	DESCRIPTION
  		"Initial version of the module."
           ::= { tiaraModules 1 }

-- devices return a sysObjectID value that corresponds to the
-- device model number

tiara1400  OBJECT IDENTIFIER ::= { tiaraProducts 1  }
tiara1400E OBJECT IDENTIFIER ::= { tiaraProducts 2  }
tiara6100  OBJECT IDENTIFIER ::= { tiaraProducts 3  }
tiara6200  OBJECT IDENTIFIER ::= { tiaraProducts 4  }
tiara6200E OBJECT IDENTIFIER ::= { tiaraProducts 5  }
tiara6300  OBJECT IDENTIFIER ::= { tiaraProducts 6  }
tiara1200  OBJECT IDENTIFIER ::= { tiaraProducts 7  }
tiara1250  OBJECT IDENTIFIER ::= { tiaraProducts 8  }
tiara1450  OBJECT IDENTIFIER ::= { tiaraProducts 9  }
tiara7011  OBJECT IDENTIFIER ::= { tiaraProducts 10 }
tiara7030  OBJECT IDENTIFIER ::= { tiaraProducts 11 }
tiara7050  OBJECT IDENTIFIER ::= { tiaraProducts 12 }
tiara4100  OBJECT IDENTIFIER ::= { tiaraProducts 13 }
tiara6302  OBJECT IDENTIFIER ::= { tiaraProducts 14 }
tiara4102  OBJECT IDENTIFIER ::= { tiaraProducts 15 }
tiara1450E  OBJECT IDENTIFIER ::= { tiaraProducts 16 }

END
