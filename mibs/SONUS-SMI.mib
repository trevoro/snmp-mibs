--
-- This SMIv2 module has been generated by smidump 0.2-cvs. Do not edit.
--

SONUS-SMI DEFINITIONS ::= BEGIN

IMPORTS
    MODULE-IDENTITY, OBJECT-IDENTITY, enterprises
        FROM SNMPv2-SMI;

sonus MODULE-IDENTITY
    LAST-UPDATED    "200102030000Z"
    ORGANIZATION    
            "Sonus Networks, Inc."
    CONTACT-INFO    
            "	Sonus Networks
             Customer Service
             
             Postal:
             Sonus Networks, Inc.
             5 Carlisle Road
             Westford, MA 01886
             USA
             
             Tel: 978-692-8999
             
             E-mail: cs.snmp@sonusnet.com"
    DESCRIPTION     
            "Initial version of this MIB module."
    ::= { enterprises 2879 }


sonusProducts OBJECT-IDENTITY
    STATUS          current
    DESCRIPTION     
            "sonusProducts is the root OBJECT IDENTIFIER from
             which sysObjectID values are assigned."
    ::= { sonus 1 }

sonusGSXProducts OBJECT-IDENTITY
    STATUS          current
    DESCRIPTION     
            "The Sonus GSX family of products."
    ::= { sonusProducts 1 }

sonusGSX9000 OBJECT-IDENTITY
    STATUS          current
    DESCRIPTION     
            "The Sonus GSX 9000."
    ::= { sonusGSXProducts 1 }

sonusGSX9000HD OBJECT-IDENTITY
    STATUS          current
    DESCRIPTION     
            "The Sonus GSX 9000HD."
    ::= { sonusGSXProducts 2 }

sonusPSXProducts OBJECT-IDENTITY
    STATUS          current
    DESCRIPTION     
            "The Sonus GSX family of products."
    ::= { sonusProducts 2 }

sonusPSX6000 OBJECT-IDENTITY
    STATUS          current
    DESCRIPTION     
            "The Sonus PSX 6000."
    ::= { sonusPSXProducts 1 }

sonusSGXProducts OBJECT-IDENTITY
    STATUS          current
    DESCRIPTION     
            "The Sonus SGX family of products."
    ::= { sonusProducts 3 }

sonusSGX2000 OBJECT-IDENTITY
    STATUS          current
    DESCRIPTION     
            "The Sonus SGX 2000."
    ::= { sonusSGXProducts 1 }

sonusMgmt OBJECT-IDENTITY
    STATUS          current
    DESCRIPTION     
            "sonusMgmt is the main subtree for mib configuration."
    ::= { sonus 2 }

sonusSystemMIBs OBJECT-IDENTITY
    STATUS          current
    DESCRIPTION     
            "Root MIB node for all System-related Sonus MIBs."
    ::= { sonusMgmt 1 }

sonusResourcesMIBs OBJECT-IDENTITY
    STATUS          current
    DESCRIPTION     
            "Root MIB node for all Resource-related Sonus MIBs."
    ::= { sonusMgmt 2 }

sonusPacketMIBs OBJECT-IDENTITY
    STATUS          current
    DESCRIPTION     
            "Root MIB node for all Packet-related Sonus MIBs."
    ::= { sonusMgmt 3 }

sonusCircuitMIBs OBJECT-IDENTITY
    STATUS          current
    DESCRIPTION     
            "Root MIB node for all Circuit-related Sonus MIBs."
    ::= { sonusMgmt 4 }

sonusServicesMIBs OBJECT-IDENTITY
    STATUS          current
    DESCRIPTION     
            "Root MIB node for all Services-related Sonus MIBs."
    ::= { sonusMgmt 5 }

sonusSignallingMIBs OBJECT-IDENTITY
    STATUS          current
    DESCRIPTION     
            "Root MIB node for all Signalling-related Sonus MIBs."
    ::= { sonusMgmt 6 }

sonusToolsMIBs OBJECT-IDENTITY
    STATUS          current
    DESCRIPTION     
            "Root MIB node for all Sonus development tools MIBs."
    ::= { sonusMgmt 7 }

sonusModules OBJECT-IDENTITY
    STATUS          current
    DESCRIPTION     
            "sonusModules provides a root object identifier
             from which MODULE-IDENTITY values may be assigned."
    ::= { sonus 3 }

END -- end of module SONUS-SMI.
