INTEL-IPX-MIB DEFINITIONS ::= BEGIN

-- Copyright (C) 1997 Intel Corporation. All rights reserved.
--
-- IPX MIB, 10-06-1997
--
-- Proprietary MIB containing information about IPX.
--
-- Change History:
-- 97-08-15 Initial version
--

IMPORTS
	Counter FROM RFC1155-SMI
    TimeTicks                  FROM RFC1155-SMI
    mib2ext                    FROM INTEL-GEN-MIB
    OBJECT-TYPE                FROM RFC-1212;

    ipx                OBJECT IDENTIFIER ::= { mib2ext 22 }
    ipxControl         OBJECT IDENTIFIER ::= { ipx 1 }
    ipxConf            OBJECT IDENTIFIER ::= { ipx 2 }
    ipxStatus          OBJECT IDENTIFIER ::= { ipx 3 }
    ipxCount           OBJECT IDENTIFIER ::= { ipx 4 }
    ipxRip             OBJECT IDENTIFIER ::= { ipx 5 }
    ipxSap             OBJECT IDENTIFIER ::= { ipx 6 }


-- Data Types

FltDirection ::= INTEGER { rx(1), tx(2) }
IpxAddr      ::= OCTET STRING (SIZE(12))
FltAction    ::= INTEGER { pass(1), discard(2), disabled(3) }


-- Control

ipxControlCommand OBJECT-TYPE
    SYNTAX INTEGER { flushRipSap(1), updateRipSap(2) }
    ACCESS write-only
    STATUS mandatory
    DESCRIPTION "Control register :
                 - Write 1 to flush routing table.
                   (Affects ipxRipTable & ipxSapTable)
                 - Write 2 to update RIP & SAP tables.
                   (Affects ipxRipTable & ipxSapTable)"
    ::= { ipxControl 1 }


-- Link-specific configuration

ipxLinkConfTable OBJECT-TYPE
    SYNTAX SEQUENCE OF IpxLinkConfEntry
    ACCESS not-accessible
    STATUS mandatory
    DESCRIPTION "This table contains link-specific configuration parameters."
    ::= { ipxConf 1 }

ipxLinkConfEntry OBJECT-TYPE
    SYNTAX IpxLinkConfEntry
    ACCESS not-accessible
    STATUS mandatory
    DESCRIPTION ""
    INDEX { ipxLinkConfIpxLinkIndex }
    ::= { ipxLinkConfTable 1 }

IpxLinkConfEntry ::= SEQUENCE {
                        ipxLinkConfIpxLinkIndex
                           INTEGER,
                        ipxLinkConfRoutingProtocol
                           INTEGER,
                        ipxLinkConfNumbered
                           INTEGER,
                        ipxLinkConfNet
                           OCTET STRING,
                        ipxLinkConfFrameType
                           INTEGER,
                        ipxLinkConfFrameParam
                           OCTET STRING,
                        ipxLinkConfIpxWanNegotiation
                           INTEGER,
                        ipxLinkConfRipUpdateInterval
                           INTEGER,
                        ipxLinkConfRipTrigger
                           INTEGER,
                        ipxLinkConfSapUpdateInterval
                           INTEGER,
                        ipxLinkConfSapTrigger
                           INTEGER,
                        ipxLinkConfAutomaticDelay
                           INTEGER,
                        ipxLinkConfDelay
                           INTEGER,
                        ipxLinkConfSpxSpoofing
                           INTEGER,
                        ipxLinkConfSpxSessionTimeout
                           INTEGER,
                        ipxLinkConfType20Broadcast
                           INTEGER,
                        ipxLinkConfWatchdogSpoofing
                           INTEGER,
                        ipxLinkConfRipFltRxDefaultAction
                           FltAction,
                        ipxLinkConfRipFltTxDefaultAction
                           FltAction,
                        ipxLinkConfSapFltRxDefaultAction
                           FltAction,
                        ipxLinkConfSapFltTxDefaultAction
                           FltAction,
                        ipxLinkConfDataFltRxDefaultAction
                           FltAction,
                        ipxLinkConfDataFltTxDefaultAction
                           FltAction,
                        ipxLinkConfDataFilters
                           INTEGER,
                        ipxLinkConfCreateObj
                           OCTET STRING,
                        ipxLinkConfDeleteObj
                           INTEGER
                        }

ipxLinkConfIpxLinkIndex OBJECT-TYPE
    SYNTAX INTEGER
    ACCESS read-only
    STATUS mandatory
    DESCRIPTION "IPX Link index. This is a number that uniquely
                 identifies an IPX interface."
    ::= { ipxLinkConfEntry 1 }

ipxLinkConfRoutingProtocol OBJECT-TYPE
    SYNTAX INTEGER { ripAndSap(1), staticOrNone(2) }
    ACCESS read-write
    STATUS mandatory
    DESCRIPTION "Determines if dynamic routing using RIP and SAP is
                 enabled or if only static routes and services are used."
    ::= { ipxLinkConfEntry 2 }

ipxLinkConfNumbered OBJECT-TYPE
    SYNTAX INTEGER { no(1), yes(2) }
    ACCESS read-write
    STATUS mandatory
    DESCRIPTION "Determines if a WAN link is numbered."
    ::= { ipxLinkConfEntry 3 }

ipxLinkConfNet OBJECT-TYPE
    SYNTAX OCTET STRING (SIZE(4))
    ACCESS read-write
    STATUS mandatory
    DESCRIPTION "The IPX net number defines a unique network number.
                 This object is not relevant for unnumbered WANs."
    ::= { ipxLinkConfEntry 4 }

ipxLinkConfFrameType OBJECT-TYPE
    SYNTAX INTEGER {
              type(1),
              ieee8022(2),
              snap(4),
              ieee8023(5),
              wan(16)
             }
    ACCESS read-write
    STATUS mandatory
    DESCRIPTION "The Frame type parameter specifies the encapsulation
                 method to use. Type(1) is also called Ethernet II."
    ::= { ipxLinkConfEntry 5 }

ipxLinkConfFrameParam OBJECT-TYPE
    SYNTAX OCTET STRING (SIZE(8))
    ACCESS read-only
    STATUS mandatory
    DESCRIPTION "The actual frame format for ipx2ConfFrameType."
    ::= { ipxLinkConfEntry 6 }

ipxLinkConfIpxWanNegotiation OBJECT-TYPE
    SYNTAX INTEGER { disabled(1), enabled(2) }
    ACCESS read-write
    STATUS mandatory
    DESCRIPTION "IPX WAN 2 Protocol"
    ::= { ipxLinkConfEntry 7 }

ipxLinkConfRipUpdateInterval OBJECT-TYPE
    SYNTAX INTEGER
    ACCESS read-write
    STATUS mandatory
    DESCRIPTION "Time between RIP updates in seconds."
    ::= { ipxLinkConfEntry 8 }

ipxLinkConfRipTrigger OBJECT-TYPE
    SYNTAX INTEGER { no(1), yes(2) }
    ACCESS read-write
    STATUS mandatory
    DESCRIPTION "Use triggered RIP updates."
    ::= { ipxLinkConfEntry 9 }

ipxLinkConfSapUpdateInterval OBJECT-TYPE
    SYNTAX INTEGER
    ACCESS read-write
    STATUS mandatory
    DESCRIPTION "Time between SAP updates in seconds."
    ::= { ipxLinkConfEntry 10 }

ipxLinkConfSapTrigger OBJECT-TYPE
    SYNTAX INTEGER { no(1), yes(2) }
    ACCESS read-write
    STATUS mandatory
    DESCRIPTION "Use triggered SAP updates."
    ::= { ipxLinkConfEntry 11 }

ipxLinkConfAutomaticDelay OBJECT-TYPE
    SYNTAX INTEGER { disabled(1), enabled(2) }
    ACCESS read-write
    STATUS mandatory
    DESCRIPTION "Specifies if the delay associated with use of the
                 LAN or WAN Link is determined automatically or is
                 manually defined."
    ::= { ipxLinkConfEntry 12 }

ipxLinkConfDelay OBJECT-TYPE
    SYNTAX INTEGER
    ACCESS read-write
    STATUS mandatory
    DESCRIPTION "The configured delay in ticks (1 tick = 55 ms)"
    ::= { ipxLinkConfEntry 13 }

ipxLinkConfSpxSpoofing OBJECT-TYPE
    SYNTAX INTEGER { disabled(1), enabled(2) }
    ACCESS read-write
    STATUS mandatory
    DESCRIPTION "SPX Spoofing is used to answer SPX keep-alive packets
                 on behalf of a remote client when the WAN Link is in
                 timecut mode."
    ::= { ipxLinkConfEntry 14 }

ipxLinkConfSpxSessionTimeout OBJECT-TYPE
    SYNTAX INTEGER
    ACCESS read-write
    STATUS mandatory
    DESCRIPTION "Defines the time limit for spoofing SPX keep-alive
                 packets from the LAN on behalf of remote clients."
    ::= { ipxLinkConfEntry 15 }

ipxLinkConfType20Broadcast OBJECT-TYPE
    SYNTAX INTEGER { disabled(1), enabled(2) }
    ACCESS read-write
    STATUS mandatory
    DESCRIPTION "Type 20 packets are used to propogate broadcasts
                 using different protocols through the network."
    ::= { ipxLinkConfEntry 16 }

ipxLinkConfWatchdogSpoofing OBJECT-TYPE
    SYNTAX INTEGER { disabled(1), enabled(2) }
    ACCESS read-write
    STATUS mandatory
    DESCRIPTION "Watchdog Spoofing is used to answer IPX watchdog
                 (keep-alive) packets from a local server on behalf of
                 a remote client when the WAN Link is in timecut mode."
    ::= { ipxLinkConfEntry 17 }

ipxLinkConfRipFltRxDefaultAction OBJECT-TYPE
    SYNTAX FltAction
    ACCESS read-write
    STATUS mandatory
    DESCRIPTION "Default action for RIP Receive Filters."
    ::= { ipxLinkConfEntry 18 }

ipxLinkConfRipFltTxDefaultAction OBJECT-TYPE
    SYNTAX FltAction
    ACCESS read-write
    STATUS mandatory
    DESCRIPTION "Default action for RIP Transmit Filters."
    ::= { ipxLinkConfEntry 19 }

ipxLinkConfSapFltRxDefaultAction OBJECT-TYPE
    SYNTAX FltAction
    ACCESS read-write
    STATUS mandatory
    DESCRIPTION "Default action for SAP Receive Filters."
    ::= { ipxLinkConfEntry 20 }

ipxLinkConfSapFltTxDefaultAction OBJECT-TYPE
    SYNTAX FltAction
    ACCESS read-write
    STATUS mandatory
    DESCRIPTION "Default action for SAP Transmit Filters."
    ::= { ipxLinkConfEntry 21 }

ipxLinkConfDataFltRxDefaultAction OBJECT-TYPE
    SYNTAX FltAction
    ACCESS read-write
    STATUS mandatory
    DESCRIPTION "Default action for Data Receive Filters."
    ::= { ipxLinkConfEntry 22 }

ipxLinkConfDataFltTxDefaultAction OBJECT-TYPE
    SYNTAX FltAction
    ACCESS read-write
    STATUS mandatory
    DESCRIPTION "Default action for Data Transmit Filters."
    ::= { ipxLinkConfEntry 23 }

ipxLinkConfDataFilters OBJECT-TYPE
    SYNTAX INTEGER { disabled(1), enabled(2) }
    ACCESS read-write
    STATUS mandatory
    DESCRIPTION "Configuration status of Data Filters"
    ::= { ipxLinkConfEntry 24 }

ipxLinkConfCreateObj OBJECT-TYPE
    SYNTAX OCTET STRING (SIZE(34))
    ACCESS read-write
    STATUS mandatory
    DESCRIPTION "Create a non existing table entry. If the entry already exist,
                 genError is returned.
                 Binary format (big-endian):
                     2 bytes : ipxLinkMonMplIndex
                     1 byte  : ipxLinkConfRoutingProtocol
                     1 byte  : ipxLinkConfNumbered
                     4 bytes : ipxLinkConfNet
                     2 bytes : ipxLinkConfFrameType
                     1 byte  : ipxLinkConfIpxWanNegotiation
                     4 bytes : ipxLinkConfRipUpdateInterval
                     1 byte  : ipxLinkConfRipTrigger
                     4 bytes : ipxLinkConfSapUpdateInterval
                     1 byte  : ipxLinkConfSapTrigger
                     1 byte  : ipxLinkConfAutomaticDelay
                     1 byte  : ipxLinkConfDelay
                     1 byte  : ipxLinkConfSpxSpoofing
                     1 byte  : ipxLinkConfSpxSessionTimeout
                     1 byte  : ipxLinkConfType20Broadcast
                     1 byte  : ipxLinkConfWatchdogSpoofing
                     1 byte  : ipxLinkConfRipFltRxDefaultAction
                     1 byte  : ipxLinkConfRipFltTxDefaultAction
                     1 byte  : ipxLinkConfSapFltRxDefaultAction
                     1 byte  : ipxLinkConfSapFltTxDefaultAction
                     1 byte  : ipxLinkConfDataFltRxDefaultAction
                     1 byte  : ipxLinkConfDataFltTxDefaultAction
                     1 byte  : ipxLinkConfDataFilters"
    ::= { ipxLinkConfEntry 25 }

ipxLinkConfDeleteObj OBJECT-TYPE
    SYNTAX INTEGER { delete(1) }
    ACCESS read-write
    STATUS mandatory
    DESCRIPTION ""
    ::= { ipxLinkConfEntry 26 }


-- RIP Filters

ipxRipFltTable OBJECT-TYPE
    SYNTAX SEQUENCE OF IpxRipFltEntry
    ACCESS not-accessible
    STATUS mandatory
    DESCRIPTION "RIP Filters"
    ::= { ipxConf 2 }

ipxRipFltEntry OBJECT-TYPE
    SYNTAX IpxRipFltEntry
    ACCESS not-accessible
    STATUS mandatory
    DESCRIPTION ""
    INDEX { ipxRipFltIpxLinkIndex, ipxRipFltDirection, ipxRipFltNumber }
    ::= { ipxRipFltTable 1 }

IpxRipFltEntry ::= SEQUENCE {
                        ipxRipFltIpxLinkIndex
                           INTEGER,
                        ipxRipFltDirection
                           FltDirection,
                        ipxRipFltNumber
                           INTEGER,
                        ipxRipFltAction
                           FltAction,
                        ipxRipFltNetworkAddress
                           OCTET STRING,
                        ipxRipFltNetworkMask
                           OCTET STRING
                        }

ipxRipFltIpxLinkIndex OBJECT-TYPE
    SYNTAX INTEGER
    ACCESS read-only
    STATUS mandatory
    DESCRIPTION "IPX Link index"
    ::= { ipxRipFltEntry 1 }

ipxRipFltDirection OBJECT-TYPE
    SYNTAX FltDirection
    ACCESS read-only
    STATUS mandatory
    DESCRIPTION "Filter direction"
    ::= { ipxRipFltEntry 2 }

ipxRipFltNumber OBJECT-TYPE
    SYNTAX INTEGER
    ACCESS read-only
    STATUS mandatory
    DESCRIPTION "Filter number"
    ::= { ipxRipFltEntry 3 }

ipxRipFltAction OBJECT-TYPE
    SYNTAX FltAction
    ACCESS read-only
    STATUS mandatory
    DESCRIPTION "Action to perform on packet if filter matches."
    ::= { ipxRipFltEntry 4 }

ipxRipFltNetworkAddress OBJECT-TYPE
    SYNTAX OCTET STRING (SIZE(4))
    ACCESS read-only
    STATUS mandatory
    DESCRIPTION "Network number or group of networks.
                 If ipxRipFltNetworkAddress is 0x00000000 and
                 ipxRipFltNetworkMask is 0xFFFFFFFF then filtering
                 is disabled."
    ::= { ipxRipFltEntry 5 }

ipxRipFltNetworkMask OBJECT-TYPE
    SYNTAX OCTET STRING (SIZE(4))
    ACCESS read-only
    STATUS mandatory
    DESCRIPTION "Network mask. See also ipxRipFltNetworkAddress"
    ::= { ipxRipFltEntry 6 }


-- SAP Filters

ipxSapFltTable OBJECT-TYPE
    SYNTAX SEQUENCE OF IpxSapFltEntry
    ACCESS not-accessible
    STATUS mandatory
    DESCRIPTION "SAP Filters"
    ::= { ipxConf 3 }

ipxSapFltEntry OBJECT-TYPE
    SYNTAX IpxSapFltEntry
    ACCESS not-accessible
    STATUS mandatory
    DESCRIPTION ""
    INDEX { ipxSapFltIpxLinkIndex, ipxSapFltDirection, ipxSapFltNumber }
    ::= { ipxSapFltTable 1 }

IpxSapFltEntry ::= SEQUENCE {
                        ipxSapFltIpxLinkIndex
                           INTEGER,
                        ipxSapFltDirection
                           FltDirection,
                        ipxSapFltNumber
                           INTEGER,
                        ipxSapFltAction
                           FltAction,
                        ipxSapFltNetworkAddress
                           OCTET STRING,
                        ipxSapFltNetworkMask
                           OCTET STRING,
                        ipxSapFltNodeAddress
                           OCTET STRING,
                        ipxSapFltServiceType
                           INTEGER,
                        ipxSapFltServerName
                           OCTET STRING
                        }

ipxSapFltIpxLinkIndex OBJECT-TYPE
    SYNTAX INTEGER
    ACCESS read-only
    STATUS mandatory
    DESCRIPTION "IPX Link index"
    ::= { ipxSapFltEntry 1 }

ipxSapFltDirection OBJECT-TYPE
    SYNTAX FltDirection
    ACCESS read-only
    STATUS mandatory
    DESCRIPTION "Filter direction"
    ::= { ipxSapFltEntry 2 }

ipxSapFltNumber OBJECT-TYPE
    SYNTAX INTEGER
    ACCESS read-only
    STATUS mandatory
    DESCRIPTION "Filter number"
    ::= { ipxSapFltEntry 3 }

ipxSapFltAction OBJECT-TYPE
    SYNTAX FltAction
    ACCESS read-only
    STATUS mandatory
    DESCRIPTION "Action to perform on packet if filter matches."
    ::= { ipxSapFltEntry 4 }

ipxSapFltNetworkAddress OBJECT-TYPE
    SYNTAX OCTET STRING (SIZE(4))
    ACCESS read-only
    STATUS mandatory
    DESCRIPTION "Network number or group of networks.
                 If ipxSapFltNetworkAddress is 0x00000000 and
                 ipxSapFltNetworkMask is 0xFFFFFFFF then filtering
                 is disabled."
    ::= { ipxSapFltEntry 5 }

ipxSapFltNetworkMask OBJECT-TYPE
    SYNTAX OCTET STRING (SIZE(4))
    ACCESS read-only
    STATUS mandatory
    DESCRIPTION "Network mask"
    ::= { ipxSapFltEntry 6 }

ipxSapFltNodeAddress OBJECT-TYPE
    SYNTAX OCTET STRING (SIZE(6))
    ACCESS read-only
    STATUS mandatory
    DESCRIPTION "If node is 0x00000000 filtering is disabled."
    ::= { ipxSapFltEntry 7 }

ipxSapFltServiceType OBJECT-TYPE
    SYNTAX INTEGER
    ACCESS read-only
    STATUS mandatory
    DESCRIPTION "Service type"
    ::= { ipxSapFltEntry 8 }

ipxSapFltServerName OBJECT-TYPE
    SYNTAX OCTET STRING (SIZE(48))
    ACCESS read-only
    STATUS mandatory
    DESCRIPTION "Server name"
    ::= { ipxSapFltEntry 9 }


-- Data Filters

ipxDataFltTable OBJECT-TYPE
    SYNTAX SEQUENCE OF IpxDataFltEntry
    ACCESS not-accessible
    STATUS mandatory
    DESCRIPTION "Data Filters"
    ::= { ipxConf 4 }

ipxDataFltEntry OBJECT-TYPE
    SYNTAX IpxDataFltEntry
    ACCESS not-accessible
    STATUS mandatory
    DESCRIPTION ""
    INDEX { ipxDataFltIpxLinkIndex, ipxDataFltDirection, ipxDataFltNumber }
    ::= { ipxDataFltTable 1 }

IpxDataFltEntry ::= SEQUENCE {
                        ipxDataFltIpxLinkIndex
                           INTEGER,
                        ipxDataFltDirection
                           FltDirection,
                        ipxDataFltNumber
                           INTEGER,
                        ipxDataFltAction
                           FltAction,
                        ipxDataFltDstNetworkAddress
                           OCTET STRING,
                        ipxDataFltDstNetworkMask
                           OCTET STRING,
                        ipxDataFltDstNodeAddress
                           OCTET STRING,
                        ipxDataFltDstSocketFilter
                           INTEGER,
                        ipxDataFltDstSocket
                           INTEGER,
                        ipxDataFltSrcNetworkAddress
                           OCTET STRING,
                        ipxDataFltSrcNetworkMask
                           OCTET STRING,
                        ipxDataFltSrcNodeAddress
                           OCTET STRING,
                        ipxDataFltSrcSocketFilter
                           INTEGER,
                        ipxDataFltSrcSocket
                           INTEGER,
                        ipxDataFltPacketTypeFilter
                           INTEGER,
                        ipxDataFltPacketType
                           INTEGER,
                        ipxDataFltHits
                           Counter
                        }

ipxDataFltIpxLinkIndex OBJECT-TYPE
    SYNTAX INTEGER
    ACCESS read-only
    STATUS mandatory
    DESCRIPTION "IPX Link index"
    ::= { ipxDataFltEntry 1 }

ipxDataFltDirection OBJECT-TYPE
    SYNTAX FltDirection
    ACCESS read-only
    STATUS mandatory
    DESCRIPTION "Filter direction"
    ::= { ipxDataFltEntry 2 }

ipxDataFltNumber OBJECT-TYPE
    SYNTAX INTEGER
    ACCESS read-only
    STATUS mandatory
    DESCRIPTION "Filter number"
    ::= { ipxDataFltEntry 3 }

ipxDataFltAction OBJECT-TYPE
    SYNTAX FltAction
    ACCESS read-only
    STATUS mandatory
    DESCRIPTION "Action to perform on packet if filter matches."
    ::= { ipxDataFltEntry 4 }

ipxDataFltDstNetworkAddress OBJECT-TYPE
    SYNTAX OCTET STRING (SIZE(4))
    ACCESS read-only
    STATUS mandatory
    DESCRIPTION "Network number or group of networks.
                 If ipxDataFltDstNetworkAddress is 0x00000000 and
                 ipxDataFltDstNetworkMask is 0xFFFFFFFF then filtering
                 is disabled."
    ::= { ipxDataFltEntry 5 }

ipxDataFltDstNetworkMask OBJECT-TYPE
    SYNTAX OCTET STRING (SIZE(4))
    ACCESS read-only
    STATUS mandatory
    DESCRIPTION "Destination network mask"
    ::= { ipxDataFltEntry 6 }

ipxDataFltDstNodeAddress OBJECT-TYPE
    SYNTAX OCTET STRING (SIZE(6))
    ACCESS read-only
    STATUS mandatory
    DESCRIPTION "If node is 0x00000000 filtering is disabled."
    ::= { ipxDataFltEntry 7 }

ipxDataFltDstSocketFilter OBJECT-TYPE
    SYNTAX INTEGER { disabled(1), enabled(2) }
    ACCESS read-only
    STATUS mandatory
    DESCRIPTION "Determines if filtering on destination socket is
                 enabled."
    ::= { ipxDataFltEntry 8 }

ipxDataFltDstSocket OBJECT-TYPE
    SYNTAX INTEGER
    ACCESS read-only
    STATUS mandatory
    DESCRIPTION "Destination socket"
    ::= { ipxDataFltEntry 9 }

ipxDataFltSrcNetworkAddress OBJECT-TYPE
    SYNTAX OCTET STRING (SIZE(4))
    ACCESS read-only
    STATUS mandatory
    DESCRIPTION "Network number or group of networks.
                 If ipxDataFltDstNetworkAddress is 0x00000000 and
                 ipxDataFltDstNetworkMask is 0xFFFFFFFF then filtering
                 is disabled."
    ::= { ipxDataFltEntry 10 }

ipxDataFltSrcNetworkMask OBJECT-TYPE
    SYNTAX OCTET STRING (SIZE(4))
    ACCESS read-only
    STATUS mandatory
    DESCRIPTION "Source network mask"
    ::= { ipxDataFltEntry 11 }

ipxDataFltSrcNodeAddress OBJECT-TYPE
    SYNTAX OCTET STRING (SIZE(6))
    ACCESS read-only
    STATUS mandatory
    DESCRIPTION "If node is 0x00000000 filtering is disabled."
    ::= { ipxDataFltEntry 12 }

ipxDataFltSrcSocketFilter OBJECT-TYPE
    SYNTAX INTEGER { disabled(1), enabled(2) }
    ACCESS read-only
    STATUS mandatory
    DESCRIPTION "Determines if filtering on source socket is
                 enabled."
    ::= { ipxDataFltEntry 13 }

ipxDataFltSrcSocket OBJECT-TYPE
    SYNTAX INTEGER
    ACCESS read-only
    STATUS mandatory
    DESCRIPTION "Source socket"
    ::= { ipxDataFltEntry 14 }

ipxDataFltPacketTypeFilter OBJECT-TYPE
    SYNTAX INTEGER { disabled(1), enabled(2) }
    ACCESS read-only
    STATUS mandatory
    DESCRIPTION "Determines if filtering on packet type is
                 enabled."
    ::= { ipxDataFltEntry 15 }

ipxDataFltPacketType OBJECT-TYPE
    SYNTAX INTEGER
    ACCESS read-only
    STATUS mandatory
    DESCRIPTION "Packet Type"
    ::= { ipxDataFltEntry 16 }

ipxDataFltHits OBJECT-TYPE
    SYNTAX Counter
    ACCESS read-only
    STATUS mandatory
    DESCRIPTION "Number of matches for this filter"
    ::= { ipxDataFltEntry 17 }


-- Global Configuration

ipxConfAutoIntNetNumber OBJECT-TYPE
    SYNTAX INTEGER { disabled(1), enabled(2) }
    ACCESS read-write
    STATUS mandatory
    DESCRIPTION "Specifies if the Internal Network Number should be
                 defined automatically (which means that the 4 lower bytes
                 of the MAC address are used."
    ::= { ipxConf 5 }

ipxConfIntNetNumber OBJECT-TYPE
    SYNTAX OCTET STRING (SIZE(4))
    ACCESS read-write
    STATUS mandatory
    DESCRIPTION "Internal Network Number"
    ::= { ipxConf 6 }


-- Status

ipxLinkMonTable OBJECT-TYPE
    SYNTAX SEQUENCE OF IpxLinkMonEntry
    ACCESS not-accessible
    STATUS mandatory
    DESCRIPTION "This table contains link-specific parameters."
    ::= { ipxStatus 1 }

ipxLinkMonEntry OBJECT-TYPE
    SYNTAX IpxLinkMonEntry
    ACCESS not-accessible
    STATUS mandatory
    DESCRIPTION ""
    INDEX { ipxLinkMonIpxLinkIndex }
    ::= { ipxLinkMonTable 1 }

IpxLinkMonEntry ::= SEQUENCE {
                        ipxLinkMonIpxLinkIndex
                           Counter,
                        ipxLinkMonIfIndex
                           INTEGER,
                        ipxLinkMonState
                           INTEGER,
                        ipxLinkMonDelay
                           INTEGER,
                        ipxLinkMonMtuSize
                           INTEGER
                        }

ipxLinkMonIpxLinkIndex OBJECT-TYPE
    SYNTAX Counter
    ACCESS read-only
    STATUS mandatory
    DESCRIPTION "IPX Link index."
    ::= { ipxLinkMonEntry 1 }

ipxLinkMonIfIndex OBJECT-TYPE
    SYNTAX INTEGER
    ACCESS read-only
    STATUS mandatory
    DESCRIPTION "Interface index for layer below."
    ::= { ipxLinkMonEntry 2 }

ipxLinkMonState OBJECT-TYPE
    SYNTAX INTEGER { down(1), up(2), negotiating(3) }
    ACCESS read-only
    STATUS mandatory
    DESCRIPTION "Link state"
    ::= { ipxLinkMonEntry 3 }

ipxLinkMonDelay OBJECT-TYPE
    SYNTAX INTEGER
    ACCESS read-only
    STATUS mandatory
    DESCRIPTION "Link Delay in ticks (1 tick = 55 ms).
                 The delay can be calculated automatically or
                 configured manuallly."
    ::= { ipxLinkMonEntry 4 }

ipxLinkMonMtuSize OBJECT-TYPE
    SYNTAX INTEGER
    ACCESS read-only
    STATUS mandatory
    DESCRIPTION "MTU Size is maximum packet size that can be
                 received and transmitted"
    ::= { ipxLinkMonEntry 5 }


-- Global status

ipxStatusConfigTimeStamp OBJECT-TYPE
    SYNTAX TimeTicks
    ACCESS read-only
    STATUS mandatory
    DESCRIPTION "Last configuration time in time ticks (like
                 sysUpTime)."
    ::= { ipxStatus 2 }

ipxStatusReachableNets OBJECT-TYPE
    SYNTAX Counter
    ACCESS read-only
    STATUS mandatory
    DESCRIPTION "Number of reachable networks in RIP Table."
    ::= { ipxStatus 3 }

ipxStatusDeadNets OBJECT-TYPE
    SYNTAX Counter
    ACCESS read-only
    STATUS mandatory
    DESCRIPTION "Number of dead networks in RIP Table."
    ::= { ipxStatus 4 }

ipxStatusReachableServices OBJECT-TYPE
    SYNTAX Counter
    ACCESS read-only
    STATUS mandatory
    DESCRIPTION "Number of reachable networks in SAP Table."
    ::= { ipxStatus 5 }

ipxStatusDeadServices OBJECT-TYPE
    SYNTAX Counter
    ACCESS read-only
    STATUS mandatory
    DESCRIPTION "Number of dead (hops=16) networks in SAP Table."
    ::= { ipxStatus 6 }

ipxStatusLinkTimeStamp OBJECT-TYPE
    SYNTAX TimeTicks
    ACCESS read-only
    STATUS mandatory
    DESCRIPTION "Last change in a link state in time ticks (like sysUpTime)."
    ::= { ipxStatus 7 }


-- Link-specific counters

ipxLinkCntTable OBJECT-TYPE
    SYNTAX SEQUENCE OF IpxLinkCntEntry
    ACCESS not-accessible
    STATUS mandatory
    DESCRIPTION "This table contains link-specific counters."
    ::= { ipxCount 1 }

ipxLinkCntEntry OBJECT-TYPE
    SYNTAX IpxLinkCntEntry
    ACCESS not-accessible
    STATUS mandatory
    DESCRIPTION ""
    INDEX { ipxLinkCntIpxLinkIndex }
    ::= { ipxLinkCntTable 1 }

IpxLinkCntEntry ::= SEQUENCE {
                        ipxLinkCntIpxLinkIndex
                           INTEGER,
                        ipxLinkCntRxTotal
                           Counter,
                        ipxLinkCntTxTotal
                           Counter,
                        ipxLinkCntTxFailed
                           Counter,
                        ipxLinkCntRxFiltered
                           Counter,
                        ipxLinkCntTxFiltered
                           Counter,
                        ipxLinkCntRxTooManyHops
                           Counter,
                        ipxLinkCntRxHeaderErr
                           Counter,
                        ipxLinkCntRxSapReq
                           Counter,
                        ipxLinkCntTxSapReq
                           Counter,
                        ipxLinkCntRxSapResp
                           Counter,
                        ipxLinkCntTxSapReply
                           Counter,
                        ipxLinkCntRxSapInvalid
                           Counter,
                        ipxLinkCntRxRipReq
                           Counter,
                        ipxLinkCntTxRipReq
                           Counter,
                        ipxLinkCntRxRipResp
                           Counter,
                        ipxLinkCntTxRipReply
                           Counter,
                        ipxLinkCntRxRipInvalid
                           Counter,
                        ipxLinkCntRxType20
                           Counter,
                        ipxLinkCntTxType20
                           Counter,
                        ipxLinkCntType20Disc
                           Counter,
                        ipxLinkCntNoRoute
                           Counter,
                        ipxLinkCntRxDiscarded
                           Counter,
                        ipxLinkCntSpxSpoofed
                           Counter,
                        ipxLinkCntWatchdogSpoofed
                           Counter,
                        ipxLinkCntForwarded
                           Counter,
                        ipxLinkCntCacheHits
                           Counter,
                        ipxLinkCntSPXCacheHits
                           Counter,
                        ipxLinkCntRxDefDataFltHits
                           Counter,
                        ipxLinkCntTxDefDataFltHits
                           Counter
                        }

ipxLinkCntIpxLinkIndex OBJECT-TYPE
    SYNTAX INTEGER
    ACCESS read-only
    STATUS mandatory
    DESCRIPTION "IPX Link index."
    ::= { ipxLinkCntEntry 1 }

ipxLinkCntRxTotal OBJECT-TYPE
    SYNTAX Counter
    ACCESS read-only
    STATUS mandatory
    DESCRIPTION "Total number of received IPX packets."
    ::= { ipxLinkCntEntry 2 }

ipxLinkCntTxTotal OBJECT-TYPE
    SYNTAX Counter
    ACCESS read-only
    STATUS mandatory
    DESCRIPTION "Total number of transmitted IPX packets."
    ::= { ipxLinkCntEntry 3 }

ipxLinkCntTxFailed OBJECT-TYPE
    SYNTAX Counter
    ACCESS read-only
    STATUS mandatory
    DESCRIPTION "Number of packets that could not be transmitted."
    ::= { ipxLinkCntEntry 4 }

ipxLinkCntRxFiltered OBJECT-TYPE
    SYNTAX Counter
    ACCESS read-only
    STATUS mandatory
    DESCRIPTION "Total number of received packets that were filtered."
    ::= { ipxLinkCntEntry 5 }

ipxLinkCntTxFiltered OBJECT-TYPE
    SYNTAX Counter
    ACCESS read-only
    STATUS mandatory
    DESCRIPTION "Total number of packets to be transmitted that were filtered."
    ::= { ipxLinkCntEntry 6 }

ipxLinkCntRxTooManyHops OBJECT-TYPE
    SYNTAX Counter
    ACCESS read-only
    STATUS mandatory
    DESCRIPTION "Total number of IPX packets that have exceeded the
                 maximum hop count."
    ::= { ipxLinkCntEntry 7 }

ipxLinkCntRxHeaderErr OBJECT-TYPE
    SYNTAX Counter
    ACCESS read-only
    STATUS mandatory
    DESCRIPTION "Total number of IPX packets with bad length."
    ::= { ipxLinkCntEntry 8 }

ipxLinkCntRxSapReq OBJECT-TYPE
    SYNTAX Counter
    ACCESS read-only
    STATUS mandatory
    DESCRIPTION "Total number of IPX SAP request packets received."
    ::= { ipxLinkCntEntry 9 }

ipxLinkCntTxSapReq OBJECT-TYPE
    SYNTAX Counter
    ACCESS read-only
    STATUS mandatory
    DESCRIPTION "Total number of IPX SAP request packets transmitted."
    ::= { ipxLinkCntEntry 10 }

ipxLinkCntRxSapResp OBJECT-TYPE
    SYNTAX Counter
    ACCESS read-only
    STATUS mandatory
    DESCRIPTION "Total number of IPX SAP response packets received."
    ::= { ipxLinkCntEntry 11 }

ipxLinkCntTxSapReply OBJECT-TYPE
    SYNTAX Counter
    ACCESS read-only
    STATUS mandatory
    DESCRIPTION "Total number of IPX SAP reply packets transmitted."
    ::= { ipxLinkCntEntry 12 }

ipxLinkCntRxSapInvalid OBJECT-TYPE
    SYNTAX Counter
    ACCESS read-only
    STATUS mandatory
    DESCRIPTION "Number of invalid IPX SAP request packets."
    ::= { ipxLinkCntEntry 13 }

ipxLinkCntRxRipReq OBJECT-TYPE
    SYNTAX Counter
    ACCESS read-only
    STATUS mandatory
    DESCRIPTION "Total number of IPX RIP request packets received."
    ::= { ipxLinkCntEntry 14 }

ipxLinkCntTxRipReq OBJECT-TYPE
    SYNTAX Counter
    ACCESS read-only
    STATUS mandatory
    DESCRIPTION "Total number of IPX RIP request packets transmitted."
    ::= { ipxLinkCntEntry 15 }

ipxLinkCntRxRipResp OBJECT-TYPE
    SYNTAX Counter
    ACCESS read-only
    STATUS mandatory
    DESCRIPTION "Total number of IPX RIP response packets received."
    ::= { ipxLinkCntEntry 16 }

ipxLinkCntTxRipReply OBJECT-TYPE
    SYNTAX Counter
    ACCESS read-only
    STATUS mandatory
    DESCRIPTION "Total number of IPX RIP reply packets transmitted."
    ::= { ipxLinkCntEntry 17 }

ipxLinkCntRxRipInvalid OBJECT-TYPE
    SYNTAX Counter
    ACCESS read-only
    STATUS mandatory
    DESCRIPTION "Number of invalid IPX RIP request packets."
    ::= { ipxLinkCntEntry 18 }

ipxLinkCntRxType20 OBJECT-TYPE
    SYNTAX Counter
    ACCESS read-only
    STATUS mandatory
    DESCRIPTION "Total number of Type 20 propagation packet received."
    ::= { ipxLinkCntEntry 19 }

ipxLinkCntTxType20 OBJECT-TYPE
    SYNTAX Counter
    ACCESS read-only
    STATUS mandatory
    DESCRIPTION "Total number of Type 20 propagation packet transmitted."
    ::= { ipxLinkCntEntry 20 }

ipxLinkCntType20Disc OBJECT-TYPE
    SYNTAX Counter
    ACCESS read-only
    STATUS mandatory
    DESCRIPTION "Number of Type 20 Propagation discarded."
    ::= { ipxLinkCntEntry 21 }

ipxLinkCntNoRoute OBJECT-TYPE
    SYNTAX Counter
    ACCESS read-only
    STATUS mandatory
    DESCRIPTION "Total number of IPX packets dropped due to unknown
                 net number."
    ::= { ipxLinkCntEntry 22 }

ipxLinkCntRxDiscarded OBJECT-TYPE
    SYNTAX Counter
    ACCESS read-only
    STATUS mandatory
    DESCRIPTION "Total number of discarded IPX packets."
    ::= { ipxLinkCntEntry 23 }

ipxLinkCntSpxSpoofed OBJECT-TYPE
    SYNTAX Counter
    ACCESS read-only
    STATUS mandatory
    DESCRIPTION "Number of SPX packets spoofed."
    ::= { ipxLinkCntEntry 24 }

ipxLinkCntWatchdogSpoofed OBJECT-TYPE
    SYNTAX Counter
    ACCESS read-only
    STATUS mandatory
    DESCRIPTION "Number of Watchdog packets spoofed."
    ::= { ipxLinkCntEntry 25 }

ipxLinkCntForwarded OBJECT-TYPE
    SYNTAX Counter
    ACCESS read-only
    STATUS mandatory
    DESCRIPTION "Number of packets sent that were received on
                 another interface."
    ::= { ipxLinkCntEntry 26 }

ipxLinkCntCacheHits OBJECT-TYPE
    SYNTAX Counter
    ACCESS read-only
    STATUS mandatory
    DESCRIPTION "Number of packets that were cache forwarded."
    ::= { ipxLinkCntEntry 27 }

ipxLinkCntSPXCacheHits OBJECT-TYPE
    SYNTAX Counter
    ACCESS read-only
    STATUS mandatory
    DESCRIPTION "Number of cache hits in SPX Spoofing Table."
    ::= { ipxLinkCntEntry 28 }

ipxLinkCntRxDefDataFltHits OBJECT-TYPE
    SYNTAX Counter
    ACCESS read-only
    STATUS mandatory
    DESCRIPTION "Number of times a packet did not match any receive
                 filters and the default action was used."
    ::= { ipxLinkCntEntry 29 }

ipxLinkCntTxDefDataFltHits OBJECT-TYPE
    SYNTAX Counter
    ACCESS read-only
    STATUS mandatory
    DESCRIPTION "Number of times a packet did not match any transmit
                 filters and the default action was used."
    ::= { ipxLinkCntEntry 30 }


-- Link-specific byte counters

ipxLinkByteCntTable OBJECT-TYPE
    SYNTAX SEQUENCE OF IpxLinkByteCntEntry
    ACCESS not-accessible
    STATUS mandatory
    DESCRIPTION "This table contains link-specific byte counters."
    ::= { ipxCount 2 }

ipxLinkByteCntEntry OBJECT-TYPE
    SYNTAX IpxLinkByteCntEntry
    ACCESS not-accessible
    STATUS mandatory
    DESCRIPTION ""
    INDEX { ipxLinkByteCntIpxLinkIndex }
    ::= { ipxLinkByteCntTable 1 }

IpxLinkByteCntEntry ::= SEQUENCE {
                        ipxLinkByteCntIpxLinkIndex
                           INTEGER,
                        ipxLinkByteCntRxTotal
                           Counter,
                        ipxLinkByteCntTxTotal
                           Counter,
                        ipxLinkByteCntRxOther
                           Counter,
                        ipxLinkByteCntTxOther
                           Counter,
                        ipxLinkByteCntRxNcp
                           Counter,
                        ipxLinkByteCntTxNcp
                           Counter,
                        ipxLinkByteCntRxSpx
                           Counter,
                        ipxLinkByteCntTxSpx
                           Counter,
                        ipxLinkByteCntRxRip
                           Counter,
                        ipxLinkByteCntTxRip
                           Counter,
                        ipxLinkByteCntRxSap
                           Counter,
                        ipxLinkByteCntTxSap
                           Counter,
                        ipxLinkByteCntRxType20
                           Counter,
                        ipxLinkByteCntTxType20
                           Counter
                        }

ipxLinkByteCntIpxLinkIndex OBJECT-TYPE
    SYNTAX INTEGER
    ACCESS read-only
    STATUS mandatory
    DESCRIPTION "IPX Link index."
    ::= { ipxLinkByteCntEntry 1 }

ipxLinkByteCntRxTotal OBJECT-TYPE
    SYNTAX Counter
    ACCESS read-only
    STATUS mandatory
    DESCRIPTION "Number of bytes received in total for link."
    ::= { ipxLinkByteCntEntry 2 }

ipxLinkByteCntTxTotal OBJECT-TYPE
    SYNTAX Counter
    ACCESS read-only
    STATUS mandatory
    DESCRIPTION "Number of bytes transmitted in total for link."
    ::= { ipxLinkByteCntEntry 3 }

ipxLinkByteCntRxOther OBJECT-TYPE
    SYNTAX Counter
    ACCESS read-only
    STATUS mandatory
    DESCRIPTION "Number of bytes received of unknown types."
    ::= { ipxLinkByteCntEntry 4 }

ipxLinkByteCntTxOther OBJECT-TYPE
    SYNTAX Counter
    ACCESS read-only
    STATUS mandatory
    DESCRIPTION "Number of bytes transmitted of unknown types."
    ::= { ipxLinkByteCntEntry 5 }

ipxLinkByteCntRxNcp OBJECT-TYPE
    SYNTAX Counter
    ACCESS read-only
    STATUS mandatory
    DESCRIPTION "Number of NCP bytes received."
    ::= { ipxLinkByteCntEntry 6 }

ipxLinkByteCntTxNcp OBJECT-TYPE
    SYNTAX Counter
    ACCESS read-only
    STATUS mandatory
    DESCRIPTION "Number of NCP bytes transmitted."
    ::= { ipxLinkByteCntEntry 7 }

ipxLinkByteCntRxSpx OBJECT-TYPE
    SYNTAX Counter
    ACCESS read-only
    STATUS mandatory
    DESCRIPTION "Number of SPX bytes received."
    ::= { ipxLinkByteCntEntry 8 }

ipxLinkByteCntTxSpx OBJECT-TYPE
    SYNTAX Counter
    ACCESS read-only
    STATUS mandatory
    DESCRIPTION "Number of SPX bytes transmitted."
    ::= { ipxLinkByteCntEntry 9 }

ipxLinkByteCntRxRip OBJECT-TYPE
    SYNTAX Counter
    ACCESS read-only
    STATUS mandatory
    DESCRIPTION "Number of RIP bytes received."
    ::= { ipxLinkByteCntEntry 10 }

ipxLinkByteCntTxRip OBJECT-TYPE
    SYNTAX Counter
    ACCESS read-only
    STATUS mandatory
    DESCRIPTION "Number of RIP bytes transmitted."
    ::= { ipxLinkByteCntEntry 11 }

ipxLinkByteCntRxSap OBJECT-TYPE
    SYNTAX Counter
    ACCESS read-only
    STATUS mandatory
    DESCRIPTION "Number of SAP bytes received."
    ::= { ipxLinkByteCntEntry 12 }

ipxLinkByteCntTxSap OBJECT-TYPE
    SYNTAX Counter
    ACCESS read-only
    STATUS mandatory
    DESCRIPTION "Number of SAP bytes transmitted."
    ::= { ipxLinkByteCntEntry 13 }

ipxLinkByteCntRxType20 OBJECT-TYPE
    SYNTAX Counter
    ACCESS read-only
    STATUS mandatory
    DESCRIPTION "Number of Type 20 bytes received."
    ::= { ipxLinkByteCntEntry 14 }

ipxLinkByteCntTxType20 OBJECT-TYPE
    SYNTAX Counter
    ACCESS read-only
    STATUS mandatory
    DESCRIPTION "Number of Type 20 bytes transmitted."
    ::= { ipxLinkByteCntEntry 15 }


-- Counters for all links

ipxCountRxTotal OBJECT-TYPE
    SYNTAX Counter
    ACCESS read-only
    STATUS mandatory
    DESCRIPTION "Total number of received IPX packets."
    ::= { ipxCount 3 }

ipxCountTxTotal OBJECT-TYPE
    SYNTAX Counter
    ACCESS read-only
    STATUS mandatory
    DESCRIPTION "Total number of transmitted IPX packets."
    ::= { ipxCount 4 }

ipxCountTxFailed OBJECT-TYPE
    SYNTAX Counter
    ACCESS read-only
    STATUS mandatory
    DESCRIPTION "Number of packets that could not be transmitted."
    ::= { ipxCount 5 }

ipxCountRxFiltered OBJECT-TYPE
    SYNTAX Counter
    ACCESS read-only
    STATUS mandatory
    DESCRIPTION "Total number of received packets that were filtered."
    ::= { ipxCount 6 }

ipxCountTxFiltered OBJECT-TYPE
    SYNTAX Counter
    ACCESS read-only
    STATUS mandatory
    DESCRIPTION "Total number of packets to be transmitted that were filtered."
    ::= { ipxCount 7 }

ipxCountRxTooManyHops OBJECT-TYPE
    SYNTAX Counter
    ACCESS read-only
    STATUS mandatory
    DESCRIPTION "Total number of IPX packets that have exceeded the
                 maximum hop count."
    ::= { ipxCount 8 }

ipxCountRxHeaderErr OBJECT-TYPE
    SYNTAX Counter
    ACCESS read-only
    STATUS mandatory
    DESCRIPTION "Total number of IPX packets with bad length."
    ::= { ipxCount 9 }

ipxCountRxSapReq OBJECT-TYPE
    SYNTAX Counter
    ACCESS read-only
    STATUS mandatory
    DESCRIPTION "Total number of IPX SAP request packets received."
    ::= { ipxCount 10 }

ipxCountTxSapReq OBJECT-TYPE
    SYNTAX Counter
    ACCESS read-only
    STATUS mandatory
    DESCRIPTION "Total number of IPX SAP request packets transmitted."
    ::= { ipxCount 11 }

ipxCountRxSapResp OBJECT-TYPE
    SYNTAX Counter
    ACCESS read-only
    STATUS mandatory
    DESCRIPTION "Total number of IPX SAP response packets received."
    ::= { ipxCount 12 }

ipxCountTxSapReply OBJECT-TYPE
    SYNTAX Counter
    ACCESS read-only
    STATUS mandatory
    DESCRIPTION "Total number of IPX SAP reply packets transmitted."
    ::= { ipxCount 13 }

ipxCountRxSapInvalid OBJECT-TYPE
    SYNTAX Counter
    ACCESS read-only
    STATUS mandatory
    DESCRIPTION "Number of invalid IPX SAP request packets."
    ::= { ipxCount 14 }

ipxCountRxRipReq OBJECT-TYPE
    SYNTAX Counter
    ACCESS read-only
    STATUS mandatory
    DESCRIPTION "Total number of IPX RIP request packets received."
    ::= { ipxCount 15 }

ipxCountTxRipReq OBJECT-TYPE
    SYNTAX Counter
    ACCESS read-only
    STATUS mandatory
    DESCRIPTION "Total number of IPX RIP request packets transmitted."
    ::= { ipxCount 16 }

ipxCountRxRipResp OBJECT-TYPE
    SYNTAX Counter
    ACCESS read-only
    STATUS mandatory
    DESCRIPTION "Total number of IPX RIP response packets received."
    ::= { ipxCount 17 }

ipxCountTxRipReply OBJECT-TYPE
    SYNTAX Counter
    ACCESS read-only
    STATUS mandatory
    DESCRIPTION "Total number of IPX RIP reply packets transmitted."
    ::= { ipxCount 18 }

ipxCountRxRipInvalid OBJECT-TYPE
    SYNTAX Counter
    ACCESS read-only
    STATUS mandatory
    DESCRIPTION "Number of invalid IPX RIP request packets."
    ::= { ipxCount 19 }

ipxCountRxType20 OBJECT-TYPE
    SYNTAX Counter
    ACCESS read-only
    STATUS mandatory
    DESCRIPTION "Total number of Type 20 propagation packet received."
    ::= { ipxCount 20 }

ipxCountTxType20 OBJECT-TYPE
    SYNTAX Counter
    ACCESS read-only
    STATUS mandatory
    DESCRIPTION "Total number of Type 20 propagation packet transmitted."
    ::= { ipxCount 21 }

ipxCountType20Disc OBJECT-TYPE
    SYNTAX Counter
    ACCESS read-only
    STATUS mandatory
    DESCRIPTION "Number of Type 20 Propagation discarded."
    ::= { ipxCount 22 }

ipxCountNoRoute OBJECT-TYPE
    SYNTAX Counter
    ACCESS read-only
    STATUS mandatory
    DESCRIPTION "Total number of IPX packets dropped due to unknownnet number."
    ::= { ipxCount 23 }

ipxCountRxDiscarded OBJECT-TYPE
    SYNTAX Counter
    ACCESS read-only
    STATUS mandatory
    DESCRIPTION "Total number of discarded IPX packets."
    ::= { ipxCount 24 }

ipxCountSpxSpoofed OBJECT-TYPE
    SYNTAX Counter
    ACCESS read-only
    STATUS mandatory
    DESCRIPTION "Number of SPX packets spoofed."
    ::= { ipxCount 25 }

ipxCountWatchdogSpoofed OBJECT-TYPE
    SYNTAX Counter
    ACCESS read-only
    STATUS mandatory
    DESCRIPTION "Number of Watchdog packets spoofed."
    ::= { ipxCount 26 }

ipxCountForwarded OBJECT-TYPE
    SYNTAX Counter
    ACCESS read-only
    STATUS mandatory
    DESCRIPTION "Number of packets sent that were received onanother interface."
    ::= { ipxCount 27 }

ipxCountCacheHits OBJECT-TYPE
    SYNTAX Counter
    ACCESS read-only
    STATUS mandatory
    DESCRIPTION "Number of packets that were cache forwarded."
    ::= { ipxCount 28 }

ipxCountSPXCacheHits OBJECT-TYPE
    SYNTAX Counter
    ACCESS read-only
    STATUS mandatory
    DESCRIPTION "Number of cache hits in SPX Spoofing Table."
    ::= { ipxCount 29 }


-- RIP table

ipxRipTable OBJECT-TYPE
    SYNTAX SEQUENCE OF IpxRipEntry
    ACCESS not-accessible
    STATUS mandatory
    DESCRIPTION "RIP table - supplement to table in Novells MIB"
    ::= { ipxRip 1 }

ipxRipEntry OBJECT-TYPE
    SYNTAX IpxRipEntry
    ACCESS not-accessible
    STATUS mandatory
    DESCRIPTION ""
    INDEX { ipxRipNetwork }
    ::= { ipxRipTable 1 }

IpxRipEntry ::= SEQUENCE {
                        ipxRipNetwork
                           OCTET STRING,
                        ipxRipIpxLinkIndex
                           INTEGER,
                        ipxRipIfIndex
                           INTEGER,
                        ipxRipProtocol
                           INTEGER,
                        ipxRipDelay
                           INTEGER,
                        ipxRipHops
                           INTEGER,
                        ipxRipAge
                           INTEGER,
                        ipxRipIpxAddr
                           IpxAddr,
                        ipxRipStaticCount
                           INTEGER
                        }

ipxRipNetwork OBJECT-TYPE
    SYNTAX OCTET STRING (SIZE(4))
    ACCESS read-only
    STATUS mandatory
    DESCRIPTION ""
    ::= { ipxRipEntry 1 }

ipxRipIpxLinkIndex OBJECT-TYPE
    SYNTAX INTEGER
    ACCESS read-only
    STATUS mandatory
    DESCRIPTION "Network received on interface with this IPX Link index."
    ::= { ipxRipEntry 2 }

ipxRipIfIndex OBJECT-TYPE
    SYNTAX INTEGER
    ACCESS read-only
    STATUS mandatory
    DESCRIPTION "Network received on interface with this interface index."
    ::= { ipxRipEntry 3 }

ipxRipProtocol OBJECT-TYPE
    SYNTAX INTEGER {
        other(1),
        local(2),
        rip(3),
        nlsp(4),
        static(5),
        staticBackup(6)
    }
    ACCESS read-only
    STATUS mandatory
    DESCRIPTION "Specifies where the network entry came from.
                 Note: local is the same as direct."
    ::= { ipxRipEntry 4 }

ipxRipDelay OBJECT-TYPE
    SYNTAX INTEGER
    ACCESS read-only
    STATUS mandatory
    DESCRIPTION "Delay to destination measured in ticks (1 tick = 55 ms)."
    ::= { ipxRipEntry 5 }

ipxRipHops OBJECT-TYPE
    SYNTAX INTEGER
    ACCESS read-only
    STATUS mandatory
    DESCRIPTION "Number of hops to route."
    ::= { ipxRipEntry 6 }

ipxRipAge OBJECT-TYPE
    SYNTAX INTEGER
    ACCESS read-only
    STATUS mandatory
    DESCRIPTION "Time in milliseconds since (re)insertion."
    ::= { ipxRipEntry 7 }

ipxRipIpxAddr OBJECT-TYPE
    SYNTAX IpxAddr
    ACCESS read-only
    STATUS mandatory
    DESCRIPTION "The route was learned from this IPX address."
    ::= { ipxRipEntry 8 }

ipxRipStaticCount OBJECT-TYPE
    SYNTAX INTEGER
    ACCESS read-only
    STATUS mandatory
    DESCRIPTION "Number of other static route to this network."
    ::= { ipxRipEntry 9 }


-- SAP table

ipxSapTable OBJECT-TYPE
    SYNTAX SEQUENCE OF IpxSapEntry
    ACCESS not-accessible
    STATUS mandatory
    DESCRIPTION "SAP table - supplement to table in Novells MIB"
    ::= { ipxSap 1 }

ipxSapEntry OBJECT-TYPE
    SYNTAX IpxSapEntry
    ACCESS not-accessible
    STATUS mandatory
    DESCRIPTION ""
    INDEX { ipxSapServerAddr, ipxSapServerType }
    ::= { ipxSapTable 1 }

IpxSapEntry ::= SEQUENCE {
                        ipxSapServerAddr
                           IpxAddr,
                        ipxSapServerType
                           INTEGER,
                        ipxSapServerName
                           OCTET STRING,
                        ipxSapIpxLinkIndex
                           INTEGER,
                        ipxSapIfIndex
                           INTEGER,
                        ipxSapAge
                           INTEGER,
                        ipxSapProtocol
                           INTEGER,
                        ipxSapHops
                           INTEGER,
                        ipxSapStaticCount
                           INTEGER
                        }

ipxSapServerAddr OBJECT-TYPE
    SYNTAX IpxAddr
    ACCESS read-only
    STATUS mandatory
    DESCRIPTION "Address of server"
    ::= { ipxSapEntry 1 }

ipxSapServerType OBJECT-TYPE
    SYNTAX INTEGER
    ACCESS read-only
    STATUS mandatory
    DESCRIPTION "Service type"
    ::= { ipxSapEntry 2 }

ipxSapServerName OBJECT-TYPE
    SYNTAX OCTET STRING (SIZE(48))
    ACCESS read-only
    STATUS mandatory
    DESCRIPTION ""
    ::= { ipxSapEntry 3 }

ipxSapIpxLinkIndex OBJECT-TYPE
    SYNTAX INTEGER
    ACCESS read-only
    STATUS mandatory
    DESCRIPTION "Service received on interface with this IPX Link index."
    ::= { ipxSapEntry 4 }

ipxSapIfIndex OBJECT-TYPE
    SYNTAX INTEGER
    ACCESS read-only
    STATUS mandatory
    DESCRIPTION "Service received on interface with this interface index."
    ::= { ipxSapEntry 5 }

ipxSapAge OBJECT-TYPE
    SYNTAX INTEGER
    ACCESS read-only
    STATUS mandatory
    DESCRIPTION "Time in milliseconds since (re)insertion."
    ::= { ipxSapEntry 6 }

ipxSapProtocol OBJECT-TYPE
    SYNTAX INTEGER { static(5), sap(6) }
    ACCESS read-only
    STATUS mandatory
    DESCRIPTION "Specifies how the service was learned."
    ::= { ipxSapEntry 7 }

ipxSapHops OBJECT-TYPE
    SYNTAX INTEGER
    ACCESS read-only
    STATUS mandatory
    DESCRIPTION ""
    ::= { ipxSapEntry 8 }

ipxSapStaticCount OBJECT-TYPE
    SYNTAX INTEGER
    ACCESS read-only
    STATUS mandatory
    DESCRIPTION "Number of other static services with this name and type."
    ::= { ipxSapEntry 9 }

END
