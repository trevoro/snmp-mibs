INFORMANT-BIZTALK DEFINITIONS ::= BEGIN

IMPORTS
    MODULE-IDENTITY, OBJECT-TYPE, Gauge32
        FROM SNMPv2-SMI
    informant
        FROM WTCS;

bizTalkServer MODULE-IDENTITY
    LAST-UPDATED "200402290633Z"
    ORGANIZATION "Informant Systems, Inc."
    CONTACT-INFO
            "        Garth Williams
                Tel: +1 780 433 7973
             E-mail: garth.williams@wtcs.org"
    DESCRIPTION
            "The MIB module for SNMP Informant BizTalk
             performance counter entries."
    REVISION      "200402290633Z"
    DESCRIPTION
            "Changed the syntax of the datapoints from
			 integer to gauge."
    REVISION      "200401220612Z"
    DESCRIPTION
            "The initial revision of this MIB module."
    ::= { informant 4 }

btsActivatedScheduleInstances OBJECT-TYPE
    SYNTAX     Gauge32
    MAX-ACCESS read-only
    STATUS     current
    DESCRIPTION
	    "The number of activated schedule instances."
    ::= { bizTalkServer 1 }

btsAsynchronousSubmissions OBJECT-TYPE
    SYNTAX     Gauge32
    MAX-ACCESS read-only
    STATUS     current
    DESCRIPTION
	    "The number of interchanges received through
	    asynchronous submissions."
    ::= { bizTalkServer 2 }

btsAsynchronousSubmissionsPerSec OBJECT-TYPE
    SYNTAX     Gauge32
    MAX-ACCESS read-only
    STATUS     current
    DESCRIPTION
	    "The rate at which interchanges are received
	    through a Submit method call."
    ::= { bizTalkServer 3 }

btsCompletedSchedInstances OBJECT-TYPE
    SYNTAX     Gauge32
    MAX-ACCESS read-only
    STATUS     current
    DESCRIPTION
	    "The number of schedule instances completed
	    successfully."
    ::= { bizTalkServer 4 }

btsCompletedSchedInstancesPerSec OBJECT-TYPE
    SYNTAX     Gauge32
    MAX-ACCESS read-only
    STATUS     current
    DESCRIPTION
	    "The rate at which schedule instances
	    sucessfully complete."
    ::= { bizTalkServer 5 }

btsDehydratedScheduleInstances OBJECT-TYPE
    SYNTAX     Gauge32
    MAX-ACCESS read-only
    STATUS     current
    DESCRIPTION
	    "The current number of dehydrated schedule
	    instances."
    ::= { bizTalkServer 6 }

btsDocumentsMappedPerSec OBJECT-TYPE
    SYNTAX     Gauge32
    MAX-ACCESS read-only
    STATUS     current
    DESCRIPTION
	    "The document mapping rate."
    ::= { bizTalkServer 7 }

btsDocumentsParsedPerSec OBJECT-TYPE
    SYNTAX     Gauge32
    MAX-ACCESS read-only
    STATUS     current
    DESCRIPTION
	    "The document parsing rate."
    ::= { bizTalkServer 8 }

btsDocumentsProcessed OBJECT-TYPE
    SYNTAX     Gauge32
    MAX-ACCESS read-only
    STATUS     current
    DESCRIPTION
	    "The number of documents processed."
    ::= { bizTalkServer 9 }

btsDocumentsProcessedPerSec OBJECT-TYPE
    SYNTAX     Gauge32
    MAX-ACCESS read-only
    STATUS     current
    DESCRIPTION
	    "The document processing rate."
    ::= { bizTalkServer 10 }

btsDocumentsReceived OBJECT-TYPE
    SYNTAX     Gauge32
    MAX-ACCESS read-only
    STATUS     current
    DESCRIPTION
	    "The number of documents received through
	    synchronous and asynchronous submissions."
    ::= { bizTalkServer 11 }

btsDocumentsReceivedPerSec OBJECT-TYPE
    SYNTAX     Gauge32
    MAX-ACCESS read-only
    STATUS     current
    DESCRIPTION
	    "The rate at which documents are received
	    through synchronous and asynchronous
	    submissions."
    ::= { bizTalkServer 12 }

btsDocumentsSerializedPerSec OBJECT-TYPE
    SYNTAX     Gauge32
    MAX-ACCESS read-only
    STATUS     current
    DESCRIPTION
	    "Document serialization rate."
    ::= { bizTalkServer 13 }

btsFailedScheduleInstances OBJECT-TYPE
    SYNTAX     Gauge32
    MAX-ACCESS read-only
    STATUS     current
    DESCRIPTION
	    "The number of failed schedule instances."
    ::= { bizTalkServer 14 }

btsFailedScheduleInstancesPerSec OBJECT-TYPE
    SYNTAX     Gauge32
    MAX-ACCESS read-only
    STATUS     current
    DESCRIPTION
	    "The rate at which schedule instances fail."
    ::= { bizTalkServer 15 }

btsInterchangesDecodedPerSec OBJECT-TYPE
    SYNTAX     Gauge32
    MAX-ACCESS read-only
    STATUS     current
    DESCRIPTION
	    "The interchange decoding rate."
    ::= { bizTalkServer 16 }

btsInterchangesDecryptedPerSec OBJECT-TYPE
    SYNTAX     Gauge32
    MAX-ACCESS read-only
    STATUS     current
    DESCRIPTION
	    "The interchange decryption rate."
    ::= { bizTalkServer 17 }

btsInterchangesEncodedPerSec OBJECT-TYPE
    SYNTAX     Gauge32
    MAX-ACCESS read-only
    STATUS     current
    DESCRIPTION
	    "The interchange encoding rate."
    ::= { bizTalkServer 18 }

btsInterchangesEncryptedPerSec OBJECT-TYPE
    SYNTAX     Gauge32
    MAX-ACCESS read-only
    STATUS     current
    DESCRIPTION
	    "The interchange encryption rate."
    ::= { bizTalkServer 19 }

btsInterchangesReceived OBJECT-TYPE
    SYNTAX     Gauge32
    MAX-ACCESS read-only
    STATUS     current
    DESCRIPTION
	    "The number of interchanges received through
	    synchronous and asynchronous submissions."
    ::= { bizTalkServer 20 }

btsInterchangesReceivedPerSec OBJECT-TYPE
    SYNTAX     Gauge32
    MAX-ACCESS read-only
    STATUS     current
    DESCRIPTION
	    "The rate at which interchanges are received
	    through synchronous and asynchronous
	    submissions."
    ::= { bizTalkServer 21 }

btsInterchangesTransmittedPerSec OBJECT-TYPE
    SYNTAX     Gauge32
    MAX-ACCESS read-only
    STATUS     current
    DESCRIPTION
	    "The rate at which interchanges are
	    transmitted."
    ::= { bizTalkServer 22 }

btsItemsSuspended OBJECT-TYPE
    SYNTAX     Gauge32
    MAX-ACCESS read-only
    STATUS     current
    DESCRIPTION
	    "The number of items that are suspended due to
	    a processing failure. An item can be an
	    interchange, a document, or an unrecognizable
	    submission."
    ::= { bizTalkServer 23 }

btsItemsSuspendedPerSec OBJECT-TYPE
    SYNTAX     Gauge32
    MAX-ACCESS read-only
    STATUS     current
    DESCRIPTION
	    "The rate at which items are suspended due to a
	    processing failure. An item can be an
	    interchange, a document, or an unrecognizable
	    submission."
    ::= { bizTalkServer 24 }

btsRunningSchedInstances OBJECT-TYPE
    SYNTAX     Gauge32
    MAX-ACCESS read-only
    STATUS     current
    DESCRIPTION
	    "The current number of running schedule
	    instances."
    ::= { bizTalkServer 25 }

btsRunningSchedInstancesPerSec OBJECT-TYPE
    SYNTAX     Gauge32
    MAX-ACCESS read-only
    STATUS     current
    DESCRIPTION
	    "The current number of running schedule
	    instances rate."
    ::= { bizTalkServer 26 }

btsSchedulesActivatedPerSec OBJECT-TYPE
    SYNTAX     Gauge32
    MAX-ACCESS read-only
    STATUS     current
    DESCRIPTION
	    "The rate at which schedules get activated."
    ::= { bizTalkServer 27 }

btsSynchronousSubmissions OBJECT-TYPE
    SYNTAX     Gauge32
    MAX-ACCESS read-only
    STATUS     current
    DESCRIPTION
	    "The number of interchanges received through
	    synchronous submissions."
    ::= { bizTalkServer 28 }

btsSynchronousSubmissionsPerSec OBJECT-TYPE
    SYNTAX     Gauge32
    MAX-ACCESS read-only
    STATUS     current
    DESCRIPTION
	    "The rate at which interchanges are received
	    through synchronous submissions."
    ::= { bizTalkServer 29 }

btsTransactionsAborted OBJECT-TYPE
    SYNTAX     Gauge32
    MAX-ACCESS read-only
    STATUS     current
    DESCRIPTION
	    "The number of transactions aborted during
	    schedule instance execution."
    ::= { bizTalkServer 30 }

btsTransactionsAbortedPerSec OBJECT-TYPE
    SYNTAX     Gauge32
    MAX-ACCESS read-only
    STATUS     current
    DESCRIPTION
	    "Transaction abort rate during schedule
	    execution."
    ::= { bizTalkServer 31 }

END
