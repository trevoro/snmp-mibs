-- COPYRIGHT 1994, 1995  ASCOM TIMEPLEX

-- What                @(#)mib.txt	1.7
-- sccs ID:            1.7
-- get date:           10/15/97
-- get time:           16:59:04
-- delta date:         8/28/97
-- delta time:         17:17:49
-- module type:        

STMIB DEFINITIONS ::= BEGIN

IMPORTS
	enterprises, IpAddress, Counter,Gauge,
	TimeTicks, NetworkAddress
		FROM RFC1155-SMI
	
	OBJECT-TYPE
		FROM RFC-1212

--	TRAP-TYPE
--		FROM RFC-1215;

	DisplayString
		FROM RFC1213-MIB;


-- ST-50 private MIB

-- ST-50 private types

NodeAddr        ::=	-- region(0 in Rel. 1):node ID(1..2000)
		OCTET STRING (SIZE  (2))

NestAddr        ::=     -- nest
		OCTET STRING (SIZE  (1))

SlotAddr        ::=     -- nest(1):slot(1)
		OCTET STRING (SIZE  (2))

PortAddr        ::=	-- nest(1):slot(1):port(2)  for physical port
                     	-- type(1):group(1):port(2) for virtual port
                     	-- group (1..64)
			-- port
			--	for physical port (1..64)
			--	for virtual port (1..32767)
			--	for LGM virtual port (1..64)
			-- type = 128 for FSM virtual port
                     	-- type = 129 for AGM virtual port
			-- type = 130 for ASM X50 virtual port
			-- type = 131 for DSM virtual port
			-- type = 132 for LGM virtual port
			-- type = 180 for voice trunk group
			-- type = 181 for AD10 trunk group

		OCTET STRING (SIZE  (4))


Ad10PortAddr    ::= 	-- type:group:port agm virtual port
                    	-- Ad10 port local address(2)
		OCTET STRING (SIZE  (6))

AsmX50CkAddr    ::=  	-- type(130):group:port:AsmX50CkLocalAddr(1-20)
                     	-- X50 Circuit Address on X50 aggregrate entering
			-- ASM port
		OCTET STRING (SIZE (6))

RtmAdPortAddr	::= 	-- nest:slot:port:element
                    	-- element is AD-3/AD-7 port local address
		OCTET STRING (SIZE (6))

BundleAddr      ::=  	-- nest(1):slot(1):port(2):bundle(2)
                     	-- (1..31)
		OCTET STRING (SIZE  (6))

ChannelAddr     ::=     -- address one end of a channel
                        -- nest:slot:port:network element(2), or
                        -- type:group:port:network element(2)
                        -- network element is bundle id for
                        -- T1M/E1M port, 0 for SDM Port
                        -- DLCI for FSM port, or
                        -- Ad10 local address for Ad10 port
		OCTET STRING (SIZE  (6))

ChannelStatusAddr ::= 	-- used to retrieve the status of channel
                      	-- terminating or bypassing the node.
                      	-- 1. channel address for local orig channel
                      	-- 2. 255: node ID(2): Channel Address(6)
                      	-- for a bypass channel
		OCTET STRING (SIZE  (9))

RecordIndex     ::=     -- table(2):record(2)
		OCTET STRING (SIZE  (4))

AlarmRecord     ::=     -- structure of alarm record (64)
		OCTET STRING (SIZE  (64))

Link2Index	::=	-- serves as index to Link-2<->ST-50 translation table
			-- nest(1):slot(1):entry(2) (has nothing to do with any
			-- adressing). The ranges are:
			--	nest - 1..3,
			--	slot - 1..18,
			--	entry - 1..32
			-- It is just a logical number commonly known by both,
			-- Link-2 and ST-50
		OCTET STRING (SIZE  (4))

Link2Addr	::=	-- Link-2 address format:
			-- node(2):nest(1):slot(1):port(2):[xch(2)].
			-- The node may be in the range 1 - 2000, which takes
			-- 2 octet strings to define (identical to ST-50 node).
			-- The ranges for the rest of the fields are:
			--	nest - 1..3,
			--      slot - 1..18,
			--      port - 1..32,
			--	xch  - 0..31
		OCTET STRING (SIZE  (8))

-- private             OBJECT IDENTIFIER ::=    { internet 4 }
-- enterprises         OBJECT IDENTIFIER ::=    { private 1 }
timeplex            OBJECT IDENTIFIER ::=    { enterprises 16 }
synchrony           OBJECT IDENTIFIER ::=    { timeplex 101 }
st50                OBJECT IDENTIFIER ::=    { synchrony 1 }

security            OBJECT IDENTIFIER ::=    { st50 1 }
resource            OBJECT IDENTIFIER ::=    { st50 2 }
alarm               OBJECT IDENTIFIER ::=    { st50 3 }

reConfig            OBJECT IDENTIFIER ::=    { resource 1 }
reStatus            OBJECT IDENTIFIER ::=    { resource 2 }
reStatistics        OBJECT IDENTIFIER ::=    { resource 3 }

-- Security MIB

-- Partition Entry for transaction processing on security section

scPartitionHeader        OBJECT IDENTIFIER ::= { security 1 }

scPartitionControl 	OBJECT-TYPE
		SYNTAX    INTEGER {
			      validateCRC(1),
			      invalidateCRC(2)
			  }
		ACCESS    write-only
		STATUS    mandatory
		DESCRIPTION "Parameter Type = Immediate."
		::= { scPartitionHeader 1 }

scPartitionCRCCheck 	OBJECT-TYPE
		SYNTAX    INTEGER {
			      succeed(1),
			      fail(2)
 			  }
		ACCESS    read-only
		STATUS    mandatory
		DESCRIPTION "Parameter Type = Internal."
		::= { scPartitionHeader 2 }

scPartitionFlushMode 	OBJECT-TYPE
		SYNTAX    INTEGER {
			      enable(1),
			      disable(2)
  	           	  }
		ACCESS    read-write
		STATUS    mandatory
		DESCRIPTION "Parameter Type = Immediate."
		DEFVAL { disable }
		::= { scPartitionHeader 3 }


-- System Profiles

scSystemProfile OBJECT IDENTIFIER ::= { security 2 }

scSysNodeUpdate OBJECT-TYPE
		SYNTAX    INTEGER {
                              loaded(1),
			      resetReq(3)
                          }
		ACCESS    read-only
		STATUS    mandatory
		DESCRIPTION "Parameter Type = Internal.
			This field will be set to loaded when
			the node is reset."
		DEFVAL { resetReq }
		::= { scSystemProfile 1 }

scSysNodeControl 	OBJECT-TYPE
		SYNTAX  INTEGER {
			    resetNode(3),
			    validateDatabase(1),
			    invalidateDatabase(2),
			    updateThroughput(4),
			    updateCpiProfile(5)
			}
		ACCESS  write-only
		STATUS  mandatory
		DESCRIPTION "Parameter Type = Immediate.
			    Validate database will set the database
			    version number to the value used for this
			    revision of ST software.

			    Invalidate database will set the database
			    version number to zero. This will flush the
			    database when the node is reset.

			    Update throughput will load all of the
			    throughput values from the node access
			    table.

			    Update CPI profile will load the CPI system
			    information (control, three passwords,
			    session time-out value, and maximum number
			    of passthru sessions."
		::= { scSystemProfile 2 }

scSysNodeNumber 	OBJECT-TYPE
		SYNTAX    NodeAddr
		ACCESS    read-write
		STATUS    mandatory
		DESCRIPTION "Parameter Type = Intrusive."
		::= { scSystemProfile 3 }

scSysNodeDate 	OBJECT-TYPE
		SYNTAX    DisplayString ( SIZE(0..10))
		ACCESS    read-write
		STATUS    mandatory
		DESCRIPTION "Parameter Type = Immediate.
			This will update the NCP RTC clock. The
			format of the string is mm/dd/yyyy."
		::= { scSystemProfile 4 }

scSysNodeTime 	OBJECT-TYPE
		SYNTAX    DisplayString ( SIZE(0..8))
		ACCESS    read-write
		STATUS    mandatory
		DESCRIPTION "Parameter Type = Immediate.
			This will update the NCP RTC clock. The
			format of the string is hh:mm:ss."
		::= { scSystemProfile 5 }

scSysNodeType 	OBJECT-TYPE
		SYNTAX    INTEGER {
                              rootNode(1),
                              dedicatedNode(2),
                              sharedNode(3)
                          }
		ACCESS    read-write
		STATUS    mandatory
		DESCRIPTION "Parameter Type = Intrusive.
			A dedicated node is dedicated to a user
			or the CNMS.

			A root node is a dedicated node that
			serves as an active gateway to other ST
			nodes in the same network.

			A shared node is owned by the CNMS, with
			resources on the node allocated to
			multiple user partitions."
		DEFVAL { dedicatedNode }
		::= { scSystemProfile 6 }

scSysNodePartitionID 	OBJECT-TYPE
		SYNTAX    INTEGER (1..1023)
		ACCESS    read-write
		STATUS    mandatory
		DESCRIPTION "Parameter Type = Intrusive.
			1 is reserved for CNMS."
		DEFVAL { 1 }
		::= { scSystemProfile 7 }


scSysNodeMasterClockPriority 	OBJECT-TYPE
		SYNTAX    INTEGER {
                                   master1(1),
                                   master2(2),
                                   master3(3),
                                   master4(4),
                                   master5(5),
                                   master6(6),
                                   master7(7),
                                   master8(8),
                                   master9(9),
                                   master10(10),
                                   master11(11),
                                   master12(12),
                                   master13(13),
                                   master14(14),
                                   master15(15),
                                   master16(16),
                                   slave(17)
                                   }
		ACCESS    read-write
		STATUS    mandatory
		DESCRIPTION "Parameter Type = Immediate."
		DEFVAL { slave }
		::= { scSystemProfile 8 }

scSysNodeMasterClockList 	OBJECT-TYPE
		SYNTAX    OCTET STRING (SIZE (32))
		ACCESS    read-write
		STATUS    mandatory
		DESCRIPTION "Parameter Type = Immediate.
			Up to 16 master clock nodes, with two
			bytes used for each node number."
		::= { scSystemProfile 9 }

scSysNodeDatabaseVersion 	OBJECT-TYPE
		SYNTAX  DisplayString (SIZE (0..8))
		ACCESS  read-only
		STATUS  mandatory
		DESCRIPTION "Parameter Type = Internal.
			    Nonvolatile RAM database version number.
			    If this number does not match the internal
			    version number used for the revision of NCP
			    code running at node startup, then the
			    database will be flushed. In this event,
			    the user can reconfigure the node and reset
			    it to put the node back into operation."
		::= { scSystemProfile 10 }

scSysNodeDefaultRoot 	OBJECT-TYPE
		SYNTAX    NodeAddr
		ACCESS    read-write
		STATUS    mandatory
		DESCRIPTION "Parameter Type = Immediate.
			Used by the trap generator to send traps if
			there is no alLogNotificationList specified."
		::= { scSystemProfile 11 }

scSysNodeCpiProfileUpdate 	OBJECT-TYPE
		SYNTAX    INTEGER {
				loaded(1),
				updateCpiProfileReq(2)
                          }
		ACCESS    read-only
		STATUS    mandatory
		DESCRIPTION "Parameter Type = Internal.
			Indicates whether the CPI password control, the
			CPI session timeout time, the CPI maximum number
			of passthru sessions, or any of the three CPI
			passwords have been changed since the last
			update CPI profile command was invoked."
		DEFVAL { updateCpiProfileReq }
		::= { scSystemProfile 12 }

scSysNodeCpiPasswordControl 	OBJECT-TYPE
		SYNTAX    INTEGER {
                                   enable(1),
                                   disable(2),
				   enablePassthru(3)
                                   }
		ACCESS    read-write
		STATUS    mandatory
		DESCRIPTION "Parameter Type = Non-intrusive.
			Indicates whether CPI access is controlled
			using passwords or not. This field and the
			three CPI passwords apply to CPI access
			through the CPI port, through the modem port,
			and through access devices. The enablePassthru
			value shall disable password control for the
			CPI and modem ports, but enable it for access
			devices."
		DEFVAL { disable }
		::= { scSystemProfile 13 }

scSysNodeCpiPasswordLevel1 	OBJECT-TYPE
		SYNTAX    DisplayString ( SIZE (1..16) )
		ACCESS    write-only
		STATUS    mandatory
		DESCRIPTION "Parameter Type = Non-intrusive.
			This password allows both read and write access
			to both local and remote nodes if password
			control is enabled. It applies to users
			accessing the node from the CPI port, modem
			port, or an access device."
		DEFVAL { "public" }
		::= { scSystemProfile 14 }

scSysNodeCpiPasswordLevel2 	OBJECT-TYPE
		SYNTAX    DisplayString ( SIZE (1..16) )
		ACCESS    write-only
		STATUS    mandatory
		DESCRIPTION "Parameter Type = Non-intrusive.
			This password allows both read and write access
			to the local node and read-only access to
			remote nodes if password control is enabled.
			It applies to users accessing the node from
			the CPI port, modem port, or an access device."
		DEFVAL { "public" }
		::= { scSystemProfile 15 }

scSysNodeCpiPasswordLevel3 	OBJECT-TYPE
		SYNTAX    DisplayString ( SIZE (1..16) )
		ACCESS    write-only
		STATUS    mandatory
		DESCRIPTION "Parameter Type = Non-intrusive.
			This password allows read-only access to both
			local and remote nodes if password control is
			enabled. It applies to users accessing the node
			from the CPI port, modem port, or an access
			device."
		DEFVAL { "public" }
		::= { scSystemProfile 16 }

scSysNodeCpiSessionTimeOut 	OBJECT-TYPE
		SYNTAX    INTEGER (1..1440)
		ACCESS    read-write
		STATUS    mandatory
		DESCRIPTION "Parameter Type = Non-intrusive.
		 	CPI session will terminate when no request is
			made for number of minutes given by this value.
			For the CPI port, this time-out only occurs if
			password control is enabled. For the modem
			port, the session can terminate regardless of
			the password control state, and the port will
			be switch to an NMS session in SLIP mode."
		DEFVAL { 30 }
		::= { scSystemProfile 17 }

scSysNodeCpiMaxPassthruSessions 	OBJECT-TYPE
		SYNTAX	INTEGER (0..4)
		ACCESS	read-write
		STATUS	mandatory
		DESCRIPTION "Parameter Type = Non-intrusive.
			This value indicates the maximum number
			of CPI access device passthru sessions
			that can be active simultaneously."
		DEFVAL { 4 }
		::= { scSystemProfile 18 }


-- Root Access List

scRootAccessTable 	OBJECT-TYPE
		SYNTAX    SEQUENCE OF ScRootAccessEntry
		ACCESS    not-accessible
		STATUS    mandatory
		DESCRIPTION " "
		::=  { security 3 }

scRootAccessEntry 	OBJECT-TYPE
		SYNTAX    ScRootAccessEntry
		ACCESS    not-accessible
		STATUS    mandatory
		DESCRIPTION " "
		INDEX { scRootAccessIndex }
		::=  { scRootAccessTable 1 }

ScRootAccessEntry        ::=  SEQUENCE {
                         scRootAccessIndex
                                   INTEGER,
                         scRootAccessControlMode
                                   INTEGER,
                         scRootAccessIp
                                   IpAddress
                          }

scRootAccessIndex 	OBJECT-TYPE
		SYNTAX    INTEGER (1..16)
		ACCESS    read-only
		STATUS    mandatory
		DESCRIPTION "Parameter Type = Internal.
			Up to 16 EMS stations can access the node."
		::=  { scRootAccessEntry 1 }

scRootAccessControlMode 	OBJECT-TYPE
		SYNTAX    INTEGER {
                                   enable(1),
                                   disable(2),
                                   erase(3)
                                   }
		ACCESS    read-write
		STATUS    mandatory
		DESCRIPTION "Parameter Type = Immediate."
		DEFVAL { disable }
		::=  { scRootAccessEntry 2 }

scRootAccessIp 	OBJECT-TYPE
		SYNTAX    IpAddress
		ACCESS    read-write
		STATUS    mandatory
		DESCRIPTION "Parameter Type = Immediate."
		::=  { scRootAccessEntry 3 }

-- Node Access List

scNodeAccessTable 	OBJECT-TYPE
		SYNTAX    SEQUENCE OF ScNodeAccessEntry
		ACCESS    not-accessible
		STATUS    mandatory
		DESCRIPTION " "
		::=  { security 4 }

scNodeAccessEntry 	OBJECT-TYPE
		SYNTAX    ScNodeAccessEntry
		ACCESS    not-accessible
		STATUS    mandatory
		DESCRIPTION " "
		INDEX { scNodeAccessIndex }
		::=  { scNodeAccessTable 1 }

ScNodeAccessEntry 	::=  SEQUENCE {
                         scNodeAccessIndex
                                   INTEGER,
                         scNodeAccessControlMode
                                   INTEGER,
			 scNodeAccessUpdate
                                   INTEGER,
                         scNodeAccessRootList
                                   OCTET STRING,
                         scNodeAccessChPrfList
                                   OCTET STRING,
                         scNodeAccessThroughput
                                   INTEGER,
			 scNodeAccessVoicePrfList
			   OCTET STRING,
                         scNodeAccessLink2TraEntriesMin
			   INTEGER,
			 scNodeAccessLink2TraEntriesMax
			   INTEGER
			  }

scNodeAccessIndex 	OBJECT-TYPE
		SYNTAX    INTEGER (1..1023)
		ACCESS    read-only
		STATUS    mandatory
		DESCRIPTION "Parameter Type = Internal.
			Maximum of 32 partitions per node.

			If the node is a dedicated CNMS node, only the
			entry for CNMS (partition ID 1) exists. The
			rest of the entries are empty.

			If the node is a dedicated user node, only the
			entries for CNMS (partition 1) and the
			partition ID of the user exist. The rest of
			the entries are empty.

			If the node is a shared node, the entry for
			CNMS (partition 1) always exists. Thirty-one
			other entries with partitions 2 through 1023
			can be created. These entries represent user
			partitions that have access to the node."
		::=  { scNodeAccessEntry 1 }

scNodeAccessControlMode 	OBJECT-TYPE
		SYNTAX    INTEGER {
                                   fullAccess(59),
                                   tableAccess(60),
                                   disable(2),
                                   erase(3)
                                   }
		ACCESS    read-write
		STATUS    mandatory
		DESCRIPTION "Parameter Type = Immediate.
			Full access will only check the requester's
			partition ID.

			Table access will use the root node list to
			verify the requester's partition ID and node
			number.

			Disable means that the entry is not in effect.
			The CNMS entry cannot be set to disable.

			Erase will erase this entry. The CNMS entry
			cannot be set to erase."
		::=  { scNodeAccessEntry 2 }

scNodeAccessUpdate 	OBJECT-TYPE
		SYNTAX    INTEGER {
				   loaded(1),
				   updateThroughputReq(3)
				   }
		ACCESS    read-only
		STATUS    mandatory
		DESCRIPTION "Parameter Type = Internal.
			Indicates whether current throughput value
			has been loaded. Load all throughput values
			using scSysNodeControl(updateThroughput)."
		DEFVAL { updateThroughputReq }
		::=  { scNodeAccessEntry 3 }

scNodeAccessRootList 	OBJECT-TYPE
		SYNTAX    OCTET STRING (SIZE (0..32))
		ACCESS    read-write
		STATUS    mandatory
		DESCRIPTION "Parameter Type = Immediate.
			A list of up to 16 root nodes (2 bytes per node
			number) within the partition that have access
			to this node. This list is only used if the
			control mode is set to table access."
		::=  { scNodeAccessEntry 4 }

scNodeAccessChPrfList 	OBJECT-TYPE
		SYNTAX    OCTET STRING (SIZE (32))
		ACCESS    read-write
		STATUS    mandatory
		DESCRIPTION "Parameter Type = Immediate.
			A bit map representing which channel profiles
			(1-255) are assigned to this partition. The
			rightmost bit of the rightmost octet
			(lsb of the last byte), represents
			channel profile 1. A channel profile can be
			assigned to multiple partitions."
		::=  { scNodeAccessEntry 5 }

scNodeAccessThroughput 	OBJECT-TYPE
		SYNTAX    INTEGER
		ACCESS    read-write
		STATUS    mandatory
		DESCRIPTION "Parameter Type = Intrusive.
			Access bandwidth for this partition, in units
			of bps. This field is only used on a shared
			node."
		::=  { scNodeAccessEntry 6 }

scNodeAccessVoicePrfList 	OBJECT-TYPE
		SYNTAX    OCTET STRING (SIZE (32))
		ACCESS    read-write
		STATUS    mandatory
		DESCRIPTION "Parameter Type = Immediate.

			INTRODUCED 2.0.0

			A bit map representing which voice profiles
			(1-255) are assigned to this partition. The
			rightmost bit of the rightmost octet
			(lsb of the last byte), represents
			voice profile 1. A voice profile can be
			assigned to multiple partitions."
		::=  { scNodeAccessEntry 7 }

scNodeAccessLink2TraEntriesMin 	OBJECT-TYPE
		SYNTAX	INTEGER (0..1728)
		ACCESS	read-write
		STATUS	mandatory
		DESCRIPTION "Parameter Type = Immediate.

			INTRODUCED 2.0.0

			Defines the number of LINK translation table
			entries, that are reserved for this partition.
			The sum of the values of this attribute across
			all the partitions may not exceed the maximum
			number of entries available (1728).

			This attribute may be set only by the
			global user (partition 1)."
		DEFVAL { 0 }
		::= { scNodeAccessEntry 8 }

scNodeAccessLink2TraEntriesMax 	OBJECT-TYPE
		SYNTAX	INTEGER (0..1728)
		ACCESS	read-write
		STATUS	mandatory
		DESCRIPTION "Parameter Type = Immediate.

			INTRODUCED 2.0.0

			Defines the limit of the number of LINK
			translation table entries that may be used by
			this partition. This number of the LINK
			translation table entries may or may not be
			available for this partition, depending on the
			rest of the partitions user's activities.
			The sum of the values of this attribute across
			all the partitions may exceed the maximum number
			of entries available (1728).

			This attribute may be set only by the
			global user (partition 1)."
		DEFVAL { 1728 }
		::= { scNodeAccessEntry 9 }

-- Synchrony MIBViews

scCommunityTable 	OBJECT-TYPE
		SYNTAX    SEQUENCE OF ScCommunityEntry
		ACCESS    not-accessible
		STATUS    deprecated
		DESCRIPTION " "
		::=  { security 5 }

scCommunityEntry 	OBJECT-TYPE
		SYNTAX    ScCommunityEntry
		ACCESS    not-accessible
		STATUS    deprecated
		DESCRIPTION " "
		INDEX { scCommunityIndex }
		::=  { scCommunityTable 1 }

ScCommunityEntry         ::=  SEQUENCE {
                         scCommunityIndex
                                   RecordIndex,
                         scCommunityControlMode
                                   INTEGER,
                         scCommunityName
                                   DisplayString,
                         scCommunityscMap
                                   OCTET STRING,
                         scCommunityrecfMap
                                   OCTET STRING,
                         scCommunityrestMap
                                   OCTET STRING,
                         scCommunityrestatisticsMap
                                   OCTET STRING,
                         scCommunityalMap
                                   OCTET STRING
                         }

scCommunityIndex 	OBJECT-TYPE
		SYNTAX    RecordIndex
		ACCESS    read-only
		STATUS    deprecated
		DESCRIPTION "Parameter Type = Internal.
			Format is partition ID (1-1023):entry ID (1-5).
			Only 32 partitions can be entered, each with
			5 entries."
		::=  { scCommunityEntry 1 }

scCommunityControlMode 	OBJECT-TYPE
		SYNTAX    INTEGER {
                                   enable(1),
                                   disable(2),
                                   erase(3)
                                   }
		ACCESS    read-write
		STATUS    deprecated
		DESCRIPTION "Parameter Type = Immediate.
		     A community entry cannot be erased if it is
		     enabled. Community entry 1.1 cannot be disabled
		     or erased."
		::=  { scCommunityEntry 2 }

scCommunityName 	OBJECT-TYPE
		SYNTAX    DisplayString (SIZE (0..24))
		ACCESS    read-write
		STATUS    deprecated
		DESCRIPTION "Parameter Type = Immediate."
		DEFVAL { "public" }
		::=  { scCommunityEntry 3 }

scCommunityscMap 	OBJECT-TYPE
		SYNTAX    OCTET STRING (SIZE (11))
		ACCESS    read-write
		STATUS    deprecated
		DESCRIPTION "Parameter Type = Immediate.
			Represents which groups in the security MIB
			this community has access to. For each octet,
			1 means no access, 2 means read-only, and
			3 means read-write.

			OCTET 1: partition header
			OCTET 2: system profile
			OCTET 3: root access
			OCTET 4: node access
			OCTET 5: community
			OCTET 6: trap access
			OCTET 7: channel profile
			OCTET 8: softload
			OCTET 9: CPI access
			OCTET 10: modem port access
			OCTET 11: IP access."
		DEFVAL { '0303030303030303030303'h }
		::=  { scCommunityEntry 4 }

scCommunityrecfMap 	OBJECT-TYPE
		SYNTAX    OCTET STRING (SIZE (13))
		ACCESS    read-write
		STATUS    deprecated
		DESCRIPTION "Parameter Type = Immediate.
			Represents which groups in the resource
			configuration MIB this community has access to.
			For each octet, 1 means no access, 2 means
			read-only, and 3 means read-write.

			OCTET 1: partition header
			OCTET 2: node
			OCTET 3: nest
			OCTET 4: slot
			OCTET 5: module
			OCTET 6: port
			OCTET 7: bundle
			OCTET 8: INL
			OCTET 9: TDM channel
			OCTET 10: frame relay
			OCTET 11: ad10
			OCTET 12: ASM X.50, ADPCM, CELP
			OCTET 13: RTM port, RTM AD port."
		DEFVAL { '03030303030303030303030303'h }
		::=  { scCommunityEntry 5 }

scCommunityrestMap 	OBJECT-TYPE
		SYNTAX    OCTET STRING (SIZE (11))
		ACCESS    read-write
		STATUS    deprecated
		DESCRIPTION "Parameter Type = Immediate.
			Represents which groups in the resource status
			MIB this community has access to. For each
			octet, 1 means no access, 2 means read-only,
			and 3 means read-write.

			OCTET 1: node
			OCTET 2: nest
			OCTET 3: slot
			OCTET 4: module
			OCTET 5: port
			OCTET 6: bundle
			OCTET 7: INL
			OCTET 8: INL contents
			OCTET 9: channel
			OCTET 10: ad10
			OCTET 11: ASM X.50, ADPCM, CELP."
		DEFVAL { '0303030303030303030303'h }
		::=  { scCommunityEntry 6 }


scCommunityrestatisticsMap 	OBJECT-TYPE
		SYNTAX    OCTET STRING (SIZE (4))
		ACCESS    read-write
		STATUS    deprecated
		DESCRIPTION "Parameter Type = Immediate.
			Represents which groups in the resource
			statistics MIB this community has access to.
			For each octet, 1 means no access, 2 means
			read-only, and 3 means read-write.

			OCTET 1: port
			OCTET 2: channel
			OCTET 3: INL
			OCTET 4: ad10."
		DEFVAL { '03030303'h }
		::=  { scCommunityEntry 7 }

scCommunityalMap 	OBJECT-TYPE
		SYNTAX    OCTET STRING (SIZE (4))
		ACCESS    read-write
		STATUS    deprecated
		DESCRIPTION "Parameter Type = Immediate.
			Represents which groups in the alarm MIB
			this community has access to. For each octet,
			1 means no access, 2 means read-only, and
			3 means read-write.

			OCTET 1: partition header
			OCTET 2: alarm profile
			OCTET 3: log
			OCTET 4: log records."
		DEFVAL { '03030303'h }
		::=  { scCommunityEntry 8 }


-- Synchrony Trap Subscription List

scTrapAccessTable 	OBJECT-TYPE
		SYNTAX    SEQUENCE OF ScTrapAccessEntry
		ACCESS    not-accessible
		STATUS    mandatory
		DESCRIPTION " "
		::=  { security 6 }

scTrapAccessEntry 	OBJECT-TYPE
		SYNTAX    ScTrapAccessEntry
		ACCESS    not-accessible
		STATUS    mandatory
		DESCRIPTION " "
		INDEX { scTrapAccessIndex }
		::=  { scTrapAccessTable 1 }

ScTrapAccessEntry        ::=  SEQUENCE {
                         scTrapAccessIndex
                                   INTEGER,
                         scTrapAccessControlMode
                                   INTEGER,
                         scTrapAccessIp
                                   IpAddress
                          }

scTrapAccessIndex 	OBJECT-TYPE
		SYNTAX    INTEGER (1..8)
		ACCESS    read-only
		STATUS    mandatory
		DESCRIPTION "Parameter Type = Internal.
			Indicates which of up to 8 EMS stations will
			receive traps."
		::=  { scTrapAccessEntry 1 }

scTrapAccessControlMode 	OBJECT-TYPE
		SYNTAX    INTEGER {
                                   enable(1),
                                   disable(2),
                                   erase(3)
                                   }
		ACCESS    read-write
		STATUS    mandatory
		DESCRIPTION "Parameter Type = Immediate."
		DEFVAL { disable }
		::=  { scTrapAccessEntry 2 }

scTrapAccessIp 	OBJECT-TYPE
		SYNTAX    IpAddress
		ACCESS    read-write
		STATUS    mandatory
		DESCRIPTION "Parameter Type = Immediate."
		::=  { scTrapAccessEntry 3 }


-- Channel Profile Configuration

scChProfileTable 	OBJECT-TYPE
		SYNTAX    SEQUENCE OF ScChProfileEntry
		ACCESS    not-accessible
		STATUS    mandatory
		DESCRIPTION " "
		::=  { security 7 }

scChProfileEntry 	OBJECT-TYPE
		SYNTAX    ScChProfileEntry
		ACCESS    not-accessible
		STATUS    mandatory
		DESCRIPTION " "
		INDEX { scChProfileIndex }
		::=  { scChProfileTable 1 }

ScChProfileEntry        ::=  SEQUENCE {
                         scChProfileIndex
                                   INTEGER,
                         scChProfileControlMode
                                   INTEGER,
                         scChProfileCostType
                                   INTEGER,
                         scChProfileMaxCost
                                   INTEGER,
                         scChProfilePriority
                                   INTEGER,
                         scChProfileEncryption
                                   INTEGER,
                         scChProfileMaxSatHop
                                   INTEGER,
                         scChProfileErrPerformReq
                                   INTEGER,
                         scChProfileINLGroup
                                   INTEGER,
                         scChProfileOverrideMode
                                   INTEGER,
                         scChProfileRetryTimer
                                   INTEGER,
                         scChProfileInfoAlarmGen
                                   INTEGER
                          }

scChProfileIndex 	OBJECT-TYPE
		SYNTAX    INTEGER (1..255)
		ACCESS    read-only
		STATUS    mandatory
		DESCRIPTION "Parameter Type = Internal."
		::= { scChProfileEntry 1 }

scChProfileControlMode 	OBJECT-TYPE
		SYNTAX    INTEGER {
                                   enable(1),
                                   disable(2),
                                   erase(3)
                                   }
		ACCESS    read-write
		STATUS    mandatory
		DESCRIPTION "Parameter Type = Immediate."
		::= { scChProfileEntry 2 }

scChProfileCostType 	OBJECT-TYPE
		SYNTAX    INTEGER {
                                   hops(1),
                                   userDesignatedCost(2),
                                   queuingDelay(3),
                                   delayAndCost(4)
                                   }
		ACCESS    read-write
		STATUS    mandatory
		DESCRIPTION "Parameter Type = Immediate."
		DEFVAL { hops }
		::= { scChProfileEntry 3 }

scChProfileMaxCost 	OBJECT-TYPE
		SYNTAX    INTEGER
		ACCESS    read-write
		STATUS    mandatory
		DESCRIPTION "Parameter Type = Immediate."
		DEFVAL { 16 }
		::= { scChProfileEntry 4 }

scChProfilePriority 	OBJECT-TYPE
		SYNTAX    INTEGER (1..16)
		ACCESS    read-write
		STATUS    mandatory
		DESCRIPTION "Parameter Type = Immediate."
		DEFVAL { 1 }
		::= { scChProfileEntry 5 }

scChProfileEncryption 	OBJECT-TYPE
		SYNTAX    INTEGER {
                                   doNotCare(1),
                                   required(2)
                                   }
		ACCESS    read-write
		STATUS    mandatory
		DESCRIPTION "Parameter Type = Immediate."
		DEFVAL { doNotCare }
		::= { scChProfileEntry 6 }

scChProfileMaxSatHop 	OBJECT-TYPE
		SYNTAX    INTEGER (0..5)
		ACCESS    read-write
		STATUS    mandatory
		DESCRIPTION "Parameter Type = Immediate."
		DEFVAL { 0 }
		::= { scChProfileEntry 7 }

scChProfileErrPerformReq 	OBJECT-TYPE
		SYNTAX    INTEGER (4..9)
		ACCESS    read-write
		STATUS    mandatory
		DESCRIPTION "Parameter Type = Immediate.
			Error performance requirement (x) used as
			10E-(x). Range 10E-4 to 10E-9."
		DEFVAL { 6 }
		::= { scChProfileEntry 8 }

scChProfileINLGroup 	OBJECT-TYPE
		SYNTAX    INTEGER (0..7)
		ACCESS    read-write
		STATUS    mandatory
		DESCRIPTION "Parameter Type = Immediate.
			0 means do not care."
		DEFVAL { 0 }
		::= { scChProfileEntry 9 }

scChProfileOverrideMode 	OBJECT-TYPE
		SYNTAX    INTEGER {
                                   enable(1),
                                   disable(2)
                                   }
		ACCESS    read-write
		STATUS    mandatory
		DESCRIPTION "Parameter Type = Immediate."
		DEFVAL { enable }
		::= { scChProfileEntry 10 }

scChProfileRetryTimer 	OBJECT-TYPE
		SYNTAX    INTEGER (1..60)
		ACCESS    read-write
		STATUS    mandatory
		DESCRIPTION "Parameter Type = Immediate.
			Each unit represents 5 seconds. Retry
			range is 5 seconds to 5 minutes."
		DEFVAL { 6 }
		::= { scChProfileEntry 11 }

scChProfileInfoAlarmGen 	OBJECT-TYPE
		SYNTAX    INTEGER {
			   enable(1),
			   disable(2)
			   }
		ACCESS    read-write
		STATUS    mandatory
		DESCRIPTION "Parameter Type = Immediate.
			Indicates whether channel alarms of severity
			info will be generated or not."
		DEFVAL { disable }
		::= { scChProfileEntry 12 }


-- Softload Entry

scSoftloadEntry			OBJECT IDENTIFIER ::= { security 8 }

scSoftloadControl 	OBJECT-TYPE
		SYNTAX  INTEGER {
			    startDownload(1),
			    onlineCopy(2),
			    startDownloadToRecovery(3)
			}
		ACCESS  write-only
		STATUS  mandatory
		DESCRIPTION "Parameter Type = Immediate.
		    <startDownload> is the command to initiate
		    download from EMS, local CPS, or another ST
		    node to online FLASH memory location.

		    <onlineCopy> is the command to initiate
		    online image copy from offline FLASH memory
		    location (not mapped by the NCP map file)
		    to the online one (mapped by the NCP map
		    file).

		    <startDownloadToRecovery> is the command to
		    initiate download from EMS, local CPS, or
		    another ST node to offline FLASH memory
		    location."
		::=  { scSoftloadEntry 1 }

scSoftloadFileName 	OBJECT-TYPE
		SYNTAX    DisplayString (SIZE (1..32))
		ACCESS    read-write
		STATUS    mandatory
		DESCRIPTION "Parameter Type = Immediate.
			Specifies the file on EMS or CPS station to be
			downloaded into NCP program store. The type of
			code in the file is indicated by
			scSoftloadSoftwareType."
		::=  { scSoftloadEntry 2 }

scSoftloadDirectoryName 	OBJECT-TYPE
		SYNTAX    DisplayString (SIZE (1..32))
		ACCESS    read-write
		STATUS    mandatory
		DESCRIPTION "Parameter Type = Immediate.
			Specifies the directory path where the file
			that is to be downloaded resides on the EMS
			or CPS station."
		::=  { scSoftloadEntry 3 }

scSoftloadDestPort 	OBJECT-TYPE
		SYNTAX    PortAddr
		ACCESS    read-write
		STATUS    mandatory
		DESCRIPTION "Parameter Type = Immediate.
			Destination module/port for downloading
			software. If module address, then format is
			nest:slot:0. If the address is 0:0:0, then the
			file will be downloaded to the active NCP."
		::=  { scSoftloadEntry 4 }

scSoftloadSoftwareType 	OBJECT-TYPE
		SYNTAX    INTEGER {
                                   ncp(1),
                                   t1m(5),
                                   e1m(6),
                                   sgm(7),
                                   lgm(8),
                                   asm(9),
                                   fsm(11),
                                   sdm(12),
				   rtm(14),
				   dsm(19),
				   e3m(20),
				   ad10(128),
                                   tableOC(254),
                                   mibSchema(252),
                                   stDatabase(255),
				   ad10Database(251),
				   rtmAdDatabase(253)
                                   }
		ACCESS    read-write
		STATUS    mandatory
		DESCRIPTION "Parameter Type = Immediate.
			Identifies the module type for downloading
			software or database image."
		::=  { scSoftloadEntry 5 }

scSoftloadEmsNodeID 	OBJECT-TYPE
		SYNTAX    NodeAddr
		ACCESS    read-write
		STATUS    mandatory
		DESCRIPTION "Parameter Type = Immediate.
			Root node ID for the source EMS or ST node.
			Only used if scSoftloadSourceEmsIp is not
			1.0.0.0."
		::=  { scSoftloadEntry 6 }

scSoftloadSourceEmsIp 	OBJECT-TYPE
		SYNTAX    IpAddress
		ACCESS    read-write
		STATUS    mandatory
		DESCRIPTION "Parameter Type = Immediate.
			Indicates the download server. If the value is
			1.0.0.0, then CPS is being used. If value is
			2.0.0.0, then another ST node is being used,
			whose node ID is specified in
			scSoftloadEmsNodeID. Otherwise, the EMS is
			being used, with access through the root node
			specified in scSoftloadEmsNodeID."
		::=  { scSoftloadEntry 7 }

scSoftloadTimeout 	OBJECT-TYPE
		SYNTAX    INTEGER (1..300)
		ACCESS    read-write
		STATUS    mandatory
		DESCRIPTION "Parameter Type = Immediate.
		 	In units of seconds."
		DEFVAL { 120 }
		::=  { scSoftloadEntry 8 }


-- CPI Access Control

scCpiAccess 	OBJECT IDENTIFIER ::= { security 9 }

scCpiControl 	OBJECT-TYPE
		SYNTAX    INTEGER {
				resetCpiPort(3),
				logoff(40)
                          }
		ACCESS    write-only
		STATUS    mandatory
		DESCRIPTION "Parameter Type = Immediate.
			Log off will terminate a session that was
			enabled by entering a password. If password
			control is disabled, then the command will do
			nothing.

			Reset will load the new CPI port settings. As
			a side effect, the current session will be
			logged off."
		::= { scCpiAccess 1 }

scCpiControlUpdate 	OBJECT-TYPE
		SYNTAX    INTEGER {
				loaded(1),
				resetReq(3)
                          }
		ACCESS    read-only
		STATUS    mandatory
		DESCRIPTION "Parameter Type = Internal."
		DEFVAL { resetReq }
		::= { scCpiAccess 2 }

scCpiSpeed 	OBJECT-TYPE
		SYNTAX    INTEGER {
                                   a2400(1),
                                   a4800(2),
                                   a9600(3),
                                   a14400(4),
                                   a19200(5)
                                   }
		ACCESS    read-write
		STATUS    mandatory
		DESCRIPTION "Parameter Type = Intrusive.
			In units of bps."
		DEFVAL { a9600 }
                         ::= { scCpiAccess 3 }

scCpiDataBits 	OBJECT-TYPE
		SYNTAX    INTEGER {
                                   b7(1),
                                   b8(2)
                                   }
		ACCESS    read-write
		STATUS    mandatory
		DESCRIPTION "Parameter Type = Intrusive."
		DEFVAL { b8 }
		::= { scCpiAccess 4 }

scCpiParity 	OBJECT-TYPE
		SYNTAX    INTEGER {
                                   noParity(1),
                                   even(3),
                                   odd(2)
                                   }
		ACCESS    read-write
		STATUS    mandatory
		DESCRIPTION "Parameter Type = Intrusive."
		DEFVAL { noParity }
		::= { scCpiAccess 5 }

scCpiStopBits 	OBJECT-TYPE
		SYNTAX    INTEGER {
                                   b1(1),
                                   b2(2)
                                   }
		ACCESS    read-write
		STATUS    mandatory
		DESCRIPTION "Parameter Type = Intrusive."
		DEFVAL { b1 }
		::= { scCpiAccess 6 }


-- Modem Port Access Control

scModemAccess 	OBJECT IDENTIFIER ::= { security 10 }

scModemControl 	OBJECT-TYPE
		SYNTAX    INTEGER {
				enableCpsSession(1),
				resetModemPort(3),
				logoff(40)
			  }
		ACCESS    write-only
		STATUS    mandatory
		DESCRIPTION "Parameter Type = Immediate.
			Log off will terminate a session that was
			enabled by entering a password. If password
			control is disabled, then the command will do
			nothing.

			Reset will load the new CPI port settings. As
			a side effect, the current session will be
			logged off.

			Enable CPS session will switch the modem port
			from SLIP mode to CPI mode. The mode will be
			changed back to SLIP after a nodal power cycle
			or a reset modem port command."
		::= { scModemAccess 1 }

scModemControlUpdate 	OBJECT-TYPE
		SYNTAX    INTEGER {
				loaded(1),
				resetReq(3)
			  }
		ACCESS    read-only
		STATUS    mandatory
		DESCRIPTION "Parameter Type = Internal."
		DEFVAL { resetReq }
		::= { scModemAccess 2 }

scModemSpeed 	OBJECT-TYPE
		SYNTAX    INTEGER {
                                   a2400(1),
                                   a4800(2),
                                   a9600(3),
                                   a14400(4),
                                   a19200(5)
                                   }
		ACCESS    read-write
		STATUS    mandatory
		DESCRIPTION "Parameter Type = Intrusive."
		DEFVAL { a9600 }
		::= { scModemAccess 3 }

scModemDataBits 	OBJECT-TYPE
		SYNTAX    INTEGER {
                                   b8(2)
                                   }
		ACCESS    read-only
		STATUS    mandatory
		DESCRIPTION "Parameter Type = Intrusive."
		DEFVAL { b8 }
		::= { scModemAccess 4 }

scModemParity 	OBJECT-TYPE
		SYNTAX    INTEGER {
                                   noParity(1),
                                   even(3),
                                   odd(2)
                                   }
		ACCESS    read-write
		STATUS    mandatory
		DESCRIPTION "Parameter Type = Intrusive."
		DEFVAL { noParity }
		::= { scModemAccess 5 }

scModemStopBits 	OBJECT-TYPE
		SYNTAX    INTEGER {
                                   b1(1),
                                   b2(2)
                                   }
		ACCESS    read-write
		STATUS    mandatory
		DESCRIPTION "Parameter Type = Intrusive."
		DEFVAL { b1 }
		::= { scModemAccess 6 }

scModemControlLead 	OBJECT-TYPE
		SYNTAX    INTEGER {
				eIA(1),
				noEIA(2)
			  }
		ACCESS    read-write
		STATUS    mandatory
		DESCRIPTION "Parameter Type = Intrusive.
			This field is not currently used."
		DEFVAL { noEIA }
		::= { scModemAccess 7 }



-- IP Access Control for Root Node

scIpAccess 	OBJECT IDENTIFIER ::= { security 11 }

scIpProfile 	OBJECT IDENTIFIER ::= { scIpAccess 1 }

scIpControl 	OBJECT-TYPE
		SYNTAX    INTEGER {
				resetIp(1)
			  }
		ACCESS    write-only
		STATUS    mandatory
		DESCRIPTION "Parameter Type = Immediate."
		::= { scIpProfile 1 }

scIpControlUpdate 	OBJECT-TYPE
		SYNTAX    INTEGER {
                                   loaded(1),
				   resetReq(3)
                                   }
		ACCESS    read-only
		STATUS    mandatory
		DESCRIPTION "Parameter Type = Internal.
			Indicates changes to both the IP profile
			and the IP offline subnet table."
		DEFVAL { resetReq }
		::= { scIpProfile 2 }

scIpWANIpAddress 	OBJECT-TYPE
		SYNTAX    IpAddress
		ACCESS    read-only
		STATUS    mandatory
		DESCRIPTION "Parameter Type = Internal."
		::= { scIpProfile 3 }

scIpSubNetworkMask 	OBJECT-TYPE
		SYNTAX    IpAddress
		ACCESS    read-write
		STATUS    mandatory
		DESCRIPTION "Parameter Type = Intrusive.
			Network ID mask for ST-50 network."
		::= { scIpProfile 4 }

scIpRootGatewayIp 	OBJECT-TYPE
		SYNTAX    IpAddress
		ACCESS    read-write
		STATUS    mandatory
		DESCRIPTION "Parameter Type = Intrusive.
			Root node Ethernet port IP address."
		::= { scIpProfile 5 }

scIpRootGatewayMask 	OBJECT-TYPE
		SYNTAX    IpAddress
		ACCESS    read-write
		STATUS    mandatory
		DESCRIPTION "Parameter Type = Intrusive.
			Network mask for root node's Ethernet port.
			This is the mask for the user's IP network."
		::= { scIpProfile 6 }

scIpRootGatewayEthernet 	OBJECT-TYPE
		SYNTAX    INTEGER {
				ethernetII(2),
				e802d3(1)
			  }
		ACCESS    read-write
		STATUS    mandatory
		DESCRIPTION "Parameter Type = Intrusive.
			Specifies the Ethernet protocol of the user's
			IP network."
		DEFVAL { ethernetII }
		::= { scIpProfile 7 }

scIpDefaultExtGateway 	OBJECT-TYPE
		SYNTAX    IpAddress
		ACCESS    read-write
		STATUS    mandatory
		DESCRIPTION "Parameter Type = Intrusive.
			Default gateway IP address used by the root
			node."
		::= { scIpProfile 8 }

scIpSlipAddress OBJECT-TYPE
		SYNTAX    IpAddress
		ACCESS    read-write
		STATUS    mandatory
		DESCRIPTION "Parameter Type = Intrusive.
			IP address of the SLIP interface on the
			modem port."
		::= { scIpProfile 9 }

scIpSlipMask 	OBJECT-TYPE
		SYNTAX    IpAddress
		ACCESS    read-write
		STATUS    mandatory
		DESCRIPTION "Parameter Type = Intrusive.
			IP mask of the SLIP interface on the
			modem port."
		::= { scIpProfile 10 }



scIpOnlineSubnetTable 	OBJECT-TYPE
		SYNTAX    SEQUENCE OF ScIpOnlineSubnetEntry
		ACCESS    not-accessible
		STATUS    mandatory
		DESCRIPTION " "
		::=  { scIpAccess 2 }

scIpOnlineSubnetEntry 	OBJECT-TYPE
		SYNTAX    ScIpOnlineSubnetEntry
		ACCESS    not-accessible
		STATUS    mandatory
		DESCRIPTION " "
		INDEX { scIpOnlineSubnetIndex }
		::=  { scIpOnlineSubnetTable 1 }

ScIpOnlineSubnetEntry   ::=  SEQUENCE {
			scIpOnlineSubnetIndex
				INTEGER,
			scIpOnlineSubnetAddr
				IpAddress
                          }

scIpOnlineSubnetIndex 	OBJECT-TYPE
		SYNTAX    INTEGER (1..8)
		ACCESS    read-only
		STATUS    mandatory
		DESCRIPTION "Parameter Type = Internal."
		::=  { scIpOnlineSubnetEntry 1 }

scIpOnlineSubnetAddr 	OBJECT-TYPE
		SYNTAX    IpAddress
		ACCESS    read-only
		STATUS    mandatory
		DESCRIPTION "Parameter Type = Internal."
		::=  { scIpOnlineSubnetEntry 2 }

scIpOfflineSubnetTable 	OBJECT-TYPE
		SYNTAX    SEQUENCE OF ScIpOfflineSubnetEntry
		ACCESS    not-accessible
		STATUS    mandatory
		DESCRIPTION " "
		::=  { scIpAccess 3 }

scIpOfflineSubnetEntry 	OBJECT-TYPE
		SYNTAX    ScIpOfflineSubnetEntry
		ACCESS    not-accessible
		STATUS    mandatory
		DESCRIPTION " "
		INDEX { scIpOfflineSubnetIndex }
		::=  { scIpOfflineSubnetTable 1 }

ScIpOfflineSubnetEntry   ::=  SEQUENCE {
                                scIpOfflineSubnetIndex
                                        INTEGER,
                                scIpOfflineSubnetControl
                                        INTEGER,
                                scIpOfflineSubnetAddr
                                        IpAddress
                          }

scIpOfflineSubnetIndex 	OBJECT-TYPE
		SYNTAX    INTEGER (1..8)
		ACCESS    read-only
		STATUS    mandatory
		DESCRIPTION "Parameter Type = Internal."
		::=  { scIpOfflineSubnetEntry 1 }

scIpOfflineSubnetControl 	OBJECT-TYPE
		SYNTAX    INTEGER {
				erase(3)
			   }
		ACCESS    write-only
		STATUS    mandatory
		DESCRIPTION "Parameter Type = Intrusive."
		::=  { scIpOfflineSubnetEntry 2 }

scIpOfflineSubnetAddr 	OBJECT-TYPE
		SYNTAX    IpAddress
		ACCESS    read-write
		STATUS    mandatory
		DESCRIPTION "Parameter Type = Intrusive."
		::=  { scIpOfflineSubnetEntry 3 }

-- Routing table for LGM Applications

scLgmStaticRouteTable 	OBJECT-TYPE
		SYNTAX	SEQUENCE OF ScLgmStaticRouteEntry
		ACCESS	not-accessible
		STATUS	mandatory
		DESCRIPTION " "
		::= { security 12 }

scLgmStaticRouteEntry 	OBJECT-TYPE
		SYNTAX	ScLgmStaticRouteEntry
		ACCESS	not-accessible
		STATUS	mandatory
		DESCRIPTION " "
		INDEX { scLgmStaticRouteNode,
			scLgmStaticRouteIndex }
		::= { scLgmStaticRouteTable  1 }

ScLgmStaticRouteEntry  		::= SEQUENCE 	{
		    			scLgmStaticRouteNode
			   			NodeAddr,
		       			scLgmStaticRouteIndex
				    		INTEGER,
		    			scLgmStaticRouteStartMode
		  	 			INTEGER,
		    			scLgmStaticRouteNextIafHop
			   			INTEGER,
		    			scLgmStaticRouteLink2GwyNode
			   			NodeAddr,
		    			scLgmStaticRoutePathDelay
			   			INTEGER
			       	}

scLgmStaticRouteNode 	OBJECT-TYPE
		SYNTAX	NodeAddr
		ACCESS	read-only
		STATUS	mandatory
		DESCRIPTION  "Parameter Type = Internal.
			Routing destination node number."
		::= { scLgmStaticRouteEntry 1 }

scLgmStaticRouteIndex 	OBJECT-TYPE
		SYNTAX	INTEGER (1..32)
		ACCESS  read-only
		STATUS  mandatory
		DESCRIPTION "Parameter Type = Internal.
			Specifies a route entry number in
			the routing table for given node."
		::= { scLgmStaticRouteEntry 2 }

scLgmStaticRouteStartMode 	OBJECT-TYPE
		SYNTAX	INTEGER {
			automatic(1),
			off(2),
			erase(3)
			}
		ACCESS  read-write
		STATUS 	mandatory
		DESCRIPTION "Parameter Type = Immediate.
			Setting to off will prevent this
			table entry from being used on
			routing (invalidates it).
			Setting to erase will free the entry."
		DEFVAL { off }
		::= { scLgmStaticRouteEntry 3 }

scLgmStaticRouteNextIafHop 	OBJECT-TYPE
		SYNTAX  INTEGER (1..32767)
		ACCESS	read-write
		STATUS	mandatory
		DESCRIPTION "Parameter Type = Immediate.
			Specifies next hop along given route.
			The hops are presented in terms of
			Link-2 IAFs. It is, in fact, LGM port
			number (server type 132 without further
			specification of a group ID), which
			is local to this node."
		::= { scLgmStaticRouteEntry 4 }

scLgmStaticRouteLink2GwyNode 	OBJECT-TYPE
		SYNTAX	NodeAddr
		ACCESS	read-write
		STATUS  mandatory
		DESCRIPTION "Parameter Type = Immediate.
    			Specifies Link-2 gateway node (node
			which has a LGM module) to get
			access into Link-2 subnetwork."
		::= { scLgmStaticRouteEntry 5 }

scLgmStaticRoutePathDelay 	OBJECT-TYPE
		SYNTAX	INTEGER (0..7)
		ACCESS	read-write
		STATUS 	mandatory
		DESCRIPTION "Parameter Type = Immediate.
			Defines the number of Link-2
			nodes (non-ST-50 hops) to this node.
			No ST-50 INLs are counted."
		::= { scLgmStaticRouteEntry 6 }


-- Voice Profile MIB

scVoicePrf 	OBJECT IDENTIFIER ::= { security 13 }

-- Voice Profile Network Wide MIB

scVoicePrfNetTable 	OBJECT-TYPE
		SYNTAX  SEQUENCE OF ScVoicePrfNetEntry
		ACCESS  not-accessible
		STATUS  mandatory
		DESCRIPTION "Voice profile entries in this table
			will serve as a network wide profile for
			multiple voice connections across the
			network. Even though it is not enforced
			by the node, it is suggested  that such
			enforcement be provided by Network
			Management.

			A given index refers to the same voice
			profile in both this MIB section and
			scVoicePrfNodeTable.  When a new voice
			profile is created in one section it
			will also be created with the proper
			default values in the other.

			Entry number one in this table shall
			always exist on the node.  It will be
			initialized with all default values of
			this section except
			scVoicePrfNetControlMode shal be enable.
			This entry cannot be disabled or erased.

			Changes for all entries will take effect
			immediately on new connections. However,
			they will not affect channels that are
			already connected."
		::= { scVoicePrf 1 }

scVoicePrfNetEntry 	OBJECT-TYPE
		SYNTAX  ScVoicePrfNetEntry
		ACCESS  not-accessible
		STATUS  mandatory
		DESCRIPTION "INTRODUCED 2.0.0"
		INDEX   { scVoicePrfNetIndex }
		::= { scVoicePrfNetTable 1 }

ScVoicePrfNetEntry   	::= SEQUENCE {
			scVoicePrfNetIndex
				INTEGER,
			scVoicePrfNetControlMode
				INTEGER,
			scVoicePrfNetCompressMode
				INTEGER,
			scVoicePrfNetSpeed
				INTEGER,
			scVoicePrfNetDTMFRelay
				INTEGER,
			scVoicePrfNetFaxRelay
				INTEGER,
			scVoicePrfNetFaxNSFMode
				INTEGER,
			scVoicePrfNetVocoderEnable
				INTEGER,
			scVoicePrfNetDataMode
				INTEGER,
			scVoicePrfNetSignalingType
				INTEGER,
			scVoicePrfNetSigIdlePttrn
				INTEGER
			}

scVoicePrfNetIndex 	OBJECT-TYPE
		SYNTAX  INTEGER (1..255)
		ACCESS  read-only
		STATUS  mandatory
		DESCRIPTION "Parameter Type = Internal.
			Index of the voice profile entry."
		::= { scVoicePrfNetEntry 1 }

scVoicePrfNetControlMode 	OBJECT-TYPE
		SYNTAX  INTEGER {
			enable(1),
			disable(2),
			erase(3)
			}
		ACCESS  read-write
		STATUS  mandatory
		DESCRIPTION "Parameter Type = Immediate.
			Disable will prevent this
			voice profile from being applied
			to the any new voice connections.

			Erase will remove this voice
			profile from the table."
		DEFVAL { disable }
		::= { scVoicePrfNetEntry 2 }

scVoicePrfNetCompressMode 	OBJECT-TYPE
		SYNTAX  INTEGER {
			tCelp(1),
			atc(2),
			adpcm(3),
			pcm(255)
			}
		ACCESS  read-write
		STATUS  mandatory
		DESCRIPTION "Parameter Type = Immediate.
			Defines which compression algorithm to
			use for voice channels connected using
			this voice profile."
		DEFVAL { pcm }
		::= { scVoicePrfNetEntry 3 }

scVoicePrfNetSpeed 	OBJECT-TYPE
		SYNTAX  INTEGER {
			    b5333(40), b7200(54), b7466(56),
			    b8000(60), b8533(64), b9066(68),
			    b9600(72), b10133(76), b10666(80),
			    b11200(84), b11733(88), b12266(92),
			    b12800(96), b13333(100),
			    b13866(104), b14400(108),
			    b14933(112), b15466(116),
			    b16000(120), b16533(124),
			    b17066(128), b17600(132),
			    b18133(136), b18666(140),
			    b19200(144), b19733(148),
			    b20266(152), b20800(156),
			    b21333(160), b21866(164),
			    b22400(168), b22933(172),
			    b23466(176), b24000(180),
			    b24533(184), b25066(188),
			    b25600(192), b26133(196),
			    b26666(200), b27200(204),
			    b27733(208), b28266(212),
			    b28800(216), b29333(220),
			    b29866(224), b30400(228),
			    b30933(232), b31466(236),
			    b31733(238), b32000(240),
			    b36000(270), b64000(480)
			}
		ACCESS  read-write
		STATUS  mandatory
		DESCRIPTION "Parameter Type = Immediate.
			The compressed channel data rate for
			any voice subrate connections using
			this voice profile.

			For channels using a CELP compression
			algorithm, only speeds of 5.333 Kbps,
			7.2 Kbps, 8 Kbps, and 9.6 Kbps will be
			supported.

			For channels using the ATC compression
			algorithm, only the speeds between
			7.466 Kbps and 32 Kbps (in increments of
			533 bps) is supported.

			For channels using the ADPCM compression
			algorithm, only the speeds 31.733 and
			32.000 Kbps is supported.

			For channels using PCM (uncompressed
			mode), only the speed of 64 Kbps is
			supported."
		DEFVAL { b64000 }
		::= { scVoicePrfNetEntry 4 }

scVoicePrfNetDTMFRelay 	OBJECT-TYPE
		SYNTAX  INTEGER {
			enable(2),
			disable(1)
			}
		ACCESS  read-write
		STATUS  mandatory
		DESCRIPTION "Parameter Type = Immediate.
			Controls the DTMF relay on any voice
			connections that use this voice
			profile. When enabled, DTMF signals are
			transferred through the connection.

			Not applicable in PCM and ADPCM mode."
		DEFVAL { enable }
		::= { scVoicePrfNetEntry 5 }

scVoicePrfNetFaxRelay 	OBJECT-TYPE
		SYNTAX  INTEGER {
			enable(2),
			disable(1)
			}
		ACCESS  read-write
		STATUS  mandatory
		DESCRIPTION "Parameter Type = Immediate.
			Controls the fax relay on any voice
			connections that use this voice
			profile. When enabled, fax operation
			will be supported over the connection.

			Not applicable in PCM and ADPCM mode."
		DEFVAL { enable }
		::= { scVoicePrfNetEntry 6 }

scVoicePrfNetFaxNSFMode 	OBJECT-TYPE
		SYNTAX  INTEGER {
			enable(2),
			disable(1)
			}
		ACCESS  read-write
		STATUS  mandatory
		DESCRIPTION "Parameter Type = Immediate.
			Controls the non-standard fax mode on
			any voice connections that use this
			voice profile.

			Not applicable in PCM and ADPCM mode."
		DEFVAL { disable }
		::= { scVoicePrfNetEntry 7 }

scVoicePrfNetVocoderEnable 	OBJECT-TYPE
		SYNTAX  INTEGER {
			normal(1),
			disable(2)
			}
		ACCESS  read-write
		STATUS  mandatory
		DESCRIPTION "Parameter Type = Immediate.
			Controls the vocoder mode on any
			voice connections that use this voice
			profile.

			Not applicable in PCM and ADPCM mode."
		DEFVAL { normal }
		::= { scVoicePrfNetEntry 8 }

scVoicePrfNetDataMode 	OBJECT-TYPE
		SYNTAX  INTEGER {
			enable(2),
			disable(1)
			}
		ACCESS  read-write
		STATUS  mandatory
		DESCRIPTION "Parameter Type = Immediate.
			Controls the 2100 Hz detection logic
			and data mode operation with the ATC
			vocoder on any voice connections
			that use this voice profile.

			Applies only for ATC mode."
		DEFVAL { disable }
		::= { scVoicePrfNetEntry 9 }

scVoicePrfNetSignalingType 	OBJECT-TYPE
		SYNTAX  INTEGER {
			none(1),
			a(2),
			ab(3),
			abcd(4),
			ac15-dtmf(8),
			ac15-dp(9)
			}
		ACCESS  read-write
		STATUS  mandatory
		DESCRIPTION "Parameter Type = Immediate.
			The type of signaling used by the
			T1M/E1M bundles that connect to voice
			ports using this voice profile."
		DEFVAL { none }
		::= { scVoicePrfNetEntry 10 }

scVoicePrfNetSigIdlePttrn 	OBJECT-TYPE
		SYNTAX	INTEGER {
			a0-b0-c0-d0(16),
			a0-b0-c0-d1(8),
			a0-b0-c1-d0(4),
			a0-b0-c1-d1(12),
			a0-b1-c0-d0(2),
			a0-b1-c0-d1(10),
			a0-b1-c1-d0(6),
			a0-b1-c1-d1(14),
			a1-b0-c0-d0(1),
			a1-b0-c0-d1(9),
			a1-b0-c1-d0(5),
			a1-b0-c1-d1(13),
			a1-b1-c0-d0(3),
			a1-b1-c0-d1(11),
			a1-b1-c1-d0(7),
			a1-b1-c1-d1(15)
			}
		ACCESS  read-write
		STATUS  mandatory
		DESCRIPTION "Parameter Type = Immediate.
			Defines the idle signaling pattern on
			any ASM voice ports that use this voice
			profile. This pattern is delivered to
			receive signal channel connections at
			times prior to the availability of a
			verified reliable signal channel
			source."
		DEFVAL { a0-b0-c0-d0 }
		::= { scVoicePrfNetEntry 11 }


-- Voice Profile Nodal MIB

scVoicePrfNodeTable 	OBJECT-TYPE
		SYNTAX  SEQUENCE OF ScVoicePrfNodeEntry
		ACCESS  not-accessible
		STATUS  mandatory
		DESCRIPTION "Voice profile entries in this table
			will serve as a nodal part of profile
			for voice connections. It is
			intended for individual fine adjustment
			of the voice parameters on each end of
			the connection.

			A given index refers to the same voice
			profile in both this MIB section and
			scVoicePrfNetTable.  When a new voice
			profile is created in one section it
			will also be created with the proper
			default values in the other.

			Changes for all entries will take effect
			immediately on new connections. However,
			they will not affect channels that
			are already connected."
		::= { scVoicePrf 2 }

scVoicePrfNodeEntry 	OBJECT-TYPE
		SYNTAX  ScVoicePrfNodeEntry
		ACCESS  not-accessible
		STATUS  mandatory
		DESCRIPTION "INTRODUCED 2.0.0"
		INDEX   { scVoicePrfNodeIndex }
		::= { scVoicePrfNodeTable 1 }

ScVoicePrfNodeEntry         	::= SEQUENCE {
			scVoicePrfNodeIndex
				INTEGER,
			scVoicePrfNodeRdnGrpId
				INTEGER,
			scVoicePrfNodeTxAudSrcMode
				INTEGER,
			scVoicePrfNodeRxAudOutMode
				INTEGER,
			scVoicePrfNodeEchoCancel
				INTEGER,
			scVoicePrfNodeNonLinear
				INTEGER,
			scVoicePrfNodeTxPCMGain
				INTEGER,
			scVoicePrfNodeRxPCMGain
				INTEGER,
			scVoicePrfNodePCMPhasorSize
				INTEGER,
			scVoicePrfNodeSubratePhSize
				INTEGER,
			scVoicePrfNodeNetSigMode
				INTEGER
			}

scVoicePrfNodeIndex 	OBJECT-TYPE
		SYNTAX  INTEGER (1..255)
		ACCESS  read-only
		STATUS  mandatory
		DESCRIPTION "Parameter Type = Internal.
			Index of the voice profile entry."
		::= { scVoicePrfNodeEntry 1 }

scVoicePrfNodeRdnGrpId 	OBJECT-TYPE
		SYNTAX    INTEGER (1..64)
		ACCESS    read-write
		STATUS    mandatory
		DESCRIPTION "Parameter Type = Immediate.
			Specifies the redundancy group value
			of the server module that the voice
			port will be allocated on."
		DEFVAL { 1 }
		::= { scVoicePrfNodeEntry 2 }

scVoicePrfNodeTxAudSrcMode 	OBJECT-TYPE
		SYNTAX  INTEGER {
			normal(1),
			silence(2),
			toneDMW(3)
			}
		ACCESS  read-write
		STATUS  mandatory
		DESCRIPTION "Parameter Type = Immediate.
			Controls the transmit audio source on
			any voice connections that use this
			voice profile.

			Not applicable in PCM mode."
		DEFVAL { normal }
		::= { scVoicePrfNodeEntry 3 }

scVoicePrfNodeRxAudOutMode 	OBJECT-TYPE
		SYNTAX  INTEGER {
			normal(1),
			silence(2),
			toneDMW(3)
			}
		ACCESS  read-write
		STATUS  mandatory
		DESCRIPTION "Parameter Type = Immediate.
			Controls the receive audio output on
			any voice connections that use this
			voice profile.

			Not applicable in PCM mode."
		DEFVAL { normal }
		::= { scVoicePrfNodeEntry 4 }

scVoicePrfNodeEchoCancel 	OBJECT-TYPE
		SYNTAX  INTEGER {
			enable(2),
			disable(1)
			}
		ACCESS  read-write
		STATUS  mandatory
		DESCRIPTION "Parameter Type = Immediate.
			Controls the echo cancellation on any
			voice connections that use this
			voice profile.

			Not applicable in PCM and ADPCM mode."
		DEFVAL { enable }
		::= { scVoicePrfNodeEntry 5 }

scVoicePrfNodeNonLinear 	OBJECT-TYPE
		SYNTAX  INTEGER {
			enable(2),
			disable(1)
			}
		ACCESS  read-write
		STATUS  mandatory
		DESCRIPTION "Parameter Type = Immediate.
			Controls the non-linear processing
			inside the echo canceller on any
			voice connections that use this voice
			profile.

			Not applicable in PCM and ADPCM mode."
		DEFVAL { disable }
		::= { scVoicePrfNodeEntry 6 }

scVoicePrfNodeTxPCMGain 	OBJECT-TYPE
		SYNTAX  INTEGER (1..256)
		ACCESS  read-write
		STATUS  mandatory
		DESCRIPTION "Parameter Type = Immediate.
			Controls the transmit PCM gain on any
			voice connections that use this voice
			profile. Range is defined from -33.0 dB
			to +18.0 dB with .2 dB increments.
			Default is 0 dB.

			Not applicable in PCM mode."
		DEFVAL { 166 }
		::= { scVoicePrfNodeEntry 7 }

scVoicePrfNodeRxPCMGain 	OBJECT-TYPE
		SYNTAX  INTEGER (1..256)
		ACCESS  read-write
		STATUS  mandatory
		DESCRIPTION "Parameter Type = Immediate.
			Controls the receive PCM gain on any
			voice connections that use this voice
			profile. Range is defined from -33.0 dB
			to +18.0 dB with .2 dB increments.
			Default is 0 dB.

			Not applicable in PCM mode."
		DEFVAL { 166 }
		::= { scVoicePrfNodeEntry 8 }

scVoicePrfNodePCMPhasorSize 	OBJECT-TYPE
		SYNTAX  INTEGER (4..255)
		ACCESS  read-write
		STATUS  mandatory
		DESCRIPTION "Parameter Type = Immediate.
			Size of the phasor (in bytes) on the
			PCM (64K) side of any voice connections
			using this voice profile.

			Not applicable in PCM mode."
		DEFVAL { 16 }
		::= { scVoicePrfNodeEntry 9 }

scVoicePrfNodeSubratePhSize 	OBJECT-TYPE
		SYNTAX  INTEGER (4..100)
		ACCESS  read-write
		STATUS  mandatory
		DESCRIPTION "Parameter Type = Immediate.
			Size of the phasor (in bytes) on the
			subrate side of any voice connections
			using this voice profile.

			Not applicable in PCM mode."
		DEFVAL { 16 }
		::= { scVoicePrfNodeEntry 10 }

scVoicePrfNodeNetSigMode 	OBJECT-TYPE
		SYNTAX  INTEGER {
			auto(1),
			st(2),
			link(3)
			}
		ACCESS  read-write
		STATUS  mandatory
		DESCRIPTION "Parameter Type = Immediate.
			Enable autodetection of CELP/ATC channel
			connected equipment so as to
			automatically change format to become
			compatible with either LINK (5 byte) or
			ST (8 byte) channel modes.  Alternately,
			this parameter hard sets CELP/ATC
			channels to be compatible only with
			either LINK or ST mode compatible
			equipment."
		DEFVAL { st }
		::= { scVoicePrfNodeEntry 11 }


-- Community MIB Section

scCmntyAccess 	OBJECT IDENTIFIER ::= { security 14 }

-- Community Common Table

scCmntyAccessTable 	OBJECT-TYPE
		SYNTAX  SEQUENCE OF ScCmntyAccessEntry
		ACCESS  not-accessible
		STATUS  mandatory
		DESCRIPTION "Represents the common attributes of
			multiple community tables."
		::= { scCmntyAccess 1 }

scCmntyAccessEntry 	OBJECT-TYPE
		SYNTAX	ScCmntyAccessEntry
		ACCESS  not-accessible
		STATUS  mandatory
		DESCRIPTION "INTRODUCED 2.0.0"
		INDEX { scCmntyAccessIndex }
		::= { scCmntyAccessTable 1 }

ScCmntyAccessEntry		::= SEQUENCE {
			scCmntyAccessIndex
				RecordIndex,
			scCmntyAccessControlMode
				INTEGER,
			scCmntyAccessCommunityName
				DisplayString
			}

scCmntyAccessIndex 	OBJECT-TYPE
		SYNTAX	RecordIndex
		ACCESS	read-only
		STATUS  mandatory
		DESCRIPTION "Parameter Type = Internal.
			Format is:
			   partition ID (1-1023):entry ID (1-5).
			Only 32 partitions can be entered,
			each with 5 entries."
		::= { scCmntyAccessEntry 1 }

scCmntyAccessControlMode 	OBJECT-TYPE
		SYNTAX	INTEGER {
			enable(1),
			disable(2),
			erase(3)
			}
		ACCESS	read-write
		STATUS  mandatory
		DESCRIPTION "Parameter Type = Immediate.
		    A community entry cannot be erased if it
		    is enabled. Community entry 1.1 cannot be
		    disabled or erased."
		::= { scCmntyAccessEntry 2 }

scCmntyAccessCommunityName 	OBJECT-TYPE
		SYNTAX	DisplayString (SIZE (0..24))
		ACCESS  read-write
		STATUS  mandatory
		DESCRIPTION "Parameter Type = Immediate."
		DEFVAL { "public" }
		::= { scCmntyAccessEntry 3 }

-- Community MIB Tables

-- MIB-II Community Access Table

scCmntyMib2Table 	OBJECT-TYPE
		SYNTAX  SEQUENCE OF ScCmntyMib2Entry
		ACCESS  not-accessible
		STATUS  mandatory
		DESCRIPTION "Community profile table for MIB-II
		    sections that are supported by ST.

		    A community profile entry will define which
		    sections of MIB-II a user has access to
		    based upon the community name that the user
		    has specified."
		::= { scCmntyAccess 2 }

scCmntyMib2Entry 	OBJECT-TYPE
		SYNTAX  ScCmntyMib2Entry
		ACCESS  not-accessible
		STATUS  mandatory
		DESCRIPTION "INTRODUCED 2.0.1"
		INDEX   { scCmntyMib2Index }
		::= { scCmntyMib2Table 1 }

ScCmntyMib2Entry		::= SEQUENCE {
			scCmntyMib2Index
			    RecordIndex,
			scCmntyMib2SystemAccess
			    INTEGER,
			scCmntyMib2InterfacesAccess
			    INTEGER,
			scCmntyMib2AtAccess
			    INTEGER,
			scCmntyMib2IpAccess
			    INTEGER,
			scCmntyMib2IcmpAccess
			    INTEGER,
			scCmntyMib2UdpAccess
			    INTEGER,
			scCmntyMib2SnmpAccess
			    INTEGER
			}

scCmntyMib2Index 	OBJECT-TYPE
		SYNTAX  RecordIndex
		ACCESS  read-only
		STATUS  mandatory
		DESCRIPTION "Parameter Type = Internal.
		    The first two bytes of this index are a
		    partition ID with a range of 1 to 1023.
		    There can be at most 32 partitions for a
		    single node, and each partition must
		    already have a corresponding node access
		    table entry defined. The last two bytes are
		    an entry ID with a range of 1 to 5. For
		    each partition, up to 5 entries may be
		    defined."
		::= { scCmntyMib2Entry 1 }

scCmntyMib2SystemAccess 	OBJECT-TYPE
		SYNTAX  INTEGER {
			    noAccess(1),
			    readOnly(2),
			    readWrite(3)
			}
		ACCESS  read-write
		STATUS  mandatory
		DESCRIPTION "Parameter Type = Immediate.
		    Defines access rights for a community entry
		    to the MIB-II system group."
		::= { scCmntyMib2Entry 2 }

scCmntyMib2InterfacesAccess 	OBJECT-TYPE
		SYNTAX  INTEGER {
			    noAccess(1),
			    readOnly(2),
			    readWrite(3)
			}
		ACCESS  read-write
		STATUS  mandatory
		DESCRIPTION "Parameter Type = Immediate.
		    Defines access rights for a community entry
		    to the MIB-II interfaces group."
		::= { scCmntyMib2Entry 3 }

scCmntyMib2AtAccess 	OBJECT-TYPE
		SYNTAX  INTEGER {
			    noAccess(1),
			    readOnly(2),
			    readWrite(3)
			}
		ACCESS  read-write
		STATUS  mandatory
		DESCRIPTION "Parameter Type = Immediate.
		    Defines access rights for a community entry
		    to the MIB-II at group."
		::= { scCmntyMib2Entry 4 }

scCmntyMib2IpAccess 	OBJECT-TYPE
		SYNTAX  INTEGER {
			    noAccess(1),
			    readOnly(2),
			    readWrite(3)
			}
		ACCESS  read-write
		STATUS  mandatory
		DESCRIPTION "Parameter Type = Immediate.		
			Defines access rights for a community entry
			to the MIB-II ip group."
		::= { scCmntyMib2Entry 5 }

scCmntyMib2IcmpAccess 	OBJECT-TYPE
			SYNTAX  INTEGER {
			    noAccess(1),
			    readOnly(2),
			    readWrite(3)
			}
			ACCESS  read-write
			STATUS  mandatory
		DESCRIPTION "Parameter Type = Immediate.
		    Defines access rights for a community entry
		    to the MIB-II icmp group."
		::= { scCmntyMib2Entry 6 }

scCmntyMib2UdpAccess 	OBJECT-TYPE
		SYNTAX  INTEGER {
			    noAccess(1),
			    readOnly(2),
			    readWrite(3)
			}
		ACCESS  read-write
		STATUS  mandatory
		DESCRIPTION "Parameter Type = Immediate.
		    Defines access rights for a community entry
		    to the MIB-II udp group."
		::= { scCmntyMib2Entry 7 }

scCmntyMib2SnmpAccess 	OBJECT-TYPE
		SYNTAX  INTEGER {
			    noAccess(1),
			    readOnly(2),
			    readWrite(3)
			}
		ACCESS  read-write
		STATUS  mandatory
		DESCRIPTION "Parameter Type = Immediate.
		    Defines access rights for a community entry
		    to the MIB-II snmp group."
		::= { scCmntyMib2Entry 8 }

-- Sec Community Access Table

scCmntySecTable 	OBJECT-TYPE
		SYNTAX	SEQUENCE OF ScCmntySecEntry
		ACCESS  not-accessible
		STATUS	mandatory
		DESCRIPTION "Represents which groups in
			the security MIB this community
			has access to."
		::= { scCmntyAccess 3 }

scCmntySecEntry 	OBJECT-TYPE
		SYNTAX	ScCmntySecEntry
		ACCESS  not-accessible
		STATUS  mandatory
		DESCRIPTION "INTRODUCED 2.0.0"
		INDEX { scCmntySecIndex }
		::= { scCmntySecTable 1 }

ScCmntySecEntry ::=  SEQUENCE {
			scCmntySecIndex
				RecordIndex,
			scCmntySecPartHeaderAccess
				INTEGER,
			scCmntySecSystemProfileAccess
				INTEGER,
			scCmntySecRootAccess
				INTEGER,
			scCmntySecNodeAccess
				INTEGER,
			scCmntySecTrapAccess
				INTEGER,
			scCmntySecChanProfileAccess
				INTEGER,
			scCmntySecSoftloadAccess
				INTEGER,
			scCmntySecCPIAccess
				INTEGER,
			scCmntySecModemAccess
				INTEGER,
			scCmntySecIPAccess
				INTEGER,
			scCmntySecLGMRoutingAccess
				INTEGER,
			scCmntySecVoiceProfileAccess
				INTEGER,
			scCmntySecCommunityAccess
				INTEGER
			}

scCmntySecIndex 	OBJECT-TYPE
		SYNTAX	RecordIndex
		ACCESS	read-only
		STATUS  mandatory
		DESCRIPTION "Parameter Type = Internal.
			Format is:
			   partition ID (1-1023):entry ID (1-5).
			Only 32 partitions can be entered,
			each with 5 entries."
		::= { scCmntySecEntry 1 }

scCmntySecPartHeaderAccess 	OBJECT-TYPE
		SYNTAX	INTEGER {
			noAccess(1),
			readOnly(2),
			readWrite(3)
			}
		ACCESS  read-write
		STATUS  mandatory
		DESCRIPTION "Parameter Type = Immediate.
			Specifies access to scPartitionHeader -
			the security MIB partition header."
		DEFVAL { readWrite }
		::= { scCmntySecEntry 2 }

scCmntySecSystemProfileAccess 	OBJECT-TYPE
		SYNTAX	INTEGER {
			noAccess(1),
			readOnly(2),
			readWrite(3)
			}
		ACCESS  read-write
		STATUS  mandatory
		DESCRIPTION "Parameter Type = Immediate.
			Specifies access to scSystemProfile -
			the security MIB system prof. section."
		DEFVAL { readWrite }
		::= { scCmntySecEntry 3 }

scCmntySecRootAccess 	OBJECT-TYPE
		SYNTAX	INTEGER {
			noAccess(1),
			readOnly(2),
			readWrite(3)
			}
		ACCESS  read-write
		STATUS  mandatory
		DESCRIPTION "Parameter Type = Immediate.
			Specifies access to scRootAccessTable -
			the security MIB root access section."
		DEFVAL { readWrite }
		::= { scCmntySecEntry 4 }

scCmntySecNodeAccess 	OBJECT-TYPE
		SYNTAX	INTEGER {
			noAccess(1),
			readOnly(2),
			readWrite(3)
			}
		ACCESS  read-write
		STATUS  mandatory
		DESCRIPTION "Parameter Type = Immediate.
			Specifies access to scNodeAccessTable -
			the security MIB node access section."
		DEFVAL { readWrite }
		::= { scCmntySecEntry 5 }

scCmntySecTrapAccess 	OBJECT-TYPE
		SYNTAX	INTEGER {
			noAccess(1),
			readOnly(2),
			readWrite(3)
			}
		ACCESS  read-write
		STATUS  mandatory
		DESCRIPTION "Parameter Type = Immediate.
			Specifies access to scTrapAccessTable -
			the security MIB trap access section."
		DEFVAL { readWrite }
		::= { scCmntySecEntry 6 }

scCmntySecChanProfileAccess 	OBJECT-TYPE
		SYNTAX	INTEGER {
			noAccess(1),
			readOnly(2),
			readWrite(3)
			}
		ACCESS  read-write
		STATUS  mandatory
		DESCRIPTION "Parameter Type = Immediate.
			Specifies access to scChProfileTable -
			the security MIB channel prof. section."
		DEFVAL { readWrite }
		::= { scCmntySecEntry 7 }

scCmntySecSoftloadAccess 	OBJECT-TYPE
		SYNTAX	INTEGER {
			noAccess(1),
			readOnly(2),
			readWrite(3)
			}
		ACCESS  read-write
		STATUS  mandatory
		DESCRIPTION "Parameter Type = Immediate.
			Specifies access to scSoftloadEntry -
			the security MIB softload section."
		DEFVAL { readWrite }
		::= { scCmntySecEntry 8 }

scCmntySecCPIAccess 	OBJECT-TYPE
		SYNTAX	INTEGER {
			noAccess(1),
			readOnly(2),
			readWrite(3)
			}
		ACCESS  read-write
		STATUS  mandatory
		DESCRIPTION "Parameter Type = Immediate.
			Specifies access to scCpiAccess - the
			security MIB CPI access section."
		DEFVAL { readWrite }
		::= { scCmntySecEntry 9 }

scCmntySecModemAccess 	OBJECT-TYPE
		SYNTAX	INTEGER {
			noAccess(1),
			readOnly(2),
			readWrite(3)
			}
		ACCESS  read-write
		STATUS  mandatory
		DESCRIPTION "Parameter Type = Immediate.
			Specifies access to scModemAccess - the
			security MIB modem access section."
		DEFVAL { readWrite }
		::= { scCmntySecEntry 10 }

scCmntySecIPAccess 	OBJECT-TYPE
		SYNTAX	INTEGER {
			noAccess(1),
			readOnly(2),
			readWrite(3)
			}
		ACCESS  read-write
		STATUS  mandatory
		DESCRIPTION "Parameter Type = Immediate.
			Specifies access to scIpAccess -
			the security MIB IP access section."
		DEFVAL { readWrite }
		::= { scCmntySecEntry 11 }

scCmntySecLGMRoutingAccess 	OBJECT-TYPE
		SYNTAX	INTEGER {
			noAccess(1),
			readOnly(2),
			readWrite(3)
			}
		ACCESS  read-write
		STATUS  mandatory
		DESCRIPTION "Parameter Type = Immediate.
			Specifies access to
			scLgmStaticRouteTable - the security
			MIB LGM static routing table section."
		DEFVAL { readWrite }
		::= { scCmntySecEntry 12 }

scCmntySecVoiceProfileAccess 	OBJECT-TYPE
		SYNTAX	INTEGER {
			noAccess(1),
			readOnly(2),
			readWrite(3)
			}
		ACCESS  read-write
		STATUS  mandatory
		DESCRIPTION "Parameter Type = Immediate.
			Specifies access to scVoicePrf -
			the security MIB voice profile section."
		DEFVAL { readWrite }
		::= { scCmntySecEntry 13 }

scCmntySecCommunityAccess 	OBJECT-TYPE
			SYNTAX	INTEGER {
			noAccess(1),
			readOnly(2),
			readWrite(3)
			}
			ACCESS  read-write
			STATUS  mandatory
		DESCRIPTION "Parameter Type = Immediate.
			Specifies access to scCmntyAccess -
			the security MIB community section."
		DEFVAL { readWrite }
		::= { scCmntySecEntry 14 }


-- Resource Configuration Community Access Table

scCmntyRecfTable 	OBJECT-TYPE
		SYNTAX	SEQUENCE OF ScCmntyRecfEntry
		ACCESS  not-accessible
		STATUS	mandatory
		DESCRIPTION "Represents which groups in
			the resource configuration MIB this
			community has access to."
		::= { scCmntyAccess 4 }

scCmntyRecfEntry 	OBJECT-TYPE
		SYNTAX	ScCmntyRecfEntry
		ACCESS  not-accessible
		STATUS  mandatory
		DESCRIPTION "INTRODUCED 2.0.0"
		INDEX { scCmntyRecfIndex }
		::= { scCmntyRecfTable 1 }

ScCmntyRecfEntry		::=  SEQUENCE {
			scCmntyRecfIndex
				RecordIndex,
			scCmntyRecfPartHeader
				INTEGER,
			scCmntyRecfNodeAccess
				INTEGER,
			scCmntyRecfNestAccess
				INTEGER,
			scCmntyRecfSlotAccess
				INTEGER,
			scCmntyRecfModuleAccess
				INTEGER,
			scCmntyRecfPortAccess
				INTEGER,
			scCmntyRecfBundleAccess
				INTEGER,
			scCmntyRecfINLAccess
				INTEGER,
			scCmntyRecfTDMChannelAccess
				INTEGER,
			scCmntyRecfFrRelayAccess
				INTEGER,
			scCmntyRecfAd10PortAccess
				INTEGER,
			scCmntyRecfAsmPortAccess
				INTEGER,
			scCmntyRecfRtmPortAccess
				INTEGER,
			scCmntyRecfLgmPortAccess
				INTEGER,
			scCmntyRecfDsmPortAccess
				INTEGER,
			scCmntyRecfTranslationAccess
				INTEGER,
			scCmntyRecfHwRscAccess
				INTEGER
			}

scCmntyRecfIndex 	OBJECT-TYPE
		SYNTAX	RecordIndex
		ACCESS	read-only
		STATUS  mandatory
		DESCRIPTION "Parameter Type = Internal.
			Format is:
			   partition ID (1-1023):entry ID (1-5).
			Only 32 partitions can be entered,
			each with 5 entries."
		::= { scCmntyRecfEntry 1 }

scCmntyRecfPartHeader 	OBJECT-TYPE
		SYNTAX	INTEGER {
			noAccess(1),
			readOnly(2),
			readWrite(3)
			}
		ACCESS  read-write
		STATUS  mandatory
		DESCRIPTION "Parameter Type = Immediate.
			Specifies access to
			recfPartitionHeader - the resource MIB
			partition header section."
		DEFVAL { readWrite }
		::= { scCmntyRecfEntry 2 }

scCmntyRecfNodeAccess 	OBJECT-TYPE
		SYNTAX	INTEGER {
			noAccess(1),
			readOnly(2),
			readWrite(3)
			}
		ACCESS  read-write
		STATUS  mandatory
		DESCRIPTION "Parameter Type = Immediate.
			Specifies access to recfNode - the
			resource configuration MIB node
			section."
		DEFVAL { readWrite }
		::= { scCmntyRecfEntry 3 }

scCmntyRecfNestAccess 	OBJECT-TYPE
		SYNTAX	INTEGER {
			noAccess(1),
			readOnly(2),
			readWrite(3)
			}
		ACCESS  read-write
		STATUS  mandatory
		DESCRIPTION "Parameter Type = Immediate.
			Specifies access to recfNest - the
			resource configuration MIB nest
			section."
		DEFVAL { readWrite }
		::= { scCmntyRecfEntry 4 }

scCmntyRecfSlotAccess 	OBJECT-TYPE
			SYNTAX	INTEGER {
			noAccess(1),
			readOnly(2),
			readWrite(3)
			}
			ACCESS  read-write
			STATUS  mandatory
		DESCRIPTION "Parameter Type = Immediate.
			Specifies access to recfSlot - the
			resource configuration MIB slot
			section."
		DEFVAL { readWrite }
		::= { scCmntyRecfEntry 5 }

scCmntyRecfModuleAccess 	OBJECT-TYPE
		SYNTAX	INTEGER {
			noAccess(1),
			readOnly(2),
			readWrite(3)
			}
		ACCESS  read-write
		STATUS  mandatory
		DESCRIPTION "Parameter Type = Immediate.
			Specifies access to recfModule -
			the resource configuration MIB
			generic module section."
		DEFVAL { readWrite }
		::= { scCmntyRecfEntry 6 }

scCmntyRecfPortAccess 	OBJECT-TYPE
		SYNTAX	INTEGER {
			noAccess(1),
			readOnly(2),
			readWrite(3)
			}
		ACCESS  read-write
		STATUS  mandatory
		DESCRIPTION "Parameter Type = Immediate.
			Specifies access to recfPort - the
			resource configuration MIB generic
			port section."
		DEFVAL { readWrite }
		::= { scCmntyRecfEntry 7 }

scCmntyRecfBundleAccess 	OBJECT-TYPE
		SYNTAX	INTEGER {
			noAccess(1),
			readOnly(2),
			readWrite(3)
			}
		ACCESS  read-write
		STATUS  mandatory
		DESCRIPTION "Parameter Type = Immediate.
			Specifies access to recfBundle -
			the resource configuration MIB bundle
			section."
		DEFVAL { readWrite }
		::= { scCmntyRecfEntry 8 }

scCmntyRecfINLAccess 	OBJECT-TYPE
		SYNTAX	INTEGER {
			noAccess(1),
			readOnly(2),
			readWrite(3)
			}
		ACCESS  read-write
		STATUS  mandatory
		DESCRIPTION "Parameter Type = Immediate.
			Specifies access to recfINL - the
			resource configuration MIB INL section."
		DEFVAL { readWrite }
		::= { scCmntyRecfEntry 9 }

scCmntyRecfTDMChannelAccess 	OBJECT-TYPE
		SYNTAX	INTEGER {
			noAccess(1),
			readOnly(2),
			readWrite(3)
			}
		ACCESS  read-write
		STATUS  mandatory
		DESCRIPTION "Parameter Type = Immediate.
			Specifies access to recfTDMChannel -
			the resource configuration MIB TDM
			channel section."
		DEFVAL { readWrite }
		::= { scCmntyRecfEntry 10 }

scCmntyRecfFrRelayAccess 	OBJECT-TYPE
		SYNTAX	INTEGER {
			noAccess(1),
			readOnly(2),
			readWrite(3)
			}
		ACCESS  read-write
		STATUS  mandatory
		DESCRIPTION "Parameter Type = Immediate.
			Specifies access to recfFrame -
			the resource configuration MIB frame
			relay section."
		DEFVAL { readWrite }
		::= { scCmntyRecfEntry 11 }

scCmntyRecfAd10PortAccess 	OBJECT-TYPE
		SYNTAX	INTEGER {
			noAccess(1),
			readOnly(2),
			readWrite(3)
			}
		ACCESS  read-write
		STATUS  mandatory
		DESCRIPTION "Parameter Type = Immediate.
			Specifies access to recfAd10Port -
			the resource configuration MIB AD10
			port section."
		DEFVAL { readWrite }
		::= { scCmntyRecfEntry 12 }

scCmntyRecfAsmPortAccess 	OBJECT-TYPE
		SYNTAX	INTEGER {
			noAccess(1),
			readOnly(2),
			readWrite(3)
			}
		ACCESS  read-write
		STATUS  mandatory
		DESCRIPTION "Parameter Type = Immediate.
			Specifies access to recfAsmPort - the
			resource configuration MIB ASM port
			section."
		DEFVAL { readWrite }
		::= { scCmntyRecfEntry 13 }

scCmntyRecfRtmPortAccess 	OBJECT-TYPE
		SYNTAX	INTEGER {
			noAccess(1),
			readOnly(2),
			readWrite(3)
			}
		ACCESS  read-write
		STATUS  mandatory
		DESCRIPTION "Parameter Type = Immediate.
			Specifies access to recfRtmPort - the
			resource configuration MIB RTM port
			section."
		DEFVAL { readWrite }
		::= { scCmntyRecfEntry 14 }

scCmntyRecfLgmPortAccess 	OBJECT-TYPE
		SYNTAX	INTEGER {
			noAccess(1),
			readOnly(2),
			readWrite(3)
			}
		ACCESS  read-write
		STATUS  mandatory
		DESCRIPTION "Parameter Type = Immediate.
			Specifies access to recfLgmPort - the
			resource configuration MIB LGM port
			section."
		DEFVAL { readWrite }
		::= { scCmntyRecfEntry 15 }

scCmntyRecfDsmPortAccess 	OBJECT-TYPE
		SYNTAX	INTEGER {
			noAccess(1),
			readOnly(2),
			readWrite(3)
			}
		ACCESS  read-write
		STATUS  mandatory
		DESCRIPTION "Parameter Type = Immediate.
			Specifies access to recfDsmPort - the
			resource configuration MIB DSM port
			section."
		DEFVAL { readWrite }
		::= { scCmntyRecfEntry 16 }

scCmntyRecfTranslationAccess 	OBJECT-TYPE
		SYNTAX	INTEGER {
			noAccess(1),
			readOnly(2),
			readWrite(3)
			}
		ACCESS  read-write
		STATUS  mandatory
		DESCRIPTION "Parameter Type = Immediate.
			Specifies access to recfTranslation -
			the resource configuration MIB
			translation section."
		DEFVAL { readWrite }
		::= { scCmntyRecfEntry 17 }


scCmntyRecfHwRscAccess 	OBJECT-TYPE
		SYNTAX  INTEGER {
			    noAccess(1),
			    readOnly(2),
			    readWrite(3)
			}
		ACCESS  read-write
		STATUS  mandatory
		DESCRIPTION "Parameter Type = Immediate.
			    INTRODUCED 2.0.1

			    Defines access rights for a community entry
			    to the resource configuration hardware
			    resource section (recfHwRsc)."
		DEFVAL { readWrite }
		::= { scCmntyRecfEntry 18 }


-- Resource Status Community Access Table

scCmntyRestTable 	OBJECT-TYPE
		SYNTAX	SEQUENCE OF ScCmntyRestEntry
		ACCESS  not-accessible
		STATUS	mandatory
		DESCRIPTION "Represents which groups in
			the resource status MIB this
			community has access to."
		::= { scCmntyAccess 5 }

scCmntyRestEntry 	OBJECT-TYPE
		SYNTAX	ScCmntyRestEntry
		ACCESS  not-accessible
		STATUS  mandatory
		DESCRIPTION "INTRODUCED 2.0.0"
		INDEX { scCmntyRestIndex }
		::= { scCmntyRestTable 1 }

ScCmntyRestEntry		::=  SEQUENCE {
			scCmntyRestIndex
			    RecordIndex,
			scCmntyRestNodeAccess
			    INTEGER,
			scCmntyRestNestAccess
			    INTEGER,
			scCmntyRestSlotAccess
			    INTEGER,
			scCmntyRestModuleAccess
			    INTEGER,
			scCmntyRestPortAccess
			    INTEGER,
			scCmntyRestBundleAccess
			    INTEGER,
			scCmntyRestINLAccess
			    INTEGER,
			scCmntyRestINLContentsAccess
			    INTEGER,
			scCmntyRestChannelAccess
			    INTEGER,
			scCmntyRestAd10PortAccess
			    INTEGER,
			scCmntyRestAsmPortAccess
			    INTEGER,
			scCmntyRestTrkGrpAccess
			    INTEGER,
			scCmntyRestRtmPortAccess
			    INTEGER,
			scCmntyRestLgmPortAccess
			    INTEGER,
			scCmntyRestSafAccess
			    INTEGER,
			scCmntyRestDsmPortAccess
			    INTEGER,
			scCmntyRestHwRscAccess
			    INTEGER
			}

scCmntyRestIndex 	OBJECT-TYPE
		SYNTAX	RecordIndex
		ACCESS	read-only
		STATUS  mandatory
		DESCRIPTION "Parameter Type = Internal.
			Format is:
			   partition ID (1-1023):entry ID (1-5).
			Only 32 partitions can be entered,
			each with 5 entries."
		::= { scCmntyRestEntry 1 }

scCmntyRestNodeAccess 	OBJECT-TYPE
		SYNTAX	INTEGER {
			noAccess(1),
			readOnly(2),
			readWrite(3)
			}
		ACCESS  read-write
		STATUS  mandatory
		DESCRIPTION "Parameter Type = Immediate.
			Specifies access to restNode - the
			resource status MIB node section."
		DEFVAL { readWrite }
		::= { scCmntyRestEntry 2 }

scCmntyRestNestAccess 	OBJECT-TYPE
		SYNTAX	INTEGER {
			noAccess(1),
			readOnly(2),
			readWrite(3)
			}
		ACCESS  read-write
		STATUS  mandatory
		DESCRIPTION "Parameter Type = Immediate.
			Specifies access to restNest - the
			resource status MIB nest section."
		DEFVAL { readWrite }
		::= { scCmntyRestEntry 3 }

scCmntyRestSlotAccess 	OBJECT-TYPE
		SYNTAX	INTEGER {
			noAccess(1),
			readOnly(2),
			readWrite(3)
			}
		ACCESS  read-write
		STATUS  mandatory
		DESCRIPTION "Parameter Type = Immediate.
			Specifies access to restSlot - the
			resource status MIB slot section."
		DEFVAL { readWrite }
		::= { scCmntyRestEntry 4 }

scCmntyRestModuleAccess 	OBJECT-TYPE
		SYNTAX	INTEGER {
			noAccess(1),
			readOnly(2),
			readWrite(3)
			}
		ACCESS  read-write
		STATUS  mandatory
		DESCRIPTION "Parameter Type = Immediate.
			Specifies access to restModule -
			the resource status MIB module section."
		DEFVAL { readWrite }
		::= { scCmntyRestEntry 5 }

scCmntyRestPortAccess 	OBJECT-TYPE
		SYNTAX	INTEGER {
			noAccess(1),
			readOnly(2),
			readWrite(3)
			}
		ACCESS  read-write
		STATUS  mandatory
		DESCRIPTION "Parameter Type = Immediate.
			Specifies access to restPort - the
			resource status MIB port section."
		DEFVAL { readWrite }
		::= { scCmntyRestEntry 6 }

scCmntyRestBundleAccess 	OBJECT-TYPE
			SYNTAX	INTEGER {
			noAccess(1),
			readOnly(2),
			readWrite(3)
			}
		ACCESS  read-write
		STATUS  mandatory
		DESCRIPTION "Parameter Type = Immediate.
			Specifies access to restBundle -
			the resource status MIB bundle section."
		DEFVAL { readWrite }
		::= { scCmntyRestEntry 7 }

scCmntyRestINLAccess 	OBJECT-TYPE
		SYNTAX	INTEGER {
			noAccess(1),
			readOnly(2),
			readWrite(3)
			}
		ACCESS  read-write
		STATUS  mandatory
		DESCRIPTION "Parameter Type = Immediate.
			Specifies access to restINL - the
			resource status MIB INL section."
		DEFVAL { readWrite }
		::= { scCmntyRestEntry 8 }

scCmntyRestINLContentsAccess 	OBJECT-TYPE
		SYNTAX	INTEGER {
			noAccess(1),
			readOnly(2),
			readWrite(3)
			}
		ACCESS  read-write
		STATUS  mandatory
		DESCRIPTION "Parameter Type = Immediate.
			Specifies access to
			restINLContentsTable - the resource
			status MIB INL contents section."
		DEFVAL { readWrite }
		::= { scCmntyRestEntry 9 }

scCmntyRestChannelAccess 	OBJECT-TYPE
		SYNTAX	INTEGER {
			noAccess(1),
			readOnly(2),
			readWrite(3)
			}
		ACCESS  read-write
		STATUS  mandatory
		DESCRIPTION "Parameter Type = Immediate.
			Specifies access to restChannel - the
			resource status MIB channel section."
		DEFVAL { readWrite }
		::= { scCmntyRestEntry 10 }

scCmntyRestAd10PortAccess 	OBJECT-TYPE
		SYNTAX	INTEGER {
			noAccess(1),
			readOnly(2),
			readWrite(3)
			}
		ACCESS  read-write
		STATUS  mandatory
		DESCRIPTION "Parameter Type = Immediate.
			Specifies access to restAd10Port - the
			resource status MIB AD10 port section."
		DEFVAL { readWrite }
		::= { scCmntyRestEntry 11 }

scCmntyRestAsmPortAccess 	OBJECT-TYPE
			SYNTAX	INTEGER {
			noAccess(1),
			readOnly(2),
			readWrite(3)
			}
			ACCESS  read-write
		STATUS  mandatory
		DESCRIPTION "Parameter Type = Immediate.
			Specifies access to restAsmPort - the
			resource status MIB ASM port section."
		DEFVAL { readWrite }
		::= { scCmntyRestEntry 12 }

scCmntyRestTrkGrpAccess 	OBJECT-TYPE
		SYNTAX	INTEGER {
			noAccess(1),
			readOnly(2),
			readWrite(3)
			}
		ACCESS  read-write
		STATUS  mandatory
		DESCRIPTION "Parameter Type = Immediate.
			Specifies access to restTrunkGroup -
			the resource status MIB trunk group
			section."
		DEFVAL { readWrite }
		::= { scCmntyRestEntry 13 }

scCmntyRestRtmPortAccess 	OBJECT-TYPE
		SYNTAX	INTEGER {
			noAccess(1),
			readOnly(2),
			readWrite(3)
			}
		ACCESS  read-write
		STATUS  mandatory
		DESCRIPTION "Parameter Type = Immediate.
			Specifies access to restRtmPort - the
			resource status MIB RTM port section."
		DEFVAL { readWrite }
		::= { scCmntyRestEntry 14 }

scCmntyRestLgmPortAccess 	OBJECT-TYPE
		SYNTAX	INTEGER {
			noAccess(1),
			readOnly(2),
			readWrite(3)
			}
		ACCESS  read-write
		STATUS  mandatory
		DESCRIPTION "Parameter Type = Immediate.
			Specifies access to restLgmPort - the
			resource status MIB LGM port section."
		DEFVAL { readWrite }
		::= { scCmntyRestEntry 15 }

scCmntyRestSafAccess 	OBJECT-TYPE
		SYNTAX	INTEGER {
			noAccess(1),
			readOnly(2),
			readWrite(3)
			}
		ACCESS  read-write
		STATUS  mandatory
		DESCRIPTION "Parameter Type = Immediate.
			Specifies access to restSaf - the
			resource status MIB SAF section."
		DEFVAL { readWrite }
		::= { scCmntyRestEntry 16 }

scCmntyRestDsmPortAccess 	OBJECT-TYPE
			SYNTAX	INTEGER {
			noAccess(1),
			readOnly(2),
			readWrite(3)
			}
			ACCESS  read-write
		STATUS  mandatory
		DESCRIPTION "Parameter Type = Immediate.
			Specifies access to restDsmPort - the
			resource status MIB DSM port section."
		DEFVAL { readWrite }
		::= { scCmntyRestEntry 17 }

scCmntyRestHwRscAccess 	OBJECT-TYPE
		SYNTAX	INTEGER {
			noAccess(1),
			readOnly(2),
			readWrite(3)
			}
		ACCESS  read-write
		STATUS  mandatory
		DESCRIPTION "Parameter Type = Immediate.
		    INTRODUCED 2.0.1

		    Defines access rights for a community entry
		    to the resource status hardware resource
		    section (restHwRsc)."
		DEFVAL { readWrite }
		::= { scCmntyRestEntry 18 }


-- Resource Statistics Community Access Table

scCmntyRestStTable 	OBJECT-TYPE
		SYNTAX	SEQUENCE OF ScCmntyRestStEntry
		ACCESS  not-accessible
		STATUS	mandatory
		DESCRIPTION "Represents which groups in
			the resource statistics MIB this
			community has access to."
		::= { scCmntyAccess 6 }

scCmntyRestStEntry 	OBJECT-TYPE
		SYNTAX	ScCmntyRestStEntry
		ACCESS  not-accessible
		STATUS  mandatory
		DESCRIPTION "INTRODUCED 2.0.0"
		INDEX { scCmntyRestStIndex }
		::= { scCmntyRestStTable 1 }

ScCmntyRestStEntry		::=  SEQUENCE {
			scCmntyRestStIndex
				RecordIndex,
			scCmntyRestStModuleAccess
				INTEGER,
			scCmntyRestStPortAccess
				INTEGER,
			scCmntyRestStINLAccess
				INTEGER,
			scCmntyRestStChannelAccess
				INTEGER,
			scCmntyRestStAd10Access
				INTEGER
			}

scCmntyRestStIndex 	OBJECT-TYPE
		SYNTAX	RecordIndex
		ACCESS	read-only
		STATUS  mandatory
		DESCRIPTION "Parameter Type = Internal.
			Format is:
			   partition ID (1-1023):entry ID (1-5).
			Only 32 partitions can be entered,
			each with 5 entries."
		::= { scCmntyRestStEntry 1 }

scCmntyRestStModuleAccess 	OBJECT-TYPE
		SYNTAX	INTEGER {
			noAccess(1),
			readOnly(2),
			readWrite(3)
			}
		ACCESS  read-write
		STATUS  mandatory
		DESCRIPTION "Parameter Type = Immediate.
			Specifies access to restStatModule -
			the resource statistics MIB module
			section."
		DEFVAL { readWrite }
		::= { scCmntyRestStEntry 2 }

scCmntyRestStPortAccess 	OBJECT-TYPE
		SYNTAX	INTEGER {
			noAccess(1),
			readOnly(2),
			readWrite(3)
			}
		ACCESS  read-write
		STATUS  mandatory
		DESCRIPTION "Parameter Type = Immediate.
			Specifies access to restStatPort - the
			resource statistics MIB port section."
		DEFVAL { readWrite }
		::= { scCmntyRestStEntry 3 }

scCmntyRestStINLAccess 	OBJECT-TYPE
		SYNTAX	INTEGER {
			noAccess(1),
			readOnly(2),
			readWrite(3)
			}
		ACCESS  read-write
		STATUS  mandatory
		DESCRIPTION "Parameter Type = Immediate.
			Specifies access to restStatInl - the
			resource statistics MIB INL section."
		DEFVAL { readWrite }
		::= { scCmntyRestStEntry 4 }

scCmntyRestStChannelAccess 	OBJECT-TYPE
		SYNTAX	INTEGER {
			noAccess(1),
			readOnly(2),
			readWrite(3)
			}
		ACCESS  read-write
		STATUS  mandatory
		DESCRIPTION "Parameter Type = Immediate.
			Specifies access to restStatCh - the
			resource statistics MIB channel
			section."
		DEFVAL { readWrite }
		::= { scCmntyRestStEntry 5 }

scCmntyRestStAd10Access 	OBJECT-TYPE
		SYNTAX	INTEGER {
			noAccess(1),
			readOnly(2),
			readWrite(3)
			}
		ACCESS  read-write
		STATUS  mandatory
		DESCRIPTION "Parameter Type = Immediate.
			Specifies access to restStatAd10 - the
			resource statistics MIB AD-10 section."
		DEFVAL { readWrite }
		::= { scCmntyRestStEntry 6 }


-- Alarm Community Access Table

scCmntyAlmTable 	OBJECT-TYPE
		SYNTAX	SEQUENCE OF ScCmntyAlmEntry
		ACCESS  not-accessible
		STATUS	mandatory
		DESCRIPTION "Represents which groups in
			the alarm MIB this community has
			access to."
		::= { scCmntyAccess 7 }

scCmntyAlmEntry 	OBJECT-TYPE
		SYNTAX	ScCmntyAlmEntry
		ACCESS  not-accessible
		STATUS  mandatory
		DESCRIPTION "INTRODUCED 2.0.0"
		INDEX { scCmntyAlmIndex }
		::= { scCmntyAlmTable 1 }

ScCmntyAlmEntry ::=  SEQUENCE {
			scCmntyAlmIndex
				RecordIndex,
			scCmntyAlmPartHeader
				INTEGER,
			scCmntyAlmAlarmProfileAccess
				INTEGER,
			scCmntyAlmAlarmLogAccess
				INTEGER,
			scCmntyAlmAlarmRecordAccess
				INTEGER,
			scCmntyAlmTrapAccess
				INTEGER
			}

scCmntyAlmIndex 	OBJECT-TYPE
		SYNTAX	RecordIndex
		ACCESS	read-only
		STATUS  mandatory
		DESCRIPTION "Parameter Type = Internal.
			Format is:
			   partition ID (1-1023):entry ID (1-5).
			Only 32 partitions can be entered,
			each with 5 entries."
		::= { scCmntyAlmEntry 1 }

scCmntyAlmPartHeader 	OBJECT-TYPE
		SYNTAX	INTEGER {
			noAccess(1),
			readOnly(2),
			readWrite(3)
			}
		ACCESS  read-write
		STATUS  mandatory
		DESCRIPTION "Parameter Type = Immediate.
			Specifies access to alPartitionHeader -
			the alarm MIB partition header section."
		DEFVAL { readWrite }
		::= { scCmntyAlmEntry 2 }

scCmntyAlmAlarmProfileAccess 	OBJECT-TYPE
		SYNTAX	INTEGER {
			noAccess(1),
			readOnly(2),
			readWrite(3)
			}
		ACCESS  read-write
		STATUS  mandatory
		DESCRIPTION "Parameter Type = Immediate.
			Specifies access to alSystemProfile -
			the alarm MIB alarm profile section."
		DEFVAL { readWrite }
		::= { scCmntyAlmEntry 3 }

scCmntyAlmAlarmLogAccess 	OBJECT-TYPE
		SYNTAX	INTEGER {
			noAccess(1),
			readOnly(2),
			readWrite(3)
			}
		ACCESS  read-write
		STATUS  mandatory
		DESCRIPTION "Parameter Type = Immediate.
			Specifies access to alLog - the alarm
			MIB alarm log section."
		DEFVAL { readWrite }
		::= { scCmntyAlmEntry 4 }

scCmntyAlmAlarmRecordAccess 	OBJECT-TYPE
		SYNTAX	INTEGER {
			noAccess(1),
			readOnly(2),
			readWrite(3)
			}
		ACCESS  read-write
		STATUS  mandatory
		DESCRIPTION "Parameter Type = Immediate.
			Specifies access to alLogRecord
			- the alarm MIB alarm record section."
		DEFVAL { readWrite }
		::= { scCmntyAlmEntry 5 }

scCmntyAlmTrapAccess 	OBJECT-TYPE
		SYNTAX	INTEGER {
			noAccess(1),
			readOnly(2),
			readWrite(3)
			}
		ACCESS  read-write
		STATUS  mandatory
		DESCRIPTION "Parameter Type = Immediate.
			Specifies access to alTrapContents -
			the alarm MIB trap section."
		DEFVAL { readWrite }
		::= { scCmntyAlmEntry 6 }



-- Node Configuration MIB

-- PartitionEntry for transaction processing on resource section

recfPartitionHeader 	OBJECT IDENTIFIER ::= { reConfig 1 }

recfPartitionControl 	OBJECT-TYPE
		SYNTAX    INTEGER {
			      validateCRC(1),
			      invalidateCRC(2)
			 }
		ACCESS    write-only
		STATUS    mandatory
		DESCRIPTION "Parameter Type = Immediate."
		::= { recfPartitionHeader 1 }

recfPartitionCRCCheck 	OBJECT-TYPE
		SYNTAX    INTEGER {
			      succeed(1),
			      fail(2)
			 }
		ACCESS    read-only
		STATUS    mandatory
		DESCRIPTION "Parameter Type = Internal."
		::= { recfPartitionHeader 2 }

recfPartitionFlushMode 	OBJECT-TYPE
		SYNTAX    INTEGER {
			      enable(1),
			      disable(2)
			 }
		ACCESS    read-write
		STATUS    mandatory
		DESCRIPTION "Parameter Type = Immediate."
		DEFVAL { disable }
		::= { recfPartitionHeader 3 }


-- Node Entry

recfNode                OBJECT IDENTIFIER ::=    { reConfig 2 }

recfNodeEntry           OBJECT IDENTIFIER ::=    { recfNode 1 }

recfNodeUpdate 	OBJECT-TYPE
		SYNTAX  INTEGER {
                                loaded(1),
				updateNestReq(3)
                                }
		ACCESS  read-only
		STATUS  mandatory
		DESCRIPTION "Parameter Type = Internal.
		      If set to updateNestReq, need to execute
		      restNodeDiagnostics(updateNest) to load."
		DEFVAL { updateNestReq }
		::= { recfNodeEntry 1 }

recfNodeDescr 	OBJECT-TYPE
		SYNTAX    DisplayString (SIZE (0..255))
		ACCESS    read-write
		STATUS    mandatory
		DESCRIPTION "Parameter Type = Immediate."
		DEFVAL { "" }
		::= { recfNodeEntry 2 }

recfNodeContact 	OBJECT-TYPE
		SYNTAX    DisplayString (SIZE (0..255))
		ACCESS    read-write
		STATUS    mandatory
		DESCRIPTION "Parameter Type = Immediate."
		DEFVAL { "" }
		::= { recfNodeEntry 3 }

recfNodeName 	OBJECT-TYPE
		SYNTAX    DisplayString (SIZE (0..255))
		ACCESS    read-write
		STATUS    mandatory
		DESCRIPTION "Parameter Type = Immediate."
		DEFVAL { "" }
		::= { recfNodeEntry 4 }

recfNodeLocation 	OBJECT-TYPE
		SYNTAX    DisplayString (SIZE (0..255))
		ACCESS    read-write
		STATUS    mandatory
		DESCRIPTION "Parameter Type = Immediate."
		DEFVAL { "" }
		::= { recfNodeEntry 5 }

recfNodeNumberOfNest 	OBJECT-TYPE
		SYNTAX    INTEGER (1..4)
		ACCESS    read-write
		STATUS    mandatory
		DESCRIPTION "Parameter Type = Intrusive.
		      New number of nests will not operate
		      until restNodeDiagnostics(updateNest)."
		DEFVAL { 1 }
		::= { recfNodeEntry 6 }

recfNodeClockSwitch 	OBJECT-TYPE
		SYNTAX    INTEGER {
                                  normal(1),
                                  fast(2)
                                  }
		ACCESS    read-write
		STATUS    mandatory
		DESCRIPTION "Parameter Type = Immediate."
		DEFVAL { normal }
		::= { recfNodeEntry 7 }

recfNodeAlarmRelay 	OBJECT-TYPE
		SYNTAX    INTEGER {
                                enableAlarmRelay(19),
                                disableAlarmRelay(20)
                          }
		ACCESS    read-write
		STATUS    mandatory
		DESCRIPTION "Parameter Type = Immediate."
		DEFVAL { enableAlarmRelay }
		::= { recfNodeEntry 8 }


-- Clock Fall Back Table

recfClockTable 	OBJECT-TYPE
		SYNTAX    SEQUENCE OF RecfClockEntry
		ACCESS    not-accessible
		STATUS    mandatory
		DESCRIPTION " "
		::=  { recfNode 2 }

recfClockEntry 	OBJECT-TYPE
		SYNTAX    RecfClockEntry
		ACCESS    not-accessible
		STATUS    mandatory
		DESCRIPTION " "
		INDEX { recfClockIndex }
		::=  { recfClockTable 1 }

RecfClockEntry           ::=  SEQUENCE {
                         recfClockIndex
                                   INTEGER,
                         recfClockStartMode
                                   INTEGER,
                         recfClockUpdate
                                   INTEGER,
                         recfClockType
                                   INTEGER,
                         recfClockStationSpeed
                                   INTEGER,
                         recfClockPortSource
                                   PortAddr,
                         recfClockQuality
                                   INTEGER,
                         recfClockPriority
                                   INTEGER
                         }

recfClockIndex 	OBJECT-TYPE
		SYNTAX    INTEGER (1..8)
		ACCESS    read-only
		STATUS    mandatory
		DESCRIPTION "Parameter Type = Internal."
		::=  { recfClockEntry 1 }

recfClockStartMode 	OBJECT-TYPE
		SYNTAX    INTEGER {
                                   active(44),
                                   erase(3)
                                   }
		ACCESS    read-write
		STATUS    mandatory
		DESCRIPTION "Parameter Type = Non-intrusive."
		DEFVAL { active }
		::=  { recfClockEntry 2 }

recfClockUpdate 	OBJECT-TYPE
		SYNTAX    INTEGER {
                                   loaded(1),
			   updateReq(2)
                                   }
		ACCESS    read-only
		STATUS    mandatory
		DESCRIPTION "Parameter Type = Internal.
		       If set to updateReq, need to execute
		       restNodeDiagnostics(updateClockTable)
		       to load."
		DEFVAL { updateReq }
		::=  { recfClockEntry 3 }

recfClockType 	OBJECT-TYPE
		SYNTAX    INTEGER {
                                   internal(1),
                                   station1(2),
                                   station2(3),
                                   portRxInd(4),
                                   portRxDep(5),
                                   portTx(6)
                                   }
		ACCESS    read-write
		STATUS    mandatory
		DESCRIPTION "Parameter Type = Non-intrusive."
		::=  { recfClockEntry 4 }

recfClockStationSpeed 	OBJECT-TYPE
		SYNTAX    INTEGER {
                                   s2400(1), s3200(2), s3600(3),
                                   s4000(4), s4800(5), s5600(6),
                                   s6000(7), s6400(8), s7200(9),
                                   s8000(10), s8400(11),
                                   s9600(12),
                                   s12000(13), s14400(14),
                                   s16000(15), s19200(16),
                                   s24000(17), s28800(18),
                                   s32000(19), s38400(20),
                                   s40800(21), s48000(22),
                                   s50000(23), s56000(24),
                                   s57600(25), s64000(26),
                                   s72000(27), s76800(28),
                                   s80000(29), s96000(30),
                                   s112000(31), s128000(32),
                                   s144000(33), s153600(34),
                                   s168000(35), s192000(36),
                                   s224000(37), s230400(38),
                                   s256000(39), s384000(40),
                                   s448000(41), s460800(42),
                                   s512000(43), s576000(44),
                                   s672000(45), s768000(46),
                                   s896000(47), s1024000(48),
                                   s1152000(49), s1334400(50),
                                   s1536000(51), s1544000(52),
                                   s1920000(53), s1984000(54),
                                   s2048000(55), s1856000(56),
                                   s1792000(57), s1728000(58),
                                   s1664000(59), s1600000(60),
                                   s1472000(61), s1408000(62),
                                   s1288000(63), s1280000(64),
                                   s1232000(65), s1216000(66),
                                   s1176000(67), s1120000(68),
                                   s1088000(69), s1064000(70),
                                   s1008000(71), s960000(72),
                                   s952000(73), s840000(74),
                                   s832000(75), s784000(76),
                                   s728000(77), s704000(78),
                                   s640000(79), s616000(80),
                                   s560000(81), s504000(82),
                                   s392000(83), s336000(84),
                                   s320000(85), s280000(86)
                                   }
		ACCESS    read-write
		STATUS    mandatory
		DESCRIPTION "Parameter Type = Non-intrusive."
		DEFVAL { s1544000 }
		::=  { recfClockEntry 5 }

recfClockPortSource 	OBJECT-TYPE
		SYNTAX    PortAddr
		ACCESS    read-write
		STATUS    mandatory
		DESCRIPTION "Parameter Type = Non-intrusive."
		::=  { recfClockEntry 6 }

recfClockQuality 	OBJECT-TYPE
		SYNTAX    INTEGER {
                                   high(1),
                                   low(2)
                                   }
		ACCESS    read-write
		STATUS    mandatory
		DESCRIPTION "Parameter Type = Non-intrusive."
		DEFVAL { high }
		::=  { recfClockEntry 7 }

recfClockPriority 	OBJECT-TYPE
		SYNTAX    INTEGER (1..8)
		ACCESS    read-write
		STATUS    mandatory
		DESCRIPTION "Parameter Type = Non-intrusive."
		DEFVAL { 1 }
		::=  { recfClockEntry 8 }


-- ST Available Resource MIB

recfAvailResourceTable 	OBJECT-TYPE
		SYNTAX	SEQUENCE OF RecfAvailResourceEntry
		ACCESS	not-accessible
		STATUS	mandatory
		DESCRIPTION "This MIB section serves the purpose
			of finding an available resource of the
			type specified by the instance
			identifier. The values of the instance
			identifier are enumerated in the
			recfAvailResourceIndex attribute.

			This MIB section returns the address of
			the resource of the specified type, that
			is available at the request time.
			If multiple resources of that type are
			available, the order of their return is
			not defined."
		::= { recfNode 3 }

recfAvailResourceEntry 	OBJECT-TYPE
		SYNTAX	RecfAvailResourceEntry
		ACCESS 	not-accessible
		STATUS	mandatory
		DESCRIPTION "INTRODUCED 2.0.0"
		INDEX { recfAvailResourceType }
		::= { recfAvailResourceTable  1 }

RecfAvailResourceEntry    	::= SEQUENCE 	{
			recfAvailResourceType
		  		INTEGER,
			recfAvailResourceId
				OCTET STRING
			 	}

recfAvailResourceType 	OBJECT-TYPE
		SYNTAX  INTEGER {
			link2TranslationIndex(1)
			}
		ACCESS  read-only
		STATUS	mandatory
		DESCRIPTION "Parameter Type = Internal.
			Specifies the ST resource type to
			search.

			The possible values are:
			    - link2TranslationIndex - find an
			      available entry in
			      recfLink2TraTable MIB section."
		::= { recfAvailResourceEntry 1 }

recfAvailResourceId 	OBJECT-TYPE
		SYNTAX	OCTET STRING (SIZE (1..6))
		ACCESS  read-only
		STATUS  mandatory
		DESCRIPTION "Parameter Type = Internal.
			The return value specifies an
			available ST resource address in the
			format used to access the MIB section of
			the specified type. If there are no
			available resources, then all bytes of
			the returned identifier will be equal to
			zero."
		::= { recfAvailResourceEntry 2 }


-- Nest Configuration MIB

recfNestTable 	OBJECT-TYPE
		SYNTAX    SEQUENCE OF RecfNestEntry
		ACCESS    not-accessible
		STATUS    mandatory
		DESCRIPTION " "
		::=  { reConfig 3 }

recfNestEntry 	OBJECT-TYPE
		SYNTAX    RecfNestEntry
		ACCESS    not-accessible
		STATUS    mandatory
		DESCRIPTION " "
		INDEX { recfNestAddr }
		::=  { recfNestTable 1 }

RecfNestEntry            ::=  SEQUENCE {
                         recfNestAddr
                                   NestAddr,
                         recfNestDesc
                                   DisplayString
                          }

recfNestAddr 	OBJECT-TYPE
                         SYNTAX    NestAddr
                         ACCESS    read-only
                         STATUS    mandatory
		DESCRIPTION "Parameter Type = Internal."
		::= { recfNestEntry 1 }

recfNestDesc 	OBJECT-TYPE
		SYNTAX    DisplayString (SIZE (0..255))
		ACCESS    read-write
		STATUS    mandatory
		DESCRIPTION "Parameter Type = Immediate."
		DEFVAL { "" }
		::= { recfNestEntry 2 }


-- Synchrony Slot Configuration MIB

recfSlotTable 	OBJECT-TYPE
		SYNTAX    SEQUENCE OF RecfSlotEntry
		ACCESS    not-accessible
		STATUS    mandatory
		DESCRIPTION " "
		::=  { reConfig 4 }

recfSlotEntry 	OBJECT-TYPE
		SYNTAX    RecfSlotEntry
		ACCESS    not-accessible
		STATUS    mandatory
		DESCRIPTION " "
		INDEX { recfSlotAddr }
		::=  { recfSlotTable 1 }

RecfSlotEntry 	::=  SEQUENCE {
			recfSlotAddr
			    SlotAddr,
			recfSlotModuleStartMode
			    INTEGER,
			recfSlotUpdate
			    INTEGER,
			recfSlotModuleDesc
			    DisplayString,
			recfSlotModuleType
			    INTEGER,
			recfSlotModuleSubType
			    INTEGER,
			recfSlotRedundantMode
			    INTEGER,
			recfSlotGroupID
			    INTEGER,
			recfSlotModuleMaxBypass
			    INTEGER,
			recfSlotModuleMaxSource
			    INTEGER,
			recfSlotModuleStartDiagMask
			    OCTET STRING,
			recfSlotModuleBgdDiagMask
			    OCTET STRING,
			recfSlotModulePortDiagMask
			    OCTET STRING,
			recfSlotModuleDiagoseMode
			    INTEGER,
			recfSlotModuleStartDiagMaskExt
			    OCTET STRING,
			recfSlotModuleBgdDiagMaskExt
			    OCTET STRING
			}

recfSlotAddr 	OBJECT-TYPE
                         SYNTAX    SlotAddr
                         ACCESS    read-only
                         STATUS    mandatory
		DESCRIPTION "Parameter Type = Internal."
		::= { recfSlotEntry 1 }

recfSlotModuleStartMode 	OBJECT-TYPE
		SYNTAX    INTEGER {
                                   automatic(1),
                                   off(2),
                                   erase(3)
                                   }
		ACCESS    read-write
		STATUS    mandatory
		DESCRIPTION "Parameter Type = Intrusive.
			       Setting to erase will fail if any of the
			       following conditions are true:
			       (1) The module's redundant mode is set to
			   one-to-one redundancy.
			       (2) The module has any unremoved INLs.
			       (3) The module has any channels that are not
			   disconnected.
			       (4) There is hardware present in the slot, and
			   the module is in an active or standby state,
			   or is going into an active or standby state
			   (i.e., is initializing or loading).

			       Otherwise, the erase command will erase the
			       module configuration and all of the ports,
			       bundles, INLs, and channels on the module."
		DEFVAL { off }
		::= { recfSlotEntry 2 }

recfSlotUpdate 	OBJECT-TYPE
		SYNTAX    INTEGER {
                                   loaded(1),
			   updateReq(2),
			   resetReq(3)
                                   }
		ACCESS    read-only
		STATUS    mandatory
		DESCRIPTION "Parameter Type = Internal."
		DEFVAL { resetReq }
		::=  { recfSlotEntry 3 }

recfSlotModuleDesc 	OBJECT-TYPE
		SYNTAX    DisplayString (SIZE (0..62))
		ACCESS    read-write
		STATUS    mandatory
		DESCRIPTION "Parameter Type = Immediate."
		DEFVAL { "" }
		::= { recfSlotEntry 4 }

recfSlotModuleType 	OBJECT-TYPE
		SYNTAX    INTEGER {
                                   ncp(1),
                                   lxm(3),
                                   rxm(4),
                                   t1m(5),
                                   e1m(6),
                                   sgm(7),
                                   lgm(8),
                                   asm(9),
                                   fsm(11),
                                   sdm(12),
                                   rtm(14),
			   dsm(19),
			   e3m(20)
			   }
		ACCESS    read-write
		STATUS    mandatory
		DESCRIPTION "Parameter Type = Intrusive."
		::= { recfSlotEntry 5 }

recfSlotModuleSubType 	OBJECT-TYPE
		SYNTAX  INTEGER (1..255)
		ACCESS  read-write
		STATUS  mandatory
		DESCRIPTION "Parameter Type = Intrusive.
			For NCP modules:
			NCP-1			value is 1
			NCP-2		   	value is 2
			NCP-3		   	value is 3

			For FSM modules:
			FSM-16		   	value is 1
			FSM-64		   	value is 2

			For T1M modules:
			T1M-4/DS1	   	value is 1
			T1M-4/DSX-1	   	value is 2
			T1M-2/DS1	   	value is 3
			T1M-2/DSX-1	   	value is 4

			For E1M modules:
			E1M-4/Ubal 	   	value is 1
			       		E1M-4/Bal          	value is 2
			E1M-2/Ubal	  	value is 3
			E1M-2/Bal 	   	value is 4

			For SDM modules:
			SDM-8/V.35		value is 1
			SDM-8/V.11		value is 2
			SDM-8/V.24		value is 3
			SDM-8E/V.35		value is 5
			SDM-8E/V.11		value is 6
			SDM-4R/V.35		value is 7
			SDM-4R/V.11		value is 8
			SDM-4R/E1-Bal		value is 33
			SDM-4R/E1-Ubal		value is 34
			SDM-4/64K-Co		value is 40
			SDM-4R			value is 42

			For SGM modules:
			SGM-1			value is 1
			SGM-1/128K              value is 3
			SGM-1/19.2K		value is 4

			For ASM modules:
			ASM-16			value is 1
			ASM-16A			value is 2
			ASM-16C			value is 3

			For LGM modules:
			LGM-2			value is 1

			For DSM modules:
			DSM-1			value is 1

			For E3M modules:
			E3M-1			value is 1
			E3M-2			value is 2

			Modules types not listed support only hardware
			subtype value 1."
		::= { recfSlotEntry 6 }

recfSlotRedundantMode 	OBJECT-TYPE
		SYNTAX    INTEGER {
                                   none(1),
                                   oneToOne(2),
                                   group(3)
                                   }
		ACCESS    read-write
		STATUS    mandatory
		DESCRIPTION "Parameter Type = Intrusive.
			Server modules will always have group
			redundancy regardless of the value of
			this field. Default value is none for I/O
			modules and group for server modules."
		::= { recfSlotEntry 7 }

recfSlotGroupID 	OBJECT-TYPE
		SYNTAX    INTEGER (1..64)
		ACCESS    read-write
		STATUS    mandatory
		DESCRIPTION "Parameter Type = Intrusive.
			       Applies to server modules only for
			       group redundancy."
		::= { recfSlotEntry 8 }

recfSlotModuleMaxBypass 	OBJECT-TYPE
		SYNTAX    INTEGER (0..100)
		ACCESS    read-write
		STATUS    mandatory
		DESCRIPTION "Parameter Type = Non-intrusive.
			       FSM or DSM module bypassing capability in
			       terms of percentage."
		::= { recfSlotEntry 9 }

recfSlotModuleMaxSource 	OBJECT-TYPE
		SYNTAX    INTEGER (0..100)
		ACCESS    read-write
		STATUS    mandatory
		DESCRIPTION "Parameter Type = Non-intrusive.
			       FSM module termination capability
			       in terms of percentage."
		::= { recfSlotEntry 10 }

recfSlotModuleStartDiagMask 	OBJECT-TYPE
		SYNTAX  OCTET STRING (SIZE (4))
		ACCESS  read-write
		STATUS  mandatory
		DESCRIPTION "Parameter Type = Intrusive.
			    This mask allows a module to be online or
			    standby even though some items as marked by
			    the mask have failed startup diagnostics.
			    For all tests, a bit set (1) means the
			    module will not operate if the corresponding
			    hardware is not working.

			    For all test descriptions, bit 1 refers to
			    the least significant bit of the lowest
			    byte in the octet string.

			    Startup diagnostics mask for the NCP
			    (additional tests for the NCP are defined
			    in recfSlotModuleStartDiagMaskExt):
			    NCP will ignore bits 1,3,4,7,8,10-15,25-31.
			    Bit 24 is no longer used as of 2.0.1.
			       bit 1  ID PROM
			       bit 2  LAN RAM
			       bit 3  Mailbox RAM
			       bit 4  Frame RAM
			       bit 5  CPI port
			       bit 6  Modem port
			       bit 7  ABPI
			       bit 8  unexpected interrupt
			       bit 9  Ethernet chip
			       bit 10 DBPI
			       bit 11 PARB
			       bit 12 Security MIB database
			       bit 13 Resource MIB database
			       bit 14 Alarm MIB database
			       bit 15 Database version
			       bit 16 T1M RTS (only on-line NCP)
			       bit 17 E1M RTS (only on-line NCP)
			       bit 18 FSM RTS (only on-line NCP)
			       bit 19 MIB schema (only on-line NCP)
			       bit 20 SDM RTS (only on-line NCP)
			       bit 21 SGM RTS (only on-line NCP)
			       bit 22 ASM RTS (only on-line NCP)
			       bit 23 RTM RTS (only on-line NCP)
			       bit 24 Utility (only on-line NCP)
			       bit 25 Boot PROM
			       bit 26 Flash PROM map
			       bit 27 NCP image
			       bit 28 Ticker
			       bit 29 DRAM
			       bit 30 reserved
			       bit 31 Clock
			       bit 32 reserved

			    Startup diagnostics mask for the SDM:
			bit 1  Register access
			bit 2  Ticker
			bit 3-32 reserved

			    Startup diagnostics mask for the FSM:
			bit 1-24  reserved
			bit 25 INL test
			bit 26 Ticker
			bit 27-32 reserved

			    Startup diagnostics mask for the DSM:
			bit 1-24  reserved
			bit 25 INL test
			bit 26 Ticker
			bit 27-32 reserved

			    Startup diagnostics mask for the SGM:
			bit 1  RAM 1 time slot sync drop
			bit 2  RAM 1 time slot sync add
			bit 3  RAM 2 time slot sync drop
			bit 4  RAM 2 time slot sync add
			bit 5  SGM frame RAM bank 0
			bit 6  SGM frame RAM bank 1
			bit 7  AGM frame RAM bank 0
			bit 8  AGM frame RAM bank 1
			bit 9  Pointer control RAM
			bit 10 Function RAM
			bit 11-16 reserved
			bit 17 Phasor
			bit 18-24 reserved
			bit 25 FIFO
			bit 26-32 reserved

			    Startup diagnostics mask for the RTM:
			bit 1  RTM DSP RAM
			bit 2  RTM SCC Chip
			bit 3-32 reserved

			    Startup diagnostics mask for the LGM:
			bit 1  SIM load
			bit 2  SOM load
			bit 3  SAM load
			bit 4  scanner load
			bit 5  DSP load
			bit 6-32 reserved

			    There are no startup diagnostics mask for
			    the T1M and E1M.

			    The default is to ignore all tests."
		DEFVAL { '00000000'h }
		::= { recfSlotEntry 11 }

recfSlotModuleBgdDiagMask 	OBJECT-TYPE
		SYNTAX  OCTET STRING (SIZE (4))
		ACCESS  read-write
		STATUS  mandatory
		DESCRIPTION "Parameter Type = Non-intrusive.
			    This mask allows a module to be online or
			    standby even though some items as marked by
			    the mask have failed background diagnostics.
			    For all tests, a bit set (1) means the
			    module will not operate if the corresponding
			    hardware is not working.

			    For all test descriptions, bit 1 refers to
			    the least significant bit of the lowest
			    byte in the octet string.

			    Background diagnostics mask for the NCP:
			    (additional tests for the NCP are defined
			    in recfSlotModuleBgdDiagMaskExt):
			    NCP will ignore bits 1,28,30. These tests
			    will always cause hard errors if they fail.
			bit 1  ID PROM
			bit 2-11 reserved
			bit 12 Security MIB database
			bit 13 Resource MIB database
			bit 14 Alarm MIB database
			bit 15 Database version number
			bit 16 T1M RTS
			bit 17 E1M RTS
			bit 18 FSM RTS
			bit 19 MIB schema
			bit 20 SDM RTS
			bit 21 SGM RTS
			bit 22 ASM RTS
			bit 23 RTM RTS
			bit 24 Utility
			bit 25 Boot PROM
			bit 26 Flash PROM map
			bit 27 NCP image
			bit 28 Bus frame
			bit 29 reserved
			bit 30 PLL
			bit 31 reserved
			bit 32 Code guard

			    Background diagnostics mask for the FSM:
			bit 1  reserved
			bit 2  Buffer pool
			bit 3-32 reserved

			    Background diagnostics mask for the DSM:
			bit 1  reserved
			bit 2  Buffer pool
			bit 3-32 reserved

			    There are no background diagnostics for the
			    T1M, E1M, SDM, SGM, RTM, and LGM.

			    The default is to ignore all tests."
		DEFVAL { '00000000'h }
		::= { recfSlotEntry 12 }

recfSlotModulePortDiagMask 	OBJECT-TYPE
		SYNTAX   OCTET STRING ( SIZE(64) )
		ACCESS   read-write
		STATUS   mandatory
		DESCRIPTION "Parameter Type = Non-intrusive.
			       This mask allows a module to be online or
			       standby even though some items as marked by
			       the mask have failed port startup diagnostics.
			       For all tests, a bit set (1) means the module
			       will not operate if the corresponding hardware
			       is not working. Each byte indicates the
			       diagnostic mask of a port.

			       For T1M and E1M ports:
			   bit 1 (lsb of each byte) Register access
			   bit 2  Loopback
			   bit 3  HDLC
			   bit 4-8 reserved

			       For FSM ports:
			   bit 1 (lsb of each byte) HDLC
			   bit 2-8 reserved

			       For DSM ports:
			   bit 1 (lsb of each byte) HDLC
			   bit 2-8 reserved

			       For RTM ports:
			   bit 1 (lsb of each byte) Loopback
			   bit 2-8 reserved

			       There are no port diagnostics for NCP, SDM,
			       and SGM.

			       The default is to ignore all tests."
		::= { recfSlotEntry 13 }

recfSlotModuleDiagoseMode 	OBJECT-TYPE
		SYNTAX  INTEGER (0..2147483647)
		ACCESS  read-write
		STATUS  mandatory
		DESCRIPTION "Parameter Type = Non-intrusive.
			INTRODUCED 2.0.1

			This parameter is used to control
			module-specific code for diagnosing
			problems. The interpretation of values
			for this field is determined by the
			specific type of module in the slot.
			The value zero (0) will mean normal
			operation for all module types."
		DEFVAL { 0 }
		::= { recfSlotEntry 14 }

recfSlotModuleStartDiagMaskExt 	OBJECT-TYPE
		SYNTAX  OCTET STRING (SIZE (4))
		ACCESS  read-write
		STATUS  mandatory
		DESCRIPTION "Parameter Type = Intrusive.
			    INTRODUCED 2.0.1

			    This mask allows a module to be online or
			    standby even though some items as marked by
			    the mask have failed startup diagnostics.
			    For all tests, a bit set (1) means the
			    module will not operate if the corresponding
			    hardware is not working.

			    For all test descriptions, bit 1 refers to
			    the least significant bit of the lowest
			    byte in the octet string.

			    Startup diagnostics mask for the NCP (this
			    is a continuation of the tests defined for
			    the NCP in recfSlotModuleStartDiagMask):
			bit 1  DSM RTS
			bit 2  LGM RTS
			bit 3  E3M RTS
			bit 4-32  reserved.

			    Currently, this attribute is not used for
			    any other module type except the NCP (that
			    is, all bits are reserved for the other
			    module types)."
		::= { recfSlotEntry 15 }

recfSlotModuleBgdDiagMaskExt 	OBJECT-TYPE
		SYNTAX  OCTET STRING (SIZE (4))
		ACCESS  read-write
		STATUS  mandatory
		DESCRIPTION "Parameter Type = Non-intrusive.
			    INTRODUCED 2.0.1

			    This mask allows a module to be online or
			    standby even though some items as marked by
			    the mask have failed background diagnostics.
			    For all tests, a bit set (1) means the
			    module will not operate if the corresponding
			    hardware is not working.

			    For all test descriptions, bit 1 refers to
			    the least significant bit of the lowest
			    byte in the octet string.

			    Background diagnostics mask for the NCP
			    (this is a continuation of the tests defined
			    for the NCP in recfSlotModuleBgdDiagMask):
			bit 1  DSM RTS
			bit 2  LGM RTS
			bit 3  E3M RTS
			bit 4-32  reserved.

			    Currently, this attribute is not used for
			    any other module type except the NCP (that
			    is, all bits are reserved for the other
			    module types)."
		::= { recfSlotEntry 16 }


-- Module Specific Configuration MIB

recfModule          OBJECT IDENTIFIER ::=    { reConfig 5 }

-- FSM-16 Resource Utilization

recfModuleFsm16Table 	OBJECT-TYPE
		SYNTAX  SEQUENCE OF RecfModuleFsm16Entry
		ACCESS  not-accessible
		STATUS  mandatory
		DESCRIPTION " "	
		::=  { recfModule 1 }

recfModuleFsm16Entry 	OBJECT-TYPE
		SYNTAX  RecfModuleFsm16Entry
		ACCESS  not-accessible
		STATUS  mandatory
		DESCRIPTION " "	
		INDEX { recfModuleFsm16Addr }
		::= { recfModuleFsm16Table 1 }

RecfModuleFsm16Entry     ::= SEQUENCE {
                              recfModuleFsm16Addr
                                   SlotAddr,
                              recfModuleFsm16Partition
                                   OCTET STRING
                              }

recfModuleFsm16Addr 	OBJECT-TYPE
                         SYNTAX    SlotAddr
                         ACCESS    read-only
                         STATUS    mandatory
		DESCRIPTION "Parameter Type = Internal."
		::= { recfModuleFsm16Entry 1 }

recfModuleFsm16Partition 	OBJECT-TYPE
		SYNTAX    OCTET STRING ( SIZE(32) )
		ACCESS    read-write
		STATUS    mandatory
		DESCRIPTION "Parameter Type = Non-intrusive.
			       Each two bytes is the partition ID of a
			       physical port on the module. Partition 1
			       is for CNMS. Partition 0xFFFE (65534) is
			       for any partition. When this is changed,
			       it will not change the current port
			       allocation, but it will affect any new
			       server ports being allocated."
		::= { recfModuleFsm16Entry 2 }

-- FSM-64 Resource Utilization

recfModuleFsm64Table 	OBJECT-TYPE
		SYNTAX  SEQUENCE OF RecfModuleFsm64Entry
		ACCESS  not-accessible
		STATUS  mandatory
		DESCRIPTION " "
		::=  { recfModule 2 }

recfModuleFsm64Entry 	OBJECT-TYPE
		SYNTAX  RecfModuleFsm64Entry
		ACCESS  not-accessible
		STATUS  mandatory
		DESCRIPTION " "
		INDEX { recfModuleFsm64Addr }
		::= { recfModuleFsm64Table 1 }

RecfModuleFsm64Entry     ::= SEQUENCE {
                              recfModuleFsm64Addr
                                   SlotAddr,
                              recfModuleFsm64Partition
                                   OCTET STRING
                              }

recfModuleFsm64Addr 	OBJECT-TYPE
		SYNTAX    SlotAddr
		ACCESS    read-only
		STATUS    mandatory
		DESCRIPTION "Parameter Type = Internal."
		::= { recfModuleFsm64Entry 1 }

recfModuleFsm64Partition 	OBJECT-TYPE
		SYNTAX    OCTET STRING ( SIZE(128) )
		ACCESS    read-write
		STATUS    mandatory
		DESCRIPTION "Parameter Type = Non-intrusive.
			       Each two bytes is the partition ID of a
			       physical port on the module. Partition 1
			       is for CNMS. Partition 0xFFFE (65534) is
			       for any partition. When this is changed,
			       it will not change the current port
			       allocation, but it will affect any new
			       server ports being allocated."
		::= { recfModuleFsm64Entry 2 }

-- SGM/AG Resource Utilization

recfModuleSgmAgTable 	OBJECT-TYPE
		SYNTAX  SEQUENCE OF RecfModuleSgmAgEntry
		ACCESS  not-accessible
		STATUS  mandatory
		DESCRIPTION " "
		::= { recfModule 3 }

recfModuleSgmAgEntry 	OBJECT-TYPE
		SYNTAX  RecfModuleSgmAgEntry
		ACCESS  not-accessible
		STATUS  mandatory
		DESCRIPTION " "
		INDEX { recfModuleSgmAgAddr }
		::= { recfModuleSgmAgTable 1 }

RecfModuleSgmAgEntry	::= SEQUENCE {
		recfModuleSgmAgAddr
			SlotAddr,
		recfModuleSgmAgPartition
			OCTET STRING
		}

recfModuleSgmAgAddr 	OBJECT-TYPE
		SYNTAX    SlotAddr
		ACCESS    read-only
		STATUS    mandatory
		DESCRIPTION "Parameter Type = Internal."
		::= { recfModuleSgmAgEntry 1 }

recfModuleSgmAgPartition 	OBJECT-TYPE
		SYNTAX    OCTET STRING ( SIZE(64) )
		ACCESS    read-write
		STATUS    mandatory
		DESCRIPTION "Parameter Type = Non-intrusive.
		          Each two bytes is the partition ID of a
		          physical port on the module. Partition 1
			  is for CNMS. Partition 0xFFFE (65534) is
			  for any partition. When this is changed,
			  it will not change the current port
			  allocation, but it will affect any new
			  server ports being allocated."
		::= { recfModuleSgmAgEntry 2 }


-- ASM Resource Utilization

recfModuleAsmTable 	OBJECT-TYPE
		SYNTAX  SEQUENCE OF RecfModuleAsmEntry
		ACCESS  not-accessible
		STATUS  mandatory
		DESCRIPTION " "
		::= { recfModule 4 }

recfModuleAsmEntry 	OBJECT-TYPE
		SYNTAX  RecfModuleAsmEntry
		ACCESS  not-accessible
		STATUS  mandatory
		DESCRIPTION " "
		INDEX { recfModuleAsmAddr }
		::= { recfModuleAsmTable 1 }

RecfModuleAsmEntry              ::= SEQUENCE {
			recfModuleAsmAddr
				SlotAddr,
			recfModuleAsmPartition
				OCTET STRING,
			recfModuleAsmCelpPartition
				OCTET STRING,
			recfModuleAsmMinCelpPorts
				INTEGER,
			recfModuleAsmApplType
				INTEGER
			}
	
recfModuleAsmAddr 	OBJECT-TYPE
		SYNTAX  SlotAddr
		ACCESS  read-only
		STATUS  mandatory
		DESCRIPTION "Parameter Type = Internal."
		::= { recfModuleAsmEntry 1 }

recfModuleAsmPartition 	OBJECT-TYPE
		SYNTAX  OCTET STRING ( SIZE(32) )
		ACCESS  read-write
		STATUS  mandatory
		DESCRIPTION "Parameter Type = Non-intrusive.
			Each two bytes is the partition ID of
			a physical engine on the module.
			Partition 1 is for CNMS. Partition
			0xFFFE (65534) is for any partition.
			When this is changed, it will not
			change the current port allocation,
			but it will affect any new server
			ports being allocated."
		::= { recfModuleAsmEntry 2 }

recfModuleAsmCelpPartition 	OBJECT-TYPE
		SYNTAX  OCTET STRING ( SIZE(32) )
		ACCESS  read-write
		STATUS  mandatory
		DESCRIPTION "Parameter Type = Non-intrusive.
			Each two bytes is the partition ID of a
			CELP license on the module. Partition 1
			is for CNMS. Partition 0xFFFE (65534)
			is for any partition. When this is
			changed, it will not change the current
			port allocation, but it will affect any
			new server ports being allocated."
		::= { recfModuleAsmEntry 3 }

recfModuleAsmMinCelpPorts 	OBJECT-TYPE
		SYNTAX  INTEGER (0..16)
		ACCESS  read-write
		STATUS  mandatory
		DESCRIPTION "Parameter Type = Non-intrusive.
			Defines the number of the ASM
			ports that cannot be used for
			anything else but CELP application."
		DEFVAL { 0 }
		::= { recfModuleAsmEntry 4 }

recfModuleAsmApplType 	OBJECT-TYPE
		SYNTAX	INTEGER {
			x50(1),
			celp-atc(2),
			adpcm(3),
			mixed(255)
			}
		ACCESS	read-write
		STATUS	mandatory
		DESCRIPTION "Parameter Type = Intrusive.
			Allows the user to specify a specific
			application type to be allocated to
			this ASM module. Ports with other
			application types will not be able to
			be allocated on this module.

			If the subtype of this particular ASM
			module does not support the application
			type specified here, then the module
			will still come up, but no ports will
			be able to be allocated. If this
			occurs, then the restAsmModApplTable
			section of the MIB will indicate that
			no applications are available.

			If a setting of mixed is specified,
			then allocation of a port with a
			particular application will only be
			restricited by the subtype of the
			module."
		DEFVAL { mixed }
		::= { recfModuleAsmEntry 5 }


-- LGM Resource Utilization

recfModuleLgmTable 	OBJECT-TYPE
		SYNTAX    SEQUENCE OF RecfModuleLgmEntry
		ACCESS    not-accessible
		STATUS    mandatory
		DESCRIPTION " "
		::=  { recfModule 5 }

recfModuleLgmEntry 	OBJECT-TYPE
		SYNTAX	  RecfModuleLgmEntry
		ACCESS    not-accessible
		STATUS    mandatory
		DESCRIPTION " "
		INDEX { recfModuleLgmAddr }
		::=  { recfModuleLgmTable 1 }

RecfModuleLgmEntry		::=  SEQUENCE   {
			recfModuleLgmAddr
				SlotAddr,
			recfModuleLgmPartition
				OCTET STRING
			     	}

recfModuleLgmAddr 	OBJECT-TYPE
		SYNTAX	  SlotAddr
		ACCESS	  read-only
		STATUS    mandatory
		DESCRIPTION "Parameter Type = Internal."
		::=  { recfModuleLgmEntry 1 }

recfModuleLgmPartition 	OBJECT-TYPE
		SYNTAX	  OCTET STRING (SIZE (4))
		ACCESS	  read-write
		STATUS    mandatory
		DESCRIPTION "Parameter Type = Non-intrusive.
			Each two bytes is the partition ID
			of a VILC aggregate on the module.
			Partition 1 is for CNMS.
			Partition 0xFFFE (65534) is for any
			partition. When this is changed,
			it will not change the current VILC
			allocation, but it will affect any new
			server ports being allocated."
		::=  { recfModuleLgmEntry 2 }



-- DSM Module Specific Configuration

recfModuleDsm 	OBJECT IDENTIFIER ::= { recfModule 6 }

-- DSM Module Implementation

recfModuleDsmTable 	OBJECT-TYPE
		SYNTAX  SEQUENCE OF RecfModuleDsmEntry
		ACCESS  not-accessible
		STATUS  mandatory
		DESCRIPTION " "
		::= { recfModuleDsm 1 }

recfModuleDsmEntry 	OBJECT-TYPE
		SYNTAX  RecfModuleDsmEntry
		ACCESS  not-accessible
		STATUS  mandatory
		DESCRIPTION "INTRODUCED 2.0.0"
		INDEX { recfModuleDsmAddr }
		::= { recfModuleDsmTable 1 }

RecfModuleDsmEntry              ::= SEQUENCE {
			recfModuleDsmAddr
				SlotAddr,
			recfModuleDsmPartitionMap
				OCTET STRING,
			recfModuleDsmPbxProtocol
				INTEGER,
			recfModuleDsmActiveLev1CDRMode
				INTEGER,
			recfModuleDsmRecordLev1CDRMode
				INTEGER,
			recfModuleDsmActiveLev2CDRMode
				INTEGER,
			recfModuleDsmRecordLev2CDRMode
				INTEGER
			}

recfModuleDsmAddr 	OBJECT-TYPE
		SYNTAX  SlotAddr
		ACCESS  read-only
		STATUS  mandatory
		DESCRIPTION "Parameter Type = Internal.
			DSM module address. Format is
			nest.slot."
		::= { recfModuleDsmEntry 1 }

recfModuleDsmPartitionMap 	OBJECT-TYPE
		SYNTAX  OCTET STRING ( SIZE(128) )
		ACCESS  read-write
		STATUS  mandatory
		DESCRIPTION "Parameter Type = Non-intrusive.
			Every octet pair is the partition ID of
			a physical port on the module.
			Partition 1 is for CNMS. Partition
			0xFFFE (65534) is for any partition.
			When this is changed, it will not
			change the current port allocation,
			but it will affect any new server
			ports being allocated."
		::= { recfModuleDsmEntry 2 }

recfModuleDsmPbxProtocol 	OBJECT-TYPE
		SYNTAX  INTEGER {
			dpnss(1),
			qsig(2)
			}
		ACCESS  read-write
		STATUS  mandatory
		DESCRIPTION "Parameter Type = Intrusive.
			All D-channels connected to this
			DSM module will need to be set
			up with the same PBX protocol as
			set here.

			Changes to this field will be reflected
			in recfSlotUpdate. A module reset will
			be required in order for the change to
			take effect."
		DEFVAL { dpnss }
		::= { recfModuleDsmEntry 3 }

recfModuleDsmActiveLev1CDRMode 	OBJECT-TYPE
		SYNTAX  INTEGER {
			enable(1),
			disable(2)
			}
		ACCESS  read-write
		STATUS  mandatory
		DESCRIPTION "Parameter Type = Non-intrusive.
			Specifies whether level 1 Call Detail
			Record for the calls in progress are to
			be generated by the DSM.

			This parameter affects all the
			D-channels terminated on this
			module.

			Changes to this field will be reflected
			in recfSlotUpdate. A module update will
			be required in order for the change to
			take effect. It will not disrupt any
			channel connections associated with
			DSM."
		DEFVAL { enable }
		::= { recfModuleDsmEntry 4 }

recfModuleDsmRecordLev1CDRMode 	OBJECT-TYPE
		SYNTAX  INTEGER {
			enable(1),
			disable(2)
			}
		ACCESS  read-write
		STATUS  mandatory
		DESCRIPTION "Parameter Type = Non-intrusive.
			Specifies whether level 1 Call Detail
			Record for the completed calls are to
			be generated by the DSM.

			This parameter affects all the
			D-channels terminated on this
			module.

			Changes to this field will be reflected
			in recfSlotUpdate. A module update will
			be required in order for the change to
			take effect. It will not disrupt any
			channel connections associated with
			DSM."
		DEFVAL { enable }
		::= { recfModuleDsmEntry 5 }

recfModuleDsmActiveLev2CDRMode 	OBJECT-TYPE
		SYNTAX  INTEGER {
			enable(1),
			disable(2)
			}
		ACCESS  read-write
		STATUS  mandatory
		DESCRIPTION "Parameter Type = Non-intrusive.
			Specifies whether level 2 Call Detail
			Record for the calls in progress are to
			be generated by the DSM.

			This parameter affects all the
			D-channels terminated on this
			module.

			Changes to this field will be reflected
			in recfSlotUpdate. A module update will
			be required in order for the change to
			take effect. It will not disrupt any
			channel connections associated with
			DSM."
		DEFVAL { enable }
		::= { recfModuleDsmEntry 6 }

recfModuleDsmRecordLev2CDRMode 	OBJECT-TYPE
		SYNTAX  INTEGER {
			enable(1),
			disable(2)
			}
		ACCESS  read-write
		STATUS  mandatory
		DESCRIPTION "Parameter Type = Non-intrusive.
			Specifies whether level 2 Call Detail
			Record for the completed calls are to
			be generated by the DSM.

			This parameter affects all the
			D-channels terminated on this
			module.

			Changes to this field will be reflected
			in recfSlotUpdate. A module update will
			be required in order for the change to
			take effect. It will not disrupt any
			channel connections associated with
			DSM."
		DEFVAL { enable }
		::= { recfModuleDsmEntry 7 }


-- DSM Module Recorded CDR Log implementation

recfModDsmRecCDRLogTable 	OBJECT-TYPE
		SYNTAX  SEQUENCE OF RecfModDsmRecCDRLogEntry
		ACCESS  not-accessible
		STATUS  mandatory
		DESCRIPTION " "
		::=  { recfModuleDsm 2 }

recfModDsmRecCDRLogEntry 	OBJECT-TYPE
		SYNTAX  RecfModDsmRecCDRLogEntry
		ACCESS  not-accessible
		STATUS  mandatory
		DESCRIPTION "INTRODUCED 2.0.0"
		INDEX { recfModDsmRecCDRLogAddr,
			recfModDsmRecCDRLogIndex }
		::= { recfModDsmRecCDRLogTable 1 }

RecfModDsmRecCDRLogEntry	::= SEQUENCE {
			recfModDsmRecCDRLogAddr
				SlotAddr,
			recfModDsmRecCDRLogIndex
				INTEGER,
			recfModDsmRecCDRLogControlMode
				INTEGER,
			recfModDsmRecCDRLogSize
				INTEGER,
			recfModDsmRecCDRLogOvThrshld
				INTEGER,
			recfModDsmRecCDRLogPartitionID
				INTEGER
			}

recfModDsmRecCDRLogAddr 	OBJECT-TYPE
		SYNTAX  SlotAddr
		ACCESS  read-only
		STATUS  mandatory
		DESCRIPTION "Parameter Type = Internal.
			Address of this DSM module.
			Format is nest.slot."
		::= { recfModDsmRecCDRLogEntry 1 }

recfModDsmRecCDRLogIndex 	OBJECT-TYPE
		SYNTAX  INTEGER (1..32)
		ACCESS  read-only
		STATUS  mandatory
		DESCRIPTION "Parameter Type = Internal.
			Specifies the CDR log to access."
		::= { recfModDsmRecCDRLogEntry 2 }

recfModDsmRecCDRLogControlMode 	OBJECT-TYPE
		SYNTAX  INTEGER {
			enable(1),
			disable(2),
			erase(3)
			}
		ACCESS  read-write
		STATUS  mandatory
		DESCRIPTION "Parameter Type = Non-intrusive.
			Changes will not affect channels
			that are already connected.

			Disable will prevent new CDRs to
			be recorded in this log.

			Erase will remove this CDR log.

			Changes to this field will be reflected
			in recfSlotUpdate. A module update will
			be required in order for the change to
			take effect. It will not disrupt any
			channel connections associated with this
			DSM."
		DEFVAL { disable }
		::= { recfModDsmRecCDRLogEntry 3 }

recfModDsmRecCDRLogSize 	OBJECT-TYPE
		SYNTAX  INTEGER (0..1000)
		ACCESS  read-write
		STATUS  mandatory
		DESCRIPTION "Parameter Type = Non-intrusive.
			    Assigns the maximum number of CDRs that may
			    be stored in this CDR log.

			    The total size of all CDR logs on this
			    module cannot exceed the number of total
			    records available. This number may be
			    obtain from the restDsmModuleTotalRecCDRs
			    attribute.

			    When a new DSM module is configured, CDR
			    log #1 will automatically be created with a
			    size of 1000 CDRs. Any other CDR logs that
			    are configured after this will have a
			    default size of 0.

			    Changes to this field will be reflected in
			    recfSlotUpdate. A module update will be
			    required in order for the change to take
			    effect. It will not disrupt any channel
			    connections associated with this DSM."
		DEFVAL { 0 }
		::= { recfModDsmRecCDRLogEntry 4 }

recfModDsmRecCDRLogOvThrshld 	OBJECT-TYPE
		SYNTAX  INTEGER (0..1000)
		ACCESS  read-write
		STATUS  mandatory
		DESCRIPTION "Parameter Type = Non-intrusive.
			    Defines an overflow threshold on this CDR
			    log. When reached, the threshold flag is
			    set, and the threshold exceeded alarm is
			    issued. If this value exceeds the value of
			    the recfModDsmRecCDRLogSize attribute, then
			    the threshold exceeded alarm will never be
			    generated for this CDR log.

			    When a new DSM module is configured, CDR
			    log #1 will automatically be created with a
			    threshold of 900 CDRs. Any other CDR logs
			    that are configured after this will have a
			    default threshold of 0.

			    Changes to this field will be reflected in
			    recfSlotUpdate. A module update will be
			    required in order for the change to take
			    effect. It will not disrupt any channel
			    connections associated with this DSM."
		DEFVAL { 0 }
		::= { recfModDsmRecCDRLogEntry 5 }

recfModDsmRecCDRLogPartitionID 	OBJECT-TYPE
		SYNTAX  INTEGER (1..1023)
		ACCESS  read-write
		STATUS  mandatory
		DESCRIPTION "Parameter Type = Non-intrusive.
			Specifies partition ID of this CDR log.

			Changes to this field will be reflected
			in recfSlotUpdate. A module update will
			be required in order for the change to
			take effect. It will not disrupt any
			channel connections associated with this
			DSM."
		DEFVAL { 1 }
		::= { recfModDsmRecCDRLogEntry 6 }


-- Port Configuration MIB

recfPort            OBJECT IDENTIFIER ::=    { reConfig 6 }

-- T1m Port configuration

recfT1mPortTable 	OBJECT-TYPE
		SYNTAX    SEQUENCE OF RecfT1mPortEntry
		ACCESS    not-accessible
		STATUS    mandatory
		DESCRIPTION " "
		::=  { recfPort 1 }

recfT1mPortEntry 	OBJECT-TYPE
		SYNTAX    RecfT1mPortEntry
		ACCESS    not-accessible
		STATUS    mandatory
		DESCRIPTION " "
		INDEX { recfT1mPortAddr }
		::=  { recfT1mPortTable 1 }

RecfT1mPortEntry         ::=  SEQUENCE {
                         recfT1mPortAddr
	                           PortAddr,
                         recfT1mPortStartMode
                                   INTEGER,
                         recfT1mPortUpdate
                                   INTEGER,
                         recfT1mPortFraming
                                   INTEGER,
                         recfT1mPortLineCodeType
                                   INTEGER,
                         recfT1mPortDs1Option
                                   INTEGER,
                         recfT1mPortDsx1Distance
                                   INTEGER,
                         recfT1mPortEquGain
                                   INTEGER,
                         recfT1mPortBundleMap
                                   OCTET STRING,
                         recfT1mPortErrorThreshold
                                   INTEGER,
                         recfT1mPortSevereThreshold
                                   INTEGER,
                         recfT1mPortAlarmThreshold
                                   INTEGER,
                         recfT1mPortFailThreshold
                                   INTEGER,
                         recfT1mPortFailToggleRequest
                                   INTEGER,
                         recfT1mPortOOSBitPattern
                                   INTEGER,
                         recfT1mPortOOSASignaling
                                   INTEGER,
                         recfT1mPortOOSBSignaling
                                   INTEGER,
                         recfT1mPortOOSCDSignaling
                                   INTEGER,
                         recfT1mPortSigInversion
			   INTEGER
			  }


recfT1mPortAddr 	OBJECT-TYPE
                         SYNTAX    PortAddr
                         ACCESS    read-only
                         STATUS    mandatory
		DESCRIPTION "Parameter Type = Internal."
		::= { recfT1mPortEntry 1 }

recfT1mPortStartMode 	OBJECT-TYPE
		SYNTAX    INTEGER {
                                   automatic(1),
                                   off(2),
                                   erase(3)
                                   }
		ACCESS    read-write
		STATUS    mandatory
		DESCRIPTION "Parameter Type = Intrusive.
			       Setting to erase will fail if the port
			       has any unremoved INLs or channels that
			       are not disconnected. Otherwise, it will
			       return the port's configuration to its
			       default values, and erase any bundles,
			       INLs, and channels on the port."
		DEFVAL { off }
		::= { recfT1mPortEntry 2 }

recfT1mPortUpdate 	OBJECT-TYPE
		SYNTAX   INTEGER {
                                  loaded(1),
			  updateReq(2),
			  resetReq(3)
                                  }
		ACCESS    read-only
		STATUS    mandatory
		DESCRIPTION "Parameter Type = Internal."
		DEFVAL { resetReq }
		::= { recfT1mPortEntry 3 }

-- T1mPort Format is always framed

recfT1mPortFraming 	OBJECT-TYPE
		SYNTAX    INTEGER {
                                   sf(1),
                                   attESF(2),
                                   ansiESF(3)
                                    }
		ACCESS    read-write
		STATUS    mandatory
		DESCRIPTION "Parameter Type = Intrusive."
		DEFVAL { ansiESF }
		::= { recfT1mPortEntry 4 }

recfT1mPortLineCodeType 	OBJECT-TYPE
		SYNTAX    INTEGER {
                                   b8zs(1),
                                   ami(2),
                                   zeroCodeSuppression(3)
			    }
		ACCESS    read-write
		STATUS    mandatory
		DESCRIPTION "Parameter Type = Intrusive."
		DEFVAL { b8zs }
		::= { recfT1mPortEntry 5 }


-- T1mPort TxClockSource is always system

recfT1mPortDs1Option 	OBJECT-TYPE
		SYNTAX    INTEGER {
                                   a(1),
                                   b(2),
                                   c(3)
                                    }
		ACCESS    read-write
		STATUS    mandatory
		DESCRIPTION "Parameter Type = Intrusive.
			This field refers to the line build out of the
			T1M port. The values should be interpreted as
			follows:
			a: 0 dB
			b: -7.5 dB
			c: -15 dB."
		DEFVAL { a }
		::= { recfT1mPortEntry 6 }

recfT1mPortDsx1Distance 	OBJECT-TYPE
		SYNTAX    INTEGER {
                                   from0to133ft(1),
                                   from134to266ft(2),
                                   from267to399ft(3),
                                   from400to533ft(4),
                                   from534to655ft(5),
                                   fccOptionA(6)
                                    }
		ACCESS    read-write
		STATUS    mandatory
		DESCRIPTION "Parameter Type = Intrusive."
		DEFVAL { from0to133ft }
		::= { recfT1mPortEntry 7 }


recfT1mPortEquGain 	OBJECT-TYPE
		SYNTAX    INTEGER {
                                   g36db(1),
                                   g26db(2)
                                    }
		ACCESS    read-write
		STATUS    mandatory
		DESCRIPTION "Parameter Type = Intrusive."
		DEFVAL { g36db }
		::= { recfT1mPortEntry 8 }

recfT1mPortBundleMap 	OBJECT-TYPE
		SYNTAX    OCTET STRING (SIZE  (24))
		ACCESS    read-write
		STATUS    mandatory
		DESCRIPTION "Parameter Type = Immediate.
		       Each byte represents a DS0 in T1m Port,
		       starting 1 from the right most byte. The
		       bundle is identified by the number of the
		       lowest DS0 of the bundle."
		::= { recfT1mPortEntry 9 }

recfT1mPortErrorThreshold 	OBJECT-TYPE
		SYNTAX    INTEGER (0..65535)
		ACCESS    read-write
		STATUS    mandatory
		DESCRIPTION "Parameter Type = Non-intrusive."
		DEFVAL { 65535 }
		::= { recfT1mPortEntry 10 }

recfT1mPortSevereThreshold 	OBJECT-TYPE
		SYNTAX    INTEGER (0..65535)
		ACCESS    read-write
		STATUS    mandatory
		DESCRIPTION "Parameter Type = Non-intrusive."
		DEFVAL { 65535 }
		::= { recfT1mPortEntry 11 }

recfT1mPortAlarmThreshold 	OBJECT-TYPE
		SYNTAX    INTEGER (1..9)
		ACCESS    read-write
		STATUS    mandatory
		DESCRIPTION "Parameter Type = Non-intrusive.
		       If port BER quality is below this
		       threshold for four consecutive seconds, a
		       port error alarm will be sent."
		DEFVAL { 3 }
		::= { recfT1mPortEntry 12 }

recfT1mPortFailThreshold 	OBJECT-TYPE
		SYNTAX    INTEGER (1..9)
		ACCESS    read-write
		STATUS    mandatory
		DESCRIPTION "Parameter Type = Non-intrusive.
		       If port BER quality is below this
		       threshold for ten consecutive seconds, a
		       port down alarm will be sent."
		DEFVAL { 2 }
		::= { recfT1mPortEntry 13 }

recfT1mPortFailToggleRequest 	OBJECT-TYPE
		SYNTAX    INTEGER {
                                   toggleIfPortFail(61),
                                   noToggle(62)
                                   }
		ACCESS    read-write
		STATUS    mandatory
		DESCRIPTION "Parameter Type = Non-intrusive."
		DEFVAL { toggleIfPortFail }
		::= { recfT1mPortEntry 14 }

recfT1mPortOOSBitPattern 	OBJECT-TYPE
		SYNTAX    INTEGER {
                                   x7f(1),
                                   x1a(2),
                                   xd5(3),
                                   x7e(4)
                                    }
		ACCESS    read-write
		STATUS    mandatory
		DESCRIPTION "Parameter Type = Intrusive."
		DEFVAL { x7f }
		::= { recfT1mPortEntry 15 }

recfT1mPortOOSASignaling 	OBJECT-TYPE
		SYNTAX    INTEGER {
                                   space(1),
                                   mark(2),
                                   spaceMark(3),
                                   markSpace(4)
                                    }
		ACCESS    read-write
		STATUS    mandatory
		DESCRIPTION "Parameter Type = Intrusive."
		DEFVAL { spaceMark }
		::= { recfT1mPortEntry 16 }

recfT1mPortOOSBSignaling 	OBJECT-TYPE
		SYNTAX    INTEGER {
                                   space(1),
                                   mark(2),
                                   spaceMark(3),
                                   markSpace(4)
                                    }
		ACCESS    read-write
		STATUS    mandatory
		DESCRIPTION "Parameter Type = Intrusive."
		DEFVAL { spaceMark }
		::= { recfT1mPortEntry 17 }

recfT1mPortOOSCDSignaling 	OBJECT-TYPE
		SYNTAX    INTEGER {
                                   spaceSpace(1),
                                   markMark(2),
                                   spaceMark(3),
                                   markSpace(4)
                                    }
		ACCESS    read-write
		STATUS    mandatory
		DESCRIPTION "Parameter Type = Intrusive."
		DEFVAL { spaceMark }
		::= { recfT1mPortEntry 18 }

recfT1mPortSigInversion 	OBJECT-TYPE
		SYNTAX    INTEGER {
                                   normal(1),
                                   inverted(2)
                                    }
		ACCESS    read-write
		STATUS    deprecated
		DESCRIPTION "Parameter Type = Intrusive."
		DEFVAL { normal }
		::= { recfT1mPortEntry 19 }

-- E1m Port configuration

recfE1mPortTable 	OBJECT-TYPE
		SYNTAX    SEQUENCE OF RecfE1mPortEntry
		ACCESS    not-accessible
		STATUS    mandatory
		DESCRIPTION " "
		::=  { recfPort 2 }

recfE1mPortEntry 	OBJECT-TYPE
		SYNTAX    RecfE1mPortEntry
		ACCESS    not-accessible
		STATUS    mandatory
		DESCRIPTION " "
		INDEX { recfE1mPortAddr }
		::=  { recfE1mPortTable 1 }

RecfE1mPortEntry         ::=  SEQUENCE {
                         recfE1mPortAddr
                                   PortAddr,
                         recfE1mPortStartMode
                                   INTEGER,
                         recfE1mPortUpdate
                                   INTEGER,
                         recfE1mPortFraming
                                   INTEGER,
                         recfE1mPortCrcMultiFrame
                                   INTEGER,
                         recfE1mPortSigInversion
                                   INTEGER,
                         recfE1mPortInternationalBit
                                   INTEGER,
                         recfE1mPortNationalBit
                                   INTEGER,
                         recfE1mPortTransmitEBit
                                   INTEGER,
                         recfE1mPortReceiveEBit
                                   INTEGER,
                         recfE1mPortBundleMap
                                   OCTET STRING,
                         recfE1mPortErrorThreshold
                                   INTEGER,
                         recfE1mPortSevereThreshold
                                   INTEGER,
                         recfE1mPortAlarmThreshold
                                   INTEGER,
                         recfE1mPortFailThreshold
                                   INTEGER,
                         recfE1mPortFailToggleRequest
                                   INTEGER,
                         recfE1mPortOOSBitPattern
                                   INTEGER,
                         recfE1mPortOOSASignaling
                                   INTEGER,
                         recfE1mPortOOSBSignaling
                                   INTEGER,
                         recfE1mPortOOSCDSignaling
                                   INTEGER
                          }


recfE1mPortAddr 	OBJECT-TYPE
		SYNTAX    PortAddr
		ACCESS    read-only
		STATUS    mandatory
		DESCRIPTION "Parameter Type = Internal."
		::= { recfE1mPortEntry 1 }

recfE1mPortStartMode 	OBJECT-TYPE
		SYNTAX    INTEGER {
                                   automatic(1),
                                   off(2),
                                   erase(3)
                                   }
		ACCESS    read-write
		STATUS    mandatory
		DESCRIPTION "Parameter Type = Intrusive.
		       Setting to erase will fail if the port
		       has any unremoved INLs or channels that
		       are not disconnected. Otherwise, it will
		       return the port's configuration to its
		       default values, and erase any bundles,
		       INLs, and channels on the port."
		DEFVAL { off }
		::= { recfE1mPortEntry 2 }


recfE1mPortUpdate 	OBJECT-TYPE
		SYNTAX    INTEGER {
                                   loaded(1),
				   updateReq(2),
				   resetReq(3)
                                   }
		ACCESS    read-only
		STATUS    mandatory
		DESCRIPTION "Parameter Type = Internal."
		DEFVAL { resetReq }
		::= {  recfE1mPortEntry 3 }

-- E1M Port Format is always framed

recfE1mPortFraming 	OBJECT-TYPE
		SYNTAX    INTEGER {
                                   g732n(1),
                                   g732s(2)
                                    }
		ACCESS    read-write
		STATUS    mandatory
		DESCRIPTION "Parameter Type = Intrusive."
		DEFVAL { g732n }
		::= { recfE1mPortEntry 4 }

recfE1mPortCrcMultiFrame 	OBJECT-TYPE
		SYNTAX    INTEGER {
                                   enable(1),
                                   disable(2)
                                    }
		ACCESS    read-write
		STATUS    mandatory
		DESCRIPTION "Parameter Type = Intrusive."
		DEFVAL { disable }
		::= { recfE1mPortEntry 5 }


recfE1mPortSigInversion 	OBJECT-TYPE
		SYNTAX    INTEGER {
                                   normal(1),
                                   inverted(2)
                                    }
		ACCESS    read-write
		STATUS    deprecated
		DESCRIPTION "Parameter Type = Intrusive."
		DEFVAL { normal }
		::= { recfE1mPortEntry 6 }

recfE1mPortInternationalBit 	OBJECT-TYPE
		SYNTAX    INTEGER (0..1)
		ACCESS    read-write
		STATUS    mandatory
		DESCRIPTION "Parameter Type = Intrusive."
		DEFVAL { 1 }
		::= { recfE1mPortEntry 7 }

recfE1mPortNationalBit 	OBJECT-TYPE
		SYNTAX    INTEGER (0..31)
		ACCESS    read-write
		STATUS    mandatory
		DESCRIPTION "Parameter Type = Intrusive."
		DEFVAL { 31 }
		::= { recfE1mPortEntry 8 }

recfE1mPortTransmitEBit 	OBJECT-TYPE
		SYNTAX    INTEGER {
                                   enable(1),
                                   disable(2)
                                   }
		ACCESS    read-write
		STATUS    mandatory
		DESCRIPTION "Parameter Type = Intrusive."
		DEFVAL { disable }
		::= { recfE1mPortEntry 9 }

recfE1mPortReceiveEBit 	OBJECT-TYPE
		SYNTAX    INTEGER {
                                   monitor(1),
                                   ignore(2)
                                    }
		ACCESS    read-write
		STATUS    mandatory
		DESCRIPTION "Parameter Type = Intrusive."
		DEFVAL { ignore }
		::= { recfE1mPortEntry 10 }

recfE1mPortBundleMap 	OBJECT-TYPE
		SYNTAX    OCTET STRING (SIZE (31))
		ACCESS    read-write
		STATUS    mandatory
		DESCRIPTION "Parameter Type = Immediate.
		       Each byte represents a DS0 in E1m Port,
		       starting 1 from the right most byte. The
		       bundle is identified by the number of the
		       lowest DS0 of the bundle. If framing is
		       g732s, time slot 16 is reserved to be a
		       signalling byte."
		::= { recfE1mPortEntry 11 }

recfE1mPortErrorThreshold 	OBJECT-TYPE
		SYNTAX    INTEGER (0..65535)
		ACCESS    read-write
		STATUS    mandatory
		DESCRIPTION "Parameter Type = Non-intrusive."
		DEFVAL { 65535 }
		::= { recfE1mPortEntry 12 }

recfE1mPortSevereThreshold 	OBJECT-TYPE
		SYNTAX    INTEGER (0..65535)
		ACCESS    read-write
		STATUS    mandatory
		DESCRIPTION "Parameter Type = Non-intrusive."
		DEFVAL { 65535 }
		::= { recfE1mPortEntry 13 }

recfE1mPortAlarmThreshold 	OBJECT-TYPE
		SYNTAX    INTEGER (1..9)
		ACCESS    read-write
		STATUS    mandatory
		DESCRIPTION "Parameter Type = Non-intrusive.
			If port BER quality is below this
			threshold for four consecutive seconds, a
		       	port error alarm will be sent."
		DEFVAL { 3 }
		::= { recfE1mPortEntry 14 }

recfE1mPortFailThreshold 	OBJECT-TYPE
		SYNTAX    INTEGER (1..9)
		ACCESS    read-write
		STATUS    mandatory
		DESCRIPTION "Parameter Type = Non-intrusive.
		       If port BER quality is below this
		       threshold for ten consecutive seconds, a
		       port down alarm will be sent."
		DEFVAL { 2 }
		::= { recfE1mPortEntry 15 }

recfE1mPortFailToggleRequest 	OBJECT-TYPE
		SYNTAX    INTEGER {
                                   toggleIfPortFail(61),
                                   noToggle(62)
                                   }
		ACCESS    read-write
		STATUS    mandatory
		DESCRIPTION "Parameter Type = Non-intrusive."
		DEFVAL { toggleIfPortFail }
		::= { recfE1mPortEntry 16 }

recfE1mPortOOSBitPattern 	OBJECT-TYPE
		SYNTAX    INTEGER {
                                   x7f(1),
                                   x1a(2),
                                   xd5(3),
                                   x7e(4)
                                    }
		ACCESS    read-write
		STATUS    mandatory
		DESCRIPTION "Parameter Type = Intrusive."
		DEFVAL { xd5 }
		::= { recfE1mPortEntry 17 }

recfE1mPortOOSASignaling 	OBJECT-TYPE
		SYNTAX    INTEGER {
                                   space(1),
                                   mark(2),
                                   spaceMark(3),
                                   markSpace(4)
                                    }
		ACCESS    read-write
		STATUS    mandatory
		DESCRIPTION "Parameter Type = Intrusive."
		DEFVAL { spaceMark }
		::= { recfE1mPortEntry 18 }

recfE1mPortOOSBSignaling 	OBJECT-TYPE
		SYNTAX    INTEGER {
                                   space(1),
                                   mark(2),
                                   spaceMark(3),
                                   markSpace(4)
                                    }
		ACCESS    read-write
		STATUS    mandatory
		DESCRIPTION "Parameter Type = Intrusive."
		DEFVAL { spaceMark }
		::= { recfE1mPortEntry 19 }

recfE1mPortOOSCDSignaling 	OBJECT-TYPE
		SYNTAX    INTEGER {
                                   spaceSpace(1),
                                   markMark(2),
                                   spaceMark(3),
                                   markSpace(4)
                                    }
		ACCESS    read-write
		STATUS    mandatory
		DESCRIPTION "Parameter Type = Intrusive."
		DEFVAL { spaceMark }
		::= { recfE1mPortEntry 20 }


-- SDM port configuration

recfSdmPortTable 	OBJECT-TYPE
		SYNTAX  SEQUENCE OF RecfSdmPortEntry
		ACCESS  not-accessible
		STATUS  mandatory
		DESCRIPTION " "
		::=  { recfPort 3 }

recfSdmPortEntry 	OBJECT-TYPE
		SYNTAX  RecfSdmPortEntry
		ACCESS  not-accessible
		STATUS  mandatory
		DESCRIPTION " "
		INDEX { recfSdmPortAddr }
		::=  { recfSdmPortTable 1 }

RecfSdmPortEntry                ::=  SEQUENCE {
			recfSdmPortAddr
				PortAddr,
			recfSdmPortStartMode
				INTEGER,
			recfSdmPortUpdate
				INTEGER,
			recfSdmPortSpeed
				INTEGER,
			recfSdmPortInterface
				INTEGER,
			recfSdmPortTxClockSource
				INTEGER,
			recfSdmPortBitMode
				INTEGER,
			recfSdmPortOOSOper
				INTEGER,
			recfSdmPortGen
				INTEGER,
			recfSdmPortPolarity
				INTEGER,
			recfSdmPortType
				INTEGER,
			recfSdmPortINLNumber
				INTEGER,
			recfSdmDeviceType
				INTEGER,
			recfSdmPortPartitionID
				INTEGER,
			recfSdmPortFunctions
				OCTET STRING,
			recfSdmPortContentionSet
				INTEGER,
			recfSdmPortLoopbackSupport
				INTEGER,
			recfSdmPortSatelliteBuffer
				INTEGER,
			recfSdmPortFailToggleRequest
				INTEGER,
			recfSdmPortKGPolarity
				INTEGER,
			recfSdmPortKGSignalType
				INTEGER,
			recfSdmPortKGMode
				INTEGER
			}

recfSdmPortAddr 	OBJECT-TYPE
			SYNTAX  PortAddr
			ACCESS  read-only
			STATUS  mandatory
		DESCRIPTION "Parameter Type = Internal."
		::= { recfSdmPortEntry 1 }

recfSdmPortStartMode 	OBJECT-TYPE
		SYNTAX  INTEGER {
			automatic(1),
			off(2),
			erase(3)
			}
		ACCESS  read-write
		STATUS  mandatory
		DESCRIPTION "Parameter Type = Intrusive.
			Setting to erase will fail if the port
			has any unremoved INLs or channels that
			are not disconnected. Otherwise, it will
			return the port's configuration to its
			default values, and erase any INLs and
			channels on the port."
		DEFVAL { off }
		::= { recfSdmPortEntry 2 }

recfSdmPortUpdate 	OBJECT-TYPE
		SYNTAX  INTEGER {
			loaded(1),
			updateReq(2),
			resetReq(3)
			}
		ACCESS  read-only
		STATUS  mandatory
		DESCRIPTION "Parameter Type = Intrusive."
		DEFVAL { resetReq }
		::=  { recfSdmPortEntry 3 }

recfSdmPortSpeed 	OBJECT-TYPE
		SYNTAX  INTEGER {
			s1200(9), s2400(18), s4800(36),
			s7200(54), s9600(72),
			s14400(108), s19200(144),
			s38400(288), s48000(360),

			bsf448k(3360), bsf896k(6720),
			bsf1344k(10080),

			b64k(480), b128k(960),
			b192k(1440), b256k(1920),
			b320k(2400), b384k(2880),
			b512k(3840), b576k(4320),
			b640k(4800), b704k(5280),
			b768k(5760), b832k(6240),
			b960k(7200), b1024k(7680),
			b1088k(8160), b1152k(8640),
			b1216k(9120), b1280k(9600),
			b1408k(10560), b1472k(11040),
			b1536k(11520), b1600k(12000),
			b1664k(12480), b1728k(12960),
			b1792k(13440), b1856k(13920),
			b1920k(14400), b1984k(14880),
			b2048k(15360),

			sf56k(420), sf112k(840),
			sf168k(1260), sf224k(1680),
			sf280k(2100), sf336k(2520),
			sf392k(2940), sf504k(3780),
			sf560k(4200), sf616k(4620),
			sf672k(5040), sf728k(5460),
			sf784k(5880), sf840k(6300),
			sf952k(7140), sf1008k(7560),
			sf1064k(7980), sf1120k(8400),
			sf1176k(8820), sf1232k(9240),
			sf1288k(9660)
			}
		ACCESS  read-write
		STATUS  mandatory
		DESCRIPTION "Parameter Type = Intrusive.
			s is for subrate speeds.

			b is for bundle speeds (n x 64K).

			sf is for stuffed speeds (n x 56K).

			bsf is for speeds that can be bundle
			(b8bit) or stuffed (b7bit), depending
			on the value of recfSdmPortBitMode.

			sf56k is the switched 56k if
			recfSdmDeviceType=2."
		DEFVAL { b64k }
		::= { recfSdmPortEntry 4 }

recfSdmPortInterface 	OBJECT-TYPE
		SYNTAX  INTEGER {
			dte1(1),
			dte2(2),
			dte3(3),
			dce1(4),
			dce2(5),
			dce3(6)
			}
		ACCESS  read-write
		STATUS  mandatory
		DESCRIPTION "Parameter Type = Intrusive."
		DEFVAL { dce1 }
		::= { recfSdmPortEntry 5 }

recfSdmPortTxClockSource 	OBJECT-TYPE
		SYNTAX  INTEGER {
			system(1),
			receive(2),
			send(3)
			}
		ACCESS  read-write
		STATUS  mandatory
		DESCRIPTION "Parameter Type = Intrusive."
		DEFVAL { system }
		::= { recfSdmPortEntry 6 }

recfSdmPortBitMode 	OBJECT-TYPE
		SYNTAX  INTEGER {
			b7bit(1),
			b8bit(2)
			}
		ACCESS  read-write
		STATUS  mandatory
		DESCRIPTION "Parameter Type = Intrusive."
		DEFVAL { b8bit }
		::= { recfSdmPortEntry 7 }

recfSdmPortOOSOper 	OBJECT-TYPE
		SYNTAX  INTEGER {
			doNothing(1),
			forceFNS(2),
			mark(3),
			markFF(4),
			space(5),
			spaceFF(6)
			}
		ACCESS  read-write
		STATUS  mandatory
		DESCRIPTION "Parameter Type = Intrusive."
		DEFVAL { doNothing }
		::= { recfSdmPortEntry 8 }

recfSdmPortGen 	OBJECT-TYPE
		SYNTAX  INTEGER {
			dsrDtr(2),
			trans(3)
			}
		ACCESS  read-write
		STATUS  mandatory
		DESCRIPTION "Parameter Type = Intrusive."
		DEFVAL { trans }
		::= { recfSdmPortEntry 9 }

recfSdmPortPolarity 	OBJECT-TYPE
		SYNTAX  INTEGER {
			normal(1),
			inverted(2)
			}
		ACCESS  read-write
		STATUS  mandatory
		DESCRIPTION "Parameter Type = Intrusive."
		DEFVAL { normal }
		::= { recfSdmPortEntry 10 }

recfSdmPortType 	OBJECT-TYPE
		SYNTAX  INTEGER {
			null(1),
			io(2),
			bandContent(3),
			inl(4),
			fsm16Connect(5)
			}
		ACCESS  read-write
		STATUS  mandatory
		DESCRIPTION "Parameter Type = Intrusive."
		DEFVAL { null }
		::= { recfSdmPortEntry 11 }

recfSdmPortINLNumber 	OBJECT-TYPE
		SYNTAX  INTEGER (0..31)
		ACCESS  read-only
		STATUS  mandatory
		DESCRIPTION "Parameter Type = Intrusive.
			Applicable only if recfSdmPortType is
			set to inl."
		DEFVAL { 0 }
		::= { recfSdmPortEntry 12 }

recfSdmDeviceType 	OBJECT-TYPE
		SYNTAX  INTEGER (1..255)
		ACCESS  read-write
		STATUS  mandatory
		DESCRIPTION "Parameter Type = Intrusive.
			This field indicates the type of device
			connected to the port.

			Values 1-10 and 255 are reserved by
			ST-50, of which 1 is for voice, 2 is
			for switch 56, 3 is for clear channel,
			and 255 is for INL. Values 11 to 254
			can be used by the user to define
			user-specific device types.

			For TDM channels connected between I/O
			ports, the channel will not connect if
			the device types do not match. For I/O
			to server port connections, the device
			types will not be compared.

			This field is not used by the ST node
			if recfSdmPortType is null or inl. Note
			that if the recfSdmPortType is inl but
			this field is not 255, the inl will not
			be failed. Also, if the recfSdmPortType
			is not inl but this field is 255, then
			the channel defined on this port will
			still be able to connect."
		DEFVAL { 3 }
		::= { recfSdmPortEntry 13 }

recfSdmPortPartitionID 	OBJECT-TYPE
		SYNTAX  INTEGER (1..1023)
		ACCESS  read-write
		STATUS  mandatory
		DESCRIPTION "Parameter Type = Intrusive."
		::= { recfSdmPortEntry 14 }

recfSdmPortFunctions 	OBJECT-TYPE
		SYNTAX  OCTET STRING (SIZE (1))
		ACCESS  read-write
		STATUS  mandatory
		DESCRIPTION "Parameter Type = Intrusive.
			The four least significant bits
			represent whether the function mapped
			to that bit should be forced or not.
			bit 1 (lsb) - DSR if DCE,
				      DTR if DTE
			bit 2 - DCD if DCE,
				RTS if DTE
			bit 3 - reserved
			bit 4 - CTS if DCE,
				reserved if DTE

			The four most significant bits
			represent what the function mapped
			to that bit should be forced to when
			that function is suppose to be forced.
			bit 5 - DSR if DCE,
				DTR if DTE
			bit 6 - DCD if DCE,
				RTS if DTE
			bit 7 - reserved
			bit 8 - CTS if DCE,
				reserved if DTE"
		DEFVAL { '00'h }
		::= { recfSdmPortEntry 15 }

recfSdmPortContentionSet 	OBJECT-TYPE
			SYNTAX  INTEGER {
			f1nf1(1),
			f2nf2(2),
			f4nf4(7),
			nf4f4(8),
			disable(255)
			}
			ACCESS  read-write
			STATUS  mandatory
		DESCRIPTION "Parameter Type = Intrusive."
		DEFVAL { disable }
		::= { recfSdmPortEntry 16 }

recfSdmPortLoopbackSupport 	OBJECT-TYPE
		SYNTAX  INTEGER {
			none(15),
			ll(13),
			rl(11),
			tm(7),
			llRl(9),
			llTm(5),
			rlTm(3),
			llRlTm(1)
			}
		ACCESS  read-write
		STATUS  mandatory
		DESCRIPTION "Parameter Type = Intrusive.
			Indicates whether the SDM port should
			support the signals for LL, RL, and TM.
			If a signal is supported, then that
			loopback signal will be recognized by
			the SDM. Otherwise, the signal will be
			ignored."
		DEFVAL { none }
		::= { recfSdmPortEntry 17 }

recfSdmPortSatelliteBuffer 	OBJECT-TYPE
		SYNTAX  INTEGER {
			enable(15),
			disable(3)
			}
		ACCESS  read-write
		STATUS  mandatory
		DESCRIPTION "Parameter Type = Intrusive."
		DEFVAL { disable }
		::= { recfSdmPortEntry 18 }

recfSdmPortFailToggleRequest 	OBJECT-TYPE
		SYNTAX  INTEGER {
			toggleIfPortFail(61),
			noToggle(62)
			}
		ACCESS  read-write
		STATUS  mandatory
		DESCRIPTION "Parameter Type = Non-intrusive."
		DEFVAL { toggleIfPortFail }
		::= { recfSdmPortEntry 19 }

recfSdmPortKGPolarity 	OBJECT-TYPE
		SYNTAX  INTEGER {
			kgPositive(1),
			kgNegative(2)
			}
		ACCESS  read-write
		STATUS  mandatory
		DESCRIPTION "Parameter Type = Intrusive.
			Specifies the polarity of KG-resync
			signal."
		DEFVAL { kgPositive }
		::= { recfSdmPortEntry 20 }

recfSdmPortKGSignalType 	OBJECT-TYPE
		SYNTAX  INTEGER {
			kgPulse(1),
			kgLevel(2)
			}
		ACCESS  read-write
		STATUS  mandatory
		DESCRIPTION "Parameter Type = Intrusive.
			Specifies the type of of KG-resync
			signal."
		DEFVAL { kgPulse }
		::= { recfSdmPortEntry 21 }

recfSdmPortKGMode 	OBJECT-TYPE
		SYNTAX  INTEGER {
			kgEnable(1),
			kgDisable(2)
			}
		ACCESS  read-write
		STATUS  mandatory
		DESCRIPTION "Parameter Type = Intrusive.
			Specifies the KG-resync mode."
		DEFVAL { kgDisable }
		::= { recfSdmPortEntry 22 }


-- Bundle Configuration

recfBundleTable 	OBJECT-TYPE
		SYNTAX    SEQUENCE OF RecfBundleEntry
		ACCESS    not-accessible
		STATUS    mandatory
		DESCRIPTION " "
		::=  { reConfig 7 }

recfBundleEntry 	OBJECT-TYPE
		SYNTAX    RecfBundleEntry
		ACCESS    not-accessible
		STATUS    mandatory
		DESCRIPTION " "
		INDEX { recfBundleAddr }
		::=  { recfBundleTable 1 }

RecfBundleEntry          ::=  SEQUENCE {
                         recfBundleAddr
                                   BundleAddr,
                         recfBundleStartMode
                                   INTEGER,
                         recfBundleUpdate
                                   INTEGER,
                         recfBundleSignaling
                                   INTEGER,
                         recfBundleOOSBitPattern
                                   INTEGER,
                         recfBundleOOSASignaling
                                   INTEGER,
                         recfBundleOOSBSignaling
                                   INTEGER,
                         recfBundleOOSCDSignaling
                                   INTEGER,
                         recfBundleNullIdlePattern
                                   INTEGER,
                         recfBundleBwCntIdlePattern
                                   INTEGER,
                         recfBundleBusyOutTimer
                                   INTEGER,
                         recfBundleSeizureTime
                                   INTEGER,
                         recfBundlePreemptionTime
                                   INTEGER,
                         recfBundleOrgDisconnectTime
                                   INTEGER,
                         recfBundleAttenuationRx
                                   INTEGER,
                         recfBundleAttenuationTx
                                   INTEGER,
                         recfBundleType
                                   INTEGER,
                         recfBundleINLNumber
                                   INTEGER,
                         recfBundleDeviceType
                                   INTEGER,
			 recfBundleContentionSet
				   INTEGER,
                         recfBundlePartitionID
                                   INTEGER,
                         recfBundleBwCntBusyPattern
                                   INTEGER,
			 recfBundleSigInversion
				   INTEGER,
			 recfBundleDataPolarity
				   INTEGER,
			 recfBundlePCMLaw
				   INTEGER
                          }

recfBundleAddr 	OBJECT-TYPE
                         SYNTAX    BundleAddr
                         ACCESS    read-only
                         STATUS    mandatory
		DESCRIPTION "Parameter Type = Internal."
		::= { recfBundleEntry 1 }

recfBundleStartMode 	OBJECT-TYPE
		SYNTAX    INTEGER {
                                   automatic(1),
                                   off(2),
                                   erase(3)
                                   }
		ACCESS    read-write
		STATUS    mandatory
		DESCRIPTION "Parameter Type = Intrusive.
			       Setting to erase will fail if the bundle
			       has an unremoved INL or a channel that
			       is not disconnected. Otherwise, it will
			       erase the bundle configuration as well as
			       the INL or channel defined on the bundle.
			       It will also erase this bundle from the
			       T1M or E1M port bundle map."
		DEFVAL { off }
		::= { recfBundleEntry 2 }

recfBundleUpdate 	OBJECT-TYPE
		SYNTAX    INTEGER {
                                   loaded(1),
				   updateReq(2),
				   resetReq(3)
                                   }
		ACCESS     read-only
		STATUS     mandatory
		DESCRIPTION "Parameter Type = Internal."
		DEFVAL { resetReq }
		::= { recfBundleEntry 3 }

recfBundleSignaling 	OBJECT-TYPE
		SYNTAX    INTEGER {
                                   none(1),
                                   a(2),
                                   ab(3),
                                   abcd(4)
                                    }
		ACCESS    read-write
		STATUS    mandatory
		DESCRIPTION "Parameter Type = Intrusive."
		DEFVAL { none }
		::= { recfBundleEntry 4 }

recfBundleOOSBitPattern 	OBJECT-TYPE
		SYNTAX    INTEGER {
                                   x7f(1),
                                   x1a(2),
                                   xd5(3),
                                   x7e(4)
                                    }
		ACCESS    read-write
		STATUS    mandatory
		DESCRIPTION "Parameter Type = Intrusive."
		::= { recfBundleEntry 5 }

recfBundleOOSASignaling 	OBJECT-TYPE
		SYNTAX    INTEGER {
                                   space(1),
                                   mark(2),
                                   spaceMark(3),
                                   markSpace(4)
                                    }
		ACCESS    read-write
		STATUS    mandatory
		DESCRIPTION "Parameter Type = Intrusive."
		DEFVAL { spaceMark }
		::= { recfBundleEntry 6 }

recfBundleOOSBSignaling 	OBJECT-TYPE
		SYNTAX    INTEGER {
                                   space(1),
                                   mark(2),
                                   spaceMark(3),
                                   markSpace(4)
                                    }
		ACCESS    read-write
		STATUS    mandatory
		DESCRIPTION "Parameter Type = Intrusive."
		DEFVAL { spaceMark }
		::= { recfBundleEntry 7 }

recfBundleOOSCDSignaling 	OBJECT-TYPE
		SYNTAX    INTEGER {
                                   spaceSpace(1),
                                   markMark(2),
                                   spaceMark(3),
                                   markSpace(4)
                                    }
		ACCESS    read-write
		STATUS    mandatory
		DESCRIPTION "Parameter Type = Intrusive."
		DEFVAL { spaceMark }
		::= { recfBundleEntry 8 }


recfBundleNullIdlePattern 	OBJECT-TYPE
		SYNTAX    INTEGER {
                                    space(1),
                                    mark(2)
                                    }
		ACCESS    read-write
		STATUS    mandatory
		DESCRIPTION "Parameter Type = Intrusive."
		DEFVAL { mark }
		::= { recfBundleEntry 9 }

recfBundleBwCntIdlePattern 	OBJECT-TYPE
		SYNTAX  INTEGER {
			a0-b0-c0-d0(16),
			a0-b0-c0-d1(8),
			a0-b0-c1-d0(4),
			a0-b0-c1-d1(12),
			a0-b1-c0-d0(2),
			a0-b1-c0-d1(10),
			a0-b1-c1-d0(6),
			a0-b1-c1-d1(14),
			a1-b0-c0-d0(1),
			a1-b0-c0-d1(9),
			a1-b0-c1-d0(5),
			a1-b0-c1-d1(13),
			a1-b1-c0-d0(3),
			a1-b1-c0-d1(11),
			a1-b1-c1-d0(7),
			a1-b1-c1-d1(15)
			}
		ACCESS  read-write
		STATUS  mandatory
		DESCRIPTION "Parameter Type = Intrusive.
			Bit pattern output to equipment
			indicating bundle availability.

			T1M bundles will have a default pattern
			of a0-b0-c0-d0. E1M bundles will have a
			default pattern of a0-b1-c0-d1."
		::= { recfBundleEntry 10 }

recfBundleBusyOutTimer 	OBJECT-TYPE
		SYNTAX    INTEGER {
			sec5(5),
			sec10(10),
			sec20(20),
			sec30(30),
			sec40(40),
			sec50(50),
			sec60(60),
			sec70(70),
			sec80(80),
			sec90(90),
			sec100(100),
			sec110(110),
			sec120(120),
			sec130(130),
			sec140(140),
			sec150(150),
			sec160(160),
			sec170(170),
			sec180(180),
			sec190(190),
			sec200(200),
			sec210(210),
			sec220(220),
			sec230(230),
			sec240(240),
			permanent(255)
                                    }
		ACCESS    read-write
		STATUS    mandatory
		DESCRIPTION "Parameter Type = Intrusive."
		DEFVAL { permanent }
		::= { recfBundleEntry 11 }

recfBundleSeizureTime 	OBJECT-TYPE
		SYNTAX    INTEGER {
                                    ms50(1), ms100(2), ms150(3),
                                    ms200(4), ms250(5), ms300(6),
                                    ms350(7), ms400(8), ms450(9),
                                    ms500(10), ms550(11),
                                    ms600(12),
                                    ms650(13), ms700(14),
                                    ms750(15), ms800(16),
                                    ms850(17), ms900(18),
                                    ms950(19), ms1000(20)
                                    }
		ACCESS     read-write
		STATUS     mandatory
		DESCRIPTION "Parameter Type = Non-intrusive.
			For bandwidth contention channel."
		DEFVAL { ms50 }
		::= { recfBundleEntry 12 }


recfBundlePreemptionTime 	OBJECT-TYPE
		SYNTAX     INTEGER {
                                    none(1), ms250(2), ms300(3),
                                    ms350(4), ms400(5), ms450(6),
                                    ms500(7), ms550(8), ms600(9),
                                    ms650(10), ms700(11),
                                    ms750(12), ms800(13),
                                    ms850(14), ms900(15),
                                    ms950(16), s1(20), s2(21),
                                    s3(22), s4(23), s5(24),
                                    s6(25), s7(26), s8(27),
                                    s9(28), s10(29)
                                    }
		ACCESS    read-write
		STATUS    mandatory
		DESCRIPTION "Parameter Type = Non-intrusive.
			For bandwidth contention channel."
		DEFVAL { none }
		::= { recfBundleEntry 13 }


recfBundleOrgDisconnectTime 	OBJECT-TYPE
		SYNTAX    INTEGER {
                                      ms150(1), ms200(2), ms250(3),
                                      ms300(4), ms350(5), ms400(6),
                                      ms450(7), ms500(8),
                                      s10(11), s15(12), s20(13),
                                      s25(14), s30(15), s35(16),
                                      s40(17), s45(18), s50(19),
                                      s55(20), s60(21), s65(22),
                                      s70(23), s75(24), s80(25),
                                      s85(26), s90(27), s95(28),
                                      s100(29), s105(30), s110(31),
                                      s115(32), s120(33), s125(34),
                                      s130(35), s135(36), s140(37),
                                      s145(38), s150(39), s155(40),
                                      s160(41), s165(42), s170(43),
                                      s175(44), s180(45), s185(46),
                                      s190(47), s195(48),
				      s200(49), s205(50), s210(51),
                                      s215(52), s220(53), s225(54),
                                      s230(55), s235(56), s240(57),
                                      s245(58), s250(59), s255(60),
                                      s260(61), s265(62), s270(63),
                                      s275(64), s280(65), s285(66),
                                      s290(67), s295(68),
                                      s300(69), s305(70), s310(71),
                                      s315(72), s320(73), s325(74),
                                      s330(75), s335(76), s340(77),
                                      s345(78), s350(79), s355(80),
                                      s360(81), s365(82), s370(83),
                                      s375(84), s380(85), s385(86),
                                      s390(87), s395(88),
                                      s400(89), s405(90), s410(91)
                                      }
		ACCESS      read-write
		STATUS      mandatory
		DESCRIPTION "Parameter Type = Non-intrusive.
			For bandwidth contention channel. Units that
			start with 's' are in units of 1/10 seconds
			(i.e., s10 is 1.0 seconds)."
		DEFVAL { s180 }
		::= { recfBundleEntry 14 }

recfBundleAttenuationRx 	OBJECT-TYPE
		SYNTAX    INTEGER {
                                   p0db(2),
                                   p3db(3),
                                   p6db(4),
                                   p9db(5)
                                   }
		ACCESS    read-write
		STATUS    mandatory
		DESCRIPTION "Parameter Type = Intrusive.
			For voice channel."
		DEFVAL { p0db }
		::= { recfBundleEntry 15 }

recfBundleAttenuationTx 	OBJECT-TYPE
		SYNTAX    INTEGER {
                                   p0db(2),
                                   p3db(3),
                                   p6db(4),
                                   p9db(5)
                                   }
		ACCESS    read-write
		STATUS    mandatory
		DESCRIPTION "Parameter Type = Intrusive.
			For voice channel."
		DEFVAL { p0db }
		::= { recfBundleEntry 16 }

recfBundleType 	OBJECT-TYPE
		SYNTAX    INTEGER {
                                   null(1),
                                   io(2),
                                   bandContent(3),
                                   inl(4)
                                   }
		ACCESS    read-write
		STATUS    mandatory
		DESCRIPTION "Parameter Type = Intrusive."
		DEFVAL { null }
		::= { recfBundleEntry 17 }

recfBundleINLNumber 	OBJECT-TYPE
		SYNTAX    INTEGER (0..31)
		ACCESS    read-only
		STATUS    mandatory
		DESCRIPTION "Parameter Type = Internal.
			       Applicable only if recfBundleType is
			       set to inl."
		DEFVAL { 0 }
		::= { recfBundleEntry 18 }

recfBundleDeviceType 	OBJECT-TYPE
		SYNTAX    INTEGER (1..255)
		ACCESS    read-write
		STATUS    mandatory
		DESCRIPTION "Parameter Type = Non-intrusive.
			This field indicates the type of device
			connected to the port.

			Values 1-10 and 255 are reserved by ST-50, of
			which 1 is for voice, 2 is for switch 56, 3 is
			for clear channel, and 255 is for INL. Values
			11 to 254 can be used by the user to define
			user-specific device types.

			For TDM channels connected between I/O ports,
			the channel will not connect if the device
			types do not match. For I/O to server port
			connections, the device types will not be
			compared.

			This field is not used by the ST node if
			recfBundleType is null or inl. Note that if
			the recfBundleType is inl but this field is
			not 255, the inl will not be failed. Also, if
			the recfBundleType is not inl but this field
			is 255, then the channel defined on this port
			will still be able to connect."
		DEFVAL { 3 }
		::= { recfBundleEntry 19 }

recfBundleContentionSet 	OBJECT-TYPE
		SYNTAX    INTEGER {
	 			  em(1),
			          signalInvert(3),
	 			  fxo(4),
				  fxs-ard(5),
	 			  fxs(6),
	 			  disable(2)
       			  }
		ACCESS    read-write
		STATUS    mandatory
		DESCRIPTION "Parameter Type = Intrusive.
			If bundle type is not bandwidth contention,
			this field is ignored.

			This field defines the type of contention
			application.

			E&M contention type is to be used for
			E&M connections.

       			FXO contention type is to be used for FXO
       			channels in FXO/FXS contention mode.

       			FXS contention type is to be used for FXS
       			channels in FXO/FXS contention mode.

       			FXS-ARD contention type is to be used for FXS
       			auto ring down channels in contention mode.

			SIGNALINVERT contention type is NOT used
			any more.

       			For the polarity of signal bit defintion
       			for channel connect/disconnect, see
       			description in recfBundleSigInversion."
		DEFVAL { em }
		::= { recfBundleEntry 20 }


recfBundlePartitionID 	OBJECT-TYPE
		SYNTAX    INTEGER (1..1023)
		ACCESS    read-write
		STATUS    mandatory
		DESCRIPTION "Parameter Type = Intrusive."
		::= { recfBundleEntry 21 }

recfBundleBwCntBusyPattern 	OBJECT-TYPE
		SYNTAX  INTEGER {
			a0-b0-c0-d0(16),
			a0-b0-c0-d1(8),
			a0-b0-c1-d0(4),
			a0-b0-c1-d1(12),
			a0-b1-c0-d0(2),
			a0-b1-c0-d1(10),
			a0-b1-c1-d0(6),
			a0-b1-c1-d1(14),
			a1-b0-c0-d0(1),
			a1-b0-c0-d1(9),
			a1-b0-c1-d0(5),
			a1-b0-c1-d1(13),
			a1-b1-c0-d0(3),
			a1-b1-c0-d1(11),
			a1-b1-c1-d0(7),
			a1-b1-c1-d1(15),
			oos(254),
			reverse(255)
			}
		ACCESS  read-write
		STATUS  mandatory
		DESCRIPTION "Parameter Type = Intrusive.
			Bit pattern output to equipment
			indicating bundle busy.

			If the value is oos, then the busy
			pattern will be the same as the OOS
			idle pattern.

			If the value is reverse, then the busy
			pattern's A bit will be the inverse of
			the A bit value from the bundle
			bandwidth contention idle pattern. For
			T1M bundles, the B, C, and D bits will
			follow the A bit of the busy pattern.
			For E1M bundles, the B bit will be 1,
			the C bit will be 0, and the D bit will
			be 1."
		DEFVAL { reverse }
		::= { recfBundleEntry 22 }

recfBundleSigInversion 	OBJECT-TYPE
		SYNTAX    INTEGER {
			  normal(1),
			  inverted(2)
			  }
		ACCESS    read-write
		STATUS    mandatory
		DESCRIPTION "Parameter Type = Intrusive.

			INTRODUCED 2.0.0

   			For an E1M bundle, the meanings of these
			values are reversed. That is, if this
			parameter is  set as normal, the ABCD signal
			polarity will be inverted on the ST bus.
	 		If it is set as inverted, the ABCD signal
			polarity will NOT be inverted on the ST bus.

   			Contention channel connect/disconnect will
			be affected by this filed:

	  		a) For a T1M bundle set as normal or
			   an E1M bundle set as inverted:

			If recfBundleContentionSet is set as E&M:
		       	Connections are initiated when the incoming
			A bit is set to 1.
		       	Disconnections are triggered when the incoming
		       	A bit is set to 0.

		   	If recfBundleContentionSet is set as FXS:
		       	Connections are initiated when the incoming
			A bit is set to 1.
		       	Disconnections are triggered when the incoming
		       	A bit is set to 0.

		   	If recfBundleContentionSet is set as FXO:
		       	Connections are initiated when the incoming
			B bit is set to 0.
			Before FXS answers the call, disconnections
		       	will be triggered when the B bit is set to 1.

		   	If recfBundleContentionSet is set as FXS-ARD:
		       	Connections are initiated when the incoming
			A bit is set to 0.
			Disconnections are triggered when the incoming
 			A bit is a 1.

			b) For a T1M bundle set as inverted or
			   an E1M bundle set as normal:

			If recfBundleContentionSet is set as E&M:
		       	Connections are initiated when the incoming
			A bit is set to 0.
		       	Disconnections are triggered when the incoming
		       	A bit is set to 1.

		   	If recfBundleContentionSet is set as FXS:
		       	Connections are initiated when the incoming
			A bit is set to 0.
		       	Disconnections are triggered when the incoming
		       	A bit is set to 1.

		   	If recfBundleContentionSet is set as FXO:
		       	Connections are initiated when the incoming
			B bit is set to 1.
			Before FXS answers the call, disconnections
		       	will be triggered when the B bit is set to 0.

		   	If recfBundleContentionSet is set as FXS-ARD:
		       	Connections are initiated when the incoming
			A bit is set to 1.
			Disconnections are triggered when the incoming
			A bit is set to 0."
		DEFVAL { normal }
		::= { recfBundleEntry 23 }

recfBundleDataPolarity 	OBJECT-TYPE
		SYNTAX	INTEGER {
			normal(1),
			inverted(2)
			}
		ACCESS    read-write
		STATUS    mandatory
		DESCRIPTION "Parameter Type = Intrusive.

			INTRODUCED 2.0.0

			The default value must be used unless
			specific user equipment explicitly
			requires data to be inverted."
		DEFVAL { normal }
		::= { recfBundleEntry 24 }




recfBundlePCMLaw 	OBJECT-TYPE
		SYNTAX	INTEGER {
			native(1),
			converted(2)
			}
		ACCESS    read-write
		STATUS    mandatory
		DESCRIPTION "Parameter Type = Intrusive.

			INTRODUCED 2.0.0

			The values specify the following setup:
			<native> - 	T1M - u_Law
			E1M - a_Law
			<converted> - 	T1M - a_Law
			E1M - u_Law."
		DEFVAL { native }
		::= { recfBundleEntry 25 }


-- INL Configuration

recfINLTable 	OBJECT-TYPE
		SYNTAX    SEQUENCE OF RecfINLEntry
		ACCESS    not-accessible
		STATUS    mandatory
		DESCRIPTION " "
		::=  { reConfig 8 }

recfINLEntry 	OBJECT-TYPE
		SYNTAX    RecfINLEntry
		ACCESS    not-accessible
		STATUS    mandatory
		DESCRIPTION " "
		INDEX { recfINLNumber }
                         ::=  { recfINLTable 1 }

RecfINLEntry             ::=  SEQUENCE {
                         recfINLNumber
                                   INTEGER,
                         recfINLAddr
                                   BundleAddr,
                         recfINLStartMode
                                   INTEGER,
                         recfINLUpdate
                                   INTEGER,
                         recfINLArqCir
                                   INTEGER,
                         recfINLMaxPacketDS0
                                   INTEGER,
                         recfINLPacketCirOccupy
                                   INTEGER,
                         recfINLMaxTDMDS0
                                   INTEGER,
                         recfINLGroup
                                   OCTET STRING,
                         recfINLCost
                                   INTEGER,
                         recfINLEncryption
                                   INTEGER,
                         recfINLSatelliteHop
                                   INTEGER,
                         recfINLOOSTimer
                                   INTEGER,
                         recfINLOrig
                                   INTEGER,
                         recfINLRemoteNodeID
                                   NodeAddr,
                         recfINLRemoteINLID
                                   INTEGER,
                         recfINLPartitionID
                                   INTEGER,
                         recfINLKGMode
				   INTEGER
			 }

recfINLNumber 	OBJECT-TYPE
                         SYNTAX    INTEGER (1..31)
                         ACCESS    read-only
                         STATUS    mandatory
		DESCRIPTION "Parameter Type = Internal."
		::= { recfINLEntry 1 }

recfINLAddr 	OBJECT-TYPE
		SYNTAX    BundleAddr
		ACCESS    read-write
		STATUS    mandatory
		DESCRIPTION "Parameter Type = Intrusive.
		       Setting this field will set the INL
		       number field in the port or bundle
		       configuration to this INL's number."
		::= { recfINLEntry 2 }

recfINLStartMode 	OBJECT-TYPE
		SYNTAX    INTEGER {
                                   automatic(1),
                                   off(2),
                                   erase(3)
                                   }
		ACCESS    read-write
		STATUS    mandatory
		DESCRIPTION "Parameter Type = Intrusive.
		       Setting to erase will fail if the INL has
		       not been removed. Otherwise, it will
		       erase the INL configuration, and set the
		       INL number field in the port or bundle
		       configuration to zero."
		DEFVAL { off }
		::= { recfINLEntry 3 }

recfINLUpdate 	OBJECT-TYPE
		SYNTAX    INTEGER {
                                   loaded(1),
				   updateReq(2),
				   resetReq(3)
                                   }
		ACCESS    read-only
		STATUS    mandatory
		DESCRIPTION "Parameter Type = Internal."
		DEFVAL { resetReq }
		::=  { recfINLEntry 4 }

recfINLArqCir 	OBJECT-TYPE
		SYNTAX    INTEGER (0..2048000)
		ACCESS    read-write
		STATUS    mandatory
		DESCRIPTION "Parameter Type = Intrusive.
			       Unit of bps."
		DEFVAL { 9600 }
		::= { recfINLEntry 5 }

recfINLMaxPacketDS0 	OBJECT-TYPE
		SYNTAX    INTEGER (1..32)
		ACCESS    read-write
		STATUS    mandatory
		DESCRIPTION "Parameter Type = Intrusive.
		       Maximum packet bandwidth, in units of DS0.
		       (INL Bandwidth - recfMaxPacketDS0) is the
		       guaranteed TDM bandwidth."
		::= { recfINLEntry 6 }

recfINLPacketCirOccupy 	OBJECT-TYPE
		SYNTAX    INTEGER (1..100)
		ACCESS    read-write
		STATUS    mandatory
		DESCRIPTION "Parameter Type = Intrusive.
		       This number represents the CIR occupancy
		       percentage (x) of the packet band
		       bandwidth. The INL bandwidth allocation
		       shall follow the following rules:
		       1. (SUM of all TDM channel bandwidth) <=
		          INLMaxTDMDS0
		       2. (SUM of all packet channel CIR) <=
			  x * INLMaxPacketDS0
		       3. (SUM of all TDM channel bandwidth) +
			  1/x * (SUM of all packet channel CIR ) <=
			  INL Bandwidth."
		DEFVAL { 100 }
		::= { recfINLEntry 7 }

recfINLMaxTDMDS0 	OBJECT-TYPE
		SYNTAX    INTEGER (0..31)
		ACCESS    read-write
		STATUS    mandatory
		DESCRIPTION "Parameter Type = Intrusive.
		       Maximum TDM bandwidth, in units of DS0.
		       (INL Bandwidth - recfMaxTDMDS0) is the
		       guaranteed packet bandwidth."
		::= { recfINLEntry 8 }

recfINLGroup 	OBJECT-TYPE
		SYNTAX    OCTET STRING (SIZE (1))
		ACCESS    read-write
		STATUS    mandatory
		DESCRIPTION "Parameter Type = Non-intrusive.
		       Up to seven groups for each INL.
		       Bit map bits 1 (lsb) to 7 indicates the
		       group(s) of the INL."
		DEFVAL { '7f'h }
		::= { recfINLEntry 9 }

recfINLCost 	OBJECT-TYPE
		SYNTAX    INTEGER (1..65535)
		ACCESS    read-write
		STATUS    mandatory
		DESCRIPTION "Parameter Type = Non-intrusive.
		       Assigned by user."
		DEFVAL { 1 }
		::= { recfINLEntry 10 }

recfINLEncryption 	OBJECT-TYPE
		SYNTAX    INTEGER {
                                   normal (1),
                                   encrypted(2)
                                   }
		ACCESS    read-write
		STATUS    mandatory
		DESCRIPTION "Parameter Type = Non-intrusive."
		DEFVAL { normal }
		::= { recfINLEntry 11 }

recfINLSatelliteHop 	OBJECT-TYPE
		SYNTAX    INTEGER (0..3)
		ACCESS    read-write
		STATUS    mandatory
		DESCRIPTION "Parameter Type = Non-intrusive."
		DEFVAL { 0 }
		::= { recfINLEntry 12 }

recfINLOOSTimer 	OBJECT-TYPE
		SYNTAX    INTEGER (1..60)
		ACCESS    read-write
		STATUS    mandatory
		DESCRIPTION "Parameter Type = Non-intrusive.
		       In units of seconds. To disqualify a INL
		       beyond."
		DEFVAL { 10 }
		::= { recfINLEntry 13 }

recfINLOrig 	OBJECT-TYPE
		SYNTAX    INTEGER {
                                    yes(1),
                                    no(2)
                                   }
		ACCESS    read-write
		STATUS    mandatory
		DESCRIPTION "Parameter Type = Internal.
		       For EMS usage."
		DEFVAL { no }
		::= { recfINLEntry 14 }

recfINLRemoteNodeID 	OBJECT-TYPE
		SYNTAX    NodeAddr
		ACCESS    read-write
		STATUS    mandatory
		DESCRIPTION "Parameter Type = Intrusive.
		       0 means don't care."
		DEFVAL { '0000'h }
		::= { recfINLEntry 15 }

recfINLRemoteINLID 	OBJECT-TYPE
		SYNTAX    INTEGER (0..31)
		ACCESS    read-write
		STATUS    mandatory
		DESCRIPTION "Parameter Type = Intrusive.
		       INL number of remote side.
		       0 means don't care."
		DEFVAL { 0 }
		::= { recfINLEntry 16 }

recfINLPartitionID 	OBJECT-TYPE
		SYNTAX    INTEGER (1..1023)
		ACCESS    read-only
		STATUS    mandatory
		DESCRIPTION "Parameter Type = Internal.
		       Used by security server to enforce
		       shared node."
		::= { recfINLEntry 17 }

recfINLKGMode 	OBJECT-TYPE
		SYNTAX    INTEGER {
			           kgEnable(1),
				   kgDisable(2)
			   }
		ACCESS    read-only
		STATUS    mandatory
		DESCRIPTION "Parameter Type = Internal.
                       	Used by Link Maintenance to take action
			in KG-resync mode."
		::= { recfINLEntry 18 }


-- TDM Channel Configuration

recfTDMChannelTable 	OBJECT-TYPE
		SYNTAX    SEQUENCE OF RecfTDMChannelEntry
		ACCESS    not-accessible
		STATUS    mandatory
		DESCRIPTION " "
		::=  { reConfig 9 }

recfTDMChannelEntry 	OBJECT-TYPE
		SYNTAX    RecfTDMChannelEntry
		ACCESS    not-accessible
		STATUS    mandatory
		DESCRIPTION " "
		INDEX { recfTDMChannelAddr }
		::=  { recfTDMChannelTable 1 }

RecfTDMChannelEntry      ::=  SEQUENCE {
                         recfTDMChannelAddr
                                   ChannelAddr,
                         recfTDMChannelDestNodeID
                                   NodeAddr,
                         recfTDMChannelDestAddr
                                   ChannelAddr,
                         recfTDMChannelControlMode
                                   INTEGER,
                         recfTDMChannelUpdate
                                   INTEGER,
                         recfTDMChannelModuleType
                                   INTEGER,
                         recfTDMChannelDeviceType
                                   INTEGER,
                         recfTDMChannelProfile
                                   INTEGER,
                         recfTDMChannelOrig
                                   INTEGER,
                         recfTDMChannelPartitionID
                                   INTEGER,
                         recfTDMChannelState
                                   INTEGER,
			 recfTDMChannelDestCheckMode
				   INTEGER,
                         recfTDMChannelConnectMode
                                   INTEGER,
			 recfTDMChannelSpecialPrfType
				   INTEGER,
			 recfTDMChannelSpecialProfile
				   INTEGER,
			 recfTDMChannelDestNodeType
				   INTEGER
                          }

recfTDMChannelAddr 	OBJECT-TYPE
		SYNTAX    ChannelAddr
		ACCESS    read-only
		STATUS    mandatory
		DESCRIPTION "Parameter Type = Internal."
		::= { recfTDMChannelEntry 1 }

recfTDMChannelDestNodeID 	OBJECT-TYPE
		SYNTAX    NodeAddr
		ACCESS    read-write
		STATUS    mandatory
		DESCRIPTION "Parameter Type = Immediate."
		::= { recfTDMChannelEntry 2 }

recfTDMChannelDestAddr 	OBJECT-TYPE
		SYNTAX    ChannelAddr
		ACCESS    read-write
		STATUS    mandatory
		DESCRIPTION "Parameter Type = Immediate."
		::= { recfTDMChannelEntry 3 }

recfTDMChannelControlMode 	OBJECT-TYPE
		SYNTAX   INTEGER {
			enable(1),
			disable(2),
			erase(3)
			}
		ACCESS   read-write
		STATUS   mandatory
		DESCRIPTION "Parameter Type = Intrusive.
			      Indicates whether the channel can be
			      used in a connection request or not.
			      The value erase is used to wipe out
			      the channel configuration MIB. Setting
			      this to erase will not succeed if the
			      channel is not disconnected."
		DEFVAL { disable }
		::= { recfTDMChannelEntry 4 }

recfTDMChannelUpdate 	OBJECT-TYPE
		SYNTAX    INTEGER {
                                 loaded(1),
				 resetReq(3)
                                 }
		ACCESS    read-only
		STATUS    mandatory
		DESCRIPTION "Parameter Type = Internal."
		DEFVAL { resetReq }
		::= { recfTDMChannelEntry 5 }

recfTDMChannelModuleType 	OBJECT-TYPE
		SYNTAX    INTEGER {
                                   t1m(5),
                                   e1m(6),
                                   sgm(7),
                                   lgm(8),
                                   asm(9),
                                   fsm(11),
                                   sdm(12),
                                   sgmAg(13),
				   rtm(14),
				   dsm(19),
				   e3m(20)
                                   }
		ACCESS    read-only
		STATUS    mandatory
		DESCRIPTION "Parameter Type = Internal.
			     The type of module on which this channel
			     endpoint is located. Derived from the port
			     or that the channel is configured on."
		::= { recfTDMChannelEntry 6 }

recfTDMChannelDeviceType 	OBJECT-TYPE
		SYNTAX    INTEGER (0..255)
		ACCESS    read-only
		STATUS    mandatory
		DESCRIPTION "Parameter Type = Internal.
			     The type of device connected to this
			     channel endpoint. Derived from the port or
			     bundle that the channel is configured on.
			     Always zero for server ports. Values 1-10
			     are reserved by ST-50, of which 1 is for
			     voice, 2 is for switch 56, and 3 is for
			     clear channel. Values 11 and up can be used
			     by the user to define user-specific device
			     types. For TDM channels connected between
			     I/O ports, the channel will not connect if
			     the device types do not match. For I/O to
			     server port connections, the device types
			     will not be compared."
		::= { recfTDMChannelEntry 7 }

recfTDMChannelProfile 	OBJECT-TYPE
		SYNTAX    INTEGER (1..255)
		ACCESS    read-write
		STATUS    mandatory
		DESCRIPTION "Parameter Type = Intrusive."
		DEFVAL { 1 }
		::= { recfTDMChannelEntry 8 }

recfTDMChannelOrig 	OBJECT-TYPE
		SYNTAX    INTEGER {
                                    yes(1),
                                    no(2)
                                    }
		ACCESS    read-write
		STATUS    mandatory
		DESCRIPTION "Parameter Type = Internal.
			       For EMS usage."
		DEFVAL { no }
		::= { recfTDMChannelEntry 9 }

recfTDMChannelPartitionID 	OBJECT-TYPE
		SYNTAX    INTEGER (1..1023)
		ACCESS    read-only
		STATUS    mandatory
		DESCRIPTION "Parameter Type = Internal.
			       Used by security server to enforce shared
			       node. Derived from end point."
		::= { recfTDMChannelEntry 10 }

recfTDMChannelState 	OBJECT-TYPE
		SYNTAX    INTEGER {
			   connected(35),
			   processing(34),
			   nodeReset(33),
			   noSourceIoMIB(86),
			   noSourceChProfile(110),
			   noDestChProfile(111),
                           sourceIoUnusable(88),
                           destIoUnusable(112),
			   sourceChMibOff(117),
			   destChMibOff(118),
                           noDestChMIB(89),
			   noDestIoMIB(90),
			   notMatchDeviceType(91),
			   notMatchIoSpeed(92),
			   notMatchPartition(93),
			   notMatchBitMode(113),
			   notMatchSignalling(114),
			   destBusy(115),
		  	   destMismatch(116),
			   contentionTerminate(104),
			   userInitiate(105),
			   noInlBw(41),
			   noRoute(42),
			   noServer(30),
			   sourceExceedSharedBw(119),
			   destExceedSharedBw(120),
			   disconnectedSAF(125),
			   rejectBySourceModule(128),
			   rejectByDestModule(129),
			   channelLimitExceeded(130),
			   linkDisconnectError(94),
			   noBypassServer(151),
			   noSrcServer(152),
			   noDestServer(153),
			   noSrcSgmSaf(154),
			   noDestSgmSaf(155),
			   noSrcSgmScf(156),
			   noDestSgmScf(157),
			   noSrcAgmSaf(158),
			   noDestAgmSaf(159),
			   noSrcAgmScf(160),
			   noDestAgmScf(161),
			   noSrcAsmSaf(162),
			   noDestAsmSaf(163),
			   noSrcAsmScf(164),
			   noDestAsmScf(165),
			   noSrcLgmSaf(166),
			   noDestLgmSaf(167),
			   noSrcLgmScf(168),
			   noDestLgmScf(169),
			   noSrcRtmSaf(170),
			   noDestRtmSaf(171),
			   noSrcRtmScf(172),
			   noDestRtmScf(173),
			   noSrcVoicePort(174),
			   noDestVoicePort(175),
			   notApplicable(255)
                                   }
		ACCESS    read-only
		STATUS    mandatory
		DESCRIPTION "Parameter Type = Internal.
		       If value is connected, then restChannelStatus is
		       also set to connected. If value is processing,
		       then restChannelStatus is set to any value
		       besides connected and disconnected. For all
		       other values, restChannelStatus is set to
		       disconnected and this attribute specifies the
		       reason for the disconnection."
		DEFVAL { notApplicable }
		::= { recfTDMChannelEntry 11 }

recfTDMChannelDestCheckMode 	OBJECT-TYPE
		SYNTAX   INTEGER {
				enable(1),
				disable(2)
			}
		ACCESS   read-write
		STATUS   mandatory
		DESCRIPTION "Parameter Type = Intrusive.
			      Indicates if the remote node ID and
			      remote address in the destination's
			      channel MIB need to verify the source's
			      node ID and address before allowing a
			      channel connection."
		DEFVAL { disable }
		::= { recfTDMChannelEntry 12 }

recfTDMChannelConnectMode 	OBJECT-TYPE
		SYNTAX   INTEGER {
				autoConnect(1),
				userInitiate(2)
			}
		ACCESS   read-write
		STATUS   mandatory
		DESCRIPTION "Parameter Type = Intrusive.
			      Indicates whether a channel should be
			      automatically connected when a port
			      comes up, or if the user is responsible
			      for connecting the channel."
		DEFVAL { userInitiate }
		::= { recfTDMChannelEntry 13 }

recfTDMChannelSpecialPrfType 	OBJECT-TYPE
		SYNTAX    INTEGER {
			   	voiceProfile(1),
				dataProfile(2),
				none(255)
			 	}
		ACCESS    read-write
		STATUS    mandatory
		DESCRIPTION "Parameter Type = Intrusive.

			INTRODUCED 2.0.0

			Specifies the type of special profile
			that is used on this channel connection."
		DEFVAL { none }
		::= { recfTDMChannelEntry 14 }

recfTDMChannelSpecialProfile 	OBJECT-TYPE
		SYNTAX    INTEGER (1..255)
		ACCESS    read-write
		STATUS    mandatory
		DESCRIPTION "Parameter Type = Intrusive.

			INTRODUCED 2.0.0

			Specifies the particular special profile
			index used on this channel connection."
		DEFVAL { 1 }
		::= { recfTDMChannelEntry 15 }

recfTDMChannelDestNodeType 	OBJECT-TYPE
		SYNTAX	INTEGER {
			    st(1),
			    link(2)
			}
		ACCESS	read-write
		STATUS	mandatory
		DESCRIPTION "Parameter Type = Intrusive.

			INTRODUCED 2.0.0

			This attribute defines the type of the
			destination node for this channel. If set
			to <link>, then the LGM translation table entry
			indexed by the value of recfTDMChannelDestAddr
			will be allocated, with the Link2TraStAddr
			attribute set to the value of recfTDMChannelAddr
			for this TDM channel. If this attribute has an
			illegal translation table index value, the
			command should fail."
		DEFVAL { st }
		::= { recfTDMChannelEntry 16 }


-- Frame Relay Configuration MIB

recfFrame           OBJECT IDENTIFIER ::=    { reConfig 10 }


-- Frame Relay Port Configuration

recfFrPortTable 	OBJECT-TYPE
		SYNTAX    SEQUENCE OF RecfFrPortEntry
		ACCESS    not-accessible
		STATUS    mandatory
		DESCRIPTION " "
		::=  { recfFrame 1 }

recfFrPortEntry 	OBJECT-TYPE
		SYNTAX    RecfFrPortEntry
		ACCESS    not-accessible
		STATUS    mandatory
		DESCRIPTION " "
		INDEX { recfFrPortAddr }
		::=  { recfFrPortTable 1 }

RecfFrPortEntry          ::=  SEQUENCE {
                         recfFrPortAddr
                                   PortAddr,
                         recfFrPortDescription
                                   DisplayString,
                         recfFrPortStartMode
                                   INTEGER,
                         recfFrPortUpdate
                                   INTEGER,
                         recfFrPortLmiActive
                                   INTEGER,
                         recfFrPortLmiPollingTimer
                                   INTEGER,
                         recfFrPortLmiWaitingTimer
                                   INTEGER,
                         recfFrPortLmiFullEnqInterval
                                   INTEGER,
                         recfFrPortLmiMonitoredEvents
                                   INTEGER,
                         recfFrPortErrorThreshold
                                   INTEGER,
                         recfFrPortDeviceType
                                   INTEGER,
                         recfFrPortAd10NodeID
                                   NodeAddr,
                         recfFrPortAd10PortID
                                   PortAddr,
                         recfFrPortBitMode
                                   INTEGER,
                         recfFrPortMaxFrameSize
                                   INTEGER,
                         recfFrPortSharedZeroFlag
                                   INTEGER,
                         recfFrPortMaxCIR
                                   INTEGER,
                         recfFrPortAvgPktSize
                                   INTEGER,
                         recfFrPortAllocationPref
                                   INTEGER,
                         recfFrPortBillingSegSize
                                   INTEGER,
                         recfFrPortBillingControl
                                   INTEGER,
                         recfFrPortPartitionID
                                   INTEGER,
                         recfFrPortEncodingType
                                   INTEGER
                         }

recfFrPortAddr 	OBJECT-TYPE
		SYNTAX    PortAddr
		ACCESS    read-only
		STATUS    mandatory
		DESCRIPTION "Parameter Type = Internal."
		::= { recfFrPortEntry 1 }

recfFrPortDescription 	OBJECT-TYPE
		SYNTAX    DisplayString ( SIZE(0..15) )
		ACCESS    read-write
		STATUS    mandatory
		DESCRIPTION "Parameter Type = Intrusive.
			       Used by EMS ITM and other applications."
		DEFVAL { "" }
		::= { recfFrPortEntry 2 }

recfFrPortStartMode 	OBJECT-TYPE
		SYNTAX    INTEGER {
                                   automatic(1),
                                   off(2),
                                   erase(3)
                                   }
		ACCESS    read-write
		STATUS    mandatory
		DESCRIPTION "Parameter Type = Intrusive.
			Setting this to erase will erase the port
			configuration MIB, as well as any TDM and
			frame relay channels defined on this port.
			The erase will not succeed if any of the
			channels on the port are not disconnected."
		DEFVAL { off }
		::= { recfFrPortEntry 3 }

recfFrPortUpdate 	OBJECT-TYPE
		SYNTAX    INTEGER {
                                   loaded(1),
			   resetReq(3)
                                   }
		ACCESS    read-only
		STATUS    mandatory
		DESCRIPTION "Parameter Type = Internal."
		DEFVAL { resetReq }
		::= { recfFrPortEntry 4 }

recfFrPortLmiActive 	OBJECT-TYPE
		SYNTAX    INTEGER {
                                   ansi617D(1),
			   ccittQ933A(2),
                                   disabled(3)
                                   }
		ACCESS    read-write
		STATUS    mandatory
		DESCRIPTION "Parameter Type = Intrusive."
		DEFVAL { ansi617D }
		::= { recfFrPortEntry 5 }

recfFrPortLmiPollingTimer 	OBJECT-TYPE
		SYNTAX    INTEGER {
                                   sec5(1),
                                   sec10(2),
                                   sec15(3),
                                   sec20(4),
                                   sec25(5),
                                   sec30(6)
                                   }
		ACCESS    read-write
		STATUS    mandatory
		DESCRIPTION "Parameter Type = Intrusive."
		DEFVAL { sec5 }
		::= { recfFrPortEntry 6 }

recfFrPortLmiWaitingTimer 	OBJECT-TYPE
		SYNTAX    INTEGER {
                                   sec5(1),
                                   sec10(2),
                                   sec15(3),
                                   sec20(4),
                                   sec25(5),
                                   sec30(6)
                                   }
		ACCESS    read-write
		STATUS    mandatory
		DESCRIPTION "Parameter Type = Intrusive."
		DEFVAL { sec10 }
		::= { recfFrPortEntry 7 }

recfFrPortLmiFullEnqInterval 	OBJECT-TYPE
		SYNTAX    INTEGER (1..255)
		ACCESS    read-write
		STATUS    mandatory
		DESCRIPTION "Parameter Type = Intrusive."
		DEFVAL { 10 }
		::= { recfFrPortEntry 8 }

recfFrPortLmiMonitoredEvents 	OBJECT-TYPE
		SYNTAX    INTEGER (1..10)
		ACCESS    read-write
		STATUS    mandatory
		DESCRIPTION "Parameter Type = Intrusive."
		DEFVAL { 5 }
		::= { recfFrPortEntry 9 }

recfFrPortErrorThreshold 	OBJECT-TYPE
		SYNTAX    INTEGER (1..10)
		ACCESS    read-write
		STATUS    mandatory
		DESCRIPTION "Parameter Type = Intrusive."
		DEFVAL { 3 }
		::= { recfFrPortEntry 10 }

recfFrPortDeviceType 	OBJECT-TYPE
		SYNTAX    INTEGER {
                                   networkToUser(1),
                                   userToNetwork(2),
                                   networkToNetwork(3),
                                   regularHdlc(5),
                                   ad10(4)
                                   }
		ACCESS    read-write
		STATUS    mandatory
		DESCRIPTION "Parameter Type = Intrusive.
			Indicates port usage. For regular HDLC ports,
			only one connection can be made. All HDLC ports
			shall be connected to an SDM I/O port."
		DEFVAL { networkToUser }
		::= { recfFrPortEntry 11 }

-- the AD-10 config resides in the FrPortAd10PortID virtual
-- port of the FrPortAd10NodeID node for EMS internal use

recfFrPortAd10NodeID 	OBJECT-TYPE
		SYNTAX    NodeAddr
		ACCESS    read-write
		STATUS    mandatory
		DESCRIPTION "Parameter Type = Intrusive."
		::= { recfFrPortEntry 12 }

recfFrPortAd10PortID 	OBJECT-TYPE
		SYNTAX    PortAddr
		ACCESS    read-write
		STATUS    mandatory
		DESCRIPTION "Parameter Type = Intrusive."
		::= { recfFrPortEntry 13 }

recfFrPortBitMode 	OBJECT-TYPE
		SYNTAX    INTEGER {
                                   b7bit(1),
				   b8bit(2)
                                   }
		ACCESS    read-write
		STATUS    mandatory
		DESCRIPTION "Parameter Type = Intrusive."
		DEFVAL { b8bit }
		::= { recfFrPortEntry 14 }

recfFrPortMaxFrameSize 	OBJECT-TYPE
		SYNTAX    INTEGER (10..4096)
		ACCESS    read-write
		STATUS    mandatory
		DESCRIPTION "Parameter Type = Intrusive."
		DEFVAL { 4096 }
		::= { recfFrPortEntry 15 }

recfFrPortSharedZeroFlag 	OBJECT-TYPE
		SYNTAX    INTEGER {
                                   yes(1),
                                   no(2)
                                   }
		ACCESS    read-write
		STATUS    mandatory
		DESCRIPTION "Parameter Type = Intrusive."
		DEFVAL { yes }
		::= { recfFrPortEntry 16 }

recfFrPortMaxCIR 	OBJECT-TYPE
		SYNTAX    INTEGER (0..3000000)
		ACCESS    read-write
		STATUS    mandatory
		DESCRIPTION "Parameter Type = Intrusive.
			       This value (in units of bps) is used to
			       determine how many packets per second the
			       I/O to server connection will require from
			       the FSM module resources."
		DEFVAL { 64000 }
		::= { recfFrPortEntry 17 }

recfFrPortAvgPktSize 	OBJECT-TYPE
		SYNTAX    INTEGER {
                                    b32(1),
                                    b64(2),
                                    b128(3),
                                    b256(4)
                                    }
		ACCESS    read-write
		STATUS    mandatory
		DESCRIPTION "Parameter Type = Intrusive."
		DEFVAL { b256 }
		::= { recfFrPortEntry 18 }

recfFrPortAllocationPref 	OBJECT-TYPE
		SYNTAX    INTEGER {
                                    dontCare(1),
                                    fsm16(2),
                                    fsm64(3)
                                    }
		ACCESS    read-write
		STATUS    mandatory
		DESCRIPTION "Parameter Type = Intrusive."
		DEFVAL { dontCare }
		::= { recfFrPortEntry 19 }

recfFrPortBillingSegSize 	OBJECT-TYPE
		SYNTAX    INTEGER {
                                    b64(2),
                                    b128(3),
                                    b256(4),
                                    b512(5),
                                    b1024(6),
                                    pktsize(1)
                                    }
		ACCESS    read-write
		STATUS    mandatory
		DESCRIPTION "Parameter Type = Intrusive.
			THIS ATTRIBUTE IS NOT USED."
		DEFVAL { pktsize }
		::= { recfFrPortEntry 20 }


recfFrPortBillingControl 	OBJECT-TYPE
		SYNTAX    INTEGER {
                                    enable(1),
                                    disable(2)
                                    }
		ACCESS    read-write
		STATUS    mandatory
		DESCRIPTION "Parameter Type = Intrusive.
			THIS ATTRIBUTE IS NOT USED."
		DEFVAL { disable }
		::= { recfFrPortEntry 21 }

recfFrPortPartitionID 	OBJECT-TYPE
		SYNTAX    INTEGER (1..1023)
		ACCESS    read-write
		STATUS    mandatory
		DESCRIPTION "Parameter Type = Intrusive."
		::= { recfFrPortEntry 22 }

recfFrPortEncodingType 	OBJECT-TYPE
		SYNTAX  INTEGER {
			nrz(1),
			nrzb(2),
			nrzi-space(4),
			nrzi-mark(3)
			}
		ACCESS  read-write
		STATUS  mandatory
		DESCRIPTION "Parameter Type = Intrusive."
		DEFVAL { nrz }
		::= { recfFrPortEntry 23 }


-- FrameChannel

recfFrChannelTable 	OBJECT-TYPE
		SYNTAX    SEQUENCE OF RecfFrChannelEntry
		ACCESS    not-accessible
		STATUS    mandatory
		DESCRIPTION " "
		::=  { recfFrame 2 }

recfFrChannelEntry 	OBJECT-TYPE
		SYNTAX    RecfFrChannelEntry
		ACCESS    not-accessible
		STATUS    mandatory
		DESCRIPTION " "
		INDEX { recfFrChannelAddr }
		::=  { recfFrChannelTable 1 }

RecfFrChannelEntry         ::=  SEQUENCE {
                         recfFrChannelAddr
                                   ChannelAddr,
                         recfFrChannelDestNodeID
                                   NodeAddr,
                         recfFrChannelDestAddr
                                   ChannelAddr,
                         recfFrChannelControlMode
                                   INTEGER,
                         recfFrChannelUpdate
                                   INTEGER,
                         recfFrChannelType
                                   INTEGER,
                         recfFrChannelCirTransPriority
                                   INTEGER,
                         recfFrChannelCIR
                                   INTEGER,
                         recfFrChannelEIR
                                   INTEGER,
                         recfFrChannelBc
                                   INTEGER,
                         recfFrChannelProfile
                                   INTEGER,
                         recfFrChannelOrig
                                   INTEGER,
                         recfFrChannelPartitionID
                                   INTEGER,
                         recfFrChannelState
                                   INTEGER,
			 recfFrChannelDestCheckMode
				   INTEGER,
                         recfFrChannelConnectMode
                                   INTEGER,
			 recfFrChannelModuleType
				   INTEGER
                          }


recfFrChannelAddr 	OBJECT-TYPE
                         SYNTAX    ChannelAddr
                         ACCESS    read-only
                         STATUS    mandatory
		DESCRIPTION "Parameter Type = Internal.
			       If the end point is a HDLC port, EMS can
			       define a DLCI (1-1023)"
		::= { recfFrChannelEntry 1 }

recfFrChannelDestNodeID 	OBJECT-TYPE
		SYNTAX    NodeAddr
		ACCESS    read-write
		STATUS    mandatory
		DESCRIPTION "Parameter Type = Intrusive."
		::= { recfFrChannelEntry 2 }

recfFrChannelDestAddr 	OBJECT-TYPE
		SYNTAX    ChannelAddr
		ACCESS    read-write
		STATUS    mandatory
		DESCRIPTION "Parameter Type = Intrusive."
		::= { recfFrChannelEntry 3 }

recfFrChannelControlMode 	OBJECT-TYPE
		SYNTAX   INTEGER {
			enable(1),
			disable(2),
			erase(3)
			}
		ACCESS   read-write
		STATUS   mandatory
		DESCRIPTION "Parameter Type = Intrusive.
			Indicates whether the channel can be used in a
			connection request or not. The value erase is
			used to wipe out the channel configuration MIB.
			Setting this to erase will not succeed if the
			channel is not disconnected."
		DEFVAL { disable }
		::= { recfFrChannelEntry 4 }

recfFrChannelUpdate 	OBJECT-TYPE
		SYNTAX   INTEGER {
                                  loaded(1),
				  resetReq(3)
                                  }
		ACCESS   read-only
		STATUS   mandatory
		DESCRIPTION "Parameter Type = Internal."
		DEFVAL { resetReq }
		::= { recfFrChannelEntry 5 }

recfFrChannelType 	OBJECT-TYPE
		SYNTAX    INTEGER {
                                   regular(1),
				   expressRouting(3)
                                   }
		ACCESS    read-write
		STATUS    mandatory
		DESCRIPTION "Parameter Type = Intrusive.
			When a channel is added, a notification shall be
			sent to the associated FSM through maintenance
			agent. Regular connection is point-to-point.
			Express routing is for TimeLan Router."
		DEFVAL { regular }
		::= { recfFrChannelEntry 6 }

recfFrChannelCirTransPriority 	OBJECT-TYPE
		SYNTAX    INTEGER (0..7)
		ACCESS    read-write
		STATUS    mandatory
		DESCRIPTION "Parameter Type = Intrusive.
			       Use high for timing critical traffic.
			       7 is the highest priority."
		DEFVAL { 4 }
		::= { recfFrChannelEntry 7 }

recfFrChannelCIR 	OBJECT-TYPE
		SYNTAX    INTEGER (0..2048000)
		ACCESS    read-write
		STATUS    mandatory
		DESCRIPTION "Parameter Type = Intrusive.
			       Commit information rate (bps)."
		DEFVAL { 0 }
		::= { recfFrChannelEntry 8 }

recfFrChannelEIR 	OBJECT-TYPE
		SYNTAX    INTEGER (0..2048000)
		ACCESS    read-write
		STATUS    mandatory
		DESCRIPTION "Parameter Type = Intrusive.
			       Excessive information rate (bps)."
		DEFVAL { 0 }
		::= { recfFrChannelEntry 9 }

recfFrChannelBc 	OBJECT-TYPE
		SYNTAX    INTEGER (0..2147483647)
		ACCESS    read-write
		STATUS    mandatory
		DESCRIPTION "Parameter Type = Intrusive.
			       Commit burst rate."
		DEFVAL { 0 }
		::= { recfFrChannelEntry 10 }

recfFrChannelProfile 	OBJECT-TYPE
		SYNTAX    INTEGER (1..255)
		ACCESS    read-write
		STATUS    mandatory
		DESCRIPTION "Parameter Type = Intrusive."
		DEFVAL { 1 }
		::= { recfFrChannelEntry 11 }

recfFrChannelOrig 	OBJECT-TYPE
		SYNTAX    INTEGER {
                                    yes(1),
                                    no(2)
                                    }
		ACCESS    read-write
		STATUS    mandatory
		DESCRIPTION "Parameter Type = Internal.
			       For EMS internal usage."
		DEFVAL { no }
		::= { recfFrChannelEntry 12 }


recfFrChannelPartitionID 	OBJECT-TYPE
		SYNTAX    INTEGER  (1..1023)
		ACCESS    read-write
		STATUS    mandatory
		DESCRIPTION "Parameter Type = Intrusive.
			Used for security on shared nodes.

			For channels defined on FSM port, this
			attribute can only be set to the port
			partition ID.

			For channels defined on DSM PVC port:
			- on dedicated/root nodes may be
			  set only to the node owner
			  partition ID;
			- on shared nodes may be set
			  to any partition ID in the
			  node access list."
		::= { recfFrChannelEntry 13 }

recfFrChannelState 	OBJECT-TYPE
		SYNTAX    INTEGER {
			 connected(35),
			 processing(34),
			 nodeReset(33),
			 noSourceIoMIB(86),
			 noSourceChProfile(110),
			 noDestChProfile(111),
			 sourceIoUnusable(88),
			 destIoUnusable(112),
			 sourceChMibOff(117),
			 destChMibOff(118),
			 noDestChMIB(89),
			 noDestIoMIB(90),
			 notMatchDeviceType(91),
			 notMatchIoSpeed(92),
			 notMatchPartition(93),
			 destBusy(115),
			 destMismatch(116),
			 contentionTerminate(104),
			 userInitiate(105),
			 noInlBw(41),
			 noRoute(42),
			 noServer(30),
			 sourceExceedSharedBw(119),
			 destExceedSharedBw(120),
			 rejectBySourceModule(128),
			 rejectByDestModule(129),
			 sourceHdlcExcessDlcis(130),
			 destHdlcExcessDlcis(131),
			 sourceNoAvailableDlcis(132),
			 destNoAvailableDlcis(133),
			 sourceNoAvailablePvc(134),
			 destNoAvailablePvc(135),
			 bypassNoAvailablePvc(136),
			 sourceNoAvailableThroughput(137),
			 destNoAvailableThroughput(138),
			 sourceNoAvailableModuleMemory(139),
			 destNoAvailableModuleMemory(140),
			 bypassNoAvailableThroughput(141),
			 noBypassServer(151),
			 noSrcServer(152),
			 noDestServer(153),
			 notApplicable(255)
			 }
		ACCESS read-only
		STATUS mandatory
		DESCRIPTION "Parameter Type = Internal.
			       If value is connected, then restChannelStatus is
			       also set to connected. If value is processing,
			       then restChannelStatus is set to any value
			       besides connected and disconnected. For all
			       other values, restChannelStatus is set to
			       disconnected and this attribute specifies the
			       reason for the disconnection."
		DEFVAL { notApplicable }
		::= { recfFrChannelEntry 14 }

recfFrChannelDestCheckMode 	OBJECT-TYPE
		SYNTAX   INTEGER {
			enable(1),
			disable(2)
			}
		ACCESS   read-write
		STATUS   mandatory
		DESCRIPTION "Parameter Type = Intrusive.
			      Indicates if the remote node ID and
			      remote address in the destination's channel
			      MIB need to verify the source's node ID and
			      address before allowing a channel connection."
		DEFVAL { disable }
		::= { recfFrChannelEntry 15 }

recfFrChannelConnectMode 	OBJECT-TYPE
		SYNTAX   INTEGER {
			autoConnect(1),
			userInitiate(2)
			}
		ACCESS   read-write
		STATUS   mandatory
		DESCRIPTION "Parameter Type = Intrusive.
			      Indicates whether a channel should be
			      automatically connected when a port
			      comes up, or if the user is responsible
			      for connecting the channel."
		DEFVAL { userInitiate }
		::= { recfFrChannelEntry 16 }

recfFrChannelModuleType 	OBJECT-TYPE
		SYNTAX   INTEGER {
                                   fsm(11),
				   dsm(19)
                                   }
		ACCESS    read-only
		STATUS    mandatory
		DESCRIPTION "Parameter Type = Internal.
			     The type of module on which this channel
			     endpoint is located. Derived from the port
			     or that the channel is configured on."
		::= { recfFrChannelEntry 17 }


-- Ad10 Configuration MIB

recfAd10Port             OBJECT IDENTIFIER ::=    { reConfig 11 }


-- Ad10 AGM Port Configuration

recfAd10AgmPortTable 	OBJECT-TYPE
		SYNTAX    SEQUENCE OF RecfAd10AgmPortEntry
		ACCESS    not-accessible
		STATUS    mandatory
		DESCRIPTION " "
		::=  { recfAd10Port 1 }

recfAd10AgmPortEntry 	OBJECT-TYPE
		SYNTAX    RecfAd10AgmPortEntry
		ACCESS    not-accessible
		STATUS    mandatory
		DESCRIPTION " "
		INDEX { recfAd10AgmPortAddr }
		::=  { recfAd10AgmPortTable 1 }

RecfAd10AgmPortEntry       ::=  SEQUENCE {
                         recfAd10AgmPortAddr
                                   PortAddr,
                         recfAd10AgmPortStartMode
                                   INTEGER,
                         recfAd10AgmPortUpdate
                                   INTEGER,
                         recfAd10AgmPortSpeed
                                   INTEGER,
                         recfAd10AgmPortDef
                                   OCTET STRING,
                         recfAd10AgmPortPartitionID
                                   INTEGER
                         }

recfAd10AgmPortAddr 	OBJECT-TYPE
		SYNTAX    PortAddr
		ACCESS    read-only
		STATUS    mandatory
		DESCRIPTION "Parameter Type = Internal."
		::= { recfAd10AgmPortEntry 1 }

recfAd10AgmPortStartMode 	OBJECT-TYPE
		SYNTAX    INTEGER {
                                    automatic(1),
                                    off(2),
                                    erase(3)
                                    }
		ACCESS    read-write
		STATUS    mandatory
		DESCRIPTION "Parameter Type = Intrusive."
		DEFVAL { off }
		::= { recfAd10AgmPortEntry 2 }

recfAd10AgmPortUpdate 	OBJECT-TYPE
		SYNTAX    INTEGER {
                                   loaded(1),
			   resetReq(3)
                                   }
		ACCESS    read-only
		STATUS    mandatory
		DESCRIPTION "Parameter Type = Internal."
		DEFVAL { resetReq }
		::= { recfAd10AgmPortEntry 3 }

recfAd10AgmPortSpeed 	OBJECT-TYPE
		SYNTAX  INTEGER {
			    b19200(144),
			    b56000(420),
			    b64000(480),
			    b128000(960)
			}
		ACCESS  read-write
		STATUS  mandatory
		DESCRIPTION "Parameter Type = Intrusive.
			    The 19.2 kbps speed is not supported on
			    SGM/AG modules with a hardware subtype of
			    1 or 3.

			    The 56 kbps speed is not supported on
			    SGM/AG modules with a hardware subtype of
			    3 or 4.

			    The 128 kbps speed is not supported on
			    SGM/AG modules with a hardware subtype of
			    1 or 4."
		DEFVAL { b64000 }
		::= { recfAd10AgmPortEntry 4 }

recfAd10AgmPortDef 	OBJECT-TYPE
		SYNTAX    OCTET STRING (SIZE(64))
		ACCESS    read-only
		STATUS    mandatory
		DESCRIPTION "Parameter Type = Internal.
			       Defines AD-10 port usage. Each OCTET
			       indicates an AD-10 port type. FF for
			       not defined, 1 for data, 2 for voice
			       and 3 for packet band."
		::= { recfAd10AgmPortEntry 5 }

recfAd10AgmPortPartitionID 	OBJECT-TYPE
		SYNTAX    INTEGER (1..1023)
		ACCESS    read-write
		STATUS    mandatory
		DESCRIPTION "Parameter Type = Intrusive."
		::= { recfAd10AgmPortEntry 6 }


-- Ad10 Data Port Configuration

recfAd10DataPortTable 	OBJECT-TYPE
		SYNTAX    SEQUENCE OF RecfAd10DataPortEntry
		ACCESS    not-accessible
		STATUS    mandatory
		DESCRIPTION " "
		::=  { recfAd10Port 2 }

recfAd10DataPortEntry 	OBJECT-TYPE
		SYNTAX    RecfAd10DataPortEntry
		ACCESS    not-accessible
		STATUS    mandatory
		DESCRIPTION " "
		INDEX { recfAd10DataPortAddr }
		::=  { recfAd10DataPortTable 1 }

RecfAd10DataPortEntry 	::=  SEQUENCE {
		recfAd10DataPortAddr
			Ad10PortAddr,
		recfAd10DataPortStartMode
			INTEGER,
		recfAd10DataPortUpdate
			INTEGER,
		recfAd10DataPortPhysSlot
			INTEGER,
		recfAd10DataPortPhysPort
			INTEGER,
		recfAd10DataPortTDMDataRate
			INTEGER,
		recfAd10DataPortType
			INTEGER
		}

recfAd10DataPortAddr 	OBJECT-TYPE
		SYNTAX  Ad10PortAddr
		ACCESS  read-only
		STATUS  mandatory
		DESCRIPTION "Parameter Type = Internal."
		::= { recfAd10DataPortEntry 1 }

recfAd10DataPortStartMode 	OBJECT-TYPE
		SYNTAX  INTEGER {
			automatic(1),
			off(2),
			erase(3)
			}
		ACCESS  read-write
		STATUS  mandatory
		DESCRIPTION "Parameter Type = Intrusive."
		DEFVAL { off }
		::= { recfAd10DataPortEntry 2 }

recfAd10DataPortUpdate 	OBJECT-TYPE
		SYNTAX  INTEGER {
			loaded(1),
			resetReq(3)
			}
		ACCESS  read-only
		STATUS  mandatory
		DESCRIPTION "Parameter Type = Internal.
			If set to resetReq, need to reset the
			AD-10 data port."
		DEFVAL { resetReq }
		::= { recfAd10DataPortEntry 3 }

recfAd10DataPortPhysSlot 	OBJECT-TYPE
		SYNTAX  INTEGER {
			a(1),
			b(2),
			c(3),
			d(4)
			}
		ACCESS  read-write
		STATUS  mandatory
		DESCRIPTION "Parameter Type = Intrusive."
		::= { recfAd10DataPortEntry 4 }

recfAd10DataPortPhysPort 	OBJECT-TYPE
		SYNTAX  INTEGER (1..4)
		ACCESS  read-write
		STATUS  mandatory
		DESCRIPTION "Parameter Type = Intrusive."
		::= { recfAd10DataPortEntry 5 }

recfAd10DataPortTDMDataRate 	OBJECT-TYPE
		SYNTAX  INTEGER {
			b1200(9), b2400(18),
			b4800(36), b7200(54),
			b9600(72), b12000(90),
			b14400(108), b16000(120),
			b16800(126), b19200(144),
			b24000(180), b28800(216),
			b32000(240), b38400(288),
			b48000(360), b56000(420),
			disabled(65535)
			}
		ACCESS  read-write
		STATUS  mandatory
		DESCRIPTION "Parameter Type = Intrusive."
		DEFVAL { disabled }
		::= { recfAd10DataPortEntry 6 }

recfAd10DataPortType 	OBJECT-TYPE
		SYNTAX  INTEGER {
			tdm-sync(1),
			stat-mux-async(2),
			bisync(3),
			hdlc(4)
			}
		ACCESS  read-write
		STATUS  mandatory
		DESCRIPTION "Parameter Type = Intrusive."
		::= { recfAd10DataPortEntry 7 }


-- Ad10 Voice Port Configuration

recfAd10VoicePortTable 	OBJECT-TYPE
		SYNTAX  SEQUENCE OF RecfAd10VoicePortEntry
		ACCESS  not-accessible
		STATUS  mandatory
		DESCRIPTION " "
		::=  { recfAd10Port 3 }

recfAd10VoicePortEntry 	OBJECT-TYPE
		SYNTAX  RecfAd10VoicePortEntry
		ACCESS  not-accessible
		STATUS  mandatory
		DESCRIPTION " "
		INDEX { recfAd10VoicePortAddr }
		::=  { recfAd10VoicePortTable 1 }

RecfAd10VoicePortEntry     ::=  SEQUENCE {
			recfAd10VoicePortAddr
				Ad10PortAddr,
			recfAd10VoicePortStartMode
				INTEGER,
			recfAd10VoicePortUpdate
				INTEGER,
			recfAd10VoicePortPhysSlot
				INTEGER,
			recfAd10VoicePortPhysPort
				INTEGER,
			recfAd10VoicePortDBAMode
				INTEGER,
			recfAd10VoicePortCompressMode
				INTEGER,
			recfAd10VoicePortFaxMode
				INTEGER,
			recfAd10VoicePortSpeed
				INTEGER
			}

recfAd10VoicePortAddr 	OBJECT-TYPE
		SYNTAX  Ad10PortAddr
		ACCESS  read-only
		STATUS  mandatory
		DESCRIPTION "Parameter Type = Internal."
		::= { recfAd10VoicePortEntry 1 }

recfAd10VoicePortStartMode 	OBJECT-TYPE
		SYNTAX  INTEGER {
			automatic(1),
			off(2),
			erase(3)
			}
		ACCESS  read-write
		STATUS  mandatory
		DESCRIPTION "Parameter Type = Intrusive."
		DEFVAL { off }
		::= { recfAd10VoicePortEntry 2 }

recfAd10VoicePortUpdate 	OBJECT-TYPE
		SYNTAX  INTEGER {
			loaded(1),
			resetReq(3)
			}
		ACCESS  read-only
		STATUS  mandatory
		DESCRIPTION "Parameter Type = Internal.
			If set to resetReq, need to reset the
			AD-10 voice port."
		DEFVAL { resetReq }
		::= { recfAd10VoicePortEntry 3 }

recfAd10VoicePortPhysSlot 	OBJECT-TYPE
		SYNTAX  INTEGER (1..8)
		ACCESS  read-write
		STATUS  mandatory
		DESCRIPTION "Parameter Type = Intrusive."
		::= { recfAd10VoicePortEntry 4 }

recfAd10VoicePortPhysPort 	OBJECT-TYPE
		SYNTAX  INTEGER (1..4)
		ACCESS  read-write
		STATUS  mandatory
		DESCRIPTION "Parameter Type = Intrusive."
		DEFVAL { 1 }
		::= { recfAd10VoicePortEntry 5 }

recfAd10VoicePortDBAMode 	OBJECT-TYPE
		SYNTAX  INTEGER {
			enabled(1),
			disabled(2)
			}
		ACCESS  read-write
		STATUS  mandatory
		DESCRIPTION "Parameter Type = Intrusive."
		DEFVAL { disabled }
		::= { recfAd10VoicePortEntry 6 }

recfAd10VoicePortCompressMode 	OBJECT-TYPE
		SYNTAX  INTEGER {
			tCelp(1),
			atc(2)
			}
		ACCESS  read-write
		STATUS  mandatory
		DESCRIPTION "Parameter Type = Intrusive."
		DEFVAL { tCelp }
		::= { recfAd10VoicePortEntry 7 }

recfAd10VoicePortFaxMode 	OBJECT-TYPE
		SYNTAX  INTEGER {
			faxIIIenable-NSFenable(1),
			faxIIIenable-NSFdisable(2),
			faxIIIdisable-NSFdontcare(3)
			}
		ACCESS  read-write
		STATUS  mandatory
		DESCRIPTION "Parameter Type = Intrusive."
		DEFVAL { faxIIIdisable-NSFdontcare }
		::= { recfAd10VoicePortEntry 8 }

recfAd10VoicePortSpeed 	OBJECT-TYPE
		SYNTAX  INTEGER {
			b5333(40), b7200(54), b7466(56),
			b8000(60), b8533(64),
			b9066(68), b9600(72),
			b10133(76), b10666(80),
			b11200(84), b11733(88),
			b12266(92), b12800(96),
			b13333(100), b13866(104),
			b14400(108), b14933(112),
			b15466(116), b16000(120),
			b16533(124), b17066(128),
			b17600(132), b18133(136),
			b18666(140), b19200(144),
			b19733(148), b20266(152),
			b20800(156), b21333(160),
			b21866(164), b22400(168),
			b22933(172), b23466(176),
			b24000(180), b24533(184),
			b25066(188), b25600(192),
			b26133(196), b26666(200),
			b27200(204), b27733(208),
			b28266(212), b28800(216),
			b29333(220), b29866(224),
			b30400(228), b30933(232),
			b31466(236), b32000(240),
			disabled(65535)
			}
		ACCESS  read-write
		STATUS  mandatory
		DESCRIPTION "Parameter Type = Intrusive.
			The compressed channel data rate for
			this AD-10 voice port.

			For ports using a CELP compression
			algorithm, only speeds of 5.333 Kbps,
			7.2 Kbps, 8 Kbps, and 9.6 Kbps will be
			supported.

			For ports using the ATC compression
			algorithm, only the speeds between
			7.466 Kbps and 32 Kbps will be
			supported."
		DEFVAL { b8000 }
		::= { recfAd10VoicePortEntry 9 }


-- Ad10 Packet Band Configuration

recfAd10PktBandTable 	OBJECT-TYPE
		SYNTAX   SEQUENCE OF RecfAd10PktBandEntry
		ACCESS    not-accessible
		STATUS    mandatory
		DESCRIPTION " "
		::=  { recfAd10Port 4 }


recfAd10PktBandEntry 	OBJECT-TYPE
		SYNTAX    RecfAd10PktBandEntry
		ACCESS    not-accessible
		STATUS    mandatory
		DESCRIPTION " "
		INDEX { recfAd10PktBandAddr }
		::=  { recfAd10PktBandTable 1 }

RecfAd10PktBandEntry     ::=  SEQUENCE {
                         recfAd10PktBandAddr
                                   Ad10PortAddr,
                         recfAd10PktBandStartMode
				   INTEGER,
			 recfAd10PktBandUpdate
                                   INTEGER,
                         recfAd10PktBandBaudRate
                                   INTEGER,
			 recfAd10PktBandDBAMode
				   INTEGER
                         }

recfAd10PktBandAddr 	OBJECT-TYPE
		SYNTAX    Ad10PortAddr
		ACCESS    read-only
		STATUS    mandatory
		DESCRIPTION "Parameter Type = Internal."
		::= { recfAd10PktBandEntry 1 }

recfAd10PktBandStartMode 	OBJECT-TYPE
		SYNTAX    INTEGER {
			    automatic(1),
			    off(2)
			    }
		ACCESS    read-write
		STATUS    mandatory
		DESCRIPTION "Parameter Type = Intrusive."
		DEFVAL { off }
		::= { recfAd10PktBandEntry 2 }

recfAd10PktBandUpdate 	OBJECT-TYPE
		SYNTAX   INTEGER {
                                  loaded(1),
				  resetReq(3)
                                  }
		ACCESS   read-only
		STATUS   mandatory
		DESCRIPTION "Parameter Type = Internal.
			If set to resetReq, need to reset
			the AD-10 packet band."
		DEFVAL { resetReq }
		::= { recfAd10PktBandEntry 3 }

recfAd10PktBandBaudRate 	OBJECT-TYPE
		SYNTAX  INTEGER {
			    b1200(9), b1334(10), b1600(12),
			    b1867(14), b2000(15), b2134(16),
			    b2400(18), b2667(20), b2800(21),
			    b3200(24), b3600(27), b3734(28),
			    b4000(30), b4267(32), b4667(35),
			    b4800(36), b5334(40), b5600(42),
			    b6000(45), b6400(48), b7200(54),
			    b7467(56), b8000(60), b8400(63),
			    b9334(70), b9600(72), b10667(80),
			    b11200(84), b12000(90), b12800(96),
			    b14000(105), b14400(108),
			    b14934(112), b16000(120),
			    b16800(126), b18000(135),
			    b18667(140), b19200(144),
			    b21334(160), b22400(168),
			    b24000(180), b25200(189),
			    b28000(210), b28800(216),
			    b29867(224), b32000(240),
			    b33600(252), b36000(270),
			    b37334(280), b38400(288),
			    b42000(315), b44800(336),
			    b48000(360), b50400(378),
			    b56000(420), b57600(432),
			    b64000(480), b67200(504),
			    b72000(540), b74667(560),
			    b84000(630), b89600(672),
			    b96000(720), b100800(756),
			    b112000(840), b115200(864),
			    b126000(945), b128000(960)
			}
		ACCESS  read-write
		STATUS  mandatory
		DESCRIPTION "Parameter Type = Intrusive.
			If recfAd10PktBandDBAMode is enabled,
			then this attribute is ignored.

			In this case, the actual rate will be dynamically
			based on the unused bandwidth of
			the AD-10 aggregrate."
		DEFVAL { b9600 }
		::= { recfAd10PktBandEntry 4 }

recfAd10PktBandDBAMode 	OBJECT-TYPE
		SYNTAX    INTEGER {
				enabled(1),
				disabled(2)
				}
		ACCESS    read-write
		STATUS    mandatory
		DESCRIPTION "Parameter Type = Intrusive."
		DEFVAL { disabled }
		::= { recfAd10PktBandEntry 5 }


-- AD-10 Trunk Group Configuration MIB

recfAd10TrkGrpTable 	OBJECT-TYPE
		SYNTAX  SEQUENCE OF RecfAd10TrkGrpEntry
		ACCESS  not-accessible
		STATUS  mandatory
		DESCRIPTION "Trunk group entries in this table
			will map a single AD-10 trunk group
			address to multiple AD-10 port
			addresses. It is intended to provide
			port contention within a single AD-10
			unit."
		::= { recfAd10Port 5 }

recfAd10TrkGrpEntry 	OBJECT-TYPE
		SYNTAX  RecfAd10TrkGrpEntry
		ACCESS  not-accessible
		STATUS  mandatory
		DESCRIPTION " "
		INDEX   { recfAd10TrkGrpAddr }
		::= { recfAd10TrkGrpTable 1 }

RecfAd10TrkGrpEntry             ::= SEQUENCE {
			recfAd10TrkGrpAddr
				PortAddr,
			recfAd10TrkGrpStartMode
				INTEGER,
			recfAd10TrkGrpAgmPort
				PortAddr,
			recfAd10TrkGrpLowElement
				INTEGER,
			recfAd10TrkGrpHighElement
				INTEGER,
			recfAd10TrkGrpRemoteNodeID
				NodeAddr,
			recfAd10TrkGrpRemoteAddr
				PortAddr,
			recfAd10TrkGrpPartitionID
				INTEGER,
			recfAd10TrkGrpSearchDirection
				INTEGER
			}

recfAd10TrkGrpAddr 	OBJECT-TYPE
		SYNTAX  PortAddr
		ACCESS  read-only
		STATUS  mandatory
		DESCRIPTION "Parameter Type = Internal.
			Address of the AD-10 trunk group."
		::= { recfAd10TrkGrpEntry 1 }

recfAd10TrkGrpStartMode 	OBJECT-TYPE
		SYNTAX  INTEGER {
			automatic(1),
			off(2),
			erase(3)
			}
		ACCESS  read-write
		STATUS  mandatory
		DESCRIPTION "Parameter Type = Immediate.
			Changes will not affect channels that
			are already connected.

			Erase will fail if there are any AD-10
			channels connected that are using this
			trunk group MIB."
		DEFVAL { off }
		::= { recfAd10TrkGrpEntry 2 }

recfAd10TrkGrpAgmPort 	OBJECT-TYPE
		SYNTAX  PortAddr
		ACCESS  read-write
		STATUS  mandatory
		DESCRIPTION "Parameter Type = Immediate.
			Changes will not affect channels that
			are already connected.

			Defines the AGM port that this AD-10
			trunk group may be connected to. The
			range of available AD-10 ports is
			determined by this field,
			recfAd10TrkGrpLowElement, and
			recfAd10TrkGrpHighElement."
		::= { recfAd10TrkGrpEntry 3 }

recfAd10TrkGrpLowElement 	OBJECT-TYPE
		SYNTAX  INTEGER (0..64)
		ACCESS  read-write
		STATUS  mandatory
		DESCRIPTION "Parameter Type = Immediate.
			Changes will not affect channels that
			are already connected.

			The low end of the element range
			available for use by this AD-10
			trunk group on on the AGM port
			set in recfAd10TrkGrpAgmPort.

			If the value of this field is greater
			than recfAd10TrkGrpHighElement, then
			this trunk group is invalid, and any
			attempt to connect a channel using this
			trunk group will fail."
		::= { recfAd10TrkGrpEntry 4 }

recfAd10TrkGrpHighElement 	OBJECT-TYPE
		SYNTAX  INTEGER (0..64)
		ACCESS  read-write
		STATUS  mandatory
		DESCRIPTION "Parameter Type = Immediate.
			Changes will not affect channels that
			are already connected.

			The high end of the element range
			available for use by this AD-10
			trunk group on on the AGM port
			set in recfAd10TrkGrpAgmPort.

			If the value of this field is less
			than recfAd10TrkGrpLowElement, then
			this trunk group is invalid, and any
			attempt to connect a channel using this
			trunk group will fail."
		::= { recfAd10TrkGrpEntry 5 }

recfAd10TrkGrpRemoteNodeID 	OBJECT-TYPE
		SYNTAX  NodeAddr
		ACCESS  read-write
		STATUS  mandatory
		DESCRIPTION "Parameter Type = Immediate.
			Changes will not affect channels that
			are already connected.

			The node that any AD-10 subrate channel
			using this trunk group will connect to.
			May be the same as the local node that
			this AD-10 trunk group is defined on."
		::= { recfAd10TrkGrpEntry 6 }

recfAd10TrkGrpRemoteAddr 	OBJECT-TYPE
		SYNTAX  PortAddr
		ACCESS  read-write
		STATUS  mandatory
		DESCRIPTION "Parameter Type = Immediate.
			Changes will not affect channels that
			are already connected.

			The trunk group used for the remote end
			of any AD-10 subrate channel using this
			trunk group."
		::= { recfAd10TrkGrpEntry 7 }

recfAd10TrkGrpPartitionID 	OBJECT-TYPE
		SYNTAX  INTEGER (1..1023)
		ACCESS  read-write
		STATUS  mandatory
		DESCRIPTION "Parameter Type = Immediate.
			Changes will not affect channels that
			are already connected.

			The partition ID of this trunk group.
			Used to enforce security on shared
			node."
		::= { recfAd10TrkGrpEntry 8 }

recfAd10TrkGrpSearchDirection 	OBJECT-TYPE
		SYNTAX	INTEGER	{
			lowHigh(1),
			highLow(2)
			}
		ACCESS  read-write
		STATUS  mandatory
		DESCRIPTION "Parameter Type = Immediate.

			INTRODUCED 2.0.0

			Indicates the search order
			within the range specified by
			recfAd10TrkGrpLowElement
			and
			recfAd10TrkGrpHighElement
			attributes."
		DEFVAL { highLow }
		::= { recfAd10TrkGrpEntry 9 }


-- ASM Port Configuration MIB

recfAsmPort    OBJECT IDENTIFIER   ::= { reConfig 12 }

-- ASM X50 Application Configuration MIB

recfAsmX50Table     OBJECT IDENTIFIER   ::= { recfAsmPort 1 }


-- ASM X50 Port Configuration MIB

recfAsmX50PortTable 	OBJECT-TYPE
		SYNTAX    SEQUENCE OF RecfAsmX50PortEntry
		ACCESS    not-accessible
		STATUS    mandatory
		DESCRIPTION " "
		::= { recfAsmX50Table 1 }

recfAsmX50PortEntry 	OBJECT-TYPE
		SYNTAX    RecfAsmX50PortEntry
		ACCESS    not-accessible
		STATUS    mandatory
		DESCRIPTION " "
		INDEX { recfAsmX50PortAddr }
		::= { recfAsmX50PortTable 1 }

RecfAsmX50PortEntry ::= SEQUENCE {
                         recfAsmX50PortAddr
                              PortAddr,
                         recfAsmX50PortStartMode
                              INTEGER,
                         recfAsmX50PortUpdate
                              INTEGER,
			 recfAsmX50PortSpeed
                              INTEGER,
                         recfAsmX50PortProtocol
                              INTEGER,
                         recfAsmX50PortIdlePattern
                              INTEGER,
                         recfAsmX50PortOosTimer
                              INTEGER,
                         recfAsmX50PortPhasorSize
                              INTEGER,
                         recfAsmX50PortTxHouseKbits
                              OCTET STRING,
                         recfAsmX50PortCircuitMap
                              OCTET STRING,
                         recfAsmX50PortPartitionID
                              INTEGER
                         }

recfAsmX50PortAddr 	OBJECT-TYPE
		SYNTAX    PortAddr
		ACCESS    read-only
		STATUS    mandatory
		DESCRIPTION "Parameter Type = Internal."
		::= { recfAsmX50PortEntry 1 }

recfAsmX50PortStartMode 	OBJECT-TYPE
		SYNTAX    INTEGER {
                                   automatic(1),
                                   off(2),
                                   erase(3)
                                   }
		ACCESS    read-write
		STATUS    mandatory
		DESCRIPTION "Parameter Type = Intrusive."
		DEFVAL { off }
		::= { recfAsmX50PortEntry  2 }

recfAsmX50PortUpdate 	OBJECT-TYPE
		SYNTAX    INTEGER {
                                   loaded(1),
				   resetReq(3)
                                   }
		ACCESS    read-only
		STATUS    mandatory
		DESCRIPTION "Parameter Type = Internal."
		DEFVAL { resetReq }
		::= { recfAsmX50PortEntry  3 }

recfAsmX50PortSpeed 	OBJECT-TYPE
		SYNTAX    INTEGER {
			   b64000(480)
                                   }
		ACCESS    read-only
		STATUS    mandatory
		DESCRIPTION "Parameter Type = Internal."
		DEFVAL { b64000 }
		::= { recfAsmX50PortEntry 4 }

recfAsmX50PortProtocol 	OBJECT-TYPE
		SYNTAX    INTEGER {
                                   div2(2),
                                   div3(3),
                                   ad7(7)
                                   }
		ACCESS    read-write
		STATUS    mandatory
		DESCRIPTION "Parameter Type = Intrusive."
		DEFVAL { div2 }
		::= { recfAsmX50PortEntry 5 }

recfAsmX50PortIdlePattern 	OBJECT-TYPE
		SYNTAX    INTEGER (0..127)
		ACCESS    read-write
		STATUS    mandatory
		DESCRIPTION "Parameter Type = Intrusive."
		DEFVAL { 45 }
		::= { recfAsmX50PortEntry 6 }

recfAsmX50PortOosTimer 	OBJECT-TYPE
		SYNTAX  INTEGER {
			sec3(3),
			sec4(4),
			sec5(5),
			sec6(6),
			sec7(7),
			sec8(8),
			sec9(9),
			sec10(10),
			sec11(11),
			sec12(12),
			sec13(13),
			sec14(14),
			sec15(15),
			sec16(16),
			sec17(17),
			sec18(18),
			sec19(19),
			sec20(20),
			sec21(21),
			sec22(22),
			sec23(23),
			sec24(24),
			sec25(25),
			sec26(26),
			sec27(27),
			sec28(28),
			sec29(29),
			sec30(30),
			disabled(255)
			}
		ACCESS  read-write
		STATUS  mandatory
		DESCRIPTION "Parameter Type = Intrusive.
			Time before the port will go out-of-service.
			If disabled, port will never go OOS."
		DEFVAL { sec3 }
		::= { recfAsmX50PortEntry 7 }

recfAsmX50PortPhasorSize 	OBJECT-TYPE
		SYNTAX    INTEGER {
                                   p4(4),
                                   p8(8),
                                   p16(16)
                                   }
		ACCESS    read-write
		STATUS    mandatory
		DESCRIPTION "Parameter Type = Intrusive."
		DEFVAL { p16 }
		::= { recfAsmX50PortEntry  8 }

recfAsmX50PortTxHouseKbits 	OBJECT-TYPE
		SYNTAX    OCTET STRING ( SIZE(1) )
		ACCESS    read-write
		STATUS    mandatory
		DESCRIPTION "Parameter Type = Intrusive.
			The following is the map between bits in the bit
			map and housekeeping bits.
			bit 0 (lsb) - 'H'
			bit 1 - 'G'
			bit 2 - 'F'
			bit 3 - 'E'
			bit 4 - 'D'
			bit 5 - 'C'
			bit 6 - 'B'
			bit 7 - reserved"
		DEFVAL { '00'h }
		::= { recfAsmX50PortEntry  9 }

recfAsmX50PortCircuitMap 	OBJECT-TYPE
		SYNTAX    OCTET STRING ( SIZE(20) )
		ACCESS    read-only
		STATUS    mandatory
		DESCRIPTION "Parameter Type = Internal.
			  Each byte indicates the usage of the circuit on the
			  X.50 aggregate. 1 is for defined, and 0xFF is for
			  undefined."
		::= { recfAsmX50PortEntry  10 }

recfAsmX50PortPartitionID 	OBJECT-TYPE
		SYNTAX    INTEGER (1..1023)
		ACCESS    read-write
		STATUS    mandatory
		DESCRIPTION "Parameter Type = Intrusive."
		::= { recfAsmX50PortEntry  11 }


-- ASM X50 Circuit Configuration MIB

recfAsmX50CkTable 	OBJECT-TYPE
		SYNTAX    SEQUENCE OF RecfAsmX50CkEntry
		ACCESS    not-accessible
		STATUS    mandatory
		DESCRIPTION " "
		::= { recfAsmX50Table 2 }

recfAsmX50CkEntry 	OBJECT-TYPE
		SYNTAX    RecfAsmX50CkEntry
		ACCESS    not-accessible
		STATUS    mandatory
		DESCRIPTION " "
		INDEX { recfAsmX50CkAddr }
		::= { recfAsmX50CkTable 1 }

RecfAsmX50CkEntry   ::= SEQUENCE {
                         recfAsmX50CkAddr
                              AsmX50CkAddr,
                         recfAsmX50CkStartMode
                              INTEGER,
                         recfAsmX50CkUpdate
                              INTEGER,
                         recfAsmX50CkSpeed
                              INTEGER,
                         recfAsmX50CkTimeSlot
                              INTEGER,
                         recfAsmX50CkPhasorSize
                              INTEGER,
                         recfAsmX50CkSbitConnectState
                              INTEGER
                         }

recfAsmX50CkAddr 	OBJECT-TYPE
		SYNTAX    AsmX50CkAddr
		ACCESS    read-only
		STATUS    mandatory
		DESCRIPTION "Parameter Type = Internal."
		::= { recfAsmX50CkEntry 1 }

recfAsmX50CkStartMode 	OBJECT-TYPE
		SYNTAX    INTEGER {
                                   automatic(1),
                                   off(2),
                                   erase(3)
                                   }
		ACCESS    read-write
		STATUS    mandatory
		DESCRIPTION "Parameter Type = Intrusive."
		DEFVAL { off }
		::= { recfAsmX50CkEntry 2 }

recfAsmX50CkUpdate 	OBJECT-TYPE
		SYNTAX  INTEGER {
			loaded(1),
			resetReq(3)
			}
		ACCESS  read-only
		STATUS  mandatory
		DESCRIPTION "Parameter Type = Internal.
			If set to resetReq, need to reset the
			ASM X.50 circuit."
		DEFVAL { resetReq }
		::= { recfAsmX50CkEntry 3 }

recfAsmX50CkSpeed 	OBJECT-TYPE
		SYNTAX    INTEGER {
                                   s2400(18),
                                   s4800(36),
                                   s9600(72),
                                   s19200(144)
                                   }
		ACCESS    read-write
		STATUS    mandatory
		DESCRIPTION "Parameter Type = Intrusive."
		DEFVAL { s9600 }
		::= { recfAsmX50CkEntry 4 }

recfAsmX50CkTimeSlot 	OBJECT-TYPE
		SYNTAX    INTEGER {
                                   ab(81),
                                   cd(83),
                                   a(41),
                                   b(42),
                                   c(43),
                                   d(44),
                                   e(45),
                                   a1(1),
                                   a2(6),
                                   a3(11),
                                   a4(16),
                                   b1(2),
                                   b2(7),
                                   b3(12),
                                   b4(17),
                                   c1(3),
                                   c2(8),
                                   c3(13),
                                   c4(18),
                                   d1(4),
                                   d2(9),
                                   d3(14),
                                   d4(19),
                                   e1(5),
                                   e2(10),
                                   e3(15),
                                   e4(20)
                                   }
		ACCESS    read-write
		STATUS    mandatory
		DESCRIPTION "Parameter Type = Intrusive."
		DEFVAL { a }
		::= { recfAsmX50CkEntry 5 }

recfAsmX50CkPhasorSize 	OBJECT-TYPE
		SYNTAX    INTEGER {
                                   p4(4),
                                   p6(6),
                                   p8(8),
                                   p12(12),
                                   p16(16)
                                   }
		ACCESS    read-write
		STATUS    mandatory
		DESCRIPTION "Parameter Type = Intrusive."
		DEFVAL { p16 }
		::= { recfAsmX50CkEntry 6 }

recfAsmX50CkSbitConnectState 	OBJECT-TYPE
		SYNTAX    INTEGER {
                                   one(1),
                                   zero(2)
                                   }
		ACCESS    read-write
		STATUS    mandatory
		DESCRIPTION "Parameter Type = Intrusive."
		DEFVAL { one }
		::= { recfAsmX50CkEntry 7 }

-- ASM Voice Application Configuration MIB

recfAsmVoice 	OBJECT IDENTIFIER ::= { recfAsmPort 2 }


-- ASM Voice Trunk Group Configuration MIB

recfAsmVoiceTrkGrpTable 	OBJECT-TYPE
		SYNTAX  SEQUENCE OF RecfAsmVoiceTrkGrpEntry
		ACCESS  not-accessible
		STATUS  mandatory
		DESCRIPTION "Trunk group entries in this table
			will serve as a profile for multiple
			physical ASM ports.

			If intended to use as a non-contention
			system, then this trunk group will
			represent only one ASM Voice port."
		::= { recfAsmVoice 1 }

recfAsmVoiceTrkGrpEntry 	OBJECT-TYPE
		SYNTAX  RecfAsmVoiceTrkGrpEntry
		ACCESS  not-accessible
		STATUS  mandatory
		DESCRIPTION " "
		INDEX   { recfAsmVoiceTrkGrpAddr }
		::= { recfAsmVoiceTrkGrpTable 1 }

RecfAsmVoiceTrkGrpEntry         ::= SEQUENCE {
			recfAsmVoiceTrkGrpAddr
				PortAddr,
			recfAsmVoiceTrkGrpStartMode
				INTEGER,
			recfAsmVoiceTrkGrpPort
				PortAddr,
			recfAsmVoiceTrkGrpLowElement
				INTEGER,
			recfAsmVoiceTrkGrpHighElement
				INTEGER,
			recfAsmVoiceTrkGrpRemoteNodeID
				NodeAddr,
			recfAsmVoiceTrkGrpRemoteAddr
				PortAddr,
			recfAsmVoiceTrkGrpPartitionID
				INTEGER,
			recfAsmVoiceTrkGrpCompressMode
				INTEGER,
			recfAsmVoiceTrkGrpSpeed
				INTEGER,
			recfAsmVoiceTrkGrpSignalingType
				INTEGER,
			recfAsmVoiceTrkGrpDTMFRelay
				INTEGER,
			recfAsmVoiceTrkGrpFaxRelay
				INTEGER,
			recfAsmVoiceTrkGrpFaxNSFMode
				INTEGER,
			recfAsmVoiceTrkGrpTxAudSrcMode
				INTEGER,
			recfAsmVoiceTrkGrpRxAudOutMode
				INTEGER,
			recfAsmVoiceTrkGrpEchoCancel
				INTEGER,
			recfAsmVoiceTrkGrpNonLinear
				INTEGER,
			recfAsmVoiceTrkGrpDataMode
				INTEGER,
			recfAsmVoiceTrkGrpTxPCMGain
				INTEGER,
			recfAsmVoiceTrkGrpRxPCMGain
				INTEGER,
			recfAsmVoiceTrkGrpVocoderEnable
				INTEGER,
			recfAsmVoiceTrkGrpSigIdlePttrn
				INTEGER,
			recfAsmVoiceTrkGrpPCMPhasorSize
				INTEGER,
			recfAsmVoiceTrkGrpSubratePhSize
				INTEGER,
			recfAsmVoiceTrkGrpLocalSigConf
				INTEGER,
			recfAsmVoiceTrkGrpRemoteSigConf
				INTEGER,
			recfAsmVoiceTrkGrpRmtSigPattern
				INTEGER,
			recfAsmVoiceTrkGrpCelpNetSigMd
				INTEGER,
			recfAsmVoiceTrkGrpSearchDir
				INTEGER
			}

recfAsmVoiceTrkGrpAddr 	OBJECT-TYPE
		SYNTAX  PortAddr
		ACCESS  read-only
		STATUS  mandatory
		DESCRIPTION "Parameter Type = Internal.
			Address of the voice trunk group."
		::= { recfAsmVoiceTrkGrpEntry 1 }

recfAsmVoiceTrkGrpStartMode 	OBJECT-TYPE
		SYNTAX  INTEGER {
			automatic(1),
			off(2),
			erase(3)
			}
		ACCESS  read-write
		STATUS  mandatory
		DESCRIPTION "Parameter Type = Immediate.
			Changes will not affect channels that
			are already connected.

			Erase will fail if there are any voice
			channels connected that are using this
			trunk group MIB."
		DEFVAL { off }
		::= { recfAsmVoiceTrkGrpEntry 2 }

recfAsmVoiceTrkGrpPort 	OBJECT-TYPE
		SYNTAX  PortAddr
		ACCESS  read-write
		STATUS  mandatory
		DESCRIPTION "Parameter Type = Immediate.
			Changes will not affect channels that
			are already connected.

			Defines the T1M/E1M port that this voice
			trunk group may be connected to. The
			range of available bundles is
			determined by this field,
			recfAsmVoiceTrkGrpLowElement, and
			recfAsmVoiceTrkGrpHighElement."
		::= { recfAsmVoiceTrkGrpEntry 3 }

recfAsmVoiceTrkGrpLowElement 	OBJECT-TYPE
		SYNTAX  INTEGER (0..31)
		ACCESS  read-write
		STATUS  mandatory
		DESCRIPTION "Parameter Type = Immediate.
			Changes will not affect channels that
			are already connected.

			The low end of the element range
			available for use by this Voice
			trunk group on on the T1M/E1M port
			set in recfAsmVoiceTrkGrpPort.

			If the value of this field is the same
			as recfAsmVoiceTrkGrpHighElement, then
			this Voice port is not a contention port.

			If the value of this field is greater
			than recfAsmVoiceTrkGrpHighElement, then
			this trunk group is invalid, and any
			attempt to connect a channel using this
			trunk group will fail."
		::= { recfAsmVoiceTrkGrpEntry 4 }

recfAsmVoiceTrkGrpHighElement 	OBJECT-TYPE
		SYNTAX  INTEGER (0..31)
		ACCESS  read-write
		STATUS  mandatory
		DESCRIPTION "Parameter Type = Immediate.
			Changes will not affect channels that
			are already connected.

			The high end of the element range
			available for use by this voice
			trunk group on on the T1M/E1M port
			set in recfAsmVoiceTrkGrpPort.

			If the value of this field is the same
			as recfAsmVoiceTrkGrpLowElement, then
			this voice port is not a contention port.

			If the value of this field is less
			than recfAsmVoiceTrkGrpLowElement, then
			this trunk group is invalid, and any
			attempt to connect a channel using this
			trunk group will fail."
		::= { recfAsmVoiceTrkGrpEntry 5 }

recfAsmVoiceTrkGrpRemoteNodeID 	OBJECT-TYPE
		SYNTAX  NodeAddr
		ACCESS  read-write
		STATUS  mandatory
		DESCRIPTION "Parameter Type = Immediate.
			Changes will not affect channels that
			are already connected.

			The node that any voice subrate channel
			using this trunk group will connect to.
			May be the same as the local node that
			this voice trunk group is defined on."
		::= { recfAsmVoiceTrkGrpEntry 6 }

recfAsmVoiceTrkGrpRemoteAddr 	OBJECT-TYPE
		SYNTAX  PortAddr
		ACCESS  read-write
		STATUS  mandatory
		DESCRIPTION "Parameter Type = Immediate.
			Changes will not affect channels that
			are already connected.

			The trunk group used for the remote end
			of any voice subrate channel using this
			trunk group."
		::= { recfAsmVoiceTrkGrpEntry 7 }

recfAsmVoiceTrkGrpPartitionID 	OBJECT-TYPE
		SYNTAX  INTEGER (1..1023)
		ACCESS  read-write
		STATUS  mandatory
		DESCRIPTION "Parameter Type = Immediate.
			Changes will not affect channels that
			are already connected.

			The partition ID of this trunk group.
			Used to enforce security on shared
			node."
		::= { recfAsmVoiceTrkGrpEntry 8 }

recfAsmVoiceTrkGrpCompressMode 	OBJECT-TYPE
		SYNTAX  INTEGER {
			tCelp(1),
			atc(2),
			adpcm(3)
			}
		ACCESS  read-write
		STATUS  mandatory
		DESCRIPTION "Parameter Type = Immediate.
			Changes will not affect channels that
			are already connected.

			Defines which compression algorithm to
			use for voice channels connected using
			this voice trunk group."
		DEFVAL { tCelp }
		::= { recfAsmVoiceTrkGrpEntry 9 }

recfAsmVoiceTrkGrpSpeed 	OBJECT-TYPE
		SYNTAX  INTEGER {
			b5333(40), b7200(54), b7466(56),
			b8000(60), b8533(64),
			b9066(68), b9600(72),
			b10133(76), b10666(80),
			b11200(84), b11733(88),
			b12266(92), b12800(96),
			b13333(100), b13866(104),
			b14400(108), b14933(112),
			b15466(116), b16000(120),
			b16533(124), b17066(128),
			b17600(132), b18133(136),
			b18666(140), b19200(144),
			b19733(148), b20266(152),
			b20800(156), b21333(160),
			b21866(164), b22400(168),
			b22933(172), b23466(176),
			b24000(180), b24533(184),
			b25066(188), b25600(192),
			b26133(196), b26666(200),
			b27200(204), b27733(208),
			b28266(212), b28800(216),
			b29333(220), b29866(224),
			b30400(228), b30933(232),
			b31466(236), b31733(238),
			b32000(240), b36000(270)
			}
		ACCESS  read-write
		STATUS  mandatory
		DESCRIPTION "Parameter Type = Immediate.
			Changes will not affect channels that
			are already connected.

			The compressed channel data rate for
			any voice subrate connections using
			this voice trunk group.

			For channels using a CELP compression
			algorithm, only speeds of 5.333 Kbps,
			7.2 Kbps, 8 Kbps, and 9.6 Kbps will be
			supported.

			For channels using the ATC compression
			algorithm, only the speeds between
			7.466 Kbps and 32 Kbps will be
			supported.

			For channels using the ADPCM compression
			algorithm, only the speeds 31.733 and
			32.000 Kbps will be supported."
		DEFVAL { b8000 }
		::= { recfAsmVoiceTrkGrpEntry 10 }

recfAsmVoiceTrkGrpSignalingType 	OBJECT-TYPE
		SYNTAX  INTEGER {
			none(1),
			a(2),
			ab(3),
			abcd(4),
			ac15-dtmf(8),
			ac15-dp(9)
			}
		ACCESS  read-write
		STATUS  mandatory
		DESCRIPTION "Parameter Type = Immediate.
			Changes will not affect channels that
			are already connected.

			The type of signaling used by the
			T1M/E1M bundles that connect to voice
			ports using this trunk group."
		DEFVAL { none }
		::= { recfAsmVoiceTrkGrpEntry 11 }

recfAsmVoiceTrkGrpDTMFRelay 	OBJECT-TYPE
		SYNTAX  INTEGER {
			enable(2),
			disable(1)
			}
		ACCESS  read-write
		STATUS  mandatory
		DESCRIPTION "Parameter Type = Immediate.
			Changes will not affect channels that
			are already connected.

			Controls the DTMF relay on any ASM voice
			ports that use this trunk group. When
			enabled, DTMF signals are transferred
			through the connection.

			Not applicable in ADPCM mode."
		DEFVAL { enable }
		::= { recfAsmVoiceTrkGrpEntry 12 }

recfAsmVoiceTrkGrpFaxRelay 	OBJECT-TYPE
		SYNTAX  INTEGER {
			enable(2),
			disable(1)
			}
		ACCESS  read-write
		STATUS  mandatory
		DESCRIPTION "Parameter Type = Immediate.
			Changes will not affect channels that
			are already connected.

			Controls the fax relay on any ASM voice
			ports that use this trunk group. When
			enabled, fax operation will be
			supported over the connection.

			Not applicable in ADPCM mode."
		DEFVAL { enable }
		::= { recfAsmVoiceTrkGrpEntry 13 }

recfAsmVoiceTrkGrpFaxNSFMode 	OBJECT-TYPE
		SYNTAX  INTEGER {
			enable(2),
			disable(1)
			}
		ACCESS  read-write
		STATUS  mandatory
		DESCRIPTION "Parameter Type = Immediate.
			Changes will not affect channels that
			are already connected.

			Controls the non-standard fax mode on
			any ASM voice ports that use this trunk
			group.

			Not applicable in ADPCM mode."
		DEFVAL { disable }
		::= { recfAsmVoiceTrkGrpEntry 14 }

recfAsmVoiceTrkGrpTxAudSrcMode 	OBJECT-TYPE
		SYNTAX  INTEGER {
			normal(1),
			silence(2),
			toneDMW(3)
			}
		ACCESS  read-write
		STATUS  mandatory
		DESCRIPTION "Parameter Type = Immediate.
			Changes will not affect channels that
			are already connected.

			Controls the transmit audio source on
			any ASM voice ports that use this trunk
			group."
		DEFVAL { normal }
		::= { recfAsmVoiceTrkGrpEntry 15 }

recfAsmVoiceTrkGrpRxAudOutMode 	OBJECT-TYPE
		SYNTAX  INTEGER {
			normal(1),
			silence(2),
			toneDMW(3)
			}
		ACCESS  read-write
		STATUS  mandatory
		DESCRIPTION "Parameter Type = Immediate.
			Changes will not affect channels that
			are already connected.

			Controls the receive audio output on
			any ASM voice ports that use this trunk
			group."
		DEFVAL { normal }
		::= { recfAsmVoiceTrkGrpEntry 16 }

recfAsmVoiceTrkGrpEchoCancel 	OBJECT-TYPE
		SYNTAX  INTEGER {
			enable(2),
			disable(1)
			}
		ACCESS  read-write
		STATUS  mandatory
		DESCRIPTION "Parameter Type = Immediate.
			Changes will not affect channels that
			are already connected.

			Controls the echo cancellation on any
			ASM voice ports that use this trunk
			group.

			Not applicable in ADPCM mode."
		DEFVAL { enable }
		::= { recfAsmVoiceTrkGrpEntry 17 }

recfAsmVoiceTrkGrpNonLinear 	OBJECT-TYPE
		SYNTAX  INTEGER {
			enable(2),
			disable(1)
			}
		ACCESS  read-write
		STATUS  mandatory
		DESCRIPTION "Parameter Type = Immediate.
			Changes will not affect channels that
			are already connected.

			Controls the non-linear processing
			inside the echo canceller on any ASM
			voice ports that use this trunk group.

			Not applicable in ADPCM mode."
		DEFVAL { disable }
		::= { recfAsmVoiceTrkGrpEntry 18 }

recfAsmVoiceTrkGrpDataMode 	OBJECT-TYPE
		SYNTAX  INTEGER {
			enable(2),
			disable(1)
			}
		ACCESS  read-write
		STATUS  mandatory
		DESCRIPTION "Parameter Type = Immediate.
			Changes will not affect channels that
			are already connected.

			Controls the 2100 Hz detection logic
			and data mode operation with the ATC
			vocoder on any ASM Voice ports that use
			this trunk group."
		DEFVAL { disable }
		::= { recfAsmVoiceTrkGrpEntry 19 }

recfAsmVoiceTrkGrpTxPCMGain 	OBJECT-TYPE
		SYNTAX  INTEGER (1..256)
		ACCESS  read-write
		STATUS  mandatory
		DESCRIPTION "Parameter Type = Immediate.
			Changes will not affect channels that
			are already connected.

			Controls the transmit PCM gain on any
			ASM voice ports that use this trunk
			group. Range is defined from -33.0 dB
			to +18.0 dB with .2 dB increments.
			Default is 0 dB."
		DEFVAL { 166 }
		::= { recfAsmVoiceTrkGrpEntry 20 }

recfAsmVoiceTrkGrpRxPCMGain 	OBJECT-TYPE
		SYNTAX  INTEGER (1..256)
		ACCESS  read-write
		STATUS  mandatory
		DESCRIPTION "Parameter Type = Immediate.
			Changes will not affect channels that
			are already connected.

			Controls the receive PCM gain on any
			ASM voice ports that use this trunk
			group. Range is defined from -33.0 dB
			to +18.0 dB with .2 dB increments.
			Default is 0 dB."
		DEFVAL { 166 }
		::= { recfAsmVoiceTrkGrpEntry 21 }

recfAsmVoiceTrkGrpVocoderEnable 	OBJECT-TYPE
		SYNTAX  INTEGER {
			normal(1),
			disable(2)
			}
		ACCESS  read-write
		STATUS  mandatory
		DESCRIPTION "Parameter Type = Immediate.
			Changes will not affect channels that
			are already connected.

			Controls the vocoder mode on any ASM
			voice ports that use this trunk group.

			Not applicable in ADPCM mode."
		DEFVAL { normal }
		::= { recfAsmVoiceTrkGrpEntry 22 }

recfAsmVoiceTrkGrpSigIdlePttrn 	OBJECT-TYPE
		SYNTAX  INTEGER {
			a0-b0-c0-d0(16),
			a0-b0-c0-d1(8),
			a0-b0-c1-d0(4),
			a0-b0-c1-d1(12),
			a0-b1-c0-d0(2),
			a0-b1-c0-d1(10),
			a0-b1-c1-d0(6),
			a0-b1-c1-d1(14),
			a1-b0-c0-d0(1),
			a1-b0-c0-d1(9),
			a1-b0-c1-d0(5),
			a1-b0-c1-d1(13),
			a1-b1-c0-d0(3),
			a1-b1-c0-d1(11),
			a1-b1-c1-d0(7),
			a1-b1-c1-d1(15)
			}
		ACCESS  read-write
		STATUS  mandatory
		DESCRIPTION "Parameter Type = Immediate.
			Changes will not affect channels that
			are already connected.

			Defines the idle signaling pattern on
			any ASM voice ports that use this trunk
			group. This pattern is delivered to
			receive signal channel connections at
			times prior to the availability of a
			verified reliable signal channel
			source."
		DEFVAL { a0-b0-c0-d0 }
		::= { recfAsmVoiceTrkGrpEntry 23 }

recfAsmVoiceTrkGrpPCMPhasorSize 	OBJECT-TYPE
		SYNTAX  INTEGER (4..255)
		ACCESS  read-write
		STATUS  mandatory
		DESCRIPTION "Parameter Type = Immediate.
			Changes will not affect channels that
			are already connected.

			Size of the phasor (in bytes) on the
			PCM (64K) side of any ASM voice port
			using this trunk group."
		DEFVAL { 16 }
		::= { recfAsmVoiceTrkGrpEntry 24 }

recfAsmVoiceTrkGrpSubratePhSize 	OBJECT-TYPE
		SYNTAX  INTEGER (4..100)
		ACCESS  read-write
		STATUS  mandatory
		DESCRIPTION "Parameter Type = Immediate.
			Changes will not affect channels that
			are already connected.

			Size of the phasor (in bytes) on the
			subrate side of any ASM voice port
			using this trunk group."
		DEFVAL { 16 }
		::= { recfAsmVoiceTrkGrpEntry 25 }

recfAsmVoiceTrkGrpLocalSigConf 	OBJECT-TYPE
		SYNTAX  INTEGER {
			fxs-ard(2),
			fxo(3),
			fxs-or-em(4)
			}
		ACCESS  read-write
		STATUS  mandatory
		DESCRIPTION "Parameter Type = Immediate.
			Changes will not affect channels that
			are already connected.

			AD-10 and ASM signalling
			incompatibility parameters."
		DEFVAL { fxs-ard }
		::= { recfAsmVoiceTrkGrpEntry 26 }

recfAsmVoiceTrkGrpRemoteSigConf 	OBJECT-TYPE
		SYNTAX  INTEGER {
			other(1),
			ad10Fxs(2),
			ad10Fxo(3),
			ad10Em(4)
			}
		ACCESS  read-write
		STATUS  mandatory
		DESCRIPTION "Parameter Type = Immediate.
			Changes will not affect channels that
			are already connected.

			AD-10 and ASM signalling
			incompatibility parameters."
		DEFVAL { other }
		::= { recfAsmVoiceTrkGrpEntry 27 }

recfAsmVoiceTrkGrpRmtSigPattern 	OBJECT-TYPE
		SYNTAX  INTEGER {
			a0-b0-c0-d0(16),
			a0-b0-c0-d1(8),
			a0-b0-c1-d0(4),
			a0-b0-c1-d1(12),
			a0-b1-c0-d0(2),
			a0-b1-c0-d1(10),
			a0-b1-c1-d0(6),
			a0-b1-c1-d1(14),
			a1-b0-c0-d0(1),
			a1-b0-c0-d1(9),
			a1-b0-c1-d0(5),
			a1-b0-c1-d1(13),
			a1-b1-c0-d0(3),
			a1-b1-c0-d1(11),
			a1-b1-c1-d0(7),
			a1-b1-c1-d1(15)
			}
		ACCESS  read-write
		STATUS  mandatory
		DESCRIPTION "Parameter Type = Immediate.
			Changes will not affect channels that
			are already connected.

			Defines the remote signaling pattern on
			any ASM voice ports that use this trunk
			group. This pattern is delivered to
			receive signal channel connections at
			times prior to the availability of a
			verified reliable signal channel
			source."
		DEFVAL { a0-b0-c0-d0 }
		::= { recfAsmVoiceTrkGrpEntry 28 }

recfAsmVoiceTrkGrpCelpNetSigMd 	OBJECT-TYPE
		SYNTAX	INTEGER	{
			auto(1),
			st(2),
			link(3)
			}
		ACCESS  read-write
		STATUS  mandatory
		DESCRIPTION "Parameter Type = Immediate.

			INTRODUCED 2.0.0

			Enable autodetection of CELP/ATC channel
			connected equipment so as to
			automatically change format to become
			compatible with either LINK (5 byte) or
			ST (8 byte) channel modes.  Alternately,
			this parameter hard sets CELP/ATC
			channels to be compatible only with
			either LINK or ST mode compatible
			equipment."
		DEFVAL { st }
		::= { recfAsmVoiceTrkGrpEntry 29 }

recfAsmVoiceTrkGrpSearchDir 	OBJECT-TYPE
		SYNTAX	INTEGER	{
			lowHigh(1),
			highLow(2)
			}
		ACCESS  read-write
		STATUS  mandatory
		DESCRIPTION "Parameter Type = Immediate.

			INTRODUCED 2.0.0

			Indicates the search order
			within the range specified by
			recfAsmVoiceTrkGrpLowElement
			and
			recfAsmVoiceTrkGrpHighElement
			attributes."
		DEFVAL { highLow }
		::= { recfAsmVoiceTrkGrpEntry 30 }



-- RTM Port Configuration

recfRtmPort 	OBJECT IDENTIFIER ::= { reConfig 13 }

recfRtmPortTable 	OBJECT-TYPE
		SYNTAX	SEQUENCE OF RecfRtmPortEntry
		ACCESS	not-accessible
		STATUS	mandatory
		DESCRIPTION " "
		::= { recfRtmPort 1 }

recfRtmPortEntry 	OBJECT-TYPE
		SYNTAX	RecfRtmPortEntry
		ACCESS	not-accessible
		STATUS	mandatory
		DESCRIPTION " "
		INDEX { recfRtmPortAddr }
		::= { recfRtmPortTable 1 }

RecfRtmPortEntry                ::= SEQUENCE {
			recfRtmPortAddr
				PortAddr,
			recfRtmPortStartMode
				INTEGER,
			recfRtmPortUpdate
				INTEGER,
			recfRtmPortType
				INTEGER,
			recfRtmPortPartitionID
				INTEGER
			}

recfRtmPortAddr 	OBJECT-TYPE
		SYNTAX	PortAddr
		ACCESS	read-only
		STATUS	mandatory
		DESCRIPTION "Parameter Type = Internal."
		::= { recfRtmPortEntry 1 }

recfRtmPortStartMode 	OBJECT-TYPE
		SYNTAX	INTEGER {
			automatic(1),
			off(2),
			erase(3)
			}
		ACCESS	read-write
		STATUS	mandatory
		DESCRIPTION "Parameter Type = Intrusive.
			Erase will reset all parameters to
			their default values."
		DEFVAL { off }
		::= { recfRtmPortEntry 2 }

recfRtmPortUpdate 	OBJECT-TYPE
		SYNTAX	INTEGER {
			loaded(1),
			resetReq(3)
			}
		ACCESS  read-only
		STATUS  mandatory
		DESCRIPTION "Parameter Type = Internal."
		DEFVAL { resetReq }
		::= { recfRtmPortEntry 3 }

recfRtmPortType 	OBJECT-TYPE
		SYNTAX	INTEGER {
			null(1),
			ad3(2),
			ad7(3)
			}
		ACCESS  read-write
		STATUS  mandatory
		DESCRIPTION "Parameter Type = Intrusive.
			Setting AD-3 or AD-7 will allocate all
			of the access device ports with their
			default parameters."
		DEFVAL { null }
		::= { recfRtmPortEntry 4 }

recfRtmPortPartitionID 	OBJECT-TYPE
		SYNTAX	INTEGER (1..1023)
		ACCESS  read-write
		STATUS  mandatory
		DESCRIPTION "Parameter Type = Intrusive.
			Default value is the partition ID of
			the node."
		::= { recfRtmPortEntry 5 }


-- AD-3 and AD-7 Port Configuration

recfRtmAdPortTable 	OBJECT-TYPE
		SYNTAX	SEQUENCE OF RecfRtmAdPortEntry
		ACCESS	not-accessible
		STATUS	mandatory
		DESCRIPTION " "
		::= { recfRtmPort 2 }

recfRtmAdPortEntry 	OBJECT-TYPE
		SYNTAX	RecfRtmAdPortEntry
		ACCESS  not-accessible
		STATUS  mandatory
		DESCRIPTION " "
		INDEX	{ recfRtmAdPortAddr }
		::= { recfRtmAdPortTable 1 }

RecfRtmAdPortEntry              ::= SEQUENCE {
			recfRtmAdPortAddr
				RtmAdPortAddr,
			recfRtmAdPortStartMode
				INTEGER,
			recfRtmAdPortUpdate
				INTEGER,
			recfRtmAdPortSpeed
				INTEGER,
			recfRtmAdPortDataBits
				INTEGER,
			recfRtmAdPortCommMode
				INTEGER,
			recfRtmAdPortType
				INTEGER
			}

recfRtmAdPortAddr 	OBJECT-TYPE
		SYNTAX	RtmAdPortAddr
		ACCESS	read-only
		STATUS	mandatory
		DESCRIPTION "Parameter Type = Internal."
		::= { recfRtmAdPortEntry 1 }

recfRtmAdPortStartMode 	OBJECT-TYPE
		SYNTAX	INTEGER {
			automatic(1),
			off(2),
			erase(3)
			}
		ACCESS	read-write
		STATUS	mandatory
		DESCRIPTION "Parameter Type = Intrusive.
			Erase will reset all parameters to
			their default values."
		DEFVAL { off }
		::= { recfRtmAdPortEntry 2 }

recfRtmAdPortUpdate 	OBJECT-TYPE
		SYNTAX  INTEGER {
			loaded(1),
			resetReq(3)
			}
		ACCESS  read-only
		STATUS  mandatory
		DESCRIPTION "Parameter Type = Internal."
		DEFVAL { resetReq }
		::= { recfRtmAdPortEntry 3 }

recfRtmAdPortSpeed 	OBJECT-TYPE
		SYNTAX  INTEGER {
			s150(2), s300(3),
			s1200(9), s2400(18),
			s4800(36), s8000(60),
			s9600(72), s14400(108),
			s19200(144), s32000(240),
			s38400(288), s48000(360),
			s56000(420), s64000(480),
			s128000(960)
			}
		ACCESS  read-write
		STATUS  mandatory
		DESCRIPTION "Parameter Type = Intrusive.
			If the speed is set to s56000 and
			recfRtmAdPortDataBits attribute set
			to b7, the channel will be transported
			as a 64000 bit stuffed channel.
			If the speed is set to s56000 and
			recfRtmAdPortDataBits attribute set
			to b8, the channel will be a subrate
			channel."
		DEFVAL { s64000 }
		::= { recfRtmAdPortEntry 4 }

recfRtmAdPortDataBits 	OBJECT-TYPE
		SYNTAX	INTEGER {
			b7(1),
			b8(2)
			}
		ACCESS  read-write
		STATUS  mandatory
		DESCRIPTION "Parameter Type = Intrusive.
			Value b7 cannot be used in subrate
			connections."
		DEFVAL { b8 }
		::= { recfRtmAdPortEntry 5 }

recfRtmAdPortCommMode 	OBJECT-TYPE
		SYNTAX  INTEGER {
			sync(1),
			async(2)
			}
		ACCESS  read-write
		STATUS  mandatory
		DESCRIPTION "Parameter Type = Intrusive."
		DEFVAL { sync }
		::= { recfRtmAdPortEntry 6 }

recfRtmAdPortType 	OBJECT-TYPE
		SYNTAX  INTEGER {
			null(1),
			io(2),
			bandContent(3)
			}
		ACCESS  read-write
		STATUS  mandatory
		DESCRIPTION "Parameter Type = Intrusive."
		DEFVAL { null }
		::= { recfRtmAdPortEntry 7 }


-- LGM port Configuration

recfLgmPort 	OBJECT IDENTIFIER ::= { reConfig 14 }

recfLgmPortTable 	OBJECT-TYPE
		SYNTAX    SEQUENCE OF RecfLgmPortEntry
		ACCESS    not-accessible
		STATUS    mandatory
		DESCRIPTION " "
		::=  { recfLgmPort 1 }

recfLgmPortEntry 	OBJECT-TYPE
		SYNTAX    RecfLgmPortEntry
		ACCESS    not-accessible
		STATUS    mandatory
		DESCRIPTION "INTRODUCED 2.0.0"
		INDEX { recfLgmPortAddr }
		::=  { recfLgmPortTable 1 }

RecfLgmPortEntry 		::=  SEQUENCE 	{
			recfLgmPortAddr
				PortAddr,
			recfLgmPortStartMode
				INTEGER,
			recfLgmPortUpdate
				INTEGER,
			recfLgmPortArq
				INTEGER,
			recfLgmPortGroup
				OCTET STRING,
			recfLgmPortEncryption
				INTEGER,
   			recfLgmPortSyncChar
	       			INTEGER,
			recfLgmPortSyncLevel
	      			INTEGER,
			recfLgmPortSatelliteHop
				INTEGER,
			recfLgmPortOosTimer
				INTEGER,
			recfLgmPortPartitionID
				INTEGER,
			recfLgmPortBitMode
				INTEGER,
			recfLgmPortInbandSuperrate
				INTEGER,
			recfLgmPortInbandSubrate
				INTEGER,
			recfLgmPortOutbandSuperrate
				INTEGER,
			recfLgmPortOutbandSubrate
				INTEGER
			}

recfLgmPortAddr 	OBJECT-TYPE
		SYNTAX    PortAddr
		ACCESS    read-only
		STATUS    mandatory
		DESCRIPTION "Parameter Type = Internal.
			This is a virtual port address
			in type:group:port format."
		::= { recfLgmPortEntry 1 }

recfLgmPortStartMode 	OBJECT-TYPE
		SYNTAX	INTEGER {
			automatic(1),
			off(2),
			erase(3)
			}
		ACCESS	read-write
		STATUS 	mandatory
		DESCRIPTION "Parameter Type = Intrusive.
			Setting to erase will fail if the
			LGM port has any non-removed channels.
			If successful, returns the initial
			port configuration (with its default
			values) and erases any channels defined
			on this port."
		DEFVAL { off }
		::= { recfLgmPortEntry 2 }

recfLgmPortUpdate 	OBJECT-TYPE
		SYNTAX	INTEGER {
				loaded(1),
	       			updateReq(2),
	       			resetReq(3)
			}
		ACCESS	read-only
		STATUS	mandatory
		DESCRIPTION "Parameter Type = Internal."
		DEFVAL { resetReq }
		::=  { recfLgmPortEntry 3 }

recfLgmPortArq 	OBJECT-TYPE
		SYNTAX  INTEGER {
			s3200(1),
			s6400(2),
			s9600(3)
			}
		ACCESS  read-write
		STATUS	mandatory
		DESCRIPTION "Parameter Type = Intrusive.
			Specifies ARQ speed. Unit of bps, i
			which may not exceed the 9600. "
		DEFVAL { s9600 }
		::= { recfLgmPortEntry 4 }

recfLgmPortGroup 	OBJECT-TYPE
		SYNTAX	OCTET STRING (SIZE (1))
		ACCESS 	read-write
		STATUS	mandatory
		DESCRIPTION "Parameter Type = Non-intrusive.
			Intended to force channels to use
			specific groups of LGM ports. There
			can be up to seven groups for each
			LGM port.
			       		Bit map bits 1 (lsb) to 7 indicates i
			the group(s) of the LGM."
		DEFVAL { '7f'h }
		::= { recfLgmPortEntry 5 }

recfLgmPortEncryption 	OBJECT-TYPE
		SYNTAX	INTEGER {
			normal (1),
			encrypted(2)
			}
		ACCESS 	read-write
		STATUS	mandatory
		DESCRIPTION "Parameter Type = Non-intrusive."
		DEFVAL { normal }
		::= { recfLgmPortEntry 6 }

recfLgmPortSatelliteHop 	OBJECT-TYPE
		SYNTAX	INTEGER (0..4)
		ACCESS	read-write
		STATUS	mandatory
		DESCRIPTION "Parameter Type = Non-intrusive.
			Specifies the number of satellite hops
			per end - to - end point connection.
			Earth station - satellite - earth
			station connection represents one hop."
		DEFVAL { 0 }
		::= { recfLgmPortEntry 7 }

recfLgmPortSyncChar 	OBJECT-TYPE
		SYNTAX	INTEGER {
			syncChar4(4),
			syncChar8(8)
			}
		ACCESS	read-write
		STATUS	mandatory
		DESCRIPTION "Parameter Type = Intrusive.
			Specifies number of sync characters
			per frame."
		DEFVAL { syncChar4 }
		::= { recfLgmPortEntry 8 }

recfLgmPortSyncLevel 	OBJECT-TYPE
		SYNTAX	INTEGER {
			level1(1),
			level2(2)
			}
		ACCESS	read-write
		STATUS	mandatory
		DESCRIPTION "Parameter Type = Intrusive.
			Synchronization level parameter."
		DEFVAL { level1 }
		::= { recfLgmPortEntry 9 }

recfLgmPortOosTimer 	OBJECT-TYPE
		SYNTAX	INTEGER (1..300)
		ACCESS 	read-write
		STATUS  mandatory
		DESCRIPTION "Parameter Type = Non-intrusive.
			In units of seconds. The Out-Of-Service
			state is entered if this time is
			exceeded."
		DEFVAL { 16 }
		::= { recfLgmPortEntry 10 }

recfLgmPortPartitionID 	OBJECT-TYPE
		SYNTAX	INTEGER (1..1023)
		ACCESS	read-write
		STATUS  mandatory
		DESCRIPTION "Parameter Type = Intrusive.
			Used by security server to enforce
			       		shared node."
		::= { recfLgmPortEntry 11 }

recfLgmPortBitMode 	OBJECT-TYPE
		SYNTAX  INTEGER {
			b7Bit(1),
			b8Bit(2)
			}
		ACCESS  read-write
		STATUS  mandatory
		DESCRIPTION "Parameter Type = Intrusive.
			Defines the bit mode of this
			port."
		DEFVAL { b8Bit }
		::= { recfLgmPortEntry 12 }

recfLgmPortInbandSuperrate 	OBJECT-TYPE
		SYNTAX	INTEGER {
			nack(1),
			forceActive(2),
			pass(3)
			}
		ACCESS  read-write
		STATUS  mandatory
		DESCRIPTION "Parameter Type = Non-intrusive.
			Specifies how the signaling function
			transport for inband superrate is
			handled.
			<nack> - reject a channel connection
			 with a NO BANDWIDTH response,
			 so an alternative LINK path
			 may be found.
			<forceActive> - sets all the functions
			 active.
			<pass> - passes the functions the way
			 they are set (slower than
			 LINK)."
		DEFVAL { forceActive }
		::= { recfLgmPortEntry 13 }

recfLgmPortInbandSubrate 	OBJECT-TYPE
		SYNTAX	INTEGER {
			nack(1),
			pass(3)
			}
		ACCESS  read-write
		STATUS  mandatory
		DESCRIPTION "Parameter Type = Non-intrusive.
			Specifies how the signaling function
			transport for inband subrate is
			handled.
			<nack> - reject a channel connection
			 with a NO BANDWIDTH response,
			 so an alternative LINK path
			 may be found.
			<pass> - passes the functions the way
			 they are set (slower than
			 LINK)."
		DEFVAL { pass }
		::= { recfLgmPortEntry 14 }

recfLgmPortOutbandSuperrate 	OBJECT-TYPE
		SYNTAX	INTEGER {
			nack(1),
			forceActive(2),
			pass(3)
			}
		ACCESS  read-write
		STATUS  mandatory
		DESCRIPTION "Parameter Type = Non-intrusive.
			Specifies how the signaling function
			transport for outband superrate is
			handled.
			<nack> - reject a channel connection
			 with a NO BANDWIDTH response,
			 so an alternative LINK path
			 may be found.
			<forceActive> - sets all the functions
			 active.
			<pass> - passes the functions the way
			 they are set (slower than
			 LINK)."
		DEFVAL { forceActive }
		::= { recfLgmPortEntry 15 }

recfLgmPortOutbandSubrate 	OBJECT-TYPE
		SYNTAX	INTEGER {
			nack(1),
			pass(3)
			}
		ACCESS  read-write
		STATUS  mandatory
		DESCRIPTION "Parameter Type = Non-intrusive.
			Specifies how the signaling function
			transport for outband subrate is
			handled.
			<nack> - reject a channel connection
			 with a NO BANDWIDTH response,
			 so an alternative LINK path
			 may be found.
			<pass> - passes the functions the way
			 they are set (slower than
			 LINK)."
		DEFVAL { pass }
		::= { recfLgmPortEntry 16 }


-- DSM Port Configuration

recfDsmPort 	OBJECT IDENTIFIER ::= { reConfig 15 }

-- DSM Inter DSM Communication Port (IDCP) Configuration

recfDsmIDCPortTable 	OBJECT-TYPE
		SYNTAX  SEQUENCE OF RecfDsmIDCPortEntry
		ACCESS  not-accessible
		STATUS  mandatory
		DESCRIPTION "This section of the MIB is not
			changeable. It is included so that the
			user can verify the existance of PVC
			port.

			The user can configure frame
			relay channels on these ports by
			using the recfFrChannelEntry
			section of the MIB."
		::= { recfDsmPort 1 }

recfDsmIDCPortEntry 	OBJECT-TYPE
		SYNTAX  RecfDsmIDCPortEntry
		ACCESS  not-accessible
		STATUS  mandatory
		DESCRIPTION "INTRODUCED 2.0.0"
		INDEX { recfDsmIDCPortAddr }
		::= { recfDsmIDCPortTable 1 }

RecfDsmIDCPortEntry             ::= SEQUENCE {
			recfDsmIDCPortAddr
				PortAddr
			}

recfDsmIDCPortAddr 	OBJECT-TYPE
		SYNTAX  PortAddr
		ACCESS  read-only
		STATUS  mandatory
		DESCRIPTION "Parameter Type = Internal.
			Port address format is nest.slot.65."
		::= { recfDsmIDCPortEntry 1 }


-- DSM D-Channel Port

recfDsmDChPort 	OBJECT IDENTIFIER ::= { recfDsmPort 2 }

-- DSM D-Channel Port Configuration

recfDsmDChPortTable 	OBJECT-TYPE
		SYNTAX  SEQUENCE OF RecfDsmDChPortEntry
		ACCESS  not-accessible
		STATUS  mandatory
		DESCRIPTION "This MIB section is used to
			configure D-channel virtual ports.

			The user can configure TDM channels on
			these ports in the recfTDMChannelEntry
			section of the MIB. These TDM channels
			can connect at a rate of 64 kbps to a
			T1M or E1M common-channel signaling
			bundle."
		::= { recfDsmDChPort 1 }

recfDsmDChPortEntry 	OBJECT-TYPE
		SYNTAX  RecfDsmDChPortEntry
		ACCESS  not-accessible
		STATUS  mandatory
		DESCRIPTION "INTRODUCED 2.0.0"
		INDEX { recfDsmDChPortAddr }
		::= { recfDsmDChPortTable 1 }

RecfDsmDChPortEntry           	::= SEQUENCE {
			recfDsmDChPortAddr
				PortAddr,
			recfDsmDChPortStartMode
				INTEGER,
			recfDsmDChPortUpdate
				INTEGER,
			recfDsmDChPortPartitionID
				INTEGER,
			recfDsmDChPortPbxProtocol
				INTEGER,
			recfDsmDChPortPbxLayer3Type
				INTEGER,
			recfDsmDChPortPbxLayer2Type
				INTEGER,
			recfDsmDChPortSharedZeroFlag
				INTEGER,
			recfDsmDChPortEncodingType
				INTEGER,
			recfDsmDChPortActiveLev1CDRMode
				INTEGER,
			recfDsmDChPortRecordLev1CDRMode
				INTEGER,
			recfDsmDChPortActiveLev2CDRMode
				INTEGER,
			recfDsmDChPortRecordLev2CDRMode
				INTEGER,
			recfDsmDChPortCallsPerSecond
				INTEGER
			}

recfDsmDChPortAddr 	OBJECT-TYPE
		SYNTAX  PortAddr
		ACCESS  read-only
		STATUS  mandatory
		DESCRIPTION "Parameter Type = Internal.
			Port address format is type.group.port.
			The server type is 131."
		::= { recfDsmDChPortEntry 1 }

recfDsmDChPortStartMode 	OBJECT-TYPE
		SYNTAX  INTEGER {
			automatic(1),
			off(2),
			erase(3)
			}
		ACCESS  read-write
		STATUS  mandatory
		DESCRIPTION "Parameter Type = Intrusive.
			If set to off, then the D-channel
			cannot be connected.

			In order to set to erase, the D-channel
			must be disconnected."
		DEFVAL { off }
		::= { recfDsmDChPortEntry 2 }

recfDsmDChPortUpdate 	OBJECT-TYPE
		SYNTAX  INTEGER {
			loaded(1),
			updateReq(2),
			resetReq(3)
			}
		ACCESS  read-only
		STATUS  mandatory
		DESCRIPTION "Parameter Type = Internal.
			If set to resetReq, then the user must
			reset the port (which involves
			disconnecting and reconnecting the
			D-channel) in order for the parameter
			changes to take effect.

			If set to updateReq, then the user can
			update the port without affecting the
			D-channel connection in order for the
			parameter changes to take effect."
		DEFVAL { resetReq }
		::= { recfDsmDChPortEntry 3 }

recfDsmDChPortPartitionID 	OBJECT-TYPE
		SYNTAX  INTEGER (1..1023)
		ACCESS  read-write
		STATUS  mandatory
		DESCRIPTION "Parameter Type = Intrusive.
			Used for security on shared nodes. The
			default value is the partition ID of
			the node."
		::= { recfDsmDChPortEntry 4 }

recfDsmDChPortPbxProtocol 	OBJECT-TYPE
		SYNTAX  INTEGER {
			dpnss(1),
			qsig(2)
			}
		ACCESS  read-write
		STATUS  mandatory
		DESCRIPTION "Parameter Type = Intrusive.
			Protocol used by the PBX using this
			D-channel. If the protocol type does
			not match the PBX protocol, then the
			port will not be able to come up."
		DEFVAL { dpnss }
		::= { recfDsmDChPortEntry 5 }

recfDsmDChPortPbxLayer3Type 	OBJECT-TYPE
		SYNTAX  INTEGER {
			master(1),
			slave(2)
			}
		ACCESS  read-write
		STATUS  mandatory
		DESCRIPTION "Parameter Type = Intrusive.
			This parameter indicates whether the
			PBX or the DSM will be responsible for
			serving B-channels requests (layer 3
			master or slave mode). If set to master
			DSM controls the assignment of
			B-channels. Otherwise the PBX controls
			it.

			To function properly, the DSM and PBX
			should be configured as different
			types."
		DEFVAL { master }
		::= { recfDsmDChPortEntry 6 }

recfDsmDChPortPbxLayer2Type 	OBJECT-TYPE
		SYNTAX  INTEGER {
			master(1),
			slave(2)
			}
		ACCESS  read-write
		STATUS  mandatory
		DESCRIPTION "Parameter Type = Intrusive.
			This parameter is independent of layer 3
			master or slave mode. To function
			properly, the DSM and PBX should be
			configured as different types."
		DEFVAL { master }
		::= { recfDsmDChPortEntry 7 }

recfDsmDChPortSharedZeroFlag 	OBJECT-TYPE
		SYNTAX    INTEGER {
			yes(1),
			no(2)
			}
		ACCESS    read-write
		STATUS    mandatory
		DESCRIPTION "Parameter Type = Intrusive.
			Indicates whether the zero bit of a
			frame's end flag can be combined with
			the zero bit of the next frame's start
			flag."
		DEFVAL { yes }
		::= { recfDsmDChPortEntry 8 }

recfDsmDChPortEncodingType 	OBJECT-TYPE
		SYNTAX  INTEGER {
			nrz(1),
			nrzb(2),
			nrzi-space(4),
			nrzi-mark(3)
			}
		ACCESS  read-write
		STATUS  mandatory
		DESCRIPTION "Parameter Type = Intrusive."
		DEFVAL { nrz }
		::= { recfDsmDChPortEntry 9 }

recfDsmDChPortActiveLev1CDRMode 	OBJECT-TYPE
		SYNTAX  INTEGER {
			enable(1),
			disable(2)
			}
		ACCESS  read-write
		STATUS  mandatory
		DESCRIPTION "Parameter Type = Non-intrusive.
			Specifies whether level 1 Call Detail
			Records for the calls in progress are to
			be collected for this D-channel.

			Changing this parameter will not
			disrupt any port operations."
		DEFVAL { enable }
		::= { recfDsmDChPortEntry 10 }

recfDsmDChPortRecordLev1CDRMode 	OBJECT-TYPE
		SYNTAX  INTEGER {
			enable(1),
			disable(2)
			}
		ACCESS  read-write
		STATUS  mandatory
		DESCRIPTION "Parameter Type = Non-intrusive.
			Specifies whether level 1 Call Detail
			Records for the completed calls are to
			be collected for this D-channel.

			Changing this parameter will not
			disrupt any port operations."
		DEFVAL { enable }
		::= { recfDsmDChPortEntry 11 }

recfDsmDChPortActiveLev2CDRMode 	OBJECT-TYPE
		SYNTAX  INTEGER {
			enable(1),
			disable(2)
			}
		ACCESS  read-write
		STATUS  mandatory
		DESCRIPTION "Parameter Type = Non-intrusive.
			Specifies whether level 2 Call Detail
			Records for the calls in progress are to
			be collected for this D-channel.

			Changing this parameter will not
			disrupt any port operations."
		DEFVAL { enable }
		::= { recfDsmDChPortEntry 12 }

recfDsmDChPortRecordLev2CDRMode 	OBJECT-TYPE
		SYNTAX  INTEGER {
			enable(1),
			disable(2)
			}
		ACCESS  read-write
		STATUS  mandatory
		DESCRIPTION "Parameter Type = Non-intrusive.
			Specifies whether level 2 Call Detail
			Records for the completed calls are to
			be collected for this D-channel.

			Changing this parameter will not
			disrupt any port operations."
		DEFVAL { enable }
		::= { recfDsmDChPortEntry 13 }

recfDsmDChPortCallsPerSecond 	OBJECT-TYPE
		SYNTAX  INTEGER (1..1000)
		ACCESS  read-write
		STATUS  mandatory
		DESCRIPTION "Parameter Type = Intrusive.
			This attribute is an estimate of
			the number of calls per second (in
			units of 0.01 calls per second) on
			this D-channel port."
		DEFVAL { 1 }
		::= { recfDsmDChPortEntry 14 }


-- DSM B-Channel on D-channel Port Configuration

recfDsmDChBChTable 	OBJECT-TYPE
		SYNTAX  SEQUENCE OF RecfDsmDChBChEntry
		ACCESS  not-accessible
		STATUS  mandatory
		DESCRIPTION "This MIB section is used to
			configure information about B-channels
			that are associated with the D-channel."
		::= { recfDsmDChPort 2 }

recfDsmDChBChEntry 	OBJECT-TYPE
		SYNTAX  RecfDsmDChBChEntry
		ACCESS  not-accessible
		STATUS  mandatory
		DESCRIPTION "INTRODUCED 2.0.0"
		INDEX { recfDsmDChBChAddr,
			recfDsmDChBChBundle }
		::= { recfDsmDChBChTable 1 }

RecfDsmDChBChEntry		::= SEQUENCE {
			recfDsmDChBChAddr
				PortAddr,
			recfDsmDChBChBundle
				INTEGER,
			recfDsmDChBChDirection
				INTEGER
			}

recfDsmDChBChAddr 	OBJECT-TYPE
		SYNTAX  PortAddr
		ACCESS  read-only
		STATUS  mandatory
		DESCRIPTION "Parameter Type = Internal.
			Port address of associated D-channel
			port. The format is type.group.port.
			The server type is 131."
		::= { recfDsmDChBChEntry 1 }

recfDsmDChBChBundle 	OBJECT-TYPE
		SYNTAX  INTEGER (1..31)
		ACCESS  read-only
		STATUS  mandatory
		DESCRIPTION "Parameter Type = Internal.
			Identifies the bundle which is
			associated with this D-channel port."
		::= { recfDsmDChBChEntry 2 }

recfDsmDChBChDirection 	OBJECT-TYPE
		SYNTAX  INTEGER {
			outgoing(1),
			incoming(2),
			bidirectional(3),
			none(255)
			}
		ACCESS  read-write
		STATUS  mandatory
		DESCRIPTION "Parameter Type = Non-intrusive.
			Specifies the direction of the calls
			on this B-channel.

			The values are:
			  - outgoing: allows calls originating
			      on PBX to ST
			  - incoming: allows calls originating
			      on ST to PBX
			  - bidirectional: allows calls in any
				   direction
			  - none: this B-channel is not allowed
			  for use.

			Changes to this field will be reflected
			in recfDsmDChPortUpdate. A port update
			will be required in order for the change
			to take effect. It will not disrupt any
			channel connections associated with this
			D-channel port."
		DEFVAL { bidirectional }
		::= { recfDsmDChBChEntry 3 }


-- D-channel Exchange Codes Table

recfDsmDChExchTable 	OBJECT-TYPE
		SYNTAX  SEQUENCE OF RecfDsmDChExchEntry
		ACCESS  not-accessible
		STATUS  mandatory
		DESCRIPTION "This MIB section is used to
			assign up to 16 exchange codes
			to a D-channel."
		::= { recfDsmDChPort 3 }

recfDsmDChExchEntry 	OBJECT-TYPE
		SYNTAX  RecfDsmDChExchEntry
		ACCESS  not-accessible
		STATUS  mandatory
		DESCRIPTION "INTRODUCED 2.0.0"
		INDEX { recfDsmDChExchDChAddr,
			recfDsmDChExchIndex }
		::= { recfDsmDChExchTable 1 }

RecfDsmDChExchEntry		::= SEQUENCE {
			recfDsmDChExchDChAddr
				PortAddr,
			recfDsmDChExchIndex
				INTEGER,
			recfDsmDChExchControlMode
				INTEGER,
			recfDsmDChExchCode
				DisplayString
			}

recfDsmDChExchDChAddr 	OBJECT-TYPE
		SYNTAX  PortAddr
		ACCESS  read-only
		STATUS  mandatory
		DESCRIPTION "Parameter Type = Internal.
			D-channel port address. The format is
			type.group.port.
			The server type is 131."
		::= { recfDsmDChExchEntry 1 }

recfDsmDChExchIndex 	OBJECT-TYPE
		SYNTAX  INTEGER (1..16)
		ACCESS  read-only
		STATUS  mandatory
		DESCRIPTION "Parameter Type = Internal.
			Indexing the exchange code within this
			D-channel."
		::= { recfDsmDChExchEntry 2 }

recfDsmDChExchControlMode 	OBJECT-TYPE
		SYNTAX  INTEGER {
			enable(1),
			disable(2),
			erase(3)
			}
		ACCESS  read-write
		STATUS  mandatory
		DESCRIPTION "Parameter Type = Non-intrusive.
			Indicates whether this exchange
			code may be used to make a call.
			The value erase is used to wipe
			out the existing exchange code.

			Changes to this field will be reflected
			in recfDsmDChPortUpdate. A port update
			will be required in order for the change
			to take effect. It will not disrupt any
			channel connections associated with this
			D-channel port."
		DEFVAL { disable }
		::= { recfDsmDChExchEntry 3 }

recfDsmDChExchCode 	OBJECT-TYPE
		SYNTAX  DisplayString ( SIZE(0..16) )
		ACCESS  read-write
		STATUS  mandatory
		DESCRIPTION "Parameter Type = Non-intrusive.
			The valid characters are 0 - 9.

			Changes to this field will be reflected
			in recfDsmDChPortUpdate. A port update
			will be required in order for the change
			to take effect. It will not disrupt any
			channel connections associated with this
			D-channel port."
		DEFVAL { "" }
		::= { recfDsmDChExchEntry 4 }


-- Quality Of Service Table

recfDsmDChQOSTable 	OBJECT-TYPE
		SYNTAX    SEQUENCE OF RecfDsmDChQOSEntry
		ACCESS    not-accessible
		STATUS    mandatory
		DESCRIPTION "This MIB section specifies
			the source node quality of service
			resolution entry that is to be  used
			for the channel connection."
		::= { recfDsmDChPort 4 }

recfDsmDChQOSEntry 	OBJECT-TYPE
		SYNTAX  RecfDsmDChQOSEntry
		ACCESS    not-accessible
		STATUS    mandatory
		DESCRIPTION "INTRODUCED 2.0.0"
		INDEX { recfDsmDChQOSDChAddr,
			recfDsmDChQOSIndex }
		::= { recfDsmDChQOSTable 1 }

RecfDsmDChQOSEntry		::=  SEQUENCE {
			recfDsmDChQOSDChAddr
				PortAddr,
			recfDsmDChQOSIndex
				INTEGER,
			recfDsmDChQOSControlMode
				INTEGER,
			recfDsmDChQOSLowBChan
				INTEGER,
			recfDsmDChQOSHighBChan
				INTEGER,
			recfDsmDChQOSLowExchCode
				DisplayString,
			recfDsmDChQOSHighExchCode
				DisplayString,
			recfDsmDChQOSCallType
				INTEGER,
			recfDsmDChQOSChPrfIndex
				INTEGER,
			recfDsmDChQOSSpecialPrfIndex
				INTEGER
			}

recfDsmDChQOSDChAddr 	OBJECT-TYPE
		SYNTAX  PortAddr
		ACCESS    read-only
		STATUS    mandatory
		DESCRIPTION "Parameter Type = Internal.
			Address of D-channel, for which this
			entry is being used."
		::= { recfDsmDChQOSEntry 1 }

recfDsmDChQOSIndex 	OBJECT-TYPE
		SYNTAX  INTEGER (1..64)
		ACCESS    read-only
		STATUS    mandatory
		DESCRIPTION "Parameter Type = Internal.
			Index of the quality of service entry."
		::= { recfDsmDChQOSEntry 2 }

recfDsmDChQOSControlMode 	OBJECT-TYPE
		SYNTAX  INTEGER {
			enable(1),
			disable(2),
			erase(3)
			}
		ACCESS    read-write
		STATUS    mandatory
		DESCRIPTION "Parameter Type = Non-intrusive.
			Changes will not affect channels
			that are already connected.

			Disable will prevent this quality
			of service entry from being applied
			to the new voice connections.

			Erase will remove this quality
			of service entry from the table.

			Changes to this field will be reflected
			in recfDsmDChPortUpdate. A port update
			will be required in order for the change
			to take effect. It will not disrupt any
			channel connections associated with this
			D-channel port."
		DEFVAL { disable }
		::= { recfDsmDChQOSEntry 3 }

recfDsmDChQOSLowBChan 	OBJECT-TYPE
		SYNTAX  INTEGER (0..31)
		ACCESS    read-write
		STATUS    mandatory
		DESCRIPTION "Parameter Type = Non-intrusive.
			The low end of the source bundle range
			available for use by this D-channel.

			If this attribute is set to 0, then the
			used value is set to lowest valid
			number.

			The range is invalid if this attribute
			is set to the value greater than
			recfDsmDChQOSHighBChan.

			Changes to this field will be reflected
			in recfDsmDChPortUpdate. A port update
			will be required in order for the change
			to take effect. It will not disrupt any
			channel connections associated with this
			D-channel port."
		DEFVAL { 0 }
		::= { recfDsmDChQOSEntry 4 }

recfDsmDChQOSHighBChan 	OBJECT-TYPE
		SYNTAX  INTEGER (0..31)
		ACCESS    read-write
		STATUS    mandatory
		DESCRIPTION "Parameter Type = Non-intrusive.
			The high end of the source bundle range
			available for use by this D-channel.

			If this attribute is set to 0, then the
			used value is set to highest valid
			number.

			The range is invalid if this attribute
			is not 0 and set to the value less than
			recfDsmDChQOSLowBChan.

			Changes to this field will be reflected
			in recfDsmDChPortUpdate. A port update
			will be required in order for the change
			to take effect. It will not disrupt any
			channel connections associated with this
			D-channel port."
		DEFVAL { 0 }
		::= { recfDsmDChQOSEntry 5 }

recfDsmDChQOSLowExchCode 	OBJECT-TYPE
		SYNTAX  DisplayString ( SIZE(0..16) )
		ACCESS    read-write
		STATUS    mandatory
		DESCRIPTION "Parameter Type = Non-intrusive.
			The valid characters are 0 - 9.

			The low end of the destination exchange
			codes range. The comparison type used is
			based upon the ASCII codes for the
			character string. Thus, for example,
			'5545' is less than '555'.

			If this attribute is set to an empty
			string, then the lowest valid
			value is used.

			The range is invalid if the value of
			this attribute is greater than
			recfDsmDChQOSHighExchCode.

			Changes to this field will be reflected
			in recfDsmDChPortUpdate. A port update
			will be required in order for the change
			to take effect. It will not disrupt any
			channel connections associated with this
			D-channel port."
		DEFVAL { "" }
		::= { recfDsmDChQOSEntry 6 }

recfDsmDChQOSHighExchCode 	OBJECT-TYPE
		SYNTAX  DisplayString ( SIZE(0..16) )
		ACCESS    read-write
		STATUS    mandatory
		DESCRIPTION "Parameter Type = Non-intrusive.
			The valid characters are 0 - 9.

			The high  end of the destination
			exchange codes  range. The comparison
			type used is based upon the ASCII codes
			for the character string. Thus, for
			example, '5545' is less than '555'.

			If this attribute is set to an empty
			string, then the highest valid
			value is used.

			The range is invalid if the value of
			this attribute is not an empty string
			and less than recfDsmDChQOSLowExchCode.

			Changes to this field will be reflected
			in recfDsmDChPortUpdate. A port update
			will be required in order for the change
			to take effect. It will not disrupt any
			channel connections associated with this
			D-channel port."
		DEFVAL { "" }
		::= { recfDsmDChQOSEntry 7 }

recfDsmDChQOSCallType 	OBJECT-TYPE
		SYNTAX  INTEGER {
			voice(1),
			data(2)
			}
		ACCESS  read-write
		STATUS  mandatory
		DESCRIPTION "Parameter Type = Non-intrusive.
			This attribute specifies the call type.

			Changes to this field will be reflected
			in recfDsmDChPortUpdate. A port update
			will be required in order for the change
			to take effect. It will not disrupt any
			channel connections associated with this
			D-channel port."
		DEFVAL { voice }
		::= { recfDsmDChQOSEntry 8 }

recfDsmDChQOSChPrfIndex 	OBJECT-TYPE
		SYNTAX  INTEGER (1..255)
		ACCESS  read-write
		STATUS  mandatory
		DESCRIPTION "Parameter Type = Non-intrusive.
			This attribute specifies the channel
			profile table index that is defined in
			the channel profile MIB section on the
			source node.

			Changes to this field will be reflected
			in recfDsmDChPortUpdate. A port update
			will be required in order for the change
			to take effect. It will not disrupt any
			channel connections associated with this
			D-channel port."
		DEFVAL { 1 }
		::= { recfDsmDChQOSEntry 9 }

recfDsmDChQOSSpecialPrfIndex 	OBJECT-TYPE
		SYNTAX  INTEGER (1..255)
		ACCESS  read-write
		STATUS  mandatory
		DESCRIPTION "Parameter Type = Non-intrusive.
			This attribute specifies the special
			profile table index that is defined in
			the applicable profile MIB section on
			the source node (for example if the
			attribute recfDsmDChQOSCallType is set
			to voice, then the special profile table
			will be the scVoicePrf table).

			Changes to this field will be reflected
			in recfDsmDChPortUpdate. A port update
			will be required in order for the change
			to take effect. It will not disrupt any
			channel connections associated with this
			D-channel port."
		DEFVAL { 1 }
		::= { recfDsmDChQOSEntry 10 }



-- DSM D-channel port DPNSS protocol related configuration

recfDsmDChDPNSSTable 	OBJECT-TYPE
		SYNTAX  SEQUENCE OF RecfDsmDChDPNSSEntry
		ACCESS  not-accessible
		STATUS  mandatory
		DESCRIPTION "This MIB section is used to
			configure D-channel DPNSS protocol
			related attributes."
		::= { recfDsmDChPort 5 }

recfDsmDChDPNSSEntry 	OBJECT-TYPE
		SYNTAX  RecfDsmDChDPNSSEntry
		ACCESS  not-accessible
		STATUS  mandatory
		DESCRIPTION "INTRODUCED 2.0.0"
		INDEX { recfDsmDChDPNSSAddr }
		::= { recfDsmDChDPNSSTable 1 }

RecfDsmDChDPNSSEntry		::= SEQUENCE {
			recfDsmDChDPNSSAddr
				PortAddr,
			recfDsmDChDPNSSNL
				INTEGER,
			recfDsmDChDPNSSNT1
				INTEGER,
			recfDsmDChDPNSSNT2
				INTEGER,
			recfDsmDChDPNSSUnrecMsgIdle
				INTEGER,
			recfDsmDChDPNSSInterDgtTmr
				INTEGER
			}

recfDsmDChDPNSSAddr 	OBJECT-TYPE
		SYNTAX  PortAddr
		ACCESS  read-only
		STATUS  mandatory
		DESCRIPTION "Parameter Type = Internal.
			D-channel port address. Format
			is type.group.port.
			The server type is 131."
		::= { recfDsmDChDPNSSEntry 1 }

recfDsmDChDPNSSNL 	OBJECT-TYPE
		SYNTAX  INTEGER (1..255)
		ACCESS  read-write
		STATUS  mandatory
		DESCRIPTION "Parameter Type = Intrusive.
			The minimum number of retransmissions
			of a command frame if no acknowledge
			received.

			Changes to this field will be reflected
			in recfDsmDChPortUpdate. A port reset
			will be required in order for the change
			to take effect."
		DEFVAL { 64 }
		::= { recfDsmDChDPNSSEntry 2 }

recfDsmDChDPNSSNT1 	OBJECT-TYPE
		SYNTAX  INTEGER (1..255)
		ACCESS  read-write
		STATUS  mandatory
		DESCRIPTION "Parameter Type = Intrusive.
			Duration for which retransmission is
			done (in units of 10 milliseconds).

			Changes to this field will be reflected
			in recfDsmDChPortUpdate. A port reset
			will be required in order for the change
			to take effect."
		DEFVAL { 50 }
		::= { recfDsmDChDPNSSEntry 3 }

recfDsmDChDPNSSNT2 	OBJECT-TYPE
		SYNTAX  INTEGER (0..255)
		ACCESS  read-write
		STATUS  mandatory
		DESCRIPTION "Parameter Type = Intrusive.
			Post retransmission acknowledge delay.
			In other words, this is an additional
			time after recfDsmDChDPNSSNL
			and recfDsmDChDPNSSNT1 expiration,
			before layer 2 informs layer 3 of a
			failure (in units of 10 milliseconds).
			If the PBX and DSM connected through a
			satellite, this attribute should be set
			to 52.

			Changes to this field will be reflected
			in recfDsmDChPortUpdate. A port reset
			will be required in order for the change
			to take effect."
		DEFVAL { 0 }
		::= { recfDsmDChDPNSSEntry 4 }

recfDsmDChDPNSSUnrecMsgIdle 	OBJECT-TYPE
		SYNTAX  INTEGER (1..255)
		ACCESS  read-write
		STATUS  mandatory
		DESCRIPTION "Parameter Type = Intrusive.
			If DSM has received unrecognized local
			PBX message, this setting specifies the
			idle time whithin which there will not
			be any outgoing calls attempted (in
			units of 1 second).

			Changes to this field will be reflected
			in recfDsmDChPortUpdate. A port reset
			will be required in order for the change
			to take effect."
		DEFVAL { 4 }
		::= { recfDsmDChDPNSSEntry 5 }

recfDsmDChDPNSSInterDgtTmr 	OBJECT-TYPE
		SYNTAX  INTEGER (1..255)
		ACCESS  read-write
		STATUS  mandatory
		DESCRIPTION "Parameter Type = Intrusive.
			Specifies the maximum time between
			PBX service request messages used to set
			up a call (in units of 1 second). If
			this time is exceeded call is cleared.

			Changes to this field will be reflected
			in recfDsmDChPortUpdate. A port reset
			will be required in order for the change
			to take effect."
		DEFVAL { 5 }
		::= { recfDsmDChDPNSSEntry 6 }


-- DSM D-channel port Q.Sig protocol related configuration

recfDsmDChQSigTable 	OBJECT-TYPE
		SYNTAX  SEQUENCE OF RecfDsmDChQSigEntry
		ACCESS  not-accessible
		STATUS  mandatory
		DESCRIPTION "This MIB section is used to
			configure D-channel QSig protocol
			related attributes."
		::= { recfDsmDChPort 6 }

recfDsmDChQSigEntry 	OBJECT-TYPE
		SYNTAX  RecfDsmDChQSigEntry
		ACCESS  not-accessible
		STATUS  mandatory
		DESCRIPTION "INTRODUCED 2.0.0"
		INDEX { recfDsmDChQSigAddr }
		::= { recfDsmDChQSigTable 1 }

RecfDsmDChQSigEntry		::= SEQUENCE {
			recfDsmDChQSigAddr
				PortAddr,
			recfDsmDChQSigK
				INTEGER,
			recfDsmDChQSigN200
				INTEGER,
			recfDsmDChQSigT200
				INTEGER,
			recfDsmDChQSigT203
				INTEGER,
			recfDsmDChQSigT302
				INTEGER,
			recfDsmDChQSigT303
				INTEGER,
			recfDsmDChQSigT304
				INTEGER,
			recfDsmDChQSigT305
				INTEGER,
			recfDsmDChQSigT308
				INTEGER,
			recfDsmDChQSigT309
				INTEGER,
			recfDsmDChQSigT314
				INTEGER,
			recfDsmDChQSigT316
				INTEGER,
			recfDsmDChQSigT322
				INTEGER
			}

recfDsmDChQSigAddr 	OBJECT-TYPE
		SYNTAX  PortAddr
		ACCESS  read-only
		STATUS  mandatory
		DESCRIPTION "Parameter Type = Internal.
			D-channel port address. Format
			is type.group.port.
			The server type is 131."
		::= { recfDsmDChQSigEntry 1 }

recfDsmDChQSigK 	OBJECT-TYPE
		SYNTAX  INTEGER (1..127)
		ACCESS  read-write
		STATUS  mandatory
		DESCRIPTION "Parameter Type = Intrusive.
			Maximum number of outstanding
			(unacknowledged) I-frames.

			Changes to this field will be reflected
			in recfDsmDChPortUpdate. A port reset
			will be required in order for the change
			to take effect."
		DEFVAL { 7 }
		::= { recfDsmDChQSigEntry 2 }

recfDsmDChQSigN200 	OBJECT-TYPE
		SYNTAX  INTEGER (1..255)
		ACCESS  read-write
		STATUS  mandatory
		DESCRIPTION "Parameter Type = Intrusive.
			Maximum number of frame retransmissions.

			Changes to this field will be reflected
			in recfDsmDChPortUpdate. A port reset
			will be required in order for the change
			to take effect."
		DEFVAL { 3 }
		::= { recfDsmDChQSigEntry 3 }

recfDsmDChQSigT200 	OBJECT-TYPE
		SYNTAX  INTEGER (1..255)
		ACCESS  read-write
		STATUS  mandatory
		DESCRIPTION "Parameter Type = Intrusive.
			Maximum time (in units of 1 second)
			before frame retransmission is
			initiated.

			Changes to this field will be reflected
			in recfDsmDChPortUpdate. A port reset
			will be required in order for the change
			to take effect."
		DEFVAL { 1 }
		::= { recfDsmDChQSigEntry 4 }

recfDsmDChQSigT203 	OBJECT-TYPE
		SYNTAX  INTEGER (1..255)
		ACCESS  read-write
		STATUS  mandatory
		DESCRIPTION "Parameter Type = Intrusive.
			Maximum time (in units of 1 second)
			allowed on layer 2 without frame
			exchange. If no frame is sent during
			this time, then layer 2 monitoring frame
			is sent.

			Changes to this field will be reflected
			in recfDsmDChPortUpdate. A port reset
			will be required in order for the change
			to take effect."
		DEFVAL { 10 }
		::= { recfDsmDChQSigEntry 5 }

recfDsmDChQSigT302 	OBJECT-TYPE
		SYNTAX  INTEGER (1..255)
		ACCESS  read-write
		STATUS  mandatory
		DESCRIPTION "Parameter Type = Intrusive.
			Maximum time between PBX service request
			messages used to set up a call (in units
			of 1 second). If this time is exceeded
			then the call is cleared.

			Changes to this field will be reflected
			in recfDsmDChPortUpdate. A port reset
			will be required in order for the change
			to take effect."
		DEFVAL { 16 }
		::= { recfDsmDChQSigEntry 6 }

recfDsmDChQSigT303 	OBJECT-TYPE
		SYNTAX  INTEGER (1..255)
		ACCESS  read-write
		STATUS  mandatory
		DESCRIPTION "Parameter Type = Intrusive.
			SETUP message maximum response time (in
			units of 1 second). If exceeded, the
			SETUP messge will be sent once more. If
			there is still no response during this
			period of time, then the call is
			cleared.

			Changes to this field will be reflected
			in recfDsmDChPortUpdate. A port reset
			will be required in order for the change
			to take effect."
		DEFVAL { 6 }
		::= { recfDsmDChQSigEntry 7 }

recfDsmDChQSigT304 	OBJECT-TYPE
		SYNTAX  INTEGER (1..255)
		ACCESS  read-write
		STATUS  mandatory
		DESCRIPTION "Parameter Type = Intrusive.
			Maximum time (in units of 1 second)
			after receipt of SETUP ACK before one
			of the following messages is received:
			CALL PROCEEDING,
			ALERTING,
			CONNECT or
			DISCONNECT
			If while waiting DSM sends any message
			to PBX, the timer should be restarted.

			Changes to this field will be reflected
			in recfDsmDChPortUpdate. A port reset
			will be required in order for the change
			to take effect."
		DEFVAL { 30 }
		::= { recfDsmDChQSigEntry 8 }

recfDsmDChQSigT305 	OBJECT-TYPE
		SYNTAX  INTEGER (1..255)
		ACCESS  read-write
		STATUS  mandatory
		DESCRIPTION "Parameter Type = Intrusive.
			Maximum time (in units of 1 second) for
			DISCONNECT message response.

			Changes to this field will be reflected
			in recfDsmDChPortUpdate. A port reset
			will be required in order for the change
			to take effect."
		DEFVAL { 30 }
		::= { recfDsmDChQSigEntry 9 }

recfDsmDChQSigT308 	OBJECT-TYPE
		SYNTAX  INTEGER (1..255)
		ACCESS  read-write
		STATUS  mandatory
		DESCRIPTION "Parameter Type = Intrusive.
			Maximum time (in units of 1 second) for
			RELEASE message response.

			Changes to this field will be reflected
			in recfDsmDChPortUpdate. A port reset
			will be required in order for the change
			to take effect."
		DEFVAL { 6 }
		::= { recfDsmDChQSigEntry 10 }

recfDsmDChQSigT309 	OBJECT-TYPE
		SYNTAX  INTEGER (1..255)
		ACCESS  read-write
		STATUS  mandatory
		DESCRIPTION "Parameter Type = Intrusive.
			Maximum time (in units of 1 second)
			allowed to restore connection
			upon detection of a failure. If
			expired, both the connection and
			call are cleared.

			Changes to this field will be reflected
			in recfDsmDChPortUpdate. A port reset
			will be required in order for the change
			to take effect."
		DEFVAL { 90 }
		::= { recfDsmDChQSigEntry 11 }

recfDsmDChQSigT314 	OBJECT-TYPE
		SYNTAX  INTEGER (1..255)
		ACCESS  read-write
		STATUS  mandatory
		DESCRIPTION "Parameter Type = Intrusive.
			Maximum time (in units of 1 second)
			allowed to receive all of the segments
			of a message. This parameter applies
			only to segmented messages.

			Changes to this field will be reflected
			in recfDsmDChPortUpdate. A port reset
			will be required in order for the change
			to take effect."
		DEFVAL { 6 }
		::= { recfDsmDChQSigEntry 12 }

recfDsmDChQSigT316 	OBJECT-TYPE
		SYNTAX  INTEGER (1..255)
		ACCESS  read-write
		STATUS  mandatory
		DESCRIPTION "Parameter Type = Intrusive.
			Maximum time (in units of 1 second) for
			RESTART message response.

			Changes to this field will be reflected
			in recfDsmDChPortUpdate. A port reset
			will be required in order for the change
			to take effect."
		DEFVAL { 20 }
		::= { recfDsmDChQSigEntry 13 }

recfDsmDChQSigT322 	OBJECT-TYPE
		SYNTAX  INTEGER (1..255)
		ACCESS  read-write
		STATUS  mandatory
		DESCRIPTION "Parameter Type = Intrusive.
			Maximum time (in units of 1 second) for
			STATUS INQUIRY message.

			Changes to this field will be reflected
			in recfDsmDChPortUpdate. A port reset
			will be required in order for the change
			to take effect."
		DEFVAL { 6 }
		::= { recfDsmDChQSigEntry 14 }


-- ST Translation MIB section

recfTranslation 	OBJECT IDENTIFIER ::= { reConfig 16 }

-- LGM Translation table

recfLink2TraTable 	OBJECT-TYPE
		SYNTAX	SEQUENCE OF RecfLink2TraEntry
		ACCESS	not-accessible
		STATUS	mandatory
		DESCRIPTION " "
		::= { recfTranslation 1 }

recfLink2TraEntry 	OBJECT-TYPE
		SYNTAX	RecfLink2TraEntry
		ACCESS 	not-accessible
		STATUS	mandatory
		DESCRIPTION "INTRODUCED 2.0.0"
		INDEX { recfLink2TraIndex }
		::= { recfLink2TraTable  1 }

RecfLink2TraEntry      		::= SEQUENCE 	{
			recfLink2TraIndex
		  		Link2Index,
 			recfLink2TraStartMode
	 			INTEGER,
 			recfLink2TraStAddr
	 			ChannelAddr,
 			recfLink2TraL2Addr
	 			Link2Addr,
			recfLink2TraFunctions
				INTEGER,
			recfLink2TraPartition
				INTEGER
			 	}

recfLink2TraIndex 	OBJECT-TYPE
		SYNTAX	Link2Index
		ACCESS  read-only
		STATUS	mandatory
		DESCRIPTION "Parameter Type = Internal.
			Translation table index, notated in
			Link-2 specific notation. Does not
			indicate any particular addresses,
			however must be set to the same value
			on both, Link-2 and ST-50 nodes. It
			is a link logical entity pointing to
			the translation table entry containing
			both, Link-2 and ST-50 physical
			addresses."
		::= { recfLink2TraEntry 1 }

recfLink2TraStartMode 	OBJECT-TYPE
		SYNTAX	INTEGER {
			automatic(1),
			off(2),
			erase(3)
			}
		ACCESS  read-write
		STATUS  mandatory
		DESCRIPTION "Parameter Type = Immediate.
			Setting to off will prevent this
			table entry from being used on
			connection (invalidates it).
			Setting to erase will free the entry."
		DEFVAL { off }
		::= { recfLink2TraEntry 2 }

recfLink2TraStAddr 	OBJECT-TYPE
		SYNTAX	ChannelAddr
		ACCESS	read-only
		STATUS 	mandatory
		DESCRIPTION "Parameter Type = Immediate.
			Represents local ST-50 TDM channel
			Link2 channel (defined by
			recfLink2TraL2Addr attribute) is
			connected to. Used by ST-50 as a
			connection end point address."
		::= { recfLink2TraEntry 3 }

recfLink2TraL2Addr 	OBJECT-TYPE
		SYNTAX	Link2Addr
		ACCESS	read-write
		STATUS	mandatory
		DESCRIPTION "Parameter Type = Immediate.
			Represents Link2 address in Link2
			network ST-50 TDM channel (defined
			by recfLink2TraStAddr attribute) is
			connected to. If this attribute has
			[:xch] part not equal zero, then
			it represents X50 subrate address,
			otherwise it is a regular address."
		::= { recfLink2TraEntry 4 }

recfLink2TraFunctions 	OBJECT-TYPE
		SYNTAX	INTEGER {
			none(1),
			inBand(2),
			outBand(3)
			}
		ACCESS  read-write
		STATUS  mandatory
		DESCRIPTION "Parameter Type = Immediate.
			Selects the mode of functions
			exchange. In inBand mode the
			same time slot as data is being
			used. In outBand it is a separate
			channel."
		DEFVAL { none }
		::= { recfLink2TraEntry 5 }

recfLink2TraPartition 	OBJECT-TYPE
		SYNTAX	INTEGER (1..1023)
		ACCESS	read-only
		STATUS	mandatory
		DESCRIPTION "Parameter Type = Internal.
			Displays the partition assigned to this
			translation table entry. This partition
			is inherited from the TDM channel
			associated with this entry."
		::= { recfLink2TraEntry 6 }


-- Hardware Resource Configuration MIB

recfHwRsc 	OBJECT IDENTIFIER ::= { reConfig 17 }

recfHwRscEngineTable 	OBJECT-TYPE
		SYNTAX  SEQUENCE OF RecfHwRscEngineEntry
		ACCESS  not-accessible
		STATUS  mandatory
		DESCRIPTION "This MIB section is used for
			    configuration of on-board engines on a
			    module in an ST node.
			    
			    The engine configuration will be set up
			    with default values when the module is
			    configured in the recfSlotTable MIB. It
			    will be erased when the module is erased
			    from the recfSlotTable MIB."
		::= { recfHwRsc 1 }

recfHwRscEngineEntry 	OBJECT-TYPE
		SYNTAX  RecfHwRscEngineEntry
		ACCESS  not-accessible
		STATUS  mandatory
		DESCRIPTION "INTRODUCED 2.0.1"
		INDEX { recfHwRscEngineModuleAddr,
			recfHwRscEngineID }
		::= { recfHwRscEngineTable 1 }

RecfHwRscEngineEntry		::= SEQUENCE {
			recfHwRscEngineModuleAddr
			    SlotAddr,
			recfHwRscEngineID
			    INTEGER,
			recfHwRscEngineStartMode
			    INTEGER,
			recfHwRscEngineUpdate
			    INTEGER,
			recfHwRscEngineApplication
			    INTEGER,
			recfHwRscEnginePartitionID
			    INTEGER
			}

recfHwRscEngineModuleAddr 	OBJECT-TYPE
		SYNTAX  SlotAddr
		ACCESS  read-only
		STATUS  mandatory
		DESCRIPTION "The address of the module that
			    this engine is located on. Format is
			    <nest>.<slot>."
		::= { recfHwRscEngineEntry 1 }

recfHwRscEngineID 	OBJECT-TYPE
		SYNTAX  INTEGER (1..16)
		ACCESS  read-only
		STATUS  mandatory
		DESCRIPTION "The engine ID on the module."
		::= { recfHwRscEngineEntry 2 }

recfHwRscEngineStartMode 	OBJECT-TYPE
		SYNTAX  INTEGER {
			    automatic(1),
			    offline(2)
			}
		ACCESS  read-write
		STATUS  mandatory
		DESCRIPTION "Parameter Type = Intrusive.
			    Controls whether the engine should start as
			    inserted or removed when the module comes
			    up. If the value is set to automatic, then
			    the engine will start as inserted.
			    Otherwise, it will start as removed."
		DEFVAL { automatic }
		::= { recfHwRscEngineEntry 3 }

recfHwRscEngineUpdate 	OBJECT-TYPE
		SYNTAX  INTEGER {
			    loaded(1),
			    resetRequired(3)
			}
		ACCESS  read-only
		STATUS  mandatory
		DESCRIPTION "Indicates if the current settings
			    in the engine configuration MIB represent
			    the active settings on the module or not.

			    If this value is resetRequired, then an
			    engine reset command is required for the
			    current configuration to take effect. This
			    is done by setting the MIB attribute
			    restHwRscEngineDiagnostics to reset."
		DEFVAL { resetRequired }
		::= { recfHwRscEngineEntry 4 }

recfHwRscEngineApplication 	OBJECT-TYPE
		SYNTAX  INTEGER {
			    x50(1),
			    celp-atc(2),
			    adpcm(3),
			    link(4),
			    any(255)
			}
		ACCESS  read-write
		STATUS  mandatory
		DESCRIPTION "Parameter Type = Intrusive.
			    Used to reserve an engine for a specific
			    application type. If no application type
			    reservation is desired, then the value any
			    should be used.

			    If the application type specified is not
			    supported for the module that the engine is
			    located on, then the engine will not be
			    able to be used for any applications. In
			    this event, the module will generate an
			    engine failure alarm to indicate a bad
			    configuration."
		DEFVAL { any }
		::= { recfHwRscEngineEntry 5 }

recfHwRscEnginePartitionID 	OBJECT-TYPE
		SYNTAX  INTEGER (1..1023)
		ACCESS  read-write
		STATUS  mandatory
		DESCRIPTION "Parameter Type = Intrusive."
		::= { recfHwRscEngineEntry 6 }


-- Resource Status MIB

-- Node Status MIB

restNode 	OBJECT IDENTIFIER ::=    { reStatus 1 }

restNodeEntry 	OBJECT IDENTIFIER ::= { restNode 1 }

restNodeDiagnostics 	OBJECT-TYPE
		SYNTAX    INTEGER {
                                   updateNest(7),
                                   updateClockTable(10),
                                   selectClock1(21),
                                   selectClock2(22),
                                   selectClock3(23),
                                   selectClock4(24),
                                   selectClock5(25),
                                   selectClock6(26),
                                   selectClock7(27),
                                   selectClock8(28),
	                           -- test generator
                                   enableTestGenLocal(11),
                                   enableTestGenRemote(12),
                                   disableTestGen(13),
	                           -- alarm relay
                                   turnOnMajorAlarmRly(17),
                                   turnOffMajorAlarmRly(18),
                                   turnOnMinorAlarmRly(108),
                                   turnOffMinorAlarmRly(109),
				   clearNcpBgDiagResults(122),
				   clearNcpStartupDiagResults(123)
                                 }
		ACCESS    write-only
		STATUS    mandatory
		DESCRIPTION "updateNest will update the node with the
			new nest number. If the new nest number is
			greater than the old number, then the new nests
			will be added, and any modules in those nests
			will be able to start running. If the new nest
			number is less than the old nest number, then
			the old nests  and any modules in them will be
			removed.

			updateClockTable will update the clock fallback
			list. This will not affect the currently
			running clock, but will take affect when the
			current clock fails.

			The selectClock commands will force the
			specified clock to go active. It does not load
			the MIB configuration settings, but instead
			uses the current clock fallback list."
		::= { restNodeEntry 1 }

restNodeStatus 	OBJECT-TYPE
		--if MA not ready, return 1
		SYNTAX    INTEGER {
                                   initializing(49),
                                   online(48),
                                   fail(43)
                                   }
		ACCESS    read-only
		STATUS    mandatory
		DESCRIPTION " "		
		::= { restNodeEntry 2 }

restNodeCondition 	OBJECT-TYPE
		SYNTAX    INTEGER {
                                   normal(57),
                                   exception(52)
                                   }
		ACCESS    read-only
		STATUS    mandatory
		DESCRIPTION " "
		::= { restNodeEntry 3 }

restNodeSWRevision 	OBJECT-TYPE
		SYNTAX    DisplayString (SIZE (8))
		ACCESS    read-only
		STATUS    mandatory
		DESCRIPTION "Version number of the NCP software that
			is currently running."
		::= { restNodeEntry 4 }

restNodeMIBRevision 	OBJECT-TYPE
		SYNTAX    DisplayString (SIZE (8))
		ACCESS    read-only
		STATUS    mandatory
		DESCRIPTION "Version number of the MIB schema that the
			NCP is currently using."
		::= { restNodeEntry 5 }

restNodeUpTime 	OBJECT-TYPE
		SYNTAX    INTEGER
		ACCESS    read-only
		STATUS    mandatory
		DESCRIPTION " "
		::= { restNodeEntry 6 }


restNodeErrorMinutes 	OBJECT-TYPE
		SYNTAX    INTEGER (0..1440)
		ACCESS    read-only
		STATUS    mandatory
		DESCRIPTION "Count of the error minutes in the bus
			for the past 24 hours."
		::=  { restNodeEntry 7 }

restNodeNumOfNest 	OBJECT-TYPE
		SYNTAX    INTEGER (1..4)
		ACCESS    read-only
		STATUS    mandatory
		DESCRIPTION " "
		::=  { restNodeEntry 8 }

restNodePktBandBWAvail 	OBJECT-TYPE
		SYNTAX    INTEGER
		ACCESS    read-only
		STATUS    mandatory
		DESCRIPTION " "
		::=  { restNodeEntry 9 }

restNodePktBandBWMax 	OBJECT-TYPE
		SYNTAX    INTEGER
		ACCESS    read-only
		STATUS    mandatory
		DESCRIPTION " "
		::=  { restNodeEntry 10 }

-- Clock Status

restNodeMasterClockPriority 	OBJECT-TYPE
		SYNTAX    INTEGER {
                                   master1(1),
                                   master2(2),
                                   master3(3),
                                   master4(4),
                                   master5(5),
                                   master6(6),
                                   master7(7),
                                   master8(8),
                                   master9(9),
                                   master10(10),
                                   master11(11),
                                   master12(12),
                                   master13(13),
                                   master14(14),
                                   master15(15),
                                   master16(16),
                                   slave(17)
                                   }
		ACCESS    read-only
		STATUS    mandatory
		DESCRIPTION " "
		::=  { restNodeEntry 11 }

restNodeMasterClockMsg 	OBJECT-TYPE
		SYNTAX    INTEGER {
                                   asertingMasterMode(1),
                                   defaultInternal(2),
                                   unavailable(3)
                                   }
		ACCESS    read-only
		STATUS    mandatory
		DESCRIPTION " "
		::=  { restNodeEntry 12 }

restNodeClockTableIndex 	OBJECT-TYPE
		SYNTAX    INTEGER (0..8)
		ACCESS    read-only
		STATUS    mandatory
		DESCRIPTION "Indicates which clock in the clock
			fallback table is in use. If the clock status
			is slave holdover, then this field may return
			zero."
		::=  { restNodeEntry 13 }

restNodeClockStatus 	OBJECT-TYPE
		SYNTAX    INTEGER {
                                   locked(3),
                                   lockedStable(4),
                                   locking(5),
                                   relocking(9),
                                   slaveHoldover(15),
                                   waitInternal(11),
                                   hardwareCheck(14),
				   startup(16),
				   defaultIntOsc(17)
                                   }
		ACCESS    read-only
		STATUS    mandatory
		DESCRIPTION " "
		::=  { restNodeEntry 14 }

restNodeClockSubStatus 	OBJECT-TYPE
		SYNTAX    INTEGER {
                                   checkQualifier(1),
                                   delayFallback(2),
                                   preQualifyClock(6),
                                   qualifyInvalid(7),
                                   qualifyValid(8),
                                   requalifying(10),
                                   waitInvalid(12),
                                   waitQualify(13),
				   notApplicable(255)
                                   }
		ACCESS    read-only
		STATUS    mandatory
		DESCRIPTION "These are the substates associated with
			slaveHoldover state. If the clock status is
			not slaveHoldover, then notApplicable will be
			returned."
		::=  { restNodeEntry 15 }

restNodeClockSourceType 	OBJECT-TYPE
		SYNTAX    INTEGER {
                                   internal(1),
                                   station1(2),
                                   station2(3),
                                   portRxInd(4),
                                   portRxDep(5),
                                   portTx(6),
				   notApplicable(255)
                                   }
		ACCESS    read-only
		STATUS    mandatory
		DESCRIPTION "Type of the clock currently in use. If
			the clock status is slave holdover, then this
			field may return not applicable."
		::=  { restNodeEntry 16 }

restNodeClockSourcePort 	OBJECT-TYPE
		SYNTAX    PortAddr
		ACCESS    read-only
		STATUS    mandatory
		DESCRIPTION "Source port address of the clock
			currently in use, if the clock type is
			portRxInd, portRxDep, or portTx. If the
			clock type is a different value, then
			this field will be zero."
		::=  { restNodeEntry 17 }

restNodeClockSourcePriority 	OBJECT-TYPE
		SYNTAX    INTEGER (0..8)
		ACCESS    read-only
		STATUS    mandatory
		DESCRIPTION "Priority of the clock currently in use.
			If the clock status is slave holdover, then
			this field may return zero."
		::=  { restNodeEntry 18 }

restNodeClockSourceQuality 	OBJECT-TYPE
		SYNTAX    INTEGER {
                                   high(1),
                                   low(2),
			   notApplicable(255)
                                   }
		ACCESS    read-only
		STATUS    mandatory
		DESCRIPTION "Quality of the clock currently in use.
			If the clock status is slave holdover, then
			this field may return not applicable."
		::=  { restNodeEntry 19 }

restNodeClockQualifierStatus 	OBJECT-TYPE
		SYNTAX    INTEGER {
                                   good(57),
                                   error(58)
                                   }
		ACCESS    read-only
		STATUS    mandatory
		DESCRIPTION " "
		::=  { restNodeEntry 20 }
			
restNodeTestGenStatus 	OBJECT-TYPE
		SYNTAX    INTEGER {
                                   idle(36),
                                   good(57),
                                   error(58)
                                   }
		ACCESS    read-only
		STATUS    mandatory
		DESCRIPTION "Current status of the test generator for
			TDM nDS0 channels."
		::=  { restNodeEntry 21 }

restNodeTestGenType 	OBJECT-TYPE
		SYNTAX   INTEGER {
			   none(1),
			   local(2),
			   remote(3)
                                  }
		ACCESS   read-only
		STATUS   mandatory
		DESCRIPTION "Current type of the test generator for
			TDM nDS0 channels."
		::=  { restNodeEntry 22 }

restNodeTestGenTDMChannel 	OBJECT-TYPE
		SYNTAX    ChannelAddr
		ACCESS    read-write
		STATUS    mandatory
		DESCRIPTION "Current channel address that the TDM test
			generator is being used on."
		::=  { restNodeEntry 23 }

restNodeAlarmRelayStatus 	OBJECT-TYPE
		SYNTAX   INTEGER  {
                                  enabled(1),
                                  disabled(2)
                                  }
		ACCESS   read-only
		STATUS   mandatory
		DESCRIPTION "Indicates whether the alarm relay port
			is programmed to be used or not."
		::= { restNodeEntry 24 }

restNodeAlarmRelaySubStatus 	OBJECT-TYPE
		SYNTAX   INTEGER  {
                                  onOn(48),
                                  onOff(106),
                                  offOn(40),
                                  offOff(107)
                                   }
		ACCESS   read-only
		STATUS   mandatory
		DESCRIPTION "Indicates the status of the major alarm
		 	relay (first value) and the minor alarm relay
			(second value). This field is only valid if
			the alarm relay is enabled."
		::= { restNodeEntry 25 }

restNodeCpiStatus 	OBJECT-TYPE
		SYNTAX   INTEGER  {
                                  idle(1),
                                  inSession(2)
                                  }
		ACCESS   read-only
		STATUS   mandatory
		DESCRIPTION "Indicates the current status of the
			CPI port."
		::= { restNodeEntry 26 }

restNodeModemStatus 	OBJECT-TYPE
		SYNTAX   INTEGER  {
                                  idle(1),
                                  inCpsSession(2),
                                  inEmsSession(3)
                                  }
		ACCESS   read-only
		STATUS   mandatory
		DESCRIPTION "Indicates the current status of the
			modem port."
		::= { restNodeEntry 27 }

restNodeSoftloadStatus 	OBJECT-TYPE
		SYNTAX  INTEGER {
			    idle(36),

			    -- softloading is in progress
			    softloading(66),
			    copyToStandbyNcp(124),
			    copyToModule(128),
			    copyToOnline(131),

			    -- softload completed without error
			    success(65),

			    -- softload completed with error
			    notMatchModuleType(45),
			    unknownModuleType(80),
			    outOfFlash(81),
			    flashWriteError(82),
			    crcError(83),
			    comError(84),
			    invalidNodeID(85),
			    fileNameNotExist(67),
			    cannotComWithServer(101),
			    invalidIPaddress(102),
			    invalidFileNameExt(103),
			    cannotComWithStandby(104),
			    standbyCrcError(105),
			    maxSessionsInProgress(126),
			    loadingInProgress(127),
			    destSlotBusy(129),
			    invalidDestSlot(130),
			    miscFailure(43)
			}
		ACCESS  read-only
		STATUS  mandatory
		DESCRIPTION "Indicates the softload status.

			    'Idle' means that no softload has been run
			    yet since the node went online.

			    'Softloading' indicates that a download is
			    underway from an SNMS, CPS, or another
			    node.

			    'Copy to standby NCP' means that a file is
			    being transferred from the active NCP to
			    the standby NCP.

			    'Copy to module' means that a file that is
			    not stored on the NCP is being transferred
			    to the module that is responsible for
			    storing the file (for example, with AD-10
			    code, the file will be copied to the SGM/AG
			    module that the AD-10 is connected to).

			    'Copy to online' means that a file is being
			    transferred from the flash recovery area to
			    its proper location in flash.

			    'Success' indicates that a download
			    completed with no errors.

			    The remaining values are used to indicate
			    the different errors that can occur during
			    a softload."
		::= { restNodeEntry 28 }

restNodeSoftloadTotal 	OBJECT-TYPE
		SYNTAX   INTEGER
		ACCESS   read-only
		STATUS   mandatory
		DESCRIPTION "Total number of bytes to be softloaded.
			If no softloading is in progress, then this
			value is zero."
		::= { restNodeEntry 29 }

restNodeSoftloadSize 	OBJECT-TYPE
		SYNTAX   INTEGER
		ACCESS   read-only
		STATUS   mandatory
		DESCRIPTION "Number of bytes that have been
			softloaded. Divide this by the value of
			restNodeSoftloadTotal to determine the
			completion percentage. If no softloading
			is in progress, then this value is zero."
		::= { restNodeEntry 30 }

restNodeSoftloadSoftwareType 	OBJECT-TYPE
		SYNTAX   INTEGER {
				ncp(1),
				t1m(5),
				e1m(6),
				sgm(7),
				lgm(8),
				asm(9),
				fsm(11),
				sdm(12),
				rtm(14),
				dsm(19),
				e3m(20),
				ad10(128),
				tableOC(254),
				mibSchema(252),
				stDatabase(255),
				ad10Database(251),
				rtmAdDatabase(253),
				notApplicable(256)
			      }	
		ACCESS   read-only
		STATUS   mandatory
		DESCRIPTION "Indicates type of software being
			   transferred if a softload is in progress.
			   notApplicable will be returned if no
			   softload is in progress."
		::= { restNodeEntry 31 }

restNodeUploadStatus 	OBJECT-TYPE
		SYNTAX   OCTET STRING ( SIZE(8) )
		ACCESS   read-only
		STATUS   mandatory
		DESCRIPTION "Each upload client, which is used to upload
		    files to SNMS or to other nodes, is represented by
		    one octet. There are a maximum of eight upload
		    clients per ST node. The possible values for a
		    single octet (that is, a single upload client) are
		    the following:
			idle(36) - no upload has occurred
			uploading(68) - upload is in progress
			success(65) - upload completed successfully
			noResource(106) - upload failure reason
			transmitFailure(107) - upload failure reason
			receiveFailure(108) - upload failure reason
			failure(43) - miscellaneous failure"
		::= { restNodeEntry 32 }

restNodeUploadTotal 	OBJECT-TYPE
		SYNTAX   OCTET STRING ( SIZE(32) )
		ACCESS   read-only
		STATUS   mandatory
		DESCRIPTION "Total number of bytes to be uploaded to
			ech of up to eight clients. Each client uses
			four bytes for its value. If no uploading is
			in progress, then the value for that client
			will be zero."
		::= { restNodeEntry 33 }

restNodeUploadSize 	OBJECT-TYPE
		SYNTAX   OCTET STRING ( SIZE(32) )
		ACCESS   read-only
		STATUS   mandatory
		DESCRIPTION "Number of bytes that have been uploaded
			to each of up to eight clients. Each client
			uses four bytes for its value. Divide each
			client's value in this field by the
			corresponding value in restNodeUploadTotal to
			determine the completion percentage. If no
			uploading is in progress, then the value for
			that client will be zero."
		::= { restNodeEntry 34 }

restNodeUploadClientID 	OBJECT-TYPE
		SYNTAX   OCTET STRING ( SIZE (16) )
		ACCESS   read-only
		STATUS   mandatory
		DESCRIPTION "Specifies the node numbers of the eight
			clients that this node is serving during an
			upload. Each client is identified by two bytes.
			If the client is an EMS, then the value will be
			xFFFE."
		::= { restNodeEntry 35 }

restNodeTotalDsmCallsPerSecond 	OBJECT-TYPE
		SYNTAX	 INTEGER
		ACCESS   read-only
		STATUS   mandatory
		DESCRIPTION "This is the total amount of calls
			per second (in units of 0.01 calls per
			second) allocated for DSM in this node."
		::= { restNodeEntry 36 }


-- Nest Status MIB

restNestTable 	OBJECT-TYPE
		SYNTAX    SEQUENCE OF RestNestEntry
		ACCESS    not-accessible
		STATUS    mandatory
		DESCRIPTION "This section of the MIB does not
			support getNext."
		::=  { reStatus 2 }

restNestEntry 	OBJECT-TYPE
		SYNTAX    RestNestEntry
		ACCESS    not-accessible
		STATUS    mandatory
		DESCRIPTION " "
		INDEX { restNestAddr }
		::=  { restNestTable 1 }

RestNestEntry            ::=  SEQUENCE {
                         restNestAddr
                                   NestAddr,
                         restNestDiagnostics
                                   INTEGER,
                         restNestStatus
                                   INTEGER,
                         restNestCondition
                                   INTEGER,
                         restNestNumberOfModules
                                   INTEGER,
                         restNestPowerStatus
                                   INTEGER,
                         restNestFanStatus
                                   INTEGER,
                         restNestTemperature
                                   INTEGER,
                         restNestClockReference1
                                   INTEGER,
                         restNestClockReference2
                                   INTEGER,
                         restNestBusLoopbackStatus
                                   INTEGER,
                         restNestSlotPresence
                                   OCTET STRING,
                         restNestActiveRight
                                   INTEGER,
                         restNestActiveLeft
                                   INTEGER,
			 restNestRxmCkt1Status
				   INTEGER,
			 restNestRxmCkt2Status
				   INTEGER,
			 restNestLxmCkt1Status
				   INTEGER,
			 restNestLxmCkt2Status
				   INTEGER
                          }


restNestAddr 	OBJECT-TYPE
		SYNTAX    NestAddr
		ACCESS    read-only
		STATUS    mandatory
		DESCRIPTION " "
		::= { restNestEntry 1 }

restNestDiagnostics 	OBJECT-TYPE
		SYNTAX    INTEGER {
                                   reset(3),
                                   insert(4),
                                   remove(5),
                                   resetRightCircuit(13),
                                   resetLeftCircuit(14),
                                   toggleRightCircuit(15),
                                   toggleLeftCircuit(16),
                                   setLoopbackLxm(21),
                                   setLoopbackRxm(22),
                                   clearLoopbackLxm(23),
                                   clearLoopbackRxm(24)
                                    }
		ACCESS    write-only
		STATUS    mandatory
		DESCRIPTION "Remove will logically remove all of the
			 	modules in the nest, except the NCP, LXM, and
			RXM. This will free up the bus bandwidth. The
			configuration start mode of each module that is
			removed will be set to off.

			Insert will logically insert all of the modules
			in the nest, except the NCP, LXM, and RXM. The
			configuration MIB for each module will be
			loaded. The configuration start mode of each
			module that is inserted will be set to
			automatic.

			Reset will reset all modules in the nest except
			for the NCP, LXM, and RXM. It is equivalent to
			a remove followed by an insert, except that the
			configuration start modes in the slot MIBs are
			not changed.

			Reset right circuit will reset the RXM to
			circuit 1.

			Reset left circuit will reset the LXM to
			circuit 1.

			Toggle right circuit will toggle the circuit on
			the RXM.

			Toggle left circuit will toggle the circuit on
			the LXM.

			Set loopback LXM and set loopback RXM will
			loopback the appropriate end module in the nest.

			Clear loopback LXM and set loopback RXM will
			clear the loopback on the appropriate end
			module in the nest."
		::= { restNestEntry 2 }

restNestStatus 	OBJECT-TYPE
		SYNTAX    INTEGER {
                                   initializing(49),
                                   online(48),
                                   failed(43)
                                   }
		ACCESS    read-only
		STATUS    mandatory
		DESCRIPTION " "
		::= { restNestEntry 3 }

restNestCondition 	OBJECT-TYPE
		SYNTAX    INTEGER {
                                   normal(57),
                                   exception(52)
                                   }
		ACCESS    read-only
		STATUS    mandatory
		DESCRIPTION " "
		::= { restNestEntry 4 }

restNestNumberOfModules 	OBJECT-TYPE
		SYNTAX    INTEGER (1..17)
		ACCESS    read-only
		STATUS    mandatory
		DESCRIPTION " "
		::= { restNestEntry 5 }

restNestPowerStatus 	OBJECT-TYPE
		SYNTAX    INTEGER {
                                   good(57),
                                   fail(43)
                                   }
		ACCESS    read-only
		STATUS    mandatory
		DESCRIPTION " "
		::= { restNestEntry 6 }

restNestFanStatus 	OBJECT-TYPE
		SYNTAX    INTEGER {
                                   good(57),
                                   fail(43)
                                   }
		ACCESS    read-only
		STATUS    mandatory
		DESCRIPTION " "
		::= { restNestEntry 7 }

restNestTemperature 	OBJECT-TYPE
		SYNTAX    INTEGER {
                                     normal(1),
                                     tooHigh(2)
                                     }
		ACCESS    read-only
		STATUS    mandatory
		DESCRIPTION " "
		::= { restNestEntry 8 }

restNestClockReference1 	OBJECT-TYPE
		SYNTAX    INTEGER {
                                         enable(1),
                                         disable(2)
                                         }
		ACCESS    read-only
		STATUS    mandatory
		DESCRIPTION " "
		::= { restNestEntry 9 }

restNestClockReference2 	OBJECT-TYPE
		SYNTAX    INTEGER {
                                        enable(1),
                                        disable(2)
                                        }
		ACCESS    read-only
		STATUS    mandatory
		DESCRIPTION " "
		::= { restNestEntry 10 }

restNestBusLoopbackStatus 	OBJECT-TYPE
		SYNTAX    INTEGER {
                                   leftEnable(33),
                                   rightEnable(34),
                                   disable(2)
                                   }
		ACCESS    read-only
		STATUS    mandatory
		DESCRIPTION " "
		::= { restNestEntry 11 }

restNestSlotPresence 	OBJECT-TYPE
		SYNTAX   OCTET STRING ( SIZE(2) )
		ACCESS    read-only
		STATUS    mandatory
		DESCRIPTION "The lsb of the second octet represents
			slot 1, and the msb of the first octet
			represents slot 16. Slot 17 always has an RXM.
			Each bit set to 1 indicates that a module is
			present in that slot."
		::= { restNestEntry 12 }

restNestActiveRight 	OBJECT-TYPE
		SYNTAX    INTEGER {
                                   circuit1(1),
                                   circuit2(2),
				   noRxm(3)
                                   }
		ACCESS    read-only
		STATUS    mandatory
		DESCRIPTION "RXM status."
		::= { restNestEntry 13 }

restNestActiveLeft 	OBJECT-TYPE
		SYNTAX    INTEGER {
                                   circuit1(1),
                                   circuit2(2),
                                   noLxm(3)
                                   }
		ACCESS    read-only
		STATUS    mandatory
		DESCRIPTION "LXM status."
		::= { restNestEntry 14 }

restNestRxmCkt1Status 	OBJECT-TYPE
		SYNTAX    INTEGER {
				pass(1),
				fail(2),
				noRxm(3)
			  }
		ACCESS    read-only
		STATUS    mandatory
		DESCRIPTION " "
		::= { restNestEntry 15 }

restNestRxmCkt2Status 	OBJECT-TYPE
		SYNTAX    INTEGER {
				pass(1),
				fail(2),
				noRxm(3)
			  }
		ACCESS    read-only
		STATUS    mandatory
		DESCRIPTION " "
		::= { restNestEntry 16 }

restNestLxmCkt1Status 	OBJECT-TYPE
		SYNTAX    INTEGER {
				pass(1),
				fail(2),
				noLxm(3)
                          }
		ACCESS    read-only
		STATUS    mandatory
		DESCRIPTION " "
		::= { restNestEntry 17 }

restNestLxmCkt2Status 	OBJECT-TYPE
		SYNTAX    INTEGER {
				pass(1),
				fail(2),
				noLxm(3)
                          }
		ACCESS    read-only
		STATUS    mandatory
		DESCRIPTION " "
		::= { restNestEntry 18 }




-- Synchrony Slot Status MIB

restSlotTable 	OBJECT-TYPE
		SYNTAX    SEQUENCE OF RestSlotEntry
		ACCESS    not-accessible
		STATUS    mandatory
		DESCRIPTION " "
		::=  { reStatus 3 }

restSlotEntry 	OBJECT-TYPE
		SYNTAX    RestSlotEntry
		ACCESS    not-accessible
		STATUS    mandatory
		DESCRIPTION " "
		INDEX { restSlotAddr }
		::=  { restSlotTable 1 }

RestSlotEntry            ::=  SEQUENCE {
                         restSlotAddr
                                   SlotAddr,
                         restSlotModuleDiagnostics
                                   INTEGER,
                         restSlotModuleStatus
                                   INTEGER,
                         restSlotModuleFailureType
                                   INTEGER,
                         restSlotModuleCondition
                                   INTEGER,
                         restSlotSWModuleType
                                   INTEGER,
                         restSlotSWModuleSubType
                                   INTEGER,
                         restSlotModuleIDFormat
                                   INTEGER,
                         restSlotHWModuleType
                                   INTEGER,
                         restSlotHWModuleSubType
                                   INTEGER,
                         restSlotModuleAssemblyNum
                                   DisplayString,
                         restSlotModuleRevision
                                   DisplayString,
                         restSlotModuleSerialNum
                                   DisplayString,
                         restSlotModuleDateMade
                                   DisplayString,
                         restSlotActiveRedundantSlot
                                   SlotAddr,
                         restSlotModuleSWRevision
                                   DisplayString,
                         restSlotStartupDiagResults
                                   OCTET STRING,
                         restSlotBGDiagResults
                                   OCTET STRING,
			 restSlotNumActivePorts
				   INTEGER,
			 restSlotNumNormalPorts
				   INTEGER
                          }

restSlotAddr 	OBJECT-TYPE
		SYNTAX    SlotAddr
		ACCESS    read-only
		STATUS    mandatory
		DESCRIPTION " "
		::= { restSlotEntry 1 }

restSlotModuleDiagnostics 	OBJECT-TYPE
		SYNTAX    INTEGER {
                                   reset(3),
                                   insert(4),
                                   remove(5),
                                   update(7)
                                   }
		ACCESS    write-only
		STATUS    mandatory
		DESCRIPTION "Remove will free bus bandwidth used by
			the ports of the module, and set the module
			start mode in the configuration MIB to off.

			Insert on a removed module will get the new
			MIB and software, and set the module start
			mode in the configuration MIB to automatic.

			Reset is equivalent to a remove and insert,
			except it does not change the module start
			mode in the configuration MIB.

			Update will load the non-intrusive parameters
			from the module configuration MIB. If any
			intrusive parameters have been changed, then
			update will fail."
		::= { restSlotEntry 2 }

restSlotModuleStatus 	OBJECT-TYPE
		SYNTAX    INTEGER {
                                   active(44),
                                   standby(47),
                                   fail(43),
                                   removed(5),
                                   busDisable(53),
                                   loading(54),
				   initializing(55)
                                    }
		ACCESS    read-only
		STATUS    mandatory
		DESCRIPTION " "
		::= { restSlotEntry 3 }

restSlotModuleFailureType 	OBJECT-TYPE
		SYNTAX   INTEGER {
                                    module(1),
                                    port(2),
                                    noMib(3),
                                    errorMib(4),
                                    noRTS(5),
				    notApplicable(255)
                                    }
		ACCESS   read-only
		STATUS   mandatory
		DESCRIPTION "If module status is fail,
		   	indicates what type of failure occurred.
			notApplicable will be returned if the
			module status is not fail. noRTS means
			that the module's run-time software is
			not on the NCP flash."
		::= { restSlotEntry 4 }

restSlotModuleCondition 	OBJECT-TYPE
		SYNTAX    INTEGER {
                                   normal(57),
                                   exception(52)
                                   }
		ACCESS    read-only
		STATUS    mandatory
		DESCRIPTION " "
		::= { restSlotEntry 5 }

restSlotSWModuleType 	OBJECT-TYPE
		SYNTAX    INTEGER {
                                   ncp(1),
                                   lxm(3),
                                   rxm(4),
                                   t1m(5),
                                   e1m(6),
                                   sgm(7),
                                   lgm(8),
                                   asm(9),
                                   fsm(11),
                                   sdm(12),
                                   sgmAg(13),
                                   rtm(14),
			   dsm(19),
			   e3m(20)
			    }
		ACCESS    read-only
		STATUS    mandatory
		DESCRIPTION " "
		::= { restSlotEntry 6 }

restSlotSWModuleSubType 	OBJECT-TYPE
		SYNTAX    INTEGER (1..255)
		ACCESS    read-only
		STATUS    mandatory
		DESCRIPTION "All the subtypes are defined in
			      recfSlotModuleSubType entry."
		::= { restSlotEntry 7 }

restSlotModuleIDFormat 	OBJECT-TYPE
		SYNTAX    INTEGER
		ACCESS    read-only
		STATUS    mandatory
		DESCRIPTION " "
		::= { restSlotEntry 8 }

restSlotHWModuleType 	OBJECT-TYPE
		SYNTAX    INTEGER {
                                   ncp(1),
                                   lxm(3),
                                   rxm(4),
                                   t1m(5),
                                   e1m(6),
                                   sgm(7),
                                   lgm(8),
                                   asm(9),
                                   fsm(11),
                                   sdm(12),
                                   rtm(14),
				   dsm(19),
				   e3m(20)
			    }
		ACCESS    read-only
		STATUS    mandatory
		DESCRIPTION " "
		::= { restSlotEntry 9 }

restSlotHWModuleSubType 	OBJECT-TYPE
		SYNTAX    INTEGER (1..255)
		ACCESS    read-only
		STATUS    mandatory
		DESCRIPTION "All the subtypes are defined in
			recfSlotModuleSubType entry. "
		::= { restSlotEntry 10 }

restSlotModuleAssemblyNum 	OBJECT-TYPE
		SYNTAX    DisplayString (SIZE (16))
		ACCESS    read-only
		STATUS    mandatory
		DESCRIPTION " "
		::= { restSlotEntry 11 }

restSlotModuleRevision 	OBJECT-TYPE
		SYNTAX    DisplayString (SIZE (16))
		ACCESS    read-only
		STATUS    mandatory
		DESCRIPTION " "
		::= { restSlotEntry 12 }

restSlotModuleSerialNum 	OBJECT-TYPE
		SYNTAX    DisplayString (SIZE (16))
		ACCESS    read-only
		STATUS    mandatory
		DESCRIPTION " "
		::= { restSlotEntry 13 }

restSlotModuleDateMade 	OBJECT-TYPE
		SYNTAX    DisplayString (SIZE (8))
		ACCESS    read-only
		STATUS    mandatory
		DESCRIPTION " "
		::= { restSlotEntry 14 }

restSlotActiveRedundantSlot 	OBJECT-TYPE
		SYNTAX    SlotAddr
		ACCESS    read-only
		STATUS    mandatory
		DESCRIPTION " "
		::= { restSlotEntry 15 }

restSlotModuleSWRevision 	OBJECT-TYPE
		SYNTAX    DisplayString (SIZE (8))
		ACCESS    read-only
		STATUS    mandatory
		DESCRIPTION " "
		::= { restSlotEntry 16 }

restSlotStartupDiagResults 	OBJECT-TYPE
		SYNTAX  OCTET STRING (SIZE (4..8))
		ACCESS  read-only
		STATUS  mandatory
		DESCRIPTION "Each bit displays the result
			    (pass/fail) of a startup diagnostic. The
			    bit map for the first four bytes is defined
			    in recfSlotModuleStartDiagMask. The bit map
			    for the last four bytes is defined in
			    recfSlotModuleStartDiagMaskExt."
		::= { restSlotEntry 17 }

restSlotBGDiagResults 	OBJECT-TYPE
		SYNTAX  OCTET STRING (SIZE (4..8))
		ACCESS  read-only
		STATUS  mandatory
		DESCRIPTION "Each bit displays the result
			    (pass/fail) of a background diagnostic. The
			    bit map for the first four bytes is defined
			    in recfSlotModuleBgdDiagMask. The bit map
			    for the last four bytes is defined in
			    recfSlotModuleBgdDiagMaskExt."
		::= { restSlotEntry 18 }

restSlotNumActivePorts 	OBJECT-TYPE
		SYNTAX    INTEGER
		ACCESS    read-only
		STATUS    mandatory
		DESCRIPTION "INTRODUCED 2.0.0

			Number of ports on this module that
			have a restPortStatus value of active."
		::= { restSlotEntry 19 }

restSlotNumNormalPorts 	OBJECT-TYPE
		SYNTAX    INTEGER
		ACCESS    read-only
		STATUS    mandatory
		DESCRIPTION "INTRODUCED 2.0.0

			Number of ports on this module that
			have a restPortCondition value of normal."
		::= { restSlotEntry 20 }


-- Module Status MIB

restModule          OBJECT IDENTIFIER ::=    { reStatus 4 }

-- Ncp Module status

restNcpTable 	OBJECT-TYPE
		SYNTAX  SEQUENCE OF RestNcpEntry
		ACCESS  not-accessible
		STATUS  mandatory
		DESCRIPTION " "
		::= { restModule 1 }

restNcpEntry 	OBJECT-TYPE
		SYNTAX  RestNcpEntry
		ACCESS  not-accessible
		STATUS  mandatory
		DESCRIPTION " "
		INDEX { restNcpAddr }
		::= { restNcpTable 1 }

RestNcpEntry 	::=  SEQUENCE {
			restNcpAddr
			    SlotAddr,
			restNcpBootPromRevision
			    DisplayString,
			restNcpMacAddr
			    DisplayString,
			restNcpFlashObjectVersions
			    OCTET STRING
			}

restNcpAddr 	OBJECT-TYPE
		SYNTAX  SlotAddr
		ACCESS  read-only
		STATUS  mandatory
		DESCRIPTION " "
		::= { restNcpEntry 1 }

restNcpBootPromRevision 	OBJECT-TYPE
		SYNTAX  DisplayString (SIZE (8))
		ACCESS  read-only
		STATUS  mandatory
		DESCRIPTION " "
		::= { restNcpEntry 2 }

restNcpMacAddr 	OBJECT-TYPE
		SYNTAX  DisplayString (SIZE (17))
		ACCESS  read-only
		STATUS  mandatory
		DESCRIPTION " "
		::= { restNcpEntry 3 }

restNcpFlashObjectVersions 	OBJECT-TYPE
		SYNTAX  OCTET STRING (SIZE (0..120))
		ACCESS  read-only
		STATUS  deprecated
		DESCRIPTION "DEPRECATED 2.0.1
			    The information in this attribute has been
			    replaced by the restNcpFlashTable section
			    of the MIB.

			    For each module type whose run-time software
			    is stored in the NCP flash PROM, this
			    attribute returns the software type (2
			    bytes), CRC (2 bytes), and version number
			    (4 bytes). The values for software type
			    match the enumerations for the attribute
			    scSoftloadSoftwareType. If the flash PROM
			    of the NCP cannot currently be read (such
			    as when a softload is in progress), this
			    attribute will return eight bytes with all
			    zeros."
		::= { restNcpEntry 4 }


-- NCP Flash PROM Status Table

restNcpFlashTable 	OBJECT-TYPE
		SYNTAX  SEQUENCE OF RestNcpFlashEntry
		ACCESS  not-accessible
		STATUS  mandatory
		DESCRIPTION "This MIB section lists all of the
			    module object files stored in the flash
			    PROM of the specified NCP.

			    This section of the MIB does not support
			    getNext.

			    If the flash PROM is currently being
			    written to, then all attributes in this MIB
			    section will return an error."
		::= { restModule 2 }

restNcpFlashEntry 	OBJECT-TYPE
		SYNTAX  RestNcpFlashEntry
		ACCESS  not-accessible
		STATUS  mandatory
		DESCRIPTION "INTRODUCED 2.0.1"
		INDEX   { restNcpFlashAddr,
			  restNcpFlashIndex }
		::= { restNcpFlashTable 1 }

RestNcpFlashEntry		::= SEQUENCE {
			restNcpFlashAddr
			    SlotAddr,
			restNcpFlashIndex
			    INTEGER,
			restNcpFlashModuleType
			    INTEGER,
			restNcpFlashRecoveryIndicator
			    INTEGER,
			restNcpFlashCompressIndicator
			    INTEGER,
			restNcpFlashFileVersionNumber
			    DisplayString,
			restNcpFlashFileSize
			    INTEGER,
			restNcpFlashFileStoredCrc
			    INTEGER,
			restNcpFlashFileCrcCheck
			    INTEGER
			}

restNcpFlashAddr 	OBJECT-TYPE
		SYNTAX  SlotAddr
		ACCESS  read-only
		STATUS  mandatory
		DESCRIPTION "The address of the NCP."
		::= { restNcpFlashEntry 1 }

restNcpFlashIndex 	OBJECT-TYPE
		SYNTAX  INTEGER (1..255)
		ACCESS  read-only
		STATUS  mandatory
		DESCRIPTION "Used to differentiate the
			    different module object files in the NCP
			    flash PROM. This attribute does not contain
			    any information about the file in flash."
		::= { restNcpFlashEntry 2 }

restNcpFlashModuleType 	OBJECT-TYPE
		SYNTAX  INTEGER {
			    ncp(1),
			    t1m(5),
			    e1m(6),
			    sgm(7),
			    lgm(8),
			    asm(9),
			    fsm(11),
			    sdm(12),
			    rtm(14),
			    dsm(19),
			    e3m(20),
			    mibSchema(252),
			    tableOfContents(254)
			}
		ACCESS  read-only
		STATUS  mandatory
		DESCRIPTION "The module type of this object
			    file."
		::= { restNcpFlashEntry 3 }

restNcpFlashRecoveryIndicator 	OBJECT-TYPE
		SYNTAX  INTEGER {
			    recovery(2),
			    normal(1)
			}
		ACCESS  read-only
		STATUS  mandatory
		DESCRIPTION "Indicates whether or not this
			    object file is stored in the softload
			    recovery area."
		::= { restNcpFlashEntry 4 }

restNcpFlashCompressIndicator 	OBJECT-TYPE
		SYNTAX  INTEGER {
			    compressed(1),
			    uncompressed(2)
			}
		ACCESS  read-only
		STATUS  mandatory
		DESCRIPTION "Indicates whether or not this
			    object file is compressed or uncompressed."
		::= { restNcpFlashEntry 5 }

restNcpFlashFileVersionNumber 	OBJECT-TYPE
		SYNTAX  DisplayString (SIZE (8))
		ACCESS  read-only
		STATUS  mandatory
		DESCRIPTION "The software revision number of
			    this module object file."
		::= { restNcpFlashEntry 6 }

restNcpFlashFileSize 	OBJECT-TYPE
		SYNTAX  INTEGER (0..2048000)
		ACCESS  read-only
		STATUS  mandatory
		DESCRIPTION "The size of this module object
			    file in bytes."
		::= { restNcpFlashEntry 7 }

restNcpFlashFileStoredCrc 	OBJECT-TYPE
		SYNTAX  INTEGER (0..65535)
		ACCESS  read-only
		STATUS  mandatory
		DESCRIPTION "The stored CRC of this module
			    object file."
		::= { restNcpFlashEntry 8 }

restNcpFlashFileCrcCheck 	OBJECT-TYPE
		SYNTAX  INTEGER {
			    pass(1),
			    fail(2),
			    notApplicable(255)
			}
		ACCESS  read-only
		STATUS  mandatory
		DESCRIPTION "If pass is returned, then the file
			    image in flash passed a CRC check. If fail
			    is returned, then the CRC check failed and
			    the file is corrupted. If not applicable is
			    returned, then we do not support CRC
			    checking for this file on this NCP."
		::= { restNcpFlashEntry 9 }


-- Fsm Module status

restFsmTable 	OBJECT-TYPE
		SYNTAX    SEQUENCE OF RestFsmEntry
		ACCESS    not-accessible
		STATUS    mandatory
		DESCRIPTION " "
		::=  { restModule 6 }

restFsmEntry 	OBJECT-TYPE
		SYNTAX    RestFsmEntry
		ACCESS    not-accessible
		STATUS    mandatory
		DESCRIPTION " "
		INDEX { restFsmAddr }
		::=  { restFsmTable 1 }

RestFsmEntry 	::=  SEQUENCE {
		restFsmAddr
			SlotAddr,
		restFsmBypassBandwidth
			INTEGER,
		restFsmSourceBandwidth
			INTEGER,
		restFsmBandwidthAvail
			INTEGER,
		restFsmPortSpeedAvail
			INTEGER,
		restFsmDlciTotal
			INTEGER,
		restFsmDlciAvail
			INTEGER,
		restFsmDlciConfig
			INTEGER,
		restFsmBypChanTotal
			INTEGER,
		restFsmBypChanAvail
			INTEGER,
		restFsmCirTotal
			INTEGER,
		restFsmCirAvail
			INTEGER,
		restFsmVciCtrlBlkTotal
			INTEGER,
		restFsmVciCtrlBlkAvail
			INTEGER,
		restFsmTotalBuffers
			INTEGER,
		restFsmBuffersAvail
			INTEGER,
		restFsmCcfSupportIndicator
			INTEGER
		}

restFsmAddr 	OBJECT-TYPE
		SYNTAX    SlotAddr
		ACCESS    read-only
		STATUS    mandatory
		DESCRIPTION " "
		::= { restFsmEntry 1 }

restFsmBypassBandwidth 	OBJECT-TYPE
		SYNTAX    INTEGER
		ACCESS    read-only
		STATUS    mandatory
		DESCRIPTION "Maximum available bypass capability
			in units of packets. Bypass capability is
			also limited by restFsmBandwidthAvail."
		::= { restFsmEntry 2 }


restFsmSourceBandwidth 	OBJECT-TYPE
		SYNTAX    INTEGER
		ACCESS    read-only
		STATUS    mandatory
		DESCRIPTION "Maximum available termination capability
			in units of packets. Termination capability
			also limited by restFsmBandwidthAvail."
		::= { restFsmEntry 3 }

restFsmBandwidthAvail 	OBJECT-TYPE
		SYNTAX    INTEGER
		ACCESS    read-only
		STATUS    mandatory
		DESCRIPTION "FSM available processing capability to
			serve new termination or bypass channel, in
			units of packets. This may be less than the
			sum of restFsmBypassBandwidth and
			restFsmSourceBandwidth."
		::= { restFsmEntry 4 }

restFsmPortSpeedAvail 	OBJECT-TYPE
		SYNTAX    INTEGER
		ACCESS    read-only
		STATUS    mandatory
		DESCRIPTION "FSM available port speed capability
			in units of bps. This only indicates the
			capability to support termination
			channels."
		::= { restFsmEntry 5 }

restFsmDlciTotal 	OBJECT-TYPE
		SYNTAX  INTEGER
		ACCESS  read-only
		STATUS  mandatory
		DESCRIPTION "Total number of DLCIs permitted on this
			FSM module."
		::= { restFsmEntry 6 }

restFsmDlciAvail 	OBJECT-TYPE
		SYNTAX  INTEGER
		ACCESS  read-only
		STATUS  mandatory
		DESCRIPTION "Number of DLCIs that can still be
			connected on this FSM module. The number of
			DLCIs that are connected on the module can be
			determined by subtracting this value from
			restFsmDlciTotal."
		::= { restFsmEntry 7 }

restFsmDlciConfig 	OBJECT-TYPE
		SYNTAX  INTEGER
		ACCESS  read-only
		STATUS  mandatory
		DESCRIPTION "Number of DLCIs that are configured on
			frame relay ports allocated to this FSM module.
			A new FSM port cannot be allocated on this
			module if the number of DLCIs configured on the
			port plus this value exceeds the value of
			restFsmDlciTotal.

			For FSM ports which are currently allocated,
			new DLCIs which are configured will increment
			this value. In this case, this value will be
			allowed to exceed restFsmDlciTotal so that
			existing channel connections will not be
			disrupted. However, the new DLCIs cannot be
			connected when restFsmDlciAvail is zero."
		::= { restFsmEntry 8 }

restFsmBypChanTotal 	OBJECT-TYPE
		SYNTAX  INTEGER
		ACCESS  read-only
		STATUS  mandatory
		DESCRIPTION "Total number of bypass channels permitted
			on this FSM module."
		::= { restFsmEntry 9 }

restFsmBypChanAvail 	OBJECT-TYPE
		SYNTAX  INTEGER
		ACCESS  read-only
		STATUS  mandatory
		DESCRIPTION "Number of bypass channels that can still
			be connected on this FSM module. The number of
			bypass channels that are connected on the module
			can be determined by subtracting this value from
			restFsmBypChanTotal."
		::= { restFsmEntry 10 }

restFsmCirTotal 	OBJECT-TYPE
		SYNTAX  INTEGER
		ACCESS  read-only
		STATUS  mandatory
		DESCRIPTION "Total CIR on FSM module."
		::= { restFsmEntry 11 }

restFsmCirAvail 	OBJECT-TYPE
		SYNTAX  INTEGER
		ACCESS  read-only
		STATUS  mandatory
		DESCRIPTION "Available (unused) CIR on FSM module."
		::= { restFsmEntry 12 }

restFsmVciCtrlBlkTotal 	OBJECT-TYPE
		SYNTAX  INTEGER
		ACCESS  read-only
		STATUS  mandatory
		DESCRIPTION "Total number of Vci Control Blocks
			allowed on FSM module. Each DLCI terminated on
			the module requires one Vci Control Block.
			Each bypass channel on the module requires
			two Vci Control Blocks."
		::= { restFsmEntry 13 }

restFsmVciCtrlBlkAvail 	OBJECT-TYPE
		SYNTAX  INTEGER
		ACCESS  read-only
		STATUS  mandatory
		DESCRIPTION "Number of available (unused) PVCs
		 	on FSM module. Each DLCI terminated on
			the module requires one Vci Control Block.
			Each bypass channel on the module requires two
			Vci Control Blocks."
		::= { restFsmEntry 14 }

restFsmTotalBuffers 	OBJECT-TYPE
		SYNTAX  INTEGER
		ACCESS  read-only
		STATUS  mandatory
		DESCRIPTION "Total number of channel buffers on FSM
			 	module."
		::= { restFsmEntry 15 }

restFsmBuffersAvail 	OBJECT-TYPE
		SYNTAX  INTEGER
		ACCESS  read-only
		STATUS  mandatory
		DESCRIPTION "Number of available (unused) channel
			 	buffers on FSM module."
		::= { restFsmEntry 16 }

restFsmCcfSupportIndicator 	OBJECT-TYPE
		SYNTAX  INTEGER {
			supported(1),
			notSupported(2)
			}
		ACCESS  read-only
		STATUS  mandatory
		DESCRIPTION "INTRODUCED 2.1.0
			Indicates whether or not this
			module is capable of supporting CCFs."
		::= { restFsmEntry 17 }


-- SGM/AG Module Specific MIB

restSgmAgTable 	OBJECT-TYPE
		SYNTAX    SEQUENCE OF RestSgmAgEntry
		ACCESS    not-accessible
		STATUS    mandatory
		DESCRIPTION " "
		::= {  restModule 7 }

restSgmAgEntry 	OBJECT-TYPE
		SYNTAX    RestSgmAgEntry
		ACCESS    not-accessible
		STATUS    mandatory
		DESCRIPTION " "
		INDEX { restSgmAgAddr }
		::= { restSgmAgTable 1 }

RestSgmAgEntry 	::=  SEQUENCE {
		restSgmAgAddr
			SlotAddr,
		restSgmAgmPortAvail
			INTEGER,
		restSgmAgmPortTotal
			INTEGER,
		restSgmAgSafAvail
			INTEGER,
		restSgmAgSafTotal
			INTEGER,
		restSgmAgSgmScfAvail
			INTEGER,
		restSgmAgSgmScfTotal
			INTEGER,
		restSgmAgAgmScfAvail
			INTEGER,
		restSgmAgAgmScfTotal
			INTEGER,
		restSgmAgAgmCcfAvail
			INTEGER,
		restSgmAgAgmCcfTotal
			INTEGER,
		restSgmAgAgmPortCapacity
			OCTET STRING
		}

restSgmAgAddr 	OBJECT-TYPE
		SYNTAX  SlotAddr
		ACCESS  read-only
		STATUS  mandatory
		DESCRIPTION " "
		::= { restSgmAgEntry 1 }

restSgmAgmPortAvail 	OBJECT-TYPE
		SYNTAX  INTEGER
		ACCESS  read-only
		STATUS  mandatory
		DESCRIPTION "Number of AGM ports that are available for
			use on this SGM/AG module."
		::= { restSgmAgEntry 2 }

restSgmAgmPortTotal 	OBJECT-TYPE
		SYNTAX  INTEGER
		ACCESS  read-only
		STATUS  mandatory
		DESCRIPTION "Total number of AGM ports that are on this
			SGM/AG module."
		::= { restSgmAgEntry 3 }

restSgmAgSafAvail 	OBJECT-TYPE
		SYNTAX  INTEGER
		ACCESS  read-only
		STATUS  mandatory
		DESCRIPTION "Number of SAF ports that are available for
			use on this SGM/AG module."
		::= { restSgmAgEntry 4 }

restSgmAgSafTotal 	OBJECT-TYPE
		SYNTAX  INTEGER
		ACCESS  read-only
		STATUS  mandatory
		DESCRIPTION "Total number of SAF ports that are on this
			SGM/AG module."
		::= { restSgmAgEntry 5 }

restSgmAgSgmScfAvail 	OBJECT-TYPE
		SYNTAX  INTEGER
		ACCESS  read-only
		STATUS  mandatory
		DESCRIPTION "Number of SGM SCF ports that are available
			for use on this SGM/AG module. If the software
			type of the module is AGM, then zero shall be
			returned."
		::= { restSgmAgEntry 6 }

restSgmAgSgmScfTotal 	OBJECT-TYPE
		SYNTAX  INTEGER
		ACCESS  read-only
		STATUS  mandatory
		DESCRIPTION "Total number of SGM SCF ports that are on
			this SGM/AG module. If the software type of the
			module is AGM, then zero shall be returned."
		::= { restSgmAgEntry 7 }

restSgmAgAgmScfAvail 	OBJECT-TYPE
		SYNTAX  INTEGER
		ACCESS  read-only
		STATUS  mandatory
		DESCRIPTION "Number of AGM SCF ports that are available
			for use on this SGM/AG module. This value is
			valid for both SGM and AGM module software
			types."
		::= { restSgmAgEntry 8 }

restSgmAgAgmScfTotal 	OBJECT-TYPE
		SYNTAX  INTEGER
		ACCESS  read-only
		STATUS  mandatory
		DESCRIPTION "Total number of AGM SCF ports that are on
			this SGM/AG module. This value is valid for both
			SGM and AGM module software types."
		::= { restSgmAgEntry 9 }

restSgmAgAgmCcfAvail 	OBJECT-TYPE
		SYNTAX  INTEGER
		ACCESS  read-only
		STATUS  mandatory
		DESCRIPTION "INTRODUCED 2.1.0
			Number of AGM CCF ports that are available
			for use on this SGM/AG module. This value is
			valid for both SGM and AGM module software
			types."
		::= { restSgmAgEntry 10 }

restSgmAgAgmCcfTotal 	OBJECT-TYPE
		SYNTAX  INTEGER
		ACCESS  read-only
		STATUS  mandatory
		DESCRIPTION "INTRODUCED 2.1.0
			Total number of AGM CCF ports that are on
			this SGM/AG module. This value is valid for both
			SGM and AGM module software types."
		::= { restSgmAgEntry 11 }


restSgmAgAgmPortCapacity 	OBJECT-TYPE
		SYNTAX  OCTET STRING ( SIZE(0..16))
		ACCESS  read-only
		STATUS  mandatory
		DESCRIPTION "INTRODUCED 2.1.0
			List of AGM port speeds that are supported
			by this SGM/AG module.
			
			Every 4 bytes indicates one speed.

			The following speeds are supported:
				19200 bps, 
				56000 bps,
				64000 bps, 
				128000 bps"
		::= { restSgmAgEntry 12 }



-- ASM Specific Status MIB

restAsm 	OBJECT IDENTIFIER ::= { restModule 8 }

-- ASM Module Status MIB

restAsmModuleTable 	OBJECT-TYPE
		SYNTAX    SEQUENCE OF RestAsmModuleEntry
		ACCESS    not-accessible
		STATUS    mandatory
		DESCRIPTION " "
		::= { restAsm 1 }

restAsmModuleEntry 	OBJECT-TYPE
		SYNTAX    RestAsmModuleEntry
		ACCESS    not-accessible
		STATUS    mandatory
		DESCRIPTION " "
		INDEX { restAsmModuleAddr }
		::= { restAsmModuleTable 1 }


RestAsmModuleEntry       	::= SEQUENCE 	{
			restAsmModuleAddr
				SlotAddr,
			restAsmModuleMaxCelp
				INTEGER,
			restAsmModuleNumCelpAvail
				INTEGER,
			restAsmModuleTotalEngines
				INTEGER,
			restAsmModuleAvailEngines
				INTEGER,
			restAsmModuleTotalSafScfs
				INTEGER,
			restAsmModuleAvailSafScfs
				INTEGER
			}

restAsmModuleAddr 	OBJECT-TYPE
		SYNTAX    SlotAddr
		ACCESS    read-only
		STATUS    mandatory
		DESCRIPTION " "
		::= { restAsmModuleEntry 1 }

restAsmModuleMaxCelp 	OBJECT-TYPE
		SYNTAX    INTEGER (0..16)
		ACCESS    read-only
		STATUS    deprecated
		DESCRIPTION "Indicates the number of CELP
			licenses on the module."
		::= { restAsmModuleEntry 2 }

restAsmModuleNumCelpAvail 	OBJECT-TYPE
		SYNTAX    INTEGER (0..16)
		ACCESS    read-only
		STATUS    deprecated
		DESCRIPTION "Indicates the number of CELP
			licenses on the module
			that are not in use."
		::= { restAsmModuleEntry 3 }

restAsmModuleTotalEngines 	OBJECT-TYPE
		SYNTAX    INTEGER (0..16)
		ACCESS    read-only
		STATUS    mandatory
		DESCRIPTION "Indicates the total number of DSP
			engines on the module."
		::= { restAsmModuleEntry 4 }

restAsmModuleAvailEngines 	OBJECT-TYPE
		SYNTAX    INTEGER (0..16)
		ACCESS    read-only
		STATUS    mandatory
		DESCRIPTION "Indicates the currently available
			(unused) number of DSP engines on the
			module."
		::= { restAsmModuleEntry 5 }

restAsmModuleTotalSafScfs 	OBJECT-TYPE
		SYNTAX    INTEGER (0..448)
		ACCESS    read-only
		STATUS    mandatory
		DESCRIPTION "Indicates the total number of SAFs
			and SCFs that can be allocated on this
			ASM module."
		::= { restAsmModuleEntry 6 }

restAsmModuleAvailSafScfs 	OBJECT-TYPE
		SYNTAX    INTEGER (0..448)
		ACCESS    read-only
		STATUS    mandatory
		DESCRIPTION "Indicates the currently available
			(unused) number of SAFs and SCFs on
			this ASM module."
		::= { restAsmModuleEntry 7 }


-- ASM Engine Status MIB

restAsmEngineTable 	OBJECT-TYPE
		SYNTAX 	SEQUENCE OF RestAsmEngineEntry
		ACCESS	not-accessible
		STATUS  deprecated
		DESCRIPTION "This section of the MIB
			     doesn't support getNext"
		::= { restAsm 2 }

restAsmEngineEntry 	OBJECT-TYPE
		SYNTAX	RestAsmEngineEntry
		ACCESS  not-accessible
		STATUS  deprecated
		DESCRIPTION " "
		INDEX	{ restAsmEngineModuleAddr,
			  restAsmEngineID }
		::= { restAsmEngineTable 1 }

RestAsmEngineEntry		::= SEQUENCE {
		     restAsmEngineModuleAddr
			SlotAddr,
		     restAsmEngineID
			INTEGER,
		     restAsmEngineDiagnostics
			INTEGER,
		     restAsmEngineStatus
			INTEGER,
	             restAsmEngineNumPorts
			INTEGER,
		     restAsmEngineNumSAFs
			INTEGER,
		     restAsmEngineNumSCFs
			INTEGER,
		     restAsmEngineApplication
			INTEGER
		     }

restAsmEngineModuleAddr 	OBJECT-TYPE
		SYNTAX	SlotAddr
		ACCESS	read-only
		STATUS  deprecated
		DESCRIPTION "Physical address of the ASM
			     module"
		::= { restAsmEngineEntry 1 }

restAsmEngineID 	OBJECT-TYPE
		SYNTAX	INTEGER (1..16)
		ACCESS	read-only
		STATUS  deprecated
		DESCRIPTION "The engine ID on ASM module"
		::= { restAsmEngineEntry 2 }

restAsmEngineDiagnostics 	OBJECT-TYPE
		SYNTAX  INTEGER {
			insert(4),
			remove(5),
			reset(6)
			}
		ACCESS  not-accessible
		STATUS  deprecated
		DESCRIPTION "Not used yet"
		::= { restAsmEngineEntry 3 }

restAsmEngineStatus 	OBJECT-TYPE
		SYNTAX 	INTEGER {
			x50(1),
			celp(2),
			adpcm(3),
			free(4),
			removed(5),
			normal(6),
			failed(43)
			}
		ACCESS  read-only
		STATUS  deprecated
		DESCRIPTION "These applications cannot be
			on the same engine at the same time"
		::= { restAsmEngineEntry 4 }


restAsmEngineNumPorts 	OBJECT-TYPE
		SYNTAX  INTEGER (0..4)
		ACCESS  read-only
		STATUS  deprecated
		DESCRIPTION "Number of application ports"
		::= { restAsmEngineEntry 5 }

restAsmEngineNumSAFs 	OBJECT-TYPE
		SYNTAX  INTEGER (0..4)
		ACCESS  read-only
		STATUS  deprecated
		DESCRIPTION "Number of SAF ports. If
			     none returns zero"
		::= { restAsmEngineEntry 6 }

restAsmEngineNumSCFs 	OBJECT-TYPE
		SYNTAX  INTEGER (0..80)
		ACCESS  read-only
		STATUS  deprecated
		DESCRIPTION "Number of SCF ports. If
			     none returns zero"
		::= { restAsmEngineEntry 7 }

restAsmEngineApplication 	OBJECT-TYPE
		SYNTAX	INTEGER {
			x50(1),
			celp-atc(2),
			adpcm(3),
			none(255)
			}
		ACCESS	read-only
		STATUS	deprecated
		DESCRIPTION "Indicates the type of application
			allocated on this DSP engine, if any."
		::= { restAsmEngineEntry 8 }


-- ASM Module Application Status MIB

restAsmModApplTable 	OBJECT-TYPE
		SYNTAX 	SEQUENCE OF RestAsmModApplEntry
		ACCESS	not-accessible
		STATUS  mandatory
		DESCRIPTION "This section of the MIB enables the
			user to determine the availability of
			specific resource types on an ASM module
			based upon the current resource
			allocation.

			This section of the MIB doesn't support
			getNext"
		::= { restAsm 3 }

restAsmModApplEntry 	OBJECT-TYPE
		SYNTAX	RestAsmModApplEntry
		ACCESS  not-accessible
		STATUS  mandatory
		DESCRIPTION " "
		INDEX	{ restAsmModApplModuleAddr,
			  restAsmModApplType }
		::= { restAsmModApplTable 1 }

RestAsmModApplEntry		::= SEQUENCE {
			restAsmModApplModuleAddr
				SlotAddr,
			restAsmModApplType
				INTEGER,
			restAsmModApplMaxPortsAllowed
				INTEGER,
			restAsmModApplCurPortsAllowed
				INTEGER,
			restAsmModApplCurPortsAllocated
				INTEGER,
			restAsmModApplTotalLicenses
				INTEGER,
			restAsmModApplAvailLicenses
				INTEGER,
			restAsmModApplEnginesUsed
				INTEGER,
			restAsmModApplEnginesRsvd
				INTEGER
			}

restAsmModApplModuleAddr 	OBJECT-TYPE
		SYNTAX	SlotAddr
		ACCESS	read-only
		STATUS  mandatory
		DESCRIPTION "Physical address of the ASM module"
		::= { restAsmModApplEntry 1 }

restAsmModApplType 	OBJECT-TYPE
		SYNTAX	INTEGER {
			x50(1),
			celp-atc(2),
			adpcm(3)
			}
		ACCESS	read-only
		STATUS  mandatory
		DESCRIPTION "The ASM application type."
		::= { restAsmModApplEntry 2 }

restAsmModApplMaxPortsAllowed 	OBJECT-TYPE
		SYNTAX	INTEGER (0..32)
		ACCESS	read-only
		STATUS  mandatory
		DESCRIPTION "The maximum number of ports which
			can be allocated on the ASM module
			running the specified application. This
			value assumes that the module is running
			no other applications. This value is
			based on the following factors:
			(1) total number of DSP engines on the
			    module
			(2) total number of ports allowed on
			    the module
			(3) total number of application licenses
			    on the module, if the application is
			    licensed
			(4) module application type."
		::= { restAsmModApplEntry 3 }

restAsmModApplCurPortsAllowed 	OBJECT-TYPE
		SYNTAX	INTEGER (0..32)
		ACCESS	read-only
		STATUS  mandatory
		DESCRIPTION "The current number of ports which
			can be allocated on the ASM module
			running the specified application. This
			determines how many ports can still be
			allocated based on what resources are
			currently allocated on the module. It
			indicates how many more ports of this
			application can be added if all new
			allocations are ports running this
			application. The total number of ports
			that can still be allocated in a mixed
			application scenario is NOT the sum of
			all of these values for each
			application.

			The value of this value is based on the
			following factors:
			(1) number of unallocated DSP engines
			(2) available ports on DSP engines which
			    are already allocated for this
			    application type
			(3) number of ports that can still be
			    allocated on the module
			(4) licenses available, if the
			    application is licensed
			(5) module application type."
		::= { restAsmModApplEntry 4 }

restAsmModApplCurPortsAllocated 	OBJECT-TYPE
		SYNTAX	INTEGER (0..32)
		ACCESS	read-only
		STATUS  mandatory
		DESCRIPTION "The current number of ports which
			are allocated on the ASM module and are
			running the specified application."
		::= { restAsmModApplEntry 5 }

restAsmModApplEnginesUsed 	OBJECT-TYPE
		SYNTAX	INTEGER (0..16)
		ACCESS	read-only
		STATUS  mandatory
		DESCRIPTION "The total number of DSP engines on
			the ASM module that are currently
			allocated for this application type."
		::= { restAsmModApplEntry 6 }

restAsmModApplEnginesRsvd 	OBJECT-TYPE
		SYNTAX	INTEGER (0..16)
		ACCESS	read-only
		STATUS  mandatory
		DESCRIPTION "The total number of unallocated DSP
			engines on the ASM module that are
			reserved for this application type."
		::= { restAsmModApplEntry 7 }

restAsmModApplTotalLicenses 	OBJECT-TYPE
		SYNTAX	INTEGER (0..16)
		ACCESS	read-only
		STATUS  mandatory
		DESCRIPTION "The total number of licenses
			available on the ASM module for this
			application type. If the application is
			unlicensed, then a value of zero shall
			be returned."
		::= { restAsmModApplEntry 8 }

restAsmModApplAvailLicenses 	OBJECT-TYPE
		SYNTAX	INTEGER (0..16)
		ACCESS	read-only
		STATUS  mandatory
		DESCRIPTION "A count of the licenses on the ASM
			module for this application type which
			are not currently in use. If the
			application is unlicensed, then a value
			of zero shall be returned."
		::= { restAsmModApplEntry 9 }


-- RTM Specific Status

restRtm 	OBJECT IDENTIFIER ::= { restModule 9 }

-- RTM Module Specific Status

restRtmModuleTable 	OBJECT-TYPE
		SYNTAX  SEQUENCE OF RestRtmModuleEntry
		ACCESS  not-accessible
		STATUS  mandatory
		DESCRIPTION " "
		::= { restRtm 1 }

restRtmModuleEntry 	OBJECT-TYPE
		SYNTAX  RestRtmModuleEntry
		ACCESS  not-accessible
		STATUS  mandatory
		DESCRIPTION " "
		INDEX { restRtmModuleAddr }
		::= { restRtmModuleTable 1 }

RestRtmModuleEntry		::= SEQUENCE {
			restRtmModuleAddr
				SlotAddr,
			restRtmModuleDS0sUsed
				INTEGER,
			restRtmModuleDS0sAvail
				INTEGER,
			restRtmModuleSafsUsed
				INTEGER,
			restRtmModuleSafsAvail
				INTEGER
			}

restRtmModuleAddr 	OBJECT-TYPE
		SYNTAX  SlotAddr
		ACCESS  read-only
		STATUS  mandatory
		DESCRIPTION " "	
		::= { restRtmModuleEntry 1 }

restRtmModuleDS0sUsed 	OBJECT-TYPE
		SYNTAX  INTEGER (0..24)
		ACCESS  read-only
		STATUS  mandatory
		DESCRIPTION "Current number of DS0 connections
			from AD-x units on this module."
		::= { restRtmModuleEntry 2 }

restRtmModuleDS0sAvail 	OBJECT-TYPE
		SYNTAX  INTEGER (0..24)
		ACCESS  read-only
		STATUS  mandatory
		DESCRIPTION "With the current number of DS0 and
			SAF connections, this field specifies
			the number of DS0 connections that could
			still be made assuming no more SAF
			connections are made."
		::= { restRtmModuleEntry 3 }

restRtmModuleSafsUsed 	OBJECT-TYPE
		SYNTAX  INTEGER (0..30)
		ACCESS  read-only
		STATUS  mandatory
		DESCRIPTION "Current number of SAF connections
			from AD-x units on this module."
		::= { restRtmModuleEntry 4 }

restRtmModuleSafsAvail 	OBJECT-TYPE
		SYNTAX  INTEGER (0..30)
		ACCESS  read-only
		STATUS  mandatory
		DESCRIPTION "With the current number of DS0 and
			SAF connections, this field specifies
			the number of SAF connections that could
			still be made assuming no more DS0
			connections are made."
		::= { restRtmModuleEntry 5 }


-- DSM Specific Status

restDsmModule 	OBJECT IDENTIFIER ::= { restModule 10 }

-- DSM Module Specific Status

restDsmModuleTable 	OBJECT-TYPE
		SYNTAX  SEQUENCE OF RestDsmModuleEntry
		ACCESS  not-accessible
		STATUS  mandatory
		DESCRIPTION "This section of the MIB is used to
			get status of any DSM modules defined on
			the node."
		::= { restDsmModule 1 }

restDsmModuleEntry 	OBJECT-TYPE
		SYNTAX  RestDsmModuleEntry
		ACCESS  not-accessible
		STATUS  mandatory
		DESCRIPTION "INTRODUCED 2.0.0"
		INDEX { restDsmModuleAddr }
		::= { restDsmModuleTable 1 }

RestDsmModuleEntry		::= SEQUENCE {
			restDsmModuleAddr
				SlotAddr,
			restDsmModuleNumDsmComms
				INTEGER,
			restDsmModuleNumCallsProc
				INTEGER,
			restDsmModuleNumRmtRteEntries
				INTEGER,
			restDsmModuleNumRmtRteAvail
				INTEGER,
			restDsmModuleNumLocRteEntries
				INTEGER,
			restDsmModuleNumLocRteAvail
				INTEGER,
			restDsmModuleBypassPPSTotal
				INTEGER,
			restDsmModuleBypassPPSAvail
				INTEGER,
			restDsmModuleBypChanTotal
				INTEGER,
			restDsmModuleBypChanAvail
				INTEGER,
			restDsmModuleCirTotal
				INTEGER,
			restDsmModuleCirAvail
				INTEGER,
			restDsmModuleVciCtrlBlkTotal
				INTEGER,
			restDsmModuleVciCtrlBlkAvail
				INTEGER,
			restDsmModuleTotalBuffers
				INTEGER,
			restDsmModuleBuffersAvail
				INTEGER,
			restDsmModuleTotalRecCDRs
				INTEGER,
			restDsmModuleRecCDRsAvail
				INTEGER,
			restDsmModuleTotalCallsPerSec
				INTEGER,
			restDsmModuleCallsPerSecAvail
				INTEGER,
			restDsmModuleCallsPerSecFactor
				INTEGER,
			restDsmModuleBypassFactor
				INTEGER,
			restDsmModuleTotalProcessUnits
				INTEGER,
			restDsmModuleProcessUnitsAvail
				INTEGER
			}

restDsmModuleAddr 	OBJECT-TYPE
		SYNTAX  SlotAddr
		ACCESS  read-only
		STATUS  mandatory
		DESCRIPTION "Address of this DSM module.
			Format is nest.slot."
		::= { restDsmModuleEntry 1 }

restDsmModuleNumDsmComms 	OBJECT-TYPE
		SYNTAX  INTEGER
		ACCESS  read-only
		STATUS  mandatory
		DESCRIPTION "Number of DSMs that this
			DSM is able to communicate with."
		::= { restDsmModuleEntry 2 }

restDsmModuleNumCallsProc 	OBJECT-TYPE
		SYNTAX  INTEGER
		ACCESS  read-only
		STATUS  mandatory
		DESCRIPTION "Number of calls in the
			non-idle state (in the process
			of connection, connected or in the
			process of disconnection)."
		::= { restDsmModuleEntry 3 }

restDsmModuleNumRmtRteEntries 	OBJECT-TYPE
		SYNTAX  INTEGER
		ACCESS  read-only
		STATUS  mandatory
		DESCRIPTION "Total number of entries allowed in
			the remote routing table."
		::= { restDsmModuleEntry 4 }

restDsmModuleNumRmtRteAvail 	OBJECT-TYPE
		SYNTAX  INTEGER
		ACCESS  read-only
		STATUS  mandatory
		DESCRIPTION "Number of entries in the remote
			routing table that are available.
			The number of occupied entries can be
			determined by subtracting this value
			from restDsmModuleNumRmtRteEntries."
		::= { restDsmModuleEntry 5 }

restDsmModuleNumLocRteEntries 	OBJECT-TYPE
		SYNTAX  INTEGER
		ACCESS  read-only
		STATUS  mandatory
		DESCRIPTION "Total number of entries allowed in
			the local routing table."
		::= { restDsmModuleEntry 6 }

restDsmModuleNumLocRteAvail 	OBJECT-TYPE
		SYNTAX  INTEGER
		ACCESS  read-only
		STATUS  mandatory
		DESCRIPTION "Number of entries in the local
			routing table that are available.
			The number of occupied entries can be
			determined by subtracting this value
			from restDsmModuleNumLocRteEntries."
		::= { restDsmModuleEntry 7 }

restDsmModuleBypassPPSTotal 	OBJECT-TYPE
		SYNTAX  INTEGER
		ACCESS  read-only
		STATUS  mandatory
		DESCRIPTION "Total bypass throughput allowed
			 	on this DSM module in units of packets
			per second."
		::= { restDsmModuleEntry 8 }

restDsmModuleBypassPPSAvail 	OBJECT-TYPE
		SYNTAX  INTEGER
		ACCESS  read-only
		STATUS  mandatory
		DESCRIPTION "Available bypass capability in
			units of packets per second.
			The currently being used bypass
			throughput on the module can be
			determined by subtracting this value
			from restDsmModuleBypassPPSTotal."
		::= { restDsmModuleEntry 9 }

restDsmModuleBypChanTotal 	OBJECT-TYPE
		SYNTAX  INTEGER
		ACCESS  read-only
		STATUS  mandatory
		DESCRIPTION "Total number of bypass channels
			permitted on this DSM module."
		::= { restDsmModuleEntry 10 }

restDsmModuleBypChanAvail 	OBJECT-TYPE
		SYNTAX  INTEGER
		ACCESS  read-only
		STATUS  mandatory
		DESCRIPTION "Number of bypass channels that can
			still be connected on this DSM module.
			The number of bypass channels that are
			connected on the module can be
			determined by subtracting this value
			from restDsmModuleBypChanTotal."
		::= { restDsmModuleEntry 11 }

restDsmModuleCirTotal 	OBJECT-TYPE
		SYNTAX  INTEGER
		ACCESS  read-only
		STATUS  mandatory
		DESCRIPTION "Total CIR on this DSM module."
		::= { restDsmModuleEntry 12 }

restDsmModuleCirAvail 	OBJECT-TYPE
		SYNTAX  INTEGER
		ACCESS  read-only
		STATUS  mandatory
		DESCRIPTION "Available (unused) CIR on this DSM
			module.
			The currently being used CIR can be
			determined by subtracting this value
			from restDsmModuleBypChanTotal."
		::= { restDsmModuleEntry 13 }

restDsmModuleVciCtrlBlkTotal 	OBJECT-TYPE
		SYNTAX  INTEGER
		ACCESS  read-only
		STATUS  mandatory
		DESCRIPTION "Total number of Vci Control Blocks
			allowed on this DSM module. Each DLCI
			terminated on the module requires one
			Vci Control Block. Each bypass channel
			on the module requires two Vci Control
			Blocks."
		::= { restDsmModuleEntry 14 }

restDsmModuleVciCtrlBlkAvail 	OBJECT-TYPE
		SYNTAX  INTEGER
		ACCESS  read-only
		STATUS  mandatory
		DESCRIPTION "Number of available (unused) PVCs
			on this DSM module. Each DLCI terminated
			on the module requires one Vci Control
			Block. Each bypass channel on the
			module requires two Vci Control Blocks."
		::= { restDsmModuleEntry 15 }

restDsmModuleTotalBuffers 	OBJECT-TYPE
		SYNTAX  INTEGER
		ACCESS  read-only
		STATUS  mandatory
		DESCRIPTION "Total number of channel buffers
			allowed on this DSM module."
		::= { restDsmModuleEntry 16 }

restDsmModuleBuffersAvail 	OBJECT-TYPE
		SYNTAX  INTEGER
		ACCESS  read-only
		STATUS  mandatory
		DESCRIPTION "Number of available (unused)
			channel buffers on DSM module.
			The number of channel buffers that are
			currently being used on the module can
			be determined by subtracting this value
			from restDsmModuleTotalBuffers."
		::= { restDsmModuleEntry 17 }

restDsmModuleTotalRecCDRs 	OBJECT-TYPE
		SYNTAX  INTEGER
		ACCESS  read-only
		STATUS  mandatory
		DESCRIPTION "Total number of recorded CDRs
			allowed on this DSM module. This value
			is counted across all CDR logs"
		::= { restDsmModuleEntry 18 }

restDsmModuleRecCDRsAvail 	OBJECT-TYPE
		SYNTAX  INTEGER
		ACCESS  read-only
		STATUS  mandatory
		DESCRIPTION "Number of available (unused)
			CDRs on this DSM module. These CDRs may
			be assigned to any of the CDR logs
			defined on this DSM module."
		::= { restDsmModuleEntry 19 }

restDsmModuleTotalCallsPerSec 	OBJECT-TYPE
		SYNTAX	INTEGER
		ACCESS  read-only
		STATUS  mandatory
		DESCRIPTION "This is the total amount of
			calls per second (in units of
			0.01 calls per second) that can
			be handled by this DSM."
		::= { restDsmModuleEntry 20 }

restDsmModuleCallsPerSecAvail 	OBJECT-TYPE
		SYNTAX	INTEGER
		ACCESS  read-only
		STATUS  mandatory
		DESCRIPTION "This is the amount of calls
			per second (in units of 0.01 calls
			per second) that can be allocated on
			this DSM. The number of calls per
			second currently allocated to the
			module can be determined by subtracting
			this number from the value of
			restDsmModuleTotalCallsPerSec
			attribute."
		::= { restDsmModuleEntry 21 }

restDsmModuleCallsPerSecFactor 	OBJECT-TYPE
		SYNTAX	INTEGER
		ACCESS  read-only
		STATUS  mandatory
		DESCRIPTION "This is the conversion factor
			between calls per second (in units
			of 0.01 calls per second) and
			processing units.
			The equation is:
			    processing units =
			this value * calls per second."
		::= { restDsmModuleEntry 22 }

restDsmModuleBypassFactor 	OBJECT-TYPE
		SYNTAX  INTEGER
		ACCESS  read-only
		STATUS  mandatory
		DESCRIPTION "This is the conversion factor
			between bypass bandwidth (in PPS) and
			processing units.
			The equation is:
			    processing units =
			this value * bypass bandwidth."
		::= { restDsmModuleEntry 23 }

restDsmModuleTotalProcessUnits 	OBJECT-TYPE
		SYNTAX  INTEGER
		ACCESS  read-only
		STATUS  mandatory
		DESCRIPTION "This is a rating for the total
			number of D-channel calls per second
			and bypass bandwidth allowed on
			this DSM. The two quantities are
			converted to the same units
			using the values of the
			restDsmModuleCallsPerSecFactor
			and restDsmModuleBypassFactor
			attributes."
		::= { restDsmModuleEntry 24 }

restDsmModuleProcessUnitsAvail 	OBJECT-TYPE
		SYNTAX  INTEGER
		ACCESS  read-only
		STATUS  mandatory
		DESCRIPTION "This is a rating of the number of
			the number of D-channel calls per
			second and bypass bandwidth that
			is unused on this DSM. To
			determine the amount that is
			currently allocated, subtract
			this value from
			restDsmModuleTotalProcessUnits
			attribute value."
		::= { restDsmModuleEntry 25 }


-- DSM module Recorded Call Detail Record Log Status

restDsmModRecCDRLogTable 	OBJECT-TYPE
		SYNTAX  SEQUENCE OF RestDsmModRecCDRLogEntry
		ACCESS  not-accessible
		STATUS  mandatory
		DESCRIPTION "This section of the MIB specifies
			status of the Call Detail Record log
			for completed calls."
		::= { restDsmModule 2 }

restDsmModRecCDRLogEntry 	OBJECT-TYPE
		SYNTAX  RestDsmModRecCDRLogEntry
		ACCESS    not-accessible
		STATUS    mandatory
		DESCRIPTION "INTRODUCED 2.0.0"
		INDEX { restDsmModRecCDRLogAddr,
			restDsmModRecCDRLogIndex }
		::= { restDsmModRecCDRLogTable 1 }

RestDsmModRecCDRLogEntry	::=  SEQUENCE {
			restDsmModRecCDRLogAddr
				SlotAddr,
			restDsmModRecCDRLogIndex
				INTEGER,
			restDsmModRecCDRLogStatus
				INTEGER,
			restDsmModRecCDRLogLev1Entries
				INTEGER,
			restDsmModRecCDRLogLev2Entries
				INTEGER,
			restDsmModRecCDRLogClrEntries
				INTEGER
			}

restDsmModRecCDRLogAddr 	OBJECT-TYPE
		SYNTAX  SlotAddr
		ACCESS  read-only
		STATUS  mandatory
		DESCRIPTION "Address of this DSM module.
			Format is nest.slot."
		::= { restDsmModRecCDRLogEntry 1 }

restDsmModRecCDRLogIndex 	OBJECT-TYPE
		SYNTAX  INTEGER (1..32)
		ACCESS  read-only
		STATUS  mandatory
		DESCRIPTION "CDR log number on this DSM module."
		::= { restDsmModRecCDRLogEntry 2 }

restDsmModRecCDRLogStatus 	OBJECT-TYPE
		SYNTAX  INTEGER {
			    overflow(3),
			    noOverflow(4),
			    overThreshold(5),
			    disabled(2)
   			}
		ACCESS  read-only
		STATUS  mandatory
		DESCRIPTION "This CDR log overflow flag status."
		::= { restDsmModRecCDRLogEntry 3 }

restDsmModRecCDRLogLev1Entries 	OBJECT-TYPE
		SYNTAX  INTEGER
		ACCESS  read-only
		STATUS  mandatory
		DESCRIPTION "Number of level 1 CDRs for this
			CDR log."
		::= { restDsmModRecCDRLogEntry 4 }

restDsmModRecCDRLogLev2Entries 	OBJECT-TYPE
		SYNTAX  INTEGER
		ACCESS  read-only
		STATUS  mandatory
		DESCRIPTION "Number of level 2 CDRs for this
			CDR log."
		::= { restDsmModRecCDRLogEntry 5 }

restDsmModRecCDRLogClrEntries 	OBJECT-TYPE
		SYNTAX  INTEGER (1..1000)
		ACCESS  write-only
		STATUS  mandatory
		DESCRIPTION "Number of entries on this CDR log
			to be cleared, counting from the oldest
			record."
		::= { restDsmModRecCDRLogEntry 6 }


-- DSM Module Recorded Call Detail Record Status

restDsmModRecCDRTable 	OBJECT-TYPE
		SYNTAX  SEQUENCE OF RestDsmModRecCDREntry
		ACCESS  not-accessible
		STATUS  mandatory
		DESCRIPTION "This section of the MIB contains
			the status of a Call Detail Records for
			completed call."
		::= { restDsmModule 3 }

restDsmModRecCDREntry 	OBJECT-TYPE
		SYNTAX  RestDsmModRecCDREntry
		ACCESS    not-accessible
		STATUS    mandatory
		DESCRIPTION "INTRODUCED 2.0.0"
		INDEX { restDsmModRecCDRAddr,
			restDsmModRecCDRLogNum,
			restDsmModRecCDRIndex }
		::= { restDsmModRecCDRTable 1 }

RestDsmModRecCDREntry		::=  SEQUENCE {
			restDsmModRecCDRAddr
				SlotAddr,
			restDsmModRecCDRLogNum
				INTEGER,
			restDsmModRecCDRIndex
				INTEGER,
			restDsmModRecCDRContents
				OCTET STRING
			}

restDsmModRecCDRAddr 	OBJECT-TYPE
		SYNTAX  SlotAddr
		ACCESS  read-only
		STATUS  mandatory
		DESCRIPTION "Address of this DSM module.
			Format is nest.slot."
		::= { restDsmModRecCDREntry 1 }

restDsmModRecCDRLogNum 	OBJECT-TYPE
		SYNTAX  INTEGER (1..32)
		ACCESS  read-only
		STATUS  mandatory
		DESCRIPTION "Specifies the CDR log number to be
			accessed on this DSM module."
		::= { restDsmModRecCDREntry 2 }

restDsmModRecCDRIndex 	OBJECT-TYPE
		SYNTAX  INTEGER (1..1000)
		ACCESS  read-only
		STATUS  mandatory
		DESCRIPTION "Identifies the Call Detail Record
			to be accessed on this log based on
			its position (counting from the oldest
			one)."
		::= { restDsmModRecCDREntry 3 }

restDsmModRecCDRContents 	OBJECT-TYPE
		SYNTAX  OCTET STRING (SIZE (72))
		ACCESS  read-only
		STATUS  mandatory
		DESCRIPTION "Call Detail Record from a module
			CDR log. These CDRs are for completed calls.
 
			The bytes in a CDR for a completed call are
			interpretted as follows:
                                        1: CDR type, values are:
                                              level 1 (1)
                                              level 2 (2)
                                        2: version number
                                        3-4: partition ID
                                        5-6: call ID
					7: protocol type, values are:
                                              DPNSS (1)
                                              Q.Sig (2)
                                        8: unused
 
			From this position down the contents
			definition varies, depending on the
			interface level (CDR type). For Level 1
			CDRs (Physical Characteristics):
                                        9-12: originating time
                                        13-16: answer time
                                        17-20: disconnect time
                                        21-22: B-channel source node ID
                                        23: B-channel source nest ID
                                        24: B-channel source slot ID
                                        25-26: B-channel source port ID
                                        27-28: B-channel source channel ID
                                        29-30: B-channel destination node ID
                                        31: B-channel destination nest ID
                                        32: B-channel destination slot ID
                                        33-34: B-channel destination port ID
                                        35-36: B-channel destination channel ID
                                        37: call type, values are:
                                              real (3)
                                              virtual (0)
                                        38: special profile type, values 
					    defined
                                            in attribute recfDsmDChQOSCallType
                                        39: info type, values are:
                                              Q.Sig speech (0)
                                              DPNSS A-law (1)
                                              DPNSS ADPCM (2)
                                              DPNSS Mu-law (3)
                                              Unrestricted data (8)
                                              Restricted data (9)
                                              3.1 KHz audio (16)
                                              7 KHz audio (17)
                                              video (24)
                                        40: special profile index
                                        41: channel profile index
                                        42: NCP clear cause
                                          - values are defined in
                                              recfTDMChannelState
                                        43: clear cause, values are:
					    (If NCP clear cause is not zero,
                                            this byte is not used.)
					  - DPNSS values:
					      number unobtainable (0)
					      address incomplete (1)
                                              network termination (2)
					      service unavailable (3)
					      subscriber incompatible (4)
                                              congestion/collision (7)
					      busy (8)
					      subscriber out of service (9)
					      incoming calls barred (10)
					      service incompatible (19)
					      acknowledgement (20)
                                              signal not understood (21)
					      signal not valid (22)
					      service temporarily 
					      unavailable (23)
					      facility not registered (24)
					      reject (25)
                                              message not understood (26)
					      signalling system 
					      incompatible (27)
				 	      route out of service (28)
					      transferred (29)
					      network address extension 
				              error (30)
					      no free channel or channel
				                unavailable from NCP (34)
					      channel out of service (35)
					      priority forced release (36)
					      access barred (41)
					      requested channel unavailable(44)
					      DTE controlled not ready (45)
					      DTE uncontrolled not ready (46)
                                              normal call termination (48)
					      unbinding (101)
					      version invalid (103)
					      B-channel failure cause (112)
                     			      D-channel failure cause (113)
                     			      socket failure cause (114)

					- Q.Sig values: (supported in
							Release 2.0.2)
					      no cause (0)
                                              no route (3)
                                              channel unacceptable (6)
					      normal call clearing (16)
					      user busy (17)
					      no user responding (18)
					      no answer (19)
					      call rejected (21)
					      number changed (22)
					      out of order (27)
                                              T302 timer expiration or invalid
						number format (28)
					      status response (30)
					      normal unspecified (31)
                                              no free channel or channel
						unavailable from NCP (34)
                                              link reset or temporary
						failure (41)
                                              requested channel unavailable(44)
					      bearer not authorized (57)
					      bearer not available (58)
					      service not available (63)
					      bearer not implemented (65)
					      invalid call reference (81)
					      incompatible destination (88)
                                              no bearer capability or no
						address or mandatory element
						missing (96)
					      message type not implemented (97)
					      message type incompatible (98)
					      information type not
						implemented (99)
					      invalid information element
						contents (100)
                                              unbinding (101)
					      recovery on timer expiry (102)
                                              version invalid (103)
					      protocol error (111)
					      B-channel failure cause (112)
					      D-channel failure cause (113)
					      socket failure cause (114)
                                        44: number of call attempts between 
					    DSMs
                                        45-48: transmission rate
 
                                    For Level 2 CDRs (Data Link Layer):
                                        9-12: setup final time
                                        13-16: connect request time
                                        17-20: connect response time
                                        21-22: source node ID
                                        23: source nest ID
                                        24: source slot ID
                                        25-26: destination node ID
                                        27: destination nest ID
                                        28: destination slot ID
                                        29: calling number size (number of
                                            bytes, not string length) - this
                                            number is referred to from now on
                                            as x
                                        30-(29+x): calling number
                                        (30+x): called number size (number of
                                                bytes, not string length) -
                                                this number is referred to from
                                                now on as y
                                        (31+x)-(30+x+y): called number
                                        (31+x+y): routing digits
                                        (32+x+y): unused."
		::= { restDsmModRecCDREntry 4 }


-- DSM Module Exchange Code Status

restDsmModExchTable 	OBJECT-TYPE
		SYNTAX  SEQUENCE OF RestDsmModExchEntry
		ACCESS  not-accessible
		STATUS  mandatory
		DESCRIPTION "This section of the MIB returns
			the exact exchange code used by the
			specified DSM for a given call number.

			It does not support getNext."
		::= { restDsmModule 4 }

restDsmModExchEntry 	OBJECT-TYPE
		SYNTAX  RestDsmModExchEntry
		ACCESS  not-accessible
		STATUS  mandatory
		DESCRIPTION "INTRODUCED 2.0.0"
		INDEX { restDsmModExchAddr,
			restDsmModExchCallNumLen,
			restDsmModExchCallNumber,
			restDsmModExchPartition }
		::= { restDsmModExchTable 1 }

RestDsmModExchEntry		::=  SEQUENCE {
			restDsmModExchAddr
				SlotAddr,
			restDsmModExchCallNumLen
				INTEGER,
			restDsmModExchCallNumber
				DisplayString,
			restDsmModExchPartition
				INTEGER,
			restDsmModExchCode
				DisplayString
			}

restDsmModExchAddr 	OBJECT-TYPE
		SYNTAX  SlotAddr
		ACCESS  read-only
		STATUS  mandatory
		DESCRIPTION "Address of DSM module.
			Format is nest.slot."
		::= { restDsmModExchEntry 1 }

restDsmModExchCallNumLen 	OBJECT-TYPE
		SYNTAX  INTEGER (1..16)
		ACCESS  read-only
		STATUS  mandatory
		DESCRIPTION "This attribute defines the length
			of the restDsmModExchCallNumber
			attribute."
		::= { restDsmModExchEntry 2 }

restDsmModExchCallNumber 	OBJECT-TYPE
		SYNTAX  DisplayString (SIZE (1..16))
		ACCESS  read-only
		STATUS  mandatory
		DESCRIPTION "The call number.

			The valid character set is defined in
			recfDsmDChExchTable MIB section."
		::= { restDsmModExchEntry 3 }

restDsmModExchPartition 	OBJECT-TYPE
		SYNTAX  INTEGER (1..1023)
		ACCESS  read-only
		STATUS  mandatory
		DESCRIPTION "The partition id of the instance
			the user is inquiring information on.
			Partition 1 (global) should not match
			the instance partition id. It is able to
			obtain an info for any partition."
		::= { restDsmModExchEntry 4 }

restDsmModExchCode 	OBJECT-TYPE
		SYNTAX  DisplayString ( SIZE (1..16) )
		ACCESS  read-only
		STATUS  mandatory
		DESCRIPTION "The call numbers matched exchange
			code.

			If there is no matched exchange code,
			an error message will be returned.
			The valid character set is defined in
			recfDsmDChExchTable MIB section."
		::= { restDsmModExchEntry 5 }

-- DSM Module Routing Table Status

restDsmModRteTable 	OBJECT-TYPE
		SYNTAX  SEQUENCE OF RestDsmModRteEntry
		ACCESS  not-accessible
		STATUS  mandatory
		DESCRIPTION "This section of the MIB specifies
			all entries on both the local and remote
			routing tables."
		::= { restDsmModule 5 }

restDsmModRteEntry 	OBJECT-TYPE
		SYNTAX  RestDsmModRteEntry
		ACCESS  not-accessible
		STATUS  mandatory
		DESCRIPTION "INTRODUCED 2.0.0"
		INDEX { restDsmModRteAddr,
			restDsmModRteExchCodeLen,
			restDsmModRteExchCode,
			restDsmModRtePartition,
			restDsmModRteRemoteNode,
			restDsmModRteRemoteSlot,
			restDsmModRteLocalPortNumber }
		::= { restDsmModRteTable 1 }

RestDsmModRteEntry		::=  SEQUENCE {
			restDsmModRteAddr
				SlotAddr,
			restDsmModRteExchCodeLen
				INTEGER,
			restDsmModRteExchCode
				DisplayString,
			restDsmModRtePartition
				INTEGER,
			restDsmModRteRemoteNode
				NodeAddr,
			restDsmModRteRemoteSlot
				SlotAddr,
			restDsmModRteLocalPortNumber
				INTEGER,
			restDsmModRteLocalPortAddress
				PortAddr
			}

restDsmModRteAddr 	OBJECT-TYPE
		SYNTAX  SlotAddr
		ACCESS  read-only
		STATUS  mandatory
		DESCRIPTION "Address of DSM module.
			Format is nest.slot."
		::= { restDsmModRteEntry 1 }

restDsmModRteExchCodeLen 	OBJECT-TYPE
		SYNTAX  INTEGER (1..16)
		ACCESS  read-only
		STATUS  mandatory
		DESCRIPTION "This attribute defines the length
			of the restDsmModRteExchCode attribute."
		::= { restDsmModRteEntry 2 }

restDsmModRteExchCode 	OBJECT-TYPE
		SYNTAX  DisplayString (SIZE (1..16))
		ACCESS  read-only
		STATUS  mandatory
		DESCRIPTION "The exchange code."
		::= { restDsmModRteEntry 3 }

restDsmModRtePartition 	OBJECT-TYPE
		SYNTAX  INTEGER (1..1023)
		ACCESS  read-only
		STATUS  mandatory
		DESCRIPTION "Route partition ID."
		::= { restDsmModRteEntry 4 }

restDsmModRteRemoteNode 	OBJECT-TYPE
		SYNTAX  NodeAddr
		ACCESS  read-only
		STATUS  mandatory
		DESCRIPTION "Identifies the node containing
			the DSM that this routing entry refers
			to.

			For the local routing table entries,
			this attribute has a value of 0."
		::= { restDsmModRteEntry 5 }

restDsmModRteRemoteSlot 	OBJECT-TYPE
		SYNTAX  SlotAddr
		ACCESS  read-only
		STATUS  mandatory
		DESCRIPTION "Identifies the module address in
			the node defined in
			restDsmModRteRemoteNode that contains
			the DSM that this routing entry refers
			to.

			For the local routing table entries,
			this attribute has value of 0.0."
		::= { restDsmModRteEntry 6 }

restDsmModRteLocalPortNumber 	OBJECT-TYPE
		SYNTAX  INTEGER (0..64)
		ACCESS  read-only
		STATUS  mandatory
		DESCRIPTION "Identifies the physical D-channel
			port on the DSM that this routing entry
			refers to.

			For the remote routing table entries,
			this attribute has value of 0."
		::= { restDsmModRteEntry 7 }

restDsmModRteLocalPortAddress 	OBJECT-TYPE
		SYNTAX  PortAddr
		ACCESS  read-only
		STATUS  mandatory
		DESCRIPTION "INTRODUCED 2.0.1
			    Identifies the virtual port address of the
			    D-channel port that this routing entry
			    refers to if the route is a local one.

			    For remote routing table entries, this
			    attribute will return 0.0.0."
		::= { restDsmModRteEntry 8 }


-- LGM Specific Status

restLgmModule 	OBJECT IDENTIFIER ::= { restModule 11 }

-- LGM Module Specific Status

restLgmModuleTable 	OBJECT-TYPE
		SYNTAX  SEQUENCE OF RestLgmModuleEntry
		ACCESS  not-accessible
		STATUS  mandatory
		DESCRIPTION "This section of the MIB is used to
			get status of any LGM modules defined on
			the node."
		::= { restLgmModule 1 }

restLgmModuleEntry 	OBJECT-TYPE
		SYNTAX  RestLgmModuleEntry
		ACCESS  not-accessible
		STATUS  mandatory
		DESCRIPTION "INTRODUCED 2.0.0"
		INDEX { restLgmModuleAddr }
		::= { restLgmModuleTable 1 }

RestLgmModuleEntry		::= SEQUENCE {
			restLgmModuleAddr
				SlotAddr,
			restLgmModuleTotalSAFs
				INTEGER,
			restLgmModuleAvailSAFs
				INTEGER,
			restLgmModuleTotalSCFs
				INTEGER,
			restLgmModuleAvailSCFs
				INTEGER
			}

restLgmModuleAddr 	OBJECT-TYPE
		SYNTAX  SlotAddr
		ACCESS  read-only
		STATUS  mandatory
		DESCRIPTION "Address of this LGM module.
			Format is nest.slot."
		::= { restLgmModuleEntry 1 }

restLgmModuleTotalSAFs 	OBJECT-TYPE
		SYNTAX	INTEGER
		ACCESS  read-only
		STATUS  mandatory
		DESCRIPTION "Maximum number of SAF
			allowed on this LGM module."
		::= { restLgmModuleEntry 2 }

restLgmModuleAvailSAFs 	OBJECT-TYPE
		SYNTAX  INTEGER
		ACCESS  read-only
		STATUS  mandatory
		DESCRIPTION "Number of SAF that still
			can be allocated on this LGM
			module. Note that number of SAF
			allocated on this LGM module can
			be derived by subtraction of the
			value of this attribute from the
			value of restLgmModuleTotalSAFs
			attribute."
		::= { restLgmModuleEntry 3 }

restLgmModuleTotalSCFs 	OBJECT-TYPE
		SYNTAX	INTEGER
		ACCESS  read-only
		STATUS  mandatory
		DESCRIPTION "Maximum number of SCF
			allowed on this LGM module."
		::= { restLgmModuleEntry 4 }

restLgmModuleAvailSCFs 	OBJECT-TYPE
		SYNTAX  INTEGER
		ACCESS  read-only
		STATUS  mandatory
		DESCRIPTION "Number of SCF that still
			can be allocated on this LGM
			module. Note that number of SCF
			allocated on this LGM module can
			be derived by subtraction of the
			value of this attribute from the
			value of restLgmModuleTotalSCFs
			attribute."
		::= { restLgmModuleEntry 5 }



-- Synchrony Port Status MIB

restPortTable 	OBJECT-TYPE
		SYNTAX    SEQUENCE OF RestPortEntry
		ACCESS    not-accessible
		STATUS    mandatory
		DESCRIPTION "This section of the MIB does not
			support getNext."
		::=  { reStatus 5 }

restPortEntry 	OBJECT-TYPE
		SYNTAX    RestPortEntry
		ACCESS    not-accessible
		STATUS    mandatory
		DESCRIPTION " "
		INDEX { restPortAddr }
		::=  { restPortTable 1 }

RestPortEntry            ::=  SEQUENCE {
                         restPortAddr
                                   PortAddr,
                         restPortDiagnostics
                                   INTEGER,
                         restPortStatus
                                   INTEGER,
                         restPortSubStatus
                                   INTEGER,
                         restPortCondition
                                   INTEGER,
                         restPortSubCondition
                                   INTEGER,
                         restPortType
                                   INTEGER,
                         restPortLoopbackType
                                   INTEGER,
                         restPortLoopbackDuration
                                   INTEGER,
                         restPortLoopbackStatus
                                   INTEGER,
                         restPortLoopbackInitiator
                                   INTEGER,
                         restPortErrorIndication
                                   INTEGER,
                         restPortSevereIndication
                                   INTEGER,
                         restPortBGDiagResults
                                   OCTET STRING,
                         restPortNumberOfBundles
                                   INTEGER,
                         restPortPhasorStatus
                                   OCTET STRING,
                         restPortMappedPhy
                                   PortAddr,
                         restPortSdmFunction
                                   OCTET STRING,
                         restPortSdmTFunction
                                   OCTET STRING,
			 restPortBundleInTone
				   INTEGER,
			 restPortSdmSignalStatus
				   INTEGER,
			 restPortSdmBipolarViolationInd
				   INTEGER,
			 restPortCapabilities
				   OCTET STRING
                          }


restPortAddr 	OBJECT-TYPE
		SYNTAX    PortAddr
		ACCESS    read-only
		STATUS    mandatory
		DESCRIPTION " "
		::= { restPortEntry 1 }

restPortDiagnostics 	OBJECT-TYPE
		SYNTAX    INTEGER {
				   reset(6),
                                   insert(4),
                                   remove(5),
                                   update(7),
                                   setLoopback(9),
                                   clearLoopback(8),
                                   clearEvent(10)
			   }
		ACCESS    write-only
		STATUS    mandatory
		DESCRIPTION "Remove will free up the bus bandwidth
			used by the port. It will also set the port
			configuration start mode to off. This command
			will not work on server ports. For virtual
			ports, a disconnection of the I/O to server TDM
			channel is equivalent to a remove port.

			Insert will add removed ports back onto the bus,
			and will load the new configuration MIB to the
			port. It will also set the port configuration
			start mode to automatic. This command will not
			work on server ports. For virtual ports, a
			connection of the I/O to server TDM channel is
			equivalent to an insert port.

			Reset is equivalent to removing and then
			inserting a port for I/O ports. For server
			ports, reset will disconnect the I/O to server
			TDM channel. If the I/O side of the channel is
			set to auto connect, then the channel will be
			reconnected, although the virtual port may be
			allocated to a different physical port.

			Update will load non-intrusive configuration MIB
			changes to the port. If any intrusive changes
			have been made to the port configuration, then
			the command will fail.

			Set loopback will set a loopback on the port.
			The type of loopback is specified in
			restPortLoopbackType.

			Clear loopback will clear a loopback on the
			port."
		::= { restPortEntry 2 }

restPortStatus 	OBJECT-TYPE
		SYNTAX    INTEGER {
				   active(44),
                                   standby(47),
                                   maintenance(51),
                                   inactive(46),
                                   failed(43)
                                    }
		ACCESS    read-only
		STATUS    mandatory
		DESCRIPTION " "
		::= { restPortEntry 3 }

		
restPortSubStatus 	OBJECT-TYPE
		SYNTAX    INTEGER {
                                   enabled(1),
                                   disabled(2),
                                   removed(5),
                                   undefined(50)
                                    }
		ACCESS    read-only
		STATUS    mandatory
		DESCRIPTION " "
		::= { restPortEntry 4 }

restPortCondition 	OBJECT-TYPE
		SYNTAX    INTEGER {
                                   normal(57),
                                   exception(52),
                                   undefined(50)
                                    }
		ACCESS    read-only
		STATUS    mandatory
		DESCRIPTION " "
		::= { restPortEntry 5 }

restPortSubCondition 	OBJECT-TYPE
		SYNTAX    INTEGER {
                                   none(71),
                                   redAlarm(72),
                                   yellowAlarm(73),
                                   lmiFail(74),
                                   clockFail(75),
				   msgTimeout(76),
				   cfgMismatch(77),
				   dnloadRmt(78),
                                   stToSt(79),
				   serverLoopback(80),
				   exceedPowerSpec(81),
                                   externalLoopback(82),
				   remoteEndReset(83),
				   los(98),
                                   ros(99),
                                   losAndRos(100),
                                   berOverFailThreshold(29),
				   layer2TimeOut(30),
				   layer2Mismatch(31),
                                   pending(33),
				   oos(39)
                                   }
		ACCESS    read-only
		STATUS    mandatory
		DESCRIPTION " "
		::= { restPortEntry 6 }

restPortType 	OBJECT-TYPE
		SYNTAX    INTEGER {
                                   t1m(5),
                                   e1m(6),
                                   sgm(7),
                                   lgm(8),
                                   asm(9),
                                   fsm(11),
                                   sdm(12),
                                   sgmAg(13),
				   rtm(14),
				   dsm(19),
				   e3m(20)
                                   }
		ACCESS    read-only
		STATUS    mandatory
		DESCRIPTION " "
		::= { restPortEntry 7 }

restPortLoopbackType 	OBJECT-TYPE
		SYNTAX  INTEGER {
			lim(2),
			limDisc(3),
			rim(4),
			bidirectional(5),
			extLim(12),
			extRim(13),
			extBidirectional(14),
			extUlim(15),
			extIdlRim(16),
			remoteBus(17)
			}
		ACCESS	write-only
		STATUS  mandatory
		DESCRIPTION "Indicates what type of loopback the user
			wishes to set on the port.
			lim specifies a local interface loopback.
			limDisc specifies a local interface loopback
			with disconnection.
			rim specifies a remote interface loopback.
			prefix ext means that this particular loopback
			is being set on external device, such as ADx.
			remoteBus specifies a loopback from remote
			ILC towards ST."
		::= { restPortEntry 8 }

restPortLoopbackDuration 	OBJECT-TYPE
		SYNTAX    INTEGER (0..65535)
		ACCESS    read-write
		STATUS    mandatory
		DESCRIPTION "Value 65535 specifies a permanent
			loopback."
		::= { restPortEntry 9 }

restPortLoopbackStatus 	OBJECT-TYPE
		SYNTAX	INTEGER {
			none(1),
			lim(2),
			limDisc(3),
			rim(4),
			bidirectional(5),
			facility(8),
			payload(9),
			localLoop(10),
			remoteLoop(11),
			extLim(12),
			extRim(13),
			extBidirectional(14),
			extUlim(15),
			extIdlRim(16),
			remoteBus(17)
			}
		ACCESS  read-only
		STATUS  mandatory
		DESCRIPTION "If the port is in loopback, this
			field indicates the type of loopback. If the
			port is not in loopback, then none will be
			returned."
		::= { restPortEntry 10 }

restPortLoopbackInitiator 	OBJECT-TYPE
		SYNTAX  INTEGER {
			local(1),
			remote(2),
			notApplicable(255)
			}
		ACCESS  read-only
		STATUS  mandatory
		DESCRIPTION "If value is local, then loopback
			was initiated by user. If value is
			remote, then loopback was initiated by
			network. If no loopback is enabled,
			then this field should return not
			applicable."
		::= { restPortEntry 11 }

restPortErrorIndication 	OBJECT-TYPE
		SYNTAX    INTEGER {
                                   set(1),
                                   clear(2)
                                   }
		ACCESS    read-only
		STATUS    mandatory
		DESCRIPTION " "
		::= { restPortEntry 12 }

restPortSevereIndication 	OBJECT-TYPE
		SYNTAX    INTEGER {
                                   set(1),
                                   clear(2)
                                   }
		ACCESS    read-only
		STATUS    mandatory
		DESCRIPTION " "
		::= { restPortEntry 13 }

restPortBGDiagResults 	OBJECT-TYPE
		SYNTAX    OCTET STRING (SIZE (1))
		ACCESS    read-only
		STATUS    mandatory
		DESCRIPTION "Results of port background
			diagnostics. Bit map is the same as for
			one port within recfSlotModulePortDiagMask."
		::= { restPortEntry 14 }

restPortNumberOfBundles 	OBJECT-TYPE
		SYNTAX    INTEGER (0..32)
		ACCESS    read-only
		STATUS    mandatory
		DESCRIPTION " "
		::= { restPortEntry 15 }

restPortPhasorStatus 	OBJECT-TYPE
		SYNTAX    OCTET STRING (SIZE (2))
		ACCESS     read-only
		STATUS     mandatory
		DESCRIPTION "All bits zero indicates normal.
			       bit  1 (lsb) indicates receive phasor underflow
			       bit  2 indicates receive phasor overflow
			       bit  3 indicates receive phasor empty
			       bit  4 indicates receive phasor full
			       bit  5 indicates receive phasor fifo error
			       bit  6 indicates KGROS status
			       bit  7 indicates KGLOS status
			       bit  8 indicates receive phasor not applicable
			       bit  9 indicates transmit phasor underflow
			       bit 10 indicates transmit phasor overflow
			       bit 11 indicates transmit phasor empty
			       bit 12 indicates transmit phasor full
			       bit 13 indicates transmit phasor fifo error
			       bit 14 indicates KG status is not applicable
			       bit 15 is reserved
			       bit 16 indicates transmit phasor not applicable
			    If port does not have a phasor, the return
			    value will be x8080.

			    Bits 6 and 7 are applicable only to SDM module
			    and reflect the KG-resync lines status as follows:
			    bit 6|bit 7
			    -----|-----
			      0  |  0   KG-status O.K. disabled / disabled
			      1  |  0   KG-status ERR  enabled  / disabled
			      0  |  1   KG-status ERR  disabled / enabled
			      1  |  1   KG-status ERR  enabled  / enabled ."
		::= { restPortEntry 16 }

restPortMappedPhy 	OBJECT-TYPE
		SYNTAX    PortAddr
		ACCESS    read-only
		STATUS    mandatory
		DESCRIPTION "For virtual port addresses, returns the
			physical port that this address is mapped to.
			If the virtual port address is not mapped to a
			physical port, then 0.0.0 will be returned.

			For physical port addresses, returns the virtual
			port that is mapped to this port. If no virtual
			port is mapped to this physical port address,
			then 0.0.0 will be returned."
		::= { restPortEntry 17 }

restPortSdmFunction 	OBJECT-TYPE
		SYNTAX     OCTET STRING (SIZE (1))
		ACCESS     read-only
		STATUS     mandatory
		DESCRIPTION "Only applies to SDM ports (except SDM
			modules of hardware subtypes 33 (4 ports E1
			balanced) and 34 (4 ports E1 unbalanced)).
			The bit map is:
			bit 1 (lsb) - DSR if DTE, DTR if DCE
			bit 2 - DCD if DTE, RTS if DCE
			bit 3 - reserved
			bit 4 - CTS if DTE, reserved if DCE
			bit 5 - DTR if DTE, DSR if DCE
			bit 6 - RTS if DTE, DCD if DCE
			bit 7 - indicates functions are not applicable
			bit 8 - reserved if DTE, CTS if DCE

			Module types and subtypes that do not support
			this attribute will return a value of x40."
		::= { restPortEntry 18 }

restPortSdmTFunction 	OBJECT-TYPE
		SYNTAX     OCTET STRING (SIZE (1))
		ACCESS     read-only
		STATUS     mandatory
		DESCRIPTION "Only applies to SDM ports.
			bit 1 (lsb) - TM if DTE, LL if DCE
			bit 2 - reserved if DTE, RL if DCE
			bit 3 - reserved
			bit 4 - reserved
			bit 5 - LL if DTE, TM if DCE
			bit 6 - RL if DTE, reserved if DCE
			bit 7 - reserved
			bit 8 - indicates test functions are not
			applicable

			Module types and subtypes that do not support
			this attribute will return a value of x80. In
			addition, for the SDM, test functions will be
			not applicable (x80) if KG-resync is enabled."
		::= { restPortEntry 19 }

restPortBundleInTone 	OBJECT-TYPE
		SYNTAX     INTEGER (0..31)
		ACCESS     read-only
		STATUS     mandatory
		DESCRIPTION " "
		::= { restPortEntry 20 }

restPortSdmSignalStatus 	OBJECT-TYPE
		SYNTAX     INTEGER {
			ok(1),
			los(2),
			losEvent(4),
			notApplicable(255)
			}
		ACCESS     read-only
		STATUS     mandatory
		DESCRIPTION "Only applies to SDM ports on modules of
			hardware subtypes 33 (4 ports E1 balanced)
			and 34 (4 ports E1 unbalanced). Otherwise it
			will return not applicable."
		::= { restPortEntry 21 }

restPortSdmBipolarViolationInd 	OBJECT-TYPE
		SYNTAX     INTEGER {
			event(1),
			noEvent(2),
			notApplicable(255)
			}
		ACCESS     read-only
		STATUS     mandatory
		DESCRIPTION "Only applies to SDM ports on modules of
			hardware subtypes 33 (4 ports E1 balanced)
			and 34 (4 ports E1 unbalanced). Otherwise it
			will return not applicable."
		::= { restPortEntry 22 }

restPortCapabilities 	OBJECT-TYPE
		SYNTAX    OCTET STRING (SIZE (1..4))
		ACCESS     read-only
		STATUS     mandatory
		DESCRIPTION "If this attribute is not applicable, the
			 	return value consists of octet string of size 1
			with the value none (255).

			Currently supported only by SDM port. The
			interpretation of the octet string is listed
			below. For those capabilities specified using
			bit fields (module and port speed capabilities,
			as listed below), a value of one (1) means that
			the feature is supported, while zero (0)
			indicates that it is not supported.

			First byte: physical capabilities
			01h - bulk (no separate connector for
			      this port)
			02h - 15 pin connector
			03h - 25 pin connector
			04h - RJ45 (8 pin modular) connector
			05h - 75 ohm coax connector

			Second byte: electrical capabilities
			01h - V.24
			02h - V.35
			04h - V.11
			11h - E1 balanced
			12h - E1 unbalanced
			41h - 64K G.703 codirectional

			Third byte: module capabilities
			bit 1 (lsb) - supports redundancy
			bit 2 - supports loopback leads (RL,
			LL, and TM)
			bit 3 - supports LIM/DSC
			bit 4 - supports function leads (RTS,
			CTS, etc.)
			bits 5-8 - indicates clock modes
			    01h - supports DCE
			    02h - supports DTE
			    03h - supports DTE and DCE
			    04h - supports DTE1 only

			Fourth byte: port speed capabilities
			bit 1 (lsb) - various (supports
			multiple, user-programmable
			data rates on the ports)
			bit 2 - supports 64 kbps
			bit 3 - supports 1.544 Mbps
			bit 4 - supports 2.048 Mbps
			bits 5-8 - reserved for future use"
		::= { restPortEntry 23 }


-- Bundle Status

restBundleTable 	OBJECT-TYPE
		SYNTAX    SEQUENCE OF RestBundleEntry
		ACCESS    not-accessible
		STATUS    mandatory
		DESCRIPTION "This section of the MIB does not
			support getNext.

			Creating (defining and then inserting) a new
			bundle out of available DS0s will not impact
			the existing bundles.

			Creating a new bundle out of DS0s currently
			belong to one or more other bundles will
			require that the affected bundles are removed
			and erased first.

			Expanding or shrinking an existing bundle is
			equivalent to the combination of erasing and
			then creating the bundle, as is changing the
			type of an existing bundle."
		::=  { reStatus 6 }

restBundleEntry 	OBJECT-TYPE
		SYNTAX    RestBundleEntry
		ACCESS    not-accessible
		STATUS    mandatory
		DESCRIPTION " "
		INDEX { restBundleAddr }
		::=  { restBundleTable 1 }

RestBundleEntry          ::=  SEQUENCE {
                         restBundleAddr
                                   BundleAddr,
                         restBundleDiagnostics
                                   INTEGER,
                         restBundleStatus
                                   INTEGER,
                         restBundleBwCntStatus
                                   INTEGER,
                         restBundleMillwattSignalABCD
                                   INTEGER,
                         restBundleDS0Map
                                   OCTET STRING,
			 restBundleSignalA
				   INTEGER,
			 restBundleSignalB
				   INTEGER,
			 restBundleSignalC
				   INTEGER,
			 restBundleSignalD
				   INTEGER,
                         restBundleOutSigA
				   INTEGER,
			 restBundleOutSigB
				   INTEGER,
			 restBundleOutSigC
				   INTEGER,
			 restBundleOutSigD
				   INTEGER
			 }


restBundleAddr 	OBJECT-TYPE
		SYNTAX    BundleAddr
		ACCESS    read-only
		STATUS    mandatory
		DESCRIPTION " "
		::= { restBundleEntry 1 }

restBundleDiagnostics 	OBJECT-TYPE
		SYNTAX    INTEGER {
                                   insert(4),
                                   remove(5),
                                   reset(6),
                                   update(7)
                                   }
		ACCESS    write-only
		STATUS    mandatory
		DESCRIPTION "Remove will free the bandwidth used by the
			bundle. If the bundle is an INL, then all
			channels connected over the INL will be
			disconnected. If the bundle is I/O, then that
			channel will be disconnected. The start
			mode of the bundle in the configuration
			MIB will be set to off.

			Insert only works on removed bundles (i.e.,
			bundles whose status is unknown). It will get
			the new bundle configuration MIB and attempt to
			bring the bundle up. The start mode of the
			bundle in the configuration MIB will be set to
			automatic.

			Reset is equivalent to a remove followed by an
			insert, except that the start mode in the bundle
			configuration MIB will not be changed.

			Update will load in the new bundle configuration
			MIB without affecting the INL or channel on that
			bundle. It will fail if any intrusive parameters
			in the bundle configuration MIB have been
			changed."
		::= { restBundleEntry 2 }

restBundleStatus 	OBJECT-TYPE
		SYNTAX    INTEGER {
                                   active(1),
                                   inactive(2),
                                   unknown(50)
                                    }
		ACCESS    read-only
		STATUS    mandatory
		DESCRIPTION "The status is always enabled if the bundle
			is an INL. Unknown value means that the bundle
			is undefined."
		::= { restBundleEntry 3 }


restBundleBwCntStatus 	OBJECT-TYPE
		SYNTAX    INTEGER {
                                   active(1),
                                   inactive(2),
			   busy(3),
                                   unknown(50)
                                    }
		ACCESS    read-only
		STATUS    mandatory
		DESCRIPTION  "Bandwidth contention status."
		::= { restBundleEntry 4 }

restBundleMillwattSignalABCD 	OBJECT-TYPE
		SYNTAX    INTEGER {
                                        a0-b0-c0-d0(1),
                                        a0-b0-c0-d1(2),
                                        a0-b0-c1-d0(3),
                                        a0-b0-c1-d1(4),
                                        a0-b1-c0-d0(5),
                                        a0-b1-c0-d1(6),
                                        a0-b1-c1-d0(7),
                                        a0-b1-c1-d1(8),
                                        a1-b0-c0-d0(9),
                                        a1-b0-c0-d1(10),
                                        a1-b0-c1-d0(11),
                                        a1-b0-c1-d1(12),
                                        a1-b1-c0-d0(13),
                                        a1-b1-c0-d1(14),
                                        a1-b1-c1-d0(15),
                                        a1-b1-c1-d1(16),
			disable(255)
                                        }
		ACCESS    read-write
		STATUS    mandatory
		DESCRIPTION "Controls the tone generator for
			PCM channels."
		::= { restBundleEntry 5 }


restBundleDS0Map 	OBJECT-TYPE
		SYNTAX    OCTET STRING (SIZE (4))
		ACCESS    read-only
		STATUS    mandatory
		DESCRIPTION " "
		::= { restBundleEntry 6 }

restBundleSignalA 	OBJECT-TYPE
		SYNTAX	INTEGER {
			on(1),
			off(2),
			notApplicable(255)
			}
		ACCESS	read-only
		STATUS	mandatory
		DESCRIPTION " "
		::= { restBundleEntry 7 }

restBundleSignalB 	OBJECT-TYPE
		SYNTAX	INTEGER {
			on(1),
			off(2),
			notApplicable(255)
			}
		ACCESS	read-only
		STATUS	mandatory
		DESCRIPTION " "
		::= { restBundleEntry 8 }

restBundleSignalC 	OBJECT-TYPE
		SYNTAX	INTEGER {
			on(1),
			off(2),
			notApplicable(255)
			}
		ACCESS	read-only
		STATUS	mandatory
		DESCRIPTION " "
		::= { restBundleEntry 9 }

restBundleSignalD 	OBJECT-TYPE
		SYNTAX	INTEGER {
			on(1),
			off(2),
			notApplicable(255)
			}
		ACCESS	read-only
		STATUS	mandatory
		DESCRIPTION " "
		::= { restBundleEntry 10 }

restBundleOutSigA 	OBJECT-TYPE
		SYNTAX	INTEGER {
			on(1),
			off(2),
			notApplicable(255)
			}
		ACCESS	read-only
		STATUS	mandatory
		DESCRIPTION	"This is not supported on
			 T1M and E1M 4-port hardware
			 configurationis"
		::= { restBundleEntry 11 }

restBundleOutSigB 	OBJECT-TYPE
		SYNTAX	INTEGER {
			on(1),
			off(2),
			notApplicable(255)
			}
		ACCESS	read-only
		STATUS	mandatory
		DESCRIPTION	"This is not supported on
			 T1M and E1M 4-port hardware
			 configurationis"
		::= { restBundleEntry 12 }

restBundleOutSigC 	OBJECT-TYPE
		SYNTAX	INTEGER {
			on(1),
			off(2),
			notApplicable(255)
			}
		ACCESS	read-only
		STATUS	mandatory
		DESCRIPTION	"This is not supported on
			 T1M and E1M 4-port hardware
			 configurationis"
		::= { restBundleEntry 13 }

restBundleOutSigD 	OBJECT-TYPE
		SYNTAX	INTEGER {
			on(1),
			off(2),
			notApplicable(255)
			}
		ACCESS	read-only
		STATUS	mandatory
		DESCRIPTION	"This is not supported on
			 T1M and E1M 4-port hardware
			 configurationis"
		::= { restBundleEntry 14 }


-- INL Status

restINLTable 	OBJECT-TYPE
		SYNTAX    SEQUENCE OF RestINLEntry
		ACCESS    not-accessible
		STATUS    mandatory
		DESCRIPTION " "
		::=  { reStatus 7 }

restINLEntry 	OBJECT-TYPE
		SYNTAX    RestINLEntry
		ACCESS    not-accessible
		STATUS    mandatory
		DESCRIPTION " "
		INDEX { restINLNumber }
		::=  { restINLTable 1 }

RestINLEntry             ::=  SEQUENCE {
                         restINLNumber
                                   INTEGER,
                         restINLAddr
                                   BundleAddr,
                         restINLDiagnostics
                                   INTEGER,
                         restINLStatus
                                   INTEGER,
                         restINLSubStatus
                                   INTEGER,
                         restINLLocalBERLevel
                                   INTEGER,
                         restINLLocalBERQuality
                                   INTEGER,
                         restINLRemoteNodeID
                                   NodeAddr,
                         restINLRemotePortAddr
                                   BundleAddr,
                         restINLRemoteINLID
                                   INTEGER,
                         restINLRemoteBERLevel
                                   INTEGER,
                         restINLRemoteBERQuality
                                   INTEGER,
                         restINLAvailableTDMBw
                                   INTEGER,
                         restINLAvailablePacketBw
                                   INTEGER,
                         restINLLoopbackDuration
                                   INTEGER,
                         restINLLoopbackStatus
                                   INTEGER,
                         restINLTotalCRCErrors
                                   INTEGER,
                         restINLBERWindowFill
                                  DisplayString,
                         restINLNumTdmCh
                                   INTEGER,
                         restINLNumFrCh
                                   INTEGER,
			 restINLSpeed
                                   INTEGER,
			 restINLNumSaf
				   INTEGER,
			 restINLLOSMode
				   INTEGER,
			 restINLBusFrameMode
				   INTEGER
                         }


restINLNumber 	OBJECT-TYPE
		SYNTAX    INTEGER (1..31)
		ACCESS    read-only
		STATUS    mandatory
		DESCRIPTION " "
		::= { restINLEntry 1 }

restINLAddr 	OBJECT-TYPE
		SYNTAX    BundleAddr
		ACCESS    read-only
		STATUS    mandatory
		DESCRIPTION " "
		::= { restINLEntry 2 }


restINLDiagnostics 	OBJECT-TYPE
		SYNTAX    INTEGER {
                                   enable(1),
                                   disable(2),
                                   insert(4),
                                   remove(5),
                                   reset(6),
                                   update(7),
			   restart(79),
                                   setLoopback(9),
                                   clearLoopback(8),
                                   clearINLTotalCRCErrors(63),
                                   clearINLBERWindowFill(64)
                                   }
		ACCESS    write-only
		STATUS    mandatory
		DESCRIPTION "Remove will free bus bandwidth used by
			the INL, and disconnect all channels connected
			over the INL. It will also set the INL start
			mode in the configuration MIB to off.

			Insert on a removed INL will get the new MIB
			and software, and set the INL start mode in
			the configuration MIB to automatic.

			Reset is equivalent to a remove and insert,
			except it does not change the INL start mode
			in the configuration MIB.

			Restart will reestablish the INL without
			loading in the current INL configuration
			MIB. All channels connected over the INL
			will be disconnected.

			Update will load the non-intrusive parameters
			from the INL configuration MIB. If any
			intrusive parameters have been changed, then
			update will fail. Update will not affected the
			channels connected over the INL.

			Disable will prevent any new channel
			connections from being made over an INL. It
			will not affect existing channel connections.

			Enable on an disabled INL will allow new
			channel connections to be made over the INL."
		::= { restINLEntry 3 }

restINLStatus 	OBJECT-TYPE
		SYNTAX    INTEGER {
                                   pending(33),
                                   inService(38),
                                   outOfService(39),
                                   maintenance(51)
                                   }
		ACCESS    read-only
		STATUS    mandatory
		DESCRIPTION " "
		::= { restINLEntry 4 }

restINLSubStatus 	OBJECT-TYPE
		SYNTAX    INTEGER {
                                   enable(1),
                                   disable(2)
                                   }
		ACCESS    read-only
		STATUS    mandatory
		DESCRIPTION " "
		DEFVAL { enable }
		::= { restINLEntry 5 }

restINLLocalBERLevel 	OBJECT-TYPE
		SYNTAX    INTEGER (0..16)
		ACCESS    read-only
		STATUS    mandatory
		DESCRIPTION "BER level on the local node. If the
			 	local BER quality value is notCalculatedYet,
			then this attribute will return zero."
		::= { restINLEntry 6 }

restINLLocalBERQuality 	OBJECT-TYPE
		SYNTAX    INTEGER {
                                   accepted(1),
                                   unaccepted(2),
			   notCalculatedYet(3)
                                   }
		ACCESS    read-only
		STATUS    mandatory
		DESCRIPTION " "
		::= { restINLEntry 7 }

restINLRemoteNodeID 	OBJECT-TYPE
		SYNTAX    NodeAddr
		ACCESS    read-only
		STATUS    mandatory
		DESCRIPTION "Node number that the INL terminates on.
			If no remote connection has been established,
			then this attribute will return zero."
		::= { restINLEntry 8 }

restINLRemotePortAddr 	OBJECT-TYPE
		SYNTAX    BundleAddr
		ACCESS    read-only
		STATUS    mandatory
		DESCRIPTION "Port or bundle address that the INL
			terminates on. If no remote connection has
			been established, then this attribute will
			return zero."
		::= { restINLEntry 9 }

restINLRemoteINLID 	OBJECT-TYPE
		SYNTAX    INTEGER  (0..31)
		ACCESS    read-only
		STATUS    mandatory
		DESCRIPTION "INL ID on the remote node that the INL
			terminates on. If no remote connection has
			been established, then this attribute will
			return zero."
		::= { restINLEntry 10 }

restINLRemoteBERLevel 	OBJECT-TYPE
		SYNTAX    INTEGER (0..16)
		ACCESS    read-only
		STATUS    mandatory
		DESCRIPTION "BER level on the remote node that the
			INL terminates on. If the remote BER quality
			value is notCalculatedYet, then this attribute
			will return zero."
		::= { restINLEntry 11 }

restINLRemoteBERQuality 	OBJECT-TYPE
		SYNTAX    INTEGER {
                                   accepted(1),
                                   unaccepted(2),
				   notCalculatedYet(3)
                                   }
		ACCESS    read-only
		STATUS    mandatory
		DESCRIPTION " "
		::= { restINLEntry 12 }

restINLAvailableTDMBw 	OBJECT-TYPE
		SYNTAX    INTEGER
		ACCESS    read-only
		STATUS    mandatory
		DESCRIPTION " "
		::= { restINLEntry 13 }

restINLAvailablePacketBw 	OBJECT-TYPE
		SYNTAX    INTEGER
		ACCESS    read-only
		STATUS    mandatory
		DESCRIPTION " "
		::= { restINLEntry 14 }

restINLLoopbackDuration 	OBJECT-TYPE
		SYNTAX    INTEGER (0..65535)
		ACCESS    read-write
		STATUS    mandatory
		DESCRIPTION "Value 65535 specifies a permanent
			loopback."
		::= { restINLEntry 15 }

restINLLoopbackStatus 	OBJECT-TYPE
		SYNTAX    INTEGER {
                                   none(1),
                                   originator(2),
                                   terminator(3),
                                   external(4)
                                   }
		ACCESS    read-only
		STATUS    mandatory
		DESCRIPTION " "
		::= { restINLEntry 16 }


restINLTotalCRCErrors 	OBJECT-TYPE
		SYNTAX    INTEGER
		ACCESS    read-only
		STATUS    mandatory
		DESCRIPTION " "
		::= { restINLEntry 17 }

restINLBERWindowFill 	OBJECT-TYPE
		SYNTAX    DisplayString ( SIZE(0..5))
		ACCESS    read-only
		STATUS    mandatory
		DESCRIPTION "Format e.g. 10/32, 5/32."
		::= { restINLEntry 18 }

restINLNumTdmCh 	OBJECT-TYPE
		SYNTAX    INTEGER
		ACCESS    read-only
		STATUS    mandatory
		DESCRIPTION " "
		::= { restINLEntry 19 }

restINLNumFrCh 	OBJECT-TYPE
		SYNTAX    INTEGER
		ACCESS    read-only
		STATUS    mandatory
		DESCRIPTION " "
		::= { restINLEntry 20 }

restINLSpeed 	OBJECT-TYPE
		SYNTAX    INTEGER
		ACCESS    read-only
		STATUS    mandatory
		DESCRIPTION " "
		::= { restINLEntry 21 }

restINLNumSaf 	OBJECT-TYPE
		SYNTAX    INTEGER
		ACCESS    read-only
		STATUS    mandatory
		DESCRIPTION " "
		::= { restINLEntry 22 }

restINLLOSMode 	OBJECT-TYPE
		SYNTAX    INTEGER {
			localOutOfSync(1),
			localInSync(2),
			notApplicable(255)
			}
		ACCESS    read-only
		STATUS    mandatory
		DESCRIPTION " "
		::= { restINLEntry 23 }

restINLBusFrameMode 	OBJECT-TYPE
		SYNTAX    INTEGER {
			addbackMode(1),
			fallbackMode(2),
			notApplicable(255)
			}
		ACCESS    read-only
		STATUS    mandatory
		DESCRIPTION " "
		::= { restINLEntry 24 }


-- INL Contents Status

restINLContentsTable 	OBJECT-TYPE
		SYNTAX    SEQUENCE OF RestINLContentsEntry
		ACCESS    not-accessible
		STATUS    mandatory
		DESCRIPTION "This table lists all of the
			       channels on a specified INL."
		::=  { reStatus 8 }

restINLContentsEntry 	OBJECT-TYPE
		SYNTAX    RestINLContentsEntry
		ACCESS    not-accessible
		STATUS    mandatory
		DESCRIPTION " "
		INDEX { restINLContentsINLNumber,
			restINLContentsSeqNumber }
		::=  { restINLContentsTable 1 }

RestINLContentsEntry     ::=  SEQUENCE {
                         restINLContentsINLNumber
                                   INTEGER,
                         restINLContentsSeqNumber
                                   INTEGER,
                         restINLContentsSourceNodeID
                                   NodeAddr,
                         restINLContentsSourceAddr
                                   ChannelAddr,
                         restINLContentsDestNodeID
                                   NodeAddr,
                         restINLContentsDestAddr
                                   ChannelAddr
                          }

restINLContentsINLNumber 	OBJECT-TYPE
		SYNTAX    INTEGER (1..32)
		ACCESS    read-only
		STATUS    mandatory
		DESCRIPTION "INL 32 is used to display local
			 connections."
		::= { restINLContentsEntry 1 }

restINLContentsSeqNumber 	OBJECT-TYPE
		SYNTAX    INTEGER (1..65535)
		ACCESS    read-only
		STATUS    mandatory
		DESCRIPTION " "
		::= { restINLContentsEntry 2 }

restINLContentsSourceNodeID 	OBJECT-TYPE
		SYNTAX    NodeAddr
		ACCESS    read-only
		STATUS    mandatory
		DESCRIPTION " "
		::= { restINLContentsEntry 3 }

restINLContentsSourceAddr 	OBJECT-TYPE
		SYNTAX    ChannelAddr
		ACCESS    read-only
		STATUS    mandatory
		DESCRIPTION " "
		::= { restINLContentsEntry 4 }

restINLContentsDestNodeID 	OBJECT-TYPE
		SYNTAX    NodeAddr
		ACCESS    read-only
		STATUS    mandatory
		DESCRIPTION " "
		::= { restINLContentsEntry 5 }

restINLContentsDestAddr 	OBJECT-TYPE
		SYNTAX    ChannelAddr
		ACCESS    read-only
		STATUS    mandatory
		DESCRIPTION " "
		::= { restINLContentsEntry 6 }


-- Channel Status

restChannel 	OBJECT IDENTIFIER ::= { reStatus 9 }

-- General Channel Status

restChannelTable 	OBJECT-TYPE
		SYNTAX  SEQUENCE OF RestChannelEntry
		ACCESS  not-accessible
		STATUS  mandatory
		DESCRIPTION "This section of the MIB is defined
			    for all types of channels.

			    This section of the MIB will only support
			    getNext for local channel addresses."
		::=  { restChannel 1 }

restChannelEntry 	OBJECT-TYPE
		SYNTAX    RestChannelEntry
		ACCESS    not-accessible
		STATUS    mandatory
		DESCRIPTION " "
		INDEX { restChannelStatusAddr }
		::=  { restChannelTable 1 }

RestChannelEntry		::=  SEQUENCE {
			restChannelStatusAddr
			    ChannelStatusAddr,
			restChannelSourceNodeID
			    NodeAddr,
			restChannelSourceAddr
			    ChannelAddr,
			restChannelDestNodeID
			    NodeAddr,
			restChannelDestAddr
			    ChannelAddr,
			restChannelDiagnostics
			    INTEGER,
			restChannelDirectNodeConnect
			    OCTET STRING,
			restChannelDirectPathConnect
			    OCTET STRING,
			restChannelStatus
			    INTEGER,
			restChannelSubStatus
			    INTEGER,
			restChannelType
			    INTEGER,
			restChannelBandwidth
			    INTEGER,
			restChannelBypassCount
			    INTEGER,
			restChannelPath
			    OCTET STRING,
			restChannelRouteQuality
			    INTEGER,
			restChannelConnectTime
			    INTEGER,
			restChannelRetryCounter
			    INTEGER,
			restChannelLoopbackNode
			    NodeAddr,
			restChannelNodalSubratePath
			    OCTET STRING,
			restChannelDChOrigNode
			    NodeAddr,
			restChannelDChOrigAddr
			    PortAddr,
			restChannelDChTermNode
			    NodeAddr,
			restChannelDChTermAddr
			    PortAddr,
			restChannelLoopbackModAddr
			    SlotAddr,
			restChannelNetworkPath
			    OCTET STRING
			}

restChannelStatusAddr 	OBJECT-TYPE
		SYNTAX  ChannelStatusAddr
		ACCESS  read-only
		STATUS  mandatory
		DESCRIPTION "One of two channel address types:
			    (1) Local channel address, where the channel
			originates and/or terminates on this
			node. The address specifies a channel
			endpoint that exists on this node using
			the format of the type ChannelAddr,
			with the remainder of the instance
			identifier set to zeros.
			    (2) Bypass channel address, which can be
			used to obtain the status of a channel
			at a node that does not originate and/or
			terminate the channel. This format
			specifies the node ID and channel
			address of either the source or
			destination of the channel."
		::= { restChannelEntry 1 }

restChannelSourceNodeID 	OBJECT-TYPE
		SYNTAX    NodeAddr
		ACCESS    read-only
		STATUS    mandatory
		DESCRIPTION " "
		::= { restChannelEntry 2 }

restChannelSourceAddr 	OBJECT-TYPE
		SYNTAX    ChannelAddr
		ACCESS    read-only
		STATUS    mandatory
		DESCRIPTION " "
		::= { restChannelEntry 3 }

restChannelDestNodeID 	OBJECT-TYPE
		SYNTAX    NodeAddr
		ACCESS    read-only
		STATUS    mandatory
		DESCRIPTION " "
		::= { restChannelEntry 4 }

restChannelDestAddr 	OBJECT-TYPE
		SYNTAX    ChannelAddr
		ACCESS    read-only
		STATUS    mandatory
		DESCRIPTION " "
		::= { restChannelEntry 5 }

restChannelDiagnostics 	OBJECT-TYPE
		SYNTAX    INTEGER {
                                   connect(35),
                                   disconnect(36),
                                   reset(6),
                                   setLoopback(9),
                                   clearLoopback(8)
                                   }
		ACCESS    write-only
		STATUS    mandatory
		DESCRIPTION "Reset will disconnect and then reconnect
			the specified channel.

			Set and clear loopback are the only
			controls that will accept a remote
			channel address (i.e., one consisting of
			a node number and channel address)."
		::= { restChannelEntry 6 }

restChannelDirectNodeConnect 	OBJECT-TYPE
		SYNTAX    OCTET STRING (SIZE(0..36))
		ACCESS    write-only
		STATUS    mandatory
		DESCRIPTION "Connect the channel by selecting a route
			that passes through these specific nodes. Up to
			17 node numbers can be specified. Each node
			number requires two bytes.

			For the channels originating on ST node
			and terminating on a LINK node there
			must be a delimiter, specifying the
			transition point between the ST node and
			LINK node defined. Such delimiter will
			be two byte long with 0xFFFF value."
		::= { restChannelEntry 7 }

restChannelDirectPathConnect 	OBJECT-TYPE
		SYNTAX    OCTET STRING (SIZE(0..88))
		ACCESS    write-only
		STATUS    mandatory
		DESCRIPTION "Connect the channel using the specified
			route.

			For TDM and subrate channels, each hop of
			the path is indicates using three bytes. The
			first two bytes are the node number. The third
			byte identifies the INL that the channel passes
			through.

			For packet channels, each hop of the path is
			indicated using five bytes. The first two bytes
			are the node number. The third and fourth bytes
			are the nest and slot numbers, respectively, of
			the FSM that this packet channel passes through.
			The fifth number identifies the INL that the
			channel passes through.

			For all channel types, a maximum of 17 hops may
			be specified.

			For the channels originating on ST node
			and terminating on a LINK node there
			must be a delimiter, specifying the
			transition point between the ST path and
			LINK path defined. Since this applies
			only to TDM channels, such delimiter will
			be three byte long with 0xFFFFFF value."
		::= { restChannelEntry 8 }

restChannelStatus 	OBJECT-TYPE
		SYNTAX    INTEGER {
                                   connecting(34),
                                   connected(35),
                                   disconnecting(37),
                                   loopback(9),
                                   retryNoServer(30),
                                   retryNoBW(41),
                                   retryNoRoute(42),
				   retryNoDlci(132),
                                   retryDestIoUnusable(76),
                                   retryDestIoInUse(77),
				   retryAuto(121),
                                   retryExceedShareBW(78),
                                   pending(33),
                                   disconnected(36)
                                   }
		ACCESS    read-only
		STATUS    mandatory
		DESCRIPTION "If the channel is disconnected, see
			recfTDMChannelDisconnect (for TDM and subrate
			channels) or recfFrChannelDisconnect (for packet
			channels) for the reason.

			If the channel is pending, then it is waiting
			for the end-to-end acknowledgement.

			All of the retry values indicate that the node
			is trying to connect the channel. Each
			individual value indicates why the channel
			connection has not succeeded yet."
		::= { restChannelEntry 9 }

restChannelSubStatus 	OBJECT-TYPE
		SYNTAX    INTEGER {
                                   waitForRTSAck(55),
                                   noBypassServer(151),
                                   noSrcServer(152),
                                   noDestServer(153),
                                   noSrcSgmSaf(154),
                                   noDestSgmSaf(155),
                                   noSrcSgmScf(156),
                                   noDestSgmScf(157),
                                   noSrcAgmSaf(158),
                                   noDestAgmSaf(159),
                                   noSrcAgmScf(160),
                                   noDestAgmScf(161),
                                   noSrcAsmSaf(162),
                                   noDestAsmSaf(163),
                                   noSrcAsmScf(164),
                                   noDestAsmScf(165),
                                   noSrcLgmSaf(166),
                                   noDestLgmSaf(167),
                                   noSrcLgmScf(168),
                                   noDestLgmScf(169),
                                   noSrcRtmSaf(170),
                                   noDestRtmSaf(171),
                                   noSrcRtmScf(172),
                                   noDestRtmScf(173),
                                   noSrcVoicePort(174),
                                   noDestVoicePort(175),
                                   none(36)
                                   }
		ACCESS    read-only
		STATUS    mandatory
		DESCRIPTION "The waitForRTSAck value is only valid
			when the channel status is connecting.
			None value is valid for all channel status.
			The other values are only valid when the 
			channel status is retryNoServer."
		::= { restChannelEntry 10 }

restChannelType 	OBJECT-TYPE
		SYNTAX    INTEGER {
                                   tdm(1),
                                   packet(2),
                                   subrate(4),
                                   trunkGroup(5),
				   voice(9)
			   }
		ACCESS    read-only
		STATUS    mandatory
		DESCRIPTION " "
		::= { restChannelEntry 11 }

restChannelBandwidth 	OBJECT-TYPE
		SYNTAX    INTEGER
		ACCESS    read-only
		STATUS    mandatory
		DESCRIPTION "Returns the badwidth value this
			 	channel occupies on the bus of an INL."
		::= { restChannelEntry 12 }

restChannelBypassCount 	OBJECT-TYPE
		SYNTAX    INTEGER
		ACCESS    read-only
		STATUS    mandatory
		DESCRIPTION " "
		::= { restChannelEntry 13 }

restChannelPath 	OBJECT-TYPE
		SYNTAX  OCTET STRING (SIZE (0..85))
		ACCESS  read-only
		STATUS  deprecated
		DESCRIPTION "DEPRECATED 2.0.1
			    For TDM and subrate channels, each hop of
			    the path is indicates using three bytes.
			    The first two bytes are the node number.
			    The most significant bit of the first byte
			    of the node number will be set to one if
			    the channel is connected at a subrate speed
			    and the node contains an SGM. The third
			    byte identifies the INL that the channel
			    passes through.

			    For packet channels, each hop of the path
			    is indicated using five bytes. The first
			    two bytes are the node number. The third
			    and fourth bytes are the nest and slot
			    numbers, respectively, of the FSM that this
			    packet channel passes through. The fifth
			    number identifies the INL that the channel
			    passes through."
		::= { restChannelEntry 14 }


restChannelRouteQuality 	OBJECT-TYPE
		SYNTAX    INTEGER {
                                   asSpecified(57),
                                   overriden(56)
                                   }
		ACCESS    read-only
		STATUS    mandatory
		DESCRIPTION " "
		::= { restChannelEntry 15 }

restChannelConnectTime 	OBJECT-TYPE
		SYNTAX    INTEGER
		ACCESS    read-only
		STATUS    mandatory
		DESCRIPTION "Value is number of seconds since midnight
			January 1, 1970, GMT."
		::= { restChannelEntry 16 }

restChannelRetryCounter 	OBJECT-TYPE
		SYNTAX    INTEGER
		ACCESS    read-only
		STATUS    mandatory
		DESCRIPTION " "
		::= { restChannelEntry 17 }

restChannelLoopbackNode 	OBJECT-TYPE
		SYNTAX    NodeAddr
		ACCESS    read-only
		STATUS    mandatory
		DESCRIPTION "If a channel is in loopback, this field
			indicates which node the channel loopback has
			been set on."
		::= { restChannelEntry 18 }

restChannelNodalSubratePath 	OBJECT-TYPE
		SYNTAX  OCTET STRING ( SIZE(0..96) )
		ACCESS  read-only
		STATUS  mandatory
		DESCRIPTION "Lists the path of a subrate channel
			within the node. The format for each segment
			is as follows:

			bytes 1-2: Node number if this is a remote
				address. If local address, this
				shall return zero.

			byte 3: Nest number of the segment.

			byte 4: Slot number of the segment.

			bytes 5-6: Port number of the segment. For
				SCFs, the most significant three
				bits will be set to 001. For
				SAFs, the most significant three
				bits will be set to 010.
				For CCFs, the most significant
				three bits will be set to 011.

			bytes 7-8: Element number of the segment.

			bytes 9-10: Module type of the segment.
				The values correspond the
				values of restSlotSWModuleType
				attribute.

			bytes 11-12: Channel phasor status. All bits
				zero indicates normal. Bit 1
				indicates the least significant
				bit in the second octet.
			
			bit 1 - receive phasor underflow
			bit 2 - receive phasor overflow
			bit 3 - receive phasor empty
			bit 4 - receive phasor full
			bit 5 - receive phasor fifo error
			bit 6-7 are reserved
			bit 8 - receive phasor not applicable
			bit 9 - transmit phasor underflow
			bit 10 - transmit phasor overflow
			bit 11 - transmit phasor empty
			bit 12 - transmit phasor full
			bit 13 - transmit phasor fifo error
			bits 14-15 are reserved
			bit 16 - transmit phasor not applicable

			If the subrate segment does not have a
			channel phasor, then the value of this
			attribute will be x8080."
		::= { restChannelEntry 19 }

restChannelDChOrigNode 	OBJECT-TYPE
		SYNTAX    NodeAddr
		ACCESS    read-only
		STATUS    mandatory
		DESCRIPTION "INTRODUCED 2.0.0

			This attribute indicates the node
			where the originating D-channel port is
			allocated.

			If a channel does not have any
			associated D-channels, then zero shall
			be returned."
		::= { restChannelEntry 20 }

restChannelDChOrigAddr 	OBJECT-TYPE
		SYNTAX	  PortAddr
		ACCESS    read-only
		STATUS    mandatory
		DESCRIPTION "INTRODUCED 2.0.0

			This attribute indicates the
			originating D-channel port address.

			If a channel does not have any
			associated D-channels, then zero shall
			be returned."
		::= { restChannelEntry 21 }

restChannelDChTermNode 	OBJECT-TYPE
		SYNTAX    NodeAddr
		ACCESS    read-only
		STATUS    mandatory
		DESCRIPTION "INTRODUCED 2.0.0

			This attribute indicates the node
			where the terminating D-channel port is
			allocated.

			If a channel does not have any
			associated D-channels, then zero shall
			be returned."
		::= { restChannelEntry 22 }

restChannelDChTermAddr 	OBJECT-TYPE
		SYNTAX	  PortAddr
		ACCESS    read-only
		STATUS    mandatory
		DESCRIPTION "INTRODUCED 2.0.0

			This attribute indicates the
			terminating D-channel port address.

			If a channel does not have any
			associated D-channels, then zero shall
			be returned."
		::= { restChannelEntry 23 }

restChannelLoopbackModAddr 	OBJECT-TYPE
		SYNTAX	  SlotAddr
		ACCESS    read-write
		STATUS    mandatory
		DESCRIPTION "INTRODUCED 2.0.0

			This attribute is a supplement to the
			restChannelDiagnostics attribute. It
			specifies the address of the module
			that implements this loopback. If set
			to 0.0, then the default loopback
			setup is implemented."
		::= { restChannelEntry 24 }

restChannelNetworkPath 	OBJECT-TYPE
		SYNTAX  OCTET STRING (SIZE (0..204))
		ACCESS  read-only
		STATUS  mandatory
		DESCRIPTION "INTRODUCED 2.0.1
			    This attribute represents all of the hops
			    of a channel's route within an ST network
			    or an ST-LINK hybrid network. The data for
			    each hop consists of 12 bytes that are
			    interpretted as follows:
			bytes 1-2: Node number.

			byte 3: Node information, bit mask
			   interpretted as follows:
			    bit 1: node has an SGM that is
			   bypassing this channel
			    bit 2: node has an LGM that is
			   bypassing this channel
			    bit 3: node is a LINK node
			    bits 4-8: unused

			byte 4: Nest number of bypass module, or
			   0 if this channel does not have a
			   bypass module in this node.
			   Currently, this will only be non-zero
			   for packet channels.

			byte 5: Slot number of bypass module, or
			   0 if this channel does not have a
			   bypass module in this node.
			   Currently, this will only be non-zero
			   for packet channels.

			byte 6: Next hop type, integer value
			   interpretted as follows:
			    0 - none (terminating node)
			    1 - INL
			    2 - LGM port (VILC)

			bytes 7-12: Next hop address. If next
			   hop type is none, then bytes 7-12
			   are all zero. If next hop type is
			   INL, then byte 7 is the INL number,
			   and bytes 8-12 are all zero. If next
			   hop type is LGM port, then bytes 7-12
			   are the LGM port address, with the
			   same format as a channel address
			   (server type, group, port, and
			   element)."
		::= { restChannelEntry 25 }


-- Frame Relay Channel Status

restPktChannelTable 	OBJECT-TYPE
		SYNTAX    SEQUENCE OF RestPktChannelEntry
		ACCESS    not-accessible
		STATUS    mandatory
		DESCRIPTION "This section of the MIB is only defined
			for frame relay channels."
		::=  { restChannel 2 }

restPktChannelEntry 	OBJECT-TYPE
		SYNTAX    RestPktChannelEntry
		ACCESS    not-accessible
		STATUS    mandatory
		DESCRIPTION " "
		INDEX { restPktChannelAddr }
		::=  { restPktChannelTable 1 }

RestPktChannelEntry      ::=  SEQUENCE {
                         restPktChannelAddr
                                ChannelAddr,
                         restPktChannelDiagnostics
                                INTEGER,
                         restPktChannelTestGenStatus
                                INTEGER,
                         restPktChannelTestGenFrSent
                                INTEGER,
                         restPktChannelTestGenFrRcvOK
                                INTEGER,
                         restPktChannelTestGenFrRcvErr
                                INTEGER,
                         restPktChannelTestGenFrTimeOut
                                INTEGER,
                         restPktChannelPingStatus
                                INTEGER,
                         restPktChannelPingNumTimes
                                INTEGER,
                         restPktChannelPingNumRemaining
                                INTEGER,
			 restPktChannelCommStatus
				INTEGER
			 }

restPktChannelAddr 	OBJECT-TYPE
		SYNTAX   ChannelAddr
		ACCESS   read-only
		STATUS   mandatory
		DESCRIPTION " "
		::= { restPktChannelEntry 1 }

restPktChannelDiagnostics 	OBJECT-TYPE
		SYNTAX   INTEGER {
                                   enablePktTestGenLocal(11),
                                   enablePktTestGenRemote(12),
                                   disablePktTestGen(13),
				   disablePktPing(15)
			}
		ACCESS   write-only
		STATUS   mandatory
		DESCRIPTION "For enable packet test generator commands
			(local and remote), the channel should be put
			into loopback first using the setLoopback
			command in restChannelDiagnostics. The frame
			server will prepare the test packet, send it,
			and monitor the receiving results. It will keep
			statistics about the frames sent, frames
			received OK, frames received with errors, and
			frames that timed out.

			The disable packet test generator command will
			not clear the loopback on the channel, if one
			was initiated. The loopback needs to be cleared
			using restChannelDiagnostics.

			The disable packet ping command will stop the
			ping that was enabled using the attribute
			restPktChannelPingNumTimes."
		::= { restPktChannelEntry 2 }

restPktChannelTestGenStatus 	OBJECT-TYPE
		SYNTAX    INTEGER {
                                        activeLocal(44),
                                        activeRemote(45),
                                        inactive(46)
                                        }
		ACCESS    read-only
		STATUS    mandatory
		DESCRIPTION "Specifies whether a test generator is
			currently active on this channel, and if so,
			whether it is local or remote."
		::= { restPktChannelEntry 3 }

restPktChannelTestGenFrSent 	OBJECT-TYPE
		SYNTAX    INTEGER
		ACCESS    read-only
		STATUS    mandatory
		DESCRIPTION "Number of test generator frames sent."
		::= { restPktChannelEntry 4 }

restPktChannelTestGenFrRcvOK 	OBJECT-TYPE
		SYNTAX    INTEGER
		ACCESS    read-only
		STATUS    mandatory
		DESCRIPTION "Number of test generator frames received
			without any errors."
		::= { restPktChannelEntry 5 }

restPktChannelTestGenFrRcvErr 	OBJECT-TYPE
		SYNTAX    INTEGER
		ACCESS    read-only
		STATUS    mandatory
		DESCRIPTION "Number of test generator frames received
			with at least one error."
		::= { restPktChannelEntry 6 }

restPktChannelTestGenFrTimeOut 	OBJECT-TYPE
		SYNTAX    INTEGER
		ACCESS    read-only
		STATUS    mandatory
		DESCRIPTION "Number of test generator frames sent that
			were not received."
		::= { restPktChannelEntry 7 }

restPktChannelPingStatus 	OBJECT-TYPE
		SYNTAX    INTEGER {
			   active(1),
			   inactive(2)
                                   }
		ACCESS    read-only
		STATUS    mandatory
		DESCRIPTION "Specifies whether the channel is sending
			ping messages or not."
		::= { restPktChannelEntry 8 }

restPktChannelPingNumTimes 	OBJECT-TYPE
		SYNTAX    INTEGER (0..255)
		ACCESS    write-only
		STATUS    mandatory
		DESCRIPTION "Sets the number of times that the ping
			message should be sent on the frame relay
			channel, and enables the ping. The packet ping
			command is used to collect delay and congestion
			information on the packet channel without
			putting the channel into loopback.

			If zero is specified, then the server module
			will send ping messages until explicitly
			stopped using the disablePktPing command in
			restPktChannelDiagnostics.

			The restPktChPingTable section of the MIB
			supplies results of the ping on a per-hop basis.

			If ping is already enabled on this channel when
			this attribute is set, it will be ignored even
			though the command will return successfully."
		::= { restPktChannelEntry 9 }

restPktChannelPingNumRemaining 	OBJECT-TYPE
		SYNTAX    INTEGER (0..255)
		ACCESS    read-only
		STATUS    mandatory
		DESCRIPTION "Number of times that the ping message the
			ping message still has to be sent, when ping is
			active. If ping is inactive, or if the user
			requested the ping to continue until explicitly
			stopped, then this attribute will return zero."
		::= { restPktChannelEntry 10 }

restPktChannelCommStatus 	OBJECT-TYPE
		SYNTAX  INTEGER {
			active(1),
			inactive(2),
			notApplicable(255)
			}
		ACCESS  read-only
		STATUS  mandatory
		DESCRIPTION "INTRODUCED 2.0.0

			This attribute indicates the status of the
			communication via this packet channel.

			It will return notApplicable for frame relay
			channels on FSM ports."
		::= { restPktChannelEntry 11 }


-- Frame Relay Channel Ping Status

restPktChPingTable 	OBJECT-TYPE
		SYNTAX    SEQUENCE OF RestPktChPingEntry
		ACCESS    not-accessible
		STATUS    mandatory
		DESCRIPTION "This section of the MIB is only defined
			for frame relay channels."
		::=  { restChannel 3 }

restPktChPingEntry 	OBJECT-TYPE
		SYNTAX    RestPktChPingEntry
		ACCESS    not-accessible
		STATUS    mandatory
		DESCRIPTION " "
		INDEX { restPktChPingAddr,
			restPktChPingHopNumber }
		::=  { restPktChPingTable 1 }

RestPktChPingEntry      ::=  SEQUENCE {
                         restPktChPingAddr
                                ChannelAddr,
                         restPktChPingHopNumber
                                INTEGER,
                         restPktChPingDelay
                                INTEGER,
                         restPktChPingOrigTermCong
                                INTEGER,
                         restPktChPingTermOrigCong
                                INTEGER
			 }

restPktChPingAddr 	OBJECT-TYPE
		SYNTAX   ChannelAddr
		ACCESS   read-only
		STATUS   mandatory
		DESCRIPTION " "
		::= { restPktChPingEntry 1 }

restPktChPingHopNumber 	OBJECT-TYPE
		SYNTAX   INTEGER (1..17)
		ACCESS   read-only
		STATUS   mandatory
		DESCRIPTION "Identifies what hop of the channel path
			this information applies to. The first hop
			originates from the node that the ping was
			initiated on (this node will be referred to as
			the originating node). The last hop ends on the
			node where the opposite end of the channel is
			(this node will be referred to as the
			terminating node). The field restChannelPath
			can be used to identify where each hop is in
			the network."
		::= { restPktChPingEntry 2 }

restPktChPingDelay 	OBJECT-TYPE
		SYNTAX   INTEGER
		ACCESS   read-only
		STATUS   mandatory
		DESCRIPTION "Indicates the round trip delay in units
			of 10 millseconds between this node and the
			terminating node is."
		::= { restPktChPingEntry 3 }

restPktChPingOrigTermCong 	OBJECT-TYPE
		SYNTAX   INTEGER {
			normal(1),
			yellow(2),
			red(3),
			critical(4)
			  }
		ACCESS   read-only
		STATUS   mandatory
		DESCRIPTION " "
		::= { restPktChPingEntry 4 }

restPktChPingTermOrigCong 	OBJECT-TYPE
		SYNTAX   INTEGER {
			normal(1),
			yellow(2),
			red(3),
			critical(4)
			  }
		ACCESS   read-only
		STATUS   mandatory
		DESCRIPTION " "
		::= { restPktChPingEntry 5 }


-- Ad10 Status MIB

restAd10Port             OBJECT IDENTIFIER ::=    { reStatus 10 }


-- Ad10 AGM Port Status

restAd10AgmPortTable 	OBJECT-TYPE
		SYNTAX    SEQUENCE OF RestAd10AgmPortEntry
		ACCESS    not-accessible
		STATUS    mandatory
		DESCRIPTION " "
		::=  { restAd10Port 1 }

restAd10AgmPortEntry 	OBJECT-TYPE
		SYNTAX    RestAd10AgmPortEntry
		ACCESS    not-accessible
		STATUS    mandatory
		DESCRIPTION " "
		INDEX { restAd10AgmPortAddr }
		::=  { restAd10AgmPortTable 1 }

RestAd10AgmPortEntry       ::=  SEQUENCE {
                         restAd10AgmPortAddr
                                   PortAddr,
			 restAd10AgmPortControl
				   INTEGER,
                         restAd10AgmPortCpSpeed
                                   INTEGER,
                         restAd10AgmPortCpTermType
                                   INTEGER,
			 restAd10AgmPortCpMode
				   INTEGER,
			 restAd10Date
				   DisplayString,
			 restAd10Time
				   DisplayString,
                         restAd10VersionLabel
                                   DisplayString,
                         restAd10UnitSerialNumberStr
                                   DisplayString,
                         restAd10UnitType
                                   INTEGER,
			 restAd10HWConfig
				   OCTET STRING,
			 restAd10NetworkInterface
				   INTEGER,
			 restAd10NetworkClockConf
				   INTEGER,
			 restAd10TdmMuxSwitchStatus
				   INTEGER,
			 restAd10SoftloadStatus
				   INTEGER,
			 restAd10SoftloadFileSize
				   INTEGER,
			 restAd10SoftloadTransferred
				   INTEGER,
                         restAd10SoftloadStartTime
				   INTEGER,
			 restAd10SoftloadCompletionTime
				   INTEGER
			 }


restAd10AgmPortAddr 	OBJECT-TYPE
		SYNTAX    PortAddr
		ACCESS    read-only
		STATUS    mandatory
		DESCRIPTION " "
		::= { restAd10AgmPortEntry 1 }

restAd10AgmPortControl 	OBJECT-TYPE
		SYNTAX INTEGER {
			tdmMuxSwitch(1),
			unitReset(2),
			updateHw(3)
			}
		ACCESS write-only
		STATUS mandatory
		DESCRIPTION "tdmMuxSwitch will force AD-10
			port configured speeds to match ST values.
			It will then initiate a TDM mux switch on
			the AD-10.

			unitReset will reset the AD-10 unit.

			updateHw will update the remote AD-10 unit
			internal reference hardware configuration
			record. Use this to clear the condition when
			an AD-10 reference hardware alarm is generated."
		::= { restAd10AgmPortEntry 2 }


-- Ad10 CP Port Config

restAd10AgmPortCpSpeed 	OBJECT-TYPE
		SYNTAX    INTEGER {
                                     a300(1),
                                     a1200(2),
                                     a2400(3),
                                     a9600(4)
                                     }
		ACCESS    read-only
		STATUS    mandatory
		DESCRIPTION "Console terminal baud rate"
		::= { restAd10AgmPortEntry 3 }

restAd10AgmPortCpTermType 	OBJECT-TYPE
		SYNTAX    INTEGER {
				ascii(1),
				vt100(2)
                                        }
		ACCESS    read-only
		STATUS    mandatory
		DESCRIPTION "Console terminal type"
		::= { restAd10AgmPortEntry 4 }


restAd10AgmPortCpMode 	OBJECT-TYPE
		SYNTAX INTEGER {
			enabled(2),
			disabled(1)
			}
		ACCESS read-write
		STATUS mandatory
		DESCRIPTION "Console pass through mode"
		::= { restAd10AgmPortEntry 5 }


-- Ad10 Status Information

restAd10Date 	OBJECT-TYPE
		SYNTAX    DisplayString (SIZE(0..10))
		ACCESS    read-write
		STATUS    mandatory
		DESCRIPTION "Format is mm/dd/yyyy"
		::= { restAd10AgmPortEntry 6 }

restAd10Time 	OBJECT-TYPE
		SYNTAX    DisplayString (SIZE(0..8))
		ACCESS    read-write
		STATUS    mandatory
		DESCRIPTION "Format is hh:mm:ss"
		::= { restAd10AgmPortEntry 7 }

restAd10VersionLabel 	OBJECT-TYPE
		SYNTAX    DisplayString (SIZE(20))
		ACCESS    read-only
		STATUS    mandatory
		DESCRIPTION "Format: Vxx.yy DATE:mm-dd-yy
			The date is a date stamp on the version number."
		::= { restAd10AgmPortEntry 8 }

restAd10UnitSerialNumberStr 	OBJECT-TYPE
		SYNTAX    DisplayString (SIZE(1..6))
		ACCESS    read-only
		STATUS    mandatory
		DESCRIPTION " "
		::= { restAd10AgmPortEntry 9 }

restAd10UnitType 	OBJECT-TYPE
		SYNTAX    INTEGER {
			   atixSt50(6),
			   accessPlus(7),
			   ad10(8),
			   universalType(9)
			 	   }
		ACCESS    read-only
		STATUS    mandatory
		DESCRIPTION " "
		::= { restAd10AgmPortEntry 10 }

restAd10HWConfig 	OBJECT-TYPE
		SYNTAX     OCTET STRING (SIZE (384))
		ACCESS     read-only
		STATUS     mandatory
		DESCRIPTION "Ad10 hardware configuration map.
			For each port on the Ad10 , there is a one-byte
			port type field followed by a five-byte user port
			address. The port type field may have the following
			values:
			0x01: control processor
			0x10: TDM composite
			0x11: packet band
			0x20: IOP data port
			0x22: hybrid data module (HDM) data port
			0x23: expansion data module (EDM) data port
			0x32: VF51-64K VFAX
			0x40: V.35/RS422 network port
			0x41 V.11 network port
			The user port address will be an ASCII string
			displaying the port address as seen from the
			back panel of the Ad10. The index for the table
			is a virtual port address, range 1 to 64."
		::= { restAd10AgmPortEntry 11 }


-- Ad10 Network Port Status Information

restAd10NetworkInterface 	OBJECT-TYPE
		SYNTAX INTEGER {
			rs232(1),
			v35(2),
			rs422(3),
			v11(4)
			}
		ACCESS read-only
		STATUS mandatory
		DESCRIPTION "Ad10 network port interface
			type"
		::= { restAd10AgmPortEntry 12 }

restAd10NetworkClockConf 	OBJECT-TYPE
		SYNTAX INTEGER {
			external(1),
			slave(2),
			internal(3)
			}
		ACCESS read-only
		STATUS mandatory
		DESCRIPTION "Ad10 network port clock
			configuration"
		::= { restAd10AgmPortEntry 13 }


-- Ad10 Configuration Download Status Information

restAd10TdmMuxSwitchStatus 	OBJECT-TYPE
		SYNTAX  INTEGER {
			active(1),
			inactive(2)
			}
		ACCESS  read-only
		STATUS mandatory
		DESCRIPTION     "Status of the
			tdmMuxSwitch command."
		::= { restAd10AgmPortEntry 14 }


-- Ad10 Softload Status Information

restAd10SoftloadStatus 	OBJECT-TYPE
		SYNTAX	INTEGER {
			softloading(66),
			success(65),
			idle(36),
			responseTimeout(109),
			resetTimeout(110),
			infoIncorrect(111),
			ad10LinkDown(112)
			}
		ACCESS	read-only
		STATUS	mandatory
		DESCRIPTION 	"AD10 current
			softload status."
		::= { restAd10AgmPortEntry 15 }

restAd10SoftloadFileSize 	OBJECT-TYPE
		SYNTAX  INTEGER
		ACCESS  read-only
		STATUS mandatory
		DESCRIPTION     "Total number of
			bytes to be softloaded.
			If no softloading is in
			progress returns zero."
		::= { restAd10AgmPortEntry 16 }

restAd10SoftloadTransferred 	OBJECT-TYPE
		SYNTAX  INTEGER
		ACCESS  read-only
		STATUS mandatory
		DESCRIPTION     "Number of bytes
			that have been transferred
			currently. If no softloading
			is in progress returns zero."
		::= { restAd10AgmPortEntry 17 }

restAd10SoftloadStartTime 	OBJECT-TYPE
		SYNTAX  INTEGER
		ACCESS  read-only
		STATUS mandatory
		DESCRIPTION     "Value is number of seconds
			since midnight January 1, 1970, GMT.
			Value of 0 means not applicable."
		::= { restAd10AgmPortEntry 18 }

restAd10SoftloadCompletionTime 	OBJECT-TYPE
		SYNTAX  INTEGER
		ACCESS  read-only
		STATUS mandatory
		DESCRIPTION     "Value is number of seconds
			since midnight January 1, 1970, GMT.
			Value of 0 means not applicable."
		::= { restAd10AgmPortEntry 19 }

-- Ad10 Data Port Status

restAd10DataPortTable 	OBJECT-TYPE
		SYNTAX  SEQUENCE OF RestAd10DataPortEntry
		ACCESS  not-accessible
		STATUS  mandatory
		DESCRIPTION " "
		::=  { restAd10Port 2 }

restAd10DataPortEntry 	OBJECT-TYPE
		SYNTAX  RestAd10DataPortEntry
		ACCESS  not-accessible
		STATUS  mandatory
		DESCRIPTION " "
		INDEX { restAd10DataPortAddr }
		::=  { restAd10DataPortTable 1 }

RestAd10DataPortEntry           ::=  SEQUENCE {
			restAd10DataPortAddr
				Ad10PortAddr,
			restAd10DataPortDiagnostics
				INTEGER,
			restAd10DataPortMode
				INTEGER,
			restAd10DataPortIntfType
				INTEGER,
			restAd10DataPortClockMode
				INTEGER,
			restAd10DataPortClockRate
				INTEGER,
			restAd10DataPortCtsOOS
				INTEGER,
			restAd10DataPortCtsSig
				INTEGER,
			restAd10DataPortDcdOOS
				INTEGER,
			restAd10DataPortDcdSig
				INTEGER,
			restAd10DataPortDsrOOS
				INTEGER,
			restAd10DataPortDsrSig
				INTEGER,
			restAd10DataPortRtsLoopDelay
				INTEGER,
			restAd10DataPortDtrLoopDelay
				INTEGER,
			restAd10DataPortAsyncDataBits
				INTEGER,
			restAd10DataPortAsyncStopBits
				INTEGER,
			restAd10DataPortAsyncParity
				INTEGER,
			restAd10DataPortAsyncSubMode
				INTEGER,
			restAd10DataPortAsyncSubChar
				INTEGER,
			restAd10DataPortPktFlowControl
				INTEGER,
			restAd10DataPortPktTxFlow
				INTEGER,
			restAd10DataPortPktRxFlow
				INTEGER,
			restAd10DataPortPktBuildTimeOut
				INTEGER,
			restAd10DataPortPktRxThreshold
				INTEGER,
			restAd10DataPortPktTxThreshold
				INTEGER,
			restAd10DataPortPktMinRxFrag
				INTEGER,
			restAd10DataPortBiSyncCharType
				INTEGER,
			restAd10DataPortBiSyncParity
				INTEGER,
			restAd10DataPortBiSyncIdleFill
				INTEGER,
			restAd10DataPortBiSyncMinPair
				INTEGER,
			restAd10DataPortBiSyncSyncChar
				INTEGER,
			restAd10DataPortBiSyncPadChar
				INTEGER,
			restAd10DataPortHdlcCrcType
				INTEGER,
			restAd10DataPortHdlcLineCode
				INTEGER,
			restAd10DataPortHdlcIdleFill
				INTEGER,
			restAd10DataPortHdlcMinFlags
				INTEGER,
			restAd10DataPortModemSigInfo
				OCTET STRING,
			restAd10DataPortVcMapDlci
				INTEGER,
			restAd10DataPortVcMapCir
				INTEGER,
			restAd10DataPortTDMDataRate
				INTEGER,
			restAd10DataPortType
				INTEGER,
			restAd10DataPortDtrFlLpDlyDelta
				INTEGER,
			restAd10DataPortRtsFlLpDlyDelta
				INTEGER
			}

restAd10DataPortAddr 	OBJECT-TYPE
		SYNTAX  Ad10PortAddr
		ACCESS  read-only
		STATUS  mandatory
		DESCRIPTION " "
		::= { restAd10DataPortEntry 1 }

restAd10DataPortDiagnostics 	OBJECT-TYPE
		SYNTAX    INTEGER {
			  insert(4),
			   	  remove(5),
			   	  reset(6)
			   	  }
		ACCESS    write-only
		STATUS    mandatory
		DESCRIPTION "Insert will download the new MIB
			to the module. It will not synchronize
			any configuration parameters between
			the AD-10 and the NCP.

			Remove will disconnect the connected
			channel. It will not erase the
			configuration MIB.

			Reset in essence is a remove following
			by an insert. It will also cause the
			AGM to force the AD-10 data port speed
			and type to match the values set on the
			NCP."
		::= { restAd10DataPortEntry 2 }

restAd10DataPortMode 	OBJECT-TYPE
		SYNTAX  INTEGER {
			offline(1),
			online(2),
			disableDiagnostics(3),
			bertTowardSubscriber(4),
			bertTowardNetwork(5),
			loopSubscriber(6),
			loopNetwork(7)
			}
		ACCESS  read-write
		STATUS  mandatory
		DESCRIPTION "Online/offline and diagnostic mode"
		::= { restAd10DataPortEntry 3 }

restAd10DataPortIntfType 	OBJECT-TYPE
		SYNTAX  INTEGER {
			rs232(1),
			v35(2),
			rs422(3),
			v11(4)
			}
		ACCESS  read-only
		STATUS  mandatory
		DESCRIPTION "Interface type"
		::= { restAd10DataPortEntry 4 }

restAd10DataPortClockMode 	OBJECT-TYPE
		SYNTAX  INTEGER {
			notApplicable(1),
			internal(2),
			external(3),
			txExternal(4),
			derived(5)
			}
		ACCESS  read-write
		STATUS  mandatory
		DESCRIPTION "Clock mode. Only TDM sync can use
			a value of derived. If port is async,
			notApplicable will be returned. The
			notApplicable value should not be set."
		::= { restAd10DataPortEntry 5 }

restAd10DataPortClockRate 	OBJECT-TYPE
		SYNTAX  INTEGER (0..20480)
		ACCESS  read-write
		STATUS  mandatory
		DESCRIPTION "Clock rate, in units of 100 bps."
		::= { restAd10DataPortEntry 6 }

restAd10DataPortCtsOOS 	OBJECT-TYPE
		SYNTAX  INTEGER {
			forceOff(1),
			forceOn(2),
			freeze(3)
			}
		ACCESS  read-write
		STATUS  mandatory
		DESCRIPTION "CTS out of service"
		::= { restAd10DataPortEntry 7 }

restAd10DataPortCtsSig 	OBJECT-TYPE
		SYNTAX  INTEGER {
			forceOff(1),
			forceOn(2),
			loopLocalRts(3),
			loopLocalDtr(4),
			rts(5),
			dtr(6),
			rtsAndDtr(7),
			rtsOrDtr(8)
			}
		ACCESS  read-write
		STATUS  mandatory
		DESCRIPTION "CTS setup"
		::= { restAd10DataPortEntry 8 }

restAd10DataPortDcdOOS 	OBJECT-TYPE
		SYNTAX INTEGER {
			forceOff(1),
			forceOn(2),
			freeze(3)
			}
		ACCESS read-write
		STATUS mandatory
		DESCRIPTION "DCD out of service"
		::= { restAd10DataPortEntry 9 }

restAd10DataPortDcdSig 	OBJECT-TYPE
		SYNTAX  INTEGER {
			forceOff(1),
			forceOn(2),
			loopLocalRts(3),
			loopLocalDtr(4),
			rts(5),
			dtr(6),
			rtsAndDtr(7),
			rtsOrDtr(8)
			}
		ACCESS  read-write
		STATUS  mandatory
		DESCRIPTION "DCD setup"
		::= { restAd10DataPortEntry 10 }

restAd10DataPortDsrOOS 	OBJECT-TYPE
		SYNTAX  INTEGER {
			forceOff(1),
			forceOn(2),
			freeze(3)
			}
		ACCESS  read-write
		STATUS  mandatory
		DESCRIPTION "DSR out of service"
		::= { restAd10DataPortEntry 11 }

restAd10DataPortDsrSig 	OBJECT-TYPE
		SYNTAX  INTEGER {
			forceOff(1),
			forceOn(2),
			loopLocalRts(3),
			loopLocalDtr(4),
			rts(5),
			dtr(6),
			rtsAndDtr(7),
			rtsOrDtr(8)
			}
		ACCESS  read-write
		STATUS  mandatory
		DESCRIPTION "DSR setup"
		::= { restAd10DataPortEntry 12 }

restAd10DataPortRtsLoopDelay 	OBJECT-TYPE
		SYNTAX  INTEGER (0..65535)
		ACCESS  read-write
		STATUS  mandatory
		DESCRIPTION "RTS loopback delay number in
			units of milli-seconds"
		::= { restAd10DataPortEntry 13 }

restAd10DataPortDtrLoopDelay 	OBJECT-TYPE
		SYNTAX  INTEGER (0..65535)
		ACCESS  read-write
		STATUS  mandatory
		DESCRIPTION "DTR loopback delay number in
			units of milli-seconds"
		::= { restAd10DataPortEntry 14 }

restAd10DataPortAsyncDataBits 	OBJECT-TYPE
		SYNTAX  INTEGER {
			b5bit(1),
			b6bit(2),
			b7bit(3),
			b8bit(4)
			}
		ACCESS  read-write
		STATUS  mandatory
		DESCRIPTION "Asynchronous data bits
			configuration"
		::= { restAd10DataPortEntry 15 }

restAd10DataPortAsyncStopBits 	OBJECT-TYPE
		SYNTAX  INTEGER {
			one(1),
			oneAndHalf(2),
			two(3)
			}
		ACCESS  read-write
		STATUS  mandatory
		DESCRIPTION "Asynchronous stop bits
			configuration"
		::= { restAd10DataPortEntry 16 }

restAd10DataPortAsyncParity 	OBJECT-TYPE
		SYNTAX  INTEGER {
			none(1),
			even(2),
			odd(3)
			}
		ACCESS  read-write
		STATUS  mandatory
		DESCRIPTION "Asynchronous parity configuration"
		::= { restAd10DataPortEntry 17 }

restAd10DataPortAsyncSubMode 	OBJECT-TYPE
		SYNTAX  INTEGER {
			enable(2),
			disable(1)
			}
		ACCESS  read-write
		STATUS  mandatory
		DESCRIPTION "Asynchronous parity error
			substitute mode"
		::= { restAd10DataPortEntry 18 }

restAd10DataPortAsyncSubChar 	OBJECT-TYPE
		SYNTAX  INTEGER (0..255)
		ACCESS  read-write
		STATUS  mandatory
		DESCRIPTION "Asynchronous parity error
			substitute character"
		::= { restAd10DataPortEntry 19 }

restAd10DataPortPktFlowControl 	OBJECT-TYPE
		SYNTAX  INTEGER {
			ctsDtr(1),
			xonXoff(2)
			}
		ACCESS  read-write
		STATUS  mandatory
		DESCRIPTION "Flow control mechanism (for
			async only)"
		::= { restAd10DataPortEntry 20 }

restAd10DataPortPktTxFlow 	OBJECT-TYPE
		SYNTAX  INTEGER {
			enable(2),
			disable(1)
			}
		ACCESS  read-write
		STATUS  mandatory
		DESCRIPTION "Transmit flow"
		::= { restAd10DataPortEntry 21 }

restAd10DataPortPktRxFlow 	OBJECT-TYPE
		SYNTAX  INTEGER {
			enable(2),
			disable(1)
			}
		ACCESS  read-write
		STATUS  mandatory
		DESCRIPTION "Receive flow"
		::= { restAd10DataPortEntry 22 }

restAd10DataPortPktBuildTimeOut 	OBJECT-TYPE
		SYNTAX  INTEGER (1..500)
		ACCESS  read-write
		STATUS  mandatory
		DESCRIPTION "Build packet time out (in units of
			10 milliseconds) (for async only)"
		::= { restAd10DataPortEntry 23 }

restAd10DataPortPktRxThreshold 	OBJECT-TYPE
		SYNTAX  INTEGER (0..100)
		ACCESS  read-write
		STATUS  mandatory
		DESCRIPTION "Receive threshold. Receive buffer
			capacity beyond the threshold, the flow
			control signal will send toward the
			network."
		::= { restAd10DataPortEntry 24 }

restAd10DataPortPktTxThreshold 	OBJECT-TYPE
		SYNTAX  INTEGER (0..100)
		ACCESS  read-write
		STATUS  mandatory
		DESCRIPTION "Transmit threshold. Transmit buffer
			capacity beyond the threshold, the flow
			control signal will send toward the
			network."
		::= { restAd10DataPortEntry 25 }

restAd10DataPortPktMinRxFrag 	OBJECT-TYPE
		SYNTAX  INTEGER (1..200)
		ACCESS  read-write
		STATUS  mandatory
		DESCRIPTION "Minimum receive fragment threshold.
			Specifies the minimum number received
			fragments of packet from the network
			before sending toward DTE."
		::= { restAd10DataPortEntry 26 }

restAd10DataPortBiSyncCharType 	OBJECT-TYPE
		SYNTAX  INTEGER {
			ascii7(1),
			ascii8(2),
			ebcdic(3)
			}
		ACCESS  read-write
		STATUS  mandatory
		DESCRIPTION "Bisync character type"
		::= { restAd10DataPortEntry 27 }

restAd10DataPortBiSyncParity 	OBJECT-TYPE
		SYNTAX  INTEGER {
			high(1),
			low(2),
			even(3),
			odd(4),
			notApplicable(255)
			}
		ACCESS  read-write
		STATUS  mandatory
		DESCRIPTION "Bisync parity"
		::= { restAd10DataPortEntry 28 }

restAd10DataPortBiSyncIdleFill 	OBJECT-TYPE
		SYNTAX  INTEGER {
			idle(1),
			sync(2)
			}
		ACCESS  read-write
		STATUS  mandatory
		DESCRIPTION "Bisync idle fill"
		::= { restAd10DataPortEntry 29 }

restAd10DataPortBiSyncMinPair 	OBJECT-TYPE
		SYNTAX  INTEGER (1..16)
		ACCESS  read-write
		STATUS  mandatory
		DESCRIPTION "Bisync minimum sync pair.
			Minimum number of sync character pair
			that precedes a packet."
		::= { restAd10DataPortEntry 30 }

restAd10DataPortBiSyncSyncChar 	OBJECT-TYPE
		SYNTAX  INTEGER (0..255)
		ACCESS  read-write
		STATUS  mandatory
		DESCRIPTION "Bisync sync character.
			Default is 32h for EBCDIC and 16h for
			ASCII 7 and 8."
		::= { restAd10DataPortEntry 31 }

restAd10DataPortBiSyncPadChar 	OBJECT-TYPE
		SYNTAX  INTEGER (0..255)
		ACCESS  read-write
		STATUS  mandatory
		DESCRIPTION "Bisync pad character.
			Default is 0xff for EBCDIC and ASCII 8
			and 0x7f for ASCII 7."
		::= { restAd10DataPortEntry 32 }

restAd10DataPortHdlcCrcType 	OBJECT-TYPE
		SYNTAX  INTEGER {
			crc16(1),
			crc32(2)
			}
		ACCESS  read-write
		STATUS  mandatory
		DESCRIPTION "CRC type"
		::= { restAd10DataPortEntry 33 }

restAd10DataPortHdlcLineCode 	OBJECT-TYPE
		SYNTAX  INTEGER {
			nrz(1),
			nrzi(2)
			}
		ACCESS  read-write
		STATUS  mandatory
		DESCRIPTION "Line code"
		::= { restAd10DataPortEntry 34 }

restAd10DataPortHdlcIdleFill 	OBJECT-TYPE
		SYNTAX  INTEGER {
			idle(1),
			flag(2)
			}
		ACCESS  read-write
		STATUS  mandatory
		DESCRIPTION "Idle fill"
		::= { restAd10DataPortEntry 35 }

restAd10DataPortHdlcMinFlags 	OBJECT-TYPE
		SYNTAX  INTEGER (1..16)
		ACCESS  read-write
		STATUS  mandatory
		DESCRIPTION "Minimum flags between frames"
		::= { restAd10DataPortEntry 36 }

restAd10DataPortModemSigInfo 	OBJECT-TYPE
		SYNTAX  OCTET STRING (SIZE (1))
		ACCESS  read-only
		STATUS  mandatory
		DESCRIPTION "Modem signal info. Bit map.
			bit 1 (lsb) - RTS
			bit 2 - DTR
			bit 3 - CTS
			bit 4 - DCD
			bit 5 - DSR"
		::= { restAd10DataPortEntry 37 }

restAd10DataPortVcMapDlci 	OBJECT-TYPE
		SYNTAX  INTEGER (0..1023)
		ACCESS  read-write
		STATUS  mandatory
		DESCRIPTION " "
		::= { restAd10DataPortEntry 38 }

restAd10DataPortVcMapCir 	OBJECT-TYPE
		SYNTAX  INTEGER (1..1280)
		ACCESS  read-write
		STATUS  mandatory
		DESCRIPTION "Committed information rate
			(in units of 100 bps)"
		::= { restAd10DataPortEntry 39 }

restAd10DataPortTDMDataRate 	OBJECT-TYPE
		SYNTAX  INTEGER {
			b1200(9), b2400(18),
			b4800(36), b7200(54),
			b9600(72), b12000(90),
			b14400(108), b16000(120),
			b16800(126), b19200(144),
			b24000(180), b28800(216),
			b32000(240), b38400(288),
			b48000(360), b56000(420),
			disabled(65535)
			}
		ACCESS  read-only
		STATUS  mandatory
		DESCRIPTION "This attribute must match the
			value in recfAd10DataPortTDMDataRate.
			If it does not match, the reset AD-10
			data port command can be used to
			synchronize them."
		::= { restAd10DataPortEntry 40 }

restAd10DataPortType 	OBJECT-TYPE
		SYNTAX  INTEGER {
			tdm-sync(1),
			stat-mux-async(2),
			bisync(3),
			hdlc(4)
			}
		ACCESS  read-only
		STATUS  mandatory
		DESCRIPTION "This attribute must match the
			value in recfAd10DataPortType. If it
			does not match, the reset AD-10 data
			port command can be used to synchronize
			them."
		::= { restAd10DataPortEntry 41 }

restAd10DataPortDtrFlLpDlyDelta 	OBJECT-TYPE
		SYNTAX  INTEGER (0..1000)
		ACCESS  read-write
		STATUS  mandatory
		DESCRIPTION "INTRODUCED 1.2.3

			Dtr falling edge (going from high
			to low) delay is this attribute +
			restAd10DataPortDtrLoopDelay"
		::= { restAd10DataPortEntry 42 }

restAd10DataPortRtsFlLpDlyDelta 	OBJECT-TYPE
		SYNTAX  INTEGER (0..1000)
		ACCESS  read-write
		STATUS  mandatory
		DESCRIPTION "INTRODUCED 1.2.3

			Rts falling edge (going from high
			to low) delay is this attribute +
			restAd10DataPortRtsLoopDelay"
		::= { restAd10DataPortEntry 43 }


-- Ad10 Voice Port Status

restAd10VoicePortTable 	OBJECT-TYPE
		SYNTAX    SEQUENCE OF RestAd10VoicePortEntry
		ACCESS    not-accessible
		STATUS    mandatory
		DESCRIPTION " "
		::=  { restAd10Port 3 }

restAd10VoicePortEntry 	OBJECT-TYPE
		SYNTAX    RestAd10VoicePortEntry
		ACCESS    not-accessible
		STATUS    mandatory
		DESCRIPTION " "
		INDEX { restAd10VoicePortAddr }
		::=  { restAd10VoicePortTable 1 }

RestAd10VoicePortEntry     ::=  SEQUENCE {
                         restAd10VoicePortAddr
                                   Ad10PortAddr,
			 restAd10VoicePortDiagnostics
			   INTEGER,
			 restAd10VoicePortMode
                                   INTEGER,
                         restAd10VoicePortInterface
                                   INTEGER,
                         restAd10VoicePortEchoCancel
                                   INTEGER,
                         restAd10VoicePortToneMode
                                   INTEGER,
                         restAd10VoicePortNonLinear
                                   INTEGER,
                         restAd10VoicePortEMPolarity
                                   INTEGER,
                         restAd10VoicePortUncfgCktSig
                                   INTEGER,
                         restAd10VoicePortHookStateRx
                                   INTEGER,
                         restAd10VoicePortHookStateTx
                                   INTEGER,
                         restAd10VoicePortTxLevel
                                   INTEGER,
                         restAd10VoicePortRcvLevel
                                   INTEGER,
			 restAd10VoicePortTermination
			   INTEGER,
			 restAd10VoicePortWire
			   INTEGER,
			 restAd10VoicePortAc15Dial
			   INTEGER,
			 restAd10VoicePortTelcoIntType
			   INTEGER,
			 restAd10VoicePortSpeed
			   INTEGER,
			 restAd10VoicePortCompressMode
			   INTEGER,
			 restAd10VoicePortFaxMode
			   INTEGER,
			 restAd10VoicePortOOSAudio
			   INTEGER,
			 restAd10VoicePortCelpNetSigMd
			   INTEGER,
			 restAd10VoicePortCelpNetSigSt
			   INTEGER
                         }


restAd10VoicePortAddr 	OBJECT-TYPE
		SYNTAX    Ad10PortAddr
		ACCESS    read-only
		STATUS    mandatory
		DESCRIPTION " "
		::= { restAd10VoicePortEntry 1 }

restAd10VoicePortDiagnostics 	OBJECT-TYPE
		SYNTAX    INTEGER {
			   insert(4),
			   remove(5),
			   reset(6)
			   }
		ACCESS    write-only
		STATUS    mandatory
		DESCRIPTION "Insert will download the new MIB to
			        the module. It will not synchronize any
			configuration parameters between the AD-10
			and the NCP.

			Remove will disconnect the connected channel.
			It will not erase the configuration MIB.

			Reset in essence is a remove following by an
			insert. It will also cause the AGM to force the
			AD-10 voice port speed, compression mode, and
			fax mode to match the values set on the NCP."
		::= { restAd10VoicePortEntry 2 }

restAd10VoicePortMode 	OBJECT-TYPE
		SYNTAX INTEGER {
			offline(1),
			online(2),
			disableDiagnosis(3),
			subDMW(4),
			bertTowardNetwork(5),
			loopSub(6),
			loopNet(7)
			}
		ACCESS read-write
		STATUS mandatory
		DESCRIPTION " "
		::= { restAd10VoicePortEntry 3 }

restAd10VoicePortInterface 	OBJECT-TYPE
		SYNTAX    INTEGER {
			   fxo(1),
			   fxsGndStartContRing(5),
			   fxsGndStartInterRing(6),
			   fxsLoopStartContRing(7),
			   fxsLoopStartInterRing(8),
			   emTypeI(9),
			   emTypeII(10),
			   emTypeIII(11),
			   emTypeIV(12),
			   emTypeV(13),
			   ac15(14),
			   ss5(15)
                                   }
		ACCESS    read-write
		STATUS    mandatory
		DESCRIPTION " "
		::= { restAd10VoicePortEntry 4 }

restAd10VoicePortEchoCancel 	OBJECT-TYPE
		SYNTAX    INTEGER {
			   enable(2),
			   disable(1)
                                   }
		ACCESS    read-write
		STATUS    mandatory
		DESCRIPTION " "
		::= { restAd10VoicePortEntry 5 }

restAd10VoicePortToneMode 	OBJECT-TYPE
		SYNTAX    INTEGER {
			   enable(2),
			   disable(1)
                                   }
		ACCESS    read-write
		STATUS    mandatory
		DESCRIPTION " "
		::= { restAd10VoicePortEntry 6 }

restAd10VoicePortNonLinear 	OBJECT-TYPE
		SYNTAX    INTEGER {
			   enable(2),
			   disable(1)
                                   }
		ACCESS    read-write
		STATUS    mandatory
		DESCRIPTION " "
		::= { restAd10VoicePortEntry 7 }

restAd10VoicePortEMPolarity 	OBJECT-TYPE
		SYNTAX    INTEGER {
			   reverse(1),
			   normal(2),
			   notApplicable(255)
                                   }
		ACCESS    read-write
		STATUS    mandatory
		DESCRIPTION " "
		::= { restAd10VoicePortEntry 8 }

restAd10VoicePortUncfgCktSig 	OBJECT-TYPE
		SYNTAX    INTEGER {
			   idle(1),
                                   busy(2)
                                   }
		ACCESS    read-write
		STATUS    mandatory
		DESCRIPTION " "
		::= { restAd10VoicePortEntry 9 }

restAd10VoicePortHookStateRx 	OBJECT-TYPE
		SYNTAX    INTEGER {
                                   on(1),
                                   off(2)
                                   }
		ACCESS    read-only
		STATUS    mandatory
		DESCRIPTION "Phone on/off hook status"
		::= { restAd10VoicePortEntry 10 }

restAd10VoicePortHookStateTx 	OBJECT-TYPE
		SYNTAX    INTEGER {
                                   on(1),
                                   off(2)
                                   }
		ACCESS    read-only
		STATUS    mandatory
		DESCRIPTION "Phone on/off hook status"
		::= { restAd10VoicePortEntry 11 }

restAd10VoicePortTxLevel 	OBJECT-TYPE
		SYNTAX    INTEGER (1..255)
		ACCESS    read-write
		STATUS    mandatory
		DESCRIPTION "-25.4db to +25.4db w/.2db increment"
		::= { restAd10VoicePortEntry 12 }

restAd10VoicePortRcvLevel 	OBJECT-TYPE
		SYNTAX    INTEGER (1..255)
		ACCESS    read-write
		STATUS    mandatory
		DESCRIPTION "-25.4db to +25.4db w/.2db increment"
		::= { restAd10VoicePortEntry 13 }

restAd10VoicePortTermination 	OBJECT-TYPE
		SYNTAX INTEGER {
			r600ohms(1),
			r900ohmsOrComplex(2)
			}
		ACCESS read-write
		STATUS mandatory
		DESCRIPTION " "
		::= { restAd10VoicePortEntry 14 }

restAd10VoicePortWire 	OBJECT-TYPE
		SYNTAX INTEGER {
			w4wire(1),
			w2wire(2),
			notApplicable(255)
			}
		ACCESS read-write
		STATUS mandatory
		DESCRIPTION " "
		::= { restAd10VoicePortEntry 15 }

restAd10VoicePortAc15Dial 	OBJECT-TYPE
		SYNTAX INTEGER {
			dtmf(1),
			pulse(2),
			notApplicable(255)
			}
		ACCESS read-write
		STATUS mandatory
		DESCRIPTION " "
		::= { restAd10VoicePortEntry 16 }

restAd10VoicePortTelcoIntType 	OBJECT-TYPE
		SYNTAX INTEGER {
			us(1),
			babt(2),
			austel(3)
			}
		ACCESS read-only
		STATUS mandatory
		DESCRIPTION " "
		::= { restAd10VoicePortEntry 17 }

restAd10VoicePortSpeed 	OBJECT-TYPE
		SYNTAX  INTEGER {
			b5333(40), b7200(54), b7466(56),
			b8000(60), b8533(64),
			b9066(68), b9600(72),
			b10133(76), b10666(80),
			b11200(84), b11733(88),
			b12266(92), b12800(96),
			b13333(100), b13866(104),
			b14400(108), b14933(112),
			b15466(116), b16000(120),
			b16533(124), b17066(128),
			b17600(132), b18133(136),
			b18666(140), b19200(144),
			b19733(148), b20266(152),
			b20800(156), b21333(160),
			b21866(164), b22400(168),
			b22933(172), b23466(176),
			b24000(180), b24533(184),
			b25066(188), b25600(192),
			b26133(196), b26666(200),
			b27200(204), b27733(208),
			b28266(212), b28800(216),
			b29333(220), b29866(224),
			b30400(228), b30933(232),
			b31466(236), b32000(240),
			disabled(65535)
			}
		ACCESS  read-only
		STATUS  mandatory
		DESCRIPTION " The compressed channel data rate
			for this AD-10 voice port.

			This attribute must match the value in
			recfAd10VoicePortSpeed. If it does not
			match, the reset AD-10 voice port
			command can be used to synchronize them.

			For ports using a CELP compression
			algorithm, only speeds of 5.333 Kbps,
			7.2 Kbps, 8 Kbps, and 9.6 Kbps will be
			supported.

			For ports using the ATC compression
			algorithm, only the speeds between
			7.466 Kbps and 32 Kbps will be
			supported."
		::= { restAd10VoicePortEntry 18 }

restAd10VoicePortCompressMode 	OBJECT-TYPE
		SYNTAX  INTEGER {
			tCelp(1),
			atc(2)
			}
		ACCESS  read-only
		STATUS  mandatory
		DESCRIPTION "This attribute must match the
			value in recfAd10VoicePortCompressMode.
			If it does not match, the reset AD-10
			voice port command can be used to
			synchronize them."
		::= { restAd10VoicePortEntry 19 }

restAd10VoicePortFaxMode 	OBJECT-TYPE
		SYNTAX  INTEGER {
			faxIIIenable-NSFenable(1),
			faxIIIenable-NSFdisable(2),
			faxIIIdisable-NSFdontcare(3)
			}
		ACCESS  read-only
		STATUS  mandatory
		DESCRIPTION "This attribute must match the
			value in recfAd10VoicePortFaxMode.
			If it does not match, the reset AD-10
			voice port command can be used to
			synchronize them."
		::= { restAd10VoicePortEntry 20 }

restAd10VoicePortOOSAudio 	OBJECT-TYPE
		SYNTAX  INTEGER {
			fastBusy(1),
			silence(2)
			}
		ACCESS  read-write
		STATUS  mandatory
		DESCRIPTION "INTRODUCED 1.2.3

			OOS audio signal for AD-10 voice
			ports."
		::= { restAd10VoicePortEntry 21 }

restAd10VoicePortCelpNetSigMd 	OBJECT-TYPE
		SYNTAX  INTEGER {
			auto(1),
			st(2),
			link(3)
			}
		ACCESS  read-write
		STATUS  mandatory
		DESCRIPTION "INTRODUCED 2.0.0

			Enable autodetection of CELP/ATC
			channel connected equipment so as to
			automatically change format to become
			compatible with either LINK (5 byte) or ST (8
			byte) channel mode.  Alternately, this
			parameter hard sets CELP/ATC channels to be
			compatible only with either LINK or ST mode
			compatible equipment."
		::= { restAd10VoicePortEntry 22 }

restAd10VoicePortCelpNetSigSt 	OBJECT-TYPE
		SYNTAX  INTEGER {
			indeterminate(1),
			st(2),
			link(3)
			}
		ACCESS  read-only
		STATUS  mandatory
		DESCRIPTION "INTRODUCED 2.0.0

			When restAd10VoiceTrkGrpCelpNetSigMd
			attribute is set to auto (autodetection
			mode), this parameter indicates whether
			the CELP/ATC channel connected is
			running in either LINK (5 byte) or
			ST (8 byte) mode. If the channel is not
			connected, if it is running some other
			type of voice, or if the channel is not
			currently maintaining validated channel
			signaling synchronization, then this
			parameter will indicate indeterminate.
			If autodetection is disabled, this
			parameter reflects the value of
			restAd10VoiceTrkGrpCelpNetSigMd
			attribute."
		::= { restAd10VoicePortEntry 23 }


-- Ad10 Packet Band Status

restAd10PktBandTable 	OBJECT-TYPE
		SYNTAX  SEQUENCE OF RestAd10PktBandEntry
		ACCESS  not-accessible
		STATUS  mandatory
		DESCRIPTION " "
		::=  { restAd10Port 4 }

restAd10PktBandEntry 	OBJECT-TYPE
		SYNTAX  RestAd10PktBandEntry
		ACCESS  not-accessible
		STATUS  mandatory
		DESCRIPTION " "
		INDEX { restAd10PktBandAddr }
		::=  { restAd10PktBandTable 1 }

RestAd10PktBandEntry     ::=  SEQUENCE {
			restAd10PktBandAddr
				Ad10PortAddr,
			restAd10PktBandDiagnostics
				INTEGER,
			restAd10PktBandStatMuxMode
				INTEGER,
			restAd10PktBandMaxSegSize
				INTEGER,
			restAd10PktBandBaudRate
				INTEGER,
		 	restAd10PktBandMinBandwidth
			   	INTEGER,
		 	restAd10PktBandCurBandwidth
			   	INTEGER,
		 	restAd10PktBandMaxBandwidth
			   	INTEGER
			}

restAd10PktBandAddr 	OBJECT-TYPE
		SYNTAX Ad10PortAddr
		ACCESS read-only
		STATUS mandatory
		DESCRIPTION " "
		::= { restAd10PktBandEntry 1 }

restAd10PktBandDiagnostics 	OBJECT-TYPE
		SYNTAX  INTEGER {
			insert(4),
			remove(5),
			reset(6)
			}
		ACCESS  write-only
		STATUS  mandatory
		DESCRIPTION "Insert will download the new MIB
			to the module. It will not synchronize
			any configuration parameters between
			the AD-10 and the NCP.

			Remove will disconnect the connected
			channel. It will not erase the
			configuration MIB.

			Reset in essence is a remove following
			by an insert. It will also cause the
			AGM to force the AD-10 packet band
			speed to match the values set on the
			NCP."
		::= { restAd10PktBandEntry 2 }

restAd10PktBandStatMuxMode 	OBJECT-TYPE
		SYNTAX  INTEGER {
			offline(1),
			online(2),
			disableDiagnosis(3),
			bertTowardSub(4),
			bertTowardNetwork(5),
			loopSub(6),
			loopNet(7)
			}
		ACCESS  read-write
		STATUS  deprecated
		DESCRIPTION "DEPRECATED 2.0

			Online/offline and diagnosis mode."
		::= { restAd10PktBandEntry 3 }

restAd10PktBandMaxSegSize 	OBJECT-TYPE
		SYNTAX  INTEGER {
			b64bytes(1),
			b256bytes(2)
			}
		ACCESS  read-write
		STATUS  mandatory
		DESCRIPTION "Maximum frame size"
		::= { restAd10PktBandEntry 4 }

restAd10PktBandBaudRate 	OBJECT-TYPE
		SYNTAX  INTEGER {
			    b1200(9), b1334(10), b1600(12),
			    b1867(14), b2000(15), b2134(16),
			    b2400(18), b2667(20), b2800(21),
			    b3200(24), b3600(27), b3734(28),
			    b4000(30), b4267(32), b4667(35),
			    b4800(36), b5334(40), b5600(42),
			    b6000(45), b6400(48), b7200(54),
			    b7467(56), b8000(60), b8400(63),
			    b9334(70), b9600(72), b10667(80),
			    b11200(84), b12000(90), b12800(96),
			    b14000(105), b14400(108),
			    b14934(112), b16000(120),
			    b16800(126), b18000(135),
			    b18667(140), b19200(144),
			    b21334(160), b22400(168),
			    b24000(180), b25200(189),
			    b28000(210), b28800(216),
			    b29867(224), b32000(240),
			    b33600(252), b36000(270),
			    b37334(280), b38400(288),
			    b42000(315), b44800(336),
			    b48000(360), b50400(378),
			    b56000(420), b57600(432),
			    b64000(480), b67200(504),
			    b72000(540), b74667(560),
			    b84000(630), b89600(672),
			    b96000(720), b100800(756),
			    b112000(840), b115200(864),
			    b126000(945), b128000(960),
			    disabled(65535)
			}
		ACCESS  read-only
		STATUS  mandatory
		DESCRIPTION "This attribute must match the
			value in recfAd10PktBandBaudRate. If it
			does not match, the reset AD-10 packet band
			command can be used to synchronize them.

			If recfAd10PktBandDBAMode is enabled, 
			the rate should be equal to the rate of
			the AD10 aggregrate."
		::= { restAd10PktBandEntry 5 }

restAd10PktBandMinBandwidth 	OBJECT-TYPE
		SYNTAX	INTEGER
		ACCESS  read-only
		STATUS mandatory
		DESCRIPTION     "Returns the value of the
			packet band port bandwidth with
			all configured DBA voice ports off-hook.
			The units of this value are 400/3 Hz."
		::= { restAd10PktBandEntry 6 }

restAd10PktBandCurBandwidth 	OBJECT-TYPE
		SYNTAX  INTEGER
		ACCESS  read-only
		STATUS mandatory
		DESCRIPTION     "Returns the current value of
			the packet band port bandwidth.
			The units of this value are 400/3 Hz."
		::= { restAd10PktBandEntry 7 }

restAd10PktBandMaxBandwidth 	OBJECT-TYPE
		SYNTAX	INTEGER
		ACCESS  read-only
		STATUS mandatory
		DESCRIPTION     "Returns the value of the
			packet band port bandwidth with
			all configured DBA voice ports on-hook.
			The units of this value are 400/3 Hz."
		::= { restAd10PktBandEntry 8 }


-- ASM Port Status MIB

restAsmPort 	OBJECT IDENTIFIER ::= { reStatus 11 }


-- ASM X50 Application Status MIB

restAsmX50Table 	OBJECT IDENTIFIER ::= { restAsmPort 1 }


-- ASM X50 Port Status MIB

restAsmX50PortTable 	OBJECT-TYPE
		SYNTAX    SEQUENCE OF RestAsmX50PortEntry
		ACCESS    not-accessible
		STATUS    mandatory
		DESCRIPTION "This section of the MIB does not
			support getNext."
		::= { restAsmX50Table 1 }

restAsmX50PortEntry 	OBJECT-TYPE
		SYNTAX    RestAsmX50PortEntry
		ACCESS    not-accessible
		STATUS    mandatory
		DESCRIPTION " "
		INDEX     { restAsmX50PortAddr }
		::= { restAsmX50PortTable 1 }

RestAsmX50PortEntry 		::= SEQUENCE {
                    			restAsmX50PortAddr
                         			PortAddr,
                    			restAsmX50PortEngine
                         			INTEGER,
                    			restAsmX50PortRxHouseKbits
                         			OCTET STRING,
		    			restAsmX50PortCktTimeSlotMap
                         			OCTET STRING,
		    			restAsmX50PortAggrStatus
			 			INTEGER
                    			}

restAsmX50PortAddr 	OBJECT-TYPE
		SYNTAX    PortAddr
		ACCESS    read-only
		STATUS    mandatory
		DESCRIPTION " "
		::= { restAsmX50PortEntry 1 }

restAsmX50PortEngine 	OBJECT-TYPE
		SYNTAX    INTEGER (1..16)
		ACCESS    read-only
		STATUS    mandatory
		DESCRIPTION "Indicates which DSP on the ASM
			module the port has been allocated to."
		::= { restAsmX50PortEntry 2 }

restAsmX50PortRxHouseKbits 	OBJECT-TYPE
		SYNTAX    OCTET STRING ( SIZE(1) )
		ACCESS    read-only
		STATUS    mandatory
		DESCRIPTION "bit      housekeeping bit
                                 	0 (lsb)    'H'
                                 	1          'G'
                                 	2          'F'
                                 	3          'E'
                                 	4          'D'
                                 	5          'C'
                                 	6          'B'
                                 	7         not used"
		::= { restAsmX50PortEntry 3 }

restAsmX50PortCktTimeSlotMap 	OBJECT-TYPE
		SYNTAX    OCTET STRING ( SIZE(20) )
		ACCESS    read-only
		STATUS    mandatory
		DESCRIPTION "Each byte 1-20 indicates which
			circuit is using that time slot."
		::= { restAsmX50PortEntry 4 }

restAsmX50PortAggrStatus 	OBJECT-TYPE
		SYNTAX  INTEGER {
			pending(1),
			inSync(2),
			los(4),
			ros(6),
			losRos(8),
			oos(16),
			loopback(17)
			}
		ACCESS    read-only
		STATUS    mandatory
		DESCRIPTION "Specific ASM X50 status."
		::= { restAsmX50PortEntry 5 }


-- ASM X50 Circuit Status MIB

restAsmX50CkTable 	OBJECT-TYPE
		SYNTAX    SEQUENCE OF RestAsmX50CkEntry
		ACCESS    not-accessible
		STATUS    mandatory
		DESCRIPTION "This section of the MIB does not
			support getNext."
		::= { restAsmX50Table 2 }

restAsmX50CkEntry 	OBJECT-TYPE
		SYNTAX    RestAsmX50CkEntry
		ACCESS    not-accessible
		STATUS    mandatory
		DESCRIPTION " "
		INDEX     { restAsmX50CkAddr }
		::= { restAsmX50CkTable 1 }

RestAsmX50CkEntry   ::= SEQUENCE {
                         restAsmX50CkAddr
                              AsmX50CkAddr,
			 restAsmX50CkDiagnostics
                              INTEGER,
                         restAsmX50CkSbitStatus
                              INTEGER,
                         restAsmX50CkPhasorStatus
                              OCTET STRING
                         }

restAsmX50CkAddr 	OBJECT-TYPE
		SYNTAX    AsmX50CkAddr
		ACCESS    read-only
		STATUS    mandatory
		DESCRIPTION " "
		::= { restAsmX50CkEntry 1 }

restAsmX50CkDiagnostics 	OBJECT-TYPE
		SYNTAX    INTEGER {
			   insert(4),
			   remove(5),
			   reset(6)
			   }
		ACCESS    write-only
		STATUS    mandatory
		DESCRIPTION "Insert will download the new MIB to the
			module and set the start mode in the
			configuration MIB to automatic.

			Remove will disconnect the connected channel
			and change the start mode in the configuration
			MIB to off. It will not erase the configuration
			MIB.

			Reset in essence is a remove following by an
			insert. However, it will not change the start
			mode in the configuration MIB."
		::= { restAsmX50CkEntry 2 }

restAsmX50CkSbitStatus 	OBJECT-TYPE
		SYNTAX    INTEGER {
                                   one(1),
                                   zero(2)
                                   }
		ACCESS    read-only
		STATUS    mandatory
		DESCRIPTION " "
		::= { restAsmX50CkEntry 3 }

restAsmX50CkPhasorStatus 	OBJECT-TYPE
		SYNTAX    OCTET STRING (SIZE (2))
		ACCESS     read-only
		STATUS     mandatory
		DESCRIPTION "All bits zero indicates normal.
			       bit   1 (lsb) indicates receive phasor underflow
			       bit   2 indicates receive phasor overflow
			       bit   3 indicates receive phasor empty
			       bit   4 indicates receive phasor full
			       bit   5 indicates receive phasor fifo error
			       bits  6-7 are reserved
			       bit   8 indicates receive phasor not applicable
			       bit   9 indicates transmit phasor underflow
			       bit  10 indicates transmit phasor overflow
			       bit  11 indicates transmit phasor empty
			       bit  12 indicates transmit phasor full
			       bit  13 indicates transmit phasor fifo error
			       bits 14-15 are reserved
			       bit  16 indicates transmit phasor not applicable
			    If circuit does not have a phasor, the return
			    value will be x8080."
		::= { restAsmX50CkEntry 4 }


-- ASM Voice Application Status MIB

restAsmVoice 	OBJECT IDENTIFIER ::= { restAsmPort 2 }

-- ASM Voice Port Status MIB

restAsmVoicePortTable 	OBJECT-TYPE
		SYNTAX  SEQUENCE OF RestAsmVoicePortEntry
		ACCESS	not-accessible
		STATUS  mandatory
		DESCRIPTION "This section of the MIB
			     doesn't support getNext."
		::= { restAsmVoice 1 }

restAsmVoicePortEntry 	OBJECT-TYPE
		SYNTAX  RestAsmVoicePortEntry
		ACCESS  not-accessible
		STATUS  mandatory
		DESCRIPTION " "
		INDEX   { restAsmVoicePortChannelAddr }
		::= { restAsmVoicePortTable 1 }

RestAsmVoicePortEntry		::= SEQUENCE {
			     restAsmVoicePortChannelAddr
			        ChannelAddr,
			     restAsmVoicePortAddr
				PortAddr,
			     restAsmVoicePortTrkGrpAddr
				PortAddr,
			     restAsmVoicePortEngine
				INTEGER,
			     restAsmVoicePortPacketSize
				INTEGER,
			     restAsmVoicePortBlockSize
				INTEGER,
			     restAsmVoicePortEchoCanceller
				OCTET STRING,
			     restAsmVoicePortDTMFRelay
				OCTET STRING,
			     restAsmVoicePortFaxRelay
				OCTET STRING,
			     restAsmVoicePortPacket
				OCTET STRING,
			     restAsmVoicePortSubratePhasor
				OCTET STRING,
			     restAsmVoicePortSignalingLOS
				INTEGER,
			     restAsmVoicePortFrameLOS
			        INTEGER,
			     restAsmVoicePortCelpNetSigSt
				INTEGER
			     }

restAsmVoicePortChannelAddr 	OBJECT-TYPE
		SYNTAX	ChannelAddr
		ACCESS	read-only
		STATUS  mandatory
		DESCRIPTION "Address of T1M/E1M bundle
			     which is being used by this
			     port while connected. If
			     disconnected returns error"
		::= { restAsmVoicePortEntry 1 }

restAsmVoicePortAddr 	OBJECT-TYPE
		SYNTAX	PortAddr
		ACCESS  read-only
		STATUS  mandatory
		DESCRIPTION "ASM voice port physical address
			     in nest:slot:port format"
		::= { restAsmVoicePortEntry 2 }

restAsmVoicePortTrkGrpAddr 	OBJECT-TYPE
		SYNTAX  PortAddr
		ACCESS  read-only
		STATUS  mandatory
		DESCRIPTION "Trunk group address this ASM
			     voice port is assigned to"
		::= { restAsmVoicePortEntry 3 }

restAsmVoicePortEngine 	OBJECT-TYPE
		SYNTAX	INTEGER (1..16)
		ACCESS  read-only
		STATUS  mandatory
		DESCRIPTION "The ASM module DSP number
			     allocated for this voice port"
		::= { restAsmVoicePortEntry 4 }

restAsmVoicePortPacketSize 	OBJECT-TYPE
		SYNTAX  INTEGER (20..60)
		ACCESS  read-only
		STATUS  mandatory
		DESCRIPTION "Size of compressed data block.

			   This field is not supported in this release."
		::= { restAsmVoicePortEntry 5 }

restAsmVoicePortBlockSize 	OBJECT-TYPE
		SYNTAX  INTEGER (120..240)
		ACCESS  read-only
		STATUS  mandatory
		DESCRIPTION "Size of uncompressed data block.

			   This field is not supported in this release."
		::= { restAsmVoicePortEntry 6 }

restAsmVoicePortEchoCanceller 	OBJECT-TYPE
		SYNTAX  OCTET STRING (SIZE (1))
		ACCESS  read-only
		STATUS  mandatory
		DESCRIPTION "The bit mask is:
			   bit 0(lsb)divergence (0-normal, 1-diverge)
			   bit 1     reserved
			   bit 2     filter	(0-disabled, 1-enabled)
			   bit 3     adaptation	(0-frosen, 1-adapting)
			   bit 4     reserved
			   bit 5     reserved
			   bit 6     reserved
			   bit 7(msb)reserved

			   This field is not supported in this release."
		::= { restAsmVoicePortEntry 7 }

restAsmVoicePortDTMFRelay 	OBJECT-TYPE
		SYNTAX  OCTET STRING (SIZE (1))
		ACCESS  read-only
		STATUS  mandatory
		DESCRIPTION "The bit mask is:
			   bits 0(lsb)-3   detected character
			     0 - 9 digit 0 through 9
			     10	   character '*'
			     11	   character '#'
			     12-15 characters 'A' through 'D'
			   bits 4,5        digit type (00 - DTMF)
			   bit 6     digit generation (0-off, 1-on)
			   bit 7(msb)digit detect (0-none, 1-detected)

			   This field is not supported in this release."
		::= { restAsmVoicePortEntry 8 }

restAsmVoicePortFaxRelay 	OBJECT-TYPE
		SYNTAX  OCTET STRING (SIZE (1))
		ACCESS  read-only
		STATUS  mandatory
		DESCRIPTION "The bit mask is:
			   bits 0(lsb)-4   modulation type
			     0	   V.21 300  bps
			     1	   V.27 2400 bps
			     2	   V.27 4800 bps
			     3	   V.29 7200 bps
			     4	   V.29 9600 bps
			   bit 5     reserved
			   bit 6     demodulation (0-off, 1-on)
			   bit 7(msb)modulation (0-off, 1-on)

			   This field is not supported in this release."
		::= { restAsmVoicePortEntry 9 }

restAsmVoicePortPacket 	OBJECT-TYPE
		SYNTAX  OCTET STRING (SIZE (1))
		ACCESS  read-only
		STATUS  mandatory
		DESCRIPTION "The bit mask is:
			   bit 0(lsb)sync init	(1-initializing)
			   bit 1     sync acq   (1-sync searching)
			   bit 2     sync ver   (1-verifying sync)
			   bit 3     sync mon   (1-normal)
			   bit 4     sync loss  (1-frame sync loss)
			   bit 5     sync loss time-out (1-occured)
			   bit 6     reserved
			   bit 7(msb)HBER	(1-BER > 10)

			   This field is not supported in this release."
		::= { restAsmVoicePortEntry 10 }

restAsmVoicePortSubratePhasor 	OBJECT-TYPE
		SYNTAX    OCTET STRING (SIZE (2))
		ACCESS     read-only
		STATUS     mandatory
		DESCRIPTION "All bits zero indicates normal.
			      bit   1(lsb)receive phasor underflow
			      bit   2 	  receive phasor overflow
			      bit   3-8   are reserved
			      bit   9 	  transmit phasor underflow
			      bit  10     transmit phasor overflow
			      bit  11-16  are reserved
			      If port does not have a phasor, the
			      return value will be x8080."
		::= { restAsmVoicePortEntry 11 }

restAsmVoicePortSignalingLOS 	OBJECT-TYPE
		SYNTAX	INTEGER {
			inSync(1),
			los(2)
			}
		ACCESS     read-only
		STATUS     mandatory
		DESCRIPTION "Signaling LOS status."
		::= { restAsmVoicePortEntry 12 }

restAsmVoicePortFrameLOS 	OBJECT-TYPE
		SYNTAX	INTEGER {
			inSync(1),
			los(2)
			}
		ACCESS     read-only
		STATUS     mandatory
		DESCRIPTION "Frame LOS status."
		::= { restAsmVoicePortEntry 13 }

restAsmVoicePortCelpNetSigSt 	OBJECT-TYPE
		SYNTAX  INTEGER {
			indeterminate(1),
			st(2),
			link(3)
			}
		ACCESS     read-only
		STATUS     mandatory
		DESCRIPTION "INTRODUCED 2.0.0

			When recfAsmVoiceTrkGrpCelpNetSigMd
			attribute is set to auto (autodetection
			mode), this parameter indicates whether
			the CELP/ATC channel connected is
			running in either LINK (5 byte) or
			ST (8 byte) mode. If the channel is not
			connected, if it is running some other
			type of voice, or if the channel is not
			currently maintaining validated channel
			signaling synchronization, then this
			parameter will indicate indeterminate.
			If autodetection is disabled, this
			parameter reflects the value of
			recfAsmVoiceTrkGrpCelpNetSigMd
			attribute.
			Note: this parameter may take the place
			of a currently unused, but similarly
			intended restAsmVoicePortPacketSize
			attribute."
		::= { restAsmVoicePortEntry 14 }


-- Trunk Group Application Status MIB

restTrunkGroup 	OBJECT IDENTIFIER ::= { reStatus 12 }

-- Trunk Group Status MIB

restTrkGrpTable 	OBJECT-TYPE
		SYNTAX 	SEQUENCE OF RestTrkGrpEntry
		ACCESS 	not-accessible
		STATUS 	mandatory
		DESCRIPTION "This section of the MIB is
			     intended to use for any
			     trunk groups status defined. It
			     doesn't support getNext.

			     This section is not supported in
			     this release."
		::= { restTrunkGroup 1 }

restTrkGrpEntry 	OBJECT-TYPE
		SYNTAX	RestTrkGrpEntry
		ACCESS	not-accessible
		STATUS	mandatory
		DESCRIPTION " "
		INDEX 	{ restTrkGrpAddr }
		::= { restTrkGrpTable 1 }

RestTrkGrpEntry ::= SEQUENCE {
		     restTrkGrpAddr
			PortAddr,
		     restTrkGrpStatus
			INTEGER
		     }

restTrkGrpAddr 	OBJECT-TYPE
		SYNTAX	PortAddr
		ACCESS	read-only
		STATUS  mandatory
		DESCRIPTION "Address of the trunk group"
		::= { restTrkGrpEntry 1 }


restTrkGrpStatus 	OBJECT-TYPE
		SYNTAX	INTEGER {
			active(1),
			inactive(2)
			}
		ACCESS  read-only
		STATUS  mandatory
		DESCRIPTION "The current trunk group status"
		::= { restTrkGrpEntry 2 }



-- Trunk Group Contents Status MIB

restTrkGrpContentsTable 	OBJECT-TYPE
		SYNTAX 	SEQUENCE OF RestTrkGrpContentsEntry
		ACCESS 	not-accessible
		STATUS 	mandatory
		DESCRIPTION "This section of the MIB specify
			     all the contents of the trunk
			     groups status defined. It
			     partially supports getNext
			     (only within trunk group).

			     This section is not supported in
			     this release."
		::= { restTrunkGroup 2 }

restTrkGrpContentsEntry 	OBJECT-TYPE
		SYNTAX	RestTrkGrpContentsEntry
		ACCESS	not-accessible
		STATUS	mandatory
		DESCRIPTION " "
		INDEX 	{ restTrkGrpContentsAddr,
			  restTrkGrpContentsSequenceID }
		::= { restTrkGrpContentsTable 1 }

RestTrkGrpContentsEntry		::= SEQUENCE {
		     restTrkGrpContentsAddr
			PortAddr,
		     restTrkGrpContentsSequenceID
			INTEGER,
		     restTrkGrpContentsSrcNodeID
			NodeAddr,
		     restTrkGrpContentsSrcTrkGrpAddr
			PortAddr,
		     restTrkGrpContentsSrcChAddr
			ChannelAddr,
		     restTrkGrpContentsDstNodeID
			NodeAddr,
		     restTrkGrpContentsDstTrkGrpAddr
			        PortAddr,
		     restTrkGrpContentsDstChAddr
			ChannelAddr
			     }

restTrkGrpContentsAddr 	OBJECT-TYPE
		SYNTAX	PortAddr
		ACCESS	read-only
		STATUS  mandatory
		DESCRIPTION "Address of the trunk group"
		::= { restTrkGrpContentsEntry 1 }

restTrkGrpContentsSequenceID 	OBJECT-TYPE
		SYNTAX	INTEGER (1..65535)
		ACCESS  read-only
		STATUS  mandatory
		DESCRIPTION "Used to index multiple ports
			     assigned to this trunk group"
		::= { restTrkGrpContentsEntry 2 }

restTrkGrpContentsSrcNodeID 	OBJECT-TYPE
		SYNTAX NodeAddr
		ACCESS  read-only
		STATUS  mandatory
		DESCRIPTION "Source node ID of the
			current channel"
		::= { restTrkGrpContentsEntry 3 }

restTrkGrpContentsSrcTrkGrpAddr 	OBJECT-TYPE
		SYNTAX PortAddr
		ACCESS  read-only
		STATUS  mandatory
		DESCRIPTION "Source truk group address
			of the current channel"
		::= { restTrkGrpContentsEntry 4 }

restTrkGrpContentsSrcChAddr 	OBJECT-TYPE
		SYNTAX	ChannelAddr
		ACCESS  read-only
		STATUS  mandatory
		DESCRIPTION "Source end point address of
			     the current channel (T1M/E1M port)
			     using this trunk group. When
			     disconnected returns an error"
		::= { restTrkGrpContentsEntry 5 }

restTrkGrpContentsDstNodeID 	OBJECT-TYPE
		SYNTAX NodeAddr
		ACCESS  read-only
		STATUS  mandatory
		DESCRIPTION "Destination node ID of the
			current channel"
		::= { restTrkGrpContentsEntry 6 }

restTrkGrpContentsDstTrkGrpAddr 	OBJECT-TYPE
		SYNTAX PortAddr
		ACCESS  read-only
		STATUS  mandatory
		DESCRIPTION "Destination truk group address
			of the current channel"
		::= { restTrkGrpContentsEntry 7 }

restTrkGrpContentsDstChAddr 	OBJECT-TYPE
		SYNTAX	ChannelAddr
		ACCESS  read-only
		STATUS  mandatory
		DESCRIPTION "Destination end point address of
			     the current channel (T1M/E1M port)
			     using this trunk group. When
			     disconnected returns an error"
		::= { restTrkGrpContentsEntry 8 }


-- RTM Port Status MIB

restRtmPort 	OBJECT IDENTIFIER ::= { reStatus 13 }

-- RTM Port Application Status MIB

restRtmPortTable 	OBJECT-TYPE
		SYNTAX  SEQUENCE OF RestRtmPortEntry
		ACCESS  not-accessible
		STATUS  mandatory
		DESCRIPTION " "
		::= { restRtmPort 1 }

restRtmPortEntry 	OBJECT-TYPE
		SYNTAX  RestRtmPortEntry
		ACCESS  not-accessible
		STATUS  mandatory
		DESCRIPTION " "
		INDEX   { restRtmPortAddr }
		::= { restRtmPortTable 1 }

RestRtmPortEntry              	::= SEQUENCE {
		     restRtmPortAddr
			PortAddr,
		     restRtmPortAdFmtRevision
			INTEGER,
		     restRtmPortAdType
			INTEGER,
		     restRtmPortAdSubtype
			INTEGER,
		     restRtmPortAdAssemblyNmb
			DisplayString,
		     restRtmPortAdMotherBrdAssmNmb
		        DisplayString,
		     restRtmPortAdSerialNmb
			DisplayString,
		     restRtmPortAdManufactDate
			DisplayString,
		     restRtmPortAdRamSize
			INTEGER,
		     restRtmPortAdModDiagResult
			OCTET STRING,
		     restRtmPortAdPortDiagResult
			OCTET STRING,
		     restRtmPortAdCpMode
			INTEGER,
		     restRtmPortAdCpSpeed
			INTEGER
		     }

restRtmPortAddr 	OBJECT-TYPE
		SYNTAX	PortAddr
		ACCESS	read-only
		STATUS  mandatory
		DESCRIPTION "RTM port physical address
			     in nest:slot:port format"
		::= { restRtmPortEntry 1 }

restRtmPortAdFmtRevision 	OBJECT-TYPE
		SYNTAX  INTEGER
		ACCESS	read-only
		STATUS  mandatory
		DESCRIPTION "Format revision of the ADx."
		::= { restRtmPortEntry 2 }

restRtmPortAdType 	OBJECT-TYPE
		SYNTAX  INTEGER {
			ad3(2),
			ad7(3)
			}
		ACCESS  read-only
		STATUS  mandatory
		DESCRIPTION "Type of the Adx unit."
		::= { restRtmPortEntry 3 }

restRtmPortAdSubtype 	OBJECT-TYPE
		SYNTAX  INTEGER {
			integralInt(1),
			daughterBrdInt(2),
			sipexChipInt(3)
			}
		ACCESS  read-only
		STATUS  mandatory
		DESCRIPTION "In case of integralInt all
			interfaces are V24 (AD-3I/AD-7I
			subtype).
			In case of daughterBrdInt the
			interface type is determined by
			reading restRtmAdPortElIntStatus
			MIB attribute (AD-3N/AD-7N
			subtype).
			In case of sipexChipInt the
			interface type may be programmed
			by the user (is not supported in
			this release."
		::= { restRtmPortEntry 4 }

restRtmPortAdAssemblyNmb 	OBJECT-TYPE
		SYNTAX	DisplayString (SIZE(0..16))
		ACCESS  read-only
		STATUS  mandatory
		DESCRIPTION "ADx unit assembly number."
		::= { restRtmPortEntry 5 }

restRtmPortAdMotherBrdAssmNmb 	OBJECT-TYPE
		SYNTAX  DisplayString (SIZE(0..16))
		ACCESS  read-only
		STATUS  mandatory
		DESCRIPTION "Motherboard assembly number."
		::= { restRtmPortEntry 6 }

restRtmPortAdSerialNmb 	OBJECT-TYPE
		SYNTAX  DisplayString (SIZE(0..16))
		ACCESS  read-only
		STATUS  mandatory
		DESCRIPTION "ADx unit serial number."
		::= { restRtmPortEntry 7 }

restRtmPortAdManufactDate 	OBJECT-TYPE
		SYNTAX  DisplayString (SIZE(0..8))
		ACCESS  read-only
		STATUS  mandatory
		DESCRIPTION "ADx unit manufacturing date."
		::= { restRtmPortEntry 8 }

restRtmPortAdRamSize 	OBJECT-TYPE
		SYNTAX  INTEGER
		ACCESS  read-only
		STATUS  mandatory
		DESCRIPTION "ADx unit RAM size."
		::= { restRtmPortEntry 9 }

restRtmPortAdModDiagResult 	OBJECT-TYPE
		SYNTAX 	OCTET STRING (SIZE(2))
		ACCESS  read-only
		STATUS  mandatory
		DESCRIPTION "ADx unit internal diagnostics
			result. The bit mask is:
			bit 0 (LSB)	RAM test
			bit 1		U-interface D-channel
				loopback test
			bit 2		SCC-chip D-channel
				loopback test
			bit 3		U-interface loopback
				test
			bit 4		CPI loopback test
			bit 5		PROM ID checksum
			bit 6		Port status checksum
			bit 7-15 (MSB)  reserved.
			The bit value 1 means test failure."
		::= { restRtmPortEntry 10 }

restRtmPortAdPortDiagResult 	OBJECT-TYPE
		SYNTAX  OCTET STRING (SIZE(2))
		ACCESS  read-only
		STATUS  mandatory
		DESCRIPTION "ADx port internal diagnostics
			result. The bit mask is read from right
			(LSB) to left (MSB) and represents
			corresponding elements numbers.If bit is
			set to 1 the diagnostics failed, if 0 -
			passed."
		::= { restRtmPortEntry 11 }

restRtmPortAdCpMode 	OBJECT-TYPE
		SYNTAX  INTEGER {
			disable(1),
			enable(2)
			}
		ACCESS  read-write
		STATUS  mandatory
		DESCRIPTION "CPI console pass through mode."
		DEFVAL { disable }
		::= { restRtmPortEntry 12 }

restRtmPortAdCpSpeed 	OBJECT-TYPE
		SYNTAX  INTEGER {
			a9600(1),
			a19200(2)
			}
		ACCESS  read-write
		STATUS  mandatory
		DESCRIPTION "CPI console speed value."
		DEFVAL { a9600 }
		::= { restRtmPortEntry 13 }


-- RTM ADx Port Application Status MIB

restRtmAdPortTable 	OBJECT-TYPE
		SYNTAX  SEQUENCE OF RestRtmAdPortEntry
		ACCESS	not-accessible
		STATUS  mandatory
		DESCRIPTION " "
		::= { restRtmPort 2 }

restRtmAdPortEntry 	OBJECT-TYPE
		SYNTAX  RestRtmAdPortEntry
		ACCESS  not-accessible
		STATUS  mandatory
		DESCRIPTION " "
		INDEX   { restRtmAdPortAddr }
		::= { restRtmAdPortTable 1 }

RestRtmAdPortEntry		::= SEQUENCE {
		     restRtmAdPortAddr
			RtmAdPortAddr,
		     restRtmAdPortDiagnostics
			INTEGER,
		     restRtmAdPortInterface
			INTEGER,
		     restRtmAdPortStopBits
			INTEGER,
		     restRtmAdPortGeneration
			INTEGER,
		     restRtmAdPortContention
			INTEGER,
		     restRtmAdPortOosOper
			INTEGER,
		     restRtmAdPortState
			INTEGER,
		     restRtmAdPortForcedFunc
			OCTET STRING,
		     restRtmAdPortLoopbackType
			INTEGER,
		     restRtmAdPortLoopbackStatus
			INTEGER,
		     restRtmAdPortElecInterface
			INTEGER,
		     restRtmAdPortElIntStatus
			INTEGER,
		     restRtmAdPortParSubstitution
			INTEGER,
		     restRtmAdPortParSubstChar
			INTEGER,
		     restRtmAdPortPhasorStatus
			OCTET STRING,
		     restRtmAdPortAdPhasorStatus
			OCTET STRING,
		     restRtmAdPortAdFunctions
			OCTET STRING,
		     restRtmAdPortParity
			INTEGER
		     }

restRtmAdPortAddr 	OBJECT-TYPE
		SYNTAX	RtmAdPortAddr
		ACCESS	read-only
		STATUS  mandatory
		DESCRIPTION "RTM ADx port physical address
			     in nest:slot:port:element
			     format"
		::= { restRtmAdPortEntry 1 }

restRtmAdPortDiagnostics 	OBJECT-TYPE
		SYNTAX	INTEGER {
			        insert(4),
			remove(5),
			reset(6),
			setLoopback(9),
			clearLoopback(8)
			}
		ACCESS  write-only
		STATUS  mandatory
		DESCRIPTION "Remove will disconnect the
			element and set its start mode
			to off.
			Insert on a removed element will
			get the new MIB and set its
			start mode to auto.
			Reset will disconnect and
			then reconnect the specified
			element without changing its
			start mode in the configuration
			MIB.
			Set and Clear loopback types are set
			by using restRtmAdPortLoopbackType
			control values."
		::= { restRtmAdPortEntry 2 }

restRtmAdPortInterface 	OBJECT-TYPE
		SYNTAX  INTEGER {
			    	dce1(1),
			dce3(3)
			}
		ACCESS  read-write
		STATUS  mandatory
		DESCRIPTION "Interface clocking type."
		DEFVAL { dce1 }
		::= { restRtmAdPortEntry 3 }

restRtmAdPortStopBits 	OBJECT-TYPE
		SYNTAX  INTEGER {
			oneStopBit(1),
			twoStopBit(2)
			}
		ACCESS  read-write
		STATUS  mandatory
		DESCRIPTION "Number of stop bits."
		DEFVAL { oneStopBit }
		::= { restRtmAdPortEntry 4 }

restRtmAdPortGeneration 	OBJECT-TYPE
		SYNTAX  INTEGER {
			transparent(1),
			autogen(2)
			}
		ACCESS  read-write
		STATUS  mandatory
		DESCRIPTION "Type of port generation. It
			is used in cases when end points
			of the connections are rather
			distant and passing the control (EIA)
			functions takes much time. That
			is, if autogen is set, the
			functions are being generated by
			the local equipment."
		DEFVAL { transparent }
		::= { restRtmAdPortEntry 5 }

restRtmAdPortContention 	OBJECT-TYPE
		SYNTAX  INTEGER {
			nobwc(1),
			f1nf1(2),
			f2nf2(3)
			}
		ACCESS  read-write
		STATUS  mandatory
		DESCRIPTION "Type of port contention. If f1nf1
			is set, then when F1 is ON for at least
			1 sec., the connection is requested.
			Otherwise, if F1 is OFF for at least
			1 sec., the disconnect is requested.
			If f2nf2 is set, the same rule applied
			for F2."
		DEFVAL { nobwc }
		::= { restRtmAdPortEntry 6 }

restRtmAdPortOosOper 	OBJECT-TYPE
		SYNTAX  INTEGER {
			doNothing(1),
			forceFn(2),
			mark(3),
			markFf(4),
			space(5),
			spaceFf(6)
			}
		ACCESS  read-write
		STATUS  mandatory
		DESCRIPTION "Out of Sync port
			operations types."
		DEFVAL { doNothing }
		::= { restRtmAdPortEntry 7 }

restRtmAdPortState 	OBJECT-TYPE
		SYNTAX  INTEGER {
			undefined(1),
			defined(2),
			online(3)
			}
		ACCESS  read-only
		STATUS  mandatory
		DESCRIPTION "Port state. If undefined,
			then it is neither configured, nor
			connected.
			If defined, then it is configured,
			but not connected.
			If online, then it is both,
			configured and connected."
		::= { restRtmAdPortEntry 8 }

restRtmAdPortForcedFunc 	OBJECT-TYPE
		SYNTAX  OCTET STRING (SIZE(2))
		ACCESS  read-write
		STATUS  mandatory
		DESCRIPTION "This is a bit pattern of two bytes.
			The upper byte is reserved for future
			use.

			In the lower byte, the four least
			significant bits represent whether the
			function mapped to that bit should be
			forced (bit value 1) or not (0). For
			each function that is set to be forced,
			the four most significant bits
			represent whether the corresponding
			function should be forced high (1) or
			low (0).

			The functions represented by the bits
			in the lower byte are as follows:
			bits 1 (lsb), 5 - DSR
			bits 2, 6 - DCD
			bits 3, 7 - reserved
			bits 4, 8 - CTS"
		::= { restRtmAdPortEntry 9 }

restRtmAdPortLoopbackType 	OBJECT-TYPE
		SYNTAX  INTEGER {
			adRim(1),
			adLim(2),
			adLimDisc(4),
			rtmRim(8),
			rtmLim(16),
			rtmBidirectional(32)
			}
		ACCESS  write-only
		STATUS  mandatory
		DESCRIPTION "The commands are:
			    adRim            - ADx remote loopback
			       command toward user
			       equipment
			    adLim            - ADx local loopback
			       command toward RTM/ST-50
			    adLimDisc        - ADx local loopback while
			       disconnecting user
			    rtmRim	     - RTM remote loopback
			       command toward user
			       equipment
			    rtmLim	     - RTM local loopback
			       command toward RTM/ST-50
			    rtmBidirectional - RTM local loopback while
			       disconnecting user."
		::= { restRtmAdPortEntry 10 }

restRtmAdPortLoopbackStatus 	OBJECT-TYPE
		SYNTAX  INTEGER {
			adRim(1),
			adLim(2),
			adLimDisc(4),
			rtmRim(8),
			rtmLim(16),
			rtmBidirectional(32),
			adLocalLl(64),
			adLocalRl(128),
			none(255)
			}
		ACCESS  read-only
		STATUS  mandatory
		DESCRIPTION "Status of the loopback.
			adLocalLl    - ADx local loopback set
			       by LL function of the
			       interface (circuit 141)
			adLocalRl    - ADx local loopback set
			       by RL function of the
			       interface (circuit
			       140)."
		::= { restRtmAdPortEntry 11 }

restRtmAdPortElecInterface 	OBJECT-TYPE
		SYNTAX  INTEGER {
			v24(1),
			v35(2),
			x21(3),
			noInterface(10)
			}
		ACCESS  read-only
		STATUS  mandatory
		DESCRIPTION "If restRtmAdPortHardwareType
			returns programmable(1), then
			this item is able to be of read-write
			type of access. Otherwise it is
			read-only. For this release this
			attribute access is read-only."
		DEFVAL  { v24 }
		::= { restRtmAdPortEntry 12 }

restRtmAdPortElIntStatus 	OBJECT-TYPE
		SYNTAX  INTEGER {
			nonProgrammable(1),
			programmable(2)
			}
		ACCESS  read-only
		STATUS  mandatory
		DESCRIPTION "If ADx unit has SIPEX chip
			installed, then hardware type
			would be programmable, otherwise
			it would be set to nonProgrammable."
		::= { restRtmAdPortEntry 13 }

restRtmAdPortParSubstitution 	OBJECT-TYPE
		SYNTAX  INTEGER {
			disable(1),
			enable(2)
			}
		ACCESS	read-write
		STATUS  mandatory
		DESCRIPTION "This parameter is used with
			Async ports. When there is a
			parity error detected by ADx,
			instead of sending that character
			over the line it either being
			dropped (disable) or substituted with
			another predefined character (enable)."
		DEFVAL  { disable }
		::= { restRtmAdPortEntry 14 }

restRtmAdPortParSubstChar 	OBJECT-TYPE
		SYNTAX	INTEGER (0..255)
		ACCESS  read-write
		STATUS  mandatory
		DESCRIPTION "This is the parity substitution
			character for
			restRtmAdPortParSubstitution MIB item."
		::= { restRtmAdPortEntry 15 }

restRtmAdPortPhasorStatus 	OBJECT-TYPE
		SYNTAX  OCTET STRING (SIZE(2))
		ACCESS  read-only
		STATUS  mandatory
		DESCRIPTION "The bit mask is:
			bit 0 (LSB)	receive underflow
			bit 1		receive overflow
			bit 2		receive empty
			bit 3		receive full
			bit 4-7		reserved
			bit 8		transmit underflow
			bit 9		transmit overflow
			bit 10		transmit empty
			bit 11		transmit full
			bit 12-15 (MSB)	reserved."
		::= { restRtmAdPortEntry 16 }

restRtmAdPortAdPhasorStatus 	OBJECT-TYPE
		SYNTAX  OCTET STRING (SIZE(2))
		ACCESS  read-only
		STATUS  mandatory
		DESCRIPTION "The bit mask is:
			bit 0 (LSB)	receive underflow
			bit 1		receive overflow
			bit 2		receive empty
			bit 3		receive full
			bit 4-7		reserved
			bit 8		transmit underflow
			bit 9		transmit overflow
			bit 10		transmit empty
			bit 11		transmit full
			bit 12-15 (MSB)	reserved."
		::= { restRtmAdPortEntry 17 }

restRtmAdPortAdFunctions 	OBJECT-TYPE
		SYNTAX OCTET STRING (SIZE(2))
		ACCESS  read-only
		STATUS  mandatory
		DESCRIPTION "The bit mask is:
			bit 0 (LSB)	F1 (DTR)
			bit 1		F2 (RTS)
			bit 2-3		reserved
			bit 4		LL
			bit 5		RL
			bit 6		TM
			bit 7-15 (MSB)	reserved."
		::= { restRtmAdPortEntry 18 }

restRtmAdPortParity 	OBJECT-TYPE
		SYNTAX	INTEGER {
			parNone(1),
			parEven(2),
			parOdd(3)
			}
		ACCESS  read-write
		STATUS  mandatory
		DESCRIPTION "This attribute values are
			applicable only for ASYNC mode."
		DEFVAL { parNone }
		::= { restRtmAdPortEntry 19 }

-- LGM port status MIB

restLgmPort 	OBJECT IDENTIFIER ::= { reStatus 14 }

-- LGM Port Status; Added after ASM Port status mib

restLgmPortTable 	OBJECT-TYPE
		SYNTAX	SEQUENCE OF RestLgmPortEntry
		ACCESS	not-accessible
		STATUS  mandatory
		DESCRIPTION " "
		::=  { restLgmPort 1 }

restLgmPortEntry 	OBJECT-TYPE
		SYNTAX	RestLgmPortEntry
		ACCESS  not-accessible
		STATUS	mandatory
		DESCRIPTION " "
		INDEX { restLgmPortAddr }
		::=  { restLgmPortTable 1 }

RestLgmPortEntry 		::=  SEQUENCE 	{
		 			restLgmPortAddr
			   			PortAddr,
		 			restLgmPortLocalBERQuality
			   			INTEGER,
		 			restLgmPortBERWindowFill
			  			DisplayString,
		 			restLgmPortRemoteNodeID
			   			INTEGER,
		 			restLgmPortRemotePortAddr
			   			PortAddr,
		 			restLgmPortRemoteBERQuality
			   			INTEGER,
		   			restLgmPortRemoteRevision
						INTEGER,
					restLgmPortAvailableBw
			   			INTEGER,
					restLgmPortUsedBw
			   			INTEGER,
					restLgmPortNumCh
			   			INTEGER,
		    			restLgmPortLgmPort
						PortAddr,
					restLgmPortLinkSpeed
						INTEGER,
					restLgmPortDiagnostics
						INTEGER,
					restLgmPortSyncState
						INTEGER
			 	}

restLgmPortAddr 	OBJECT-TYPE
		SYNTAX	PortAddr
		ACCESS  read-only
		STATUS	mandatory
		DESCRIPTION "LGM port virtual address
			in type:group:port format."
		::= { restLgmPortEntry 1 }

restLgmPortLocalBERQuality 	OBJECT-TYPE
		SYNTAX	INTEGER {
			notAvailable(1),
	  		pend(2),
	   		poor(3),
	   		fair(4),
	   		good(5),
	   		veryGood(6)
			}
		ACCESS  read-only
		STATUS	mandatory
		DESCRIPTION "Local Bit Error Quality value."
		::= { restLgmPortEntry 2 }

restLgmPortBERWindowFill 	OBJECT-TYPE
		SYNTAX 	DisplayString ( SIZE(0..7))
		ACCESS  read-only
		STATUS 	mandatory
		DESCRIPTION "Format e.g. 10/32, 5/32."
		::= { restLgmPortEntry 3 }

restLgmPortRemoteNodeID 	OBJECT-TYPE
		SYNTAX	INTEGER (0..2000)
		ACCESS  read-only
		STATUS  mandatory
		DESCRIPTION "Node number that the LGM
			terminates on. If no remote connection has
			been established, then this attribute will
			return zero."
		::= { restLgmPortEntry 4 }

restLgmPortRemotePortAddr 	OBJECT-TYPE
		SYNTAX  PortAddr
		ACCESS	read-only
		STATUS  mandatory
		DESCRIPTION "Port or bundle address that the
			LGM terminates on. If no remote connection has
			been established, then this attribute will
			return zero."
		::= { restLgmPortEntry 5 }

restLgmPortRemoteBERQuality 	OBJECT-TYPE
		SYNTAX  INTEGER {
			notAvailable(1),
	   		pend(2),
	   		poor(3),
	   		fair(4),
	   		good(5),
	   		veryGood(6)
			}
		ACCESS  read-only
		STATUS	mandatory
		DESCRIPTION "Remote Bit Error Quality value."
		::= { restLgmPortEntry 6 }

restLgmPortRemoteRevision 	OBJECT-TYPE
		SYNTAX	INTEGER
		ACCESS	read-only
		STATUS  mandatory
		DESCRIPTION "Revision level on remote node."
		::= { restLgmPortEntry 7 }

restLgmPortAvailableBw 	OBJECT-TYPE
		SYNTAX	INTEGER
		ACCESS  read-only
		STATUS	mandatory
		DESCRIPTION "Available bandwith in bps."
		::= { restLgmPortEntry 8 }

restLgmPortUsedBw 	OBJECT-TYPE
		SYNTAX	INTEGER
		ACCESS	read-only
		STATUS  mandatory
		DESCRIPTION "Bandwith used in bps."
		::= { restLgmPortEntry 9 }

restLgmPortNumCh 	OBJECT-TYPE
		SYNTAX	INTEGER
		ACCESS  read-only
		STATUS	mandatory
		DESCRIPTION "Number of TDM channels."
		::= { restLgmPortEntry 10 }

restLgmPortLgmPort 	OBJECT-TYPE
		SYNTAX 	PortAddr
		ACCESS  read-only
		STATUS  mandatory
		DESCRIPTION "Physical address of the LGM
			port."
		::= { restLgmPortEntry 11 }

restLgmPortLinkSpeed 	OBJECT-TYPE
		SYNTAX	INTEGER
		ACCESS  read-only
		STATUS  mandatory
		DESCRIPTION "Link aggregate port speed
			in bps."
		::= { restLgmPortEntry 12 }

restLgmPortDiagnostics 	OBJECT-TYPE
		SYNTAX	INTEGER {
			enable(1),
			disable(2),
			clearVILCBerWindowFill(64)
			}
		ACCESS  write-only
		STATUS  mandatory
		DESCRIPTION "INTRODUCED 2.0.0

			Enable on a disabled VILC will
			allow new channel connections to be
			made over this VILC.
			Disable will prevent any new channel
			connections from being made over this
			VILC.  This will not affect existing
			channel connections.
			ClearVILCBerWindowFill will remove the
			existing windows for BER
			calculations and restart it."
		::= { restLgmPortEntry 13 }

restLgmPortSyncState 	OBJECT-TYPE
		SYNTAX  INTEGER {
			inSync(1),
			los(2),
			ros(3),
			losAndRos(4)
			}
		ACCESS	read-only
		STATUS  mandatory
		DESCRIPTION "INTRODUCED 2.0.0

			Status of this LGM port
			synchronization state."
		::= { restLgmPortEntry 14 }


-- LGM Contents Status MIB

restLgmContentsTable 	OBJECT-TYPE
		SYNTAX	SEQUENCE OF RestLgmContentsEntry
		ACCESS  not-accessible
		STATUS 	mandatory
		DESCRIPTION "This table lists all of the
			channels on a specified LGM
			port."
		::=  { restLgmPort 2 }

restLgmContentsEntry 	OBJECT-TYPE
		SYNTAX	RestLgmContentsEntry
		ACCESS  not-accessible
		STATUS  mandatory
		DESCRIPTION " "
		INDEX { restLgmContentsAddr,
			restLgmContentsSequenceID }
		::=  { restLgmContentsTable 1 }

RestLgmContentsEntry		::=  SEQUENCE 	{
 			restLgmContentsAddr
	   			PortAddr,
			restLgmContentsSequenceID
				INTEGER,
 			restLgmContentsSourceNodeID
	   			NodeAddr,
 			restLgmContentsSourceAddr
	   			ChannelAddr,
 			restLgmContentsDestNodeID
	   			NodeAddr,
 			restLgmContentsDestAddr
	   			ChannelAddr
		  	}

restLgmContentsAddr 	OBJECT-TYPE
		SYNTAX	PortAddr
		ACCESS	read-only
		STATUS	mandatory
		DESCRIPTION "LGM Virtual Link address."
		::= { restLgmContentsEntry 1 }

restLgmContentsSequenceID 	OBJECT-TYPE
		SYNTAX  INTEGER (1..65535)
		ACCESS  read-only
		STATUS  mandatory
		DESCRIPTION "Index to multiple channels
			assigned to this port."
		::= { restLgmContentsEntry 2 }

restLgmContentsSourceNodeID 	OBJECT-TYPE
		SYNTAX	NodeAddr
		ACCESS  read-only
		STATUS  mandatory
		DESCRIPTION "Source node ID."
		::= { restLgmContentsEntry 3 }

restLgmContentsSourceAddr 	OBJECT-TYPE
		SYNTAX	ChannelAddr
		ACCESS  read-only
		STATUS 	mandatory
		DESCRIPTION "Source address in
			nest:slot:port:element format."
		::= { restLgmContentsEntry 4 }

restLgmContentsDestNodeID 	OBJECT-TYPE
		SYNTAX  NodeAddr
		ACCESS  read-only
		STATUS  mandatory
		DESCRIPTION "Destination node ID."
		::= { restLgmContentsEntry 5 }

restLgmContentsDestAddr 	OBJECT-TYPE
		SYNTAX	ChannelAddr
		ACCESS  read-only
		STATUS  mandatory
		DESCRIPTION "Destination address in
			nest:slot:port:element format."
		::= { restLgmContentsEntry 6 }


-- SAF status

restSaf 	OBJECT IDENTIFIER ::= { reStatus 15 }

-- SAF Port status

restSafTable 	OBJECT-TYPE
		SYNTAX	SEQUENCE OF RestSafEntry
		ACCESS	not-accessible
		STATUS  mandatory
		DESCRIPTION "This section of the MIB does not
			    support getNext."
		::= { restSaf 1 }

restSafEntry 	OBJECT-TYPE
		SYNTAX	RestSafEntry
		ACCESS  not-accessible
		STATUS	mandatory
		DESCRIPTION " "
		INDEX { restSafAddr }
		::= { restSafTable 1 }

RestSafEntry 	::= SEQUENCE {
			restSafAddr
			    PortAddr,
			restSafStatus
			    INTEGER,
			restSafSubStatus
			    INTEGER,
			restSafRemoteNode
			    NodeAddr,
			restSafRemoteAddr
			    PortAddr,
			restSafInlNumber
			    INTEGER,
			restSafBandwidthAvail
			    INTEGER,
			restSafNumChannels
			    INTEGER,
			restSafHWPhasorStatus
			    OCTET STRING,
			restSafSWPhasorStatus
			    OCTET STRING,
			restSafModNumChannels
			    INTEGER,
			restSafModBandwidthAvail
			    INTEGER,
			restSafDiagnostics
			    INTEGER,
			restSafFrameSwitchLocation
			    INTEGER,
			restSafFrameSwitchIndicator
			    INTEGER,
			restSafRemoteStatus
			    INTEGER,
			restSafSyncErrors
			    Counter,
			restSafOosErrors
			    Counter,
			restSafPhasorStatus
			    OCTET STRING
			}

restSafAddr 	OBJECT-TYPE
		SYNTAX	PortAddr
		ACCESS  read-only
		STATUS	mandatory
		DESCRIPTION "SAF address."
		::= { restSafEntry 1 }

restSafStatus 	OBJECT-TYPE
		SYNTAX	INTEGER {
			inSync(1),
			outOfSync(2),
			frameSwitch(3)
			}
		ACCESS  read-only
		STATUS	mandatory
		DESCRIPTION "Indicates whether the SAF is
			    synchronized or not, or whether the SAF is
			    currently in the middle of a frame switch."
		::= { restSafEntry 2 }

restSafSubStatus 	OBJECT-TYPE
		SYNTAX	INTEGER {
			syncError(1),
			noError(255)
			}
		ACCESS  read-only
		STATUS	mandatory
		DESCRIPTION "If the SAF status is out of sync,
			    then this attribute indicates if it is due
			    to an error or not. If the SAF is in sync
			    or in the middle of a frame switch, then
			    this attribute shall return no error."
		::= { restSafEntry 3 }

restSafRemoteNode 	OBJECT-TYPE
		SYNTAX	NodeAddr
		ACCESS  read-only
		STATUS	mandatory
		DESCRIPTION "The node in which the remote side
			    of this SAF connection resides."
		::= { restSafEntry 4 }

restSafRemoteAddr 	OBJECT-TYPE
		SYNTAX	PortAddr
		ACCESS  read-only
		STATUS	mandatory
		DESCRIPTION "The address of the remote side of
			    this SAF connection."
		::= { restSafEntry 5 }

restSafInlNumber 	OBJECT-TYPE
		SYNTAX	INTEGER (1..32)
		ACCESS  read-only
		STATUS	mandatory
		DESCRIPTION "The local INL number that this SAF
			   is located on. For a local SAF,
			   this attribute shall return 32."
		::= { restSafEntry 6 }

restSafBandwidthAvail 	OBJECT-TYPE
		SYNTAX	INTEGER (0..64000)
		ACCESS  read-only
		STATUS	mandatory
		DESCRIPTION "The available (unused) bandwidth
			    in this SAF according to the NCP."
		::= { restSafEntry 7 }

restSafNumChannels 	OBJECT-TYPE
		SYNTAX	INTEGER (0..47)
		ACCESS  read-only
		STATUS	mandatory
		DESCRIPTION "The number of subrate channels
			    currently connected through this SAF
			    according to the NCP."
		::= { restSafEntry 8 }

restSafHWPhasorStatus 	OBJECT-TYPE
		SYNTAX	OCTET STRING (SIZE (2))
		ACCESS  read-only
		STATUS	deprecated
		DESCRIPTION "DEPRECATED 2.0.1
			    This attribute will always return x8080,
			    which means not applicable."
		::= { restSafEntry 9 }

restSafSWPhasorStatus 	OBJECT-TYPE
		SYNTAX	OCTET STRING (SIZE (2))
		ACCESS  read-only
		STATUS	deprecated
		DESCRIPTION "DEPRECATED 2.0.1
			    This attribute will always return x8080,
			    which means not applicable."
		::= { restSafEntry 10 }

restSafModNumChannels 	OBJECT-TYPE
		SYNTAX	INTEGER (0..47)
		ACCESS  read-only
		STATUS	mandatory
		DESCRIPTION "INTRODUCED 2.0.1
			    The number of subrate channels currently
			    connected through this SAF according to the
			    module that this endpoint of the SAF
			    resides on."
		::= { restSafEntry 11 }

restSafModBandwidthAvail 	OBJECT-TYPE
		SYNTAX	INTEGER (0..64000)
		ACCESS  read-only
		STATUS	mandatory
		DESCRIPTION "INTRODUCED 2.0.1
			    The available (unused) bandwidth in this
			    SAF according to the module that this
			    endpoint of the SAF resides on."
		::= { restSafEntry 12 }

restSafDiagnostics 	OBJECT-TYPE
		SYNTAX  INTEGER {
			    clearStats(3),
			    setLoopback(9),
			    clearLoopback(8)
			}
		ACCESS  write-only
		STATUS  mandatory
		DESCRIPTION "INTRODUCED 2.0.1
			    clearStats will clear the counters in this
			    MIB section.

			    setLoopback will initiate a loopback on
			    this SAF. This will loopback all of the
			    channels within the SAF. Currently, the
			    only type of loopback that is supported is
			    a bidirectional bus loopback.

			    clearLoopback will clear the loopback on
			    this SAF if one exists."
		::= { restSafEntry 13 }

restSafFrameSwitchLocation 	OBJECT-TYPE
		SYNTAX  INTEGER (0..3)
		ACCESS  read-only
		STATUS  mandatory
		DESCRIPTION "INTRODUCED 2.0.1
			    If a frame switch is currently occurring on
			    this SAF, then this attribute indicates the
			    location of that frame switch. The value is
			    a sum with an initial value of zero. For
			    each possible frame switch location L in
			    the range 1 to 2, the value 2 raised to
			    (L - 1) is added to the sum if there is a
			    frame switch in that location. The possible
			    frame switch locations are the following:
			L	location
			1	add bus
			2	drop bus

			    Thus, if there is a frame switch on the add
			    bus, the value returned would be 1. If
			    there is a frame switch on the drop bus,
			    the value returned would be 2. If there is
			    a frame switch on both the add and the drop
			    busses, then the value returned would be 3.

			    If there is no frame switch occurring, then
			    the value returned will be zero (0),
			    indicating no frame switch locations."
		::= { restSafEntry 14 }

restSafFrameSwitchIndicator 	OBJECT-TYPE
		SYNTAX  INTEGER {
			    yes(1),
			    no(2)
			}
		ACCESS  read-only
		STATUS  mandatory
		DESCRIPTION "INTRODUCED 2.0.1
			    Indicates if a frame switch is needed on
			    this SAF or not."
		::= { restSafEntry 15 }

restSafRemoteStatus 	OBJECT-TYPE
		SYNTAX  INTEGER {
			    in-service(1),
			    out-of-service(2)
			}
		ACCESS  read-only
		STATUS  mandatory
		DESCRIPTION "INTRODUCED 2.0.1
			    The view of the remote endpoint of SAF from
			    the module that this endpoint of the SAF
			    resides on."
		::= { restSafEntry 16 }

restSafSyncErrors 	OBJECT-TYPE
		SYNTAX  Counter
		ACCESS  read-only
		STATUS  mandatory
		DESCRIPTION "INTRODUCED 2.0.1
			    The number of sync errors on this SAF."
		::= { restSafEntry 17 }

restSafOosErrors 	OBJECT-TYPE
		SYNTAX  Counter
		ACCESS  read-only
		STATUS  mandatory
		DESCRIPTION "INTRODUCED 2.0.1
			    The number of OOS errors on this SAF."
		::= { restSafEntry 18 }

restSafPhasorStatus 	OBJECT-TYPE
		SYNTAX  OCTET STRING (SIZE (2))
		ACCESS  read-only
		STATUS  mandatory
		DESCRIPTION "INTRODUCED 2.0.1
			    The status of the phasor for this SAF.

			    The first octet is used to indicate transmit
			    phasor status. The bits are interpretted as
			    follows (bit 1 is the least significant bit
			    of the octet):
			bit 1: phasor underflow
			bit 2: phasor overflow
			bits 3-6: unused
			bit 7: software phasor (if clear,
			       hardware phasor)
			bit 8: phasor not applicable

			    The second octet is used to indicate receive
			    phasor status. The bits are interpretted as
			    follows (bit 1 is the least significant bit
			    of the octet):
			bit 1: phasor underflow
			bit 2: phasor overflow
			bits 3-6: unused
			bit 7: software phasor (if clear,
			       hardware phasor)
			bit 8: phasor not applicable

			    For both phasors (receive and transmit), if
			    the phasor is OK, then the octet will be
			    set to 0 for a hardware phasor, or x40 for
			    a software phasor. If there is no phasor of
			    that type (receive or transmit), then the
			    octet will be set to x80.

			    If the SAF does not support any phasors,
			    then the value returned for this attribute
			    will be x8080."
		::= { restSafEntry 19 }

-- SAF Port Contents status

restSafContentsTable 	OBJECT-TYPE
		SYNTAX	SEQUENCE OF RestSafContentsEntry
		ACCESS	not-accessible
		STATUS  mandatory
		DESCRIPTION "This section of the MIB lists all
			of the channels defined on an SAF. It
			does not support getNext."
		::=  { restSaf 2 }

restSafContentsEntry 	OBJECT-TYPE
		SYNTAX	RestSafContentsEntry
		ACCESS  not-accessible
		STATUS	mandatory
		DESCRIPTION " "
		INDEX { restSafContentsAddr,
			restSafContentsSeqNum }
		::=  { restSafContentsTable 1 }

RestSafContentsEntry 		::= SEQUENCE {
			restSafContentsAddr
			PortAddr,
			restSafContentsSeqNum
			INTEGER,
			restSafContentsSrcNode
			NodeAddr,
			restSafContentsSrcAddr
			ChannelAddr,
			restSafContentsDestNode
			NodeAddr,
			restSafContentsDestAddr
			ChannelAddr
			}

restSafContentsAddr 	OBJECT-TYPE
		SYNTAX	PortAddr
		ACCESS  read-only
		STATUS	mandatory
		DESCRIPTION "SAF address."
		::=  { restSafContentsEntry 1 }

restSafContentsSeqNum 	OBJECT-TYPE
		SYNTAX	INTEGER (1..65535)
		ACCESS  read-only
		STATUS	mandatory
		DESCRIPTION "SAF channel number."
		::=  { restSafContentsEntry 2 }

restSafContentsSrcNode 	OBJECT-TYPE
		SYNTAX	NodeAddr
		ACCESS  read-only
		STATUS	mandatory
		DESCRIPTION "Source node of the channel."
		::=  { restSafContentsEntry 3 }

restSafContentsSrcAddr 	OBJECT-TYPE
		SYNTAX	ChannelAddr
		ACCESS  read-only
		STATUS	mandatory
		DESCRIPTION "Source channel address."
		::=  { restSafContentsEntry 4 }

restSafContentsDestNode 	OBJECT-TYPE
		SYNTAX	NodeAddr
		ACCESS  read-only
		STATUS	mandatory
		DESCRIPTION "Destination node of the channel."
		::=  { restSafContentsEntry 5 }

restSafContentsDestAddr 	OBJECT-TYPE
		SYNTAX	ChannelAddr
		ACCESS  read-only
		STATUS	mandatory
		DESCRIPTION "Destination channel address."
		::=  { restSafContentsEntry 6 }


-- DSM Port Specific Status

restDsmPort 	OBJECT IDENTIFIER ::= { reStatus 16 }

-- DSM D-channel Port Status

restDsmDChPortTable 	OBJECT-TYPE
		SYNTAX  SEQUENCE OF RestDsmDChPortEntry
		ACCESS  not-accessible
		STATUS  mandatory
		DESCRIPTION "This section of the MIB contains
			the D-channel port status."
		::= { restDsmPort 1 }

restDsmDChPortEntry 	OBJECT-TYPE
		SYNTAX  RestDsmDChPortEntry
		ACCESS  not-accessible
		STATUS  mandatory
		DESCRIPTION "INTRODUCED 2.0.0"
		INDEX { restDsmDChPortAddr }
		::= { restDsmDChPortTable 1 }

RestDsmDChPortEntry		::=  SEQUENCE {
			restDsmDChPortAddr
				PortAddr,
			restDsmDChPortDiagnostics
				INTEGER,
			restDsmDChPortNumCallsInProc
				INTEGER,
			restDsmDChPortNumCallsConn
				INTEGER
			}

restDsmDChPortAddr 	OBJECT-TYPE
		SYNTAX  PortAddr
		ACCESS  read-only
		STATUS  mandatory
		DESCRIPTION "Address of D-channel port.
			Format is type.group.port. The
			server type is 131."
		::= { restDsmDChPortEntry 1 }

restDsmDChPortDiagnostics 	OBJECT-TYPE
		SYNTAX  INTEGER {
			layer2Reset(1)
			}
		ACCESS  write-only
		STATUS  mandatory
		DESCRIPTION "When set to layer2Reset all
			B-channels associated with this
			D-channel will be disconnected
			(the D-channel itself will stay
			connected)."
		::= { restDsmDChPortEntry 2 }

restDsmDChPortNumCallsInProc 	OBJECT-TYPE
		SYNTAX  INTEGER
		ACCESS  read-only
		STATUS  mandatory
		DESCRIPTION "Current number of calls in process
			of being completed (until CONNECT
			messages exchange took place)."
		::= { restDsmDChPortEntry 3 }

restDsmDChPortNumCallsConn 	OBJECT-TYPE
		SYNTAX  INTEGER
		ACCESS  read-only
		STATUS  mandatory
		DESCRIPTION "Current number of calls connected
			via this D-channel."
		::= { restDsmDChPortEntry 4 }


-- DSM D-Channel Port Real Call Status MIB

restDsmDChCallRealTable 	OBJECT-TYPE
		SYNTAX  SEQUENCE OF RestDsmDChCallRealEntry
		ACCESS  not-accessible
		STATUS  mandatory
		DESCRIPTION "This section of the MIB contains
			    information about a real call from the
			    point of view of the DSM that its D-channel
			    is allocated on."
		::= { restDsmPort 2 }

restDsmDChCallRealEntry 	OBJECT-TYPE
		SYNTAX  RestDsmDChCallRealEntry
		ACCESS  not-accessible
		STATUS  mandatory
		DESCRIPTION "INTRODUCED 2.0.0"
		INDEX { restDsmDChCallRealAddr,
			restDsmDChCallRealBundle }
		::= { restDsmDChCallRealTable 1 }

RestDsmDChCallRealEntry		::= SEQUENCE {
			restDsmDChCallRealAddr
			    PortAddr,
			restDsmDChCallRealBundle
			    INTEGER,
			restDsmDChCallRealCDRContents
			    OCTET STRING,
			restDsmDChCallRealDiagnostics
			    INTEGER,
			restDsmDChCallRealLayer2Status
			    INTEGER,
			restDsmDChCallRealLayer2State
			    INTEGER,
			restDsmDChCallRealLayer3State
			    INTEGER,
			restDsmDChCallRealTransitState
			    INTEGER
			}

restDsmDChCallRealAddr 	OBJECT-TYPE
		SYNTAX  PortAddr
		ACCESS  read-only
		STATUS  mandatory
		DESCRIPTION "Address of the D-channel port
			    associated with this real call. Format is
			    type(131).group.port."
		::= { restDsmDChCallRealEntry 1 }

restDsmDChCallRealBundle 	OBJECT-TYPE
		SYNTAX  INTEGER (1..31)
		ACCESS  read-only
		STATUS  mandatory
		DESCRIPTION "Bundle number of the B-channel
			    used for this real call."
		::= { restDsmDChCallRealEntry 2 }

restDsmDChCallRealCDRContents 	OBJECT-TYPE
		SYNTAX  OCTET STRING (SIZE (0..112))
		ACCESS  read-only
		STATUS  mandatory
		DESCRIPTION "Call Detail Record for a real call
			in progress on a D-channel. Real calls are
			those that involve B-channels.
 
			The bytes in a CDR for a call in progress
			are interpretted as follows (note that this
			is the same as the interpretation for CDRs
			associated with active virtual calls):
 
			Part 1: generic information
			1: CDR type, values are:
				level 1 (1)
				level 2 (2)
				active (3) - this applies for
					both Part 2 and Part 3
				not applicable (0) - this means
					that there is no active CDR for
					this real call ID,
			2: unused
			3-4: partition ID
			5-6: call ID
			7-8: unused
 
			Part 2: Level 1 (Physical Characteristics):
			9-12: originating time
			13-16: answer time
			17-20: disconnect time
			21-22: B-channel source node ID
			23: B-channel source nest ID
			24: B-channel source slot ID
			25-26: B-channel source port ID
			27-28: B-channel source channel ID
			29-30: B-channel destination node ID
			31: B-channel destination nest ID
			32: B-channel destination slot ID
			33-34: B-channel destination port ID
			35-36: B-channel destination channel ID
			37: call type, values are:
				real (3)
				virtual (0)
			38: special profile type, values defined
				in attribute recfDsmDChQOSCallType
			39: info type, values are:
				Q.Sig speech (0)
				DPNSS A-law (1)
				DPNSS ADPCM (2)
				DPNSS Mu-law (3)
				Unrestricted data (8)
				Restricted data (9)
				3.1 KHz audio (16)
				7 KHz audio (17)
				video (24)
			40: special profile index
			41: channel profile index
			42: unused (needed for NCP clear cause,
				which is never valid for calls in progress)
			43: unused (needed for clear cause,
				which is never valid for calls in progress)
			44: number of call attempts between DSMs
			45-48: transmission rate
 
			Part 3: Level 2 (Data Link Layer):
			49-52: setup final time
			53-56: connect request time
			57-60: connect response time
			61-62: source node ID
			63: source nest ID
			64: source slot ID
			65-66: destination node ID
			67: destination nest ID
			68: destination slot ID
			69: calling number size (number of
				bytes, not string length) - this
				number is referred to from now on as x
			70-(69+x): calling number
			(70+x): called number size (number of
				bytes, not string length) -
				this number is referred to from
				now on as y
			(71+x)-(70+x+y): called number
			(71+x+y): routing digits
			(72+x+y): unused."
		::= { restDsmDChCallRealEntry 3 }

restDsmDChCallRealDiagnostics 	OBJECT-TYPE
		SYNTAX  INTEGER {
			    resetLayer2(1)
			}
		ACCESS  write-only
		STATUS  mandatory
		DESCRIPTION "INTRODUCED 2.0.1
			    resetLayer2 will reset the Layer 2 protocol
			    on the specified B-channel. It is not
			    supported for Q.Sig."
		::= { restDsmDChCallRealEntry 4 }

restDsmDChCallRealLayer2Status 	OBJECT-TYPE
		SYNTAX  INTEGER {
			    pending(1),
			    in-service(2),
			    layer2Timeout(3),
			    layer2Mismatch(4),
			    notApplicable(255)
			}
		ACCESS  read-only
		STATUS  mandatory
		DESCRIPTION "INTRODUCED 2.0.1
			    Indicates the Layer 2 status of a real call
			    the point of view of the DSM. Not applicable
			    will be returned for the D-channel bundle
			    if the DPNSS protocol is used and for the
			    bundles not used for the D-channel if the
			    Q.Sig protocol is used."
		::= { restDsmDChCallRealEntry 5 }

restDsmDChCallRealLayer2State 	OBJECT-TYPE
		SYNTAX  INTEGER {
			    idle(1),
			    ready(2),
			    waitingForResponse(3),
			    waitingForEstablishment(4),
			    outOfService(5),
			    unassignedTEI(129),
			    assignAwaitingTEI(130),
			    establishAwaitingTEI(131),
			    assignedTEI(132),
			    awaitingEstablishment(133),
			    awaitingRelease(134),
			    multipleFrameEstablished(135),
			    timeRecovery(136),
			    notApplicable(255)
			}
		ACCESS  read-only
		STATUS  mandatory
		DESCRIPTION "INTRODUCED 2.0.1
			    Indicates the Layer 2 protocol state of a
			    real call from the point of view of the DSM.
			    The values between 1 and 127 are used for
			    DPNSS states. The values between 128 and 254
			    are used for Q.Sig states. Not applicable
			    will be returned for the D-channel bundle
			    if the DPNSS protocol is used and for the
			    bundles not used for the D-channel if the
			    Q.Sig protocol is used."
		::= { restDsmDChCallRealEntry 6 }

restDsmDChCallRealLayer3State 	OBJECT-TYPE
		SYNTAX  INTEGER {
			    inactive(1),
			    idle(2),
			    outgoingService(3),
			    incomingService(4),
			    awaitNAMOut(5),
			    awaitNAMIn(6),
			    awaitCCMOut(7),
			    awaitCCMIn(8),
			    setupComplete(9),
			    callRejecting(10),
			    callClearing(11),
			    callBarred(12),
			    preIdle(13),
			    awaitRelease(14),
			    nullState(129),
			    callInit(130),
			    overlapSending(131),
			    outgoingCallProceeding(132),
			    callDelivered(133),
			    callPresent(135),
			    callReceived(136),
			    connectRequest(137),
			    incomingCallProceeding(138),
			    callActive(139),
			    disconnectRequest(140),
			    disconnectIndication(141),
			    suspendRequest(144),
			    resumeRequest(146),
			    releaseRequest(148),
			    overlapReceive(154),
			    idleState(155),
			    establishWait(156),
			    passiveAwaitingConf(157),
			    callPassive(158),
			    registerRequest(159),
			    cancelRequest(160),
			    asaiTr1State(161),
			    u10HoldRequest(162),
			    u10TransferRequest(163),
			    u10ConferenceRequest(164),
			    u10ReconnectRequest(165),
			    u10AwaitingDisc(166),
			    u10CallOnHold(167),
			    deactivated(168),
			    reactivateRequested(169),
			    deactivateRequested(170),
			    nilHoldReqU3(171),
			    nilHoldReqU4(172),
			    nilHoldReqU10(173),
			    nilRetrieveU3(174),
			    nilRetrieveU4(175),
			    nilRetrieveU10(176),
			    nilHoldActiveU3(177),
			    nilHoldActiveU4(178),
			    nilHoldActiveU10(179),
			    broadcastState(180),
			    notApplicable(255)
			}
		ACCESS  read-only
		STATUS  mandatory
		DESCRIPTION "INTRODUCED 2.0.1
			    Indicates the Layer 3 protocol state on a
			    real call from the point of view of the DSM.
			    The values between 1 and 127 are used for
			    DPNSS states. The values between 128 and 254
			    are used for Q.Sig states. Not applicable
			    will be returned for the D-channel bundle."
		::= { restDsmDChCallRealEntry 7 }

restDsmDChCallRealTransitState 	OBJECT-TYPE
		SYNTAX  INTEGER {
			    inactive(1),
			    idle(2),
			    awaitDigits(3),
			    awaitAdditionalDigits(4),
			    overlap(5),
			    incomingCallProceeding(6),
			    transitCallProceeding(7),
			    callAlerting(8),
			    active(9),
			    awaitIncomingRelease(10),
			    awaitOutgoingRelease(11),
			    awaitTwoWayRelease(12),
			    awaitCallRealChannelResponse(13),
			    awaitNcpReleaseResponse(14),
			    awaitNcpReleaseNoResponse(15),
			    awaitNcpRelease(16),
			    awaitNcpDisconnect(17),
			    awaitNcp(18),
			    notApplicable(255)
			}
		ACCESS  read-only
		STATUS  mandatory
		DESCRIPTION "INTRODUCED 2.0.1
			    Indicates the transit call control state of
			    a real call from the point of view of the
			    DSM. Not applicable will be returned for
			    the D-channel bundle."
		::= { restDsmDChCallRealEntry 8 }


-- DSM D-Channel Port Virtual Call Status MIB

restDsmDChCallVirtTable 	OBJECT-TYPE
		SYNTAX  SEQUENCE OF RestDsmDChCallVirtEntry
		ACCESS  not-accessible
		STATUS  mandatory
		DESCRIPTION "This section of the MIB contains
			    information about a virtual call from the
			    point of view of the DSM that its D-channel
			    is allocated on."
		::= { restDsmPort 3 }

restDsmDChCallVirtEntry 	OBJECT-TYPE
		SYNTAX  RestDsmDChCallVirtEntry
		ACCESS  not-accessible
		STATUS  mandatory
		DESCRIPTION "INTRODUCED 2.0.0"
		INDEX { restDsmDChCallVirtAddr,
			restDsmDChCallVirtNumber }
		::= { restDsmDChCallVirtTable 1 }

RestDsmDChCallVirtEntry		::= SEQUENCE {
			restDsmDChCallVirtAddr
			    PortAddr,
			restDsmDChCallVirtNumber
			    INTEGER,
			restDsmDChCallVirtCDRContents
			    OCTET STRING,
			restDsmDChCallVirtDiagnostics
			    INTEGER,
			restDsmDChCallVirtLayer2Status
			    INTEGER,
			restDsmDChCallVirtLayer2State
			    INTEGER,
			restDsmDChCallVirtLayer3State
			    INTEGER,
			restDsmDChCallVirtTransitState
			    INTEGER
			}

restDsmDChCallVirtAddr 	OBJECT-TYPE
		SYNTAX  PortAddr
		ACCESS  read-only
		STATUS  mandatory
		DESCRIPTION "Address of the D-channel port
			    associated with this virtual call. Format
			    is type(131).group.port."
		::= { restDsmDChCallVirtEntry 1 }

restDsmDChCallVirtNumber 	OBJECT-TYPE
		SYNTAX  INTEGER (1..480)
		ACCESS  read-only
		STATUS  mandatory
		DESCRIPTION "Identity of the virtual call to be
			   accessed. For the DPNSS protocol, this index
			   is a bundle number in the range of 1 to 31.
			   For the Q.Sig protocol, this index is an
			   artificial entity and does not reflect any
			   information about the call origination time."
		::= { restDsmDChCallVirtEntry 2 }

restDsmDChCallVirtCDRContents 	OBJECT-TYPE
		SYNTAX  OCTET STRING (SIZE (0..112))
		ACCESS  read-only
		STATUS  mandatory
		DESCRIPTION "Call Detail Record for a virtual
			call in progress on a D-channel. Virtual
			calls are those that do not involve
			B-channels.
 
			The bytes in a CDR for a call in progress
			are interpretted as follows (note that this
			is the same as the interpretation for CDRs
			associated with active real calls on a
			B-channel):
 
			Part 1: generic information
			1: CDR type, values are:
				level 1 (1)
				level 2 (2)
				active (3) - this applies for
					both Part 2 and Part 3
				not applicable (0) - this means
					that there is no active CDR for
					this virtual call ID
			2: unused
			3-4: partition ID
			5-6: call ID
			7-8: unused
 
			Part 2: Level 1 (Physical Characteristics):
			9-12: originating time
			13-16: answer time
			17-20: disconnect time
			21-22: B-channel source node ID
			23: B-channel source nest ID
			24: B-channel source slot ID
			25-26: B-channel source port ID
			27-28: B-channel source channel ID
			29-30: B-channel destination node ID
			31: B-channel destination nest ID
			32: B-channel destination slot ID
			33-34: B-channel destination port ID
			35-36: B-channel destination channel ID
			37: call type, values are:
				real (3)
				virtual (0)
			38: special profile type, values defined
				in attribute recfDsmDChQOSCallType
			39: info type, values are:
				Q.Sig speech (0)
				DPNSS A-law (1)
				DPNSS ADPCM (2)
				DPNSS Mu-law (3)
				Unrestricted data (8)
				Restricted data (9)
				3.1 KHz audio (16)
				7 KHz audio (17)
				video (24)
			40: special profile index
			41: channel profile index
			42: unused (needed for NCP clear cause,
				which is never valid for calls in
				progress)
			43: unused (needed for clear cause,
				which is never valid for calls in
				progress)
			44: number of call attempts between DSMs
			45-48: transmission rate
 
			Part 3: Level 2 (Data Link Layer):
			49-52: setup final time
			53-56: connect request time
			57-60: connect response time
			61-62: source node ID
			63: source nest ID
			64: source slot ID
			65-66: destination node ID
			67: destination nest ID
			68: destination slot ID
			69: calling number size (number of
				bytes, not string length) - this
				number is referred to from now on as x
			70-(69+x): calling number
			(70+x): called number size (number of
				bytes, not string length) -
				this number is referred to from
				now on as y
			(71+x)-(70+x+y): called number
			(71+x+y): routing digits
			(72+x+y): unused."
		::= { restDsmDChCallVirtEntry 3 }

restDsmDChCallVirtDiagnostics 	OBJECT-TYPE
		SYNTAX  INTEGER {
			    resetLayer2(1)
			}
		ACCESS  write-only
		STATUS  mandatory
		DESCRIPTION "INTRODUCED 2.0.1
			    resetLayer2 will reset the Layer 2 protocol
			    for the specified virtual call. It is not
			    supported for Q.Sig."
		::= { restDsmDChCallVirtEntry 4 }

restDsmDChCallVirtLayer2Status 	OBJECT-TYPE
		SYNTAX  INTEGER {
			    pending(1),
			    in-service(2),
			    layer2Timeout(3),
			    layer2Mismatch(4),
			    notApplicable(255)
			}
		ACCESS  read-only
		STATUS  mandatory
		DESCRIPTION "INTRODUCED 2.0.1
			    Indicates the Layer 2 status of a virtual
			    call from the point of view of the DSM. Not
			    applicable will be returned for the
			    D-channel bundle if the DPNSS protocol is
			    used and for all virtual calls if the Q.Sig
			    protocol is used."
		::= { restDsmDChCallVirtEntry 5 }

restDsmDChCallVirtLayer2State 	OBJECT-TYPE
		SYNTAX  INTEGER {
			    idle(1),
			    ready(2),
			    waitingForResponse(3),
			    waitingForEstablishment(4),
	                    outOfService(5),
			    unassignedTEI(129),
			    assignAwaitingTEI(130),
			    establishAwaitingTEI(131),
			    assignedTEI(132),
			    awaitingEstablishment(133),
			    awaitingRelease(134),
			    multipleFrameEstablished(135),
			    timeRecovery(136),
			    notApplicable(255)
			}
		ACCESS  read-only
		STATUS  mandatory
		DESCRIPTION "INTRODUCED 2.0.1
			    Indicates the Layer 2 protocol state of a
			    virtual call from the point of view of the
			    DSM. The values between 1 and 127 are used
			    for DPNSS states. The values between 128
			    and 254 are used for Q.Sig states. Not
			    applicable will be returned for the
			    D-channel bundle if the DPNSS protocol is
			    used and for all virtual calls if the Q.Sig
			    protocol is used."
		::= { restDsmDChCallVirtEntry 6 }

restDsmDChCallVirtLayer3State 	OBJECT-TYPE
		SYNTAX  INTEGER {
			    inactive(1),
			    idle(2),
			    outgoingService(3),
			    incomingService(4),
			    awaitNAMOut(5),
			    awaitNAMIn(6),
			    awaitCCMOut(7),
			    awaitCCMIn(8),
			    setupComplete(9),
			    callRejecting(10),
			    callClearing(11),
			    callBarred(12),
	                    preIdle(13),
	                    awaitRelease(14),
			    nullState(129),
			    callInit(130),
			    overlapSending(131),
			    outgoingCallProceeding(132),
			    callDelivered(133),
			    callPresent(135),
			    callReceived(136),
			    connectRequest(137),
			    incomingCallProceeding(138),
			    callActive(139),
			    disconnectRequest(140),
			    disconnectIndication(141),
			    suspendRequest(144),
			    resumeRequest(146),
			    releaseRequest(148),
			    overlapReceive(154),
			    idleState(155),
			    establishWait(156),
	                    passiveAwaitingConf(157),
	                    callPassive(158),
	                    registerRequest(159),
	                    cancelRequest(160),
	                    asaiTr1State(161),
	                    u10HoldRequest(162),
	                    u10TransferRequest(163),
	                    u10ConferenceRequest(164),
	                    u10ReconnectRequest(165),
	                    u10AwaitingDisc(166),
	                    u10CallOnHold(167),
	                    deactivated(168),
	                    reactivateRequested(169),
	                    deactivateRequested(170),
	                    nilHoldReqU3(171),
	                    nilHoldReqU4(172),
	                    nilHoldReqU10(173),
	                    nilRetrieveU3(174),
	                    nilRetrieveU4(175),
	                    nilRetrieveU10(176),
	                    nilHoldActiveU3(177),
	                    nilHoldActiveU4(178),
	                    nilHoldActiveU10(179),
	                    broadcastState(180),
			    notApplicable(255)
			}
		ACCESS  read-only
		STATUS  mandatory
		DESCRIPTION "INTRODUCED 2.0.1
			    Indicates the Layer 3 protocol state of a
			    virtual call from the point of view of the
			    DSM. The values between 1 and 127 are used
			    for DPNSS states. The values between 128
			    and 254 are used for Q.Sig states. Not
			    applicable will be returned for the
			    D-channel bundle if the DPNSS protocol is
			    used."
		::= { restDsmDChCallVirtEntry 7 }

restDsmDChCallVirtTransitState 	OBJECT-TYPE
		SYNTAX  INTEGER {
			    inactive(1),
			    idle(2),
			    awaitDigits(3),
			    awaitAdditionalDigits(4),
			    overlap(5),
			    incomingCallProceeding(6),
			    transitCallProceeding(7),
			    callAlerting(8),
			    active(9),
			    awaitIncomingRelease(10),
			    awaitOutgoingRelease(11),
			    awaitTwoWayRelease(12),
			    awaitCallVirtChannelResponse(13),
	                    awaitNcpReleaseResponse(14),
	                    awaitNcpReleaseNoResponse(15),
	                    awaitNcpRelease(16),
	                    awaitNcpDisconnect(17),
	                    awaitNcp(18),
			    notApplicable(255)
			}
		ACCESS  read-only
		STATUS  mandatory
		DESCRIPTION "INTRODUCED 2.0.1
			    Indicates the transit call control state of
			    a virtual call from the point of view of
			    the DSM. Not applicable will be returned
			    for the D-channel bundle if the DPNSS
			    protocol is used."
		::= { restDsmDChCallVirtEntry 8 }


-- Hardware Resource Status MIB

restHwRsc 	OBJECT IDENTIFIER ::= { reStatus 17 }

-- Engine Status MIB

restHwRscEngineTable 	OBJECT-TYPE
		SYNTAX    SEQUENCE OF RestHwRscEngineEntry
		ACCESS    not-accessible
		STATUS    mandatory
		DESCRIPTION "This section of the MIB returns
			status of an on-board engine."
		::= { restHwRsc 1 }

restHwRscEngineEntry 	OBJECT-TYPE
		SYNTAX	RestHwRscEngineEntry
		ACCESS    not-accessible
		STATUS    mandatory
		DESCRIPTION "INTRODUCED 2.0.0"
		INDEX { restHwRscEngineModAddr,
			restHwRscEngineID }
		::= { restHwRscEngineTable 1 }

RestHwRscEngineEntry		::= SEQUENCE {
		restHwRscEngineModAddr
			SlotAddr,
		restHwRscEngineID
			INTEGER,
		restHwRscEngineDiagnostics
			INTEGER,
		restHwRscEngineStatus
			INTEGER,
		restHwRscEngineApplication
			INTEGER,
		restHwRscEngineMaxPorts
			INTEGER,
		restHwRscEngineNumPorts
			INTEGER,
		restHwRscEngineMaxSAFs
			INTEGER,
		restHwRscEngineNumSAFs
			INTEGER,
		restHwRscEngineMaxSCFs
			INTEGER,
		restHwRscEngineNumSCFs
			INTEGER,
		restHwRscEngineMaxLoad
			INTEGER,
		restHwRscEngineCurLoad
			INTEGER,
		restHwRscEngineSubStatus
			INTEGER
			}

restHwRscEngineModAddr 	OBJECT-TYPE
		SYNTAX	SlotAddr
		ACCESS	read-only
		STATUS  mandatory
		DESCRIPTION "Physical address of the module
			this engine is located on."
		::= { restHwRscEngineEntry 1 }

restHwRscEngineID 	OBJECT-TYPE
		SYNTAX	INTEGER (1..16)
		ACCESS	read-only
		STATUS  mandatory
		DESCRIPTION "The engine ID on the module."
		::= { restHwRscEngineEntry 2 }

restHwRscEngineDiagnostics 	OBJECT-TYPE
		SYNTAX  INTEGER {
			    insert(4),
			    remove(5),
			    reset(6)
			}
		ACCESS  write-only
		STATUS  mandatory
		DESCRIPTION "Insert will allow a removed engine
			    to come online again using the current
			    settings in the engine configuration MIB
			    (recfHwRscEngineTable). The start mode of
			    the engine (recfHwRscEngineStartMode) will
			    be set to automatic. This command will fail
			    if the engine is not removed.
 
			    Remove will take an active engine offline
			    and force a disconnect of any channels on
			    the engine. The start mode of the engine
			    will be set to offline. This command will
			    fail if the engine is already offline.
 
			    Reset will remove and then insert the
			    engine. It will not change the engine start
			    mode, but will load the current settings in
			    the engine configuration MIB. If the engine
			    is currently offline, then the remove
			    action will not be taken. In this case, the
			    reset is equivalent to an insert. If the
			    engine start mode is set to offline, then
			    the insert action will not be taken. In
			    this case, the reset is equivalent to a
			    remove. This command will force a
			    disconnect of any channels on the engine."
		::= { restHwRscEngineEntry 3 }


restHwRscEngineStatus 	OBJECT-TYPE
		SYNTAX 	INTEGER {
			removed(5),
			normal(6),
			failed(43)
			}
		ACCESS  read-only
		STATUS  mandatory
		DESCRIPTION "This engine status:
			<removed>	- logically removed,
			<normal>	- up and running
			<failed>	- engine failure."
		::= { restHwRscEngineEntry 4 }

restHwRscEngineApplication 	OBJECT-TYPE
		SYNTAX	INTEGER {
			x50(1),
			celp-atc(2),
			adpcm(3),
			link(4),
			none(255)
			}
		ACCESS	read-only
		STATUS	mandatory
		DESCRIPTION "Indicates the type of application
			allocated on this engine, if any."
		::= { restHwRscEngineEntry 5 }

restHwRscEngineMaxPorts 	OBJECT-TYPE
		SYNTAX  INTEGER
		ACCESS  read-only
		STATUS  mandatory
		DESCRIPTION "Maximum number of application ports
			on this engine. If none returns zero."
		::= { restHwRscEngineEntry 6 }

restHwRscEngineNumPorts 	OBJECT-TYPE
		SYNTAX  INTEGER
		ACCESS  read-only
		STATUS  mandatory
		DESCRIPTION "Number of application ports
			on this engine. If none returns zero."
		::= { restHwRscEngineEntry 7 }

restHwRscEngineMaxSAFs 	OBJECT-TYPE
		SYNTAX  INTEGER
		ACCESS  read-only
		STATUS  mandatory
		DESCRIPTION "Maximum number of SAF ports on this
			engine. If none returns zero."
		::= { restHwRscEngineEntry 8 }

restHwRscEngineNumSAFs 	OBJECT-TYPE
		SYNTAX  INTEGER
		ACCESS  read-only
		STATUS  mandatory
		DESCRIPTION "Number of SAF ports on this
			engine. If none returns zero."
		::= { restHwRscEngineEntry 9 }

restHwRscEngineMaxSCFs 	OBJECT-TYPE
		SYNTAX  INTEGER
		ACCESS  read-only
		STATUS  mandatory
		DESCRIPTION "Maximum number of SCF ports on this
			engine. If none returns zero."
		::= { restHwRscEngineEntry 10 }

restHwRscEngineNumSCFs 	OBJECT-TYPE
		SYNTAX  INTEGER
		ACCESS  read-only
		STATUS  mandatory
		DESCRIPTION "Number of SCF ports on this
			engine. If none returns zero."
		::= { restHwRscEngineEntry 11 }

restHwRscEngineMaxLoad 	OBJECT-TYPE
		SYNTAX  INTEGER
		ACCESS  read-only
		STATUS  mandatory
		DESCRIPTION "Indicates the total load capacity
			of this engine."
		::= { restHwRscEngineEntry 12 }

restHwRscEngineCurLoad 	OBJECT-TYPE
		SYNTAX  INTEGER
		ACCESS  read-only
		STATUS  mandatory
		DESCRIPTION "Indicates the percentage of the
			total load capacity of this engine that
			is currently in use."
		::= { restHwRscEngineEntry 13 }


restHwRscEngineSubStatus 	OBJECT-TYPE
		SYNTAX  INTEGER {
			    startupDiagnosticsFailure(1),
			    noWellAndAlive(2),
			    none(255)
			}
		ACCESS  read-only
		STATUS  mandatory
		DESCRIPTION "INTRODUCED 2.0.1
			    If an engine is in a failed state, then
			    this value will indicate the reason for the
			    failure. If the engine is not failed, then
			    none will be returned."
		::= { restHwRscEngineEntry 14 }


-- Resource Statistics MIB

-- Port Statistics MIB

restStatPort 	OBJECT IDENTIFIER ::= { reStatistics 1 }


-- T1M Port Statistics

restStatPortT1mTable 	OBJECT-TYPE
		SYNTAX    SEQUENCE OF RestStatPortT1mEntry
		ACCESS    not-accessible
		STATUS    mandatory
		DESCRIPTION " "
		::= { restStatPort 1 }


restStatPortT1mEntry 	OBJECT-TYPE
		SYNTAX    RestStatPortT1mEntry
		ACCESS    not-accessible
		STATUS    mandatory
		DESCRIPTION " "
		INDEX	{ restStatPortT1mAddr,
			  restStatPortT1mIndex }
		::= { restStatPortT1mTable 1 }


RestStatPortT1mEntry	::= SEQUENCE {
		restStatPortT1mAddr
			PortAddr,
		restStatPortT1mIndex
			INTEGER,
		restStatPortT1mStartTime
			INTEGER,
		restStatPortT1mErrSec
			INTEGER,
		restStatPortT1mSevErrSec
			INTEGER,
		restStatPortT1mBstyErrSec
			INTEGER,
		restStatPortT1mUnavailSec
			INTEGER,
		restStatPortT1mLostFrame
			INTEGER,
		restStatPortT1mControlMode
			INTEGER
		}


restStatPortT1mAddr 	OBJECT-TYPE
		SYNTAX    PortAddr
		ACCESS    read-only
		STATUS    mandatory
		DESCRIPTION " "
		::= { restStatPortT1mEntry 1 }

restStatPortT1mIndex 	OBJECT-TYPE
		SYNTAX    INTEGER (0..96)
		ACCESS    read-only
		STATUS    mandatory
		DESCRIPTION " "
		::= { restStatPortT1mEntry 2 }

restStatPortT1mStartTime 	OBJECT-TYPE
		SYNTAX    INTEGER
		ACCESS    read-only
		STATUS    mandatory
		DESCRIPTION "Indicates when this statistics interval
			was started."
		::= { restStatPortT1mEntry 3 }

restStatPortT1mErrSec 	OBJECT-TYPE
		SYNTAX    INTEGER
		ACCESS    read-only
		STATUS    mandatory
		DESCRIPTION " "
		::= { restStatPortT1mEntry 4 }

restStatPortT1mSevErrSec 	OBJECT-TYPE
		SYNTAX    INTEGER
		ACCESS    read-only
		STATUS    mandatory
		DESCRIPTION " "
		::= { restStatPortT1mEntry 5 }

restStatPortT1mBstyErrSec 	OBJECT-TYPE
		SYNTAX    INTEGER
		ACCESS    read-only
		STATUS    mandatory
		DESCRIPTION " "
		::= { restStatPortT1mEntry 6 }

restStatPortT1mUnavailSec 	OBJECT-TYPE
		SYNTAX    INTEGER
		ACCESS    read-only
		STATUS    mandatory
		DESCRIPTION " "
		::= { restStatPortT1mEntry 7 }

restStatPortT1mLostFrame 	OBJECT-TYPE
		SYNTAX    INTEGER
		ACCESS    read-only
		STATUS    mandatory
		DESCRIPTION " "
		::= { restStatPortT1mEntry 8 }

restStatPortT1mControlMode 	OBJECT-TYPE
		SYNTAX    INTEGER {
			  clearStats(3)
			}
		ACCESS    write-only
		STATUS    mandatory
		DESCRIPTION " "
		::= { restStatPortT1mEntry 9 }

-- E1M Port Statistics

restStatPortE1mTable 	OBJECT-TYPE
		SYNTAX    SEQUENCE OF RestStatPortE1mEntry
		ACCESS    not-accessible
		STATUS    mandatory
		DESCRIPTION " "
		::= { restStatPort 2 }


restStatPortE1mEntry 	OBJECT-TYPE
		SYNTAX    RestStatPortE1mEntry
		ACCESS    not-accessible
		STATUS    mandatory
		DESCRIPTION " "
		INDEX	{ restStatPortE1mAddr,
			  restStatPortE1mIndex }
		::= { restStatPortE1mTable 1 }


RestStatPortE1mEntry	::= SEQUENCE {
		restStatPortE1mAddr
			PortAddr,
		restStatPortE1mIndex
			INTEGER,
		restStatPortE1mStartTime
			INTEGER,
		restStatPortE1mErrSec
			INTEGER,
		restStatPortE1mSevErrSec
			INTEGER,
		restStatPortE1mBstyErrSec
			INTEGER,
		restStatPortE1mUnavailSec
			INTEGER,
		restStatPortE1mLostFrame
			INTEGER,
		restStatPortE1mControlMode
			INTEGER
		}



restStatPortE1mAddr 	OBJECT-TYPE
		SYNTAX    PortAddr
		ACCESS    read-only
		STATUS    mandatory
		DESCRIPTION " "
		::= { restStatPortE1mEntry 1 }


restStatPortE1mIndex 	OBJECT-TYPE
		SYNTAX    INTEGER (0..96)
		ACCESS    read-only
		STATUS    mandatory
		DESCRIPTION " "
		::= { restStatPortE1mEntry 2 }

restStatPortE1mStartTime 	OBJECT-TYPE
		SYNTAX    INTEGER
		ACCESS    read-only
		STATUS    mandatory
		DESCRIPTION "Indicates when this statistics interval
			was started."
		::= { restStatPortE1mEntry 3 }

restStatPortE1mErrSec 	OBJECT-TYPE
		SYNTAX    INTEGER
		ACCESS    read-only
		STATUS    mandatory
		DESCRIPTION " "
		::= { restStatPortE1mEntry 4 }

restStatPortE1mSevErrSec 	OBJECT-TYPE
		SYNTAX    INTEGER
		ACCESS    read-only
		STATUS    mandatory
		DESCRIPTION " "
		::= { restStatPortE1mEntry 5 }

restStatPortE1mBstyErrSec 	OBJECT-TYPE
		SYNTAX    INTEGER
		ACCESS    read-only
		STATUS    mandatory
		DESCRIPTION " "
		::= { restStatPortE1mEntry 6 }

restStatPortE1mUnavailSec 	OBJECT-TYPE
		SYNTAX    INTEGER
		ACCESS    read-only
		STATUS    mandatory
		DESCRIPTION " "
		::= { restStatPortE1mEntry 7 }

restStatPortE1mLostFrame 	OBJECT-TYPE
		SYNTAX    INTEGER
		ACCESS    read-only
		STATUS    mandatory
		DESCRIPTION " "
		::= { restStatPortE1mEntry 8 }

restStatPortE1mControlMode 	OBJECT-TYPE
		SYNTAX    INTEGER {
			  clearStats(3)
			}
		ACCESS    write-only
		STATUS    mandatory
		DESCRIPTION " "
		::= { restStatPortE1mEntry 9 }


-- Packet Port Statistics

restStatPortPktTable 	OBJECT-TYPE
		SYNTAX  SEQUENCE OF RestStatPortPktEntry
		ACCESS  not-accessible
		STATUS  mandatory
		DESCRIPTION "This section of the MIB does not
			support getNext."
		::= { restStatPort 3 }

restStatPortPktEntry 	OBJECT-TYPE
		SYNTAX  RestStatPortPktEntry
		ACCESS  not-accessible
		STATUS  mandatory
		DESCRIPTION " "
		INDEX { restStatPortPktAddr }
		::= { restStatPortPktTable 1 }

RestStatPortPktEntry		::= SEQUENCE {
		restStatPortPktAddr
			PortAddr,
		restStatPortPktControlMode
			INTEGER,
		restStatPortPktSegmentSent
			Counter,
		restStatPortPktSegmentRecv
			Counter,
		restStatPortPktOctetSent
			Counter,
		restStatPortPktOctetRecv
			Counter,
		restStatPortPktDlciDiscard
			Counter,
		restStatPortPktBadAddrDiscard
			Counter,
		restStatPortPktOvrszeDiscard
			Counter,
		restStatPortPktUnderszeDiscard
			Counter,
		restStatPortPktCRCDiscard
			Counter,
		restStatPortPktSwOvrRunDiscard
			Counter,
		restStatPortPktUnderRunDiscard
			Counter,
		restStatPortPktAbortDiscard
			Counter,
		restStatPortPktHwOvrRunDiscard
			Counter,
		restStatPortPktLmiSegmentSent
			Counter,
		restStatPortPktLmiSegmentRecv
			Counter,
		restStatPortPktLmiSyntaxErr
			Counter,
		restStatPortPktLmiWrongSeq
			Counter,
		restStatPortPktLmiPollTimeOut
			Counter,
		restStatPortPktLmiWaitTimeOut
			Counter,
		restStatPortPktLmiTxSeqNum
			INTEGER,
		restStatPortPktLmiRxSeqNum
			INTEGER,
		restStatPortPktLmiNumGoodEvents
			INTEGER,
		restStatPortPktLmiNumBadEvents
			INTEGER,
		restStatPortPktLmiEventHistory
			OCTET STRING
		}

restStatPortPktAddr 	OBJECT-TYPE
		SYNTAX  PortAddr
		ACCESS  read-only
		STATUS  mandatory
		DESCRIPTION " "
		::= { restStatPortPktEntry 1 }

restStatPortPktControlMode 	OBJECT-TYPE
		SYNTAX  INTEGER {
			clearStats(3)
			}
		ACCESS  write-only
		STATUS  mandatory
		DESCRIPTION " "
		::= { restStatPortPktEntry 2 }

restStatPortPktSegmentSent 	OBJECT-TYPE
		SYNTAX  Counter
		ACCESS  read-only
		STATUS  mandatory
		DESCRIPTION "Segments sent from the network to
			the user device on any of the DLCIs on
			this port."
		::= { restStatPortPktEntry 3 }

restStatPortPktSegmentRecv 	OBJECT-TYPE
		SYNTAX  Counter
		ACCESS  read-only
		STATUS  mandatory
		DESCRIPTION "Segments received at the network
			from the user device on any of the
			DLCIs on this port."
		::= { restStatPortPktEntry 4 }

restStatPortPktOctetSent 	OBJECT-TYPE
		SYNTAX  Counter
		ACCESS  read-only
		STATUS  mandatory
		DESCRIPTION "Octets sent from the network to
			the user device on any of the DLCIs on
			this port."
		::= { restStatPortPktEntry 5 }

restStatPortPktOctetRecv 	OBJECT-TYPE
		SYNTAX  Counter
		ACCESS  read-only
		STATUS  mandatory
		DESCRIPTION "Octets received at the network
			from the user device on any of the
			DLCIs on this port."
		::= { restStatPortPktEntry 6 }

restStatPortPktDlciDiscard 	OBJECT-TYPE
		SYNTAX  Counter
		ACCESS  read-only
		STATUS  mandatory
		DESCRIPTION "Number of frames discarded because
			the destination DLCI was not active."
		::= { restStatPortPktEntry 7 }

restStatPortPktBadAddrDiscard 	OBJECT-TYPE
		SYNTAX  Counter
		ACCESS  read-only
		STATUS  mandatory
		DESCRIPTION "Number of frames discarded because
			the address field was not two bytes in
			length."
		::= { restStatPortPktEntry 8 }

restStatPortPktOvrszeDiscard 	OBJECT-TYPE
		SYNTAX  Counter
		ACCESS  read-only
		STATUS  mandatory
		DESCRIPTION "Number of frames received from the
			user device that were discarded because
			they exceeded the maximum frame size."
		::= { restStatPortPktEntry 9 }

restStatPortPktUnderszeDiscard 	OBJECT-TYPE
		SYNTAX  Counter
		ACCESS  read-only
		STATUS  mandatory
		DESCRIPTION "Number of HDLC frames discarded
			because the frame was too short."
		::= { restStatPortPktEntry 10 }

restStatPortPktCRCDiscard 	OBJECT-TYPE
		SYNTAX  Counter
		ACCESS  read-only
		STATUS  mandatory
		DESCRIPTION "Number of HDLC frames discarded
			because the CRC was bad."
		::= { restStatPortPktEntry 11 }

restStatPortPktSwOvrRunDiscard 	OBJECT-TYPE
		SYNTAX  Counter
		ACCESS  read-only
		STATUS  mandatory
		DESCRIPTION "Number of frames discarded because
			of port software buffer over run."
		::= { restStatPortPktEntry 12 }

restStatPortPktUnderRunDiscard 	OBJECT-TYPE
		SYNTAX  Counter
		ACCESS  read-only
		STATUS  mandatory
		DESCRIPTION "Number of HDLC frames discarded
			because of under run."
		::= { restStatPortPktEntry 13 }

restStatPortPktAbortDiscard 	OBJECT-TYPE
		SYNTAX  Counter
		ACCESS  read-only
		STATUS  mandatory
		DESCRIPTION "Number of HDLC frames discarded
			because frame abort was received."
		::= { restStatPortPktEntry 14 }

restStatPortPktHwOvrRunDiscard 	OBJECT-TYPE
		SYNTAX  Counter
		ACCESS  read-only
		STATUS  mandatory
		DESCRIPTION "Number of frames discarded because
			of port hardware over run."
		::= { restStatPortPktEntry 15 }

restStatPortPktLmiSegmentSent 	OBJECT-TYPE
		SYNTAX  Counter
		ACCESS  read-only
		STATUS  mandatory
		DESCRIPTION "Number of LMI message segments
			sent."
		::= { restStatPortPktEntry 16 }

restStatPortPktLmiSegmentRecv 	OBJECT-TYPE
		SYNTAX  Counter
		ACCESS  read-only
		STATUS  mandatory
		DESCRIPTION "Number of LMI message segments
			received."
		::= { restStatPortPktEntry 17 }

restStatPortPktLmiSyntaxErr 	OBJECT-TYPE
		SYNTAX  Counter
		ACCESS  read-only
		STATUS  mandatory
		DESCRIPTION "Number of LMI messages dropped due
			to syntax errors."
		::= { restStatPortPktEntry 18 }

restStatPortPktLmiWrongSeq 	OBJECT-TYPE
		SYNTAX  Counter
		ACCESS  read-only
		STATUS  mandatory
		DESCRIPTION "Number of LMI messages dropped due
			to incorrect sequence numbers."
		::= { restStatPortPktEntry 19 }

restStatPortPktLmiPollTimeOut 	OBJECT-TYPE
		SYNTAX  Counter
		ACCESS  read-only
		STATUS  mandatory
		DESCRIPTION "Number of LMI messages dropped due
			to poll time outs. The parameter
			recfFrPortLmiPollingTimer controls the
			duration of this timer."
		::= { restStatPortPktEntry 20 }

restStatPortPktLmiWaitTimeOut 	OBJECT-TYPE
		SYNTAX  Counter
		ACCESS  read-only
		STATUS  mandatory
		DESCRIPTION "Number of LMI messages dropped due
			to wait time outs. The parameter
			recfFrPortLmiWaitingTimer controls the
			duration of this timer."
		::= { restStatPortPktEntry 21 }

restStatPortPktLmiTxSeqNum 	OBJECT-TYPE
		SYNTAX  INTEGER
		ACCESS  read-only
		STATUS  mandatory
		DESCRIPTION "LMI transmit sequence number."
		::= { restStatPortPktEntry 22 }

restStatPortPktLmiRxSeqNum 	OBJECT-TYPE
		SYNTAX  INTEGER
		ACCESS  read-only
		STATUS  mandatory
		DESCRIPTION "LMI receive sequence number."
		::= { restStatPortPktEntry 23 }

restStatPortPktLmiNumGoodEvents 	OBJECT-TYPE
		SYNTAX  INTEGER
		ACCESS  read-only
		STATUS  mandatory
		DESCRIPTION "Number of good LMI events within
			the current monitor window. The size of
			this window is controlled by the
			recfFrPortLmiMonitoredEvents attribute."
		::= { restStatPortPktEntry 24 }

restStatPortPktLmiNumBadEvents 	OBJECT-TYPE
		SYNTAX  INTEGER
		ACCESS  read-only
		STATUS  mandatory
		DESCRIPTION "Number of bad LMI events within
			the current monitor window. The size of
			this window is controlled by the
			recfFrPortLmiMonitoredEvents attribute."
		::= { restStatPortPktEntry 25 }

restStatPortPktLmiEventHistory 	OBJECT-TYPE
		SYNTAX  OCTET STRING (SIZE (4))
		ACCESS  read-only
		STATUS  mandatory
		DESCRIPTION "Shows the last eight LMI events.
			Each event requires four bits. Bits 1
			(lsb), 2, 3 and 4 of the last octet
			represent the most recent event.

			The event values are as follows:
			 1 - received status enquiry
			 2 - received full status
			     enquiry
			 3 - received status
			 4 - received full status
			 5 - transmitted status enquiry
			 6 - transmitted full status
			     enquiry
			 7 - transmitted status
			 8 - transmitted full status
			 9 - poll timer expired
			10 - wait timer expired."
		::= { restStatPortPktEntry 26 }



-- ASM X.50 Port Statistics

restStatPortAsmX50Table 	OBJECT-TYPE
		SYNTAX    SEQUENCE OF RestStatPortAsmX50Entry
		ACCESS    not-accessible
		STATUS    mandatory
		DESCRIPTION "This section of the MIB does not
			support getNext."
		::= { restStatPort 4 }

restStatPortAsmX50Entry 	OBJECT-TYPE
		SYNTAX  RestStatPortAsmX50Entry
		ACCESS  not-accessible
		STATUS  mandatory
		DESCRIPTION " "
		INDEX   { restStatPortAsmX50Addr }
		::= { restStatPortAsmX50Table 1 }

RestStatPortAsmX50Entry    ::= SEQUENCE {
		restStatPortAsmX50Addr
			PortAddr,
		restStatPortAsmX50Control
			INTEGER,
		restStatPortAsmX50RxFrameErrors
			Counter,
		restStatPortAsmX50LocalOs
			Counter,
		restStatPortAsmX50RemoteOs
			Counter
		}

restStatPortAsmX50Addr 	OBJECT-TYPE
		SYNTAX	PortAddr
		ACCESS	read-only
		STATUS	mandatory
		DESCRIPTION " "
		::= { restStatPortAsmX50Entry 1 }

restStatPortAsmX50Control 	OBJECT-TYPE
		SYNTAX	INTEGER {
			clearStats(1)
			}
		ACCESS	write-only
		STATUS	mandatory
		DESCRIPTION " "
		::= { restStatPortAsmX50Entry 2 }

restStatPortAsmX50RxFrameErrors 	OBJECT-TYPE
		SYNTAX	Counter
		ACCESS	read-only
		STATUS	mandatory
		DESCRIPTION " "
		::= { restStatPortAsmX50Entry 3 }

restStatPortAsmX50LocalOs 	OBJECT-TYPE
		SYNTAX	Counter
		ACCESS	read-only
		STATUS	mandatory
		DESCRIPTION " "
		::= { restStatPortAsmX50Entry 4 }

restStatPortAsmX50RemoteOs 	OBJECT-TYPE
		SYNTAX	Counter
		ACCESS	read-only
		STATUS	mandatory
		DESCRIPTION " "
		::= { restStatPortAsmX50Entry 5 }



-- RTM Port Statistics MIB

restStatPortRtmTable 	OBJECT-TYPE
		SYNTAX  SEQUENCE OF RestStatPortRtmEntry
		ACCESS  not-accessible
		STATUS  mandatory
		DESCRIPTION " "
		::= { restStatPort 5 }

restStatPortRtmEntry 	OBJECT-TYPE
		SYNTAX  RestStatPortRtmEntry
		ACCESS  not-accessible
		STATUS  mandatory
		DESCRIPTION " "
		INDEX   { restStatPortRtmAddr }
		::= { restStatPortRtmTable 1 }

RestStatPortRtmEntry           	::= SEQUENCE {
	     restStatPortRtmAddr
			PortAddr,
	     restStatPortRtmControl
			INTEGER,
	     restStatPortRtmUIFarEndBlkErr
			Counter,
	     restStatPortRtmUINearEndBlkErr
			Counter,
	     restStatPortRtmAdUIFarEndBlkErr
		  	Counter,
	     restStatPortRtmAdUINrEndBlkErr
			Counter,
	     restStatPortRtmOOSTransitions
			Counter
	     }

restStatPortRtmAddr 	OBJECT-TYPE
		SYNTAX	PortAddr
		ACCESS	read-only
		STATUS  mandatory
		DESCRIPTION "RTM port physical address
			     in nest:slot:port format"
		::= { restStatPortRtmEntry 1 }

restStatPortRtmControl 	OBJECT-TYPE
		SYNTAX  INTEGER {
			clearStats(3)
			}
		ACCESS  write-only
		STATUS  mandatory
		DESCRIPTION "Clears the statistics of a
			port."
		::= { restStatPortRtmEntry 2 }

restStatPortRtmUIFarEndBlkErr 	OBJECT-TYPE
		SYNTAX  Counter
		ACCESS	read-only
		STATUS  mandatory
		DESCRIPTION "Count of RTM port U-interface
			far end block errors. It is a count
			that is being kept by RTM module."
		::= { restStatPortRtmEntry 3 }

restStatPortRtmUINearEndBlkErr 	OBJECT-TYPE
		SYNTAX  Counter
		ACCESS  read-only
		STATUS  mandatory
		DESCRIPTION "Count of RTM port U-interface near
			end block errors. It is a count
			that is being kept by RTM module."
		::= { restStatPortRtmEntry 4 }

restStatPortRtmAdUIFarEndBlkErr 	OBJECT-TYPE
		SYNTAX  Counter
		ACCESS	read-only
		STATUS  mandatory
		DESCRIPTION "Count of RTM port U-interface
			far end block errors. It is a count
			that is being kept by RTM AD module."
		::= { restStatPortRtmEntry 5 }

restStatPortRtmAdUINrEndBlkErr 	OBJECT-TYPE
		SYNTAX  Counter
		ACCESS  read-only
		STATUS  mandatory
		DESCRIPTION "Count of RTM port U-interface near
			end block errors. It is a count
			that is being kept by RTM AD module."
		::= { restStatPortRtmEntry 6 }

restStatPortRtmOOSTransitions 	OBJECT-TYPE
		SYNTAX  Counter
		ACCESS  read-only
		STATUS  mandatory
		DESCRIPTION "Count of RTM port OOS transition
			occurances. It is a summary of
			this events for all the elements
			on the port ."
		::= { restStatPortRtmEntry 7 }

-- ASM Voice Port Statistics

restStatPortAsmVoiceTable 	OBJECT-TYPE
		SYNTAX  SEQUENCE OF RestStatPortAsmVoiceEntry
		ACCESS  not-accessible
		STATUS  mandatory
		DESCRIPTION "This section of the MIB does not
			support getNext."
		::= { restStatPort 6 }

restStatPortAsmVoiceEntry 	OBJECT-TYPE
		SYNTAX  RestStatPortAsmVoiceEntry
		ACCESS  not-accessible
		STATUS  mandatory
		DESCRIPTION " "
		INDEX   { restStatPortAsmVoiceChanAddr }
		::= { restStatPortAsmVoiceTable 1 }

RestStatPortAsmVoiceEntry      	::= SEQUENCE {
	     restStatPortAsmVoiceChanAddr
			ChannelAddr,
	     restStatPortAsmVoiceControl
			INTEGER,
	     restStatPortAsmVoiceFrameOOSs
			Counter,
	     restStatPortAsmVoiceSignalOOSs
			Counter,
	     restStatPortAsmVoiceHighBERs
		  	Counter
	     }

restStatPortAsmVoiceChanAddr 	OBJECT-TYPE
		SYNTAX  ChannelAddr
		ACCESS  read-only
		STATUS  mandatory
		DESCRIPTION "Address of T1M/E1M bundle
			which is being used by this
			port while connected. If
			disconnected returns error."
		::= { restStatPortAsmVoiceEntry 1 }

restStatPortAsmVoiceControl 	OBJECT-TYPE
		SYNTAX 	INTEGER {
			clearStats(3)
			}
		ACCESS	write-only
		STATUS  mandatory
		DESCRIPTION "Clear stats will clear all
			statistics for specified port."
		::= { restStatPortAsmVoiceEntry 2 }

restStatPortAsmVoiceFrameOOSs 	OBJECT-TYPE
		SYNTAX	Counter
		ACCESS  read-only
		STATUS  mandatory
		DESCRIPTION "Frame OOS statistics."
		::= { restStatPortAsmVoiceEntry 3 }

restStatPortAsmVoiceSignalOOSs 	OBJECT-TYPE
		SYNTAX  Counter
		ACCESS  read-only
		STATUS  mandatory
		DESCRIPTION "Signaling OOS statistics."
		::= { restStatPortAsmVoiceEntry 4 }

restStatPortAsmVoiceHighBERs 	OBJECT-TYPE
		SYNTAX  Counter
		ACCESS  read-only
		STATUS  mandatory
		DESCRIPTION "HBER statistics."
		::= { restStatPortAsmVoiceEntry 5 }


-- LGM Port Statistics

restStatPortLgmTable 	OBJECT-TYPE
		SYNTAX	SEQUENCE OF RestStatPortLgmEntry
		ACCESS	not-accessible
		STATUS  mandatory
		DESCRIPTION " "
		::=  { restStatPort 7 }

restStatPortLgmEntry 	OBJECT-TYPE
		SYNTAX	RestStatPortLgmEntry
		ACCESS 	not-accessible
		STATUS	mandatory
		DESCRIPTION " "
		INDEX { restStatPortLgmAddr }
		::= { restStatPortLgmTable 1 }

RestStatPortLgmEntry 		::=  SEQUENCE 	{
			restStatPortLgmAddr
				PortAddr,
			restStatPortLgmControlMode
	   			INTEGER,
 			restStatPortLgmFrameSent
	   			INTEGER,
 			restStatPortLgmFrameRecd
	   			INTEGER,
 			restStatPortLgmFrameReTx
	   			INTEGER,
 			restStatPortLgmFrameNak
	   			INTEGER,
 			restStatPortLgmBadSync
	   			INTEGER,
 			restStatPortLgmOosCount
	   			INTEGER,
 			restStatPortLgmSabmSent
		   		INTEGER,
 			restStatPortLgmSabmRecd
	   			INTEGER,
 			restStatPortLgmRnrSent
	   			INTEGER,
 			restStatPortLgmRnrRecd
	   			INTEGER
	 	}

restStatPortLgmAddr 	OBJECT-TYPE
		SYNTAX	PortAddr
		ACCESS 	read-only
		STATUS 	mandatory
		DESCRIPTION "Address of the LGM port in
			type:group:port format."
		::= { restStatPortLgmEntry 1 }

restStatPortLgmControlMode 	OBJECT-TYPE
		SYNTAX  INTEGER  {
			clearStats(1)
			}
		ACCESS   write-only
		STATUS   mandatory
		DESCRIPTION "Clears the statistics of a
			port."
		::= { restStatPortLgmEntry 2 }

restStatPortLgmBadSync 	OBJECT-TYPE
		SYNTAX 	INTEGER (0..65536)
		ACCESS	read-only
		STATUS  mandatory
		DESCRIPTION "Number of bad sync count
			received."
		::= { restStatPortLgmEntry 3 }

restStatPortLgmOosCount 	OBJECT-TYPE
		SYNTAX 	INTEGER (0..65536)
		ACCESS	read-only
		STATUS	mandatory
		DESCRIPTION "Number of out of sync
			conditions."
		::= { restStatPortLgmEntry 4 }

restStatPortLgmFrameSent 	OBJECT-TYPE
		SYNTAX 	INTEGER (0..65536)
		ACCESS  read-only
		STATUS  mandatory
		DESCRIPTION "Number of frames transmitted."
		::= { restStatPortLgmEntry 5 }

restStatPortLgmFrameRecd 	OBJECT-TYPE
		SYNTAX	INTEGER (0..65536)
		ACCESS 	read-only
		STATUS  mandatory
		DESCRIPTION "Number of frames received."
		::= { restStatPortLgmEntry 6 }

restStatPortLgmFrameReTx 	OBJECT-TYPE
		SYNTAX 	INTEGER (0..65536)
		ACCESS	read-only
		STATUS	mandatory
		DESCRIPTION "Number of frames retransmitted."
		::= { restStatPortLgmEntry 7 }

restStatPortLgmFrameNak 	OBJECT-TYPE
		SYNTAX	INTEGER (0..65536)
		ACCESS 	read-only
		STATUS  mandatory
		DESCRIPTION "Number of NACKs sent."
		::= { restStatPortLgmEntry 8 }

restStatPortLgmSabmSent 	OBJECT-TYPE
		SYNTAX	INTEGER (0..65536)
		ACCESS 	read-only
		STATUS  mandatory
		DESCRIPTION "Number of SABMs sent."
		::= { restStatPortLgmEntry 9 }

restStatPortLgmSabmRecd 	OBJECT-TYPE
		SYNTAX	INTEGER (0..65536)
		ACCESS  read-only
		STATUS  mandatory
		DESCRIPTION "Number of SABMs received."
		::= { restStatPortLgmEntry 10 }

restStatPortLgmRnrSent 	OBJECT-TYPE
		SYNTAX	INTEGER (0..65536)
		ACCESS  read-only
		STATUS	mandatory
		DESCRIPTION "Number of Receiver_Not_Ready
			sent."
		::= { restStatPortLgmEntry 11 }

restStatPortLgmRnrRecd 	OBJECT-TYPE
		SYNTAX	INTEGER (0..65536)
		ACCESS  read-only
		STATUS	mandatory
		DESCRIPTION "Number of Receiver_Not_Ready
			received."
		::= { restStatPortLgmEntry 12 }


-- DSM D-channel Port Statistics

restStatPortDsm 	OBJECT IDENTIFIER ::= { restStatPort 8 }

restStatPortDsmDChTable 	OBJECT-TYPE
		SYNTAX  SEQUENCE OF RestStatPortDsmDChEntry
		ACCESS  not-accessible
		STATUS  mandatory
		DESCRIPTION "This section contains the call
			statistics maintained for each
			D-channel port.

			There are also HDLC statistics
			maintained for D-channel ports. These
			are defined in restStatPortPktTable."
		::= { restStatPortDsm 1 }

restStatPortDsmDChEntry 	OBJECT-TYPE
		SYNTAX  RestStatPortDsmDChEntry
		ACCESS  not-accessible
		STATUS  mandatory
		DESCRIPTION "INTRODUCED 2.0.0"
		INDEX   { restStatPortDsmDChAddr }
		::= { restStatPortDsmDChTable 1 }

RestStatPortDsmDChEntry		::= SEQUENCE {
		restStatPortDsmDChAddr
			PortAddr,
		restStatPortDsmDChControlMode
			INTEGER,
		restStatPortDsmDChOrigAttempts
			Counter,
		restStatPortDsmDChTermAttempts
			Counter,
		restStatPortDsmDChPbxLayer2Errs
			Counter,
		restStatPortDsmDChPbxLayer3Errs
			Counter,
		restStatPortDsmDChPbxLinkResets
			Counter,
		restStatPortDsmDChPbxDisconns
			Counter,
		restStatPortDsmDChPbxUnkExchs
			Counter,
		restStatPortDsmDChPbxNoBws
			Counter,
		restStatPortDsmDChPbxNoCmprs
			Counter,
		restStatPortDsmDChPbxNoBchs
			Counter,
		restStatPortDsmDChPbxOtherFails
			Counter,
		restStatPortDsmDChNetDisconns
			Counter,
		restStatPortDsmDChNetOtherFails
			Counter
		}

restStatPortDsmDChAddr 	OBJECT-TYPE
		SYNTAX  PortAddr
		ACCESS  read-only
		STATUS  mandatory
		DESCRIPTION "Address of the D-channel in
			type.group.port format. The server type
			is 131."
		::= { restStatPortDsmDChEntry 1 }

restStatPortDsmDChControlMode 	OBJECT-TYPE
		SYNTAX  INTEGER {
			clearStats(3)
			}
		ACCESS  write-only
		STATUS  mandatory
		DESCRIPTION "Setting this field to clearStats
			will reset all of the counters in this
			MIB section to zero."
		::= { restStatPortDsmDChEntry 2 }

restStatPortDsmDChOrigAttempts 	OBJECT-TYPE
		SYNTAX  Counter
		ACCESS  read-only
		STATUS  mandatory
		DESCRIPTION "Number of calls attempted by the
			ISPBX over this D-channel. This includes
			both successful and failed calls."
		::= { restStatPortDsmDChEntry 3 }

restStatPortDsmDChTermAttempts 	OBJECT-TYPE
		SYNTAX  Counter
		ACCESS  read-only
		STATUS  mandatory
		DESCRIPTION "Number of calls attempted by the
			ST network to the ISPBX connected to
			this D-channel. This includes both
			successful and failed calls."
		::= { restStatPortDsmDChEntry 4 }

restStatPortDsmDChPbxLayer2Errs 	OBJECT-TYPE
		SYNTAX  Counter
		ACCESS  read-only
		STATUS  mandatory
		DESCRIPTION "Number of layer 2 errors detected
			by the DSM on this D-channel."
		::= { restStatPortDsmDChEntry 5 }

restStatPortDsmDChPbxLayer3Errs 	OBJECT-TYPE
		SYNTAX  Counter
		ACCESS  read-only
		STATUS  mandatory
		DESCRIPTION "Number of layer 3 errors detected
			by the DSM on this D-channel."
		::= { restStatPortDsmDChEntry 6 }

restStatPortDsmDChPbxLinkResets 	OBJECT-TYPE
		SYNTAX  Counter
		ACCESS  read-only
		STATUS  mandatory
		DESCRIPTION "Number of layer 2 reset commands
			received from the ISPBX on this
			D-channel."
		::= { restStatPortDsmDChEntry 7 }

restStatPortDsmDChPbxDisconns 	OBJECT-TYPE
		SYNTAX  Counter
		ACCESS  read-only
		STATUS  mandatory
		DESCRIPTION "Number of calls disconnected on
			this D-channel due to a request from
			the local ISPBX."
		::= { restStatPortDsmDChEntry 8 }

restStatPortDsmDChPbxUnkExchs 	OBJECT-TYPE
		SYNTAX  Counter
		ACCESS  read-only
		STATUS  mandatory
		DESCRIPTION "Number of call attempts
			originating from the local ISPBX that
			failed because the called number did
			not fall into any exchange codes to
			which the DSM has a route."
		::= { restStatPortDsmDChEntry 9 }

restStatPortDsmDChPbxNoBws 	OBJECT-TYPE
		SYNTAX  Counter
		ACCESS  read-only
		STATUS  mandatory
		DESCRIPTION "Number of call attempts
			originating from the local ISPBX that
			failed because no route could be found
			between the source and destination
			nodes with enough bandwidth for the
			channel connection."
		::= { restStatPortDsmDChEntry 10 }

restStatPortDsmDChPbxNoCmprs 	OBJECT-TYPE
		SYNTAX  Counter
		ACCESS  read-only
		STATUS  mandatory
		DESCRIPTION "Number of call attempts
			originating from the local ISPBX that
			failed because a compression resource
			was not available in either the source
			or destination node of the channel
			connection."
		::= { restStatPortDsmDChEntry 11 }

restStatPortDsmDChPbxNoBchs 	OBJECT-TYPE
		SYNTAX  Counter
		ACCESS  read-only
		STATUS  mandatory
		DESCRIPTION "Number of call attempts
			originating from the local ISPBX that
			failed because there were no available
			B-channels that could handle an
			outgoing call."
		::= { restStatPortDsmDChEntry 12 }

restStatPortDsmDChPbxOtherFails 	OBJECT-TYPE
		SYNTAX  Counter
		ACCESS  read-only
		STATUS  mandatory
		DESCRIPTION "Number of call attempts
			originating from the local ISPBX that
			failed for any reason not covered by
			the other statistics in this MIB
			section."
		::= { restStatPortDsmDChEntry 13 }

restStatPortDsmDChNetDisconns 	OBJECT-TYPE
		SYNTAX  Counter
		ACCESS  read-only
		STATUS  mandatory
		DESCRIPTION "Number of calls disconnected on
			this D-channel due to a request from
			the ST network."
		::= { restStatPortDsmDChEntry 14 }

restStatPortDsmDChNetOtherFails 	OBJECT-TYPE
		SYNTAX  Counter
		ACCESS  read-only
		STATUS  mandatory
		DESCRIPTION "Number of calls attempting to
			terminate on the local ISPBX that
			failed for any reason not covered by
			the other statistics in this MIB
			section."
		::= { restStatPortDsmDChEntry 15 }


-- Channel Statistics MIB

restStatCh 	OBJECT IDENTIFIER ::= { reStatistics 2 }


-- Packet Channel Source-Destination Statistics

restStatChPktTable 	OBJECT-TYPE
		SYNTAX    SEQUENCE OF RestStatChPktEntry
		ACCESS    not-accessible
		STATUS    mandatory
		DESCRIPTION " "
		::= { restStatCh 1 }

restStatChPktEntry 	OBJECT-TYPE
		SYNTAX  RestStatChPktEntry
		ACCESS  not-accessible
		STATUS  mandatory
		DESCRIPTION " "
		INDEX { restStatChPktAddr }
		::= { restStatChPktTable 1 }

RestStatChPktEntry  ::= SEQUENCE {
                    restStatChPktAddr
                         ChannelAddr,
                    restStatChPktSourceNodeID
                         NodeAddr,
                    restStatChPktSourceChAddr
                         ChannelAddr,
                    restStatChPktDestNodeID
                         NodeAddr,
                    restStatChPktDestChAddr
                         ChannelAddr,
                    restStatChPktControlMode
                         INTEGER,
                    restStatChPktSegmentsToUser
                         INTEGER,
                    restStatChPktSegmentsToNetwork
                         INTEGER,
                    restStatChPktYellowThreshold
                         INTEGER,
                    restStatChPktRedThreshold
                         INTEGER,
                    restStatChPktCritThreshold
                         INTEGER,
                    restStatChPktPortCongMode
                         INTEGER,
                    restStatChPktNetCongMode
                         INTEGER,
                    restStatChPktRemoteCongMode
                         INTEGER,
                    restStatChPktCIRCredit
                         INTEGER,
                    restStatChPktEIRCredit
                         INTEGER,
                    restStatChPktFECNSent
                         Counter,
                    restStatChPktBECNSent
                         Counter,
                    restStatChPktPortCIRSegSent
                         Counter,
                    restStatChPktPortCIRSegRcv
                         Counter,
                    restStatChPktPortEIRSegSent
                         Counter,
                    restStatChPktPortEIRSegRcv
                         Counter,
                    restStatChPktPortCIROctetSent
                         Counter,
                    restStatChPktPortCIROctetRcv
                         Counter,
                    restStatChPktPortEIROctetSent
                         Counter,
                    restStatChPktPortEIROctetRcv
                         Counter,
                    restStatChPktPortCIRSegDrops
                         Counter,
                    restStatChPktPortEIRSegDrops
                         Counter,
                    restStatChPktPortCIROctetDrops
                         Counter,
                    restStatChPktPortEIROctetDrops
                         Counter,
                    restStatChPktNetCIRSegSent
                         Counter,
                    restStatChPktNetCIRSegRcv
                         Counter,
                    restStatChPktNetEIRSegSent
                         Counter,
                    restStatChPktNetEIRSegRcv
                         Counter,
                    restStatChPktNetCIROctetSent
                         Counter,
                    restStatChPktNetCIROctetRcv
                         Counter,
                    restStatChPktNetEIROctetSent
                         Counter,
                    restStatChPktNetEIROctetRcv
                         Counter,
                    restStatChPktNetCIRSegDrops
                         Counter,
                    restStatChPktNetEIRSegDrops
                         Counter,
                    restStatChPktNetCIROctetDrops
                         Counter,
                    restStatChPktNetEIROctetDrops
                         Counter,
                    restStatChPktSegEIRDiscard
                         Counter,
                    restStatChPktSegSeqDiscard
                         Counter,
                    restStatChPktSegCongPortDiscard
                         Counter,
                    restStatChPktSegCongNetDiscard
                         Counter,
                    restStatChPktSegExcDiscard
                         Counter,
                    restStatChPktSegUnderszDiscard
                         Counter,
                    restStatChPktSegV120ErrDiscard
                         Counter,
                    restStatChPktSegInacPortDiscard
                         Counter,
                    restStatChPktSegInacNetDiscard
                         Counter
                    }

restStatChPktAddr 	OBJECT-TYPE
		SYNTAX  ChannelAddr
		ACCESS  read-only
		STATUS  mandatory
		DESCRIPTION " "
		::= { restStatChPktEntry 1 }

restStatChPktSourceNodeID 	OBJECT-TYPE
		SYNTAX  NodeAddr
		ACCESS  read-only
		STATUS  mandatory
		DESCRIPTION "Source node of the channel."
		::= { restStatChPktEntry 2 }

restStatChPktSourceChAddr 	OBJECT-TYPE
		SYNTAX  ChannelAddr
		ACCESS  read-only
		STATUS  mandatory
		DESCRIPTION "Source address of the channel."
		::= { restStatChPktEntry 3 }

restStatChPktDestNodeID 	OBJECT-TYPE
		SYNTAX  NodeAddr
		ACCESS  read-only
		STATUS  mandatory
		DESCRIPTION "Destination node of the channel."
		::= { restStatChPktEntry 4 }

restStatChPktDestChAddr 	OBJECT-TYPE
		SYNTAX  ChannelAddr
		ACCESS  read-only
		STATUS  mandatory
		DESCRIPTION "Destination address of the
			channel."
		::= { restStatChPktEntry 5 }

restStatChPktControlMode 	OBJECT-TYPE
		SYNTAX  INTEGER {
			clearStats(3)
			}
		ACCESS  write-only
		STATUS  mandatory
		DESCRIPTION "Clear stats will clear all of the
			statistics for the specified frame
			relay channel."
		::= { restStatChPktEntry 6 }

restStatChPktSegmentsToUser 	OBJECT-TYPE
		SYNTAX  INTEGER
		ACCESS  read-only
		STATUS  mandatory
		DESCRIPTION "Number of segments currently
			queued to be sent to the user device."
		::= { restStatChPktEntry 7 }

restStatChPktSegmentsToNetwork 	OBJECT-TYPE
		SYNTAX  INTEGER
		ACCESS  read-only
		STATUS  mandatory
		DESCRIPTION "Number of segments currently
			queued to be sent into the network
			bound for the other end of the frame
			relay channel."
		::= { restStatChPktEntry 8 }

restStatChPktYellowThreshold 	OBJECT-TYPE
		SYNTAX  INTEGER
		ACCESS  read-only
		STATUS  mandatory
		DESCRIPTION "Number of segments that can be in
			any queue before that channel is in
			yellow congestion mode. This value is
			40% of the critical threshold."
		::= { restStatChPktEntry 9 }

restStatChPktRedThreshold 	OBJECT-TYPE
		SYNTAX  INTEGER
		ACCESS  read-only
		STATUS  mandatory
		DESCRIPTION "Number of segments that can be in
			any queue before that channel is in
			red congestion mode. This value is
			86% of the critical threshold."
		::= { restStatChPktEntry 10 }

restStatChPktCritThreshold 	OBJECT-TYPE
		SYNTAX  INTEGER
		ACCESS  read-only
		STATUS  mandatory
		DESCRIPTION "Number of segments that can be in
			any queue before that channel is in
			critical congestion mode. This value is
			the maximum number of segments that the
			queue can contain."
		::= { restStatChPktEntry 11 }

restStatChPktPortCongMode 	OBJECT-TYPE
		SYNTAX  INTEGER {
			normal(1),
			yellow(2),
			red(3),
			critical(4)
			}
		ACCESS  read-only
		STATUS  mandatory
		DESCRIPTION "Congestion mode of the port queue,
			which forwards segments to the user
			device."
		::= { restStatChPktEntry 12 }

restStatChPktNetCongMode 	OBJECT-TYPE
		SYNTAX  INTEGER {
			normal(1),
			yellow(2),
			red(3),
			critical(4)
			}
		ACCESS  read-only
		STATUS  mandatory
		DESCRIPTION "Congestion mode of the network
			queue, which forwards segments to the
			network, destined for the other
			endpoint of the frame relay channel."
		::= { restStatChPktEntry 13 }

restStatChPktRemoteCongMode 	OBJECT-TYPE
		SYNTAX  INTEGER {
			normal(1),
			yellow(2),
			red(3),
			critical(4)
			}
		ACCESS  read-only
		STATUS  mandatory
		DESCRIPTION "Worst congestion mode of all of
			the segment queues between this node
			and the other endpoint of the frame
			relay channel."
		::= { restStatChPktEntry 14 }

restStatChPktCIRCredit 	OBJECT-TYPE
		SYNTAX  INTEGER
		ACCESS  read-only
		STATUS  mandatory
		DESCRIPTION "Number of CIR octets that can be
			sent per second."
		::= { restStatChPktEntry 15 }

restStatChPktEIRCredit 	OBJECT-TYPE
		SYNTAX  INTEGER
		ACCESS  read-only
		STATUS  mandatory
		DESCRIPTION "Number of EIR octets that can be
			sent per second."
		::= { restStatChPktEntry 16 }

restStatChPktFECNSent 	OBJECT-TYPE
		SYNTAX  Counter
		ACCESS  read-only
		STATUS  mandatory
		DESCRIPTION " "
		::= { restStatChPktEntry 17 }

restStatChPktBECNSent 	OBJECT-TYPE
		SYNTAX  Counter
		ACCESS  read-only
		STATUS  mandatory
		DESCRIPTION " "
		::= { restStatChPktEntry 18 }

restStatChPktPortCIRSegSent 	OBJECT-TYPE
		SYNTAX  Counter
		ACCESS  read-only
		STATUS  mandatory
		DESCRIPTION "Number of CIR segments sent from
			the network to the user device."
		::= { restStatChPktEntry 19 }

restStatChPktPortCIRSegRcv 	OBJECT-TYPE
		SYNTAX  Counter
		ACCESS  read-only
		STATUS  mandatory
		DESCRIPTION "Number of CIR segments received
			from the user device to be sent to the
			network."
		::= { restStatChPktEntry 20 }

restStatChPktPortEIRSegSent 	OBJECT-TYPE
		SYNTAX  Counter
		ACCESS  read-only
		STATUS  mandatory
		DESCRIPTION "Number of EIR segments sent from
			the network to the user device."
		::= { restStatChPktEntry 21 }

restStatChPktPortEIRSegRcv 	OBJECT-TYPE
		SYNTAX  Counter
		ACCESS  read-only
		STATUS  mandatory
		DESCRIPTION "Number of EIR segments received
			from the user device to be sent to the
			network."
		::= { restStatChPktEntry 22 }

restStatChPktPortCIROctetSent 	OBJECT-TYPE
		SYNTAX  Counter
		ACCESS  read-only
		STATUS  mandatory
		DESCRIPTION "Number of CIR octets sent from the
			network to the user device."
		::= { restStatChPktEntry 23 }

restStatChPktPortCIROctetRcv 	OBJECT-TYPE
		SYNTAX  Counter
		ACCESS  read-only
		STATUS  mandatory
		DESCRIPTION "Number of CIR octets received from
			the user device to be sent to the
			network."
		::= { restStatChPktEntry 24 }

restStatChPktPortEIROctetSent 	OBJECT-TYPE
		SYNTAX  Counter
		ACCESS  read-only
		STATUS  mandatory
		DESCRIPTION "Number of EIR octets sent from the
			network to the user device."
		::= { restStatChPktEntry 25 }

restStatChPktPortEIROctetRcv 	OBJECT-TYPE
		SYNTAX  Counter
		ACCESS  read-only
		STATUS  mandatory
		DESCRIPTION "Number of EIR octets received from
			the user device to be sent to the
			network."
		::= { restStatChPktEntry 26 }

restStatChPktPortCIRSegDrops 	OBJECT-TYPE
		SYNTAX  Counter
		ACCESS  read-only
		STATUS  mandatory
		DESCRIPTION "Number of CIR segments received
			from the user device that have been
			dropped."
		::= { restStatChPktEntry 27 }

restStatChPktPortEIRSegDrops 	OBJECT-TYPE
		SYNTAX  Counter
		ACCESS  read-only
		STATUS  mandatory
		DESCRIPTION "Number of EIR segments received
			from the user device that have been
			dropped."
		::= { restStatChPktEntry 28 }

restStatChPktPortCIROctetDrops 	OBJECT-TYPE
		SYNTAX  Counter
		ACCESS  read-only
		STATUS  mandatory
		DESCRIPTION "Number of CIR octets received from
			the user device that have been dropped."
		::= { restStatChPktEntry 29 }

restStatChPktPortEIROctetDrops 	OBJECT-TYPE
		SYNTAX  Counter
		ACCESS  read-only
		STATUS  mandatory
		DESCRIPTION "Number of EIR octets received from
			the user device that have been dropped."
		::= { restStatChPktEntry 30 }

restStatChPktNetCIRSegSent 	OBJECT-TYPE
		SYNTAX  Counter
		ACCESS  read-only
		STATUS  mandatory
		DESCRIPTION "Number of CIR segments sent from
			the user device to the network."
		::= { restStatChPktEntry 31 }

restStatChPktNetCIRSegRcv 	OBJECT-TYPE
		SYNTAX  Counter
		ACCESS  read-only
		STATUS  mandatory
		DESCRIPTION "Number of CIR segments received
			from the network to be sent to the user
			device."
		::= { restStatChPktEntry 32 }

restStatChPktNetEIRSegSent 	OBJECT-TYPE
		SYNTAX  Counter
		ACCESS  read-only
		STATUS  mandatory
		DESCRIPTION "Number of EIR segments sent from
			the user device to the network."
		::= { restStatChPktEntry 33 }

restStatChPktNetEIRSegRcv 	OBJECT-TYPE
		SYNTAX  Counter
		ACCESS  read-only
		STATUS  mandatory
		DESCRIPTION "Number of EIR segments received
			from the network to be sent to the user
			device."
		::= { restStatChPktEntry 34 }

restStatChPktNetCIROctetSent 	OBJECT-TYPE
		SYNTAX  Counter
		ACCESS  read-only
		STATUS  mandatory
		DESCRIPTION "Number of CIR octets sent from the
			user device to the network."
		::= { restStatChPktEntry 35 }

restStatChPktNetCIROctetRcv 	OBJECT-TYPE
		SYNTAX  Counter
		ACCESS  read-only
		STATUS  mandatory
		DESCRIPTION "Number of CIR octets received from
			the network to be sent to the user
			device."
		::= { restStatChPktEntry 36 }

restStatChPktNetEIROctetSent 	OBJECT-TYPE
		SYNTAX  Counter
		ACCESS  read-only
		STATUS  mandatory
		DESCRIPTION "Number of EIR octets sent from the
			user device to the network."
		::= { restStatChPktEntry 37 }

restStatChPktNetEIROctetRcv 	OBJECT-TYPE
		SYNTAX  Counter
		ACCESS  read-only
		STATUS  mandatory
		DESCRIPTION "Number of EIR octets received from
			the network to be sent to the user
			device."
		::= { restStatChPktEntry 38 }

restStatChPktNetCIRSegDrops 	OBJECT-TYPE
		SYNTAX  Counter
		ACCESS  read-only
		STATUS  mandatory
		DESCRIPTION "Number of CIR segments received
			from the network that have been
			dropped."
		::= { restStatChPktEntry 39 }

restStatChPktNetEIRSegDrops 	OBJECT-TYPE
		SYNTAX  Counter
		ACCESS  read-only
		STATUS  mandatory
		DESCRIPTION "Number of EIR segments received
			from the network that have been
			dropped."
		::= { restStatChPktEntry 40 }

restStatChPktNetCIROctetDrops 	OBJECT-TYPE
		SYNTAX  Counter
		ACCESS  read-only
		STATUS  mandatory
		DESCRIPTION "Number of CIR octets received from
			the network that have been dropped."
		::= { restStatChPktEntry 41 }

restStatChPktNetEIROctetDrops 	OBJECT-TYPE
		SYNTAX  Counter
		ACCESS  read-only
		STATUS  mandatory
		DESCRIPTION "Number of EIR octets received from
			the network that have been dropped."
		::= { restStatChPktEntry 42 }

restStatChPktSegEIRDiscard 	OBJECT-TYPE
		SYNTAX  Counter
		ACCESS  read-only
		STATUS  mandatory
		DESCRIPTION "Number of segments discarded
			because the system was unable to send
			EIR traffic."
		::= { restStatChPktEntry 43 }

restStatChPktSegSeqDiscard 	OBJECT-TYPE
		SYNTAX  Counter
		ACCESS  read-only
		STATUS  mandatory
		DESCRIPTION "Number of segments discarded
			because a sequence error was detected."
		::= { restStatChPktEntry 44 }

restStatChPktSegCongPortDiscard 	OBJECT-TYPE
		SYNTAX  Counter
		ACCESS  read-only
		STATUS  mandatory
		DESCRIPTION "Number of segments discarded
			because of congestion on the queue with
			segments to send to the user device."
		::= { restStatChPktEntry 45 }

restStatChPktSegCongNetDiscard 	OBJECT-TYPE
		SYNTAX  Counter
		ACCESS  read-only
		STATUS  mandatory
		DESCRIPTION "Number of segments discarded
			because of congestion on the queue with
			segments to send to the network."
		::= { restStatChPktEntry 46 }

restStatChPktSegExcDiscard 	OBJECT-TYPE
		SYNTAX  Counter
		ACCESS  read-only
		STATUS  mandatory
		DESCRIPTION "Number of segments discarded
			because the available CIR or EIR credit
			has been exceeded."
		::= { restStatChPktEntry 47 }

restStatChPktSegUnderszDiscard 	OBJECT-TYPE
		SYNTAX  Counter
		ACCESS  read-only
		STATUS  mandatory
		DESCRIPTION "Number of segments discarded
			because the size was less than the
			minimum."
		::= { restStatChPktEntry 48 }

restStatChPktSegV120ErrDiscard 	OBJECT-TYPE
		SYNTAX  Counter
		ACCESS  read-only
		STATUS  mandatory
		DESCRIPTION "Number of segments discarded
			because the V120 header was bad (used
			with Ad-10 only)."
		::= { restStatChPktEntry 49 }

restStatChPktSegInacPortDiscard 	OBJECT-TYPE
		SYNTAX  Counter
		ACCESS  read-only
		STATUS  mandatory
		DESCRIPTION "Number of segments discarded
			because the destination DLCI was
			inactive."
		::= { restStatChPktEntry 50 }

restStatChPktSegInacNetDiscard 	OBJECT-TYPE
		SYNTAX  Counter
		ACCESS  read-only
		STATUS  mandatory
		DESCRIPTION "Number of segments discarded
			because this DLCI was inactive."
		::= { restStatChPktEntry 51 }


-- Packet Channel Bypass Statistics

restStatChPktBypTable 	OBJECT-TYPE
		SYNTAX    SEQUENCE OF RestStatChPktBypEntry
		ACCESS    not-accessible
		STATUS    mandatory
		DESCRIPTION "This section of the MIB does not
			support getNext."
		::= { restStatCh 2 }

restStatChPktBypEntry 	OBJECT-TYPE
		SYNTAX    RestStatChPktBypEntry
		ACCESS  not-accessible
		STATUS  mandatory
		DESCRIPTION " "
		INDEX { restStatChPktBypNodeID,
			restStatChPktBypAddr }
		::= { restStatChPktBypTable 1 }

RestStatChPktBypEntry  ::= SEQUENCE {
                    restStatChPktBypNodeID
                         NodeAddr,
                    restStatChPktBypAddr
                         ChannelAddr,
                    restStatChPktBypSourceNodeID
                         NodeAddr,
                    restStatChPktBypSourceChAddr
                         ChannelAddr,
                    restStatChPktBypDestNodeID
                         NodeAddr,
                    restStatChPktBypDestChAddr
                         ChannelAddr,
                    restStatChPktBypControlMode
                         INTEGER,
                    restStatChPktBypSegmentsToSrc
                         INTEGER,
                    restStatChPktBypSegmentsToDst
                         INTEGER,
                    restStatChPktBypYellowThreshold
                         INTEGER,
                    restStatChPktBypRedThreshold
                         INTEGER,
                    restStatChPktBypCritThreshold
                         INTEGER,
                    restStatChPktBypInCongMode
                         INTEGER,
                    restStatChPktBypOutCongMode
                         INTEGER,
                    restStatChPktBypInCIRSegSent
                         Counter,
                    restStatChPktBypInCIRSegRcv
                         Counter,
                    restStatChPktBypInEIRSegSent
                         Counter,
                    restStatChPktBypInEIRSegRcv
                         Counter,
                    restStatChPktBypInCIROctetSent
                         Counter,
                    restStatChPktBypInCIROctetRcv
                         Counter,
                    restStatChPktBypInEIROctetSent
                         Counter,
                    restStatChPktBypInEIROctetRcv
                         Counter,
                    restStatChPktBypInCIRSegDrop
                         Counter,
                    restStatChPktBypInEIRSegDrop
                         Counter,
                    restStatChPktBypInCIROctetDrop
                         Counter,
                    restStatChPktBypInEIROctetDrop
                         Counter,
                    restStatChPktBypOutCIRSegSent
                         Counter,
                    restStatChPktBypOutCIRSegRcv
                         Counter,
                    restStatChPktBypOutEIRSegSent
                         Counter,
                    restStatChPktBypOutEIRSegRcv
                         Counter,
                    restStatChPktBypOutCIROctetSent
                         Counter,
                    restStatChPktBypOutCIROctetRcv
                         Counter,
                    restStatChPktBypOutEIROctetSent
                         Counter,
                    restStatChPktBypOutEIROctetRcv
                         Counter,
                    restStatChPktBypOutCIRSegDrop
                         Counter,
                    restStatChPktBypOutEIRSegDrop
                         Counter,
                    restStatChPktBypOutCIROctetDrop
                         Counter,
                    restStatChPktBypOutEIROctetDrop
                         Counter,
                    restStatChPktBypSegSrcEIRDisc
                         Counter,
                    restStatChPktBypSegDstEIRDisc
                         Counter,
                    restStatChPktBypSegSrcDstConDsc
                         Counter,
                    restStatChPktBypSegDstSrcConDsc
                         Counter,
                    restStatChPktBypSegInacSrcDisc
                         Counter,
                    restStatChPktBypSegInacDstDisc
                         Counter
                    }

restStatChPktBypNodeID 	OBJECT-TYPE
		SYNTAX  NodeAddr
		ACCESS  read-only
		STATUS  mandatory
		DESCRIPTION " "
		::= { restStatChPktBypEntry 1 }

restStatChPktBypAddr 	OBJECT-TYPE
		SYNTAX  ChannelAddr
		ACCESS  read-only
		STATUS  mandatory
		DESCRIPTION " "
		::= { restStatChPktBypEntry 2 }

restStatChPktBypSourceNodeID 	OBJECT-TYPE
		SYNTAX  NodeAddr
		ACCESS  read-only
		STATUS  mandatory
		DESCRIPTION " "
		::= { restStatChPktBypEntry 3 }

restStatChPktBypSourceChAddr 	OBJECT-TYPE
		SYNTAX  ChannelAddr
		ACCESS  read-only
		STATUS  mandatory
		DESCRIPTION " "
		::= { restStatChPktBypEntry 4 }

restStatChPktBypDestNodeID 	OBJECT-TYPE
		SYNTAX  NodeAddr
		ACCESS  read-only
		STATUS  mandatory
		DESCRIPTION " "
		::= { restStatChPktBypEntry 5 }

restStatChPktBypDestChAddr 	OBJECT-TYPE
		SYNTAX  ChannelAddr
		ACCESS  read-only
		STATUS  mandatory
		DESCRIPTION " "
		::= { restStatChPktBypEntry 6 }

restStatChPktBypControlMode 	OBJECT-TYPE
		SYNTAX  INTEGER {
			clearStats(3)
			}
		ACCESS  write-only
		STATUS  mandatory
		DESCRIPTION " "
		::= { restStatChPktBypEntry 7 }

restStatChPktBypSegmentsToSrc 	OBJECT-TYPE
		SYNTAX  INTEGER
		ACCESS  read-only
		STATUS  mandatory
		DESCRIPTION "Number of segments currently
			queued to be sent to the source of
			this channel."
		::= { restStatChPktBypEntry 8 }

restStatChPktBypSegmentsToDst 	OBJECT-TYPE
		SYNTAX  INTEGER
		ACCESS  read-only
		STATUS  mandatory
		DESCRIPTION "Number of segments currently
			queued to be sent to the destination
			of this channel."
		::= { restStatChPktBypEntry 9 }

restStatChPktBypYellowThreshold 	OBJECT-TYPE
		SYNTAX  INTEGER
		ACCESS  read-only
		STATUS  mandatory
		DESCRIPTION "Number of segments that can be in
			any queue before that channel is in
			yellow congestion mode. This value is
			40% of the critical threshold."
		::= { restStatChPktBypEntry 10 }

restStatChPktBypRedThreshold 	OBJECT-TYPE
		SYNTAX  INTEGER
		ACCESS  read-only
		STATUS  mandatory
		DESCRIPTION "Number of segments that can be in
			any queue before that channel is in
			red congestion mode. This value is
			86% of the critical threshold."
		::= { restStatChPktBypEntry 11 }

restStatChPktBypCritThreshold 	OBJECT-TYPE
		SYNTAX  INTEGER
		ACCESS  read-only
		STATUS  mandatory
		DESCRIPTION "Number of segments that can be in
			any queue before that channel is in
			critical congestion mode. This value is
			the maximum number of segments that the
			queue can contain."
		::= { restStatChPktBypEntry 12 }

restStatChPktBypInCongMode 	OBJECT-TYPE
		SYNTAX  INTEGER {
			normal(1),
			yellow(2),
			red(3),
			critical(4)
			}
		ACCESS  read-only
		STATUS  mandatory
		DESCRIPTION "Congestion mode of the in queue,
			which forwards segments to the source
			of this channel."
		::= { restStatChPktBypEntry 13 }

restStatChPktBypOutCongMode 	OBJECT-TYPE
		SYNTAX  INTEGER {
			normal(1),
			yellow(2),
			red(3),
			critical(4)
			}
		ACCESS  read-only
		STATUS  mandatory
		DESCRIPTION "Congestion mode of the out queue,
			which forwards segments to the
			destination of this channel."
		::= { restStatChPktBypEntry 14 }

restStatChPktBypInCIRSegSent 	OBJECT-TYPE
		SYNTAX  Counter
		ACCESS  read-only
		STATUS  mandatory
		DESCRIPTION "Number of CIR segments sent from
			this node to the source of this
			channel."
		::= { restStatChPktBypEntry 15 }

restStatChPktBypInCIRSegRcv 	OBJECT-TYPE
		SYNTAX  Counter
		ACCESS  read-only
		STATUS  mandatory
		DESCRIPTION "Number of CIR segments received at
			this node from the source of this
			channel."
		::= { restStatChPktBypEntry 16 }

restStatChPktBypInEIRSegSent 	OBJECT-TYPE
		SYNTAX  Counter
		ACCESS  read-only
		STATUS  mandatory
		DESCRIPTION "Number of EIR segments sent from
			this node to the source of this
			channel."
		::= { restStatChPktBypEntry 17 }

restStatChPktBypInEIRSegRcv 	OBJECT-TYPE
		SYNTAX  Counter
		ACCESS  read-only
		STATUS  mandatory
		DESCRIPTION "Number of EIR segments received at
			this node from the source of this
			channel."
		::= { restStatChPktBypEntry 18 }

restStatChPktBypInCIROctetSent 	OBJECT-TYPE
		SYNTAX  Counter
		ACCESS  read-only
		STATUS  mandatory
		DESCRIPTION "Number of CIR octets sent from
			this node to the source of this
			channel."
		::= { restStatChPktBypEntry 19 }

restStatChPktBypInCIROctetRcv 	OBJECT-TYPE
		SYNTAX  Counter
		ACCESS  read-only
		STATUS  mandatory
		DESCRIPTION "Number of CIR octets received at
			this node from the source of this
			channel."
		::= { restStatChPktBypEntry 20 }

restStatChPktBypInEIROctetSent 	OBJECT-TYPE
		SYNTAX  Counter
		ACCESS  read-only
		STATUS  mandatory
		DESCRIPTION "Number of EIR octets sent from
			this node to the source of this
			channel."
		::= { restStatChPktBypEntry 21 }

restStatChPktBypInEIROctetRcv 	OBJECT-TYPE
		SYNTAX  Counter
		ACCESS  read-only
		STATUS  mandatory
		DESCRIPTION "Number of EIR octets received at
			this node from the source of this
			channel."
		::= { restStatChPktBypEntry 22 }

restStatChPktBypInCIRSegDrop 	OBJECT-TYPE
		SYNTAX  Counter
		ACCESS  read-only
		STATUS  mandatory
		DESCRIPTION "Number of CIR segments received at
			this node from the source of this
			channel that have been dropped."
		::= { restStatChPktBypEntry 23 }

restStatChPktBypInEIRSegDrop 	OBJECT-TYPE
		SYNTAX  Counter
		ACCESS  read-only
		STATUS  mandatory
		DESCRIPTION "Number of EIR segments received at
			this node from the source of this
			channel that have been dropped."
		::= { restStatChPktBypEntry 24 }

restStatChPktBypInCIROctetDrop 	OBJECT-TYPE
		SYNTAX  Counter
		ACCESS  read-only
		STATUS  mandatory
		DESCRIPTION "Number of CIR octets received at
			this node from the source of this
			channel that have been dropped."
		::= { restStatChPktBypEntry 25 }

restStatChPktBypInEIROctetDrop 	OBJECT-TYPE
		SYNTAX  Counter
		ACCESS  read-only
		STATUS  mandatory
		DESCRIPTION "Number of EIR octets received at
			this node from the source of this
			channel that have been dropped."
		::= { restStatChPktBypEntry 26 }

restStatChPktBypOutCIRSegSent 	OBJECT-TYPE
		SYNTAX  Counter
		ACCESS  read-only
		STATUS  mandatory
		DESCRIPTION "Number of CIR segments sent from
			this node to the destination of this
			channel."
		::= { restStatChPktBypEntry 27 }

restStatChPktBypOutCIRSegRcv 	OBJECT-TYPE
		SYNTAX  Counter
		ACCESS  read-only
		STATUS  mandatory
		DESCRIPTION "Number of CIR segments received at
			this node from the destination of this
			channel."
		::= { restStatChPktBypEntry 28 }

restStatChPktBypOutEIRSegSent 	OBJECT-TYPE
		SYNTAX  Counter
		ACCESS  read-only
		STATUS  mandatory
		DESCRIPTION "Number of EIR segments sent from
			this node to the destination of this
			channel."
		::= { restStatChPktBypEntry 29 }

restStatChPktBypOutEIRSegRcv 	OBJECT-TYPE
		SYNTAX  Counter
		ACCESS  read-only
		STATUS  mandatory
		DESCRIPTION "Number of EIR segments received at
			this node from the destination of this
			channel."
		::= { restStatChPktBypEntry 30 }

restStatChPktBypOutCIROctetSent 	OBJECT-TYPE
		SYNTAX  Counter
		ACCESS  read-only
		STATUS  mandatory
		DESCRIPTION "Number of CIR octets sent from
			this node to the destination of this
			channel."
		::= { restStatChPktBypEntry 31 }

restStatChPktBypOutCIROctetRcv 	OBJECT-TYPE
		SYNTAX  Counter
		ACCESS  read-only
		STATUS  mandatory
		DESCRIPTION "Number of CIR octets received at
			this node from the destination of this
			channel."
		::= { restStatChPktBypEntry 32 }

restStatChPktBypOutEIROctetSent 	OBJECT-TYPE
		SYNTAX  Counter
		ACCESS  read-only
		STATUS  mandatory
		DESCRIPTION "Number of EIR octets sent from
			this node to the destination of this
			channel."
		::= { restStatChPktBypEntry 33 }

restStatChPktBypOutEIROctetRcv 	OBJECT-TYPE
		SYNTAX  Counter
		ACCESS  read-only
		STATUS  mandatory
		DESCRIPTION "Number of EIR octets received at
			this node from the destination of this
			channel."
		::= { restStatChPktBypEntry 34 }

restStatChPktBypOutCIRSegDrop 	OBJECT-TYPE
		SYNTAX  Counter
		ACCESS  read-only
		STATUS  mandatory
		DESCRIPTION "Number of CIR segments received at
			this node from the destination of this
			channel that have been dropped."
		::= { restStatChPktBypEntry 35 }

restStatChPktBypOutEIRSegDrop 	OBJECT-TYPE
		SYNTAX  Counter
		ACCESS  read-only
		STATUS  mandatory
		DESCRIPTION "Number of EIR segments received at
			this node from the destination of this
			channel that have been dropped."
		::= { restStatChPktBypEntry 36 }

restStatChPktBypOutCIROctetDrop 	OBJECT-TYPE
		SYNTAX  Counter
		ACCESS  read-only
		STATUS  mandatory
		DESCRIPTION "Number of CIR octets received at
			this node from the destination of this
			channel that have been dropped."
		::= { restStatChPktBypEntry 37 }

restStatChPktBypOutEIROctetDrop 	OBJECT-TYPE
		SYNTAX  Counter
		ACCESS  read-only
		STATUS  mandatory
		DESCRIPTION "Number of EIR octets received at
			this node from the destination of this
			channel that have been dropped."
		::= { restStatChPktBypEntry 38 }

restStatChPktBypSegSrcEIRDisc 	OBJECT-TYPE
		SYNTAX  Counter
		ACCESS  read-only
		STATUS  mandatory
		DESCRIPTION "Number of segments from the source
			of this channel that were discarded
			because the system was unable to send
			EIR traffic."
		::= { restStatChPktBypEntry 39 }

restStatChPktBypSegDstEIRDisc 	OBJECT-TYPE
		SYNTAX  Counter
		ACCESS  read-only
		STATUS  mandatory
		DESCRIPTION "Number of segments from the
			destination of this channel that were
			discarded because the system was unable
			to send EIR traffic."
		::= { restStatChPktBypEntry 40 }

restStatChPktBypSegSrcDstConDsc 	OBJECT-TYPE
		SYNTAX  Counter
		ACCESS  read-only
		STATUS  mandatory
		DESCRIPTION "Number of segments from the source
			of this channel that were discarded
			because the queue of segments to send
			to the destination was congested."
		::= { restStatChPktBypEntry 41 }

restStatChPktBypSegDstSrcConDsc 	OBJECT-TYPE
		SYNTAX  Counter
		ACCESS  read-only
		STATUS  mandatory
		DESCRIPTION "Number of segments from the
			destination of this channel that were
			discarded because the queue of segments
			to send to the source was congested."
		::= { restStatChPktBypEntry 42 }

restStatChPktBypSegInacSrcDisc 	OBJECT-TYPE
		SYNTAX  Counter
		ACCESS  read-only
		STATUS  mandatory
		DESCRIPTION "Number of segments discarded
			because the source of this channel
			was inactive."
		::= { restStatChPktBypEntry 43 }

restStatChPktBypSegInacDstDisc 	OBJECT-TYPE
		SYNTAX  Counter
		ACCESS  read-only
		STATUS  mandatory
		DESCRIPTION "Number of segments discarded
			because the destination of this
			channel was inactive."
		::= { restStatChPktBypEntry 44 }


-- INL Statistics MIB

restStatInl 	OBJECT IDENTIFIER ::= { reStatistics 3 }

restStatInlTable 	OBJECT-TYPE
		SYNTAX    SEQUENCE OF RestStatInlEntry
		ACCESS    not-accessible
		STATUS    mandatory
		DESCRIPTION " "
		::= { restStatInl 1 }

restStatInlEntry 	OBJECT-TYPE
		SYNTAX    RestStatInlEntry
		ACCESS  not-accessible
		STATUS  mandatory
		DESCRIPTION " "
		INDEX	{ restStatInlNumber,
			  restStatInlIndex }
		::= { restStatInlTable 1 }

RestStatInlEntry        	::= SEQUENCE {
		restStatInlNumber
			INTEGER,
		restStatInlIndex
			INTEGER,
		restStatInlStartTime
			INTEGER,
		restStatInlPktOctetSent
			INTEGER,
		restStatInlPktOctetRcv
			INTEGER
		}

restStatInlNumber 	OBJECT-TYPE
		SYNTAX    INTEGER (1..31)
		ACCESS  read-only
		STATUS  mandatory
		DESCRIPTION " "
		::= { restStatInlEntry 1 }

restStatInlIndex 	OBJECT-TYPE
		SYNTAX    INTEGER (1..96)
		ACCESS  read-only
		STATUS  mandatory
		DESCRIPTION " "
		::= { restStatInlEntry 2 }

restStatInlStartTime 	OBJECT-TYPE
		SYNTAX    INTEGER
		ACCESS    not-accessible
		STATUS    mandatory
		DESCRIPTION "Indicates when this statistics
			interval was started."
		::= { restStatInlEntry 3 }

restStatInlPktOctetSent 	OBJECT-TYPE
		SYNTAX  INTEGER
		ACCESS  read-only
		STATUS  mandatory
		DESCRIPTION "Number of octets sent across the
			INL. A value of 0 means that no data
			is available for that interval."
		::= { restStatInlEntry 4 }

restStatInlPktOctetRcv 	OBJECT-TYPE
		SYNTAX  INTEGER
		ACCESS  read-only
		STATUS  mandatory
		DESCRIPTION "Number of octets received across
			the INL. A value of 0 means that no
			data is available for that interval."
		::= { restStatInlEntry 5 }


-- Ad10 Statistics

restStatAd10 	OBJECT IDENTIFIER ::= { reStatistics 4 }


-- Ad10 Data Port Statistics

restStatAd10DataPortTable 	OBJECT-TYPE
		SYNTAX   SEQUENCE OF RestStatAd10DataPortEntry
		ACCESS   not-accessible
		STATUS   mandatory
		DESCRIPTION " "
		::= { restStatAd10 1 }

restStatAd10DataPortEntry 	OBJECT-TYPE
		SYNTAX   RestStatAd10DataPortEntry
		ACCESS   not-accessible
		STATUS   mandatory
		DESCRIPTION " "
		INDEX { restStatAd10DataPortAddr }
		::= { restStatAd10DataPortTable 1 }

RestStatAd10DataPortEntry    ::= SEQUENCE {
		restStatAd10DataPortAddr
			Ad10PortAddr,
		restStatAd10DataPortControl
			INTEGER,
		restStatAd10DataPortTxTotFrames
			Counter,
		restStatAd10DataPortRxTotFrames
			Counter,
		restStatAd10DataPortRxFrSeqErr
			Counter,
		restStatAd10DataPortRxFrHdrErr
			Counter,
		restStatAd10DataPortRxCongDisc
			Counter,
		restStatAd10DataPortTxCongDisc
			Counter,
		restStatAd10DataPortRxBecnCount
			Counter,
		restStatAd10DataPortTxBecnCount
			Counter,
		restStatAd10DataPortTxSCCOvrRun
			Counter,
		restStatAd10DataPortRxSCCUndRun
			Counter,
		restStatAd10DataPortTxSCCAbort
			Counter,
		restStatAd10DataPortTxFrOvrSize
			Counter,
		restStatAd10DataPortTxFifoFlCtl
			Counter,
		restStatAd10DataPortRxMinSegHt
			Counter,
		restStatAd10DataPortBertSynLoss
			Counter,
		restStatAd10DataPortBertByteCnt
			Counter,
		restStatAd10DataPortBertBitErr
			Counter
		}

restStatAd10DataPortAddr 	OBJECT-TYPE
		SYNTAX   Ad10PortAddr
		ACCESS   read-only
		STATUS   mandatory
		DESCRIPTION " "
		::= { restStatAd10DataPortEntry 1 }

restStatAd10DataPortControl 	OBJECT-TYPE
		SYNTAX   INTEGER {
			clearStats(1),
			clearBertStats(2)
			}
		ACCESS   write-only
		STATUS   mandatory
		DESCRIPTION " "
		::= { restStatAd10DataPortEntry 2 }

restStatAd10DataPortTxTotFrames 	OBJECT-TYPE
		SYNTAX   Counter
		ACCESS   read-only
		STATUS   mandatory
		DESCRIPTION " "
		::= { restStatAd10DataPortEntry 3 }

restStatAd10DataPortRxTotFrames 	OBJECT-TYPE
		SYNTAX   Counter
		ACCESS   read-only
		STATUS   mandatory
		DESCRIPTION " "
		::= { restStatAd10DataPortEntry 4 }

restStatAd10DataPortRxFrSeqErr 	OBJECT-TYPE
		SYNTAX   Counter
		ACCESS   read-only
		STATUS   mandatory
		DESCRIPTION " "
		::= { restStatAd10DataPortEntry 5 }

restStatAd10DataPortRxFrHdrErr 	OBJECT-TYPE
		SYNTAX   Counter
		ACCESS   read-only
		STATUS   mandatory
		DESCRIPTION " "
		::= { restStatAd10DataPortEntry 6 }

restStatAd10DataPortRxCongDisc 	OBJECT-TYPE
		SYNTAX   Counter
		ACCESS   read-only
		STATUS   mandatory
		DESCRIPTION " "
		::= { restStatAd10DataPortEntry 7 }

restStatAd10DataPortTxCongDisc 	OBJECT-TYPE
		SYNTAX   Counter
		ACCESS   read-only
		STATUS   mandatory
		DESCRIPTION " "
		::= { restStatAd10DataPortEntry 8 }

restStatAd10DataPortRxBecnCount 	OBJECT-TYPE
		SYNTAX   Counter
		ACCESS   read-only
		STATUS   mandatory
		DESCRIPTION " "
		::= { restStatAd10DataPortEntry 9 }

restStatAd10DataPortTxBecnCount 	OBJECT-TYPE
		SYNTAX   Counter
		ACCESS   read-only
		STATUS   mandatory
		DESCRIPTION " "
		::= { restStatAd10DataPortEntry 10 }

restStatAd10DataPortTxSCCOvrRun 	OBJECT-TYPE
		SYNTAX   Counter
		ACCESS   read-only
		STATUS   mandatory
		DESCRIPTION " "
		::= { restStatAd10DataPortEntry 11 }

restStatAd10DataPortRxSCCUndRun 	OBJECT-TYPE
		SYNTAX   Counter
		ACCESS   read-only
		STATUS   mandatory
		DESCRIPTION " "
		::= { restStatAd10DataPortEntry 12 }

restStatAd10DataPortTxSCCAbort 	OBJECT-TYPE
		SYNTAX   Counter
		ACCESS   read-only
		STATUS   mandatory
		DESCRIPTION " "
		::= { restStatAd10DataPortEntry 13 }

restStatAd10DataPortTxFrOvrSize 	OBJECT-TYPE
		SYNTAX   Counter
		ACCESS   read-only
		STATUS   mandatory
		DESCRIPTION " "
		::= { restStatAd10DataPortEntry 14 }

restStatAd10DataPortTxFifoFlCtl 	OBJECT-TYPE
		SYNTAX   Counter
		ACCESS   read-only
		STATUS   mandatory
		DESCRIPTION " "
		::= { restStatAd10DataPortEntry 15 }

restStatAd10DataPortRxMinSegHt 	OBJECT-TYPE
		SYNTAX   Counter
		ACCESS   read-only
		STATUS   mandatory
		DESCRIPTION " "
		::= { restStatAd10DataPortEntry 16 }

restStatAd10DataPortBertSynLoss 	OBJECT-TYPE
		SYNTAX   Counter
		ACCESS   read-only
		STATUS   mandatory
		DESCRIPTION " "
		::= { restStatAd10DataPortEntry 17 }

restStatAd10DataPortBertByteCnt 	OBJECT-TYPE
		SYNTAX   Counter
		ACCESS   read-only
		STATUS   mandatory
		DESCRIPTION " "
		::= { restStatAd10DataPortEntry 18 }

restStatAd10DataPortBertBitErr 	OBJECT-TYPE
		SYNTAX   Counter
		ACCESS   read-only
		STATUS   mandatory
		DESCRIPTION " "
		::= { restStatAd10DataPortEntry 19 }


-- Ad10 Voice Port Statistics

restStatAd10VoicePortTable 	OBJECT-TYPE
		SYNTAX   SEQUENCE OF RestStatAd10VoicePortEntry
		ACCESS   not-accessible
		STATUS   mandatory
		DESCRIPTION " "
		::= { restStatAd10 2 }

restStatAd10VoicePortEntry 	OBJECT-TYPE
		SYNTAX   RestStatAd10VoicePortEntry
		ACCESS   not-accessible
		STATUS   mandatory
		DESCRIPTION " "
		INDEX { restStatAd10VoicePortAddr }
		::= { restStatAd10VoicePortTable 1 }

RestStatAd10VoicePortEntry    ::= SEQUENCE {
		restStatAd10VoicePortAddr
			Ad10PortAddr,
		restStatAd10VoicePortControl
			INTEGER,
		restStatAd10VoicePortHber
			Counter,
		restStatAd10VoicePortSyncLoss
			Counter,
		restStatAd10VoicePortBertByte
			Counter,
		restStatAd10VoicePortBertBitErr
			Counter
		}

restStatAd10VoicePortAddr 	OBJECT-TYPE
		SYNTAX   Ad10PortAddr
		ACCESS   read-only
		STATUS   mandatory
		DESCRIPTION " "
		::= { restStatAd10VoicePortEntry 1 }

restStatAd10VoicePortControl 	OBJECT-TYPE
		SYNTAX   INTEGER {
			clearStats(1),
			clearBertStats(2)
			}
		ACCESS   write-only
		STATUS   mandatory
		DESCRIPTION " "
		::= { restStatAd10VoicePortEntry 2 }

restStatAd10VoicePortHber 	OBJECT-TYPE
		SYNTAX    Counter
		ACCESS    read-only
		STATUS    mandatory
		DESCRIPTION " "
		::= { restStatAd10VoicePortEntry 3 }

restStatAd10VoicePortSyncLoss 	OBJECT-TYPE
		SYNTAX    Counter
		ACCESS    read-only
		STATUS    mandatory
		DESCRIPTION " "
		::= { restStatAd10VoicePortEntry 4 }

restStatAd10VoicePortBertByte 	OBJECT-TYPE
		SYNTAX   Counter
		ACCESS   read-only
		STATUS   mandatory
		DESCRIPTION " "
		::= { restStatAd10VoicePortEntry 5 }

restStatAd10VoicePortBertBitErr 	OBJECT-TYPE
		SYNTAX   Counter
		ACCESS   read-only
		STATUS   mandatory
		DESCRIPTION " "
		::= { restStatAd10VoicePortEntry 6 }


-- Ad10 Packet Band Statistics

restStatAd10PktBandTable 	OBJECT-TYPE
		SYNTAX   SEQUENCE OF RestStatAd10PktBandEntry
		ACCESS   not-accessible
		STATUS   mandatory
		DESCRIPTION " "
		::= { restStatAd10 3 }

restStatAd10PktBandEntry 	OBJECT-TYPE
		SYNTAX   RestStatAd10PktBandEntry
		ACCESS   not-accessible
		STATUS   mandatory
		DESCRIPTION " "
		INDEX { restStatAd10PktBandAddr }
		::= { restStatAd10PktBandTable 1 }

RestStatAd10PktBandEntry    ::= SEQUENCE {
		restStatAd10PktBandAddr
			Ad10PortAddr,
		restStatAd10PktBandControl
			INTEGER,
		restStatAd10PktBandTxTotFrames
			Counter,
		restStatAd10PktBandRxTotFrames
			Counter,
		restStatAd10PktBandRxFrErr
			Counter,
		restStatAd10PktBandRxSCCOvrRun
			Counter,
		restStatAd10PktBandTxSCCUndRun
			Counter,
		restStatAd10PktBandRxSCCAbort
			Counter,
		restStatAd10PktBandRxInvDlci
			Counter,
		restStatAd10PktBandRxFrOvrSize
			Counter,
		restStatAd10PktBandRxCrcErr
			Counter
		}

restStatAd10PktBandAddr 	OBJECT-TYPE
		SYNTAX   Ad10PortAddr
		ACCESS   read-only
		STATUS   mandatory
		DESCRIPTION " "
		::= { restStatAd10PktBandEntry 1 }

restStatAd10PktBandControl 	OBJECT-TYPE
		SYNTAX   INTEGER {
			clearStats(1)
			}
		ACCESS   write-only
		STATUS   mandatory
		DESCRIPTION " "
		::= { restStatAd10PktBandEntry 2 }

restStatAd10PktBandTxTotFrames 	OBJECT-TYPE
		SYNTAX    Counter
		ACCESS    read-only
		STATUS    mandatory
		DESCRIPTION " "
		::= { restStatAd10PktBandEntry 3 }

restStatAd10PktBandRxTotFrames 	OBJECT-TYPE
		SYNTAX    Counter
		ACCESS    read-only
		STATUS    mandatory
		DESCRIPTION " "
		::= { restStatAd10PktBandEntry 4 }

restStatAd10PktBandRxFrErr 	OBJECT-TYPE
		SYNTAX    Counter
		ACCESS    read-only
		STATUS    mandatory
		DESCRIPTION " "
		::= { restStatAd10PktBandEntry 5 }

restStatAd10PktBandRxSCCOvrRun 	OBJECT-TYPE
		SYNTAX    Counter
		ACCESS    read-only
		STATUS    mandatory
		DESCRIPTION " "
		::= { restStatAd10PktBandEntry 6 }

restStatAd10PktBandTxSCCUndRun 	OBJECT-TYPE
		SYNTAX    Counter
		ACCESS    read-only
		STATUS    mandatory
		DESCRIPTION " "
		::= { restStatAd10PktBandEntry 7 }

restStatAd10PktBandRxSCCAbort 	OBJECT-TYPE
		SYNTAX    Counter
		ACCESS    read-only
		STATUS    mandatory
		DESCRIPTION " "
		::= { restStatAd10PktBandEntry 8 }

restStatAd10PktBandRxInvDlci 	OBJECT-TYPE
		SYNTAX    Counter
		ACCESS    read-only
		STATUS    mandatory
		DESCRIPTION " "
		::= { restStatAd10PktBandEntry 9 }

restStatAd10PktBandRxFrOvrSize 	OBJECT-TYPE
		SYNTAX    Counter
		ACCESS    read-only
		STATUS    mandatory
		DESCRIPTION " "
		::= { restStatAd10PktBandEntry 10 }

restStatAd10PktBandRxCrcErr 	OBJECT-TYPE
		SYNTAX    Counter
		ACCESS    read-only
		STATUS    mandatory
		DESCRIPTION " "
		::= { restStatAd10PktBandEntry 11 }


-- Module-Level Statistics

restStatModule 	OBJECT IDENTIFIER ::= { reStatistics 5 }

-- DSM Module-Level Statistics

restStatModDsmTable 	OBJECT-TYPE
		SYNTAX  SEQUENCE OF RestStatModDsmEntry
		ACCESS  not-accessible
		STATUS  mandatory
		DESCRIPTION " "
		::= { restStatModule 1 }

restStatModDsmEntry 	OBJECT-TYPE
		SYNTAX  RestStatModDsmEntry
		ACCESS  not-accessible
		STATUS  mandatory
		DESCRIPTION "INTRODUCED 2.0.0"
		INDEX   { restStatModDsmAddr }
		::= { restStatModDsmTable 1 }

RestStatModDsmEntry		::= SEQUENCE {
		restStatModDsmAddr
			SlotAddr,
		restStatModDsmControlMode
			INTEGER,
		restStatModDsmRejectOrigCalls
			Counter,
		restStatModDsmRejectTermCalls
			Counter
		}

restStatModDsmAddr 	OBJECT-TYPE
		SYNTAX  SlotAddr
		ACCESS  read-only
		STATUS  mandatory
		DESCRIPTION "Address of a DSM module. The
			format of the address is nest.slot."
		::= { restStatModDsmEntry 1 }

restStatModDsmControlMode 	OBJECT-TYPE
		SYNTAX  INTEGER {
			clearStats(3)
			}
		ACCESS  write-only
		STATUS  mandatory
		DESCRIPTION "Setting this field to clearStats
			will reset all of the counters in this
			MIB section to zero."
		::= { restStatModDsmEntry 2 }

restStatModDsmRejectOrigCalls 	OBJECT-TYPE
		SYNTAX  Counter
		ACCESS  read-only
		STATUS  mandatory
		DESCRIPTION "Number of calls initiated by a
			local ISPBX that were rejected for any
			reason."
		::= { restStatModDsmEntry 3 }

restStatModDsmRejectTermCalls 	OBJECT-TYPE
		SYNTAX  Counter
		ACCESS  read-only
		STATUS  mandatory
		DESCRIPTION "Number of calls initiated by a DSM
			that would be terminated on this DSM
			and that were rejected for any reason."
		::= { restStatModDsmEntry 4 }

-- Alarm MIB

alPartitionHeader 	OBJECT IDENTIFIER ::= { alarm 1 }

alPartitionControl 	OBJECT-TYPE
		SYNTAX    INTEGER {
			      validateCRC(1),
			      invalidateCRC(2)
			 }
		ACCESS    write-only
		STATUS    mandatory
		DESCRIPTION "Parameter Type = Immediate."
		::= { alPartitionHeader 1 }

alPartitionCRCCheck 	OBJECT-TYPE
		SYNTAX    INTEGER {
			      succeed(1),
			      fail(2)
			 }
		ACCESS    read-only
		STATUS    mandatory
		DESCRIPTION "Parameter Type = Internal."
		::= { alPartitionHeader 2 }

alPartitionFlushMode 	OBJECT-TYPE
		SYNTAX    INTEGER {
			      enable(1),
			      disable(2)
			 }
		ACCESS    read-write
		STATUS    mandatory
		DESCRIPTION "Parameter Type = Immediate."
		::= { alPartitionHeader 3 }


-- Synchrony Alarm System Configuration

alSystemProfile 	OBJECT IDENTIFIER ::=  { alarm 2 }

alSysLogSize 	OBJECT-TYPE
		SYNTAX    OCTET STRING (SIZE (32))
		ACCESS    read-write
		STATUS    mandatory
		DESCRIPTION "Parameter Type = Immediate.
			Assign the size to each of the 32 alarm logs.
			The sizes are specified in units of Kbytes.
			The total size cannot exceed 128K bytes."
		::=  { alSystemProfile 1 }

alSysLogSizeAvailable 	OBJECT-TYPE
		SYNTAX    INTEGER
		ACCESS    read-only
		STATUS    mandatory
		DESCRIPTION "Parameter Type = Internal.
			The amount of remaining alarm log space
			in units of Kbytes."
		::=  { alSystemProfile 2 }


-- Synchrony Alarm Log Configuration

alLogTable 	OBJECT-TYPE
		SYNTAX    SEQUENCE OF AlLogEntry
		ACCESS    not-accessible
		STATUS    mandatory
		DESCRIPTION " "
		::=  { alarm 3 }

alLogEntry 	OBJECT-TYPE
		SYNTAX    AlLogEntry
		ACCESS    not-accessible
		STATUS    mandatory
		DESCRIPTION " "
		INDEX { alLogIndex }
		::=  { alLogTable 1 }

AlLogEntry 	::=  SEQUENCE {
                         alLogIndex
                                   INTEGER,
                         alLogDiagnostics
                                   INTEGER,
                         alLogState
                                   INTEGER,
                         alLogTotalEntries
                                   INTEGER,
                         alLogAvailableEntries
                                   INTEGER,
                         alLogNotificationList
                                   OCTET STRING,
			 alLogClearEntries
				   INTEGER,
                         alLogPartitionID
                                   INTEGER
		}


alLogIndex 	OBJECT-TYPE
		SYNTAX    INTEGER (1..32)
		ACCESS    read-only
		STATUS    mandatory
		DESCRIPTION "Parameter Type = Internal."
		::=  { alLogEntry 1 }

alLogDiagnostics 	OBJECT-TYPE
		SYNTAX    INTEGER {
                                   enableNotification(1),
                                   disableNotification(2),
                                   clearAlarmLog(3),
                                   disableLogging(4),
                                   clearOverflow(5)
                                   }
		ACCESS    write-only
		STATUS    mandatory
		DESCRIPTION "Parameter Type = Immediate."
		::=  { alLogEntry 2 }

alLogState 	OBJECT-TYPE
		SYNTAX    INTEGER {
                                   notificationOn(1),
                                   notificationOff(2),
                                   notificationOnWoverflow(3),
                                   notificationOffWoverflow(4),
                                   loggingDisabled(5)
                                   }
		ACCESS    read-only
		STATUS    mandatory
		DESCRIPTION "Parameter Type = Internal."
		::=  { alLogEntry 3 }

alLogTotalEntries 	OBJECT-TYPE
		SYNTAX    INTEGER
		ACCESS    read-only
		STATUS    mandatory
		DESCRIPTION "Parameter Type = Internal.
			The number of outstanding alarms contained
			within this alarm log."
		::=  { alLogEntry 4 }

alLogAvailableEntries 	OBJECT-TYPE
		SYNTAX    INTEGER
		ACCESS    read-only
		STATUS    mandatory
		DESCRIPTION "Parameter Type = Internal.
			The total number of available entries in the
			alarm log. This is based on the size of the
			alarm log."
		::=  { alLogEntry 5 }

alLogNotificationList 	OBJECT-TYPE
		SYNTAX    OCTET STRING (SIZE (32))
		ACCESS    read-write
		STATUS    mandatory
		DESCRIPTION "Parameter Type = Immediate.
			Specifies root nodes that should receive alarm
			notifications for alarms in this log. These
			root nodes will send traps to EMS stations
			based upon their own trap access tables. Up to
			16 root node address can be specified."
		::=  { alLogEntry 6 }

alLogClearEntries 	OBJECT-TYPE
		SYNTAX    INTEGER
		ACCESS    write-only
		STATUS    mandatory
		DESCRIPTION "Parameter Type = Immediate.
			   Set this field to the number of
                           alarm entries you wish to clear from the
                           top of the log."
		::=  { alLogEntry 7 }

alLogPartitionID 	OBJECT-TYPE
		SYNTAX    INTEGER (1..1023)
		ACCESS    read-write
		STATUS    mandatory
		DESCRIPTION "Parameter Type = Immediate."
		::=  { alLogEntry 8 }


-- Synchrony Logged Alarm Records

alLogRecTable 	OBJECT-TYPE
		SYNTAX    SEQUENCE OF AlLogRecEntry
		ACCESS    not-accessible
		STATUS    mandatory
		DESCRIPTION " "
		::=  { alarm 4 }

alLogRecEntry 	OBJECT-TYPE
		SYNTAX    AlLogRecEntry
		ACCESS    not-accessible
		STATUS    mandatory
		DESCRIPTION " "
		INDEX { alLogRecIndex }
		::=  { alLogRecTable 1 }


AlLogRecEntry   ::=  SEQUENCE {
                         alLogRecIndex
                                   RecordIndex,
                         alLogRecContents
                                   AlarmRecord
		}

alLogRecIndex 	OBJECT-TYPE
		SYNTAX    RecordIndex
		ACCESS    read-only
		STATUS    mandatory
		DESCRIPTION "Parameter Type = Internal."
		::=  { alLogRecEntry 1 }


alLogRecContents 	OBJECT-TYPE
		SYNTAX    AlarmRecord
		ACCESS    read-only
		STATUS    mandatory
		DESCRIPTION "Parameter Type = Internal."
		::=  { alLogRecEntry 2 }


-- Trap Contents

alTrapContents 	OBJECT-TYPE
		SYNTAX    OCTET STRING (SIZE (10))
		ACCESS    not-accessible
		STATUS    mandatory
		DESCRIPTION " "
		::=  { alarm 5 }

END
