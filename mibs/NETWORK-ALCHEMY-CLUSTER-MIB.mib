NETWORK-ALCHEMY-CLUSTER-MIB DEFINITIONS ::= BEGIN

-- Title:		    Network Alchemy Crypto Cluster MIB
-- Date:		    January 22, 2000
-- Author:		    Jonny Larson (jlarson@network-alchemy.com)
-- Location:		    Santa Cruz, CA

IMPORTS  netalModules, cryptoCluster, netalTraps
             FROM NETAL-SMI
         MODULE-IDENTITY, OBJECT-TYPE, NOTIFICATION-TYPE, IpAddress, Integer32
             FROM SNMPv2-SMI
         DisplayString
             FROM SNMPv2-TC;

networkAlchemyClusterMIB MODULE-IDENTITY
    LAST-UPDATED "200010250000Z"
    ORGANIZATION "Network Alchemy, Inc."
    CONTACT-INFO 
		 "	Network Alchemy
			Customer Support

		  Postal: 1538 Pacific Av.
			Santa Cruz, CA 95060
			USA
	          E-Mail: snmp-contact@network-alchemy.com"

    DESCRIPTION "Cluster MIB module."
    REVISION "200010250000Z"
    DESCRIPTION "Cleanup."
    ::= { netalModules 2 }

clusterInfoName OBJECT-TYPE
    SYNTAX      DisplayString
    MAX-ACCESS  read-only
    STATUS      current
    DESCRIPTION "Name of this cluster"
    ::= { cryptoCluster 1 }

clusterMemberInfoNumMembers OBJECT-TYPE
    SYNTAX      INTEGER (0..255)
    MAX-ACCESS  read-only
    STATUS      current
    DESCRIPTION "Number of members in this cluster"
    ::= { cryptoCluster 2 }

clusterAddrTable OBJECT-TYPE
        SYNTAX        SEQUENCE OF ClusterAddrEntry
        MAX-ACCESS    not-accessible
        STATUS        current
	DESCRIPTION   "List of IP addresses for this cluster."
	::= { cryptoCluster 3 }

clusterAddrEntry OBJECT-TYPE
        SYNTAX        ClusterAddrEntry
        MAX-ACCESS    not-accessible
        STATUS        current
	DESCRIPTION   ""
	INDEX	      { clusterAddrIndex }
	::= { clusterAddrTable 1 }

ClusterAddrEntry ::= SEQUENCE {
		 clusterAddrIndex	INTEGER,
                 clusterInfoAddrs       IpAddress
		 }

clusterAddrIndex OBJECT-TYPE
        SYNTAX        INTEGER (0..255)
        MAX-ACCESS    read-only
        STATUS        current
	DESCRIPTION   "The index of the member list for this cluster"
	::= { clusterAddrEntry 1 }

clusterInfoAddrs OBJECT-TYPE
        SYNTAX        IpAddress
        MAX-ACCESS    read-only
        STATUS        current
	DESCRIPTION   "List of the cluster's IP addresses"
	::= { clusterAddrEntry 2 }

-- The cluster table

clusterMemberTable OBJECT-TYPE
    SYNTAX	SEQUENCE OF ClusterMemberEntry
    MAX-ACCESS  not-accessible
    STATUS      current
    DESCRIPTION	"A list of information, one entry for each member of the cluster"
    ::= { cryptoCluster 4 }

clusterMemberEntry OBJECT-TYPE
        SYNTAX        ClusterMemberEntry
        MAX-ACCESS    not-accessible
        STATUS        current
        DESCRIPTION   "A table entry containing information about a member of the cluster."
        INDEX         { clusterMemberIndex }
        ::= { clusterMemberTable 1 }

ClusterMemberEntry ::= SEQUENCE {
                clusterMemberIndex              INTEGER,
                clusterMemberPrimaryIPAddr      IpAddress,
                clusterMemberWorkload           INTEGER (0..255),
                clusterMemberMaster             INTEGER (0..255)
	     }

clusterMemberIndex OBJECT-TYPE
        SYNTAX        INTEGER (1..255)
        MAX-ACCESS    read-only
        STATUS        current
        DESCRIPTION   "A unique value for each member in the
                      cluster.  The value ranges between 1 and the value of
                      clusterMemberInfoNumMembers."
        ::= { clusterMemberEntry 1 }

clusterMemberPrimaryIPAddr OBJECT-TYPE
        SYNTAX        IpAddress
        MAX-ACCESS    read-only
        STATUS        current
	DESCRIPTION   "The member's primary IP address"
	::= { clusterMemberEntry 2 }

clusterMemberWorkload OBJECT-TYPE
        SYNTAX        INTEGER (0..255)
        MAX-ACCESS    read-only
        STATUS        current
	DESCRIPTION   "The member's workload"
	::= { clusterMemberEntry 3 }

clusterMemberMaster OBJECT-TYPE
        SYNTAX        INTEGER { no(0), yes(1) }
        MAX-ACCESS    read-only
        STATUS        current
	DESCRIPTION   "Is this member the master???"
	::= { clusterMemberEntry 4 }

-- Each member of the cluster can have a list of secondary IP addresses...

clusterMemberSecondaryIPAddrTable OBJECT-TYPE
         SYNTAX	SEQUENCE OF ClusterMemberSecondaryIPAddrEntry
         MAX-ACCESS not-accessible
         STATUS current
         DESCRIPTION	"A table of secondary IP addresses for this cluster member"
	 ::= { cryptoCluster 5 }

clusterMemberSecondaryIPAddrEntry OBJECT-TYPE
	SYNTAX        ClusterMemberSecondaryIPAddrEntry
        MAX-ACCESS    not-accessible
        STATUS        current
        DESCRIPTION   "List of the secondary (outside) addresses of the cluster
			    members.  This is only valid if this member is the
			    master node of the cluster."
        INDEX         { clusterMemberIndex, clusterMemberSecondaryIPAddrIndex }
        ::= { clusterMemberSecondaryIPAddrTable 1 }

ClusterMemberSecondaryIPAddrEntry ::= SEQUENCE {
		clusterMemberSecondaryIPAddr			IpAddress,
		clusterMemberSecondaryIPAddrIndex		Integer32
	     }

clusterMemberSecondaryIPAddr OBJECT-TYPE
        SYNTAX        IpAddress
        MAX-ACCESS    read-only
        STATUS        current
	DESCRIPTION   "One member of the cluster's secondary IP address"
	::= { clusterMemberSecondaryIPAddrEntry 1 }


clusterMemberSecondaryIPAddrIndex OBJECT-TYPE
        SYNTAX       Integer32
        MAX-ACCESS   not-accessible
        STATUS       current
        DESCRIPTION "Second index for clusterMemberSecondaryIPAddrTable. The
		      first entry has index 1, the second 2, etc."
        ::= { clusterMemberSecondaryIPAddrEntry 2 }


-- Following are the various cluster traps that can and will be sent.

netalTrap0 NOTIFICATION-TYPE
    STATUS     current
    DESCRIPTION
        "Trap."
    ::= { netalTraps 0 }

clusterMemberJoin NOTIFICATION-TYPE
    STATUS     current
    DESCRIPTION
        "Signifies that a member node has joined the cluster."
    ::= { netalTrap0 1 }

clusterMemberLeft NOTIFICATION-TYPE
    STATUS     current
    DESCRIPTION
        "Signifies that a node has left the cluster."
    ::= { netalTrap0 2 }

clusterMemberBecameMaster NOTIFICATION-TYPE
    STATUS     current
    DESCRIPTION
        "Sent when a node has been made the master."
    ::= { netalTrap0 3 }

END
