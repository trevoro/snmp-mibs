AVICI-TC DEFINITIONS ::= BEGIN

IMPORTS
   MODULE-IDENTITY, Unsigned32
      FROM SNMPv2-SMI
   DisplayString, TEXTUAL-CONVENTION
      FROM SNMPv2-TC   
   aviciTypes
      FROM AVICI-SMI;

aviciTextualConventions MODULE-IDENTITY
   LAST-UPDATED   "000907140000Z"
   ORGANIZATION   "Avici Systems, Inc."
   CONTACT-INFO   "
                  Avici Systems, Inc.
                  101 Billerica Avenue
                  North Billerica, MA 01862-1256
 
                  (978) 964-2000
                  (978) 964-2100 (fax)
 
                  snmp@avici.com"
   DESCRIPTION
      "This MIB module specifies the types to be used in Avici MIBs."
   REVISION      "000907140000Z"
   DESCRIPTION
      "Added new textual conventions for fabric."
   REVISION      "990330095500Z"
   DESCRIPTION
      "Created MIB module."
   ::= { aviciTypes 1 }

  AviciSystemType ::= TEXTUAL-CONVENTION
    STATUS       current
    DESCRIPTION
        ""
    SYNTAX       INTEGER {
        tsr(1)
        }

  AviciInventoryType ::= TEXTUAL-CONVENTION
    STATUS       current
    DESCRIPTION
        ""
    SYNTAX       INTEGER {
        server (1),
	bayController (2),
	module (3),
        serverAccessModule (4)
        }

  AviciHighAvailabilityType ::= TEXTUAL-CONVENTION
    STATUS       current
    DESCRIPTION
        ""
    SYNTAX       INTEGER {
        primary (1),
        secondary (2)
        }
 

  AviciVoltageType ::= TEXTUAL-CONVENTION
    STATUS       current
    DESCRIPTION  
	""
    SYNTAX       INTEGER {
        other(1),
        bayInput(2),         -- negative 48-volt bay input
        controllerInput(3),  -- negative 48-volt selena input
        voltageRail(4)       -- 12-volt rail
	}

  AviciBayType ::= TEXTUAL-CONVENTION
    STATUS       current
    DESCRIPTION  
	"The maximum number of bays in an Avici Terabit Switch Router."
    SYNTAX       INTEGER (1..14)
	
  AviciSlotType ::= TEXTUAL-CONVENTION
    STATUS       current
    DESCRIPTION  
	"The maximum number of slots in one Avici Bay."
    SYNTAX       INTEGER (1..40)
	
  AviciSerialNumberType ::= TEXTUAL-CONVENTION
    STATUS      current
    DESCRIPTION  
	"The serial number of this object."
	SYNTAX      DisplayString (SIZE (0..13))

  AviciPartNumberType ::= TEXTUAL-CONVENTION
    STATUS      current
    DESCRIPTION  
	"The part number of this object."
	SYNTAX      DisplayString (SIZE (0..9))

  AviciProductIdType ::= TEXTUAL-CONVENTION
    STATUS      current
    DESCRIPTION  
	"The part number of this object."
	SYNTAX      DisplayString (SIZE (0..26))

  AviciProductRevisionType ::= TEXTUAL-CONVENTION
    STATUS      current
    DESCRIPTION  
	"The product revision number.  The revision number is
         a string using the form ??? to identify
         the version."
    SYNTAX      DisplayString (SIZE (0..3))	

	
  AviciRevisionType ::= TEXTUAL-CONVENTION
    STATUS      current
    DESCRIPTION  
	"The revision number of this object.  The revision number is
         a string using the form MajorRevision.MinorRevision to identify
         the version."
    SYNTAX      DisplayString (SIZE (1..6))	

  AviciTrapDescrType ::= TEXTUAL-CONVENTION
    STATUS      current
    DESCRIPTION
    "A description of the trap that has occurred."
    SYNTAX      DisplayString (SIZE(0..255))
	  
  AviciUnitType ::= TEXTUAL-CONVENTION
    STATUS      current
    DESCRIPTION
    "The type of this object."
    SYNTAX       INTEGER {
        fan(1),
        module(2),  
        breaker(3),
        bayController(4),
        voltageRail(5),
        server(6),
        multipleFailures(7)
	}
  AviciLedValue ::= TEXTUAL-CONVENTION
      STATUS       current
      DESCRIPTION
          ""
      SYNTAX       INTEGER {
          on(1),
          off(2),
          red(3),
          redblink(4),
          amber(5),
          amberblink(6),
          green(7),
          greenblink(8)
          }

  AviciPlatformIndexType ::= TEXTUAL-CONVENTION
      STATUS        current
      DESCRIPTION
          "The index number of the platform described by this object.
           The high 16 bits represents the platform type as follows
                    1  Bay Controller
                    2  Module
                    3  Server
           The low 16 bits represents the ID of the platform. For a server, 
           the ID is the server id.
           For a module, the ID is slot number + (bay number - 1) * 40.
           For a bay controller, the ID is slot number + (bay number - 1) * 2."
      SYNTAX        Unsigned32 (1..4294967295)

--
-- Avici Fabric Textual Conventions
--

AviciFabricLinkType ::= TEXTUAL-CONVENTION
   STATUS      current
   DESCRIPTION
       "The names of the fabric links."
   SYNTAX      INTEGER {
               plusX  (0),
               minusX (1),
               plusY  (2),
               minusY (3),
               plusZ  (4),
               minusZ (5),
               plusE  (6),
               minusE (7)
       }

--
-- Avici Module Name
--

AviciModuleName ::= TEXTUAL-CONVENTION
   STATUS      current
   DESCRIPTION
       "The string name for a module in a given system.

        Examples:  module 1/17
                   none
        "
   SYNTAX      DisplayString (SIZE(0..16))
  
END
