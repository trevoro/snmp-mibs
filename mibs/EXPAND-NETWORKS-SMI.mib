--
-- EXPAND-NETWORKS-SMI.my
-- MIB generated by MG-SOFT Visual MIB Builder Version 3.0 Build 253
-- Sunday, June 16, 2002 at 17:30:36
--

-- 
-- Expand Networks. 
-- Product Line MIB Version 1.0.8

	EXPAND-NETWORKS-SMI DEFINITIONS ::= BEGIN
 
		IMPORTS
			OBJECT-TYPE			
				FROM RFC-1212			
			enterprises			
				FROM RFC1155-SMI;
	
	
--
-- Node definitions
--
	
-- Begining of Expand-Networks private MIB.
		-- 1.3.1.1.1.1.3405
		expand-networks OBJECT IDENTIFIER ::= { enterprises 3405 }
		
		-- 1.3.1.1.1.1.3405.1
		expandSystemId OBJECT-TYPE
			SYNTAX OBJECT IDENTIFIER
			ACCESS read-only
			STATUS mandatory
			DESCRIPTION
				"This object identifier defines the object identifiers that
				are assigned to the various Expand-Networks operating systems,
				and hence are returned as values for sysObjectID leaf of 
				MIB 2."
			::= { expand-networks 1 }
		
		-- 1.3.1.1.1.1.3405.2
		expandProducts OBJECT IDENTIFIER ::= { expand-networks 2 }
		
		-- 1.3.1.1.1.1.3405.3
		acceleratorOs OBJECT IDENTIFIER ::= { expand-networks 3 }
		
		-- 1.3.1.1.1.1.3405.4
		p2pAccelerator OBJECT IDENTIFIER ::= { expand-networks 4 }
		
		-- 1.3.1.1.1.1.3405.10
		management OBJECT IDENTIFIER ::= { expand-networks 10 }
		
	
	END

--
-- EXPAND-NETWORKS-SMI.my
--
