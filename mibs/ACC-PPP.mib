ACC-PPP DEFINITIONS ::= BEGIN

    IMPORTS
	 OBJECT-TYPE, IpAddress, TimeTicks, Gauge, Counter FROM RFC1155-SMI
	 TRAP-TYPE FROM RFC-1215
	 ifIndex FROM RFC1213-MIB
        accTrapLogSeqNum FROM ACC-SYSTEM
--	accBRG, DisplayString, RowStatus, IfIndex, SmdsAddress
--            FROM ACC-MIB
        accMlPppIndex, accMultilink FROM ACC-MULTILINK
--      ifOperStatus FROM RFC-1213;
        ifOperStatus FROM ACC-FAKE
        accBRG, DisplayString, RowStatus, IfIndex, SmdsAddress
             FROM ACC-MIB;
--        accPppAuthParmMethodIn, accPppAuthParmUserNameIn
--            FROM ACC-PPP;
-- Point-to-Point Protocol Group
      accPpp         OBJECT IDENTIFIER ::= { accBRG 32 }
          accPppLinkTable   OBJECT-TYPE
               SYNTAX    SEQUENCE OF AccPppLinkEntry
               ACCESS    not-accessible
               STATUS    mandatory
               DESCRIPTION
                         "A table containing PPP-link specific variables
                         for this PPP implementation."
               ::= { accPpp 1 }
          accPppLinkEntry   OBJECT-TYPE
               SYNTAX    AccPppLinkEntry
               ACCESS    not-accessible
               STATUS    mandatory
               DESCRIPTION
                         "Management information about a particular PPP
                         Link."
               INDEX     { accPppLinkIndex }
               ::= { accPppLinkTable 1 }
          AccPppLinkEntry ::= SEQUENCE {
               accPppLinkIndex			INTEGER,
	       accPppLinkPhysicalIndex		INTEGER,
               accPppLinkBadAddresses		Counter,
               accPppLinkBadControls		Counter,
               accPppLinkPacketTooLongs		Counter,
               accPppLinkBadFCSs		Counter,
               accPppLinkLocalMRU		INTEGER,
               accPppLinkRemoteMRU		INTEGER,
	       accPppLinkLocalToPeerACCMap	OCTET STRING,
	       accPppLinkPeerToLocalACCMap	OCTET STRING,
	       accPppLinkLocalToRemotePC	INTEGER,
	       accPppLinkRemoteToLocalPC	INTEGER,
	       accPppLinkLocalToRemoteAC	INTEGER,
	       accPppLinkRemoteToLocalAC	INTEGER,
	       accPppLinkTransmit32BitFcs	INTEGER,
	       accPppLinkReceive32BitFcs	INTEGER,
	       accPppLinkOperStatus		INTEGER,
	       accPppLinkPacketTooShorts	Counter,
	       accPppLinkUnknownProtocols	Counter,
	       accPppLinkPacketInDiscards	Counter,
	       accPppLinkPacketOutDiscards	Counter
               }
          accPppLinkIndex   OBJECT-TYPE
               SYNTAX    INTEGER
               ACCESS    read-only
               STATUS    mandatory
               DESCRIPTION
                         "Interface number"
               ::= { accPppLinkEntry 1 }
	  accPppLinkPhysicalIndex   OBJECT-TYPE
               SYNTAX    INTEGER
               ACCESS    read-only
               STATUS    mandatory
               DESCRIPTION
			 " "
               ::= { accPppLinkEntry 2 }
          accPppLinkBadAddresses   OBJECT-TYPE
               SYNTAX    Counter
               ACCESS    read-only
               STATUS    mandatory
               DESCRIPTION
                         "The number of packets received with an
                         incorrect Address Field. " 
               ::= { accPppLinkEntry 3 }
          accPppLinkBadControls   OBJECT-TYPE
               SYNTAX    Counter
               ACCESS    read-only
               STATUS    mandatory
               DESCRIPTION
                         "The number of packets received on this link
                         with an incorrect Control Field. "
               ::= { accPppLinkEntry 4 }
          accPppLinkPacketTooLongs   OBJECT-TYPE
               SYNTAX    Counter
               ACCESS    read-only
               STATUS    mandatory
               DESCRIPTION
                         "The number of received packets that have been
                         discarded because their length exceeded the MRU."
               ::= { accPppLinkEntry 5 }
          accPppLinkBadFCSs    OBJECT-TYPE
               SYNTAX    Counter
               ACCESS    read-only
               STATUS    mandatory
               DESCRIPTION
			 "The number of bad HDLC frames received."
               ::= { accPppLinkEntry 6 }
          accPppLinkLocalMRU    OBJECT-TYPE
               SYNTAX    INTEGER
               ACCESS    read-only
               STATUS    mandatory
               DESCRIPTION
                         "The final negotiated MRU value for the local
                         PPP Entity. This value is the MRU that the
                         remote entity has accepted for the local PPP
                         entity."
               ::= { accPppLinkEntry 7 }
          accPppLinkRemoteMRU    OBJECT-TYPE
               SYNTAX    INTEGER
               ACCESS    read-only
               STATUS    mandatory
               DESCRIPTION
                         "The final negotiated MRU value for the remote
                         PPP Entity."
               ::= { accPppLinkEntry 8 }
	  accPppLinkLocalToPeerACCMap	OBJECT-TYPE
               SYNTAX    OCTET STRING
               ACCESS    read-only
               STATUS    mandatory
               DESCRIPTION
                         "For future applications.  Unused in this 
                          release."
               ::= { accPppLinkEntry 9 }
	  accPppLinkPeerToLocalACCMap	OBJECT-TYPE
               SYNTAX    OCTET STRING
               ACCESS    read-only
               STATUS    mandatory
               DESCRIPTION
                         "For future applications.  Unused in this 
                          release."
               ::= { accPppLinkEntry 10 }
	  accPppLinkLocalToRemotePC	OBJECT-TYPE
               SYNTAX    INTEGER
               ACCESS    read-only
               STATUS    mandatory
               DESCRIPTION
                         "For future applications.  Unused in this 
                          release."
               ::= { accPppLinkEntry 11 }
	  accPppLinkRemoteToLocalPC	OBJECT-TYPE
               SYNTAX    INTEGER
               ACCESS    read-only
               STATUS    mandatory
               DESCRIPTION
                         "For future applications.  Unused in this 
                          release."
               ::= { accPppLinkEntry 12 }
	  accPppLinkLocalToRemoteAC	OBJECT-TYPE
               SYNTAX    INTEGER
               ACCESS    read-only
               STATUS    mandatory
               DESCRIPTION
                         "For future applications.  Unused in this 
                          release."
               ::= { accPppLinkEntry 13 }
	  accPppLinkRemoteToLocalAC	OBJECT-TYPE
               SYNTAX    INTEGER
               ACCESS    read-only
               STATUS    mandatory
               DESCRIPTION
                         "For future applications.  Unused in this 
                          release."
               ::= { accPppLinkEntry 14 }
	  accPppLinkTransmit32BitFcs	OBJECT-TYPE
               SYNTAX    INTEGER
               ACCESS    read-only
               STATUS    mandatory
               DESCRIPTION
                         "For future applications.  Unused in this 
                          release."
               ::= { accPppLinkEntry 15 }
	  accPppLinkReceive32BitFcs	OBJECT-TYPE
               SYNTAX    INTEGER
               ACCESS    read-only
               STATUS    mandatory
               DESCRIPTION
                         "For future applications.  Unused in this 
                          release."
               ::= { accPppLinkEntry 16 }
	  accPppLinkOperStatus	OBJECT-TYPE
               SYNTAX    INTEGER {
			initial(1),
			starting(2),
			closed(3),
			stopped(4),
			closing(5),
			stopping(6),
			req-sent(7),
			ack-rcvd(8),
			ack-sent(9),
			opened(10)
			}
               ACCESS    read-only
               STATUS    mandatory
               DESCRIPTION
                         ""
               ::= { accPppLinkEntry 17 }
	  accPppLinkPacketTooShorts	OBJECT-TYPE
               SYNTAX    Counter
               ACCESS    read-only
               STATUS    mandatory
               DESCRIPTION
                         ""
               ::= { accPppLinkEntry 18 }
	  accPppLinkUnknownProtocols	OBJECT-TYPE
               SYNTAX    Counter
               ACCESS    read-only
               STATUS    mandatory
               DESCRIPTION
                         ""
               ::= { accPppLinkEntry 19 }
	  accPppLinkPacketInDiscards	OBJECT-TYPE
               SYNTAX    Counter
               ACCESS    read-only
               STATUS    mandatory
               DESCRIPTION
                         ""
               ::= { accPppLinkEntry 20 }
	  accPppLinkPacketOutDiscards	OBJECT-TYPE
               SYNTAX    Counter
               ACCESS    read-only
               STATUS    mandatory
               DESCRIPTION
                         ""
               ::= { accPppLinkEntry 21 }
          accPppLcpConfigTable   OBJECT-TYPE
               SYNTAX    SEQUENCE OF AccPppLcpConfigEntry
               ACCESS    not-accessible
               STATUS    mandatory
               DESCRIPTION
                         "A table containing the LCP configuration
                         parameters for this PPP Link. These variables
                         represent the initial configuration of the PPP
                         Link. The actual values of the parameters may
                         be changed when the link is brought up via the
                         LCP options negotiation mechanism."
               ::= { accPpp 2 }
          accPppLcpConfigEntry   OBJECT-TYPE
               SYNTAX    AccPppLcpConfigEntry
               ACCESS    not-accessible
               STATUS    mandatory
               DESCRIPTION
                         "Configuration information about a particular
                         PPP Link."
               INDEX     { accPppLcpConfigIndex }
               ::= { accPppLcpConfigTable 1 }
          AccPppLcpConfigEntry ::= SEQUENCE {
               accPppLcpConfigIndex
                    INTEGER,
               accPppLcpConfigInitialMRU
                    INTEGER,
	       accPppLcpConfigReceiveACCMap
                    OCTET STRING,
	       accPppLinkConfigXmitACCMap
		    OCTET STRING,
               accPppLcpConfigMagicNumber
                    INTEGER,
               accPppLcpConfig32BitFCS
                    INTEGER,
	       accPppLcpRestartTimer
                    INTEGER,
	       accPppLcpMaxTerminate
                    INTEGER,
	       accPppLcpMaxConfigure
                    INTEGER,
	       accPppLcpMaxFailure
		    INTEGER,
   	       accPppLcpMonInterval
		    INTEGER,
   	       accPppLcpMonEvents
		    INTEGER,
   	       accPppLcpMonThreshold
		    INTEGER,
   	       accPppLcpAdminStatus
                    INTEGER,
		accPppLinkMsgLevel
		    INTEGER
               }
          accPppLcpConfigIndex   OBJECT-TYPE
               SYNTAX    INTEGER
               ACCESS    read-only
               STATUS    mandatory
               DESCRIPTION
                         "Interface number"
               ::= { accPppLcpConfigEntry 1 }
          accPppLcpConfigInitialMRU   OBJECT-TYPE
               SYNTAX    INTEGER
               ACCESS    read-only
               STATUS    mandatory
               DESCRIPTION
                         "The initial Maximum Receive Unit (MRU) that
                         the local PPP entity will advertise to the
                         remote entity. If the value of this variable is
                         0 then the local PPP entity will not advertise
                         any MRU to the remote entity and the default
                         MRU will be assumed. Changing this object will
                         have effect when the link is next restarted."
               DEFVAL    { 1500 }
               ::= { accPppLcpConfigEntry 2 }
	  accPppLcpConfigReceiveACCMap   OBJECT-TYPE
	       SYNTAX    OCTET STRING
               ACCESS    read-only
               STATUS    mandatory
               DESCRIPTION
                         "For future applications.  Unused in this 
                          release."
               ::= { accPppLcpConfigEntry 3 }
	  accPppLinkConfigXmitACCMap	OBJECT-TYPE
	       SYNTAX    OCTET STRING
               ACCESS    read-only
               STATUS    mandatory
               DESCRIPTION
                         "For future applications.  Unused in this 
                          release."
               ::= { accPppLcpConfigEntry 4 }
          accPppLcpConfigMagicNumber   OBJECT-TYPE
               SYNTAX    INTEGER { false (1), true (2) }
               ACCESS    read-only
               STATUS    mandatory
               DESCRIPTION
                         "If true(2) then the local node will attempt to
                         perform Magic Number negotiation with the
                         remote node. If false(1) then this negotiation
                         is not performed. In any event, the local node
                         will comply with any magic number negotiations
                         attempted by the remote node, per the PPP
                         specification. Changing this object will have
                         effect when the link is next restarted."
               DEFVAL    { false }
               ::= { accPppLcpConfigEntry 5 }
          accPppLcpConfig32BitFCS   OBJECT-TYPE
	       SYNTAX    INTEGER
               ACCESS    read-only
               STATUS    mandatory
               DESCRIPTION
                         " "
               ::= { accPppLcpConfigEntry 6 }
          accPppLcpRestartTimer   OBJECT-TYPE
               SYNTAX    INTEGER (1..3600)
               ACCESS    read-write
               STATUS    mandatory
               DESCRIPTION
                         " "
               DEFVAL    { 3 }
               ::= { accPppLcpConfigEntry 7 }
          accPppLcpMaxTerminate   OBJECT-TYPE
               SYNTAX    INTEGER (1..255)
               ACCESS    read-write
               STATUS    mandatory
               DESCRIPTION
                         " "
               DEFVAL    { 2 }
               ::= { accPppLcpConfigEntry 8 }
          accPppLcpMaxConfigure   OBJECT-TYPE
               SYNTAX    INTEGER (1..255)
               ACCESS    read-write
               STATUS    mandatory
               DESCRIPTION
                         " "
               DEFVAL    { 10 }
               ::= { accPppLcpConfigEntry 9 }
          accPppLcpMaxFailure   OBJECT-TYPE
               SYNTAX    INTEGER (1..255)
               ACCESS    read-write
               STATUS    mandatory
               DESCRIPTION
                         " "
               DEFVAL    { 10 }
               ::= { accPppLcpConfigEntry 10 }
   	  accPppLcpMonInterval	OBJECT-TYPE
               SYNTAX    INTEGER (0..3600)
               ACCESS    read-write
               STATUS    mandatory
               DESCRIPTION
                         " "
               DEFVAL    { 10 }
               ::= { accPppLcpConfigEntry 11 }
   	  accPppLcpMonEvents	OBJECT-TYPE
               SYNTAX    INTEGER (1..10)
               ACCESS    read-write
               STATUS    mandatory
               DESCRIPTION
                         " "
               DEFVAL    { 5 }
               ::= { accPppLcpConfigEntry 12 }
   	  accPppLcpMonThreshold	OBJECT-TYPE
               SYNTAX    INTEGER (1..10)
               ACCESS    read-write
               STATUS    mandatory
               DESCRIPTION
                         " "
               DEFVAL    { 3 }
               ::= { accPppLcpConfigEntry 13 }
   	  accPppLcpAdminStatus	OBJECT-TYPE
               SYNTAX   INTEGER {
		   	enabled(1),
		       	disabled(2)
			}
               ACCESS    read-write
               STATUS    mandatory
               DESCRIPTION
                         " "
               ::= { accPppLcpConfigEntry 14 }
        accPppLinkMsgLevel       OBJECT-TYPE
                 SYNTAX   INTEGER (1..7)
                 ACCESS  read-write
                 STATUS  mandatory
                 DESCRIPTION
                " PPP trap message level which may be set on a per
                  port basis. No traps with a severity level greater
                  the value set will be generated."
                ::= { accPppLcpConfigEntry 15 }
          accPppLqrTable   OBJECT-TYPE
               SYNTAX    SEQUENCE OF AccPppLqrEntry
               ACCESS    not-accessible
               STATUS    mandatory
               DESCRIPTION
                         "Table containing the LQR parameters and
                         statistics for the local PPP entity."
               ::= { accPpp 3 }
          accPppLqrEntry   OBJECT-TYPE
               SYNTAX    AccPppLqrEntry
               ACCESS    not-accessible
               STATUS    mandatory
               DESCRIPTION
                         "LQR information for a particular PPP link. A
                         PPP link will have an entry in this table if
                         and only if LQR Quality Monitoring has been
                         successfully negotiated for said link."
               INDEX     { accPppLqrIndex }
               ::= { accPppLqrTable 1 }
          AccPppLqrEntry ::= SEQUENCE {
               accPppLqrIndex
                    INTEGER,
               accPppLqrQuality
                    INTEGER,
               accPppLqrInGoodOctets
                    Counter,
               accPppLqrLocalPeriod
                    INTEGER,
               accPppLqrRemotePeriod
                    INTEGER,
               accPppLqrOutLQRs
                    Counter,
               accPppLqrInLQRs
                    Counter
          }
          accPppLqrIndex   OBJECT-TYPE
               SYNTAX    INTEGER 
               ACCESS    read-only
               STATUS    mandatory
               DESCRIPTION
                         "Interface number"
               ::= { accPppLqrEntry 1 }
          accPppLqrQuality   OBJECT-TYPE
               SYNTAX    INTEGER {
                         good(1),
                         bad(2)
                    }
               ACCESS    read-only
               STATUS    mandatory
               DESCRIPTION
                         "The current quality of the link as declared by
                         the local PPP entity's Link-Quality Management
                         modules. No effort is made to define good or
                         bad, nor the policy used to determine it."
               ::= { accPppLqrEntry 2 }
          accPppLqrInGoodOctets   OBJECT-TYPE
               SYNTAX    Counter
               ACCESS    read-only
               STATUS    mandatory
               DESCRIPTION
                         "The LQR InGoodOctets counter for this link."
               ::= { accPppLqrEntry 3 }
          accPppLqrLocalPeriod   OBJECT-TYPE
               SYNTAX    INTEGER
               ACCESS    read-only
               STATUS    mandatory
               DESCRIPTION
                         "The LQR reporting period that is in effect for
                         the local PPP entity. The local entity received
                         a configure-ack for this value from the remote
                         PPP entity."
               ::= { accPppLqrEntry 4 }
          accPppLqrRemotePeriod   OBJECT-TYPE
               SYNTAX    INTEGER
               ACCESS    read-only
               STATUS    mandatory
               DESCRIPTION
                         "The LQR reporting period that is in effect for
                         the remote PPP entity. The local entity sent a
                         configure-ack for this value in response to the
                         configure-req from the remote PPP entity."
               ::= { accPppLqrEntry 5 }
          accPppLqrOutLQRs   OBJECT-TYPE
               SYNTAX    Counter
               ACCESS    read-only
               STATUS    mandatory
               DESCRIPTION
                         "The value of the OutLQRs counter on the local
                         node for the link identified by
                         accPppLqrLinkIndex."
               ::= { accPppLqrEntry 6 }
          accPppLqrInLQRs   OBJECT-TYPE
               SYNTAX    Counter
               ACCESS    read-only
               STATUS    mandatory
               DESCRIPTION
                         "The value of the InLQRs counter on the local
                         node for the link identified by
                         accPppLqrLinkIndex."
               ::= { accPppLqrEntry 7 }
          accPppLqrConfigTable   OBJECT-TYPE
               SYNTAX    SEQUENCE OF AccPppLqrConfigEntry
               ACCESS    not-accessible
               STATUS    mandatory
               DESCRIPTION
                         "Table containing the LQR Configuration
                         parameters for the local PPP entity."
               ::= { accPpp 4 }
          accPppLqrConfigEntry   OBJECT-TYPE
               SYNTAX    AccPppLqrConfigEntry
               ACCESS    not-accessible
               STATUS    mandatory
               DESCRIPTION
                         "LQR configuration information for a particular
                         PPP link."
               INDEX     { accPppLqrConfigIndex }
               ::= { accPppLqrConfigTable 1 }
          AccPppLqrConfigEntry ::= SEQUENCE {
               accPppLqrConfigIndex
                    INTEGER,
               accPppLqrConfigPeriod
                    INTEGER,
               accPppLqrConfigStatus
                    INTEGER
          }
          accPppLqrConfigIndex   OBJECT-TYPE
               SYNTAX    INTEGER
               ACCESS    read-only
               STATUS    mandatory
               DESCRIPTION
                         "Interface number"
               ::= { accPppLqrConfigEntry 1 }
          accPppLqrConfigPeriod   OBJECT-TYPE
               SYNTAX    INTEGER(0..2147483648)
               ACCESS    read-write
               STATUS    mandatory
               DESCRIPTION
                         "The LQR Reporting Period that the local PPP
                         entity will attempt to negotiate with the
                         remote entity, in units of seconds. Changing
                         this object will have effect when the link is
                         next restarted."
               DEFVAL    { 10 }
               ::= { accPppLqrConfigEntry 2 }
          accPppLqrConfigStatus   OBJECT-TYPE
               SYNTAX    INTEGER { disabled (1), enabled (2) }
               ACCESS    read-write
               STATUS    mandatory
               DESCRIPTION
                         "If enabled(2) then the local node will attempt
                         to perform LQR negotiation with the remote
                         node. If disabled(1) then this negotiation is
                         not performed. In any event, the local node
                         will comply with any magic number negotiations
                         attempted by the remote node, per the PPP
                         specification. Changing this object will have
                         effect when the link is next restarted.
                         Setting this object to the value disabled(1)
                         has the effect of invalidating the
                         corresponding entry in the accPppLqrConfigTable
                         object. It is an implementation-specific matter
                         as to whether the agent removes an invalidated
                         entry from the table. Accordingly, management
                         stations must be prepared to receive tabular
                         information from agents that corresponds to
                         entries not currently in use."
               DEFVAL    { enabled }
               ::= { accPppLqrConfigEntry 3 }
          accPppIpcpTable   OBJECT-TYPE
               SYNTAX    SEQUENCE OF AccPppIpcpEntry
               ACCESS    not-accessible
               STATUS    mandatory
               DESCRIPTION
                         "Table containing the IPCP parameters and
                         statistics for the local PPP entity."
               ::= { accPpp 5 }
          accPppIpcpEntry   OBJECT-TYPE
               SYNTAX    AccPppIpcpEntry
               ACCESS    not-accessible
               STATUS    mandatory
               DESCRIPTION
                         "IPCP information for a particular PPP link. A
                         PPP link will have an entry in this table if
                         and only if running IP over the PPP link  has
                         been successfully negotiated for said link."
               INDEX     { accPppIpcpIndex }
               ::= { accPppIpcpTable 1 }
          AccPppIpcpEntry ::= SEQUENCE {
               accPppIpcpIndex
                    INTEGER,
               accPppIpcpLocalToRemoteCompressionProtocol
                    INTEGER,
               accPppIpcpRemoteToLocalCompressionProtocol
                    INTEGER,
               accPppIpcpRemoteMaxSlotId
                    INTEGER,
               accPppIpcpLocalMaxSlotId
                    INTEGER,
   	       accPppIpOperStatus
                    INTEGER
          }
          accPppIpcpIndex   OBJECT-TYPE
               SYNTAX    INTEGER
               ACCESS    read-only
               STATUS    mandatory
               DESCRIPTION
                         "Interface number"
               ::= { accPppIpcpEntry 1 }
          accPppIpcpLocalToRemoteCompressionProtocol   OBJECT-TYPE
               SYNTAX    INTEGER {
                         none(1),
                         vj-tcp(2)
                    }
               ACCESS    read-only
               STATUS    mandatory
               DESCRIPTION
                         "The IP compression protocol that the local
                         PPP-IP entity uses when sending packets to the
                         remote PPP-IP entity."
               ::= { accPppIpcpEntry 2 }
          accPppIpcpRemoteToLocalCompressionProtocol   OBJECT-TYPE
               SYNTAX    INTEGER {
                         none(1),
                         vj-tcp(2)
                    }
               ACCESS    read-only
               STATUS    mandatory
               DESCRIPTION
                         "The IP compression protocol that the remote
                         PPP-IP entity uses when sending packets to the
                         local PPP-IP entity."
               ::= { accPppIpcpEntry 3 }
          accPppIpcpRemoteMaxSlotId   OBJECT-TYPE
               SYNTAX    INTEGER (0..255)
               ACCESS    read-only
               STATUS    mandatory
               DESCRIPTION
                         "The Max-Slot-Id parameter that the remote node
                         has advertised and that is in use on the link."
               ::= { accPppIpcpEntry 4 }
          accPppIpcpLocalMaxSlotId   OBJECT-TYPE
               SYNTAX    INTEGER(0..255)
               ACCESS    read-only
               STATUS    mandatory
               DESCRIPTION
                         "The Max-Slot-Id parameter that the local node
                         has advertised and that is in use on the link."
               ::= { accPppIpcpEntry 5 }
          accPppIpOperStatus   OBJECT-TYPE
               SYNTAX    INTEGER {
			initial(1),
			starting(2),
			closed(3),
			stopped(4),
			closing(5),
			stopping(6),
			req-sent(7),
			ack-rcvd(8),
			ack-sent(9),
			opened(10)
			}
               ACCESS    read-only
               STATUS    mandatory
               DESCRIPTION
			" "
               ::= { accPppIpcpEntry 6 }
          accPppIpcpConfigTable   OBJECT-TYPE
               SYNTAX    SEQUENCE OF AccPppIpcpConfigEntry
               ACCESS    not-accessible
               STATUS    mandatory
               DESCRIPTION
                         "Table containing the IPCP parameters and
                         statistics for the local PPP entity."
               ::= { accPpp 6 }
          accPppIpcpConfigEntry   OBJECT-TYPE
               SYNTAX    AccPppIpcpConfigEntry
               ACCESS    not-accessible
               STATUS    mandatory
               DESCRIPTION
                         "IPCP information for a particular PPP link. A
                         PPP link will have an entry in this table if
                         and only if running IP over the PPP link  has
                         been successfully negotiated for said link."
               INDEX     { accPppIpcpConfigIndex }
               ::= { accPppIpcpConfigTable 1 }
          AccPppIpcpConfigEntry ::= SEQUENCE {
               accPppIpcpConfigIndex
                    INTEGER,
               accPppIpcpConfigCompression
                    INTEGER,
               accPppIpcpConfigStatus
                    INTEGER
          }
          accPppIpcpConfigIndex   OBJECT-TYPE
               SYNTAX    INTEGER
               ACCESS    read-only
               STATUS    mandatory
               DESCRIPTION
                         "The value of ifIndex that identifies the entry
                         in the ifTable that is associated with the
                         local IPCP entity."
               ::= { accPppIpcpConfigEntry 1 }
          accPppIpcpConfigCompression   OBJECT-TYPE
               SYNTAX    INTEGER {
                         none(1),
                         vj-tcp(2)
                    }
               ACCESS    read-write
               STATUS    mandatory
               DESCRIPTION
                         "If none(1) then the local node will not
                         attempt to negotiate any IP Compression option.
                         Otherwise, the local node will attempt to
                         negotiate compression mode indicated by the
                         enumerated value Changing this object will have
                         effect when the link is next restarted."
               DEFVAL    { none }
               ::= { accPppIpcpConfigEntry 2 }
          accPppIpcpConfigStatus   OBJECT-TYPE
               SYNTAX    INTEGER {
                         disabled(1),
                         enabled(2)
                    }
               ACCESS    read-write
               STATUS    mandatory
               DESCRIPTION
                         "If enabled(2) then the local node will allow
                         IP traffic to flow across the link. If
                         disabled(1) then IP traffic will not be allowed
                         to flow across the link.  Setting this object
                         to the value disabled(1) has the effect of
                         invalidating the corresponding entry in the
                         accPppIpcpConfigTable object. It is an
                         implementation-specific matter as to whether
                         the agent removes an invalidated entry from the
                         table. Accordingly, management stations must be
                         prepared to receive tabular information from
                         agents that corresponds to entries not
                         currently in use."
               DEFVAL    { enabled }
               ::= { accPppIpcpConfigEntry 3 }
          accPppBncpTable   OBJECT-TYPE
               SYNTAX    SEQUENCE OF AccPppBncpEntry
               ACCESS    not-accessible
               STATUS    mandatory
               DESCRIPTION
                         "Table containing the parameters and statistics
                         for the local PPP entity that are related to
                         the operation of Bridging over the PPP."
               ::= { accPpp 7 }
          accPppBncpEntry   OBJECT-TYPE
               SYNTAX    AccPppBncpEntry
               ACCESS    not-accessible
               STATUS    mandatory
               DESCRIPTION
                         "Bridging NCP information for a particular PPP
                         link. A PPP link will have an entry in this
                         table if and only if Bridging over PPP has been
                         successfully negotiated for said link."
               INDEX     { accPppBncpIndex }
               ::= { accPppBncpTable 1 }
          AccPppBncpEntry ::= SEQUENCE {
               accPppBncpIndex
                    INTEGER,
               accPppBncpLocalToRemoteTinygramCompression
                    INTEGER,
               accPppBncpRemoteToLocalTinygramCompression
                    INTEGER,
               accPppBncpLocalToRemoteLanId
                    INTEGER,
               accPppBncpRemoteToLocalLanId
                    INTEGER,
               accPppBncpOperStatus
                    INTEGER
          }
          accPppBncpIndex   OBJECT-TYPE
               SYNTAX    INTEGER
               ACCESS    read-only
               STATUS    mandatory
               DESCRIPTION
                         "Interface number"
               ::= { accPppBncpEntry 1 }
          accPppBncpLocalToRemoteTinygramCompression   OBJECT-TYPE
               SYNTAX    INTEGER { false(1), true(2) }
               ACCESS    read-only
               STATUS    mandatory
               DESCRIPTION
                         "Indicates whether the local node will perform
                         Tinygram Compression when sending packets to
                         the remote entity. If false then the local
                         entity will not perform Tinygram Compression.
                         If true then the local entity will perform
                         Tinygram Compression."
               ::= { accPppBncpEntry 2 }
          accPppBncpRemoteToLocalTinygramCompression   OBJECT-TYPE
               SYNTAX    INTEGER { false(1), true(2) }
               ACCESS    read-only
               STATUS    mandatory
               DESCRIPTION
                         "Indicates what the local node believes to be
                         the remote node will perform Tinygram
                         Compression when sending packets to the local
                         node. If false then the remote entity is not
                         expected to perform Tinygram Compression. If
                         true then the remote entity is expected to
                         perform Tinygram Compression."
               ::= { accPppBncpEntry 3 }
          accPppBncpLocalToRemoteLanId   OBJECT-TYPE
               SYNTAX    INTEGER { false(1), true(2) }
               ACCESS    read-only
               STATUS    mandatory
               DESCRIPTION
                         "Indicates whether the local node will include
                         the LAN Identification field in transmitted
                         packets or not. If false(1) then the local node
                         will not transmit this field, true(2) means
                         that the field will be transmitted."
               ::= { accPppBncpEntry 4 }
          accPppBncpRemoteToLocalLanId   OBJECT-TYPE
               SYNTAX    INTEGER { false(1), true(2) }
               ACCESS    read-only
               STATUS    mandatory
               DESCRIPTION
                         "Indicates whether the remote node has
                         indicated that it will include the LAN
                         Identification field in transmitted packets or
                         not. If false(1) then the field will not be
                         transmitted, if true(2) then the field will be
                         transmitted."
               ::= { accPppBncpEntry 5 }
          accPppBncpOperStatus   OBJECT-TYPE
               SYNTAX    INTEGER {
                             initial (1),
                             starting (2),
                             closed (3),
                             stopped (4),
                             closing (5),
                             stopping (6),
                             req-sent (7),
                             ack-rcvd (8),
                             ack-sent (9),
                             opened (10)
                         }
               ACCESS    read-only
               STATUS    mandatory
               DESCRIPTION
                         "Operational status of the PPP link for this 
                          interface."
               ::= { accPppBncpEntry 6 }
          accPppBncpConfigTable   OBJECT-TYPE
               SYNTAX    SEQUENCE OF AccPppBncpConfigEntry
               ACCESS    not-accessible
               STATUS    mandatory
               DESCRIPTION
                         "Table containing the parameters and statistics
                         for the local PPP entity that are related to
                         the operation of Bridging over the PPP."
               ::= { accPpp 8 }
          accPppBncpConfigEntry   OBJECT-TYPE
               SYNTAX    AccPppBncpConfigEntry
               ACCESS    not-accessible
               STATUS    mandatory
               DESCRIPTION
                         "Bridging NCP information for a particular PPP
                         link. A PPP link will have an entry in this
                         table if and only if Bridging over PPP has been
                         successfully negotiated for said link."
               INDEX     { accPppBncpConfigIndex }
               ::= { accPppBncpConfigTable 1 }
          AccPppBncpConfigEntry ::= SEQUENCE {
               accPppBncpConfigIndex
                    INTEGER,
               accPppBncpConfigTinygram
                    INTEGER,
               accPppBncpConfigRingId
                    INTEGER,
               accPppBncpConfigLineId
                    INTEGER,
               accPppBncpConfigLanId
                    INTEGER,
   	       accPppBncpConfigAdminStatus
                    INTEGER
          }
          accPppBncpConfigIndex   OBJECT-TYPE
               SYNTAX    INTEGER
               ACCESS    read-only
               STATUS    mandatory
               DESCRIPTION
                         "The value of ifIndex that identifies the entry
                         in the interface table that is associated with
                         the local PPP Bridging NCP entity."
               ::= { accPppBncpConfigEntry 1 }
          accPppBncpConfigTinygram   OBJECT-TYPE
               SYNTAX    INTEGER { false(1), true(2) }
               ACCESS    read-write
               STATUS    mandatory
               DESCRIPTION
                         "If false then the local BNCP entity will not
                         initiate the Tinygram Compression Option
                         Negotiation. If true then the local BNCP entity
                         will initiate negotiation of this option."
               DEFVAL    { true }
               ::= { accPppBncpConfigEntry 2 }
          accPppBncpConfigRingId   OBJECT-TYPE
               SYNTAX    INTEGER { false(1), true(2) }
               ACCESS    read-write
               STATUS    mandatory
               DESCRIPTION
                         "If false then the local PPP Entity will not
                         initiate a Remote Ring Identification Option
                         negotiation. If true then the local PPP entity
                         will intiate this negotiation. This MIB object
                         is relevant only if the interface is for 802.5
                         Token Ring bridging."
               DEFVAL    { false }
               ::= { accPppBncpConfigEntry 3 }
          accPppBncpConfigLineId   OBJECT-TYPE
               SYNTAX    INTEGER { false(1), true(2) }
               ACCESS    read-write
               STATUS    mandatory
               DESCRIPTION
                         "If false then the local PPP Entity is not to
                         initiate a Line Identification Option
                         negotiation. If true then the local PPP entity
                         will intiate this negotiation. This MIB object
                         is relevant only if the interface is for 802.5
                         Token Ring bridging."
               DEFVAL    { false }
               ::= { accPppBncpConfigEntry 4 }
          accPppBncpConfigLanId   OBJECT-TYPE
               SYNTAX    INTEGER { false(1), true(2) }
               ACCESS    read-write
               STATUS    mandatory
               DESCRIPTION
                         "If false then the local BNCP entity will not
                         initiate the LAN Identification Option
                         Negotiation. If true then the local BNCP entity
                         will initiate negotiation of this option."
               DEFVAL    { false }
               ::= { accPppBncpConfigEntry 5 }
   	  accPppBncpConfigAdminStatus OBJECT-TYPE
               SYNTAX    INTEGER {
                         disabled(1),
                         enabled(2)
                    }
               ACCESS    read-write
               STATUS    mandatory
               DESCRIPTION
			" "
               ::= { accPppBncpConfigEntry 6 }
          accPppXnsTable   OBJECT-TYPE
               SYNTAX    SEQUENCE OF AccPppXnsEntry
               ACCESS    not-accessible
               STATUS    mandatory
               DESCRIPTION
                         " "
               ::= { accPpp 9 }
          accPppXnsEntry   OBJECT-TYPE
               SYNTAX    AccPppXnsEntry
               ACCESS    not-accessible
               STATUS    mandatory
               DESCRIPTION
                         " "
               INDEX     { accPppXnsIndex }
               ::= { accPppXnsTable 1 }
          AccPppXnsEntry ::= SEQUENCE {
		accPppXnsIndex
                    INTEGER,
		accPppXnsOperStatus
                    INTEGER
          }
          accPppXnsIndex   OBJECT-TYPE
               SYNTAX    INTEGER
               ACCESS    read-only
               STATUS    mandatory
               DESCRIPTION
			"Same as ifIndex."
               ::= { accPppXnsEntry 1 }
          accPppXnsOperStatus   OBJECT-TYPE
               SYNTAX    INTEGER {
			initial(1),
			starting(2),
			closed(3),
			stopped(4),
			closing(5),
			stopping(6),
			req-sent(7),
			ack-rcvd(8),
			ack-sent(9),
			opened(10)
			}
               ACCESS    read-only
               STATUS    mandatory
               DESCRIPTION
			" "
               ::= { accPppXnsEntry 2 }
          accPppXnsConfigTable   OBJECT-TYPE
               SYNTAX    SEQUENCE OF AccPppXnsConfigEntry
               ACCESS    not-accessible
               STATUS    mandatory
               DESCRIPTION
                         " "
               ::= { accPpp 10 }
          accPppXnsConfigEntry   OBJECT-TYPE
               SYNTAX    AccPppXnsConfigEntry
               ACCESS    not-accessible
               STATUS    mandatory
               DESCRIPTION
                         " "
               INDEX     { accPppXnsConfigIndex }
               ::= { accPppXnsConfigTable 1 }
          AccPppXnsConfigEntry ::= SEQUENCE {
		accPppXnsConfigIndex
                    INTEGER,
		accPppXnsConfigAdminStatus
                    INTEGER
          }
          accPppXnsConfigIndex   OBJECT-TYPE
               SYNTAX    INTEGER
               ACCESS    read-only
               STATUS    mandatory
               DESCRIPTION
			"Same as ifIndex."
               ::= { accPppXnsConfigEntry 1 }
          accPppXnsConfigAdminStatus   OBJECT-TYPE
               SYNTAX    INTEGER {
                         disabled(1),
                         enabled(2)
                    }
               ACCESS    read-write
               STATUS    mandatory
               DESCRIPTION
			" "
               ::= { accPppXnsConfigEntry 3 }
          accPppIpxTable   OBJECT-TYPE
               SYNTAX    SEQUENCE OF AccPppIpxEntry
               ACCESS    not-accessible
               STATUS    mandatory
               DESCRIPTION
                         " "
               ::= { accPpp 11 }
          accPppIpxEntry   OBJECT-TYPE
               SYNTAX    AccPppIpxEntry
               ACCESS    not-accessible
               STATUS    mandatory
               DESCRIPTION
                         " "
               INDEX     { accPppIpxIndex }
               ::= { accPppIpxTable 1 }
          AccPppIpxEntry ::= SEQUENCE {
		accPppIpxIndex
                    INTEGER,
		accPppIpxOperStatus
                    INTEGER
          }
          accPppIpxIndex   OBJECT-TYPE
               SYNTAX    INTEGER
               ACCESS    read-only
               STATUS    mandatory
               DESCRIPTION
			"Same as ifIndex."
               ::= { accPppIpxEntry 1 }
          accPppIpxOperStatus   OBJECT-TYPE
               SYNTAX    INTEGER {
			initial(1),
			starting(2),
			closed(3),
			stopped(4),
			closing(5),
			stopping(6),
			req-sent(7),
			ack-rcvd(8),
			ack-sent(9),
			opened(10)
			}
               ACCESS    read-only
               STATUS    mandatory
               DESCRIPTION
			" "
               ::= { accPppIpxEntry 2 }
          accPppIpxConfigTable   OBJECT-TYPE
               SYNTAX    SEQUENCE OF AccPppIpxConfigEntry
               ACCESS    not-accessible
               STATUS    mandatory
               DESCRIPTION
                         " "
               ::= { accPpp 12 }
          accPppIpxConfigEntry   OBJECT-TYPE
               SYNTAX    AccPppIpxConfigEntry
               ACCESS    not-accessible
               STATUS    mandatory
               DESCRIPTION
                         " "
               INDEX     { accPppIpxConfigIndex }
               ::= { accPppIpxConfigTable 1 }
          AccPppIpxConfigEntry ::= SEQUENCE {
		accPppIpxConfigIndex
                    INTEGER,
		accPppIpxConfigAdminStatus
                    INTEGER
          }
          accPppIpxConfigIndex   OBJECT-TYPE
               SYNTAX    INTEGER
               ACCESS    read-only
               STATUS    mandatory
               DESCRIPTION
			"Same as ifIndex."
               ::= { accPppIpxConfigEntry 1 }
          accPppIpxConfigAdminStatus   OBJECT-TYPE
               SYNTAX    INTEGER {
                         disabled(1),
                         enabled(2)
                    }
               ACCESS    read-write
               STATUS    mandatory
               DESCRIPTION
			" "
               ::= { accPppIpxConfigEntry 3 }
          accPppAppleTable   OBJECT-TYPE
               SYNTAX    SEQUENCE OF AccPppAppleEntry
               ACCESS    not-accessible
               STATUS    mandatory
               DESCRIPTION
                         " "
               ::= { accPpp 13 }
          accPppAppleEntry   OBJECT-TYPE
               SYNTAX    AccPppAppleEntry
               ACCESS    not-accessible
               STATUS    mandatory
               DESCRIPTION
                         " "
               INDEX     { accPppAppleIndex }
               ::= { accPppAppleTable 1 }
          AccPppAppleEntry ::= SEQUENCE {
		accPppAppleIndex
                    INTEGER,
		accPppAppleOperStatus
                    INTEGER
          }
          accPppAppleIndex   OBJECT-TYPE
               SYNTAX    INTEGER
               ACCESS    read-only
               STATUS    mandatory
               DESCRIPTION
			"Same as ifIndex."
               ::= { accPppAppleEntry 1 }
          accPppAppleOperStatus   OBJECT-TYPE
               SYNTAX    INTEGER {
			initial(1),
			starting(2),
			closed(3),
			stopped(4),
			closing(5),
			stopping(6),
			req-sent(7),
			ack-rcvd(8),
			ack-sent(9),
			opened(10)
			}
               ACCESS    read-only
               STATUS    mandatory
               DESCRIPTION
			" "
               ::= { accPppAppleEntry 2 }
          accPppAppleConfigTable   OBJECT-TYPE
               SYNTAX    SEQUENCE OF AccPppAppleConfigEntry
               ACCESS    not-accessible
               STATUS    mandatory
               DESCRIPTION
                         " "
               ::= { accPpp 14 }
          accPppAppleConfigEntry   OBJECT-TYPE
               SYNTAX    AccPppAppleConfigEntry
               ACCESS    not-accessible
               STATUS    mandatory
               DESCRIPTION
                         " "
               INDEX     { accPppAppleConfigIndex }
               ::= { accPppAppleConfigTable 1 }
          AccPppAppleConfigEntry ::= SEQUENCE {
		accPppAppleConfigIndex
                    INTEGER,
		accPppAppleConfigAdminStatus
                    INTEGER
          }
          accPppAppleConfigIndex   OBJECT-TYPE
               SYNTAX    INTEGER
               ACCESS    read-only
               STATUS    mandatory
               DESCRIPTION
			"Same as ifIndex."
               ::= { accPppAppleConfigEntry 1 }
          accPppAppleConfigAdminStatus   OBJECT-TYPE
               SYNTAX    INTEGER {
                         disabled(1),
                         enabled(2)
                    }
               ACCESS    read-write
               STATUS    mandatory
               DESCRIPTION
			" "
               ::= { accPppAppleConfigEntry 3 }
          accPppDecTable   OBJECT-TYPE
               SYNTAX    SEQUENCE OF AccPppDecEntry
               ACCESS    not-accessible
               STATUS    mandatory
               DESCRIPTION
                         " "
               ::= { accPpp 15 }
          accPppDecEntry   OBJECT-TYPE
               SYNTAX    AccPppDecEntry
               ACCESS    not-accessible
               STATUS    mandatory
               DESCRIPTION
                         " "
               INDEX     { accPppDecIndex }
               ::= { accPppDecTable 1 }
          AccPppDecEntry ::= SEQUENCE {
		accPppDecIndex
                    INTEGER,
		accPppDecOperStatus
                    INTEGER
          }
          accPppDecIndex   OBJECT-TYPE
               SYNTAX    INTEGER
               ACCESS    read-only
               STATUS    mandatory
               DESCRIPTION
			"Same as ifIndex."
               ::= { accPppDecEntry 1 }
          accPppDecOperStatus   OBJECT-TYPE
               SYNTAX    INTEGER {
			initial(1),
			starting(2),
			closed(3),
			stopped(4),
			closing(5),
			stopping(6),
			req-sent(7),
			ack-rcvd(8),
			ack-sent(9),
			opened(10)
			}
               ACCESS    read-only
               STATUS    mandatory
               DESCRIPTION
			" "
               ::= { accPppDecEntry 2 }
          accPppDecConfigTable   OBJECT-TYPE
               SYNTAX    SEQUENCE OF AccPppDecConfigEntry
               ACCESS    not-accessible
               STATUS    mandatory
               DESCRIPTION
                         " "
               ::= { accPpp 16 }
          accPppDecConfigEntry   OBJECT-TYPE
               SYNTAX    AccPppDecConfigEntry
               ACCESS    not-accessible
               STATUS    mandatory
               DESCRIPTION
                         " "
               INDEX     { accPppDecConfigIndex }
               ::= { accPppDecConfigTable 1 }
          AccPppDecConfigEntry ::= SEQUENCE {
		accPppDecConfigIndex
                    INTEGER,
		accPppDecConfigAdminStatus
                    INTEGER
          }
          accPppDecConfigIndex   OBJECT-TYPE
               SYNTAX    INTEGER
               ACCESS    read-only
               STATUS    mandatory
               DESCRIPTION
			"Same as ifIndex."
               ::= { accPppDecConfigEntry 1 }
          accPppDecConfigAdminStatus   OBJECT-TYPE
               SYNTAX    INTEGER {
                         disabled(1),
                         enabled(2)
                    }
               ACCESS    read-write
               STATUS    mandatory
               DESCRIPTION
			" "
               ::= { accPppDecConfigEntry 3 }
          accPppProtocolTable   OBJECT-TYPE
               SYNTAX    SEQUENCE OF AccPppProtocolEntry
               ACCESS    not-accessible
               STATUS    mandatory
               DESCRIPTION
                         " "
               ::= { accPpp 17 }
          accPppProtocolEntry   OBJECT-TYPE
               SYNTAX    AccPppProtocolEntry
               ACCESS    not-accessible
               STATUS    mandatory
               DESCRIPTION
                         " "
               INDEX     { accPppProtocolIndex }
               ::= { accPppProtocolTable 1 }
          AccPppProtocolEntry ::= SEQUENCE {
		accPppProtocolIndex
                    INTEGER,
		accPppProtocolProtocol
                    INTEGER,
		accPppProtocolAdminStatus
                    INTEGER,
		accPppProtocolOperStatus
                    INTEGER
          }
          accPppProtocolIndex   OBJECT-TYPE
               SYNTAX    INTEGER
               ACCESS    read-only
               STATUS    mandatory
               DESCRIPTION
			" "
               ::= { accPppProtocolEntry 1 }
          accPppProtocolProtocol   OBJECT-TYPE
               SYNTAX    INTEGER {
		        ip(33),
		        osi(35),
		        idp(37),
		        decnet(39),
		        appletalk(41),
		        ipx(43),
		        bridge(49),
		        vines(53),
		        multilink(61),
			illcp(251),	
		        ccp(253)
			}
               ACCESS    read-only
               STATUS    mandatory
               DESCRIPTION
			" "
               ::= { accPppProtocolEntry 2 }
          accPppProtocolAdminStatus   OBJECT-TYPE
               SYNTAX    INTEGER {
                         enabled(1),
                         disabled(2)
                    }
               ACCESS    read-only
               STATUS    mandatory
               DESCRIPTION
			" "
               ::= { accPppProtocolEntry 3 }
          accPppProtocolOperStatus   OBJECT-TYPE
               SYNTAX    INTEGER {
			initial(1),
			starting(2),
			closed(3),
			stopped(4),
			closing(5),
			stopping(6),
			req-sent(7),
			ack-rcvd(8),
			ack-sent(9),
			opened(10)
			}
               ACCESS    read-only
               STATUS    mandatory
               DESCRIPTION
			" "
               ::= { accPppProtocolEntry 4 }
          accPppMsg   OBJECT IDENTIFIER ::= { accPpp 18 }
          accPppMsgLevel   OBJECT-TYPE
               SYNTAX    INTEGER (1..7)
               ACCESS    read-write
               STATUS    mandatory
               DESCRIPTION
			" "
               ::= { accPppMsg 1 }
          accPppAuthStatTable   OBJECT-TYPE
               SYNTAX    SEQUENCE OF AccPppAuthStatEntry
               ACCESS    not-accessible
               STATUS    mandatory
               DESCRIPTION
                         "A table containing PPP authentication specific
                          variables for this PPP implementation."
               ::= { accPpp 19 }
          accPppAuthStatEntry   OBJECT-TYPE
               SYNTAX    AccPppAuthStatEntry
               ACCESS    not-accessible
               STATUS    mandatory
               DESCRIPTION
                         "Management information about a authentication
                          of a particular PPP Link."
               INDEX     { accPppAuthStatIndex }
               ::= { accPppAuthStatTable 1 }
        AccPppAuthStatEntry ::= SEQUENCE {
               	accPppAuthStatIndex              INTEGER,
               	accPppAuthStatPapReqSents           Counter,
               	accPppAuthStatPapReqRcvs            Counter,
               	accPppAuthStatPapAckSents        Counter,
             	accPppAuthStatPapAckRcvs           Counter,
             	accPppAuthStatPapNakSents          Counter,
             	accPppAuthStatPapNakRcvs           Counter,
             	accPppAuthStatPapRetryTimeouts    Counter,
             	accPppAuthStatChapChallengeSents  Counter,
             	accPppAuthStatChapChallengeRcvs   Counter,
             	accPppAuthStatChapResponseSents   Counter,
             	accPppAuthStatChapResponseRcvs    Counter,
               	accPppAuthStatChapAckSents        Counter,
             	accPppAuthStatChapAckRcvs         Counter,
             	accPppAuthStatChapNakSents         Counter,
             	accPppAuthStatChapNakRcvs          Counter,
             	accPppAuthStatChapResponseTimeouts  Counter,
             	accPppAuthStatChapChallengeTimeouts Counter,
             	accPppAuthStatChapAckNakTimeouts    Counter,
             	accPppAuthStatLastNegoOptions      INTEGER,
             	accPppAuthStatOutgoingCallMisMatchs Counter
             }
          accPppAuthStatIndex   OBJECT-TYPE
               SYNTAX    INTEGER
               ACCESS    read-only
               STATUS    mandatory
               DESCRIPTION
                         "Interface number"
               ::= { accPppAuthStatEntry 1 }
          accPppAuthStatPapReqSents   OBJECT-TYPE
               SYNTAX    Counter
               ACCESS    read-only
               STATUS    mandatory
               DESCRIPTION
                         "The number of times a PAP request sent."
               ::= { accPppAuthStatEntry 2 }
          accPppAuthStatPapReqRcvs   OBJECT-TYPE
               SYNTAX    Counter
               ACCESS    read-only
               STATUS    mandatory
               DESCRIPTION
                         "The number of times a PAP request received"
               ::= { accPppAuthStatEntry 3 }
          accPppAuthStatPapAckSents OBJECT-TYPE
               SYNTAX    Counter
               ACCESS    read-only
               STATUS    mandatory
               DESCRIPTION
                         "The number of times a PAP Ack sent"
               ::= { accPppAuthStatEntry 4 }
        accPppAuthStatPapAckRcvs  OBJECT-TYPE
               SYNTAX    Counter
               ACCESS    read-only
               STATUS    mandatory
               DESCRIPTION
                         "The number of times a PAP Ack Received"
               ::= { accPppAuthStatEntry 5 }
         accPppAuthStatPapNakSents  OBJECT-TYPE
               SYNTAX    Counter
               ACCESS    read-only
               STATUS    mandatory
               DESCRIPTION
                         "The number of times a PAP Nak sent."
               ::= { accPppAuthStatEntry 6 }
         accPppAuthStatPapNakRcvs  OBJECT-TYPE
               SYNTAX    Counter
               ACCESS    read-only
               STATUS    mandatory
               DESCRIPTION
                         "The number of times a PAP Nak received."
               ::= { accPppAuthStatEntry 7 }
         accPppAuthStatPapRetryTimeouts  OBJECT-TYPE
               SYNTAX    Counter
               ACCESS    read-only
               STATUS    mandatory
               DESCRIPTION
                         "The number of times a PAP retry timeout."
               ::= { accPppAuthStatEntry 8 }
         accPppAuthStatChapChallengeSents  OBJECT-TYPE
               SYNTAX    Counter
               ACCESS    read-only
               STATUS    mandatory
               DESCRIPTION
                         "The number of times a Challenge sent."
               ::= { accPppAuthStatEntry 9 }
         accPppAuthStatChapChallengeRcvs OBJECT-TYPE
               SYNTAX    Counter
               ACCESS    read-only
               STATUS    mandatory
               DESCRIPTION
                         "The number of times a challenge received."
               ::= { accPppAuthStatEntry 10 }
         accPppAuthStatChapResponseSents  OBJECT-TYPE
               SYNTAX    Counter
               ACCESS    read-only
               STATUS    mandatory
               DESCRIPTION
                         "The number of times a CHAP response sent."
               ::= { accPppAuthStatEntry 11 }
         accPppAuthStatChapResponseRcvs  OBJECT-TYPE
               SYNTAX    Counter
               ACCESS    read-only
               STATUS    mandatory
               DESCRIPTION
                         "The number of times a CHAP response  received."
               ::= { accPppAuthStatEntry 12 }
         accPppAuthStatChapAckSents  OBJECT-TYPE
               SYNTAX    Counter
               ACCESS    read-only
               STATUS    mandatory
               DESCRIPTION
                         "The number of times a CHAP ACK sent."
               ::= { accPppAuthStatEntry 13 }
         accPppAuthStatChapAckRcvs OBJECT-TYPE
               SYNTAX    Counter
               ACCESS    read-only
               STATUS    mandatory
               DESCRIPTION
                         "The number of times a CHAP ACK received."
               ::= { accPppAuthStatEntry 14 }
         accPppAuthStatChapNakSents  OBJECT-TYPE
               SYNTAX    Counter
               ACCESS    read-only
               STATUS    mandatory
               DESCRIPTION
                         "The number of times a CHAP NAK sent."
               ::= { accPppAuthStatEntry 15 }
         accPppAuthStatChapNakRcvs  OBJECT-TYPE
               SYNTAX    Counter
               ACCESS    read-only
               STATUS    mandatory
               DESCRIPTION
                         "The number of times a CHAP NAK received."
               ::= { accPppAuthStatEntry 16 }
         accPppAuthStatChapResponseTimeouts  OBJECT-TYPE
               SYNTAX    Counter
               ACCESS    read-only
               STATUS    mandatory
               DESCRIPTION
                         "The number of times a waiting CHAP response
timeout."
               ::= { accPppAuthStatEntry 17 }
         accPppAuthStatChapChallengeTimeouts  OBJECT-TYPE
               SYNTAX    Counter
               ACCESS    read-only
               STATUS    mandatory
               DESCRIPTION
                         "The number of times a waiting CHAP challenge
timeout."
               ::= { accPppAuthStatEntry 18 }
         accPppAuthStatChapAckNakTimeouts  OBJECT-TYPE
               SYNTAX    Counter
               ACCESS    read-only
               STATUS    mandatory
               DESCRIPTION
                         "The number of times a waiting CHAP ACK/NAK
timeout."
               ::= { accPppAuthStatEntry 19 }
         accPppAuthStatLastNegoOptions OBJECT-TYPE
               SYNTAX    INTEGER
               ACCESS    read-only
               STATUS    mandatory
               DESCRIPTION
                         "The most recent authentication method is
negotiated"
               ::= { accPppAuthStatEntry 20 }
          accPppAuthStatOutgoingCallMisMatchs  OBJECT-TYPE
               SYNTAX    Counter
               ACCESS    read-only
               STATUS    mandatory
               DESCRIPTION
                         "The number of times an outgoing call dial port
        authentication method is differnet than PAP
authentication negotiated in PPP"
               ::= { accPppAuthStatEntry 21 }
-- PPP Authentication parameter table
accPppAuthParmTable OBJECT-TYPE
        SYNTAX SEQUENCE OF AccPppAuthParmEntry
        ACCESS not-accessible
        STATUS mandatory
        DESCRIPTION
                "PPP Authentication Parameter Table"
      ::= { accPpp 20 }
accPppAuthParmEntry OBJECT-TYPE
        SYNTAX AccPppAuthParmEntry
        ACCESS not-accessible
        STATUS mandatory
        DESCRIPTION
                "PPP Authentication Parameter Table Entry"
        INDEX { accMlPppIndex }
      ::= { accPppAuthParmTable 1 }
AccPppAuthParmEntry ::= SEQUENCE {
        accPppAuthParmIndex            INTEGER,
        accPppAuthParmUserNameIn         DisplayString,
        accPppAuthParmPasswordIn      DisplayString,
        accPppAuthParmMethodIn       INTEGER,
        accPppAuthParmUserNameOut       DisplayString,
        accPppAuthParmPasswordOut       DisplayString,
        accPppAuthParmMethodOut       INTEGER,
        accPppAuthParmRetryInterval       TimeTicks,
        accPppAuthParmRetryCount       INTEGER,
        accPppAuthParmAcctOption       INTEGER
        }
accPppAuthParmIndex OBJECT-TYPE
        SYNTAX INTEGER
        ACCESS read-only
        STATUS mandatory
        DESCRIPTION
            "The ifIndex of the PPP physical port"
      ::= { accPppAuthParmEntry 1 }
accPppAuthParmUserNameIn OBJECT-TYPE
        SYNTAX DisplayString -- (SIZE(0..32))
        ACCESS read-write
        STATUS mandatory
        DESCRIPTION
            "incoming (remote) user name"
      ::= { accPppAuthParmEntry 2 }
accPppAuthParmPasswordIn OBJECT-TYPE
        SYNTAX DisplayString -- (SIZE(0..16))
        ACCESS read-write
        STATUS mandatory
        DESCRIPTION
             "incoming (remote) password or secret"
      ::= { accPppAuthParmEntry 3 }
accPppAuthParmMethodIn OBJECT-TYPE
        SYNTAX INTEGER {
                none(1),
                pap(2),
                chap(3),
                chap-or-pap(4)
               }
        ACCESS read-write
        STATUS mandatory
        DESCRIPTION
            "incoming authentication method"
      ::= { accPppAuthParmEntry 4 }
accPppAuthParmUserNameOut OBJECT-TYPE
        SYNTAX DisplayString -- (SIZE(0..32))
        ACCESS read-write
        STATUS mandatory
        DESCRIPTION
            "outgoing (local) user name"
      ::= { accPppAuthParmEntry 5 }
accPppAuthParmPasswordOut OBJECT-TYPE
        SYNTAX DisplayString -- (SIZE(0..16))
        ACCESS read-write
        STATUS mandatory
        DESCRIPTION
            "outgoing (local) password or secret"
      ::= { accPppAuthParmEntry 6 }
accPppAuthParmMethodOut OBJECT-TYPE
        SYNTAX INTEGER {
                none(1),
                pap(2),
                chap(3),
                chap-or-pap(4)
               }
        ACCESS read-write
        STATUS mandatory
        DESCRIPTION
             "outgoing authentication method"
      ::= { accPppAuthParmEntry 7 }
accPppAuthParmRetryInterval OBJECT-TYPE
        SYNTAX TimeTicks
        ACCESS read-write
        STATUS mandatory
        DESCRIPTION
             "authentication retry interval"
      ::= { accPppAuthParmEntry 8 }
accPppAuthParmRetryCount OBJECT-TYPE
        SYNTAX INTEGER (1..10)
        ACCESS read-write
        STATUS mandatory
        DESCRIPTION
             "authentication retry count"
      ::= { accPppAuthParmEntry 9 }
accPppAuthParmAcctOption OBJECT-TYPE
        SYNTAX INTEGER {
                on (1),
                off (2)
               }
        ACCESS read-write
        STATUS mandatory
        DESCRIPTION
            "accounting administrative status (if on, account is
             performed for this link"
      ::= { accPppAuthParmEntry 10 }
accIpHeaderCompStatTable OBJECT-TYPE
        SYNTAX SEQUENCE OF AccIpHeaderCompStatEntry
        ACCESS not-accessible
        STATUS mandatory
        DESCRIPTION
                "IP Header Compression Statistics Table"
      ::= { accPpp 23 }
accIpHeaderCompStatEntry OBJECT-TYPE
        SYNTAX AccIpHeaderCompStatEntry
        ACCESS not-accessible
        STATUS mandatory
        DESCRIPTION
                "IP Header Compression Statistics Entry"
        INDEX { accPppLinkVjhcStatIndex }
      ::= { accIpHeaderCompStatTable 1 }
AccIpHeaderCompStatEntry ::= SEQUENCE {
        accPppLinkVjhcStatIndex         INTEGER,
        accPppLinkVjhcOper              INTEGER,
        accPppLinkVjhcNegot             INTEGER,
        accPppLinkVjhcCompIn            INTEGER,
        accPppLinkVjhcUnCompIn          INTEGER,
        accPppLinkVjhcErrIn             INTEGER,
        accPppLinkVjhcCompOut           INTEGER,
        accPppLinkVjhcUnCompOut         INTEGER,
        accPppLinkVjhcErrOut            INTEGER
        }
accPppLinkVjhcStatIndex OBJECT-TYPE
        SYNTAX INTEGER
        ACCESS read-only
        STATUS mandatory
        DESCRIPTION
            "The ifIndex of the PPP physical port"
      ::= { accIpHeaderCompStatEntry 1 }
accPppLinkVjhcOper OBJECT-TYPE
        SYNTAX INTEGER {
                disabled(1),
                enabled(2)
	}
        ACCESS read-only
        STATUS mandatory
        DESCRIPTION
            "The VJ header Comp State  of the PPP physical port"
      ::= { accIpHeaderCompStatEntry 2 }
accPppLinkVjhcNegot OBJECT-TYPE
        SYNTAX INTEGER {
                notApp(1),
                failed(2),
                success(3)
        }
        ACCESS read-only
        STATUS mandatory
        DESCRIPTION
            "The VJ header Comp Negotiation Status"
      ::= { accIpHeaderCompStatEntry 3 }
accPppLinkVjhcCompIn OBJECT-TYPE
        SYNTAX INTEGER 
        ACCESS read-only
        STATUS mandatory
        DESCRIPTION
            "The VJ header Compresses packets received"
      ::= { accIpHeaderCompStatEntry 4 }
accPppLinkVjhcUnCompIn OBJECT-TYPE
        SYNTAX INTEGER 
        ACCESS read-only
        STATUS mandatory
        DESCRIPTION
            "The VJ header UnCompressed packets received"
      ::= { accIpHeaderCompStatEntry 5 }
accPppLinkVjhcErrIn OBJECT-TYPE
        SYNTAX INTEGER 
        ACCESS read-only
        STATUS mandatory
        DESCRIPTION
            "The VJ header Error packets received"
      ::= { accIpHeaderCompStatEntry 6 }
accPppLinkVjhcCompOut OBJECT-TYPE
        SYNTAX INTEGER 
        ACCESS read-only
        STATUS mandatory
        DESCRIPTION
            "The VJ header Compresses packets Sent"
      ::= { accIpHeaderCompStatEntry 7 }
accPppLinkVjhcUnCompOut OBJECT-TYPE
        SYNTAX INTEGER
        ACCESS read-only
        STATUS mandatory
        DESCRIPTION
            "The VJ header UnCompressed packets Sent"
      ::= { accIpHeaderCompStatEntry 8 }
accPppLinkVjhcErrOut OBJECT-TYPE
        SYNTAX INTEGER
        ACCESS read-only
        STATUS mandatory
        DESCRIPTION
            "The VJ header Error packets Sent"
      ::= { accIpHeaderCompStatEntry 9 }
-- START CFG_TRAP_ENHANCEMENTS
accPppTraps OBJECT IDENTIFIER ::= { accPpp 24 }
accPppTrapMsg OBJECT-TYPE
        SYNTAX DisplayString
        ACCESS read-only
        STATUS mandatory
        DESCRIPTION
            "PPP Trap Message "
      ::= { accPppTraps 1 }
-- END CFG_TRAP_ENHANCEMENTS 
-- Dial Group
      accDial         OBJECT IDENTIFIER ::= { accBRG 31 }
     --  Dial Control MIB
     CallAddress ::= OCTET STRING -- DisplayString (SIZE (0..128))
     --  Objects of this type are physical ports, identified by
     --  ifIndex value, which back up other physical ports,
     --  by ifIndex value.
     --
     BackupPort ::= INTEGER          -- 1..ifNumber
     --  Objects of this type are physical ports
     --
     PhysicalPort ::= INTEGER        -- 1..ifNumber
     --  Dial Backup Table
     -- The Dial Backup Table specifies which physical ports
     -- backup which other physical ports, and under what circumstances
     -- will be activated or de-activated.
     accDialBackupTable OBJECT-TYPE
         SYNTAX   SEQUENCE OF AccDialBackupEntry
         ACCESS   not-accessible
         STATUS   mandatory
         DESCRIPTION
            "A list of associations between physical ports."
         REFERENCE
            "Dial Control Procedure   "
         ::= { accDial 1 }
     accDialBackupEntry OBJECT-TYPE
         SYNTAX   AccDialBackupEntry
         ACCESS   not-accessible
         STATUS   mandatory
         DESCRIPTION
            "An association between two ports."
         INDEX { accDialBackupPrimary }
         ::= { accDialBackupTable 1 }
     AccDialBackupEntry ::=
         SEQUENCE {
             accDialBackupPort
                 BackupPort,
             accDialBackupPrimary
                 PhysicalPort,
             accDialBackupControl
                 INTEGER,
             accDialBackupRetry
                 INTEGER,
             accDialBackupDamp
                 INTEGER,
             accDialBackupCallCongestion
                 INTEGER,
             accDialBackupClearCongestion
                 INTEGER,
             accDialBackupCallError
                 INTEGER,
             accDialBackupCallAddress
                 CallAddress,
             accDialBackupStatus
                 INTEGER,
             accDialBackupState
                 INTEGER
     }
         accDialBackupPort OBJECT-TYPE
             SYNTAX   BackupPort
             ACCESS   read-write
             STATUS   mandatory
             DESCRIPTION
                "The ifIndex value of the port backing  up  the
                primary port."
            ::= { accDialBackupEntry 1 }
         accDialBackupPrimary OBJECT-TYPE
             SYNTAX   PhysicalPort
             ACCESS   read-only
             STATUS   mandatory
             DESCRIPTION
                "The ifIndex value of the port backed up."
            ::= { accDialBackupEntry 2 }
         accDialBackupControl OBJECT-TYPE
             SYNTAX  INTEGER {
                             master (1),     -- This system calls
                             slave (2),      -- this system is called
                             demand (3)      -- this system does either
                         }
             ACCESS   read-write
             STATUS   mandatory
             DESCRIPTION
                "Backup Control indicates under what conditions
                a call is placed or accepted."
            DEFVAL { demand }
            ::= { accDialBackupEntry 3 }
         accDialBackupRetry OBJECT-TYPE
             SYNTAX   INTEGER (0..3600)
             ACCESS   read-write
             STATUS   mandatory
             DESCRIPTION
                "The number of seconds the system will wait be-
                fore retrying a failed call."
            DEFVAL { 10 }
            ::= { accDialBackupEntry 4 }
         accDialBackupDamp OBJECT-TYPE
             SYNTAX   INTEGER
             ACCESS   read-write
             STATUS   mandatory
             DESCRIPTION
                "Damping factor."
            DEFVAL { 3 }
            ::= { accDialBackupEntry 5 }
         accDialBackupCallCongestion OBJECT-TYPE
             SYNTAX   INTEGER (0..101)
             ACCESS   read-write
             STATUS   mandatory
             DESCRIPTION
                "If the average octet rate transmitted (or,  on
                a  master,  received)  exceeds  this percentage
                times the ifSpeed of the primary link,  a  call
                will be placed."
            DEFVAL { 80 }
            ::= { accDialBackupEntry 6 }
         accDialBackupClearCongestion OBJECT-TYPE
             SYNTAX   INTEGER (0..101)
             ACCESS   read-write
             STATUS   mandatory
             DESCRIPTION
                "If the sum of the primary  and  backup  link's
                average  octet rates (transmitted or, on a mas-
                ter,  received)  falls  below  this  percentage
                times  the ifSpeed of the primary link, an out-
                standing call will be cleared.
                If ClearCongestion >= CallCongestion, the entry
                will  not  be  acted upon by software, but will
                result in a trap at system startup."
            DEFVAL { 50 }
            ::= { accDialBackupEntry 7 }
         accDialBackupCallError OBJECT-TYPE
             SYNTAX   INTEGER
             ACCESS   read-write
             STATUS   mandatory
             DESCRIPTION
                "If the average sum  of  ifInDiscards,  ifInEr-
                rors,  ifOutDiscards, ifOutErrors, accLapbStat-
                BadFCSIns,  accLapbStatT1Timeouts,  accLapbSta-
                tREJIns,  and  accLapbStatREJOuts  exceeds this
                value, a call will be placed.
                The call will be cleared when the  average  be-
                comes zero."
            DEFVAL { 5 }
            ::= { accDialBackupEntry 8 }
         accDialBackupCallAddress OBJECT-TYPE
             SYNTAX   CallAddress
             ACCESS   read-write
             STATUS   mandatory
             DESCRIPTION
                "The address to be called, in ASCII.
                No validation is performed on this variable."
            ::= { accDialBackupEntry 9 }
         accDialBackupStatus OBJECT-TYPE
             SYNTAX  INTEGER {
                     valid (1),
                     invalid (2)
                     }
             ACCESS   read-write
             STATUS   mandatory
             DESCRIPTION
                "If this object is set to 'invalid', the  entry
                is deleted."
            DEFVAL { valid }
            ::= { accDialBackupEntry 10 }
         accDialBackupState OBJECT-TYPE
             SYNTAX   INTEGER {
                         congestOut (1), -- call due to transmit congestion
                         congestIn  (2), -- call due to receive congestion
                         errors     (3), -- call due to errors on link
                         backup     (4), -- call due to primary link failure
                         manual     (5), -- call administratively placed
                         clear      (6)  -- no call active
                      }
             ACCESS   read-write
             STATUS   mandatory
             DESCRIPTION
                "The current call state from the primary link's
                perspective.   The  only values acceptable on a
                SET are 'manual' and 'clear'.  If  'manual'  is
                SET,  the backup link will place a call immedi-
                ately or when it next  becomes  available.   If
                'clear'  is SET when a call is administratively
                placed, either the call will be cleared, or the
                call  will  continue  for  another  reason.  If
                'clear' is set when no call is administratively
                placed, there is no effect."
            DEFVAL { clear }
            ::= { accDialBackupEntry 11 }
	accDialPortTable OBJECT-TYPE
		SYNTAX SEQUENCE OF AccDialPortEntry
		ACCESS not-accessible
		STATUS mandatory
		DESCRIPTION
			" A table containing DOD-port specific variables
			for this DOD implementation."
		::= { accDial 2 }
	accDialPortEntry OBJECT-TYPE
		SYNTAX AccDialPortEntry
		ACCESS not-accessible
		STATUS mandatory
		DESCRIPTION
			" Management information about a particular DOD Port."
		INDEX { accDialPortIndex }
		::= { accDialPortTable 1 }
	AccDialPortEntry ::= SEQUENCE {
		accDialPortIndex		INTEGER,
		accDialPortContents		INTEGER,
		accDialPortStationType		INTEGER,
		accDialPortAdminState		INTEGER,
		accDialPortCallState		INTEGER,
		accDialPortRetryInterval	TimeTicks,
		accDialPortRetryCount		INTEGER,
		accDialPortClearingInterv	TimeTicks,
		accDialPortMessageLevel		INTEGER,
		accDialPortPhysicalPort		INTEGER,
		accDialPortCallAddress		OCTET STRING,
		accDialPortPhysicalPortStr	OCTET STRING,
		accDialPortCallAddressStr	OCTET STRING,
		accDialPortPassword		OCTET STRING,
		accDialPortName			OCTET STRING,
	  	accDialPortAuthType             INTEGER,
		accDialPortSessionTimeout	INTEGER,
		accDialPortPriority		INTEGER,
		accDialPortCallBack		INTEGER,
		accDialPortProtocol		INTEGER,
                accDialPortAuthPeer             INTEGER,
                accDialPortPromptState          INTEGER,
                accDialPortLogin                OCTET STRING
		}
	accDialPortIndex	OBJECT-TYPE
		SYNTAX	INTEGER
		ACCESS	read-only
		STATUS	mandatory
		DESCRIPTION
			" Dial port number"
		::= { accDialPortEntry 1 }
	accDialPortContents	OBJECT-TYPE
		SYNTAX	INTEGER {
			other(1),
			invalid(2)
		}
		ACCESS	read-only
		STATUS	mandatory
		DESCRIPTION
			" Setting this object to invalid deletes dial port
			or call address or physical port."
		::= { accDialPortEntry 2 }
	accDialPortStationType	OBJECT-TYPE
		SYNTAX	INTEGER {
			master(1),
			slave(2),
			demand(3)
		}
		ACCESS	read-write
		STATUS	mandatory
		DESCRIPTION
			" Type of station for this dial port. Master can
			place calls, slave can accept calls, demand can
			do both."
		::= { accDialPortEntry 3 }
	accDialPortAdminState	OBJECT-TYPE
		SYNTAX	INTEGER {
			down(1),
			up(2)
		}
		ACCESS	read-write
		STATUS	mandatory
		DESCRIPTION
			" The administrative state of this dial port."
		::= { accDialPortEntry 4 }
	accDialPortCallState	OBJECT-TYPE
		SYNTAX	INTEGER {
			clear(1),
			call(2)
		}
		ACCESS	read-write
		STATUS	mandatory
		DESCRIPTION
			" The dial state of this dial port. This is more
			of a operator request than a state. Depending on
			the current state of the dial port the command that
			sets the value of this object may or may not be
			acted immediately."
		::= { accDialPortEntry 5 }
	accDialPortRetryInterval	OBJECT-TYPE
		SYNTAX	TimeTicks
		ACCESS	read-write
		STATUS	mandatory
		DESCRIPTION
			" Number of seconds allowed to elapse between two 
			dial attempts."
		::= { accDialPortEntry 6 }
	accDialPortRetryCount	OBJECT-TYPE
		SYNTAX	INTEGER
		ACCESS	read-write
		STATUS	mandatory
		DESCRIPTION
			" Total number of dial attempts."
		::= { accDialPortEntry 7 }
	accDialPortClearingInterv	OBJECT-TYPE
		SYNTAX	TimeTicks
		ACCESS	read-write
		STATUS	mandatory
		DESCRIPTION
			" Number of seconds to wait with no traffic
			to hangup this dial session."
		::= { accDialPortEntry 8 }
	accDialPortMessageLevel	OBJECT-TYPE
		SYNTAX	INTEGER
		ACCESS	read-write
		STATUS	mandatory
		DESCRIPTION
			" Current message level for how much to display
			for this dial port.
			1 - Error messages.
			2 - Unused + 1.
			3 - Warning messages + 2.
			4 - Unused + 3. 
			5 - Dial activity + 4.
			6 - Unused + 5.
			7 - Dial port state changes + 6."
		::= { accDialPortEntry 9 }
	accDialPortPhysicalPort	OBJECT-TYPE
		SYNTAX	INTEGER
		ACCESS	read-write
		STATUS	mandatory
		DESCRIPTION
			" One of the possible physical ports this dial
			port may associate."
		::= { accDialPortEntry 10 }
	accDialPortCallAddress	OBJECT-TYPE
		SYNTAX	OCTET STRING
		ACCESS	read-write
		STATUS	mandatory
		DESCRIPTION
			" One of the possible call addresses this dial
			port may call."
		::= { accDialPortEntry 11 }
	accDialPortPhysicalPortStr	OBJECT-TYPE
		SYNTAX	OCTET STRING
		ACCESS	read-only
		STATUS	mandatory
		DESCRIPTION
			" The concatenated string of all physical ports
			associated with this dial port."
		::= { accDialPortEntry 12 }
	accDialPortCallAddressStr	OBJECT-TYPE
		SYNTAX	OCTET STRING
		ACCESS	read-only
		STATUS	mandatory
		DESCRIPTION
			" The concatenated string of all call address/name
			entries associated with this dial port."
		::= { accDialPortEntry 13 }
	accDialPortPassword	OBJECT-TYPE
		SYNTAX	OCTET STRING
		ACCESS	read-write
		STATUS	mandatory
		DESCRIPTION
			" The password associated with the call address."
		::= { accDialPortEntry 14 }
	accDialPortName	OBJECT-TYPE
		SYNTAX	OCTET STRING
		ACCESS	read-write
		STATUS	mandatory
		DESCRIPTION
			" The name associated with the call address. 
			The combination of name and password is used for
			the outbound PAP negotiation."
		::= { accDialPortEntry 15 }
        accDialPortAuthType OBJECT-TYPE
                SYNTAX  INTEGER {
                        pap        (1),
                        chap       (2),
                        chappap    (3),
                        none       (4),
                        token-chap (5)
                }
                ACCESS  read-write
                STATUS  mandatory
                DESCRIPTION
                        " The authentication type associated with
                        the dial port."
                DEFVAL { chap }
                ::= { accDialPortEntry 16 }
      accDialPortSessionTimeout OBJECT-TYPE
        SYNTAX          INTEGER (0..86400)
        ACCESS          read-write
        STATUS          mandatory
        DESCRIPTION
        "The maximum time a dial session may be connected for in seconds.
         0 denotes forever."
      ::= { accDialPortEntry 17 }
      accDialPortPriority OBJECT-TYPE
        SYNTAX          INTEGER (0..86400)
        ACCESS          read-write
        STATUS          mandatory
        DESCRIPTION
        ""
      ::= { accDialPortEntry 18 }
      accDialPortCallBack OBJECT-TYPE
        SYNTAX          INTEGER {
				disabled (1),
				enabled (2)
			}
        ACCESS          read-write
        STATUS          mandatory
        DESCRIPTION
        	"Determines whether call back is enabled or disabled
		for this dial port."
      ::= { accDialPortEntry 19 }
      accDialPortProtocol OBJECT-TYPE
        SYNTAX          INTEGER {
				ppp(1),
				x25(2)
			}
        ACCESS          read-write
        STATUS          mandatory
        DESCRIPTION
                "Dial port protocol determined by user to be either ppp or X25."
      ::= { accDialPortEntry 20 }
      accDialPortAuthPeer OBJECT-TYPE
        SYNTAX  INTEGER {
                         none(1),
                         forced(2)
                        }
        ACCESS  read-write
        STATUS  mandatory
        DESCRIPTION
                "Dial port protocol determined by user to be either ppp or X25."
      ::= { accDialPortEntry 21 }
      accDialPortPromptState OBJECT-TYPE
        SYNTAX  INTEGER {
                         login      (1),
                         reenter    (2),
                         newpin     (3),
                         nexttoken  (4),
                         inprocess  (5),
                         idle       (6),
                         disabled   (7)
                        }
        ACCESS  read-write
        STATUS  mandatory
        DESCRIPTION
                "Dial port authentication prompt state."
      ::= { accDialPortEntry 22 }
      accDialPortLogin OBJECT-TYPE
        SYNTAX  OCTET STRING -- (SIZE(0..16))
        ACCESS  read-only
        STATUS  mandatory
        DESCRIPTION
                "Dial port authentication response to entered token."
      ::= { accDialPortEntry 23 }
	accDialPortStatTable	OBJECT-TYPE
		SYNTAX	SEQUENCE OF AccDialPortStatEntry
		ACCESS	not-accessible
		STATUS	mandatory
		DESCRIPTION
			" A table containing the operational parameters 
			for this dial port."
		::= { accDial 3 }
	accDialPortStatEntry	OBJECT-TYPE
		SYNTAX	AccDialPortStatEntry
		ACCESS	not-accessible
		STATUS	mandatory
		DESCRIPTION
			" Current status for this dial port."
		INDEX	{ accDialPortStatIndex }
		::= { accDialPortStatTable 1 }
	AccDialPortStatEntry ::= SEQUENCE {
        	accDialPortStatIndex            INTEGER,
                accDialPortStatActPhysPort      OCTET STRING,
                accDialPortStatState            INTEGER,
                accDialPortStatTrigFwdr         OCTET STRING,
                accDialPortStatElapsedTime      TimeTicks,
                accDialPortStatTrigSrcAddr      OCTET STRING,
                accDialPortStatTrigCallAddr     OCTET STRING,
                accDialPortStatSuccessOuts      Counter,
                accDialPortStatUnsuccessOuts    Counter,
                accDialPortStatSuccessIns       Counter,
                accDialPortStatUnsuccessIns     Counter,
                accDialPortStatAuthTypeClashes  Counter,
		accDialPortStatDisconnReasons	INTEGER
		}
	accDialPortStatIndex	OBJECT-TYPE
		SYNTAX	INTEGER
		ACCESS	read-only
		STATUS	mandatory
		DESCRIPTION
			" Dial port number."
		::= { accDialPortStatEntry 1 }
	accDialPortStatActPhysPort 	OBJECT-TYPE
		SYNTAX 	OCTET STRING
		ACCESS 	read-only
		STATUS 	mandatory
		DESCRIPTION
			" The physical port currently connected with
			or recently connected with."
		::= { accDialPortStatEntry 2 }
	accDialPortStatState 	OBJECT-TYPE
		SYNTAX 	INTEGER
		ACCESS 	read-write
		STATUS 	mandatory
		DESCRIPTION
			" The current state of this dial port.
			The following is a list of valid states:
			down(0),
			disconnected(1),
			queued(2),
			answering(3),
			dialing(4),
			connected(5) "
		::= { accDialPortStatEntry 3 }
	accDialPortStatTrigFwdr 	OBJECT-TYPE
		SYNTAX 	OCTET STRING
		ACCESS 	read-only
		STATUS 	mandatory
		DESCRIPTION
			" Application which started this dial session.
			The following is a list of applications:
			none(0),
			management(1),
			inbound(2),
			callback(12)
			ip(33),
			idp(37),
			decnet(39),
			appletalk(41),
			ipx(43),
			bridging(177),
			sr(179)"
		::= { accDialPortStatEntry 4 }
	accDialPortStatElapsedTime 	OBJECT-TYPE
		SYNTAX 	TimeTicks
		ACCESS 	read-only
		STATUS 	mandatory
		DESCRIPTION
			" Number of seconds that this dial port has
			been in the current state."
		::= { accDialPortStatEntry 5 }
	accDialPortStatTrigSrcAddr 	OBJECT-TYPE
		SYNTAX 	OCTET STRING
		ACCESS 	read-only
		STATUS 	mandatory
		DESCRIPTION
			" Source address of forwarder message that 
			started this dial session. "
		::= { accDialPortStatEntry 6 }
	accDialPortStatTrigCallAddr 	OBJECT-TYPE
		SYNTAX 	OCTET STRING
		ACCESS 	read-only
		STATUS 	mandatory
		DESCRIPTION
			" Phone number connected to during this dial
			session or the last dial session."
		::= { accDialPortStatEntry 7 }
	accDialPortStatSuccessOuts 	OBJECT-TYPE
		SYNTAX 	Counter
		ACCESS 	read-only
		STATUS 	mandatory
		DESCRIPTION
			" Number of successfull outgoing calls on
			this dial port."
		::= { accDialPortStatEntry 8 }
	accDialPortStatUnsuccessOuts 	OBJECT-TYPE
		SYNTAX 	Counter
		ACCESS 	read-only
		STATUS 	mandatory
		DESCRIPTION
			" Number of unsuccessfull call attempts on
			this dial port."
		::= { accDialPortStatEntry 9 }
	accDialPortStatSuccessIns 	OBJECT-TYPE
		SYNTAX 	Counter
		ACCESS 	read-only
		STATUS 	mandatory
		DESCRIPTION
			" Number of successfull incoming calls on
			this dial port."
		::= { accDialPortStatEntry 10 }
	accDialPortStatUnsuccessIns 	OBJECT-TYPE
		SYNTAX 	Counter
		ACCESS 	read-only
		STATUS 	mandatory
		DESCRIPTION
			" Total number of unsuccessfull incoming calls."
		::= { accDialPortStatEntry 11 }
        accDialPortStatAuthTypeClashes  OBJECT-TYPE
                SYNTAX  Counter
                ACCESS  read-only
                STATUS  mandatory
                DESCRIPTION
                        "Total number of Dial Port Authentication Type
                         mis-matches."
                ::= { accDialPortStatEntry 12 }
        accDialPortStatDisconnReasons    OBJECT-TYPE
                SYNTAX  INTEGER {
                         mgmtreq(1),
                         netfail(2),
                         locfail(3),
                         idletimeout(4),
                         sessiontimeout(5)
                        }
                ACCESS  read-only
                STATUS  mandatory
                DESCRIPTION
                        "The reason this dial port is in the
                         Disconnected state."
                ::= { accDialPortStatEntry 13 }
-- Dial Originate databases
-- Appletalk
  accDialOrigAtTable OBJECT-TYPE
		SYNTAX	SEQUENCE OF AccDialOrigAtEntry
		ACCESS	not-accessible
		STATUS	mandatory
		DESCRIPTION
			" A table containing dial originate database
			 for Appletalk."
		::= { accDial 4 }
	accDialOrigAtEntry	OBJECT-TYPE
		SYNTAX AccDialOrigAtEntry
		ACCESS not-accessible
		STATUS mandatory
		DESCRIPTION
			" Dial originate information entry for Appletalk."
		INDEX { accDialOrigAtDestStart,
			accDialOrigAtDestEnd,
			accDialOrigAtSourceStart,
			accDialOrigAtSourceEnd }
		::= { accDialOrigAtTable 1 }
	AccDialOrigAtEntry ::= SEQUENCE {
		accDialOrigAtStatus		INTEGER,
		accDialOrigAtDestStart		OCTET STRING,
		accDialOrigAtDestEnd		OCTET STRING,
		accDialOrigAtSourceStart	OCTET STRING,
		accDialOrigAtSourceEnd		OCTET STRING,
		accDialOrigAtTraffic		INTEGER,
		accDialOrigAtAction		INTEGER
		}
	accDialOrigAtStatus	OBJECT-TYPE
		SYNTAX	INTEGER {
				other(1),
				invalid(2)
			}
		ACCESS	read-write
		STATUS	mandatory
		DESCRIPTION
			" Writing 'invalid' deletes the filter table entry."
		::= { accDialOrigAtEntry 1 }
	accDialOrigAtDestStart	OBJECT-TYPE
		SYNTAX	OCTET STRING  -- (SIZE(2))
		ACCESS	read-write
		STATUS	mandatory
		DESCRIPTION
			" Destination range start for this Appletalk entry 
			 in the dial originate database."
		::= { accDialOrigAtEntry 2 }
	accDialOrigAtDestEnd	OBJECT-TYPE
		SYNTAX	OCTET STRING  -- (SIZE(2))
		ACCESS	read-write
		STATUS	mandatory
		DESCRIPTION
			" Destination range end for this Appletalk entry 
			 in the dial originate database."
		::= { accDialOrigAtEntry 3 }
	accDialOrigAtSourceStart	OBJECT-TYPE
		SYNTAX	OCTET STRING  -- (SIZE(2))
		ACCESS	read-write
		STATUS	mandatory
		DESCRIPTION
			" Source range start for this Appletalk entry 
			 in the dial originate database."
		::= { accDialOrigAtEntry 4 }
	accDialOrigAtSourceEnd	OBJECT-TYPE
		SYNTAX	OCTET STRING  -- (SIZE(2))
		ACCESS	read-write
		STATUS	mandatory
		DESCRIPTION
			" Source range end for this Appletalk entry 
			 in the dial originate database."
		::= { accDialOrigAtEntry 5 }
	accDialOrigAtTraffic	OBJECT-TYPE
		SYNTAX	INTEGER {
			 any(1),
			 nbp(2),
			 atp(3),
			 aep(4),
			 rtmp(5),
			 zip(6),
			 adsp(7),
			 nbpbroadcast(8),
			 nbplookup(9),
			 nbpreply(10),
			 nbpforwardreq(11)
			}
		ACCESS	read-write
		STATUS	mandatory
		DESCRIPTION
			" Traffic info for this Appletalk entry 
			 in the dial originate database."
		::= { accDialOrigAtEntry 6 }
	accDialOrigAtAction	OBJECT-TYPE
		SYNTAX	INTEGER {
			 allow(1),
			 disallow(2)
			}
		ACCESS	read-write
		STATUS	mandatory
		DESCRIPTION
			" Allow-disallow info for this Appletalk entry 
			 in the dial originate database."
		::= { accDialOrigAtEntry 7 }
-- Decnet
	accDialOrigDnTable	OBJECT-TYPE
		SYNTAX	SEQUENCE OF AccDialOrigDnEntry
		ACCESS	not-accessible
		STATUS	mandatory
		DESCRIPTION
			" A table containing dial originate database
			 for Decnet."
		::= { accDial 5 }
	accDialOrigDnEntry	OBJECT-TYPE
		SYNTAX AccDialOrigDnEntry
		ACCESS not-accessible
		STATUS mandatory
		DESCRIPTION
			" Dial originate information entry for Decnet."
		INDEX { accDialOrigDnDestAddr,
			accDialOrigDnSourceAddr }
		::= { accDialOrigDnTable 1 }
	AccDialOrigDnEntry ::= SEQUENCE {
		accDialOrigDnStatus		INTEGER,
		accDialOrigDnDestAddr		INTEGER,
		accDialOrigDnSourceAddr		INTEGER,
		accDialOrigDnAction		INTEGER
		}
	accDialOrigDnStatus	OBJECT-TYPE
		SYNTAX	INTEGER {
				other(1),
				invalid(2)
			}
		ACCESS	read-write
		STATUS	mandatory
		DESCRIPTION
			" Writing 'invalid' deletes the filter table entry."
		::= { accDialOrigDnEntry 1 }
	accDialOrigDnDestAddr	OBJECT-TYPE
		SYNTAX	INTEGER	(0..65535)
		ACCESS	read-write
		STATUS	mandatory
		DESCRIPTION
			" Destination address for this Decnet entry 
			 in the dial originate database."
		::= { accDialOrigDnEntry 2 }
	accDialOrigDnSourceAddr	OBJECT-TYPE
		SYNTAX	INTEGER	(0..65535)
		ACCESS	read-write
		STATUS	mandatory
		DESCRIPTION
			" Source address for this Decnet entry 
			 in the dial originate database."
		::= { accDialOrigDnEntry 3 }
	accDialOrigDnAction	OBJECT-TYPE
		SYNTAX	INTEGER {
			 allow(1),
			 disallow(2)
			}
		ACCESS	read-write
		STATUS	mandatory
		DESCRIPTION
			" Allow-disallow info for this Decnet entry 
			 in the dial originate database."
		::= { accDialOrigDnEntry 4 }
-- Bridge
	accDialOrigBrTable	OBJECT-TYPE
		SYNTAX	SEQUENCE OF AccDialOrigBrEntry
		ACCESS	not-accessible
		STATUS	mandatory
		DESCRIPTION
			" A table containing dial originate database
			 for Bridge."
		::= { accDial 6 }
	accDialOrigBrEntry	OBJECT-TYPE
		SYNTAX AccDialOrigBrEntry
		ACCESS not-accessible
		STATUS mandatory
		DESCRIPTION
			" Dial originate information entry for Bridge."
		INDEX { accDialOrigBrDestMacAddr,
			accDialOrigBrSourceMacAddr }
		::= { accDialOrigBrTable 1 }
	AccDialOrigBrEntry ::= SEQUENCE {
		accDialOrigBrStatus		INTEGER,
		accDialOrigBrDestMacAddr	OCTET STRING,
		accDialOrigBrSourceMacAddr	OCTET STRING,
		accDialOrigBrAction		INTEGER
		}
	accDialOrigBrStatus	OBJECT-TYPE
		SYNTAX	INTEGER {
				other(1),
				invalid(2)
			}
		ACCESS	read-write
		STATUS	mandatory
		DESCRIPTION
			" Writing 'invalid' deletes the filter table entry."
		::= { accDialOrigBrEntry 1 }
	accDialOrigBrDestMacAddr	OBJECT-TYPE
		SYNTAX	OCTET STRING -- (SIZE(6))
		ACCESS	read-write
		STATUS	mandatory
		DESCRIPTION
			" Destination mac address start for this Bridge entry 
			 in the dial originate database."
		::= { accDialOrigBrEntry 2 }
	accDialOrigBrSourceMacAddr	OBJECT-TYPE
		SYNTAX	OCTET STRING
		ACCESS	read-write
		STATUS	mandatory
		DESCRIPTION
			" Source mac address for this Bridge entry 
			 in the dial originate database."
		::= { accDialOrigBrEntry 3 }
	accDialOrigBrAction	OBJECT-TYPE
		SYNTAX	INTEGER {
			 allow(1),
			 disallow(2)
			}
		ACCESS	read-write
		STATUS	mandatory
		DESCRIPTION
			" Allow-disallow info for this Bridge entry 
			 in the dial originate database."
		::= { accDialOrigBrEntry 4 }
-- Idp
	accDialOrigIdpTable	OBJECT-TYPE
		SYNTAX	SEQUENCE OF AccDialOrigIdpEntry
		ACCESS	not-accessible
		STATUS	mandatory
		DESCRIPTION
			" A table containing dial originate database
			 for Idp."
		::= { accDial 7 }
	accDialOrigIdpEntry	OBJECT-TYPE
		SYNTAX AccDialOrigIdpEntry
		ACCESS not-accessible
		STATUS mandatory
		DESCRIPTION
			" Dial originate information entry for Idp."
		INDEX { accDialOrigIdpDestNet,
			accDialOrigIdpSourceNet }
		::= { accDialOrigIdpTable 1 }
	AccDialOrigIdpEntry ::= SEQUENCE {
		accDialOrigIdpStatus	INTEGER,
		accDialOrigIdpDestNet	OCTET STRING,
		accDialOrigIdpSourceNet	OCTET STRING,
		accDialOrigIdpAction	INTEGER
		}
	accDialOrigIdpStatus	OBJECT-TYPE
		SYNTAX	INTEGER {
				other(1),
				invalid(2)
			}
		ACCESS	read-write
		STATUS	mandatory
		DESCRIPTION
			" Writing 'invalid' deletes the filter table entry."
		::= { accDialOrigIdpEntry 1 }
	accDialOrigIdpDestNet	OBJECT-TYPE
		SYNTAX	OCTET STRING -- (SIZE(4))
		ACCESS	read-write
		STATUS	mandatory
		DESCRIPTION
			" Destination network for this Idp entry 
			 in the dial originate database."
		::= { accDialOrigIdpEntry 2 }
	accDialOrigIdpSourceNet	OBJECT-TYPE
		SYNTAX	OCTET STRING -- (SIZE(4))
		ACCESS	read-write
		STATUS	mandatory
		DESCRIPTION
			" Source network for this Idp entry 
			 in the dial originate database."
		::= { accDialOrigIdpEntry 3 }
	accDialOrigIdpAction	OBJECT-TYPE
		SYNTAX	INTEGER {
			 allow(1),
			 disallow(2)
			}
		ACCESS	read-write
		STATUS	mandatory
		DESCRIPTION
			" Allow-disallow info for this Idp entry 
			 in the dial originate database."
		::= { accDialOrigIdpEntry 4 }
-- Ip
	accDialOrigIpTable	OBJECT-TYPE
		SYNTAX	SEQUENCE OF AccDialOrigIpEntry
		ACCESS	not-accessible
		STATUS	mandatory
		DESCRIPTION
			" A table containing dial originate database for Ip."
		::= { accDial 8 }
	accDialOrigIpEntry	OBJECT-TYPE
		SYNTAX AccDialOrigIpEntry
		ACCESS not-accessible
		STATUS mandatory
		DESCRIPTION
			" Dial originate information entry for Ip."
		INDEX { accDialOrigIpDestAddr,
			accDialOrigIpDestMask,
			accDialOrigIpSourceAddr,
			accDialOrigIpSourceMask,
			accDialOrigIpParm }
		::= { accDialOrigIpTable 1 }
	AccDialOrigIpEntry ::= SEQUENCE {
		accDialOrigIpStatus	INTEGER,
		accDialOrigIpDestAddr	IpAddress,
		accDialOrigIpDestMask	IpAddress,
		accDialOrigIpSourceAddr	IpAddress,
		accDialOrigIpSourceMask	IpAddress,
		accDialOrigIpParm	OCTET STRING,
		accDialOrigIpAction	INTEGER
		}
	accDialOrigIpStatus	OBJECT-TYPE
		SYNTAX	INTEGER {
				other(1),
				invalid(2)
			}
		ACCESS	read-write
		STATUS	mandatory
		DESCRIPTION
			" Writing 'invalid' deletes the filter table entry."
		::= { accDialOrigIpEntry 1 }
	accDialOrigIpDestAddr	OBJECT-TYPE
		SYNTAX	IpAddress
		ACCESS	read-write
		STATUS	mandatory
		DESCRIPTION
			" Destination address for this Ip entry 
			 in the dial originate database."
		::= { accDialOrigIpEntry 2 }
	accDialOrigIpDestMask	OBJECT-TYPE
		SYNTAX	IpAddress
		ACCESS	read-write
		STATUS	mandatory
		DESCRIPTION
			" Destination mask for this Ip entry 
			 in the dial originate database."
		::= { accDialOrigIpEntry 3 }
	accDialOrigIpSourceAddr	OBJECT-TYPE
		SYNTAX	IpAddress
		ACCESS	read-write
		STATUS	mandatory
		DESCRIPTION
			" Source address for this Ip entry 
			 in the dial originate database."
		::= { accDialOrigIpEntry 4 }
	accDialOrigIpSourceMask	OBJECT-TYPE
		SYNTAX	IpAddress
		ACCESS	read-write
		STATUS	mandatory
		DESCRIPTION
			" Source mask for this Ip entry 
			 in the dial originate database."
		::= { accDialOrigIpEntry 5 }
	accDialOrigIpParm	OBJECT-TYPE
		 SYNTAX OCTET STRING
		 ACCESS read-write
		 STATUS mandatory
		 DESCRIPTION
			" Filter parameters;
			 Byte 0 is Operation 1
				[0,1,2] = [None, !,=]
			 Bytes 1,2 is Protocol
			 Byte 3 is Operation 2
				[0  = none
				[1,2,3,4] = both [!, <, >, =]
				[5,6,7,8] = destination [!, <, >, =]
				[9,10,11,12] = source [!, <, >, =]
			 Bytes 4,5 is UDP/TCP port number"
		::= { accDialOrigIpEntry 6 }
	accDialOrigIpAction	OBJECT-TYPE
		SYNTAX	INTEGER {
			 allow(1),
			 disallow(2)
			}
		ACCESS	read-write
		STATUS	mandatory
		DESCRIPTION
			" Allow-disallow info for this Ip entry 
			 in the dial originate database."
		::= { accDialOrigIpEntry 7 }
-- Ipx
	accDialOrigIpxTable	OBJECT-TYPE
		SYNTAX	SEQUENCE OF AccDialOrigIpxEntry
		ACCESS	not-accessible
		STATUS	mandatory
		DESCRIPTION
			" A table containing dial originate database for Ipx."
		::= { accDial 9 }
	accDialOrigIpxEntry	OBJECT-TYPE
		SYNTAX AccDialOrigIpxEntry
		ACCESS not-accessible
		STATUS mandatory
		DESCRIPTION
			" Dial originate information entry for Ipx."
		INDEX { accDialOrigIpxDestNet,
			accDialOrigIpxSourceNet }
		::= { accDialOrigIpxTable 1 }
	AccDialOrigIpxEntry ::= SEQUENCE {
		accDialOrigIpxStatus	INTEGER,
		accDialOrigIpxDestNet	OCTET STRING,
		accDialOrigIpxSourceNet	OCTET STRING,
		accDialOrigIpxAction	INTEGER
		}
	accDialOrigIpxStatus	OBJECT-TYPE
		SYNTAX	INTEGER {
				other(1),
				invalid(2)
			}
		ACCESS	read-write
		STATUS	mandatory
		DESCRIPTION
			" Writing 'invalid' deletes the filter table entry."
		::= { accDialOrigIpxEntry 1 }
	accDialOrigIpxDestNet	OBJECT-TYPE
		SYNTAX	OCTET STRING -- (SIZE(4))
		ACCESS	read-write
		STATUS	mandatory
		DESCRIPTION
			" Destination network for this Ipx entry 
			 in the dial originate database."
		::= { accDialOrigIpxEntry 2 }
	accDialOrigIpxSourceNet	OBJECT-TYPE
		SYNTAX	OCTET STRING -- (SIZE(4))
		ACCESS	read-write
		STATUS	mandatory
		DESCRIPTION
			" Source network for this Ipx entry 
			 in the dial originate database."
		::= { accDialOrigIpxEntry 3 }
	accDialOrigIpxAction	OBJECT-TYPE
		SYNTAX	INTEGER {
			 allow(1),
			 disallow(2)
			}
		ACCESS	read-write
		STATUS	mandatory
		DESCRIPTION
			" Allow-disallow info for this Ipx entry 
			 in the dial originate database."
		::= { accDialOrigIpxEntry 4 }
-- Sr
	accDialOrigSrTable	OBJECT-TYPE
		SYNTAX	SEQUENCE OF AccDialOrigSrEntry
		ACCESS	not-accessible
		STATUS	mandatory
		DESCRIPTION
			" A table containing dial originate database for Sr."
		::= { accDial 10 }
	accDialOrigSrEntry	OBJECT-TYPE
		SYNTAX AccDialOrigSrEntry
		ACCESS not-accessible
		STATUS mandatory
		DESCRIPTION
			" Dial originate information entry for Sr."
		INDEX { accDialOrigSrDestMacAddr,
			accDialOrigSrSourceMacAddr }
		::= { accDialOrigSrTable 1 }
	AccDialOrigSrEntry ::= SEQUENCE {
		accDialOrigSrStatus		INTEGER,
		accDialOrigSrDestMacAddr	OCTET STRING,
		accDialOrigSrSourceMacAddr	OCTET STRING,
		accDialOrigSrAction		INTEGER
		}
	accDialOrigSrStatus	OBJECT-TYPE
		SYNTAX	INTEGER {
				other(1),
				invalid(2)
			}
		ACCESS	read-write
		STATUS	mandatory
		DESCRIPTION
			"Writing 'invalid' deletes the filter table entry."
		::= { accDialOrigSrEntry 1 }
	accDialOrigSrDestMacAddr	OBJECT-TYPE
		SYNTAX	OCTET STRING -- (SIZE(6))
		ACCESS	read-write
		STATUS	mandatory
		DESCRIPTION
			" Destination mac address for this Sr entry 
			 in the dial originate database."
		::= { accDialOrigSrEntry 2 }
	accDialOrigSrSourceMacAddr	OBJECT-TYPE
		SYNTAX	OCTET STRING -- (SIZE(6))
		ACCESS	read-write
		STATUS	mandatory
		DESCRIPTION
			" Source mac address for this Sr entry 
			 in the dial originate database."
		::= { accDialOrigSrEntry 3 }
	accDialOrigSrAction	OBJECT-TYPE
		SYNTAX	INTEGER {
			 allow(1),
			 disallow(2)
			}
		ACCESS	read-write
		STATUS	mandatory
		DESCRIPTION
			" Allow-disallow info for this Sr entry 
			 in the dial originate database."
		::= { accDialOrigSrEntry 4 }
accDialPortRange	OBJECT IDENTIFIER ::= { accDial 11 }
      accDialPortMaxCount	OBJECT-TYPE
      	SYNTAX		INTEGER (0..999)
      	ACCESS		read-write
      	STATUS		mandatory
      	DESCRIPTION
      	"The maximum number of dial on demand ports that can be configured"
      ::= { accDialPortRange 1 }
      accDialPortRangeStart	OBJECT-TYPE
      	SYNTAX		INTEGER
      	ACCESS		read-only
      	STATUS		mandatory
      	DESCRIPTION
      	"The ifIndex for the start of the DOD port range"
      ::= { accDialPortRange 2 }
      accDialPortRangeEnd	OBJECT-TYPE
      	SYNTAX		INTEGER
      	ACCESS		read-only
      	STATUS		mandatory
      	DESCRIPTION
      	"The ifIndex for the end of the DOD port range"
      ::= { accDialPortRange 3 }
      accDialPortConnTable	OBJECT-TYPE
      	SYNTAX		SEQUENCE OF AccDialPortConnEntry
      	ACCESS		not-accessible
      	STATUS		mandatory
      	DESCRIPTION
      	"The table of users currently connected using dial ports"
      ::= { accDial 12 }
      accDialPortConnEntry	OBJECT-TYPE
      	SYNTAX		AccDialPortConnEntry
      	ACCESS		not-accessible
      	STATUS		mandatory
      	DESCRIPTION
      	"A single connected user's information"
      INDEX		{ accDialPortConnIndex}
      ::= { accDialPortConnTable 1 }
      AccDialPortConnEntry ::=
      	SEQUENCE {
      	accDialPortConnIndex	INTEGER,
      	accDialPortConnUser	OCTET STRING,
      	accDialPortConnPhyPort	INTEGER,
      	accDialPortConnLogPort	INTEGER,
      	accDialPortConnDir	INTEGER,
      	accDialPortConnAuth	IpAddress,
      	accDialPortConnStart	TimeTicks,
	accDialPortConnProf	OCTET STRING,
	accDialPortConnStack	OCTET STRING,
	accDialPortConnAddr	IpAddress,
        accDialPortConnState	INTEGER
      }
      accDialPortConnIndex	OBJECT-TYPE
      	SYNTAX		INTEGER
      	ACCESS		read-only
      	STATUS		mandatory
      	DESCRIPTION
      	"Simple incrementing integer index for table based alphabetically on
      	 connected user names."
      ::= { accDialPortConnEntry 1 }
      accDialPortConnUser	OBJECT-TYPE
      	SYNTAX		OCTET STRING
      	ACCESS		read-only
      	STATUS		mandatory
      	DESCRIPTION
      	"The user name for this dial connection"
      ::= { accDialPortConnEntry 2 }
      accDialPortConnPhyPort	OBJECT-TYPE
      	SYNTAX		INTEGER
      	ACCESS		read-only
      	STATUS		mandatory
      	DESCRIPTION
      	"The ifIndex for the physical channel that this call is using"
      ::= { accDialPortConnEntry 3 }
      accDialPortConnLogPort	OBJECT-TYPE
      	SYNTAX		INTEGER
      	ACCESS		read-only
      	STATUS		mandatory
      	DESCRIPTION
      	"The ifIndex for the logical channel this call is using"
      ::= { accDialPortConnEntry 4 }
      accDialPortConnDir	OBJECT-TYPE
      	SYNTAX		INTEGER {
      			in (1),
      			out (2)
      		}
      	ACCESS		read-only
      	STATUS		mandatory
      	DESCRIPTION
      	"The direction of this call"
      ::= { accDialPortConnEntry 5 }
      accDialPortConnAuth	OBJECT-TYPE
      	SYNTAX		IpAddress
      	ACCESS		read-only
      	STATUS		mandatory
      	DESCRIPTION
      	"The IP address of the authenticator for this call.
      	 0.0.0.0 denotes that the call was locally authenticated."
      ::= { accDialPortConnEntry 6 }
      accDialPortConnStart	OBJECT-TYPE
      	SYNTAX		TimeTicks
      	ACCESS		read-only
      	STATUS		mandatory
      	DESCRIPTION
      	"The time stamp; date of call establishment"
      ::= { accDialPortConnEntry 7 }
      accDialPortConnProf	OBJECT-TYPE
      	SYNTAX		OCTET STRING
      	ACCESS		read-only
      	STATUS		mandatory
      	DESCRIPTION
      	"The service profile assigned to this call"
      ::= { accDialPortConnEntry 8 }
      accDialPortConnStack	OBJECT-TYPE
      	SYNTAX		OCTET STRING
      	ACCESS		read-only
      	STATUS		mandatory
      	DESCRIPTION
      	"The physical and logical port stack used to terminate this call"
      ::= { accDialPortConnEntry 9 }
      accDialPortConnAddr	OBJECT-TYPE
      	SYNTAX		IpAddress
      	ACCESS		read-only
      	STATUS		mandatory
      	DESCRIPTION
      	"The IP address used to communicate to the peer for this call"
      ::= { accDialPortConnEntry 10 }
         accDialPortConnState OBJECT-TYPE
             SYNTAX  INTEGER {
                     disconnect (1)
                     }
             ACCESS   read-write
             STATUS   mandatory
             DESCRIPTION
                "If this object is set to 'Disconnect', the  entry
                is Disabled."
            DEFVAL { disconnect }
            ::= { accDialPortConnEntry 11 }
      accAccessParameter	OBJECT IDENTIFIER ::= { accDial 14 }
         accAccessTimer OBJECT-TYPE
             SYNTAX  INTEGER {
                     enable (1),
		     disable(2)
                     }
             ACCESS   read-write
             STATUS   mandatory
             DESCRIPTION
                "This object sets the access fucntion on/off." 
            ::= { accAccessParameter 1 }
         accAccessCreditDay OBJECT-TYPE
             SYNTAX  INTEGER 
             ACCESS   read-write
             STATUS   mandatory
             DESCRIPTION
                "This object sets the access credit per day." 
            ::= { accAccessParameter 2 }
         accAccessCreditYear OBJECT-TYPE
             SYNTAX  INTEGER 
             ACCESS   read-write
             STATUS   mandatory
             DESCRIPTION
                "This object sets the access credit per year." 
            ::= { accAccessParameter 3 }
         accAccessTime OBJECT-TYPE
             SYNTAX  OCTET STRING 
             ACCESS   read-write
             STATUS   mandatory
             DESCRIPTION
                "To set access time from and to" 
            ::= { accAccessParameter 4 }
         accAccessLimitDate OBJECT-TYPE
             SYNTAX  OCTET STRING 
             ACCESS   read-write
             STATUS   mandatory
             DESCRIPTION
                "To set access limit date from and to " 
            ::= { accAccessParameter 5 }
         accAccessDay OBJECT-TYPE
             SYNTAX  OCTET STRING 
             ACCESS   read-write
             STATUS   mandatory
             DESCRIPTION
                "To set access limit day " 
            ::= { accAccessParameter 6 }
         accAccessDayCreditLeft OBJECT-TYPE
             SYNTAX  INTEGER 
             ACCESS   read-only
             STATUS   mandatory
             DESCRIPTION
                "This object display  the access credit left in the day." 
            ::= { accAccessParameter 7 }
         accAccessYearCreditLeft OBJECT-TYPE
             SYNTAX  INTEGER 
             ACCESS   read-only
             STATUS   mandatory
             DESCRIPTION
                "This object display  the access credit left in the year." 
            ::= { accAccessParameter 8 }
--This mib files was introduced with th release of Ceylon 9.7
-- CCP Group
--accPppCompress 	OBJECT IDENTIFIER ::= { accBRG 31 } 
-- PPP Data Compression Table
	accPppCompressTable   OBJECT-TYPE
		SYNTAX SEQUENCE OF AccPppCompressEntry
		ACCESS not-accessible
		STATUS mandatory
		DESCRIPTION
			" A table containing PPP Data compression specific 
			variables for PPP compression implementation."
		::= { accPpp 21 }
	accPppCompressEntry OBJECT-TYPE
		SYNTAX AccPppCompressEntry
		ACCESS not-accessible
		STATUS mandatory
		DESCRIPTION
			"PPP data compression table entry containing data 
			compression parameters for a particular PPP port"
		INDEX { accPppCompressIndex }
		::= { accPppCompressTable 1 }
	AccPppCompressEntry ::= SEQUENCE {
		accPppCompressIndex 		INTEGER,
		accPppCompressMsgLevel 		INTEGER,
		accPppCompressMethod 		INTEGER,
		accPppCompressStream 		INTEGER,
	 	accPppCompressNegoMethodIn 	INTEGER,
	 	accPppCompressNegoMethodOut 	INTEGER,
	 	accPppCompressNegoStreamIn 	INTEGER,
	 	accPppCompressNegoStreamOut 	INTEGER}
	accPppCompressIndex OBJECT-TYPE
		SYNTAX INTEGER
		ACCESS read-only
		STATUS mandatory
		DESCRIPTION
			"The ifindex of the PPP port." 
		::= { accPppCompressEntry 1 }
	accPppCompressMsgLevel OBJECT-TYPE 
		SYNTAX INTEGER 
 		ACCESS read-only
		STATUS mandatory
		DESCRIPTION
			"The message level for PPP compression." 
		::= { accPppCompressEntry 2 }
	accPppCompressMethod OBJECT-TYPE
		SYNTAX INTEGER {
			none(1),
			nego(2),
			vendor(3),
			stac-seqn(4),
			stac-extd(5),
			stac-none(6),
			mppc(7)
		}
		ACCESS read-write
		STATUS mandatory
		DESCRIPTION
			"The administrative status of data compression for
			this PPP port.  None disables data compression and 
 			others enabled it."
		DEFVAL { none }
		::= { accPppCompressEntry 3 }
	accPppCompressStream OBJECT-TYPE
		SYNTAX INTEGER {
 			packet(1),
			stream(2)
		}
		ACCESS read-write
		STATUS mandatory
		DESCRIPTION
			"The stream mode of data compression for this PPP 
			port."
		DEFVAL { stream }
		::= { accPppCompressEntry 4 }
	accPppCompressNegoMethodIn OBJECT-TYPE
		SYNTAX INTEGER {
 			none(1),
			vendor(2),
			stac-seqn(3),
			stac-extd(4),
			stac-none(5),
			mppc(6)
		}
		ACCESS read-write
		STATUS mandatory
		DESCRIPTION
			"The negotiated status of data compression for 
			this PPP port.  None disables data compression 
			and others enabled it. "
		DEFVAL { none }
		::= { accPppCompressEntry 5 }
        accPppCompressNegoMethodOut OBJECT-TYPE
                SYNTAX INTEGER {
                        none(1),
                        vendor(2),
                        stac-seqn(3),
                        stac-extd(4),
                        stac-none(5),
			mppc(6)
                }
                ACCESS read-write
                STATUS mandatory
                DESCRIPTION
                        "The negotiated status of data compression for
                        this PPP port.  None disables data compression
                        and others enabled it. "
                DEFVAL { none }
                ::= { accPppCompressEntry 6 }
	accPppCompressNegoStreamIn OBJECT-TYPE
		SYNTAX INTEGER {
 			packet(1),
			stream(2)
		}
		ACCESS read-write
		STATUS mandatory
		DESCRIPTION
			"The negotiated stream mode of data compression for
			 this PPP port."
		DEFVAL { stream }
		::= { accPppCompressEntry 7 }
        accPppCompressNegoStreamOut OBJECT-TYPE
                SYNTAX INTEGER {
                        packet(1),
                        stream(2)
                }
                ACCESS read-write
                STATUS mandatory
                DESCRIPTION
                        "The negotiated stream mode of data compression for
                         this PPP port."
                DEFVAL { stream }
                ::= { accPppCompressEntry 8 }
	accPppCompressStatTable OBJECT-TYPE
		SYNTAX SEQUENCE OF AccPppCompressStatEntry
	 	ACCESS not-accessible
		STATUS mandatory
		DESCRIPTION
			"Data compression statistics table for PPP  
			ports containing data compression statistics."
		::= { accPpp 22 }
	accPppCompressStatEntry OBJECT-TYPE
		SYNTAX AccPppCompressStatEntry
		ACCESS not-accessible
		STATUS mandatory
		DESCRIPTION
			"Data compression PPP  port statistics table 
			entry containing data compression statistics for 
			a particular PPP  port "
		INDEX { accPppCompressStatIndex }
		::= { accPppCompressStatTable 1 }
	AccPppCompressStatEntry ::= SEQUENCE { 
		accPppCompressStatIndex 	INTEGER, 
		accPppCompressStatStatusIn 	INTEGER, 
		accPppCompressStatStatusOut 	INTEGER, 
		accPppCompressStatAvgCompIn 	Gauge, 
		accPppCompressStatAvgCompOut 	Gauge, 
		accPppCompressStatInOctets 	Counter, 
		accPppCompressStatOutOctets 	Counter, 
		accPppCompressStatInPackets 	Counter, 
		accPppCompressStatOutPackets 	Counter, 
		accPppCompressUnCompInStats 	Counter,
		accPppCompressUnCompOutStats 	Counter,
		accPppCompressStatHdrErrors 	Counter,
		accPppCompressStatResyncs 	Counter,
		accPppCompressStatNoEndMarks 	Counter,
		accPppCompressStatNoAvailBufs 	Counter,
		accPppCompressStatRcvResetReqs 	Counter,
		accPppCompressStatRcvResetAcks 	Counter,
		accPppCompressStatSndResetReqs 	Counter,
		accPppCompressStatSndResetAcks 	Counter,
		accPppCompressStatExpandIn	INTEGER,
		accPppCompressStatExpandOut	INTEGER,
		accPppCompressStatDiscardIn	INTEGER,
		accPppCompressStatDiscardOut 	INTEGER}
	accPppCompressStatIndex OBJECT-TYPE
		SYNTAX INTEGER
		ACCESS read-only
		STATUS mandatory
		DESCRIPTION
			"The interface index of the PPP  port." 
		::= { accPppCompressStatEntry 1 }
	accPppCompressStatStatusIn OBJECT-TYPE
		SYNTAX INTEGER {
 			disc(1),
			conn(2),
			sync(3),
			resync(4)
		}
		ACCESS read-only
		STATUS mandatory
		DESCRIPTION
			"The operational status of the PPP port."
		::= { accPppCompressStatEntry 2 }
	accPppCompressStatStatusOut OBJECT-TYPE
                SYNTAX INTEGER {
                        disc(1),
                        conn(2),
                        sync(3),
                        resync(4)
                }
                ACCESS read-only
                STATUS mandatory
                DESCRIPTION
                        "The operational status of the PPP port."
                ::= { accPppCompressStatEntry 3 }
	accPppCompressStatAvgCompIn OBJECT-TYPE
		SYNTAX Gauge
		ACCESS read-only
		STATUS mandatory
		DESCRIPTION
			"The average compression rato of packets presented
		 	for decompression expressed as a percentage between 
			0 and 10.  "
		::= { accPppCompressStatEntry 4 }
	accPppCompressStatAvgCompOut OBJECT-TYPE
		SYNTAX Gauge
		ACCESS read-only
		STATUS mandatory
		DESCRIPTION
			"The average compression rate of packets presented 
			for compression expressed as a percentage between 
			0 and 10.  "
 		::= { accPppCompressStatEntry 5 }
	accPppCompressStatInOctets OBJECT-TYPE
		SYNTAX Counter
		ACCESS read-only
		STATUS mandatory
		DESCRIPTION
			"The total number of compressed octets presented 
			for decompression."
 		::= { accPppCompressStatEntry 6 }
	accPppCompressStatOutOctets OBJECT-TYPE
 		SYNTAX Counter
		ACCESS read-only
		STATUS mandatory
		DESCRIPTION
			"The total number of compressed octets generated after 
			compression."
 		::= { accPppCompressStatEntry 7 }
	accPppCompressStatInPackets OBJECT-TYPE
		SYNTAX Counter
		ACCESS read-only
		STATUS mandatory
		DESCRIPTION
			"The total number of uncompressed packets generated 
			by decompression."
		::= { accPppCompressStatEntry 8 }
	accPppCompressStatOutPackets OBJECT-TYPE 
		SYNTAX Counter
		ACCESS read-only
		STATUS mandatory
		DESCRIPTION
			"The total number of uncompressed packets presented 				for compression."
	::= { accPppCompressStatEntry 9 }
	accPppCompressUnCompInStats OBJECT-TYPE
		SYNTAX Counter
		ACCESS read-only
		STATUS mandatory
		DESCRIPTION
			"The total number of uncompressed packets presented 
			for decompression (i.e., packets which could not be 
			compressed and were therefore received in their 
			uncompressed form)."
 		::= { accPppCompressStatEntry 10 }
	accPppCompressUnCompOutStats OBJECT-TYPE
		SYNTAX Counter
		ACCESS read-only
		STATUS mandatory
		DESCRIPTION
			"The total number of uncompressed packets presented 
			for compression which could not be compressed (i.e., 
			the packet expanded).  These packets are transmitted 
			in their uncompressed form."
		::= { accPppCompressStatEntry 11 }
	accPppCompressStatHdrErrors OBJECT-TYPE
		SYNTAX Counter
		ACCESS read-only
		STATUS mandatory
		DESCRIPTION
			"The number of packets received with invalid 
			compression headers.  A header error requires a 
			resynchronization of the history buffers at each end 
			of the link."
		::= { accPppCompressStatEntry 12 }
	accPppCompressStatResyncs OBJECT-TYPE
		SYNTAX Counter
		ACCESS read-only
		STATUS mandatory
		DESCRIPTION
			"The number of resynchronizations."
		::= { accPppCompressStatEntry 13 }
	accPppCompressStatNoEndMarks OBJECT-TYPE
		SYNTAX Counter
		ACCESS read-only
		STATUS mandatory
		DESCRIPTION
			"The number of packets received with no end marker.  
			Missing end markers require a resynchronization of 
			the history buffers at each end of the link."
		::= { accPppCompressStatEntry 14 }
	accPppCompressStatNoAvailBufs OBJECT-TYPE
		SYNTAX Counter
		ACCESS read-only
		STATUS mandatory
		DESCRIPTION
			"The number of times the PPP port was connected and 
			no history buffer could be allocated."
		::= { accPppCompressStatEntry 15 }
	accPppCompressStatRcvResetReqs OBJECT-TYPE
		SYNTAX Counter
		ACCESS read-only
		STATUS mandatory
		DESCRIPTION
			"The number of times the PPP port was connected and 
			no history buffer could be allocated."
		::= { accPppCompressStatEntry 16 }
	accPppCompressStatRcvResetAcks OBJECT-TYPE
		SYNTAX Counter
		ACCESS read-only
		STATUS mandatory
		DESCRIPTION
			"The number of times the PPP port was connected and 
			no history buffer could be allocated."
		::= { accPppCompressStatEntry 17 }
	accPppCompressStatSndResetReqs OBJECT-TYPE
		SYNTAX Counter
		ACCESS read-only
		STATUS mandatory
		DESCRIPTION
			"The number of times the PPP port was connected and 
			no history buffer could be allocated."
		::= { accPppCompressStatEntry 18 }
	accPppCompressStatSndResetAcks OBJECT-TYPE
		SYNTAX Counter
		ACCESS read-only
		STATUS mandatory
		DESCRIPTION
			"The number of times the PPP port was connected and 
			no history buffer could be allocated."
 		::= { accPppCompressStatEntry 19 }
        accPppCompressStatExpandIn OBJECT-TYPE
                SYNTAX INTEGER 
                ACCESS read-only
                STATUS mandatory
                DESCRIPTION
                        "The number of incoming packets expanded." 
                ::= { accPppCompressStatEntry 20 }
        accPppCompressStatExpandOut OBJECT-TYPE
                SYNTAX INTEGER
                ACCESS read-only
                STATUS mandatory
                DESCRIPTION
                        "The number of outgoing packets expanded."
                ::= { accPppCompressStatEntry 21 }
        accPppCompressStatDiscardIn OBJECT-TYPE
                SYNTAX INTEGER
                ACCESS read-only
                STATUS mandatory
                DESCRIPTION
                        "The number of incoming packets that are discarded."
                ::= { accPppCompressStatEntry 22 }
        accPppCompressStatDiscardOut OBJECT-TYPE
                SYNTAX INTEGER
                ACCESS read-only
                STATUS mandatory
                DESCRIPTION
                        "The number of outgoing packets that are discarded."
                ::= { accPppCompressStatEntry 23 }
--Dial Port  Data  Compression Objects
--accDialPortCompress OBJECT IDENTIFIER ::= { accBRG 31 }
--Dial Port Data Compression Table
	accDialPortCompressTable OBJECT-TYPE
		SYNTAX SEQUENCE OF AccDialPortCompressEntry 
		ACCESS not-accessible
		STATUS mandatory
		DESCRIPTION
			" A table containing Dial Port Data compression  
			specific varailbes for Dial Port compression 
			implementation."
 		::= { accDial 13 }
	accDialPortCompressEntry OBJECT-TYPE
		SYNTAX AccDialPortCompressEntry
		ACCESS not-accessible
		STATUS mandatory
		DESCRIPTION
			"Dial Port data compression table entry containing 				data compression parameters for a particular Dial 
			Port port"
		INDEX { accDialPortCompressIndex }
 		::= { accDialPortCompressTable 1 }
	AccDialPortCompressEntry ::= SEQUENCE { 
		accDialPortCompressIndex 		INTEGER, 
		accDialPortCompressMsgLevel 		INTEGER,
		accDialPortCompressMethod 		INTEGER,
		accDialPortCompressStream 		INTEGER,
		accDialPortCompressNegoMethodIn		INTEGER,
		accDialPortCompressNegoMethodOut 	INTEGER,
		accDialPortCompressNegoStreamIn		INTEGER,
		accDialPortCompressNegoStreamOut 	INTEGER}
	accDialPortCompressIndex  OBJECT-TYPE
		SYNTAX INTEGER
		ACCESS read-only
		STATUS mandatory
		DESCRIPTION
			"The ifindex of the Dial Port port." 
		::= { accDialPortCompressEntry 1 }
	accDialPortCompressMsgLevel  OBJECT-TYPE
		SYNTAX INTEGER
 		ACCESS read-only
		STATUS mandatory
		DESCRIPTION
			"The message level for Dial Port compression."
		::= { accDialPortCompressEntry 2 }
	accDialPortCompressMethod OBJECT-TYPE
		 SYNTAX INTEGER {
 			none(1),
			nego(2),
			vendor(3),
			stac-seqn(4), 
			stac-extd(5),
		 	stac-none(6),
			mppc(7)
		}
		ACCESS read-write
 		STATUS mandatory
		DESCRIPTION
			"The administrative status of data compression for 
			this Dial Port port. None disables data compression 
			and others enabled it. "
		DEFVAL { none }
		::= { accDialPortCompressEntry 3 }
	accDialPortCompressStream OBJECT-TYPE
		SYNTAX INTEGER {
 			packet(1),
			stream(2)
		}
		ACCESS read-write
		STATUS mandatory
		DESCRIPTION
			"The stream mode of data compression for this Dial 
			Port port."
		DEFVAL { stream }
		::= { accDialPortCompressEntry 4 }
	accDialPortCompressNegoMethodIn OBJECT-TYPE
		SYNTAX INTEGER {
 			none(1),
			vendor(2),
			stac-seqn(3),
			stac-extd(4),
			stac-none(5),
			mppc(6)
		}
		ACCESS read-write
		STATUS mandatory
		DESCRIPTION
			"The negotiated status of data compression for 
 			for incoming packets for this 
			Dial Port port. None disables data compression and 
			others  enabled it. "
		DEFVAL { none }
		::= { accDialPortCompressEntry 5 }
        accDialPortCompressNegoMethodOut OBJECT-TYPE
                SYNTAX INTEGER {
                        none(1),
                        vendor(2),
                        stac-seqn(3),
                        stac-extd(4),
                        stac-none(5),
			mppc(6)
                }
                ACCESS read-write
                STATUS mandatory
                DESCRIPTION
                        "The negotiated status of data compression for 
			outgoing packets for this
                        Dial Port port. None disables data compression and
                        others  enabled it. "
                DEFVAL { none }
                ::= { accDialPortCompressEntry 6 }
	accDialPortCompressNegoStreamIn OBJECT-TYPE 
		SYNTAX INTEGER {
 			packet(1), 
			stream(2)
		}
		ACCESS read-write
 		STATUS mandatory
		DESCRIPTION
			"The negotiated stream mode of data compression for 
			this Dial Port port."
		DEFVAL { stream }
		::= { accDialPortCompressEntry 7 }
        accDialPortCompressNegoStreamOut OBJECT-TYPE
                SYNTAX INTEGER {
                        packet(1),
                        stream(2)
                }
                ACCESS read-write
                STATUS mandatory
                DESCRIPTION
                        "The negotiated stream mode of data compression for
                        this Dial Port port."
                DEFVAL { stream }
                ::= { accDialPortCompressEntry 8 }
-- START CFG_TRAP_ENHANCEMENTS
-- Dod Traps Branch Enterprise
accDodTraps        OBJECT IDENTIFIER ::= { accDial 15 } 
        accDodTrapMsg OBJECT-TYPE
        	SYNTAX          DisplayString
        	ACCESS          read-only
        	STATUS          mandatory
        	DESCRIPTION
               		 "DOD Trap Message "
        	::= { accDodTraps 1 }
--Multilink Group  Data  Compression Objects
--accMlPppCompress OBJECT IDENTIFIER ::= { accBRG 9 }
--Multilink Group Data Compression Table
	accMlPppCompressTable OBJECT-TYPE
		SYNTAX SEQUENCE OF AccMlPppCompressEntry 
		ACCESS not-accessible
		STATUS mandatory
		DESCRIPTION
			" A table containing Multilink group Data compression  
			specific variables for Multilink group compression 
			implementation."
		::= { accMultilink 7 }
	accMlPppCompressEntry OBJECT-TYPE
		SYNTAX AccMlPppCompressEntry
		ACCESS not-accessible
		STATUS mandatory
		DESCRIPTION
			"Multilink group data compression table
 			entry containing data compression parameters for a 
			particular Multilink group port."
		INDEX { accMlPppCompressIndex }
		::= { accMlPppCompressTable 1 }
	AccMlPppCompressEntry ::= SEQUENCE {
                accMlPppCompressIndex 		INTEGER,
                accMlPppCompressMsgLevel 	INTEGER,
                accMlPppCompressMethod 		INTEGER,
		accMlPppCompressStream 		INTEGER,
                accMlPppCompressNegoMethodIn 	INTEGER,
		accMlPppCompressNegoMethodOut	INTEGER,
                accMlPppCompressNegoStreamIn 	INTEGER,
                accMlPppCompressNegoStreamOut 	INTEGER}
	accMlPppCompressIndex  OBJECT-TYPE
		SYNTAX INTEGER
		ACCESS read-only
		STATUS mandatory
		DESCRIPTION
			"The ifindex of the Multilink group port."
		::= { accMlPppCompressEntry 1 }
	accMlPppCompressMsgLevel  OBJECT-TYPE
		SYNTAX INTEGER 
		ACCESS read-only
		STATUS mandatory
		DESCRIPTION
			"The message level for Multilink group compression."
		::= { accMlPppCompressEntry 2 }
	accMlPppCompressMethod OBJECT-TYPE
		SYNTAX INTEGER {
 			none(1),
    			nego(2),
			vendor(3),
			stac-seqn(4),
			stac-extd(5),
			stac-none(6),
			mppc(7)
		}
		ACCESS read-write
		STATUS mandatory
		DESCRIPTION
			"The administrative status of data compression for 
			this Multilink group port.  None disables data 
			compression and others  enabled it. "
		DEFVAL { none }
		::= { accMlPppCompressEntry 3 }
	accMlPppCompressStream OBJECT-TYPE
		SYNTAX INTEGER {
 			packet(1),
			stream(2)
		}
		ACCESS read-write
		STATUS mandatory
		DESCRIPTION
			"The stream mode of data compression for this 					Multilink group port."
		DEFVAL { stream }
		::= { accMlPppCompressEntry 4 }
	accMlPppCompressNegoMethodIn OBJECT-TYPE
 		SYNTAX INTEGER { 
			none(1), 
			vendor(2),
			stac-seqn(3), 
			stac-extd(4), 
			stac-none(5),
			mppc(6)
		}
		ACCESS read-write 
		STATUS mandatory 
		DESCRIPTION
 			"The negotiated status of data compression for 
			this Multilink group port.  None disables data 
			compression and others  enabled it. "
		DEFVAL { none }
		::= { accMlPppCompressEntry 5 }
        accMlPppCompressNegoMethodOut OBJECT-TYPE
                SYNTAX INTEGER {
                        none(1),
                        vendor(2),
                        stac-seqn(3),
                        stac-extd(4),
                        stac-none(5),
			mppc(6)
                }
                ACCESS read-write
                STATUS mandatory
                DESCRIPTION
                        "The negotiated status of data compression for
                        this Multilink group port.  None disables data
                        compression and others  enabled it. "
                DEFVAL { none }
                ::= { accMlPppCompressEntry 6 }
	accMlPppCompressNegoStreamIn OBJECT-TYPE
		SYNTAX INTEGER {
 			packet(1),
			stream(2)
		}
		ACCESS read-write
		STATUS mandatory
		DESCRIPTION
			"The negotiated stream mode of data compression for 
			this Multilink group port.   "
		DEFVAL { stream }
		::= { accMlPppCompressEntry 7 }
        accMlPppCompressNegoStreamOut OBJECT-TYPE
                SYNTAX INTEGER {
                        packet(1),
                        stream(2)
                }
                ACCESS read-write
                STATUS mandatory
                DESCRIPTION
                        "The negotiated stream mode of data compression for
                        this Multilink group port.   "
                DEFVAL { stream }
                ::= { accMlPppCompressEntry 8 }
--Multilink Group compression Statitistic Table
	accMlPppCompressStatTable OBJECT-TYPE
		SYNTAX SEQUENCE OF AccMlPppCompressStatEntry 
		ACCESS not-accessible
		STATUS mandatory
		DESCRIPTION
			"Data compression statistics table for Multilink 
			group ports containing data compression statistics"
		::= { accMultilink 8 }
	accMlPppCompressStatEntry OBJECT-TYPE
		SYNTAX AccMlPppCompressStatEntry
		ACCESS not-accessible
 		STATUS mandatory
		DESCRIPTION
			"Data compression Multilink group port statistics 				table entry containing data compression statistics 
			for a particular Multilink group."
		INDEX { accMlPppCompressStatIndex }
		::= { accMlPppCompressStatTable 1 }
	AccMlPppCompressStatEntry ::= SEQUENCE { 
		accMlPppCompressStatIndex 		INTEGER, 
		accMlPppCompressStatStatus 		INTEGER, 
		accMlPppCompressStatInOctets 		Counter, 
		accMlPppCompressStatOutOctets 		Counter, 
		accMlPppCompressStatInPackets 		Counter, 
		accMlPppCompressStatOutPackets 		Counter, 
		accMlPppCompressUnCompInStats 		Counter, 
		accMlPppCompressUnCompOutStats 		Counter, 
		accMlPppCompressStatAvgCompIn 		Gauge, 
		accMlPppCompressStatAvgCompOut 		Gauge, 
		accMlPppCompressStatHdrErrors 		Counter, 
		accMlPppCompressStatResyncs 		Counter, 
		accMlPppCompressStatNoEndMarks 		Counter, 
		accMlPppCompressStatNoAvailBufs		Counter, 
		accMlPppCompressStatRcvResetReqs 	Counter, 
		accMlPppCompressStatRcvResetAcks 	Counter, 
		accMlPppCompressStatSndResetReqs 	Counter,
		accMlPppCompressStatSndResetAcks 	Counter}
	accMlPppCompressStatIndex OBJECT-TYPE
		SYNTAX INTEGER
		ACCESS read-only
		STATUS mandatory
		DESCRIPTION
			"The interface index of the Multilink group "
		::= { accMlPppCompressStatEntry 1 }
	accMlPppCompressStatStatus OBJECT-TYPE
		SYNTAX INTEGER {
			disc(1),
			conn(2),
			sync(3),
			resync(4)
		}
		ACCESS read-only
		STATUS mandatory
		DESCRIPTION
			"The operational status of the Multilink group."
		::= { accMlPppCompressStatEntry 2 }
	accMlPppCompressStatAvgCompIn OBJECT-TYPE
		SYNTAX Gauge
		ACCESS read-only
		STATUS mandatory
		DESCRIPTION
			"The average compression rato of packets presented 
			for decompression expressed as a percentage between 
			0 and 10.  "
 		::= { accMlPppCompressStatEntry 3 }
	accMlPppCompressStatAvgCompOut OBJECT-TYPE 
		SYNTAX Gauge
		ACCESS read-only
		STATUS mandatory
 		DESCRIPTION
			"The average compression rate of packets presented 				for compression expressed as a percentage between 				0 and 10.  "
 		::= { accMlPppCompressStatEntry 4 }
	accMlPppCompressStatInOctets OBJECT-TYPE
		SYNTAX Counter
		ACCESS read-only
		STATUS mandatory
		DESCRIPTION
			"The total number of compressed octets presented 
			for decompression."
		::= { accMlPppCompressStatEntry 5 }
	accMlPppCompressStatOutOctets OBJECT-TYPE
		SYNTAX Counter
		ACCESS read-only
		STATUS mandatory
		DESCRIPTION
			"The total number of compressed octets generated 
			after compression."
 		::= { accMlPppCompressStatEntry 6 }
	accMlPppCompressStatInPackets OBJECT-TYPE 
		SYNTAX Counter
		ACCESS read-only
		STATUS mandatory
		DESCRIPTION
			"The total number of uncompressed packets generated 
			by decompression."
		::= { accMlPppCompressStatEntry 7 }
	accMlPppCompressStatOutPackets OBJECT-TYPE 
		SYNTAX Counter
		ACCESS read-only
		STATUS mandatory
		DESCRIPTION
			"The total number of uncompressed packets presented 
			for compression."
		::= { accMlPppCompressStatEntry 8 }
	accMlPppCompressUnCompInStats OBJECT-TYPE 	
		SYNTAX Counter
		ACCESS read-only
		STATUS mandatory
		DESCRIPTION
			"The total number of uncompressed packets presented 
			for decompression (i.e., packets which could not be 
			compressed and were therefore received in their 
			uncompressed form)."
 		::= { accMlPppCompressStatEntry 9 }
	accMlPppCompressUnCompOutStats OBJECT-TYPE
		SYNTAX Counter
		ACCESS read-only
		STATUS mandatory
		DESCRIPTION
			"The total number of uncompressed packets presented 
			for compression which could not be compressed (i.e., 
			the packet expanded).  These packets are transmitted 
			in their uncompressed form."
		::= { accMlPppCompressStatEntry 10 }
	accMlPppCompressStatHdrErrors OBJECT-TYPE
		SYNTAX Counter
		ACCESS read-only
		STATUS mandatory
		DESCRIPTION
			"The number of packets received with invalid 
			compression headers.  A header error requires a 
			resynchronization of the history buffers at each 
			end of the link."
		::= { accMlPppCompressStatEntry 11 }
	accMlPppCompressStatResyncs OBJECT-TYPE
		SYNTAX Counter
		ACCESS read-only
		STATUS mandatory
		DESCRIPTION
			"The number of resynchronizations."
		::= { accMlPppCompressStatEntry 12 }
	accMlPppCompressStatNoEndMarks OBJECT-TYPE
		SYNTAX Counter
		ACCESS read-only
		STATUS mandatory
		DESCRIPTION
			"The number of packets received with no end marker.  
			Missing end markers require a resynchronization of 				the history buffers at each end of the link."
		::= { accMlPppCompressStatEntry 13 }
	accMlPppCompressStatNoAvailBufs OBJECT-TYPE
		SYNTAX Counter
		ACCESS read-only
		STATUS mandatory
		DESCRIPTION
			"The number of times the Multilink group was connected 	
			and no history buffer could be allocated."
		::= { accMlPppCompressStatEntry 14 }
	accMlPppCompressStatRcvResetReqs OBJECT-TYPE
		SYNTAX Counter
		ACCESS read-only
		STATUS mandatory
		DESCRIPTION
			"The number of times the Multilink group was 					connected and no history buffer could be allocated."
		::= { accMlPppCompressStatEntry 15 }
	accMlPppCompressStatRcvResetAcks OBJECT-TYPE
		SYNTAX Counter
		ACCESS read-only
		STATUS mandatory
		DESCRIPTION
			"The number of times the Multilink group was					 connected and no history buffer could be allocated."
		::= { accMlPppCompressStatEntry 16 }
	accMlPppCompressStatSndResetReqs OBJECT-TYPE
 		SYNTAX Counter
		ACCESS read-only
		STATUS mandatory
		DESCRIPTION
			"The number of times the Multilink group was 
			connected and no history buffer could be allocated."
		::= { accMlPppCompressStatEntry 17 }
	accMlPppCompressStatSndResetAcks OBJECT-TYPE
		SYNTAX Counter
		ACCESS read-only
		STATUS mandatory
		DESCRIPTION
			"The number of times the Multilink group was 
			connected and no history buffer could be allocated."
		::= { accMlPppCompressStatEntry 18 }

accPppUnIdentifiedSourceTrap1 TRAP-TYPE
        ENTERPRISE   accPppTraps 
        VARIABLES  { accPppTrapMsg ,
                      accTrapLogSeqNum}
        DESCRIPTION
               "Indicates that LCP is in authentication phase. Incoming 
	       authentication has been negotiated but there is no 
	       authentication source. We should never get here, but 
	       for some unknown reason on rare occasions we do.  
	       Rather than panic, we will generate a trap message 
SEVERITY-DEFAULT: Minor 
EVENTTYPE-DEFAULT: 10 
ADDITIONAL-TEXT-VARIABLES: { accTrapLogSeqNum,accPppTrapMsg }
PCAUSE-DEFAULT: 4 " 
 
        ::= 1
accPppLoopBackTrap2 TRAP-TYPE
        ENTERPRISE   accPppTraps 
        VARIABLES  { accPppTrapMsg,
                     ifIndex ,
accTrapLogSeqNum}
        DESCRIPTION
                "Indicates that loopback has been found 
SEVERITY-DEFAULT: Major 
EVENTTYPE-DEFAULT: 10 
ADDITIONAL-TEXT-VARIABLES: { accTrapLogSeqNum,accPppTrapMsg }
PCAUSE-DEFAULT: 6 " 
 
        ::= 2
accPppCallBackTrap3 TRAP-TYPE
        ENTERPRISE   accPppTraps 
        VARIABLES  { accPppTrapMsg ,
                      accTrapLogSeqNum}
        DESCRIPTION
                "PPP: Callback failied
SEVERITY-DEFAULT: Major 
EVENTTYPE-DEFAULT: 10 
ADDITIONAL-TEXT-VARIABLES: { accTrapLogSeqNum,accPppTrapMsg }
PCAUSE-DEFAULT: 6 " 
 
        ::= 3
        accDodPasswdTrap TRAP-TYPE
        	ENTERPRISE   accDodTraps 
        	VARIABLES  { accDodTrapMsg ,
                       accTrapLogSeqNum}
        	DESCRIPTION
                	"Indicates that Dial port was found but the 
			 password didn't match and hence the information 
			 will not be forwarded to RADIUS. 
SEVERITY-DEFAULT: Indeterminate 
EVENTTYPE-DEFAULT: 10 
ADDITIONAL-TEXT-VARIABLES: { accTrapLogSeqNum,accDodTrapMsg }
PCAUSE-DEFAULT: 4 " 
 
        	::= 1
        accPppAuthDenTrap TRAP-TYPE
        	ENTERPRISE   accDodTraps 
        	VARIABLES  { accDodTrapMsg,
               		     accPppAuthParmMethodIn,
                	     accPppAuthParmUserNameIn ,
                       accTrapLogSeqNum}
        	DESCRIPTION
                	"Indicates that either the user password not found 
			 or ppp authentication denied for the user 
SEVERITY-DEFAULT: Warning 
EVENTTYPE-DEFAULT: 10 
ADDITIONAL-TEXT-VARIABLES: { accTrapLogSeqNum,accDodTrapMsg }
PCAUSE-DEFAULT: 4 " 
 
        	::= 2
        accPppAuthNakTrap TRAP-TYPE
        	ENTERPRISE   accDodTraps 
        	VARIABLES  { accDodTrapMsg,
                	     accDialPortAuthType ,
                       accTrapLogSeqNum}
        	DESCRIPTION
               		"PPP authentication failed for various reasons, 
			 such as: Dial port is not available or Invalid PAP 
			 password or CHAP secret or Port not configured to 
			 accept incoming call or Conflicting authentication 
			 methods or Cannot accept call on this physical port
SEVERITY-DEFAULT: Indeterminate 
EVENTTYPE-DEFAULT: 10 
ADDITIONAL-TEXT-VARIABLES: { accTrapLogSeqNum,accDodTrapMsg }
PCAUSE-DEFAULT: 4 " 
 
        	::= 3
        accDodDialTrap TRAP-TYPE
        	ENTERPRISE   accDodTraps 
        	VARIABLES  { accDodTrapMsg,
               		     accDialPortIndex ,
                       accTrapLogSeqNum}
        	DESCRIPTION
               		"Indicates that while Clearing the current call and 
			 searching for work, it is found that work has been 
			 done.
SEVERITY-DEFAULT: Warning 
EVENTTYPE-DEFAULT: 10 
ADDITIONAL-TEXT-VARIABLES: { accTrapLogSeqNum,accDodTrapMsg }
PCAUSE-DEFAULT: 4 " 
 
        	::= 4
        accDodNoCktTrap TRAP-TYPE
        	ENTERPRISE   accDodTraps 
        	VARIABLES  { accDodTrapMsg,
               		     accMlPppIndex ,
                       accTrapLogSeqNum}
        	DESCRIPTION
               		"Any hunt groups referenced by dial ports need to 
			 be expanded here. It also happens during the phase 
			 after ISDN NFAS groups have been initialized;  It 
			 also happens when a dynamically installed dial port 
			 acquires a hunt group. 
SEVERITY-DEFAULT: Minor 
EVENTTYPE-DEFAULT: 10 
ADDITIONAL-TEXT-VARIABLES: { accTrapLogSeqNum,accDodTrapMsg }
PCAUSE-DEFAULT: 6 " 
 
        	::= 5
        accDodPrtBumpTrap TRAP-TYPE
        	ENTERPRISE   accDodTraps 
        	VARIABLES  { accDodTrapMsg,
               		     accDialPortIndex ,
                       accTrapLogSeqNum}
        	DESCRIPTION
                	"Indiacates that one bump port is found that has 
			 lower priority that is using one of the physical 
			 ports configured for this dial port.
SEVERITY-DEFAULT: Minor 
EVENTTYPE-DEFAULT: 2 
ADDITIONAL-TEXT-VARIABLES: { accTrapLogSeqNum,accDodTrapMsg }
PCAUSE-DEFAULT: 46 " 
 
        	::= 6
        accPhyPrtNotAvailTrap TRAP-TYPE
        	ENTERPRISE   accDodTraps 
        	VARIABLES  { accDodTrapMsg,
               		     accMlPppIndex ,
                       accTrapLogSeqNum}
        	DESCRIPTION
                	"Acquiring physical port <dial port name> failed. 
			 The physical port admin state is down or the physical 
			 port is not available.
SEVERITY-DEFAULT: Minor 
EVENTTYPE-DEFAULT: 4 
ADDITIONAL-TEXT-VARIABLES: { accTrapLogSeqNum,accDodTrapMsg }
PCAUSE-DEFAULT: 56 "  
 
		::= 7
        accDodCompressionTrap TRAP-TYPE
        	ENTERPRISE   accDodTraps 
        	VARIABLES  { accDodTrapMsg,
               		     accDialPortIndex,
                     	     accDialPortProtocol ,
                            accTrapLogSeqNum}
        	DESCRIPTION
                	" Dial Port Compression (CCP) can't be set for 
			  X.25 Dial Port.
SEVERITY-DEFAULT: Minor 
EVENTTYPE-DEFAULT: 4 
ADDITIONAL-TEXT-VARIABLES: { accTrapLogSeqNum,accDodTrapMsg }
PCAUSE-DEFAULT: 56 " 
 
        	::= 8
        accPortInUseTrap TRAP-TYPE
        	ENTERPRISE   accDodTraps 
        	VARIABLES  { accDodTrapMsg,
               	             accDialPortIndex ,
                              accTrapLogSeqNum}
        	DESCRIPTION
                	"Dial port is in use, cannot change CCP parameters.
SEVERITY-DEFAULT: Minor 
EVENTTYPE-DEFAULT: 2 
ADDITIONAL-TEXT-VARIABLES: { accTrapLogSeqNum,accDodTrapMsg }
PCAUSE-DEFAULT: 56 " 
 
        	::= 9
        accDodMaxPapPasswdTrap TRAP-TYPE
        	ENTERPRISE   accDodTraps 
        	VARIABLES  { accDodTrapMsg ,
                       accTrapLogSeqNum}
        	DESCRIPTION
                	" Indicates that the password entered by user is 
			  greater than the maximum length for the PAP password.
SEVERITY-DEFAULT: Indeterminate 
EVENTTYPE-DEFAULT: 10 
ADDITIONAL-TEXT-VARIABLES: { accTrapLogSeqNum,accDodTrapMsg }
PCAUSE-DEFAULT: 253 " 
 
        	::= 10
        accDodNeedResetTrap TRAP-TYPE
        	ENTERPRISE   accDodTraps 
        	VARIABLES  { accDodTrapMsg ,
                       accTrapLogSeqNum}
        	DESCRIPTION
                	"Dial port count change requires reset. 
SEVERITY-DEFAULT: Minor 
EVENTTYPE-DEFAULT: 10 
ADDITIONAL-TEXT-VARIABLES: { accTrapLogSeqNum,accDodTrapMsg }
PCAUSE-DEFAULT: 1 " 
 
        	::= 11 
END
