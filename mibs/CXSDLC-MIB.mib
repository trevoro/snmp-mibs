CXSDLC-MIB DEFINITIONS ::= BEGIN


IMPORTS
Counter, TimeTicks              FROM RFC1155-SMI
OBJECT-TYPE                FROM RFC-1212
cxSDLC,SapIndex,Alias
                           FROM CXProduct-SMI;


CuAddress  ::= INTEGER (1..254)


sdlcSapTable OBJECT-TYPE
SYNTAX    SEQUENCE OF SdlcSapEntry
ACCESS    not-accessible
STATUS    mandatory
DESCRIPTION
"This table contains configuration information that is used to manage the 
SDLC interface. Each row in the table defines either an upper or lower SAP 
(service access point). SAPs permit SDLC to communicate with layers above 
(always SNALC) and below it in the protocol stack.

The maximum number of rows in the table is limited by sdlcSapNumber, which 
is an integer in the range 1 to 8. Since SDLC upper and lower SAPs have a 
one-to-one relationship, this makes 4 upper and 4 lower SAPs available. 
Each pair control one physical SLDC link (via the BOP).

The SLDC interface has two modes of operation: TIU (terminal interface 
unit) and HIU (host interface unit).

- TIU mode is used when the SDLC SAP is connected to one or more SNA 
control units (secondary link stations) and their supported terminals. It 
emulates a primary link station. 

- HIU mode is used when the SLDC SAP is connected to a host. It 
communicates across a WAN link with the TIU, and locally with the host via 
SDLC. In communications with the host it emulates the control units 
(secondary link stations) connected to the TIU.

The SDLC interface supports connections with a maximum of 64 link 
stations. These can be distributed in any combination across the supported 
physical links."
REFERENCE
     "Memotec Communications Inc."
::= { cxSDLC 1 }


sdlcSapEntry OBJECT-TYPE
     SYNTAX    SdlcSapEntry
     ACCESS    not-accessible
     STATUS    mandatory
     DESCRIPTION
"Defines a row in the sdlcSapTable. Each row contains the objects which 
are used to define a service access point."
     INDEX { sdlcSapNumber }
     ::= { sdlcSapTable 1 }


SdlcSapEntry ::=
     SEQUENCE {
          sdlcSapNumber                 SapIndex,
          sdlcSapRowStatus                   INTEGER,
          sdlcSapType                        INTEGER,
          sdlcSapCuType                 INTEGER,
          sdlcSapAlias                       Alias,
          sdlcSapCompanionAlias              Alias,
          sdlcSapSnalcRef                    INTEGER,
          sdlcSapDuplex                 INTEGER,
          sdlcSapRaiseDtrOnConnectReq        INTEGER,
          sdlcPollIntAfterAckTimer           TimeTicks,
          sdlcSapLineType                    INTEGER,
          sdlcSapControl                INTEGER,
          sdlcSapOperationalMode             INTEGER,
          sdlcSapLinkStatus                  INTEGER,
          sdlcSapLinkChange                  Counter,
          sdlcSapTxDataFrames           Counter,
          sdlcSapRxDataFrames           Counter,
          sdlcSapConnectRequest              Counter,
          sdlcSapDisconnectRequest           Counter,
          sdlcSapDisconnectIndication             Counter
          }


sdlcSapNumber OBJECT-TYPE
     SYNTAX    SapIndex
     ACCESS    read-only
     STATUS    mandatory
     DESCRIPTION
"Identifies a SAP (service access point) in the sdlcSapTable. The table 
supports 8 SAPs. Numbers 1 to 4 are lower SAPs, and numbers 4 to 8 are 
upper SAPs. "
::= { sdlcSapEntry 1 }


sdlcSapRowStatus OBJECT-TYPE
     SYNTAX    INTEGER {
                    invalid        (1),
                    valid          (2)
                    }
     ACCESS    read-write
     STATUS    mandatory
     DESCRIPTION
"Determines the status of the objects in a table row.

Options:
invalid (1): Row is flagged, after next reset the values will be disabled 
and the row will be deleted from the table.

valid (2): Values are enabled.

Configuration Changed: administrative and operative"
     ::= { sdlcSapEntry 2 }


sdlcSapType OBJECT-TYPE
     SYNTAX    INTEGER {
                    lower     (1),
                    upper     (2)
                    }
     ACCESS    read-write
     STATUS    mandatory
     DESCRIPTION
"Determines the SAP (service access point) type: - 'lower' identifies a 
SAP leading to a physical SDLC port. This SAP must be bound to an upper 
BOP SAP. - 'upper' identifies a SAP acting as an internal inter-layer 
logical port. This SAP must be bound to a lower SNA Link Conversion SAP.

Configuration Changed: administrative"
     ::={ sdlcSapEntry 3 }


sdlcSapCuType OBJECT-TYPE
     SYNTAX    INTEGER {
                    terminalInterfaceUnit    (1),
                    hostInterfaceUnit   (2)
                    }
     ACCESS    read-write
     STATUS    mandatory
     DESCRIPTION
"Determines the SAP type: HIU or TIU. 

Options:
terminalInterfaceUnit (1): The SAP type is a TIU, which means it is 
connected to one or more control units (secondary link stations). The TIU 
emulates a primary link station, which polls the attached control units. 
The SDLC interface can support a total of 64 control units across all TIU 
SAPs.

hostInterfaceUnit (2): The SAP type is an HIU, which means it is connected 
to an SNA host (primary link station). The HIU emulates the control units 
connected to a TIU. It responds to polls issued by the host.

Default Value: terminalInterfaceUnit (1)

Configuration Changed: administrative"
     DEFVAL { terminalInterfaceUnit }
     ::= { sdlcSapEntry 4 }


sdlcSapAlias OBJECT-TYPE
     SYNTAX    Alias
     ACCESS    read-write
     STATUS    mandatory
     DESCRIPTION
"The textual name that identifies this SAP (service access point). Names 
must be unique for all SDLC SAPs. 

Range of Values: 1 -16 alphanumeric characters (first character must be a 
letter)

Default Value: none

Configuration Changed: administrative"
     ::= { sdlcSapEntry 5 }


sdlcSapCompanionAlias OBJECT-TYPE
     SYNTAX    Alias
     ACCESS    read-write
     STATUS    mandatory
     DESCRIPTION
"The textual name of the BOP SAP that binds with this SDLC SAP. Names must 
be unique for each service access point.

Range of Values: 1 -16 alphanumeric characters (first character must be a 
letter)

Default Value: none

Configuration Changed: administrative"
     ::= { sdlcSapEntry 6 }


sdlcSapSnalcRef OBJECT-TYPE
     SYNTAX    INTEGER  (1..8)
     ACCESS    read-write
     STATUS    mandatory
     DESCRIPTION
"This object applies only to lower SAPs (service access points).

It indicates the sdlcSapNumber of the upper SDLC SAP that is associated 
with this lower SAP.

Range of Values: 1 - 8

Default Value: none

Configuration Changed: administrative"
     ::={ sdlcSapEntry 7 }


sdlcSapDuplex OBJECT-TYPE
     SYNTAX    INTEGER {
                    fullduplex     (1),
                    halfduplex     (2)
                    }
     ACCESS    read-write
     STATUS    mandatory
     DESCRIPTION
"This object applies only to lower SAPs (service access points).

It determines if the SAP operates in full-duplex or half-duplex mode.

Range of Values: 

fullduplex (1): The SAP operates in full duplex mode, allowing data to be 
transmitted is both directions at the same time (two-way simultaneous 
transmission). On the link, RTS is raised when DTR is raised.

halfduplex (2): The SAP operates in half duplex mode, allowing data to be 
transmitted in both directions, but not at the same time (two-way 
alternate transmission). On the link, RTS is raised during transmission 
and dropped during reception.

Default Value: fullduplex (1)

Configuration Changed: administrative and operative"
     DEFVAL { fullduplex }
     ::={ sdlcSapEntry 8 }


sdlcSapRaiseDtrOnConnectReq OBJECT-TYPE
     SYNTAX    INTEGER {
                    no   (1),
                    yes  (2)
                    }
     ACCESS    read-write
     STATUS    mandatory
     DESCRIPTION
"Determines when the DTR signal is raised on the port connected to the 
SAP.

Options:
no (1): DTR is raised whether or not a connection request is received from 
the SNA link conversion layer.

yes (2): When a connection request is received from the SNA link 
conversion layer, DTR is raised on the physical port the SAP is connected 
to.

Default Value: no (1)

Configuration Changed: administrative and operative"
     DEFVAL { no }
     ::= { sdlcSapEntry 9 }


sdlcPollIntAfterAckTimer OBJECT-TYPE
     SYNTAX    TimeTicks
     ACCESS    read-write
     STATUS    mandatory
     DESCRIPTION
"This object applies only to a service access point functioning as a TIU. 

Determines the length of time allowed to elapse between the reception of 
an acknowledgment to a poll and the transmission of the next poll. Certain 
control units require a delay in order to successfully respond to polls.

Since multiple SDLC logical links may share the same SAP (i.e., multiple 
control units communicating on the same physical link), this timer applies 
globally to all logical links using this SAP. 

Range of Values: 1 - 250 (in tenths of a second), a value of 0 disables 
the timer

Default Value: 0

Related Object: sdlcSapCuType

Configuration Changed: administrative and operative"
     DEFVAL {0}
     ::= { sdlcSapEntry 10 }


sdlcSapLineType OBJECT-TYPE
    SYNTAX    INTEGER {
                   standard             (1),
                   negotiable           (2),
                   switched             (3),
                   switched-negotiable  (4)
                   }
    ACCESS    read-write
    STATUS    mandatory
    DESCRIPTION
"Determines the type of SDLC line supported by this SAP (service access 
point). When using an HIU and TIU in tandem, the settings for this object 
on both must match.

Options:
standard (1): Allows multiple CUs to be defined for this SAP. All frames 
received from attached devices must include the appropriate CU address. 
The general address (0xFF) is not supported. A standard line is also non 
negotiable.

negotiable (2): Allows the CX900 to receive an XID without sending a poll 
to the attached device. The initial address of the XID coming from the 
device cannot be the general poll (0xFF). A negotiable line can support 
more than one device.

switched (3): Allows the CX900 to receive an XID using the general poll 
address (0xFF). A switched line is not negotiable and can only support one 
attached device.

switched-negotiable (4): Allows the CX900 to receive an XID using the 
general poll address (0xFF). The line is also negotiable and can only 
support one attached device per port.

Default Value: negotiable (2)

Configuration Changed: administrative and operative"
DEFVAL { negotiable }
    ::= { sdlcSapEntry 11 }




sdlcSapControl OBJECT-TYPE
     SYNTAX    INTEGER {
                    clearStats     (1)
                    }
     ACCESS    write-only
     STATUS    mandatory
     DESCRIPTION
"Clears all statistics for this service access point.

Options:
clearStats (1): Clear statistics.

Default Value: none

Configuration Changed: administrative and operative"
     ::= { sdlcSapEntry  20 }


sdlcSapOperationalMode OBJECT-TYPE
     SYNTAX    INTEGER {
                    offline        (1),
                    online         (2)
                    }
     ACCESS    read-only
     STATUS    mandatory
     DESCRIPTION
"Indicates the state of this SAP (service access point).

Options:
offLine (1): Indicates that this SAP is not operational.

onLine (2): Indicates that this SAP is operational."
     ::={ sdlcSapEntry 30 }


sdlcSapLinkStatus OBJECT-TYPE
     SYNTAX    INTEGER {
                    down      (1),
                    up        (2)
                    }
     ACCESS    read-only
     STATUS    mandatory
     DESCRIPTION
"Indicates the physical state of this SAP (service access point) with 
respect to its associated BOP SAP (sdlcSapCompanionAlias).

Options:
down (1): Indicates that this SAP is not operational. 

up (2): Indicates that this SAP is operational."
     ::={ sdlcSapEntry 31 }


sdlcSapLinkChange OBJECT-TYPE
     SYNTAX    Counter
     ACCESS    read-only
     STATUS    mandatory
     DESCRIPTION
"Indicates the number of times that the physical link has been brought 
up."
     ::= { sdlcSapEntry  40 }


sdlcSapTxDataFrames OBJECT-TYPE
     SYNTAX    Counter
     ACCESS    read-only
     STATUS    mandatory
     DESCRIPTION
"Indicates the number of information frames sent by this SAP (service 
access point)."
     ::= { sdlcSapEntry  41 }


sdlcSapRxDataFrames OBJECT-TYPE
     SYNTAX    Counter
     ACCESS    read-only
     STATUS    mandatory
     DESCRIPTION
"Indicates the number of information frames received by this SAP (service 
access point)."
     ::= { sdlcSapEntry 42}


sdlcSapConnectRequest OBJECT-TYPE
     SYNTAX    Counter
     ACCESS    read-only
     STATUS    mandatory
     DESCRIPTION
"Indicates the number of connection requests generated by the SNA Link 
Conversion layer."
     ::= { sdlcSapEntry 43}


sdlcSapDisconnectRequest OBJECT-TYPE
     SYNTAX    Counter
     ACCESS    read-only
     STATUS    mandatory
     DESCRIPTION
"Indicates the number of connection clears generated by the SNA Link 
Conversion layer."
     ::= { sdlcSapEntry 44}
sdlcSapDisconnectIndication OBJECT-TYPE
     SYNTAX    Counter
     ACCESS    read-only
     STATUS    mandatory
     DESCRIPTION
"Indicates the number of connection clears sent to the SNA Link Conversion 
layer."
     ::= { sdlcSapEntry 45}


sdlcCuTable OBJECT-TYPE
SYNTAX    SEQUENCE OF SdlcCuEntry
ACCESS    not-accessible
STATUS    mandatory
DESCRIPTION
"This table contains configuration for the control units associated with 
SDLC SAPs. Each row identifies one control unit."
::= { cxSDLC 2 }


sdlcCuEntry OBJECT-TYPE
     SYNTAX    SdlcCuEntry
     ACCESS    not-accessible
     STATUS    mandatory
     DESCRIPTION
"Defines a row in the sdlcCuTable. Each row contains the objects which 
define one control unit (link station). Up to 64 link stations are 
supported across all SAPs.

If the row is associated with a TIU SAP, then it defines the parameters 
used to communicate with an actual control unit (secondary link station). 

If the row is associated with an HIU SAP, then it defines the parameters 
for an emulated control unit. This must match a companion definition on a 
TIU SAP. "
     INDEX { sdlcCuSap, sdlcCuId }
     ::= { sdlcCuTable 1 }


SdlcCuEntry ::=
     SEQUENCE {
          sdlcCuSap                     SapIndex,
          sdlcCuId                      CuAddress,
          sdlcCuRowStatus                    INTEGER,
          sdlcCuMaxFrameLength               INTEGER,
          sdlcCuTransmitWindow               INTEGER,
          sdlcCuPollRetry                    INTEGER,
          sdlcCuMaxRetry                INTEGER,
          sdlcCuWaitForNextSnrmOrXid              INTEGER,
          sdlcCuSendDisconnect                    INTEGER,
          sdlcCuPollAckTimer                 TimeTicks,
          sdlcCuSlowPollTimer                TimeTicks,
          sdlcCuWaitForUaFromSnalcTimer      TimeTicks,
          sdlcCuControl                      INTEGER,
          sdlcCuState                        INTEGER,
          sdlcCuOperationalMode              INTEGER,
          sdlcCuDiscReasonCode                    INTEGER,
          sdlcCuSnalcDiscReasonCode               INTEGER,
          sdlcCuConnectionStatus             INTEGER,
          sdlcCuFramesInTransmitQueue             Counter,
          sdlcCuTxFrames                Counter,
          sdlcCuRxFrames                Counter,
          sdlcCuTimeOuts                Counter,
          sdlcCuSnrmCount                    Counter,
                 sdlcCuXidCommand                 Counter,
          sdlcCuXidResponse                  Counter,
          sdlcCuUnnumberedAcks               Counter,
          sdlcCuRetransmission                    Counter,
          sdlcCuDisconnectCount                   Counter,
          sdlcCuDisconnectModeCount               Counter,
          sdlcCuTransmittedRNR                    Counter,
          sdlcCuReceivedRNR                  Counter,
          sdlcCuFrameRejects                 Counter,
          sdlcCuRemoteDisc                   Counter,
          sdlcCuConnectionRequest            Counter,
          sdlcCuDisconnectionRequest              Counter,
          sdlcCuDisconnectionIndication           Counter
          }

sdlcCuSap OBJECT-TYPE
     SYNTAX    SapIndex
     ACCESS    read-only
     STATUS    mandatory
     DESCRIPTION
"Determines the sdlcSapNumber of the SAP (service access point) this row 
(control unit) is associated with. More than one secondary link station 
can be associated with a particular sdlcSapNumber.

Default Value: none

Configuration Changed: administrative "
     ::= { sdlcCuEntry 1 }


sdlcCuId OBJECT-TYPE
     SYNTAX    CuAddress
     ACCESS    read-write
     STATUS    mandatory
     DESCRIPTION
"Determines the address of the control unit associated with this SAP. If 
this SAP is a TIU, it defines the address of the physical control unit 
attached to the SAP. If this SAP is an HIU, it defines the address of an 
emulated control unit. Note that the value of this object is decimal, but 
control units may specify this value in hexadecimal.

Range of Values: 1 - 254

Default Value: none

Configuration Changed: administrative"
     ::= { sdlcCuEntry 2 }


sdlcCuRowStatus OBJECT-TYPE
     SYNTAX    INTEGER {
                    invalid        (1),
                    valid          (2)
                    }
     ACCESS    read-write
     STATUS    mandatory
     DESCRIPTION
"Determines the status of the objects in a table row.

Options:
invalid (1): Row is flagged, after next reset the values will be disabled 
and the row will be deleted from the table.

valid (2): Values are enabled.

Configuration Changed: administrative and operative"
     ::= { sdlcCuEntry 3 }


sdlcCuMaxFrameLength OBJECT-TYPE
     SYNTAX    INTEGER (1..4096)
     ACCESS    read-write
     STATUS    mandatory
     DESCRIPTION
"Determines the largest frame that can be sent and received by this 
control unit. The value of this object must match the setting on the host 
or control unit the SAP is communicating with. Known as MAXDATA, maximum 
I- Frame size, or maximum BTU length, depending on the SNA device.

Range of Values: 1 - 4096 bytes

Default Value: 521 bytes

Configuration Changed: administrative and operative"
     DEFVAL {521}
     ::= { sdlcCuEntry 4 }


sdlcCuTransmitWindow OBJECT-TYPE
     SYNTAX    INTEGER (1..7)
     ACCESS    read-write
     STATUS    mandatory
     DESCRIPTION
"Determines the maximum number of information frames that can be 
outstanding at any given time. A frame is considered to be outstanding 
until the remote device (control unit or host) acknowledges its receipt.

Range of Values: 1 - 7

Default Value: 7

Configuration Changed: administrative and operative"
     DEFVAL {7}
     ::= { sdlcCuEntry 5 }


sdlcCuPollRetry OBJECT-TYPE
     SYNTAX    INTEGER (1..50)
     ACCESS    read-write
     STATUS    mandatory
     DESCRIPTION
"This object applies only if this entry is associated with a TIU service 
access point.

Determines the number of times an unacknowledged poll is retransmitted. A 
poll is retransmitted if an acknowledgment has not been received from the 
control unit before the sdlcCuPollAckTimer expires. 

Range of Values: 1 - 50 

Default Value: 3 

Related Objects: sdlcCuPollAckTimer

Configuration Changed: administrative and operative"
     DEFVAL {3}
     ::= { sdlcCuEntry 6 }


sdlcCuMaxRetry OBJECT-TYPE
     SYNTAX    INTEGER (1..50)
     ACCESS    read-write
     STATUS    mandatory
     DESCRIPTION
"This object applies only if this entry is associated with a TIU service 
access point.

Determines the number of times an unacknowledged DISC, SNRM, or XID is 
retransmitted during slow polling. A poll is retransmitted if an 
acknowledgment has not been received from the control unit before the 
sdlcCuSlowPollTimer expires. This timer is reset each time a DISC, SNRM, 
or XID is transmitted.

When this counter is exceeded, the link with this control unit is 
abandoned and a connection cleared message is forwarded to the SNA link 
conversion layer.

Range of Values: 1 - 50

Default Value: 3

Related Objects: sdlcCuPollAckTimer

Configuration Changed: administrative and operative"
     DEFVAL {3}
     ::= { sdlcCuEntry 7 }


sdlcCuWaitForNextSnrmOrXid OBJECT-TYPE
     SYNTAX    INTEGER {
                    no   (1),
                    yes  (2)
                    }
     ACCESS    read-write
     STATUS    mandatory
     DESCRIPTION
"This object applies only if this entry is associated with an HIU service 
access point.

Determines what the HIU does when it receives a UA or XID response from 
the control unit (on the TIU side of the link).

Options:
no (1): The HIU sends the UA or XID response to the host immediately.

yes (2): The HIU holds the UA or XID response until the host repeats the 
original poll. This is used in cases where the delay on the link between 
the HIU and TIU can cause the host to time out.

Default Value: no (1)

Configuration Changed: administrative and operative"
     DEFVAL { no }
     ::= { sdlcCuEntry 8 }


sdlcCuSendDisconnect OBJECT-TYPE
     SYNTAX    INTEGER {
                    no   (1),
                    yes  (2)
                    }
     ACCESS    read-write
     STATUS    mandatory
     DESCRIPTION
"Determines the command that is sent to disconnect the control unit. 

Options:
no (1): A SNRM is sent to disconnect the control unit.

yes (2): If entry is associated with a TIU SAP, it sends a DISC to the 
control unit (secondary link station). If entry is associated with an HIU 
SAP, it sends a DM to the host.

Default Value: yes (2)

Configuration Changed: administrative and operative"
     DEFVAL { yes }
     ::= { sdlcCuEntry 9 }


sdlcCuPollAckTimer OBJECT-TYPE
     SYNTAX    TimeTicks
     ACCESS    read-write
     STATUS    mandatory
     DESCRIPTION
"This object applies only if this entry is associated with a TIU service 
access point.

Defines the amount of time the TIU waits for the control unit (secondary 
link station) to acknowledge a poll. If no response is received before 
this timer expires, then the poll is retransmitted. The object 
sdlcCuPollRetry determines how many times the TIU retransmits a poll.

If the poll was a SNRM, XID, or DISC, then the first time this timer 
expires, the sldcCuSlowPollTimer is started, and the TIU slow polls the 
control unit. 

Range of Values: 1 - 250 (in tenths of a second), a value of 0 disables 
the timer

Default Value: 20 (2 seconds)

Related Objects: sdlcCuPollRetry sldcCuSlowPollTimer

Configuration Changed: administrative and operative"
     DEFVAL {20}
     ::= { sdlcCuEntry 10}


sdlcCuSlowPollTimer OBJECT-TYPE
     SYNTAX    TimeTicks
     ACCESS    read-write
     STATUS    mandatory
     DESCRIPTION
"This object applies only if this entry is associated with a TIU service 
access point.

Determines the amount of time the TIU waits for the control unit 
(secondary link station) to respond to a SNRM poll during slow polling. 
Each time this timer expires another poll is sent. The object 
sdlcCuMaxRetry determines how many slow polls are transmitted.

The TIU begins slow polling if the sdlcCuPollAckTimer timer expires before 
the control unit has responded to the initial SNRM, XID, or DISC poll.

Range of Values: 1 - 250 tenths of a second (a value of 0 disables the 
timer)

Default Value: 10 (1 second)

Related Objects: sdlcCuPollAckTimer sdlcCuMaxRetry

Configuration Changed: administrative and operative"
     DEFVAL {10}
     ::= { sdlcCuEntry 11 }


     sdlcCuWaitForUaFromSnalcTimer OBJECT-TYPE
     SYNTAX    TimeTicks
     ACCESS    read-write
     STATUS    mandatory
     DESCRIPTION
"If this entry is associated with an HIU SAP (service access point), it 
determines the maximum amount of time that the HIU waits for a response to 
a SNRM or DISC sent to the TIU. This is used to control link setup across 
the WAN between the HIU and TIU. When this timer expires, the link is 
dropped. Set the minimum value of this timer as follows:

= p + sdlcCuPollAckTimer + (sdlcCuSlowPollTimer * n)

Where:

p: is the propagation delay on the WAN link

n: is the number of slow polls you want to wait for. 

If this entry is associated with a TIU SAP, it determines the maximum 
amount of time that the TIU waits for a response to a DISC sent to the 
HIU. When this timer expires, the link is dropped. At a minimum this timer 
should be set greater than the propagation delay on the link.

Range of Values: 1 - 250 tenths of a second (a value of 0 disables the 
timer)

Default Value: 0

Configuration Changed: administrative and operative"
     DEFVAL {0}
     ::= { sdlcCuEntry 13}


sdlcCuControl OBJECT-TYPE
     SYNTAX    INTEGER {
                    clearStats     (1)
                    }
     ACCESS    write-only
     STATUS    mandatory
     DESCRIPTION
"Clears all statistics for this control unit.

Default Value: none

Options:
clearStats (1): Clear statistics.

Configuration Changed: administrative and operative"
     ::= { sdlcCuEntry 30 }


sdlcCuState OBJECT-TYPE
     SYNTAX    INTEGER {
                    normalDiscMode                  (1),
                    waitForSnrm              (2),
                    receivedSnrm             (3),
                    normalResponseMode  (4),
                    waitForDisc              (5),
                    receivedDisc             (6),
                    snrmSent                      (7),
                    discSent                           (8),
                    remoteDiscReceived       (9),
                    xidExchange              (10)
                    }
     ACCESS    read-only
     STATUS    mandatory
     DESCRIPTION
"Indicates the current status of the control unit. 

Options:
normalDiscMode (1): This control unit is in Normal Disconnected Mode

waitForSnrm (2): This control unit (associated with an HIU SAP) is waiting 
for a SNRM from the host.

receivedSnrm (3): This control unit (associated with an HIU SAP) has 
received a SNRM from the host.

normalResponseMode (4): The control unit is in Normal Response Mode.

waitForDisc (5): This control unit (associated with an HIU SAP) is waiting 
for a DISC from the host.

receivedDisc (6): This control unit (associated with an HIU SAP) has 
received a DISC from the host.

snrmSent (7): A SNRM has been sent to this control unit.

discSent (8): A DISC has been sent to the companion control unit on the 
HIU.

remoteDiscReceived (9): This control unit has received a (remote) DISC 
from its companion control unit on the TIU.

xidExchange (10): The TIU received an XID poll from the HIU for this 
control unit."
     ::= { sdlcCuEntry 40 }


sdlcCuOperationalMode OBJECT-TYPE
     SYNTAX    INTEGER {
                    offline        (1),
                    online         (2)
                    }
     ACCESS    read-only
     STATUS    mandatory
     DESCRIPTION
"Indicates the state of this control unit.

Options:
offLine (1): Indicates that this control unit is not operational.

onLine (2): Indicates that this control unit is operational."
     ::= { sdlcCuEntry 41 }


sdlcCuDiscReasonCode OBJECT-TYPE
     SYNTAX    INTEGER (1..20)
     ACCESS    read-only
     STATUS    mandatory
     DESCRIPTION
"Provides the reason code which indicates why this SLDC control unit was 
disconnected."
     ::= { sdlcCuEntry 42 }


sdlcCuSnalcDiscReasonCode OBJECT-TYPE
     SYNTAX    INTEGER (1..20)
     ACCESS    read-only
     STATUS    mandatory
     DESCRIPTION
"Provides the reason code which indicates why the SNA Link Conversion 
layer disconnected this SLDC control unit."
::= { sdlcCuEntry 43 }


sdlcCuConnectionStatus OBJECT-TYPE
     SYNTAX    INTEGER {
                    down      (1),
                    up        (2)
                    }
     ACCESS    read-only
     STATUS    mandatory
     DESCRIPTION
"Indicates the state of the SNA link convergence connection for this 
control unit.

Options:
up (1): Indicates that the SNA link convergence connection is operational.

down (2): Indicates that SNA link convergence link layer connection is not 
operational."
     ::={ sdlcCuEntry 44 }


sdlcCuFramesInTransmitQueue OBJECT-TYPE
     SYNTAX    Counter
     ACCESS    read-only
     STATUS    mandatory
     DESCRIPTION
"Indicates the number of frames currently in the transmit queue for this 
control unit. The number of frames should be less than 
sdlcCuTransmitWindow. If not, there may be a problem with the link."
     ::= { sdlcCuEntry 50 }

sdlcCuTxFrames OBJECT-TYPE
     SYNTAX    Counter
     ACCESS    read-only
     STATUS    mandatory
     DESCRIPTION
"If associated with a TIU service access point, this object indicates the 
number of information frames transmitted to this control unit.

If associated with an HIU service access point, this object indicates the 
number of information frames transmitted to the host by this emulated 
control unit. "
     ::= { sdlcCuEntry 51 }


sdlcCuRxFrames OBJECT-TYPE
     SYNTAX    Counter
     ACCESS    read-only
     STATUS    mandatory
     DESCRIPTION
"If associated with a TIU service access point, this object indicates the 
number of information frames received from this control unit.

If associated with an HIU service access point, this object indicates the 
number of information frames received from the host by this emulated 
control unit. "
     ::= { sdlcCuEntry 52 }


sdlcCuTimeOuts OBJECT-TYPE
     SYNTAX    Counter
     ACCESS    read-only
     STATUS    mandatory
     DESCRIPTION
"This object applies only if this entry is associated with a TIU service 
access point.

Indicates the number of times the sdlcCuPollAckTimer and the 
sdlcCuSlowPollTimer have expired."
     ::= { sdlcCuEntry 55 }


sdlcCuSnrmCount OBJECT-TYPE
     SYNTAX    Counter
     ACCESS    read-only
     STATUS    mandatory
     DESCRIPTION
"If associated with a TIU service access point, this object indicates the 
number of SNRM frames transmitted to this control unit.

If associated with an HIU service access point, this object indicates the 
number of SNRM frames received from the host by this emulated control 
unit. "
     ::= { sdlcCuEntry 56 }


sdlcCuXidCommand OBJECT-TYPE
     SYNTAX    Counter
     ACCESS    read-only
     STATUS    mandatory
     DESCRIPTION
"If associated with a TIU service access point, this object indicates the 
number of XID frames transmitted to this control unit.

If associated with an HIU service access point, this object indicates the 
number of XID frames received from the host by this emulated control 
unit."
     ::= { sdlcCuEntry 57 }


sdlcCuXidResponse OBJECT-TYPE
     SYNTAX    Counter
     ACCESS    read-only
     STATUS    mandatory
     DESCRIPTION
"If associated with a TIU service access point, this object indicates the 
number of SNRM frames transmitted to this control unit.

If associated with an HIU service access point, this object indicates the 
number of SNRM frames received from the host by this emulated control 
unit. "
     ::= { sdlcCuEntry 58 }


sdlcCuUnnumberedAcks OBJECT-TYPE
     SYNTAX    Counter
     ACCESS    read-only
     STATUS    mandatory
     DESCRIPTION
"If associated with a TIU service access point, this object indicates the 
number of UA responses received from this control unit.

If associated with an HIU service access point, this object indicates the 
number of UA responses transmitted to the host by this emulated control 
unit. "
     ::= { sdlcCuEntry 59 }


sdlcCuRetransmission OBJECT-TYPE
     SYNTAX    Counter
     ACCESS    read-only
     STATUS    mandatory
     DESCRIPTION
"If associated with a TIU service access point, this object indicates the 
number of information frames retransmitted to this control unit.

If associated with an HIU service access point, this object indicates the 
number of information frames retransmitted to the host by this emulated 
control unit. "
     ::= { sdlcCuEntry 60 }


sdlcCuDisconnectCount OBJECT-TYPE
     SYNTAX    Counter
     ACCESS    read-only
     STATUS    mandatory
     DESCRIPTION
"If associated with a TIU service access point, this object indicates the 
number of DISC commands transmitted to this control unit.

If associated with an HIU service access point, this object indicates the 
number of DISC commands received from the host by this emulated control 
unit. "
     ::= { sdlcCuEntry 61 }


sdlcCuDisconnectModeCount OBJECT-TYPE
     SYNTAX    Counter
     ACCESS    read-only
     STATUS    mandatory
     DESCRIPTION
"This object applies only if this entry is associated with a TIU service 
access point.

Indicates the total number of DM (disconnect mode) response frames 
received from this control unit."
     ::= { sdlcCuEntry 62 }


sdlcCuTransmittedRNR OBJECT-TYPE
     SYNTAX    Counter
     ACCESS    read-only
     STATUS    mandatory
     DESCRIPTION
"If associated with a TIU service access point, this object indicates the 
number of RNR frames transmitted to this control unit.

If associated with an HIU service access point, this object indicates the 
number of RNR frames transmitted to the host by this emulated control 
unit. "
     ::= { sdlcCuEntry 63 }


sdlcCuReceivedRNR OBJECT-TYPE
     SYNTAX    Counter
     ACCESS    read-only
     STATUS    mandatory
     DESCRIPTION
"If associated with a TIU service access point, this object indicates the 
number of RNR frames received from this control unit.

If associated with an HIU service access point, this object indicates the 
number of RNR frames received from the host by this emulated control unit. 
"
     ::= { sdlcCuEntry 64 }


sdlcCuFrameRejects OBJECT-TYPE
     SYNTAX    Counter
     ACCESS    read-only
     STATUS    mandatory
     DESCRIPTION
"If associated with a TIU service access point, this object indicates the 
number of FRMR response commands received from this control unit.

If associated with an HIU service access point, this object indicates the 
number of FRMR response commands transmitted to the host by this emulated 
control unit. "
     ::= { sdlcCuEntry 65 }


sdlcCuRemoteDisc OBJECT-TYPE
     SYNTAX    Counter
     ACCESS    read-only
     STATUS    mandatory
     DESCRIPTION
"This object applies only if this entry is associated with an TIU service 
access point.

Indicates the number of DISC frames transmitted by this control unit."
     ::= { sdlcCuEntry 66}


sdlcCuConnectionRequest OBJECT-TYPE
     SYNTAX    Counter
     ACCESS    read-only
     STATUS    mandatory
     DESCRIPTION
"Indicates the number of connections requested by the SNA link conversion 
layer for this control unit."
     ::= { sdlcCuEntry 67}


sdlcCuDisconnectionRequest OBJECT-TYPE
     SYNTAX    Counter
     ACCESS    read-only
     STATUS    mandatory
     DESCRIPTION
"Indicates the number of connection clear requests sent by the SNA link 
conversion layer for this control unit."
     ::= { sdlcCuEntry 68}

sdlcCuDisconnectionIndication OBJECT-TYPE
     SYNTAX    Counter
     ACCESS    read-only
     STATUS    mandatory
     DESCRIPTION
"Indicates the number of connection cleared messages sent to the SNA link 
conversion layer for this control unit."
     ::= { sdlcCuEntry 69}
END
