XYLAN-VAP-MIB DEFINITIONS ::= BEGIN

	--  RCSID information

	--  xylan-vap.mib
	--  Revision: 1.00
	--  Date: Dec 11, 1996

	--  Alcatel Internetworking, Inc.
	--  26801 W. Agoura Road
	--  Calabasas, CA 91301
	--  (818) 880-3500
	--  support@ind.alcatel.com

	--  This module provides authoritative definitions for Alcatel Internetworking, Inc.
	--  enterprise-specific virtual lan advertisement protocol MIB.

	--  This module will be extended, as needed.


	--  Alcatel Internetworking, Inc. reserves the right to make changes in 
	--  specification and other information contained in this document 
	--  without prior notice.  The reader should consult Alcatel Internetworking,
	--  Inc. to determine whether any such changes have been made.
	--  Current MIBs are availible from the following URLs:
	--		ftp://ftp.ind.alcatel.com/pub/products/mibs
	--		http://www.ind.alcatel.com

	--  In no event shall Alcatel Internetworking, Inc. be liable for any incidental, 
	--  indirect, special, or consequential damages whatsoever (including 
	--  but not limited to lost profits) arising out of or related to this
	--  document or the information contained in it, even if Alcatel Internetworking,
	--  Inc. has been advised of, known, or should have known, the 
	--  possibility of such damages.

	--  Alcatel Internetworking, Inc. grants vendors, end-users, and other interested
	--  parties a non-exclusive license to use this Specification in connection
	--  with the management of Alcatel Internetworking, Inc. products.

	--  Copyright (C) 1994, Alcatel Internetworking, Inc. All Rights Reserved.

	IMPORTS
		IpAddress
			FROM RFC1155-SMI
		OBJECT-TYPE
			FROM RFC-1212
		MacAddress
			FROM BRIDGE-MIB
		xylanVapArch
			FROM XYLAN-BASE-MIB
			;

	--  This MIB module uses the extended OBJECT-TYPE macro as defined in
	--  RFC 1212 (but known in the epilog files under RFC1213-SMI...)


	--  groups within the xylanVapArch mib

	xVapInfo		OBJECT IDENTIFIER ::= { xylanVapArch 1 }
	
	--  type codes

	XylanVapAdminStatCodes ::= INTEGER {
		disable(1),
	    	enable(2),
	        partial(3)
	} 	

	--  xVapInfo group.  This group contains the global Virtual LAN
	--  Advertisement Protocol information data.
	--  Implementation of this group is mandatory.

      xVapAdmStatus  OBJECT-TYPE
          SYNTAX  XylanVapAdminStatCodes
          ACCESS  read-write
	    STATUS  mandatory
          DESCRIPTION
             "The administrative state which can be set by
             configuration. Disable(1) will disable VAP from running
             on this device. Enable(2) will enable VAP to run on this 
             device. Partial will enable the adjacency portion of VAP only."
	    ::= { xVapInfo 1 }


	xVapTable  OBJECT-TYPE
	    SYNTAX  SEQUENCE OF VapEntry
	    ACCESS  not-accessible
	    STATUS  mandatory
	    DESCRIPTION
		 "A list of VAP entries for this physical OmniSwitch."
	    ::= { xVapInfo 2 }

	xVapEntry  OBJECT-TYPE
	    SYNTAX  VapEntry
	    ACCESS  not-accessible
	    STATUS  mandatory
	    DESCRIPTION
		 "A VAP entry." 
	    INDEX { xVapMACAddress, xVapSlot, xVapPort }
	    ::= { xVapTable 1 }

	VapEntry ::= SEQUENCE {
	    xVapPrimaryAddress
		IpAddress,
	    xVapSecondaryAddress
            IpAddress,
	    xVapSlot
		INTEGER,
	    xVapPort
	      INTEGER,
	    xVapMACAddress
		MacAddress,
	    xVapGroupId
		INTEGER
	   }

	xVapPrimaryAddress  OBJECT-TYPE
	    SYNTAX  IpAddress
	    ACCESS  read-only
	    STATUS  mandatory
	    DESCRIPTION
		 "The Primary IP address of adjacent neighbor OmniSwitch."
	    ::= { xVapEntry 1 }

	xVapSecondaryAddress  OBJECT-TYPE
	    SYNTAX  IpAddress
	    ACCESS  read-only
	    STATUS  mandatory
	    DESCRIPTION
		 "The Secondary IP address of adjacent neighbor OmniSwitch."
	    ::= { xVapEntry 2 }

	xVapSlot  OBJECT-TYPE
	    SYNTAX  INTEGER (1..9)
	    ACCESS  read-only
	    STATUS  mandatory
	    DESCRIPTION
		 "The Slot the VAP frame was received on."
	    ::= { xVapEntry 3 }
	
	xVapPort  OBJECT-TYPE
	    SYNTAX  INTEGER (1..256)
	    ACCESS  read-only
	    STATUS  mandatory
	    DESCRIPTION
		 "The Port the VAP frame was received on."
	    ::= { xVapEntry 4 }

	xVapMACAddress  OBJECT-TYPE
	    SYNTAX  MacAddress
	    ACCESS  read-only
	    STATUS  mandatory
	    DESCRIPTION
		"The MAC address of the host unit that is being
		 mapped to a VLAN."
	    ::= { xVapEntry 5 }

	 xVapGroupId  OBJECT-TYPE
            SYNTAX  INTEGER
            ACCESS  read-only
            STATUS  mandatory
            DESCRIPTION
		  "The port Group Identification."
	      ::= { xVapEntry 6 }

END
