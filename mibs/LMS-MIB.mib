LMS-MIB DEFINITIONS ::= 
BEGIN

    IMPORTS
    OBJECT-TYPE         FROM RFC-1212
    DisplayString       FROM RFC-1213
    enterprises         FROM RFC1155-SMI;

--  OBJECTS
    emersonESNA         OBJECT IDENTIFIER ::= { enterprises 885 }
    lms		OBJECT IDENTIFIER ::= { emersonESNA 2 }
    lmsSystem       OBJECT IDENTIFIER ::= { lms 1 }
    lmsCounts       OBJECT IDENTIFIER ::= { lms 2 }
    lmsChannels     OBJECT IDENTIFIER ::= { lms 3 }
    lmsTraps        OBJECT IDENTIFIER ::= { lms 5 }

--  ENTRIES
    binaryChannelNumber OBJECT-TYPE
        SYNTAX INTEGER
        ACCESS read-only
        STATUS mandatory
        DESCRIPTION
            "The number of Binary channels in the system."
    ::= { lmsCounts 1 }

    analogChannelNumber OBJECT-TYPE
        SYNTAX INTEGER
        ACCESS read-only
        STATUS mandatory
        DESCRIPTION
            "The number of Analog channels in the system."
    ::= { lmsCounts  2 }

    relayChannelNumber OBJECT-TYPE
        SYNTAX INTEGER
        ACCESS read-only
        STATUS mandatory
        DESCRIPTION
            "The number of Relay channels in the system."
    ::= { lmsCounts  3 }

    ledChannelNumber OBJECT-TYPE
        SYNTAX INTEGER
        ACCESS read-only
        STATUS mandatory
        DESCRIPTION
            "The number of LED channels in the system."
    ::= { lmsCounts  4 }

    energyChannelNumber OBJECT-TYPE
        SYNTAX INTEGER
        ACCESS read-only
        STATUS mandatory
        DESCRIPTION
            "The number of Energy Management channels in the system."
    ::= { lmsCounts  5 }

    functionChannelNumber OBJECT-TYPE
        SYNTAX INTEGER
        ACCESS read-only
        STATUS mandatory
        DESCRIPTION
            "The number of Function channels in the system."
    ::= { lmsCounts  6 }

-- Binary Channel Alarm Information
    lmsBinaryAlarmTable OBJECT-TYPE
        SYNTAX SEQUENCE OF MarconiLMSBinaryAlarmEntry
        ACCESS not-accessible
        STATUS mandatory
        DESCRIPTION    "The table entry for a Binary Alarm"
    ::= { lmsTraps 11 }

    lmsBinaryAlarmEntry OBJECT-TYPE
        SYNTAX MarconiLMSBinaryAlarmEntry
        ACCESS not-accessible
        STATUS mandatory
        DESCRIPTION     
            "An entry containing the information returned by a Binary Trap"
        INDEX { binaryAlarmIndex }
    ::= { lmsBinaryAlarmTable 1 }

    MarconiLMSBinaryAlarmEntry ::= SEQUENCE
    {
        binaryAlarmIndex        DisplayString (SIZE(0..5)),
        binaryAlarmName         DisplayString (SIZE(0..30)),
        binaryAlarmStatus       DisplayString (SIZE(0..8)),
        binaryAlarmAlarmStatus  DisplayString (SIZE(0..8)),
        binaryAlarmClass        DisplayString (SIZE(0..5)),
        binaryAlarmReportType   DisplayString (SIZE(0..10)),
        binaryAlarmDuration     DisplayString (SIZE(0..8))
    }

    binaryAlarmIndex OBJECT-TYPE
        SYNTAX DisplayString    (SIZE(0..5))
        ACCESS                  read-only
        STATUS                  mandatory
        DESCRIPTION             
        	"The Binary channel number"
    ::= { lmsBinaryAlarmEntry 1 }

    binaryAlarmName OBJECT-TYPE
        SYNTAX DisplayString    (SIZE(0..30))
        ACCESS                  read-only
        STATUS                  mandatory
        DESCRIPTION             
        	"The Binary channel name"
    ::= { lmsBinaryAlarmEntry 2 }

    binaryAlarmStatus OBJECT-TYPE
        SYNTAX DisplayString    (SIZE(0..8))
        ACCESS                  read-only
        STATUS                  mandatory
        DESCRIPTION             
        	"The Binary channel state (CC=voltage applied)"
    ::= { lmsBinaryAlarmEntry 3 }

    binaryAlarmAlarmStatus OBJECT-TYPE
        SYNTAX DisplayString    (SIZE(0..8))
        ACCESS                  read-only
        STATUS                  mandatory
        DESCRIPTION             
        	"The Binary channel alarm status"
    ::= { lmsBinaryAlarmEntry 4 }

    binaryAlarmClass OBJECT-TYPE
        SYNTAX DisplayString    (SIZE(0..5))
        ACCESS                  read-only
        STATUS                  mandatory
        DESCRIPTION             
        	"The Binary channel alarm class"
    ::= { lmsBinaryAlarmEntry 5 }

    binaryAlarmReportType OBJECT-TYPE
        SYNTAX DisplayString    (SIZE(0..10))
        ACCESS                  read-only
        STATUS                  mandatory
        DESCRIPTION             
        	"The Binary channel alarm condition"
    ::= { lmsBinaryAlarmEntry 6 }

    binaryAlarmDuration OBJECT-TYPE
        SYNTAX DisplayString    (SIZE(0..8))
        ACCESS                  read-only
        STATUS                  mandatory
        DESCRIPTION             
        	"The length of time the Binary alarm has been active"
    ::= { lmsBinaryAlarmEntry 7 }

-- Binary Channel Information
    lmsBinaryChannelTable OBJECT-TYPE
        SYNTAX SEQUENCE OF MarconiLMSBinaryChannelEntry
        ACCESS 					not-accessible
        STATUS 					mandatory
        DESCRIPTION     
        	"The table listing for the Binary channel information"
    ::= { lmsChannels 1 }
    
    lmsBinaryChannelEntry OBJECT-TYPE
        SYNTAX MarconiLMSBinaryChannelEntry
        ACCESS not-accessible
        STATUS mandatory
        DESCRIPTION
            "An entry containing information about a individual Binary channel."
        INDEX { binaryChannelIndex }
    ::= { lmsBinaryChannelTable 1 }

    MarconiLMSBinaryChannelEntry ::= SEQUENCE
    {
        binaryChannelIndex       DisplayString (SIZE(0..5)),
        binaryChannelName        DisplayString (SIZE(0..30)),
        binaryChannelStatus      DisplayString (SIZE(0..8)),
        binaryChannelAlarmStatus DisplayString (SIZE(0..8)),
        binaryChannelAlarmClass  DisplayString (SIZE(0..5))
    }

    binaryChannelIndex OBJECT-TYPE
        SYNTAX DisplayString (SIZE (0..5))
        ACCESS read-only
        STATUS mandatory
        DESCRIPTION
            "The Binary channel number"
    ::= { lmsBinaryChannelEntry 1 }

    binaryChannelName OBJECT-TYPE
        SYNTAX DisplayString (SIZE (0..30))
        ACCESS read-write
        STATUS mandatory
        DESCRIPTION
        	"The Binary channel name"
    ::= { lmsBinaryChannelEntry 2 }

    binaryChannelStatus OBJECT-TYPE
        SYNTAX DisplayString (SIZE (0..8))
        ACCESS read-only
        STATUS mandatory
        DESCRIPTION
        	"The Binary channel state (CC=voltage applied)"
    ::= { lmsBinaryChannelEntry 3 }

    binaryChannelAlarmStatus OBJECT-TYPE
        SYNTAX DisplayString (SIZE (0..8))
        ACCESS read-only
        STATUS mandatory
        DESCRIPTION
        	"The Binary channel alarm status"
    ::= { lmsBinaryChannelEntry 4 }

    binaryChannelAlarmClass OBJECT-TYPE
        SYNTAX DisplayString (SIZE (0..5))
        ACCESS read-only
        STATUS mandatory
        DESCRIPTION
			"The Binary channel alarm class"
    ::= { lmsBinaryChannelEntry 5 }    

-- Analog Channel Alarm Information
    lmsAnalogAlarmTable OBJECT-TYPE
        SYNTAX SEQUENCE OF MarconiLMSAnalogAlarmEntry
        ACCESS not-accessible
        STATUS mandatory
        DESCRIPTION    
        	"The table entry for an Analog channel Alarm"
    ::= { lmsTraps 10 }

    lmsAnalogAlarmEntry OBJECT-TYPE
        SYNTAX MarconiLMSAnalogAlarmEntry
        ACCESS not-accessible
        STATUS mandatory
        DESCRIPTION     
            "An entry containing the information returned by an Analog channel Trap"
        INDEX { analogAlarmIndex }
    ::= { lmsAnalogAlarmTable 1 }

    MarconiLMSAnalogAlarmEntry ::= SEQUENCE
    {
        analogAlarmIndex        DisplayString (SIZE(0..5)),
        analogAlarmName         DisplayString (SIZE(0..30)),
        analogAlarmValue        DisplayString (SIZE(0..8)),
        analogAlarmUnits        DisplayString (SIZE(0..4)),
        analogAlarmLimitValue   DisplayString (SIZE(0..8)),
        analogAlarmLimitType    INTEGER,
        analogAlarmLimitName    DisplayString (SIZE(0..10)),
		analogAlarmLimitClass	DisplayString (SIZE(0..5)),
        analogAlarmReportType   DisplayString (SIZE(0..10)),
        analogAlarmDuration     DisplayString (SIZE(0..8))
    }

    analogAlarmIndex OBJECT-TYPE
        SYNTAX DisplayString    (SIZE(0..5))
        ACCESS                  read-only
        STATUS                  mandatory
        DESCRIPTION
        	"The Analog channel number"
    ::= { lmsAnalogAlarmEntry 1 }

    analogAlarmName OBJECT-TYPE
        SYNTAX DisplayString    (SIZE(0..30))
        ACCESS                  read-only
        STATUS                  mandatory
        DESCRIPTION
        	"The Analog channel name"
    ::= { lmsAnalogAlarmEntry 2 }

    analogAlarmValue OBJECT-TYPE
        SYNTAX DisplayString    (SIZE(0..8))
        ACCESS                  read-only
        STATUS                  mandatory
        DESCRIPTION
        	"The Analog channel reading"
    ::= { lmsAnalogAlarmEntry 3 }

    analogAlarmUnits OBJECT-TYPE
        SYNTAX DisplayString    (SIZE(0..4))
        ACCESS                  read-only
        STATUS                  mandatory
        DESCRIPTION
        	"The Analog channel reading units of measurement"
    ::= { lmsAnalogAlarmEntry 4 }

    analogAlarmLimitValue OBJECT-TYPE
        SYNTAX DisplayString    (SIZE(0..8))
        ACCESS                  read-only
        STATUS                  mandatory
        DESCRIPTION
			"The Analog channel limit value"
    ::= { lmsAnalogAlarmEntry 5 }

    analogAlarmLimitType OBJECT-TYPE
        SYNTAX INTEGER
        ACCESS                  read-only
        STATUS                  mandatory
        DESCRIPTION
			"The Analog channel limit type"
    ::= { lmsAnalogAlarmEntry 6 }

    analogAlarmLimitName OBJECT-TYPE
        SYNTAX DisplayString    (SIZE(0..10))
        ACCESS                  read-only
        STATUS                  mandatory
        DESCRIPTION             
        	"The Analog channel limit name"
    ::= { lmsAnalogAlarmEntry 7 }

    analogAlarmLimitClass OBJECT-TYPE
        SYNTAX DisplayString    (SIZE(0..5))
        ACCESS                  read-only
        STATUS                  mandatory
        DESCRIPTION
        	"The Analog channel limit condition"
    ::= { lmsAnalogAlarmEntry 8 }

    analogAlarmReportType OBJECT-TYPE
        SYNTAX DisplayString    (SIZE(0..10))
        ACCESS                  read-only
        STATUS                  mandatory
        DESCRIPTION
        	"The Analog channel limit condition"
    ::= { lmsAnalogAlarmEntry 9 }

    analogAlarmDuration OBJECT-TYPE
        SYNTAX DisplayString    (SIZE(0..8))
        ACCESS                  read-only
        STATUS                  mandatory
        DESCRIPTION
        	"The length of time the Analog limit has been active"
    ::= { lmsAnalogAlarmEntry 10 }


-- Analog Channel Information
    lmsAnalogChannelTable OBJECT-TYPE
        SYNTAX SEQUENCE OF MarconiLMSAnalogChannelEntry
        ACCESS not-accessible
        STATUS mandatory
        DESCRIPTION     
        	"The table listing for the Analog channel information"
    ::= { lmsChannels 2 }
    
    lmsAnalogChannelEntry OBJECT-TYPE
        SYNTAX MarconiLMSAnalogChannelEntry
        ACCESS not-accessible
        STATUS mandatory
        DESCRIPTION
            "An entry containing information about an individual Analog channel."
        INDEX { analogChannelIndex }
    ::= { lmsAnalogChannelTable 1 }

    MarconiLMSAnalogChannelEntry ::= SEQUENCE
    {
        analogChannelIndex     	DisplayString (SIZE(0..5)),
        analogChannelName      	DisplayString (SIZE(0..30)),
        analogChannelValue     	DisplayString (SIZE(0..12)),
        analogChannelUnits    	DisplayString (SIZE(0..4)),
        analogChannelLimit1		DisplayString (SIZE(0..8)),
        analogChannelLimit2  	DisplayString (SIZE(0..8)),
        analogChannelLimit3  	DisplayString (SIZE(0..8)),
        analogChannelLimit4  	DisplayString (SIZE(0..8)),
        analogChannelAlarm		INTEGER
    }

    analogChannelIndex OBJECT-TYPE
        SYNTAX DisplayString (SIZE (0..5))
        ACCESS read-only
        STATUS mandatory
        DESCRIPTION
        	"The Analog channel number"
    ::= { lmsAnalogChannelEntry 1 }

    analogChannelName OBJECT-TYPE
        SYNTAX DisplayString (SIZE (0..30))
        ACCESS read-write
        STATUS mandatory
        DESCRIPTION
        	"The Analog channel name"
    ::= { lmsAnalogChannelEntry 2 }

    analogChannelValue OBJECT-TYPE
        SYNTAX DisplayString (SIZE(0..12))
        ACCESS read-only
        STATUS mandatory
        DESCRIPTION
        	"The Analog channel reading"
    ::= { lmsAnalogChannelEntry 3 }
    
    analogChannelUnits OBJECT-TYPE
        SYNTAX DisplayString (SIZE (0..4))
        ACCESS read-only
        STATUS mandatory
        DESCRIPTION
        	"The Analog channel reading units of measurement"
    ::= { lmsAnalogChannelEntry 4 }
    
    analogChannelLimit1 OBJECT-TYPE
        SYNTAX DisplayString (SIZE (0..8))
        ACCESS read-only
        STATUS mandatory
        DESCRIPTION
			"The Analog channel limit number one value"
    ::= { lmsAnalogChannelEntry 5 }
    
    analogChannelLimit2 OBJECT-TYPE
        SYNTAX DisplayString (SIZE (0..8))
        ACCESS read-only
        STATUS mandatory
        DESCRIPTION
			"The Analog channel limit number two value"
    ::= { lmsAnalogChannelEntry 6 }
    
    analogChannelLimit3 OBJECT-TYPE
        SYNTAX DisplayString (SIZE (0..8))
        ACCESS read-only
        STATUS mandatory
        DESCRIPTION
			"The Analog channel limit number three value"
    ::= { lmsAnalogChannelEntry 7 }
    
    analogChannelLimit4 OBJECT-TYPE
        SYNTAX DisplayString (SIZE (0..8))
        ACCESS read-only
        STATUS mandatory
        DESCRIPTION
			"The Analog channel limit number four value"
    ::= { lmsAnalogChannelEntry 8 }
    
    analogChannelAlarm OBJECT-TYPE
        SYNTAX INTEGER
        ACCESS read-only
        STATUS mandatory
        DESCRIPTION
        	"The Analog channel alarm status"
    ::= { lmsAnalogChannelEntry 9 }

-- Relay Channel Alarm Information
    lmsRelayAlarmTable OBJECT-TYPE
        SYNTAX SEQUENCE OF MarconiLMSRelayAlarmEntry
        ACCESS not-accessible
        STATUS mandatory
        DESCRIPTION    "The table entry for a Relay Alarm"
    ::= { lmsTraps 13 }

    lmsRelayAlarmEntry OBJECT-TYPE
        SYNTAX MarconiLMSRelayAlarmEntry
        ACCESS not-accessible
        STATUS mandatory
        DESCRIPTION     
            "An entry containing the information returned by a Relay Trap"
        INDEX { relayAlarmIndex }
    ::= { lmsRelayAlarmTable 1 }

    MarconiLMSRelayAlarmEntry ::= SEQUENCE
    {
        relayAlarmIndex        DisplayString (SIZE(0..5)),
        relayAlarmName         DisplayString (SIZE(0..30)),
        relayAlarmStatus       DisplayString (SIZE(0..8)),
        relayAlarmAlarmStatus  DisplayString (SIZE(0..8)),
        relayAlarmClass        DisplayString (SIZE(0..5)),
        relayAlarmReportType   DisplayString (SIZE(0..10)),
        relayAlarmDuration     DisplayString (SIZE(0..8))
    }

    relayAlarmIndex OBJECT-TYPE
        SYNTAX DisplayString    (SIZE(0..5))
        ACCESS                  read-only
        STATUS                  mandatory
        DESCRIPTION             
        	"The Relay channel number"
    ::= { lmsRelayAlarmEntry 1 }

    relayAlarmName OBJECT-TYPE
        SYNTAX DisplayString    (SIZE(0..30))
        ACCESS                  read-only
        STATUS                  mandatory
        DESCRIPTION             
        	"The Relay channel name"
    ::= { lmsRelayAlarmEntry 2 }

    relayAlarmStatus OBJECT-TYPE
        SYNTAX DisplayString    (SIZE(0..8))
        ACCESS                  read-only
        STATUS                  mandatory
        DESCRIPTION
        	"The Relay channel status (On, Forced, Programmed)"
    ::= { lmsRelayAlarmEntry 3 }

    relayAlarmAlarmStatus OBJECT-TYPE
        SYNTAX DisplayString    (SIZE(0..8))
        ACCESS                  read-only
        STATUS                  mandatory
        DESCRIPTION
        	"The Relay channel alarm status"
    ::= { lmsRelayAlarmEntry 4 }

    relayAlarmClass OBJECT-TYPE
        SYNTAX DisplayString    (SIZE(0..5))
        ACCESS                  read-only
        STATUS                  mandatory
        DESCRIPTION
			"The Relay channel alarm class"
    ::= { lmsRelayAlarmEntry 5 }

    relayAlarmReportType OBJECT-TYPE
        SYNTAX DisplayString    (SIZE(0..10))
        ACCESS                  read-only
        STATUS                  mandatory
        DESCRIPTION             
        	"The Relay channel alarm condition"
    ::= { lmsRelayAlarmEntry 6 }

    relayAlarmDuration OBJECT-TYPE
        SYNTAX DisplayString    (SIZE(0..8))
        ACCESS                  read-only
        STATUS                  mandatory
        DESCRIPTION             
        	"The length of time the Relay alarm has been active"
    ::= { lmsRelayAlarmEntry 7 }

-- Relay Channel Information
    lmsRelayChannelTable OBJECT-TYPE
        SYNTAX SEQUENCE OF MarconiLMSRelayChannelEntry
        ACCESS not-accessible
        STATUS mandatory
        DESCRIPTION     
        	"The table listing for the Relay channel information"
    ::= { lmsChannels 3 }
    
    lmsRelayChannelEntry OBJECT-TYPE
        SYNTAX MarconiLMSRelayChannelEntry
        ACCESS not-accessible
        STATUS mandatory
        DESCRIPTION
            "An entry containing information about an individual Relay channel."
        INDEX { relayChannelIndex }
    ::= { lmsRelayChannelTable 1 }

    MarconiLMSRelayChannelEntry ::= SEQUENCE
    {
        relayChannelIndex        DisplayString (SIZE(0..5)),
        relayChannelName         DisplayString (SIZE(0..30)),
        relayChannelStatus       DisplayString (SIZE(0..8)),
        relayChannelAlarmStatus  DisplayString (SIZE(0..8)),
        relayChannelAlarmClass   DisplayString (SIZE(0..5))
    }

    relayChannelIndex OBJECT-TYPE
        SYNTAX DisplayString (SIZE (0..5))
        ACCESS read-only
        STATUS mandatory
        DESCRIPTION
            "The Relay channel number"
    ::= { lmsRelayChannelEntry 1 }

    relayChannelName OBJECT-TYPE
        SYNTAX DisplayString (SIZE (0..30))
        ACCESS read-write
        STATUS mandatory
        DESCRIPTION             
        	"The Relay channel name"
    ::= { lmsRelayChannelEntry 2 }

    relayChannelStatus OBJECT-TYPE
        SYNTAX DisplayString (SIZE (0..8))
        ACCESS read-write
        STATUS mandatory
        DESCRIPTION
        	"The Relay channel status (On, Forced, Programmed)"
    ::= { lmsRelayChannelEntry 3 }

    relayChannelAlarmStatus OBJECT-TYPE
        SYNTAX DisplayString (SIZE (0..8))
        ACCESS read-write
        STATUS mandatory
        DESCRIPTION
        	"The Relay channel alarm status"
    ::= { lmsRelayChannelEntry 4 }

    relayChannelAlarmClass OBJECT-TYPE
        SYNTAX DisplayString (SIZE (0..5))
        ACCESS read-write
        STATUS mandatory
        DESCRIPTION
			"The Relay channel alarm class"
    ::= { lmsRelayChannelEntry 5 }
    
-- Led Channel Alarm Information
    lmsLedAlarmTable OBJECT-TYPE
        SYNTAX SEQUENCE OF MarconiLMSLedAlarmEntry
        ACCESS not-accessible
        STATUS mandatory
        DESCRIPTION    "The table entry for a Led Alarm"
    ::= { lmsTraps 1 }

    lmsLedAlarmEntry OBJECT-TYPE
        SYNTAX MarconiLMSLedAlarmEntry
        ACCESS not-accessible
        STATUS mandatory
        DESCRIPTION     
            "An entry containing the information returned by a LED Trap"
        INDEX { ledAlarmIndex }
    ::= { lmsLedAlarmTable 1 }

    MarconiLMSLedAlarmEntry ::= SEQUENCE
    {
        ledAlarmIndex        DisplayString (SIZE(0..5)),
        ledAlarmName         DisplayString (SIZE(0..30)),
        ledAlarmStatus       DisplayString (SIZE(0..8)),
        ledAlarmAlarmStatus  DisplayString (SIZE(0..8)),
        ledAlarmClass        DisplayString (SIZE(0..5)),
        ledAlarmReportType   DisplayString (SIZE(0..10)),
        ledAlarmDuration     DisplayString (SIZE(0..8))
    }

    ledAlarmIndex OBJECT-TYPE
        SYNTAX DisplayString    (SIZE(0..5))
        ACCESS                  read-only
        STATUS                  mandatory
        DESCRIPTION             
        	"The LED channel number"
    ::= { lmsLedAlarmEntry 1 }

    ledAlarmName OBJECT-TYPE
        SYNTAX DisplayString    (SIZE(0..30))
        ACCESS                  read-only
        STATUS                  mandatory
        DESCRIPTION             
        	"The LED channel name"
    ::= { lmsLedAlarmEntry 2 }

    ledAlarmStatus OBJECT-TYPE
        SYNTAX DisplayString    (SIZE(0..8))
        ACCESS                  read-only
        STATUS                  mandatory
        DESCRIPTION
        	"The LED channel status (On, Forced, Programmed)"
    ::= { lmsLedAlarmEntry 3 }

    ledAlarmAlarmStatus OBJECT-TYPE
        SYNTAX DisplayString    (SIZE(0..8))
        ACCESS                  read-only
        STATUS                  mandatory
        DESCRIPTION
        	"The LED channel alarm status"
    ::= { lmsLedAlarmEntry 4 }

    ledAlarmClass OBJECT-TYPE
        SYNTAX DisplayString    (SIZE(0..5))
        ACCESS                  read-only
        STATUS                  mandatory
        DESCRIPTION
			"The LED channel alarm class"
    ::= { lmsLedAlarmEntry 5 }

    ledAlarmReportType OBJECT-TYPE
        SYNTAX DisplayString    (SIZE(0..10))
        ACCESS                  read-only
        STATUS                  mandatory
        DESCRIPTION             
        	"The LED channel alarm condition"
    ::= { lmsLedAlarmEntry 6 }

    ledAlarmDuration OBJECT-TYPE
        SYNTAX DisplayString    (SIZE(0..8))
        ACCESS                  read-only
        STATUS                  mandatory
        DESCRIPTION             
        	"The length of time the LED alarm has been active"
    ::= { lmsLedAlarmEntry 7 }

-- Led Channel Information
    lmsLEDChannelTable OBJECT-TYPE
        SYNTAX SEQUENCE OF MarconiLMSLEDChannelEntry
        ACCESS not-accessible
        STATUS mandatory
        DESCRIPTION     
        	"The table listing for the LED channel information"
    ::= { lmsChannels 4 }
    
    lmsLEDChannelEntry OBJECT-TYPE
        SYNTAX MarconiLMSLEDChannelEntry
        ACCESS not-accessible
        STATUS mandatory
        DESCRIPTION
            "An entry containing information about an individual LED channel."
        INDEX { ledChannelIndex }
    ::= { lmsLEDChannelTable 1 }

    MarconiLMSLEDChannelEntry ::= SEQUENCE
    {
        ledChannelIndex         DisplayString (SIZE(0..5)),
        ledChannelName          DisplayString (SIZE(0..30)),
        ledChannelStatus        DisplayString (SIZE(0..8)),
        ledChannelAlarmStatus   DisplayString (SIZE(0..8)),
        ledChannelAlarmClass    DisplayString (SIZE(0..5))
    }

    ledChannelIndex OBJECT-TYPE
        SYNTAX DisplayString (SIZE (0..5))
        ACCESS read-only
        STATUS mandatory
        DESCRIPTION             
        	"The LED channel number"
    ::= { lmsLEDChannelEntry 1 }

    ledChannelName OBJECT-TYPE
        SYNTAX DisplayString (SIZE (0..30))
        ACCESS read-write
        STATUS mandatory
        DESCRIPTION             
        	"The LED channel name"
    ::= { lmsLEDChannelEntry 2 }

    ledChannelStatus OBJECT-TYPE
        SYNTAX DisplayString (SIZE (0..8))
        ACCESS read-write
        STATUS mandatory
        DESCRIPTION
        	"The LED channel status (On, Forced, Programmed)"
    ::= { lmsLEDChannelEntry 3 }

    ledChannelAlarmStatus OBJECT-TYPE
        SYNTAX DisplayString (SIZE (0..8))
        ACCESS read-write
        STATUS mandatory
        DESCRIPTION
        	"The LED channel alarm status"
    ::= { lmsLEDChannelEntry 4 }

    ledChannelAlarmClass OBJECT-TYPE
        SYNTAX DisplayString (SIZE (0..5))
        ACCESS read-write
        STATUS mandatory
        DESCRIPTION
			"The LED channel alarm class"
    ::= { lmsLEDChannelEntry 5 }


-- Energy Channel Information
    lmsEnergyChannelTable OBJECT-TYPE
        SYNTAX SEQUENCE OF MarconiLMSEnergyChannelEntry
        ACCESS not-accessible
        STATUS mandatory
        DESCRIPTION     
        	"The table listing for the Energy Management channel information"
    ::= { lmsChannels 5 }
    
    lmsEnergyChannelEntry OBJECT-TYPE
        SYNTAX MarconiLMSEnergyChannelEntry
        ACCESS not-accessible
        STATUS mandatory
        DESCRIPTION
            "An entry containing information about an individual Energy Management channel."
        INDEX { energyChannelIndex }
    ::= { lmsEnergyChannelTable 1 }

    MarconiLMSEnergyChannelEntry ::= SEQUENCE
    {
        energyChannelIndex DisplayString (SIZE(0..5)),
        energyChannelName  DisplayString (SIZE(0..30)),
	energyCapacity     DisplayString (SIZE(0..8)),
	energyShunt        DisplayString (SIZE(0..8)),
	energyRFA          INTEGER,
	energyTR           INTEGER
    }

    energyChannelIndex OBJECT-TYPE
        SYNTAX DisplayString (SIZE (0..5))
        ACCESS read-only
        STATUS mandatory
        DESCRIPTION             
        	"The Energy Management channel number"
    ::= { lmsEnergyChannelEntry 1 }

    energyChannelName OBJECT-TYPE
        SYNTAX DisplayString (SIZE (0..30))
        ACCESS read-write
        STATUS mandatory
        DESCRIPTION             
        	"The Energy Management channel name"
    ::= { lmsEnergyChannelEntry 2 }

    energyCapacity OBJECT-TYPE
        SYNTAX DisplayString (SIZE (0..8))
        ACCESS read-only
        STATUS mandatory
        DESCRIPTION             
        	"The rated capacity of the rectifier associated with the Energy Management channel"
    ::= { lmsEnergyChannelEntry 3 }

    energyShunt OBJECT-TYPE
        SYNTAX DisplayString (SIZE (0..8))
        ACCESS read-only
        STATUS mandatory
        DESCRIPTION             
        	"The current load on the rectifier associated with the Energy Management channel"
    ::= { lmsEnergyChannelEntry 4 }

    energyRFA OBJECT-TYPE
        SYNTAX INTEGER
        ACCESS read-only
        STATUS mandatory
        DESCRIPTION             
        	"The current operational status of the rectifier associated with the Energy Management channel"
    ::= { lmsEnergyChannelEntry 5 }

    energyTR OBJECT-TYPE
        SYNTAX INTEGER
        ACCESS read-only
        STATUS mandatory
        DESCRIPTION             
        	"The current control status of the rectifier associated with the Energy Management channel"
    ::= { lmsEnergyChannelEntry 6 }
    
-- Function Channel Information
    lmsFunctionChannelTable OBJECT-TYPE
        SYNTAX SEQUENCE OF MarconiLMSFunctionChannelEntry
        ACCESS not-accessible
        STATUS mandatory
        DESCRIPTION     "The table entry for a Function channel Alarm"
    ::= { lmsChannels 6 }
    
    lmsFunctionChannelEntry OBJECT-TYPE
        SYNTAX MarconiLMSFunctionChannelEntry
        ACCESS not-accessible
        STATUS mandatory
        DESCRIPTION     
            "An entry containing the information returned by a Function channel Trap"
        INDEX { functionChannelIndex }
    ::= { lmsFunctionChannelTable 1 }

    MarconiLMSFunctionChannelEntry ::= SEQUENCE
    {
        functionChannelIndex   	DisplayString (SIZE(0..5)),
        functionChannelName    	DisplayString (SIZE(0..30)),
        functionChannelValue   	DisplayString (SIZE(0..8)),
        functionChannelUnits   	DisplayString (SIZE(0..4)),
        functionChannelLimit1  	DisplayString (SIZE(0..8)),
        functionChannelLimit2  	DisplayString (SIZE(0..8)),
        functionChannelLimit3  	DisplayString (SIZE(0..8)),
        functionChannelLimit4  	DisplayString (SIZE(0..8)),
        functionChannelAlarm   	INTEGER
    }

    functionChannelIndex OBJECT-TYPE
        SYNTAX DisplayString (SIZE (0..5))
        ACCESS read-only
        STATUS mandatory
        DESCRIPTION
        	"The Function channel number"
    ::= { lmsFunctionChannelEntry 1 }

    functionChannelName OBJECT-TYPE
        SYNTAX DisplayString (SIZE (0..30))
        ACCESS read-write
        STATUS mandatory
        DESCRIPTION
        	"The Function channel name"
    ::= { lmsFunctionChannelEntry 2 }

    functionChannelValue OBJECT-TYPE
        SYNTAX DisplayString (SIZE(0..8))
        ACCESS read-only
        STATUS mandatory
        DESCRIPTION
        	"The Function channel reading"
    ::= { lmsFunctionChannelEntry 3 }
    
    functionChannelUnits OBJECT-TYPE
        SYNTAX DisplayString (SIZE (0..4))
        ACCESS read-only
        STATUS mandatory
        DESCRIPTION
        	"The Function channel reading units of measurement"
    ::= { lmsFunctionChannelEntry 4 }
    
    functionChannelLimit1 OBJECT-TYPE
        SYNTAX DisplayString (SIZE (0..8))
        ACCESS read-only
        STATUS mandatory
        DESCRIPTION
			"The Function channel limit number one value"
    ::= { lmsFunctionChannelEntry 5 }
    
    functionChannelLimit2 OBJECT-TYPE
        SYNTAX DisplayString (SIZE (0..8))
        ACCESS read-only
        STATUS mandatory
        DESCRIPTION
			"The Function channel limit number two value"
    ::= { lmsFunctionChannelEntry 6 }
    
    functionChannelLimit3 OBJECT-TYPE
        SYNTAX DisplayString (SIZE (0..8))
        ACCESS read-only
        STATUS mandatory
        DESCRIPTION
			"The Function channel limit number three value"
    ::= { lmsFunctionChannelEntry 7 }
    
    functionChannelLimit4 OBJECT-TYPE
        SYNTAX DisplayString (SIZE (0..8))
        ACCESS read-only
        STATUS mandatory
        DESCRIPTION
			"The Function channel limit number four value"
    ::= { lmsFunctionChannelEntry 8 }
    
    functionChannelAlarm OBJECT-TYPE
        SYNTAX INTEGER
        ACCESS read-only
        STATUS mandatory
        DESCRIPTION
        	"The Function channel alarm status"
    ::= { lmsFunctionChannelEntry 9 }

-- Function Channel Alarm Information
    lmsFunctionAlarmTable OBJECT-TYPE
        SYNTAX SEQUENCE OF MarconiLMSFunctionAlarmEntry
        ACCESS not-accessible
        STATUS mandatory
        DESCRIPTION    
	    	"The table entry for a Function channel Alarm"
    ::= { lmsTraps 12 }

    lmsFunctionAlarmEntry OBJECT-TYPE
        SYNTAX MarconiLMSFunctionAlarmEntry
        ACCESS not-accessible
        STATUS mandatory
        DESCRIPTION     
            "An entry containing the information returned by a Function channel Trap"
        INDEX { functionAlarmIndex }
    ::= { lmsFunctionAlarmTable 1 }

    MarconiLMSFunctionAlarmEntry ::= SEQUENCE
    {
        functionAlarmIndex		DisplayString (SIZE(0..5)),
        functionAlarmName		DisplayString (SIZE(0..30)),
        functionAlarmValue		DisplayString (SIZE(0..8)),
        functionAlarmUnits     	DisplayString (SIZE(0..5)),
        functionAlarmLimitValue	DisplayString (SIZE(0..16)),
        functionAlarmLimitType	INTEGER,
        functionAlarmLimitName 	DisplayString (SIZE(0..12)),
        functionAlarmLimitClass	DisplayString (SIZE(0..5)),
        functionAlarmReportType	DisplayString (SIZE(0..10)),
        functionAlarmDuration  	DisplayString (SIZE(0..8))
    }
    functionAlarmIndex OBJECT-TYPE
        SYNTAX DisplayString    (SIZE(0..5))
        ACCESS                  read-only
        STATUS                  mandatory
        DESCRIPTION
        	"The Function channel number"
    ::={ lmsFunctionAlarmEntry 1 }

    functionAlarmName OBJECT-TYPE
        SYNTAX DisplayString    (SIZE(0..30))
        ACCESS                  read-only
        STATUS                  mandatory
        DESCRIPTION
        	"The Function channel name"
    ::={ lmsFunctionAlarmEntry 2 }

    functionAlarmValue OBJECT-TYPE
        SYNTAX DisplayString    (SIZE(0..8))
        ACCESS                  read-only
        STATUS                  mandatory
        DESCRIPTION
        	"The Function channel reading"
    ::={ lmsFunctionAlarmEntry 3 }

    functionAlarmUnits OBJECT-TYPE
        SYNTAX DisplayString    (SIZE(0..5))
        ACCESS                  read-only
        STATUS                  mandatory
        DESCRIPTION
        	"The Function channel reading units of measurement"
    ::={ lmsFunctionAlarmEntry 4 }

    functionAlarmLimitValue OBJECT-TYPE
        SYNTAX DisplayString    (SIZE(0..16))
        ACCESS                  read-only
        STATUS                  mandatory
        DESCRIPTION
			"The Function channel limit value"
    ::={ lmsFunctionAlarmEntry 5 }

    functionAlarmLimitType OBJECT-TYPE
        SYNTAX INTEGER
        ACCESS                  read-only
        STATUS                  mandatory
        DESCRIPTION
			"The Function channel limit value"
    ::={ lmsFunctionAlarmEntry 6 }

    functionAlarmLimitName OBJECT-TYPE
        SYNTAX DisplayString    (SIZE(0..12))
        ACCESS                  read-only
        STATUS                  mandatory
        DESCRIPTION             
        	"The Function channel limit name"
    ::={ lmsFunctionAlarmEntry 7 }

    functionAlarmLimitClass OBJECT-TYPE
        SYNTAX DisplayString    (SIZE(0..5))
        ACCESS                  read-only
        STATUS                  mandatory
        DESCRIPTION             
        	"The Function channel alarm class"
    ::={ lmsFunctionAlarmEntry 8 }

    functionAlarmReportType OBJECT-TYPE
        SYNTAX DisplayString    (SIZE(0..10))
        ACCESS                  read-only
        STATUS                  mandatory
        DESCRIPTION
        	"The Function channel limit condition"
    ::= { lmsFunctionAlarmEntry 9 }

    functionAlarmDuration OBJECT-TYPE
        SYNTAX DisplayString    (SIZE(0..8))
        ACCESS                  read-only
        STATUS                  mandatory
        DESCRIPTION
        	"The length of time the Function limit has been active"
    ::= { lmsFunctionAlarmEntry 10 }


END
