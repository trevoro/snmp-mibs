PANDATEL-FOBUS-MODEM-MIB DEFINITIONS ::= BEGIN

 -- This is the private mib group section for the FOBUS modems.
 -- Because these modems must be installed in the PANDATEL modem rack
 -- the PANDATEL-MODEM-MIB also applies.

 -- Ver.1.07    Sep.13.1999

        IMPORTS
                enterprises
                        FROM RFC1155-SMI
                DisplayString
                        FROM RFC1213-MIB
                OBJECT-TYPE
                        FROM RFC-1212
                mdmSpecifics, device-id
                        FROM PANDATEL-MODEM-MIB;

-- ********************** THE MDM-FOBUS SUBTREE ******************************

-- the specific identifier is identical to the modem type integer
-- of the FOBUS modem entries in the PANDATEL-MODEM-MIB mdmModemTable.

fobus-modem      OBJECT IDENTIFIER ::= { device-id 501 }     -- chassis-mib

fobus            OBJECT IDENTIFIER ::= { mdmSpecifics 501 }  -- this subtree

fobusModemTable OBJECT-TYPE
        SYNTAX  SEQUENCE OF FobusTableEntry
        ACCESS  not-accessible
        STATUS  mandatory
        DESCRIPTION
                "This table contains information about all FOBUS units in all racks."
        ::= { fobus 1 }

fobusTableEntry OBJECT-TYPE
        SYNTAX  FobusTableEntry
        ACCESS  not-accessible
        STATUS  mandatory
        DESCRIPTION
                "The index of the table."
        INDEX   { mdmRack, mdmModem, mdmPosition }
        ::= { fobusModemTable 1 }

FobusTableEntry ::= SEQUENCE {
        mdmRack
                INTEGER,
        mdmModem
                INTEGER,
        mdmPosition
                INTEGER,
        mdmModemName
                DisplayString,
        mdmBackupStatus
                INTEGER,
        mdmActiveLink
                INTEGER,
        mdmOperationMode
                INTEGER,
        mdmAlarmConditionPort1
                INTEGER,
        mdmAlarmConditionPort2
                INTEGER,
        mdmAlarmConditionPort3
                INTEGER,
        mdmTXLaserStatusPort2
                INTEGER,
        mdmTXLaserStatusPort3
                INTEGER
        }

mdmRack OBJECT-TYPE
        SYNTAX  INTEGER
        ACCESS  read-only
        STATUS  mandatory
        DESCRIPTION
                "The index of the rack where the unit is installed."
        ::= { fobusTableEntry 1 }

mdmModem OBJECT-TYPE
        SYNTAX  INTEGER
        ACCESS  read-only
        STATUS  mandatory
        DESCRIPTION
                "This entry displays the slot number where the corresponding
                 unit is installed in the rack."
        ::= { fobusTableEntry 2 }

mdmPosition OBJECT-TYPE
        SYNTAX  INTEGER {
                local       (1),
                remote      (2)
                }
        ACCESS  read-only
        STATUS  mandatory
        DESCRIPTION
                "This entry displays the location of the corresponding unit:
                 'local' or 'remote'. The unit which is plugged into a managed
                 rack is 'local', the counterpart is 'remote'."
        ::= { fobusTableEntry 3 }

mdmModemName OBJECT-TYPE
        SYNTAX  DisplayString
        ACCESS  read-only
        STATUS  mandatory
        DESCRIPTION
                "The verbal name of this unit."
        ::= { fobusTableEntry 5 }

mdmBackupStatus OBJECT-TYPE
        SYNTAX  INTEGER {
                other           (1),
                inactive        (2),
                active          (3),
                not-available   (4),
                available       (5),
                disable         (6)
        }
        ACCESS  read-only
        STATUS  mandatory
        DESCRIPTION
                "The backup status of the unit. The available values depend on the
                generation of the unit."
        ::= { fobusTableEntry 11 }

mdmActiveLink OBJECT-TYPE
        SYNTAX  INTEGER {
                line-port-2     (2),
                line-port-3     (3),
                disable         (90)
        }
        ACCESS  read-only
        STATUS  mandatory
        DESCRIPTION
                "This entry displays the line port used for data transmission."
        ::= { fobusTableEntry 12 }

mdmOperationMode OBJECT-TYPE
        SYNTAX  INTEGER {
                other           (1),
                forced-port2    (3),
                forced-port3    (4),
                automatic       (5)
        }
        ACCESS  read-write
        STATUS  mandatory
        DESCRIPTION
                "This entry defines if data is transmitted via port 2 or port 3:
                 'forced-port2', 'forced-port3', 'automatic'."
        ::= { fobusTableEntry 66 }

mdmAlarmConditionPort1 OBJECT-TYPE
        SYNTAX  INTEGER {
                other                       (1),
                disable                     (2),
                link-signal                 (3)
        }
        ACCESS  read-write
        STATUS  mandatory
        DESCRIPTION
                "The alarm trigger mode at port 1: 'disable', i.e. no alarm is
                 triggered, or 'link-signal', i.e. an alarm is triggered if the
                 link is down."
        ::= { fobusTableEntry 110 }

mdmAlarmConditionPort2 OBJECT-TYPE
        SYNTAX  INTEGER {
                other                        (1),
                disable                      (2),
                no-link-signal               (3),
                laser-fail                   (4),
                no-link-signal-or-laser-fail (5)
        }
        ACCESS  read-write
        STATUS  mandatory
        DESCRIPTION
                "The alarm trigger mode at port 2: 'disable', i.e. no alarm
                 is triggered, 'no-link-signal', i.e. an alarm is triggered if
                 the link is down, 'laser-fail', i.e. an alarm is triggered
                 if the laser diode is defective, or 'no-link-signal-or-laser-fail',
                 i.e. the link is down or the laser diode is defective."
        ::= { fobusTableEntry 111 }

mdmAlarmConditionPort3 OBJECT-TYPE
        SYNTAX  INTEGER {
                other                        (1),
                disable                      (2),
                no-link-signal               (3),
                laser-fail                   (4),
                no-link-signal-or-laser-fail (5)
        }
        ACCESS  read-write
        STATUS  mandatory
        DESCRIPTION
                "The alarm trigger mode at port 3: 'disable', i.e. no alarm
                 is triggered, 'no-link-signal', i.e. an alarm is triggered if
                 the link is down, 'laser-fail', i.e. an alarm is triggered
                 if the laser diode is defective, or 'no-link-signal-or-laser-fail',
                 i.e. the link is down or the laser diode is defective."
        ::= { fobusTableEntry 112 }

mdmTXLaserStatusPort2 OBJECT-TYPE
        SYNTAX  INTEGER {
                other       (1),
                disable     (2),
                enable      (3)
        }
        ACCESS  read-only
        STATUS  mandatory
        DESCRIPTION
                "This entry indicates if the laser diode at port 2 is
                 transmitting data ('enable') or not ('disable')."
        ::= { fobusTableEntry 121 }

mdmTXLaserStatusPort3 OBJECT-TYPE
        SYNTAX  INTEGER {
                other       (1),
                disable     (2),
                enable      (3)
        }
        ACCESS  read-only
        STATUS  mandatory
        DESCRIPTION
                "This entry indicates if the laser diode at port 3 is
                 transmitting data ('enable') or not ('disable')."
        ::= { fobusTableEntry 122 }

END
