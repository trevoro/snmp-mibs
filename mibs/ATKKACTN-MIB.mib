ATKKACTN-MIB DEFINITIONS ::= BEGIN

-- ATKK ACCTON MIB (Original : ACCTON-MIB )
-- History : 
-- 1998/ 7/ 2 OEM Accton EH3524A as ATKK CentreCOM FH8xxE
--            Changed MIB tree from Accton's to ATKK's by ATKK.
--              accton(259).snmpMgt(6) 
--               => alliedTelesyn(207).mibObject(8).repeaterMib(1)
--                                    .newRepeaterMib(20).acctonHubMIB(3)
--            Changed SYNTAX of downloadFilename from OCTET STRING to 
--            DisplayString
-- 1998/12/24  Add "trapMgrEntryStatus" INTEGER {String}




IMPORTS
	enterprises ,IpAddress
		FROM RFC1155-SMI
OBJECT-TYPE FROM RFC1155-SMI
		DisplayString,
	PhysAddress
	FROM RFC1213-MIB;

        alliedTelesyn   OBJECT IDENTIFIER ::= { enterprises 207 }
        products        OBJECT IDENTIFIER ::= { alliedTelesyn 1 }
        mibObject       OBJECT IDENTIFIER ::= { alliedTelesyn 8 }
        repeaterMib     OBJECT IDENTIFIER ::= { mibObject 1 }
        newRepeaterMib  OBJECT IDENTIFIER ::= { repeaterMib 20 }
        acctonHubMIB    OBJECT IDENTIFIER ::= { newRepeaterMib 3 }
        acctonCommon    OBJECT IDENTIFIER ::= { acctonHubMIB 1 }

-- Common MIB definitions

    accsystem	 OBJECT IDENTIFIER ::= { acctonCommon 1 }

    majorVer OBJECT-TYPE
	SYNTAX	INTEGER
	ACCESS	read-only
	STATUS	mandatory
	DESCRIPTION	"Software major version"
	::= { accsystem 1 }

    minorVer OBJECT-TYPE
	SYNTAX	INTEGER
	ACCESS	read-only
	STATUS	mandatory
	DESCRIPTION	"Software minor version"
	::= { accsystem 2 }

    hardwareVer  OBJECT-TYPE
	SYNTAX	INTEGER
	ACCESS	read-only
	STATUS	mandatory
	DESCRIPTION	"Hardware version of system board"
	::= { accsystem 3 }

-- Community Group.
--     The community group is optional. It defines the community strings
--     accepted by the system.

    communityMgt	OBJECT IDENTIFIER ::= { acctonCommon 2 }

    communityStringSize OBJECT-TYPE
	SYNTAX	INTEGER
	ACCESS	read-only
	STATUS	mandatory
	DESCRIPTION  "The length of the community string"
	::= { communityMgt 1 }

    communityTableSize	OBJECT-TYPE
	SYNTAX	INTEGER
	ACCESS	read-only
	STATUS	mandatory
	DESCRIPTION  "The size of the community table"
	::= { communityMgt 2}

    communityTable OBJECT-TYPE
	SYNTAX	 SEQUENCE OF CommunityEntry
	ACCESS	 not-accessible
	STATUS	 mandatory
	DESCRIPTION	"Community table"
	::= { communityMgt 3 }

    communityEntry OBJECT-TYPE
	SYNTAX	 CommunityEntry
	ACCESS	 not-accessible
	STATUS	 mandatory
              DESCRIPTION ""
	INDEX	 { communityIndex }
	::= { communityTable 1 }


    CommunityEntry ::= SEQUENCE
	{
	    communityIndex
		INTEGER,
	    communityString
		DisplayString,
	    communityAccessMode
		INTEGER,
	    communityStatus
		INTEGER
	 }

    communityIndex OBJECT-TYPE
	SYNTAX	INTEGER
	ACCESS	read-only
	STATUS	mandatory
	DESCRIPTION  "Index in community table"
	::= { communityEntry 1 }

    communityString OBJECT-TYPE
	SYNTAX	DisplayString
	ACCESS	read-write
	STATUS	mandatory
	DESCRIPTION  "Community string; the length is limited by
		      communityStringSize"
	::= { communityEntry 2 }

    communityAccessMode OBJECT-TYPE
	SYNTAX	INTEGER {
			  readOnly(1),
			  readWrite(2)
			}
	ACCESS	 read-write
	STATUS	 mandatory
	DESCRIPTION  "Access mode of the community"
	::= { communityEntry 3 }

    communityStatus OBJECT-TYPE
	SYNTAX	INTEGER
	ACCESS	 read-write
	STATUS	 mandatory
	DESCRIPTION  "Entries marked valid or invalid can not be changed.
		      When a manager wants to define a new community, he
		      sets an entry from valid or invalid to underChange,
		      then begins to define values in the table. After the
		      entry is completed, change it to valid, then the
		      community is enabled. To delete a community, just
		      change the status to invalid. Currentlty, only three
		      values are accepted:

		      invalid	  -- 0,
		      underChange -- 1,
		      valid	  -- 2.
		     "

	::= { communityEntry 4 }

-- Trap manager group
--
--   The trap manager group is optional. It is used by the agent to
--   define trap managers of the agent. The trap managers are
--   network manager to receive trap or alarm messages from the agent.
--   All network managers that can send correct community is able to
--   obtain information from the device, but only trap managers receive
--   alarm messages. It requires the community group.

     trapManagerMgt	OBJECT IDENTIFIER ::= { acctonCommon 3 }

     trapManagerTableSize  OBJECT-TYPE
	SYNTAX	INTEGER
	ACCESS	read-only
	STATUS	mandatory
	DESCRIPTION  "Size of trap manager table"
	::= { trapManagerMgt 1 }

     trapManagerTable OBJECT-TYPE
	 SYNTAX  SEQUENCE OF TrapManagerEntry
	 ACCESS  not-accessible
	 STATUS  mandatory
	 DESCRIPTION  "The trap manager table"
	 ::= { trapManagerMgt 2 }

     trapManagerEntry OBJECT-TYPE
	 SYNTAX  TrapManagerEntry
	 ACCESS  not-accessible
	 STATUS  mandatory
              DESCRIPTION ""
	 INDEX	 { trapMgrIndex }
	 ::= { trapManagerTable 1 }

     TrapManagerEntry ::= SEQUENCE
	{
	     trapMgrIndex
		INTEGER,
	     trapMgrCommunityIndex
		INTEGER,
	     trapMgrIpaddress
		IpAddress,
	     trapMgrEntryStatus
		INTEGER
	}

     trapMgrIndex OBJECT-TYPE
	SYNTAX	INTEGER
	ACCESS	read-only
	STATUS	mandatory
	DESCRIPTION "Index to the trap manager table"
	::= { trapManagerEntry 1 }

     trapMgrCommunityIndex OBJECT-TYPE
	SYNTAX	INTEGER
	ACCESS	read-write
	STATUS	mandatory
	DESCRIPTION "Community string specified by the index
		     in the community table"
	::= { trapManagerEntry 2 }

     trapMgrIpaddress OBJECT-TYPE
	SYNTAX IpAddress
	ACCESS read-write
	STATUS mandatory
	DESCRIPTION  "IP address of the network manager"
	::=  { trapManagerEntry 3 }

    trapMgrEntryStatus OBJECT-TYPE
	SYNTAX	INTEGER{
                         invalid(0),
                         underChange(1),
                         valid(2)
                       }
	ACCESS	 read-write
	STATUS	 mandatory
	DESCRIPTION  "Entries marked valid or invalid can not be changed.
		      To define a new manager, set an entry from valid
		      or invalid to underChange. Then fill in the required
		      information. Setting the status to valid enables
		      the entry. Setting the status to invalid deletes
		      the entry.  Currentlty, only three value are accepted:

		      invalid	  -- 0,
		      underChange -- 1,
		      valid	  -- 2.
		     "

	::= { trapManagerEntry 4 }

--  Download Group
--
--   The download group is used to trigger download operation of the
--   agent device to get a new version of software with TFTP protocol
--   from a server computer. The manager can select to upgrade
--   software temporarily or permanantly, and to run new software
--   immediately or until next power up
--

    downloadMgt 	OBJECT IDENTIFIER ::= { acctonCommon 4 }

     downloadServerIP	OBJECT-TYPE
       SYNTAX  IpAddress
       ACCESS  read-write
       STATUS  mandatory
       DESCRIPTION "The file server with the download file"
       ::= { downloadMgt 1 }

     downloadFilename  OBJECT-TYPE
       SYNTAX  DisplayString
       ACCESS  read-write
       STATUS  mandatory
       DESCRIPTION  "Name of file to download"
	::= { downloadMgt 2 }

     downloadMode OBJECT-TYPE
       SYNTAX  INTEGER {
		   permanant(1),
		   temporary(2)
	       }
       ACCESS  read-write
       STATUS  mandatory
       DESCRIPTION
	   "Permanent upgrade stores download software into permanent
	    storage of the agent device. Temporary upgrade just puts
	    download software in RAM, often for a test only."
	 ::= { downloadMgt 3 }

     downloadAction OBJECT-TYPE
	SYNTAX INTEGER {
		  run(1),
		  noRun(2)
	       }
	ACCESS read-write
	STATUS mandatory
	DESCRIPTION
	  "DownloadAction triggers the download operation.  The run option
	   starts the new software after downloading is complete.
	   The noRun option does not execute the new software. The new
	   software will be effective after the next restart. Note that the
	   noRun option is useful only when the download is permanent."
	   ::= { downloadMgt 4}


--  Restart Group
--
--  Restart group is used to reset the agent machine
--
    restart  OBJECT-TYPE
	SYNTAX INTEGER
	ACCESS read-write
	STATUS mandatory
	DESCRIPTION   "A write to restart the machine
		       Currentlty, only three value are accepted:

		       normal	  -- 0,
		       coldstart  -- 1,
		       warmstart  -- 2.
		      "


	::= { acctonCommon 5 }

--
--  Test group
--
--	Provide testing for accton devices
--

    acctest	OBJECT IDENTIFIER ::= { acctonCommon 6 }

    testTrap OBJECT-TYPE
       SYNTAX		INTEGER { test(1) }
       ACCESS	read-write
       STATUS	mandatory
       DESCRIPTION	"A write to testTrap triggers a warm-start trap
			 for testing trap capability"
       ::= { acctest 1 }

-- IPX trap manager group
--
--   The IPX trap manager group is optional. It is used by the agent to
--   define trap managers of the agent. The trap managers are
--   network manager to receive trap or alarm messages from the agent.
--   All network managers that can send correct community is able to
--   obtain information from the device, but only trap managers receive
--   alarm messages. It requires the community group.

     ipxtrapManagerMgt	OBJECT IDENTIFIER ::= { acctonCommon 7 }

     ipxtrapManagerTableSize	OBJECT-TYPE
	SYNTAX	INTEGER
	ACCESS	read-only
	STATUS	mandatory
	DESCRIPTION  "Size of ipx trap manager table"
	::= { ipxtrapManagerMgt 1 }

     ipxtrapManagerTable	OBJECT-TYPE
	 SYNTAX  SEQUENCE OF IpxTrapManagerEntry
	 ACCESS  not-accessible
	 STATUS  mandatory
	 DESCRIPTION  "The ipx trap manager table"
	 ::= { ipxtrapManagerMgt 2 }

     ipxtrapManagerEntry	OBJECT-TYPE
	 SYNTAX  IpxTrapManagerEntry
	 ACCESS  not-accessible
	 STATUS  mandatory
              DESCRIPTION ""
	 INDEX	 { ipxtrapMgrIndex }
	 ::= { ipxtrapManagerTable 1 }

     IpxTrapManagerEntry ::= SEQUENCE
	{
	     ipxtrapMgrIndex
		INTEGER,
	     ipxtrapMgrCommunityIndex
		INTEGER,
	     ipxtrapMgrNetNumber
		OCTET STRING,
	     ipxtrapMgrNode
		PhysAddress,
	     ipxtrapMgrEntryStatus
		INTEGER
	}

     ipxtrapMgrIndex	OBJECT-TYPE
	SYNTAX	INTEGER
	ACCESS	read-only
	STATUS	mandatory
	DESCRIPTION "Index to the ipx trap manager table"
	::= { ipxtrapManagerEntry 1 }

     ipxtrapMgrCommunityIndex	OBJECT-TYPE
	SYNTAX	INTEGER
	ACCESS	read-write
	STATUS	mandatory
	DESCRIPTION "Community string specified by the index
		     in the community table"
	::= { ipxtrapManagerEntry 2 }

     ipxtrapMgrNetNumber	OBJECT-TYPE
	SYNTAX OCTET STRING (SIZE(4))
	ACCESS read-write
	STATUS mandatory
	DESCRIPTION  "The network number portion of the IPX address of
		      this network manager"
	::=  { ipxtrapManagerEntry 3 }

     ipxtrapMgrNode		OBJECT-TYPE
	SYNTAX PhysAddress
	ACCESS read-write
	STATUS mandatory
	DESCRIPTION  "The node number portion of the IPX address of
		      this network manager"
	::=  { ipxtrapManagerEntry 4 }

     ipxtrapMgrEntryStatus	     OBJECT-TYPE
	SYNTAX	INTEGER {
			   invalid (1),
			   valid (2)
			 }
	ACCESS	 read-write
	STATUS	 mandatory
	DESCRIPTION  "Entries marked valid or invalid can not be changed.
		      To define a new manager, set an entry from valid
		      or invalid to underChange. Then fill in the required
		      information. Setting the status to valid enables
		      the entry. Setting the status to invalid deletes
		      the entry."
	::= { ipxtrapManagerEntry 5 }

END
