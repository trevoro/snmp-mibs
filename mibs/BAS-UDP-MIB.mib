BAS-UDP-MIB DEFINITIONS ::= BEGIN

IMPORTS
    MODULE-IDENTITY, OBJECT-TYPE, Counter32,
    IpAddress                          FROM SNMPv2-SMI
    basAliasUdp, BasChassisId,
    BasSlotId, BasInterfaceId,
    BasLogicalPortId                   FROM BAS-MIB;

basAliasUdpMIB MODULE-IDENTITY
        LAST-UPDATED "9810071415Z"
        ORGANIZATION "Broadband Access Systems"
        CONTACT-INFO
            " Tech Support
              Broadband Access Systems
              201 Forest Street
              Marlboro, MA  01752
              U.S.A.

              508-485-8200
              support@basystems.com"
        DESCRIPTION
            "This module defines the MIB objects
            for a Broadband Access System IP Forwarding component."
        ::= { basAliasUdp  1 }

-- the UDP group

basUdpObjects      OBJECT IDENTIFIER ::= {  basAliasUdpMIB 1 }

basUdpGroupTable OBJECT-TYPE
    SYNTAX      SEQUENCE OF BasUdpGroupEntry
    MAX-ACCESS  not-accessible
    STATUS      current
    DESCRIPTION
        "Aliased UDP group objects."
    ::= { basUdpObjects 1 }

basUdpGroupEntry OBJECT-TYPE
    SYNTAX      BasUdpGroupEntry
    MAX-ACCESS  not-accessible
    STATUS      current
    DESCRIPTION
        ""
    INDEX   { basUdpGroupChassis,
              basUdpGroupSlot,
              basUdpGroupIf,
              basUdpGroupLPort }
    ::= { basUdpGroupTable 1 }

BasUdpGroupEntry ::=
    SEQUENCE {
        basUdpInDatagrams   Counter32,
        basUdpNoPorts       Counter32,
        basUdpInErrors      Counter32,
        basUdpOutDatagrams  Counter32,
        basUdpGroupChassis  BasChassisId,
        basUdpGroupSlot     BasSlotId,
        basUdpGroupIf       BasInterfaceId,
        basUdpGroupLPort    BasLogicalPortId
        }

basUdpInDatagrams OBJECT-TYPE
    SYNTAX      Counter32
    MAX-ACCESS  read-only
    STATUS      current
    DESCRIPTION
            "The total number of UDP datagrams delivered to UDP users."
    ::= { basUdpGroupEntry 1 }

basUdpNoPorts OBJECT-TYPE
    SYNTAX      Counter32
    MAX-ACCESS  read-only
    STATUS      current
    DESCRIPTION
            "The total number of received UDP datagrams for which there
            was no application at the destination port."
    ::= { basUdpGroupEntry 2 }

basUdpInErrors OBJECT-TYPE
    SYNTAX      Counter32
    MAX-ACCESS  read-only
    STATUS      current
    DESCRIPTION
            "The number of received UDP datagrams that could not be
            delivered for reasons other than the lack of an application
            at the destination port."
    ::= { basUdpGroupEntry 3 }

basUdpOutDatagrams OBJECT-TYPE
    SYNTAX      Counter32
    MAX-ACCESS  read-only
    STATUS      current
    DESCRIPTION
            "The total number of UDP datagrams sent from this entity."
    ::= { basUdpGroupEntry 4 }

basUdpGroupChassis OBJECT-TYPE
    SYNTAX      BasChassisId
    MAX-ACCESS  not-accessible
    STATUS      current
    DESCRIPTION
        "The BAS Chassis ID of the Route Server."
    ::= { basUdpGroupEntry 5 }

basUdpGroupSlot OBJECT-TYPE
    SYNTAX      BasSlotId
    MAX-ACCESS  not-accessible
    STATUS      current
    DESCRIPTION
        "The BAS Slot ID of the Route Server."
    ::= { basUdpGroupEntry 6 }

basUdpGroupIf OBJECT-TYPE
    SYNTAX      BasInterfaceId
    MAX-ACCESS  not-accessible
    STATUS      current
    DESCRIPTION
        "The BAS interface ID of the Route Server."
    ::= { basUdpGroupEntry 7 }

basUdpGroupLPort OBJECT-TYPE
    SYNTAX      BasLogicalPortId
    MAX-ACCESS  not-accessible
    STATUS      current
    DESCRIPTION
        "The BAS logical port ID of the Route Server."
    ::= { basUdpGroupEntry 8 }

-- the UDP Listener table

-- The UDP listener table contains information about this
-- entity's UDP end-points on which a local application is
-- currently accepting datagrams.

basUdpTable OBJECT-TYPE
    SYNTAX      SEQUENCE OF BasUdpEntry
    MAX-ACCESS  not-accessible
    STATUS      current
    DESCRIPTION
            "A table containing UDP listener information."
    ::= { basUdpObjects 2 }

basUdpEntry OBJECT-TYPE
    SYNTAX      BasUdpEntry
    MAX-ACCESS  not-accessible
    STATUS      current
    DESCRIPTION
            "Information about a particular current UDP listener."
    INDEX   { basUdpLisChassis,
              basUdpLisSlot,
              basUdpLisIf,
              basUdpLisLPort,
              basUdpLocalAddress,
              basUdpLocalPort }
    ::= { basUdpTable 1 }

BasUdpEntry ::= SEQUENCE {
        basUdpLocalAddress  IpAddress,
        basUdpLocalPort     INTEGER,
        basUdpLisChassis    BasChassisId,
        basUdpLisSlot       BasSlotId,
        basUdpLisIf         BasInterfaceId,
        basUdpLisLPort      BasLogicalPortId
    }

basUdpLocalAddress OBJECT-TYPE
    SYNTAX      IpAddress
    MAX-ACCESS  read-only
    STATUS      current
    DESCRIPTION
            "The local IP address for this UDP listener.  In the case of
            a UDP listener which is willing to accept datagrams for any
            IP interface associated with the node, the value 0.0.0.0 is
            used."
    ::= { basUdpEntry 1 }

basUdpLocalPort OBJECT-TYPE
    SYNTAX      INTEGER (0..65535)
    MAX-ACCESS  read-only
    STATUS      current
    DESCRIPTION
            "The local port number for this UDP listener."
    ::= { basUdpEntry 2 }

basUdpLisChassis OBJECT-TYPE
    SYNTAX      BasChassisId
    MAX-ACCESS  not-accessible
    STATUS      current
    DESCRIPTION
        "The BAS Chassis ID of the Route Server."
    ::= { basUdpEntry 3 }

basUdpLisSlot OBJECT-TYPE
    SYNTAX      BasSlotId
    MAX-ACCESS  not-accessible
    STATUS      current
    DESCRIPTION
        "The BAS Slot ID of the Route Server."
    ::= { basUdpEntry 4 }

basUdpLisIf OBJECT-TYPE
    SYNTAX      BasInterfaceId
    MAX-ACCESS  not-accessible
    STATUS      current
    DESCRIPTION
        "The BAS interface ID of the Route Server."
    ::= { basUdpEntry 5 }

basUdpLisLPort OBJECT-TYPE
    SYNTAX      BasLogicalPortId
    MAX-ACCESS  not-accessible
    STATUS      current
    DESCRIPTION
        "The BAS logical port ID of the Route Server."
    ::= { basUdpEntry 6 }

END
