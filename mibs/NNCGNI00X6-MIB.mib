--  @(#)Basic.mib	9.1 10/16/98
--------------------------------------------------------------------------------
-- file: Basic.mib
--
-- contents:
--	This file contains the Newbridge MIB extensions for a standalone
--	network element
--
-- history:
--	0.1 / 92.08.25 / J. Watt / Creation
--      0.2 / 93.04.04 / J. Watt / Removed P from Minus12Status name, changed
--				   type of ProbeMPL to OCTET STRING, fixed
--				   ACCESS for various Table's and Entry's, 
--				   removed INDEX for ProbeMPL
-- M321-B1.01 / 93.05.20 / S. Buchko / nncExtCodeSpaceStatus should be read-only
-- M321-C1.01 / 93.06.03 / S. Buchko / Added nncExtCodeSpaceLoadSize
-- M321-C3.01 / 93.06.25 / S. Buchko / changed download requestor and server to
--				       be display strings
-- M321-C3.02 / 93.06.28 / S. Buchko / added nncExtRestartCause, modified 
--				       the definition of some of the restart
--				       counters to reflect reality
-- M321-F1.01 / 93.09.30 / B. McEachern / added RestartCause definitions
--
-- Copyright 1992 to 1993 Newbridge Networks Corporation.  All Rights Reserved
--------------------------------------------------------------------------------
NNCGNI00X6-MIB	DEFINITIONS ::= BEGIN
	
	IMPORTS	
		nncExtSystem, nncExtEnvironmental, nncExtRestart,
		nncExtCodeSpace, nncExtNVM, nncExtProbe, nncExtDiag
			FROM NNCGNI00X1-SMI
			
		Counter, NetworkAddress
			FROM RFC1155-SMI
		
		OBJECT-TYPE 
			FROM RFC-1212
			
		DisplayString
			FROM RFC1213-MIB;		

		
		RestartCause ::= INTEGER {
					trbl-noproblem(0),
					trbl-unknown(1),
					trbl-buserror(2),
					trbl-addresserror(3),
					trbl-illegalinst(4),
					trbl-zerodivide(5),
					trbl-chkfailure(6),
					trbl-trapvinst(7),
					trbl-privilege(8),
					trbl-tracetrap(9),
					trbl-line1010(10),
					trbl-line1111(11),
					trbl-uninitialized(15),
					trbl-spurious(24),
					trbl-intlevel-1(25),	
					trbl-intlevel-2(26),
					trbl-intlevel-3(27),
					trbl-intlevel-4(28),
					trbl-intlevel-5(29),
					trbl-intlevel-6(30),
					trbl-intlevel-7(31),
					trbl-trap-00(32),
					trbl-trap-01(33),
					trbl-trap-02(34),
					trbl-trap-03(35),
					trbl-trap-04(36),
					trbl-trap-05(37),
					trbl-trap-06(38),
					trbl-trap-07(39),
					trbl-trap-08(40),
					trbl-trap-09(41),
					trbl-trap-10(42),
					trbl-trap-11(43),
					trbl-trap-12(44),
					trbl-trap-13(45),
					trbl-trap-14(46),
					trbl-trap-15(47),
					trbl-watchdog(48),
					trbl-ncireset(49),
					trbl-ncirunminusone(50),
					trbl-panic(51),
					trbl-runbootprom(52),
					trbl-copyramtoflash(53),
					trbl-dnldaborted(54),
					trbl-badflashconfig(55),
					trbl-nvmreset(56),
					trbl-dspreset(57),
					trbl-dspdnldfailed(58),
					trbl-dsppollfailed(59),
					trbl-dspdiedontx(60),
					trbl-dspdead(61),
					trbl-dcmpdeath(62),
					trbl-runninglowcomms(63),
					trbl-runninglowframe(64),
					trbl-runninglowsys(65),
					trbl-runninglowsonic(66),
					trbl-runninglowmgmt(67),
					trbl-runninglowpoolunknown(68),
					trbl-ncireload(69),
					trbl-pushbutton(70),
					trbl-cpureset(71),
					trbl-rdsreset(72)
				}

		

-- -----------------------------------------------------------------------------
--
-- 	System Table Extensions
--
-- -----------------------------------------------------------------------------


	nncExtSysProductName	OBJECT-TYPE
		SYNTAX	DisplayString (SIZE (1..16))
		ACCESS	read-only
		STATUS	mandatory

		::= {nncExtSystem 1}
		
		
	nncExtSysCurrentGeneric	OBJECT-TYPE
		SYNTAX	DisplayString (SIZE (1..16))
		ACCESS	read-only
		STATUS	mandatory

		::= {nncExtSystem 2}

-- -----------------------------------------------------------------------------
--
-- 	Environmental Extensions
--
-- -----------------------------------------------------------------------------

	nncExtEnvFanStatus	OBJECT-TYPE
		SYNTAX	INTEGER { fanOk(1), fanFailed(2) }
		ACCESS	read-only
		STATUS	mandatory

		::= {nncExtEnvironmental 1}
		
		
	nncExtEnvTemperatureSensor	OBJECT-TYPE
		SYNTAX	INTEGER { ok(1), tooHot(2) }
		ACCESS	read-only
		STATUS	mandatory

		::= {nncExtEnvironmental 2}
		
		
	nncExtEnvPlus12Status	OBJECT-TYPE
		SYNTAX	INTEGER { ok(1), outOfSpec(2) }
		ACCESS	read-only
		STATUS	mandatory

		::= {nncExtEnvironmental 3}
		
		
	nncExtEnvMinus12Status	OBJECT-TYPE
		SYNTAX	INTEGER { ok(1), outOfSpec(2) }
		ACCESS	read-only
		STATUS	mandatory

		::= {nncExtEnvironmental 4}


-- -----------------------------------------------------------------------------
--
-- 	Restart Info Extensions
--
-- -----------------------------------------------------------------------------

	nncExtRestarts	OBJECT-TYPE
		SYNTAX	Counter 
		ACCESS	read-only
		STATUS	mandatory

		::= {nncExtRestart 1}


	nncExtFaultInducedRestarts	OBJECT-TYPE
		SYNTAX	Counter 
		ACCESS	read-only
		STATUS	mandatory

		::= {nncExtRestart 2}


	nncExtLastFault	OBJECT-TYPE
		SYNTAX	INTEGER (0..255)  -- { ... fault kind list here ... }
		ACCESS	read-only
		STATUS	mandatory

		::= {nncExtRestart 3}


	nncExtFaultRepetitions	OBJECT-TYPE
		SYNTAX	Counter
		ACCESS	read-only
		STATUS	mandatory

		::= {nncExtRestart 4}


	nncExtRestartTracebackTable	OBJECT-TYPE
		SYNTAX	SEQUENCE OF NncExtRestartTracebackEntry
		ACCESS	not-accessible
		STATUS	mandatory

		::= {nncExtRestart 5}
		
		
	nncExtRestartTracebackEntry	OBJECT-TYPE
		SYNTAX	NncExtRestartTracebackEntry
		ACCESS	not-accessible
		STATUS	mandatory

		INDEX { nncExtRestartTracebackIndex }
		::= {nncExtRestartTracebackTable 1}
		
		
	NncExtRestartTracebackEntry
		::= SEQUENCE {
			nncExtRestartTracebackIndex
				INTEGER,
			nncExtRestartTracebackPCValue
				INTEGER
		}


	nncExtRestartTracebackIndex	OBJECT-TYPE
		SYNTAX	INTEGER (1..255)
		ACCESS	read-only
		STATUS	mandatory

		::= {nncExtRestartTracebackEntry 1}
		
		
	nncExtRestartTracebackPCValue	OBJECT-TYPE
		SYNTAX	INTEGER (0..'ffffffff'h)
		ACCESS	read-only
		STATUS	mandatory

		::= {nncExtRestartTracebackEntry 2}
		
		
	nncExtRestartRegisterTable	OBJECT-TYPE
		SYNTAX	SEQUENCE OF NncExtRestartRegisterEntry
		ACCESS	not-accessible
		STATUS	mandatory

		::= {nncExtRestart 6}
		
		
	nncExtRestartRegisterEntry	OBJECT-TYPE
		SYNTAX	NncExtRestartRegisterEntry
		ACCESS	not-accessible
		STATUS	mandatory

		INDEX { nncExtRestartRegisterIndex }
		::= {nncExtRestartRegisterTable 1}
		
-- for a Motorola processor, the register mapping is...
		
	NncExtRestartRegisterEntry
		::= SEQUENCE {
			nncExtRestartRegisterIndex
				INTEGER,
			nncExtRestartRegisterValue
				INTEGER
		}


	nncExtRestartRegisterIndex	OBJECT-TYPE
		SYNTAX	INTEGER (1..255)
		ACCESS	read-only
		STATUS	mandatory

		::= {nncExtRestartRegisterEntry 1}
		
		
	nncExtRestartRegisterValue	OBJECT-TYPE
		SYNTAX	INTEGER (0..'ffffffff'h)
		ACCESS	read-only
		STATUS	mandatory

		::= {nncExtRestartRegisterEntry 2}
		
		
		
	nncExtRestartForceToBoot	OBJECT-TYPE
		SYNTAX	INTEGER (0..36000)
		ACCESS	read-write
		STATUS	mandatory

		::= { nncExtRestart 7}


	nncExtRestartCause	OBJECT-TYPE
		SYNTAX	INTEGER {
					trbl-noproblem(0),
					trbl-unknown(1),
					trbl-buserror(2),
					trbl-addresserror(3),
					trbl-illegalinst(4),
					trbl-zerodivide(5),
					trbl-chkfailure(6),
					trbl-trapvinst(7),
					trbl-privilege(8),
					trbl-tracetrap(9),
					trbl-line1010(10),
					trbl-line1111(11),
					trbl-uninitialized(15),
					trbl-spurious(24),
					trbl-intlevel-1(25),	
					trbl-intlevel-2(26),
					trbl-intlevel-3(27),
					trbl-intlevel-4(28),
					trbl-intlevel-5(29),
					trbl-intlevel-6(30),
					trbl-intlevel-7(31),
					trbl-trap-00(32),
					trbl-trap-01(33),
					trbl-trap-02(34),
					trbl-trap-03(35),
					trbl-trap-04(36),
					trbl-trap-05(37),
					trbl-trap-06(38),
					trbl-trap-07(39),
					trbl-trap-08(40),
					trbl-trap-09(41),
					trbl-trap-10(42),
					trbl-trap-11(43),
					trbl-trap-12(44),
					trbl-trap-13(45),
					trbl-trap-14(46),
					trbl-trap-15(47),
					trbl-watchdog(48),
					trbl-ncireset(49),
					trbl-ncirunminusone(50),
					trbl-panic(51),
					trbl-runbootprom(52),
					trbl-copyramtoflash(53),
					trbl-dnldaborted(54),
					trbl-badflashconfig(55),
					trbl-nvmreset(56),
					trbl-dspreset(57),
					trbl-dspdnldfailed(58),
					trbl-dsppollfailed(59),
					trbl-dspdiedontx(60),
					trbl-dspdead(61),
					trbl-dcmpdeath(62),
					trbl-runninglowcomms(63),
					trbl-runninglowframe(64),
					trbl-runninglowsys(65),
					trbl-runninglowsonic(66),
					trbl-runninglowmgmt(67),
					trbl-runninglowpoolunknown(68),
					trbl-ncireload(69),
					trbl-pushbutton(70),
					trbl-cpureset(71),
					trbl-rdsreset(72)
				}
		ACCESS	read-only
		STATUS	mandatory

		::= {nncExtRestart 8}


	
-- -----------------------------------------------------------------------------
--
-- 	Code Space Extensions
--
-- -----------------------------------------------------------------------------

--
-- Code space 1 is always the Boot PROM
--
	CodeSpaceIndex ::= INTEGER (1..3)
	
	nncExtCodeSpaceCurrentlyActive	OBJECT-TYPE
		SYNTAX	CodeSpaceIndex 
		ACCESS	read-only
		STATUS	mandatory

		::= {nncExtCodeSpace 1}
		

	nncExtCodeSpaceNextActive	OBJECT-TYPE
		SYNTAX	CodeSpaceIndex 
		ACCESS	read-write
		STATUS	mandatory

		::= {nncExtCodeSpace 2}


	nncExtCodeSpaceNumber	OBJECT-TYPE
		SYNTAX	CodeSpaceIndex 
		ACCESS	read-only
		STATUS	mandatory

		::= {nncExtCodeSpace 3}

	nncExtCodeSpaceTable	OBJECT-TYPE
		SYNTAX	SEQUENCE OF NncExtCodeSpaceEntry  
		ACCESS	not-accessible
		STATUS	mandatory

		::= {nncExtCodeSpace 4}
		
		
	nncExtCodeSpaceEntry	OBJECT-TYPE
		SYNTAX	NncExtCodeSpaceEntry  
		ACCESS	not-accessible
		STATUS	mandatory

		INDEX { nncExtCodeSpaceIndex }
		::= {nncExtCodeSpaceTable 1}
		
		
	NncExtCodeSpaceEntry 
		::= SEQUENCE {
			nncExtCodeSpaceIndex
				CodeSpaceIndex,
			nncExtCodeSpaceSize
				INTEGER,
			nncExtCodeSpaceStatus
				INTEGER,
			nncExtCodeSpaceGeneric
				DisplayString,
			nncExtCodeSpaceDownloadDate
				DisplayString,
			nncExtCodeSpaceDownloadTime
				DisplayString,
			nncExtCodeSpaceDownloadServer
				DisplayString,
			nncExtCodeSpaceDownloadRequestor
				DisplayString,
			nncExtCodeSpaceCompressionType
				INTEGER,
			nncExtCodeSpaceLoadSize
				INTEGER
				
		}
				

	nncExtCodeSpaceIndex	OBJECT-TYPE
		SYNTAX	CodeSpaceIndex 
		ACCESS	read-only
		STATUS	mandatory

		::= {nncExtCodeSpaceEntry 1}
		
		
	nncExtCodeSpaceSize	OBJECT-TYPE
		SYNTAX	INTEGER (0..'ffffffff'h) 
		ACCESS	read-only
		STATUS	mandatory

		::= {nncExtCodeSpaceEntry 2}
		
		
	nncExtCodeSpaceStatus	OBJECT-TYPE
		SYNTAX	INTEGER  { valid(1), invalid(2) }
		ACCESS	read-only
		STATUS	mandatory

		::= {nncExtCodeSpaceEntry 3}
		
		
	nncExtCodeSpaceGeneric	OBJECT-TYPE
		SYNTAX	DisplayString (SIZE (1..16))
		ACCESS	read-only
		STATUS	mandatory

		::= {nncExtCodeSpaceEntry 4}
		
		
	nncExtCodeSpaceDownloadDate	OBJECT-TYPE
		SYNTAX	DisplayString (SIZE (9..9))
		ACCESS	read-only
		STATUS	mandatory

		::= {nncExtCodeSpaceEntry 5}
		
		
	nncExtCodeSpaceDownloadTime	OBJECT-TYPE
		SYNTAX	DisplayString (SIZE (8..8))
		ACCESS	read-only
		STATUS	mandatory

		::= {nncExtCodeSpaceEntry 6}
		
		
	nncExtCodeSpaceDownloadServer	OBJECT-TYPE
		SYNTAX	DisplayString
		ACCESS	read-only
		STATUS	mandatory

		::= {nncExtCodeSpaceEntry 7}
		
		
	nncExtCodeSpaceDownloadRequestor	OBJECT-TYPE
		SYNTAX	DisplayString
		ACCESS	read-only
		STATUS	mandatory

		::= {nncExtCodeSpaceEntry 8}
		
		
	nncExtCodeSpaceCompressionType	OBJECT-TYPE
		SYNTAX	INTEGER { none(1), c1(2), c2(3) }
		ACCESS	read-only
		STATUS	mandatory

		::= {nncExtCodeSpaceEntry 9}


	nncExtCodeSpaceLoadSize	OBJECT-TYPE
		SYNTAX	INTEGER (0..'ffffffff'h) 
		ACCESS	read-only
		STATUS	mandatory

		::= {nncExtCodeSpaceEntry 10}
		


-- -----------------------------------------------------------------------------
--
-- 	NVM Extensions
--
-- -----------------------------------------------------------------------------

	NVMPoolIndex ::= INTEGER (1..2)
	

	nncExtNVMUsageTable	OBJECT-TYPE
		SYNTAX	SEQUENCE OF NncExtNVMUsageEntry  
		ACCESS	not-accessible
		STATUS	mandatory

		::= {nncExtNVM 1}
		
		
	nncExtNVMUsageEntry	OBJECT-TYPE
		SYNTAX	NncExtNVMUsageEntry  
		ACCESS	not-accessible
		STATUS	mandatory

		INDEX { nncExtNVMPoolIndex }
		::= {nncExtNVMUsageTable 1}
		
		
	NncExtNVMUsageEntry 
		::= SEQUENCE {
			nncExtNVMPoolIndex
				NVMPoolIndex,
			nncExtNVMPoolSize
				INTEGER,
			nncExtNVMPoolBytesUsed
				INTEGER
		}


	nncExtNVMPoolIndex	OBJECT-TYPE
		SYNTAX	NVMPoolIndex
		ACCESS	read-only
		STATUS	mandatory

		::= {nncExtNVMUsageEntry 1}


	nncExtNVMPoolSize	OBJECT-TYPE
		SYNTAX	INTEGER (0..'ffffffff'h)
		ACCESS	read-only
		STATUS	mandatory

		::= {nncExtNVMUsageEntry 2}


	nncExtNVMPoolBytesUsed	OBJECT-TYPE
		SYNTAX	INTEGER (0..'ffffffff'h)
		ACCESS	read-only
		STATUS	mandatory

		::= {nncExtNVMUsageEntry 3}


	nncExtNVMLastRepair	OBJECT-TYPE
		SYNTAX	OCTET STRING (SIZE(31..31))
		ACCESS	read-only
		STATUS	mandatory

		::= {nncExtNVM 2}

-- -----------------------------------------------------------------------------
--
-- 	Probe Extensions
--
-- -----------------------------------------------------------------------------

	nncExtProbeMPLTable	OBJECT-TYPE
		SYNTAX	SEQUENCE OF NncExtProbeMPLEntry
		ACCESS	not-accessible
		STATUS	mandatory

		::= {nncExtProbe 1}
	
	nncExtProbeMPLEntry	OBJECT-TYPE
		SYNTAX	NncExtProbeMPLEntry
		ACCESS	not-accessible
		STATUS	mandatory

		::= {nncExtProbeMPLTable 1}
		
	NncExtProbeMPLEntry
		::= SEQUENCE {
			nncExtProbeMPL
				OCTET STRING
		}
		
	nncExtProbeMPL	OBJECT-TYPE
		SYNTAX	OCTET STRING (SIZE (0..255))
		ACCESS	read-write
		STATUS	mandatory

		::= {nncExtProbeMPLEntry 1}



-- -----------------------------------------------------------------------------
--
-- 	Diagnostic Extensions
--
-- -----------------------------------------------------------------------------

	nncDiagUndoAll	OBJECT-TYPE
		SYNTAX	INTEGER { undo(1) }
		ACCESS	read-write
		STATUS	mandatory

		::= {nncExtDiag 1}

END
