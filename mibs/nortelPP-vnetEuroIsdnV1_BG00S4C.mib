Nortel-Magellan-Passport-VnetEuroIsdnMIB
DEFINITIONS ::= BEGIN



IMPORTS

      OBJECT-TYPE
   FROM RFC-1212

      passportMIBs
   FROM Nortel-Magellan-Passport-UsefulDefinitionsMIB

      Counter32,
      DisplayString,
      StorageType,
      RowStatus,
      Gauge32,
      Unsigned32
   FROM Nortel-Magellan-Passport-StandardTextualConventionsMIB

      NonReplicated,
      Link
   FROM Nortel-Magellan-Passport-TextualConventionsMIB

      sigChanIndex,
      sigChan
   FROM Nortel-Magellan-Passport-VoiceNetworkingMIB;




-- LAST-UPDATED   "9904150000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     VnetEuroIsdn Enterprise MIB."

vnetEuroIsdnMIB OBJECT IDENTIFIER ::= { passportMIBs 138 }










-- SigChan/n EuroIsdn
-- The EuroIsdn component defines the characteristics of the 
-- signalling channel's connection to the external equipment on the 
-- Euro ISDN UNI (ETSI-T Interface).

sigChanEIsdn OBJECT IDENTIFIER ::= { sigChan 14 }



sigChanEIsdnRowStatusTable OBJECT-TYPE
   SYNTAX     SEQUENCE OF SigChanEIsdnRowStatusEntry
   ACCESS     not-accessible
   STATUS     mandatory
   DESCRIPTION
     "This entry controls the addition and deletion of 
      sigChanEIsdn components."
::= { sigChanEIsdn 1 }

sigChanEIsdnRowStatusEntry OBJECT-TYPE
   SYNTAX     SigChanEIsdnRowStatusEntry
   ACCESS     not-accessible
   STATUS     mandatory
   DESCRIPTION
     "A single entry in the table represents a single 
      sigChanEIsdn component."
   INDEX {
      sigChanIndex,
      sigChanEIsdnIndex }
::= { sigChanEIsdnRowStatusTable 1 }

SigChanEIsdnRowStatusEntry ::= SEQUENCE {
   sigChanEIsdnRowStatus
      RowStatus,
   sigChanEIsdnComponentName
      DisplayString,
   sigChanEIsdnStorageType
      StorageType,
   sigChanEIsdnIndex
      NonReplicated }

sigChanEIsdnRowStatus OBJECT-TYPE
   SYNTAX     RowStatus 
   ACCESS     read-write
   STATUS     mandatory
   DESCRIPTION
     "This variable is used as the basis for SNMP naming of
      sigChanEIsdn components.
      These components can be added and deleted."
::= { sigChanEIsdnRowStatusEntry 1 }

sigChanEIsdnComponentName OBJECT-TYPE
   SYNTAX     DisplayString 
   ACCESS     read-only
   STATUS     mandatory
   DESCRIPTION
     "This variable provides the component's string name for
      use with the ASCII Console Interface"
::= { sigChanEIsdnRowStatusEntry 2 }

sigChanEIsdnStorageType OBJECT-TYPE
   SYNTAX     StorageType 
   ACCESS     read-only
   STATUS     mandatory
   DESCRIPTION
     "This variable represents the storage type value for the
      sigChanEIsdn tables."
::= { sigChanEIsdnRowStatusEntry 4 }

sigChanEIsdnIndex OBJECT-TYPE
   SYNTAX     NonReplicated 
   ACCESS     not-accessible
   STATUS     mandatory
   DESCRIPTION
     "This variable represents the index for the sigChanEIsdn tables."
::= { sigChanEIsdnRowStatusEntry 10 }

sigChanEIsdnL2Table OBJECT-TYPE
   SYNTAX     SEQUENCE OF SigChanEIsdnL2Entry
   ACCESS     not-accessible
   STATUS     mandatory
   DESCRIPTION
     "This group specifies the provisionable layer 2 attributes of the Euro 
      ISDN (ETSI-T) protocol."
::= { sigChanEIsdn 11 }

sigChanEIsdnL2Entry OBJECT-TYPE
   SYNTAX     SigChanEIsdnL2Entry
   ACCESS     not-accessible
   STATUS     mandatory
   DESCRIPTION
     "An entry in the sigChanEIsdnL2Table."
   INDEX {
      sigChanIndex,
      sigChanEIsdnIndex }
::= { sigChanEIsdnL2Table 1 }

SigChanEIsdnL2Entry ::= SEQUENCE {
   sigChanEIsdnT23
      Unsigned32,
   sigChanEIsdnT200
      Unsigned32,
   sigChanEIsdnN200
      Unsigned32,
   sigChanEIsdnT203
      Unsigned32,
   sigChanEIsdnCircuitSwitchedK
      Unsigned32 }

sigChanEIsdnT23 OBJECT-TYPE
   SYNTAX     Unsigned32 (1..15)
   ACCESS     read-write
   STATUS     mandatory
   DESCRIPTION
     "This attribute specifies duration of the layer 2 enable request timer."
   DEFVAL     { 10 }
::= { sigChanEIsdnL2Entry 1 }

sigChanEIsdnT200 OBJECT-TYPE
   SYNTAX     Unsigned32 (1..20)
   ACCESS     read-write
   STATUS     mandatory
   DESCRIPTION
     "This attribute specifies the maximum elapsed time between a layer 
      2 frame and its acknowledgment."
   DEFVAL     { 1 }
::= { sigChanEIsdnL2Entry 2 }

sigChanEIsdnN200 OBJECT-TYPE
   SYNTAX     Unsigned32 (1..8)
   ACCESS     read-write
   STATUS     mandatory
   DESCRIPTION
     "This attribute specifies the maximum number of re-transmissions of 
      a layer 2 frame."
   DEFVAL     { 3 }
::= { sigChanEIsdnL2Entry 3 }

sigChanEIsdnT203 OBJECT-TYPE
   SYNTAX     Unsigned32 (2..40)
   ACCESS     read-write
   STATUS     mandatory
   DESCRIPTION
     "This attribute specifies the maximum time during which layer 2 
      frames may be absent. Expiry triggers a check on whether the far 
      end is alive."
   DEFVAL     { 10 }
::= { sigChanEIsdnL2Entry 4 }

sigChanEIsdnCircuitSwitchedK OBJECT-TYPE
   SYNTAX     Unsigned32 (1..127)
   ACCESS     read-write
   STATUS     mandatory
   DESCRIPTION
     "This attribute specifies the maximum number of sequentially 
      numbered I frames (that is, window size (k)) that may be 
      unacknowledged at any given time for a SAP supporting primary 
      rate (64kbit/sec) signalling."
   DEFVAL     { 7 }
::= { sigChanEIsdnL2Entry 6 }

sigChanEIsdnL3Table OBJECT-TYPE
   SYNTAX     SEQUENCE OF SigChanEIsdnL3Entry
   ACCESS     not-accessible
   STATUS     mandatory
   DESCRIPTION
     "This group represents the provisionable Layer 3 timer attributes of a 
      the Euro ISDN (ETSI-T) protocol."
::= { sigChanEIsdn 12 }

sigChanEIsdnL3Entry OBJECT-TYPE
   SYNTAX     SigChanEIsdnL3Entry
   ACCESS     not-accessible
   STATUS     mandatory
   DESCRIPTION
     "An entry in the sigChanEIsdnL3Table."
   INDEX {
      sigChanIndex,
      sigChanEIsdnIndex }
::= { sigChanEIsdnL3Table 1 }

SigChanEIsdnL3Entry ::= SEQUENCE {
   sigChanEIsdnT310
      Unsigned32 }

sigChanEIsdnT310 OBJECT-TYPE
   SYNTAX     Unsigned32 (10..120)
   ACCESS     read-write
   STATUS     mandatory
   DESCRIPTION
     "This attribute specifies duration of the call proceeding state timer."
   DEFVAL     { 30 }
::= { sigChanEIsdnL3Entry 4 }

sigChanEIsdnProvTable OBJECT-TYPE
   SYNTAX     SEQUENCE OF SigChanEIsdnProvEntry
   ACCESS     not-accessible
   STATUS     mandatory
   DESCRIPTION
     "This group defines the general options of the D-channel signalling 
      link."
::= { sigChanEIsdn 13 }

sigChanEIsdnProvEntry OBJECT-TYPE
   SYNTAX     SigChanEIsdnProvEntry
   ACCESS     not-accessible
   STATUS     mandatory
   DESCRIPTION
     "An entry in the sigChanEIsdnProvTable."
   INDEX {
      sigChanIndex,
      sigChanEIsdnIndex }
::= { sigChanEIsdnProvTable 1 }

SigChanEIsdnProvEntry ::= SEQUENCE {
   sigChanEIsdnSide
      INTEGER,
   sigChanEIsdnMaxNonCallConcurrent
      Unsigned32,
   sigChanEIsdnOverlapSending
      INTEGER,
   sigChanEIsdnOverlapReceiving
      INTEGER }

sigChanEIsdnSide OBJECT-TYPE
   SYNTAX     INTEGER  {
                 network(1),
                 user(2) }
   ACCESS     read-write
   STATUS     mandatory
   DESCRIPTION
     "This attribute specifies whether the interface is the network or user 
      side of the connection. The parameter applies to both the layer 2 
      and layer 3 of the interface. In addition, if this attribute is set to 
      network, then the interface is master during channel negotiation. If 
      this attribute is set to user, then the interface is slave during channel 
      negotiation."
   DEFVAL     { network }
::= { sigChanEIsdnProvEntry 1 }

sigChanEIsdnMaxNonCallConcurrent OBJECT-TYPE
   SYNTAX     Unsigned32 (0..30)
   ACCESS     read-write
   STATUS     mandatory
   DESCRIPTION
     "This attribute specifies the maximum number of simultaneous active 
      non call-associated sessions that are allowed. Reduction of the value 
      does not impact NCAS sessions already in progress."
   DEFVAL     { 30 }
::= { sigChanEIsdnProvEntry 2 }

sigChanEIsdnOverlapSending OBJECT-TYPE
   SYNTAX     INTEGER  {
                 enabled(0),
                 disabled(1) }
   ACCESS     read-write
   STATUS     mandatory
   DESCRIPTION
     "This attribute specifies whether overlap sending to the PBX is 
      enabled."
   DEFVAL     { enabled }
::= { sigChanEIsdnProvEntry 3 }

sigChanEIsdnOverlapReceiving OBJECT-TYPE
   SYNTAX     INTEGER  {
                 enabled(0),
                 disabled(1) }
   ACCESS     read-write
   STATUS     mandatory
   DESCRIPTION
     "This attribute specifies whether overlap receiving from the PBX is 
      enabled."
   DEFVAL     { enabled }
::= { sigChanEIsdnProvEntry 4 }

sigChanEIsdnStateTable OBJECT-TYPE
   SYNTAX     SEQUENCE OF SigChanEIsdnStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { sigChanEIsdn 14 }

sigChanEIsdnStateEntry OBJECT-TYPE
   SYNTAX     SigChanEIsdnStateEntry
   ACCESS     not-accessible
   STATUS     mandatory
   DESCRIPTION
     "An entry in the sigChanEIsdnStateTable."
   INDEX {
      sigChanIndex,
      sigChanEIsdnIndex }
::= { sigChanEIsdnStateTable 1 }

SigChanEIsdnStateEntry ::= SEQUENCE {
   sigChanEIsdnAdminState
      INTEGER,
   sigChanEIsdnOperationalState
      INTEGER,
   sigChanEIsdnUsageState
      INTEGER }

sigChanEIsdnAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { sigChanEIsdnStateEntry 1 }

sigChanEIsdnOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { sigChanEIsdnStateEntry 2 }

sigChanEIsdnUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { sigChanEIsdnStateEntry 3 }

sigChanEIsdnStatsTable OBJECT-TYPE
   SYNTAX     SEQUENCE OF SigChanEIsdnStatsEntry
   ACCESS     not-accessible
   STATUS     mandatory
   DESCRIPTION
     "This group provides the statistical attributes for the SigChan/x 
      EuroIsdn component."
::= { sigChanEIsdn 15 }

sigChanEIsdnStatsEntry OBJECT-TYPE
   SYNTAX     SigChanEIsdnStatsEntry
   ACCESS     not-accessible
   STATUS     mandatory
   DESCRIPTION
     "An entry in the sigChanEIsdnStatsTable."
   INDEX {
      sigChanIndex,
      sigChanEIsdnIndex }
::= { sigChanEIsdnStatsTable 1 }

SigChanEIsdnStatsEntry ::= SEQUENCE {
   sigChanEIsdnTotalCallsToIf
      Counter32,
   sigChanEIsdnTotalCallsFromIf
      Counter32,
   sigChanEIsdnNonCallAssocSessionsToIf
      Counter32,
   sigChanEIsdnNonCallAssocSessionsFromIf
      Counter32 }

sigChanEIsdnTotalCallsToIf OBJECT-TYPE
   SYNTAX     Counter32 
   ACCESS     read-only
   STATUS     mandatory
   DESCRIPTION
     "This attribute counts the total number of calls that have been made 
      to the interface. The value wraps to zero when it exceeds its 
      maximum."
::= { sigChanEIsdnStatsEntry 2 }

sigChanEIsdnTotalCallsFromIf OBJECT-TYPE
   SYNTAX     Counter32 
   ACCESS     read-only
   STATUS     mandatory
   DESCRIPTION
     "This attribute counts the total number of calls that have been made 
      from the interface. The value wraps to zero when it exceeds its 
      maximum."
::= { sigChanEIsdnStatsEntry 3 }

sigChanEIsdnNonCallAssocSessionsToIf OBJECT-TYPE
   SYNTAX     Counter32 
   ACCESS     read-only
   STATUS     mandatory
   DESCRIPTION
     "This attribute counts the total number of non call-associated 
      sessions that have been made to the interface. The value wraps to 
      zero when it exceeds its maximum."
::= { sigChanEIsdnStatsEntry 4 }

sigChanEIsdnNonCallAssocSessionsFromIf OBJECT-TYPE
   SYNTAX     Counter32 
   ACCESS     read-only
   STATUS     mandatory
   DESCRIPTION
     "This attribute counts the total number of non call-associated 
      sessions that have been made from the interface. The value wraps to 
      zero when it exceeds its maximum."
::= { sigChanEIsdnStatsEntry 5 }

sigChanEIsdnOperTable OBJECT-TYPE
   SYNTAX     SEQUENCE OF SigChanEIsdnOperEntry
   ACCESS     not-accessible
   STATUS     mandatory
   DESCRIPTION
     "This group provides the operational attributes for the SigChan/x 
      EuroIsdn component."
::= { sigChanEIsdn 16 }

sigChanEIsdnOperEntry OBJECT-TYPE
   SYNTAX     SigChanEIsdnOperEntry
   ACCESS     not-accessible
   STATUS     mandatory
   DESCRIPTION
     "An entry in the sigChanEIsdnOperTable."
   INDEX {
      sigChanIndex,
      sigChanEIsdnIndex }
::= { sigChanEIsdnOperTable 1 }

SigChanEIsdnOperEntry ::= SEQUENCE {
   sigChanEIsdnActiveChannels
      Gauge32,
   sigChanEIsdnActiveVoiceChannels
      Gauge32,
   sigChanEIsdnActiveDataChannels
      Gauge32,
   sigChanEIsdnPeakActiveChannels
      Gauge32,
   sigChanEIsdnPeakActiveVoiceChannels
      Gauge32,
   sigChanEIsdnPeakActiveDataChannels
      Gauge32,
   sigChanEIsdnDChanStatus
      INTEGER }

sigChanEIsdnActiveChannels OBJECT-TYPE
   SYNTAX     Gauge32 (0..128)
   ACCESS     read-only
   STATUS     mandatory
   DESCRIPTION
     "This attribute indicates the number of currently active channels. 
      This includes channels used by both, data and voice calls."
   DEFVAL     { 0 }
::= { sigChanEIsdnOperEntry 1 }

sigChanEIsdnActiveVoiceChannels OBJECT-TYPE
   SYNTAX     Gauge32 (0..128)
   ACCESS     read-only
   STATUS     mandatory
   DESCRIPTION
     "This attribute indicates the number of channels that are currently 
      used by voice calls. This includes modem calls."
   DEFVAL     { 0 }
::= { sigChanEIsdnOperEntry 2 }

sigChanEIsdnActiveDataChannels OBJECT-TYPE
   SYNTAX     Gauge32 (0..128)
   ACCESS     read-only
   STATUS     mandatory
   DESCRIPTION
     "This attribute indicates the number of channels that are currently 
      used by data calls. This does not include modem data."
   DEFVAL     { 0 }
::= { sigChanEIsdnOperEntry 3 }

sigChanEIsdnPeakActiveChannels OBJECT-TYPE
   SYNTAX     Gauge32 (0..128)
   ACCESS     read-only
   STATUS     mandatory
   DESCRIPTION
     "This attribute indicates the maximum value of the activeChannels 
      attribute during the last polling period."
   DEFVAL     { 0 }
::= { sigChanEIsdnOperEntry 4 }

sigChanEIsdnPeakActiveVoiceChannels OBJECT-TYPE
   SYNTAX     Gauge32 (0..128)
   ACCESS     read-only
   STATUS     mandatory
   DESCRIPTION
     "This attribute indicates the maximum value of the 
      activeVoiceChannels attribute during the last polling period."
   DEFVAL     { 0 }
::= { sigChanEIsdnOperEntry 5 }

sigChanEIsdnPeakActiveDataChannels OBJECT-TYPE
   SYNTAX     Gauge32 (0..128)
   ACCESS     read-only
   STATUS     mandatory
   DESCRIPTION
     "This attribute indicates the maximum value of the 
      activeDataChannels attribute during the last polling period."
   DEFVAL     { 0 }
::= { sigChanEIsdnOperEntry 6 }

sigChanEIsdnDChanStatus OBJECT-TYPE
   SYNTAX     INTEGER  {
                 outOfService(0),
                 establishing(1),
                 established(2),
                 enabling(3),
                 inService(4),
                 restarting(5) }
   ACCESS     read-only
   STATUS     mandatory
   DESCRIPTION
     "This attribute indicates the state of the D-channel. 
      outOfService means that there is no layer 2 or layer 3 connectivity 
      to the PBX.
      establishing means that the signalling channel is attempting to stage 
      the layer 2.
      established means that the layer 2 is enabled. If the signalling 
      channel stays in the established state, then it is waiting for a restart 
      from the PBX.
      enabling means that the resources for processing calls are being 
      initialized. If the signalling channel stays in the enabling state then 
      it is waiting for a restart acknowledgment from the PBX. 
      inService means that the resources for processing calls are 
      available. 
      restarting means that the resources for call processing are being 
      initialized."
::= { sigChanEIsdnOperEntry 7 }

sigChanEIsdnToolsTable OBJECT-TYPE
   SYNTAX     SEQUENCE OF SigChanEIsdnToolsEntry
   ACCESS     not-accessible
   STATUS     mandatory
   DESCRIPTION
     "This contains a series of operational attributes which turn on and off 
      several kinds of tracing."
::= { sigChanEIsdn 17 }

sigChanEIsdnToolsEntry OBJECT-TYPE
   SYNTAX     SigChanEIsdnToolsEntry
   ACCESS     not-accessible
   STATUS     mandatory
   DESCRIPTION
     "An entry in the sigChanEIsdnToolsTable."
   INDEX {
      sigChanIndex,
      sigChanEIsdnIndex }
::= { sigChanEIsdnToolsTable 1 }

SigChanEIsdnToolsEntry ::= SEQUENCE {
   sigChanEIsdnTracing
      OCTET STRING }

sigChanEIsdnTracing OBJECT-TYPE
   SYNTAX     OCTET STRING (SIZE (1))
   ACCESS     read-write
   STATUS     mandatory
   DESCRIPTION
     "This attribute defines which types of tracing are active on the 
      signalling channel. The tracing messages are sent to the debug 
      stream. To see the messages the agentQueueSize attribute of the 
      Lp/x Eng Ds/debug component must be greater than 0 and the 
      operator's NMIS session must have the debug stream included in its 
      data stream list (for example: set Nmis Telnet Session/1 
      dataStreams deb). Several types of tracing can be enabled 
      simultaneously. 
      Note that tracing consumes additional CPU resources and slows 
      down call processing on a heavily loaded card. If there is message 
      block exhaustion tracing is suspended for a period of time and then 
      automatically re-enabled. An alarm is generated on tracing 
      suspension and resumption. This mechanism protects the function 
      processor against excessive numbers of tracing messages.
      Types of tracing include: 
      protocolErrors - get details of any protocol errors which are 
      occurring. Protocol errors are also reported in summary form as 
      alarms. 
      q931Summary - summary of the Q.931 messages on the signalling 
      link. 
      q931Hex - Q.931 messages displayed in hex format. Useful to 
      determine protocol compliance in case of errors reported on local or 
      remote ends.
      q931Symbolic - Q.931 messages parsed to give maximum detail. 
      Useful for understanding content of messages flowing on the link.
      portHex - Q.921 messages in hex format being sent and received on 
      the link.

      Description of bits:
      protocolErrors(0)
      q931Summary(1)
      q931Hex(2)
      q931Symbolic(3)
      portHex(4)"
::= { sigChanEIsdnToolsEntry 1 }

sigChanEIsdnOptTable OBJECT-TYPE
   SYNTAX     SEQUENCE OF SigChanEIsdnOptEntry
   ACCESS     not-accessible
   STATUS     mandatory
   DESCRIPTION
     "This group specifies the provisionable attributes specific to the Euro 
      ISDN (ETSI-T) protocol."
::= { sigChanEIsdn 18 }

sigChanEIsdnOptEntry OBJECT-TYPE
   SYNTAX     SigChanEIsdnOptEntry
   ACCESS     not-accessible
   STATUS     mandatory
   DESCRIPTION
     "An entry in the sigChanEIsdnOptTable."
   INDEX {
      sigChanIndex,
      sigChanEIsdnIndex }
::= { sigChanEIsdnOptTable 1 }

SigChanEIsdnOptEntry ::= SEQUENCE {
   sigChanEIsdnVariant
      INTEGER,
   sigChanEIsdnConnectServiceTimer
      Unsigned32,
   sigChanEIsdnResponseServiceTimer
      Unsigned32,
   sigChanEIsdnLifetimeServiceTimer
      Unsigned32 }

sigChanEIsdnVariant OBJECT-TYPE
   SYNTAX     INTEGER  {
                 etsiGeneric(0),
                 austria(1),
                 germany(2) }
   ACCESS     read-write
   STATUS     mandatory
   DESCRIPTION
     "This attribute specifies the specific variant of the Euro ISDN (ETSI-
      T) protocol. Supported variants are:
      etsiGeneric - provides generic ETSI-T protocol. Only proxy of the 
      NETWORK side of the protocol is implemented,
      austria - provides ETSI-T protocol variant as per the Austrian 
      national specification. Only the USER side of the protocol is 
      implemented,
      germany - provides ETSI-T protocol variant as per the German 
      national specification. Only the USER side of the protocol is 
      implemented."
   DEFVAL     { etsiGeneric }
::= { sigChanEIsdnOptEntry 1 }

sigChanEIsdnConnectServiceTimer OBJECT-TYPE
   SYNTAX     Unsigned32 (1..10)
   ACCESS     read-write
   STATUS     mandatory
   DESCRIPTION
     "This attribute specifies duration of the 'await connection' 
      supervisory timer which applies to non call-associated sessions 
      providing bearer-independent connection-oriented transport for 
      supplementary services. The timer is started at the ingress Passport 
      when a REGISTER message is received from the source PBX and 
      stopped when a virtual circuit with the egress Passport is 
      established. If the timer expires, the non call-associated session is 
      cleared.
      The 'await connection' timer (attribute connectServiceTimer) 
      together with 'await response' timer (attribute 
      responseServiceTimer) provide equivalent of the T-ACTIVATE 
      timer described in the relevant supplementary service specifications.
      A change of the timer value does not apply to timers already 
      running."
   DEFVAL     { 8 }
::= { sigChanEIsdnOptEntry 2 }

sigChanEIsdnResponseServiceTimer OBJECT-TYPE
   SYNTAX     Unsigned32 (1..10)
   ACCESS     read-write
   STATUS     mandatory
   DESCRIPTION
     "This attribute specifies duration of the 'await response' supervisory 
      timer which applies to non call-associated sessions providing 
      bearer-independent connection-oriented transport for supplementary 
      services. The timer is started at the ingress Passport when creation 
      of a virtual circuit with the egress Passport is confirmed and stopped 
      when the first message from the destination PBX is received. If the 
      timer expires, the non call-associated session is cleared.
      The 'await connection' timer (attribute connectServiceTimer) 
      together with 'await response' timer (attribute 
      responseServiceTimer) provide equivalent of the T-ACTIVATE 
      timer described in the relevant supplementary service specifications.
      A change of the timer value does not apply to timers already 
      running."
   DEFVAL     { 8 }
::= { sigChanEIsdnOptEntry 3 }

sigChanEIsdnLifetimeServiceTimer OBJECT-TYPE
   SYNTAX     Unsigned32 (1..200)
   ACCESS     read-write
   STATUS     mandatory
   DESCRIPTION
     "This attribute specifies duration of the service lifetime supervisory 
      timer which applies to non call-associated sessions providing 
      bearer-independent connection-oriented transport for supplementary 
      services. The timer limits the duration of a virtual call. It is started 
      at the ingress Passport at the moment the first response message 
      from the destination PBX has been received and stopped when the 
      non call-associated session is released. If the timer expires, the non 
      call-associated session is cleared.
      This timer is equivalent to the T-CCBS6 timer described in the 
      relevant supplementary service specifications.
      A change of the timer value does not apply to timers already 
      running."
   DEFVAL     { 60 }
::= { sigChanEIsdnOptEntry 4 }


-- SigChan/n EuroIsdn Framer
-- 
-- The Framer component controls link layer framing for application 
-- components sending and receiving data on a link interface. It is also 
-- through Framer, that an application component is associated with a 
-- specific hardware link interface.
-- 
-- The Framer component provides provisionable attributes related to 
-- data path aspects of the hardware interface (such as CRC and frame 
-- length). The Framer component also provides a provisionable 
-- attribute which binds the application component to a specific 
-- hardware component.
-- 
-- The Framer component contains operational attributes for link 
-- interface data path statistics (such as frame counts and aborts).

sigChanEIsdnFramer OBJECT IDENTIFIER ::= { sigChanEIsdn 2 }



sigChanEIsdnFramerRowStatusTable OBJECT-TYPE
   SYNTAX     SEQUENCE OF SigChanEIsdnFramerRowStatusEntry
   ACCESS     not-accessible
   STATUS     mandatory
   DESCRIPTION
     "This entry controls the addition and deletion of 
      sigChanEIsdnFramer components."
::= { sigChanEIsdnFramer 1 }

sigChanEIsdnFramerRowStatusEntry OBJECT-TYPE
   SYNTAX     SigChanEIsdnFramerRowStatusEntry
   ACCESS     not-accessible
   STATUS     mandatory
   DESCRIPTION
     "A single entry in the table represents a single 
      sigChanEIsdnFramer component."
   INDEX {
      sigChanIndex,
      sigChanEIsdnIndex,
      sigChanEIsdnFramerIndex }
::= { sigChanEIsdnFramerRowStatusTable 1 }

SigChanEIsdnFramerRowStatusEntry ::= SEQUENCE {
   sigChanEIsdnFramerRowStatus
      RowStatus,
   sigChanEIsdnFramerComponentName
      DisplayString,
   sigChanEIsdnFramerStorageType
      StorageType,
   sigChanEIsdnFramerIndex
      NonReplicated }

sigChanEIsdnFramerRowStatus OBJECT-TYPE
   SYNTAX     RowStatus 
   ACCESS     read-only
   STATUS     mandatory
   DESCRIPTION
     "This variable is used as the basis for SNMP naming of
      sigChanEIsdnFramer components.
      These components cannot be added nor deleted."
::= { sigChanEIsdnFramerRowStatusEntry 1 }

sigChanEIsdnFramerComponentName OBJECT-TYPE
   SYNTAX     DisplayString 
   ACCESS     read-only
   STATUS     mandatory
   DESCRIPTION
     "This variable provides the component's string name for
      use with the ASCII Console Interface"
::= { sigChanEIsdnFramerRowStatusEntry 2 }

sigChanEIsdnFramerStorageType OBJECT-TYPE
   SYNTAX     StorageType 
   ACCESS     read-only
   STATUS     mandatory
   DESCRIPTION
     "This variable represents the storage type value for the
      sigChanEIsdnFramer tables."
::= { sigChanEIsdnFramerRowStatusEntry 4 }

sigChanEIsdnFramerIndex OBJECT-TYPE
   SYNTAX     NonReplicated 
   ACCESS     not-accessible
   STATUS     mandatory
   DESCRIPTION
     "This variable represents the index for the sigChanEIsdnFramer tables."
::= { sigChanEIsdnFramerRowStatusEntry 10 }

sigChanEIsdnFramerProvTable OBJECT-TYPE
   SYNTAX     SEQUENCE OF SigChanEIsdnFramerProvEntry
   ACCESS     not-accessible
   STATUS     mandatory
   DESCRIPTION
     "This group contains the base provisioning data for the Framer 
      component. Application or hardware interface specific provisioning 
      data is contained in other provisionable Framer groups."
::= { sigChanEIsdnFramer 10 }

sigChanEIsdnFramerProvEntry OBJECT-TYPE
   SYNTAX     SigChanEIsdnFramerProvEntry
   ACCESS     not-accessible
   STATUS     mandatory
   DESCRIPTION
     "An entry in the sigChanEIsdnFramerProvTable."
   INDEX {
      sigChanIndex,
      sigChanEIsdnIndex,
      sigChanEIsdnFramerIndex }
::= { sigChanEIsdnFramerProvTable 1 }

SigChanEIsdnFramerProvEntry ::= SEQUENCE {
   sigChanEIsdnFramerInterfaceName
      Link }

sigChanEIsdnFramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { sigChanEIsdnFramerProvEntry 1 }

sigChanEIsdnFramerStateTable OBJECT-TYPE
   SYNTAX     SEQUENCE OF SigChanEIsdnFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { sigChanEIsdnFramer 12 }

sigChanEIsdnFramerStateEntry OBJECT-TYPE
   SYNTAX     SigChanEIsdnFramerStateEntry
   ACCESS     not-accessible
   STATUS     mandatory
   DESCRIPTION
     "An entry in the sigChanEIsdnFramerStateTable."
   INDEX {
      sigChanIndex,
      sigChanEIsdnIndex,
      sigChanEIsdnFramerIndex }
::= { sigChanEIsdnFramerStateTable 1 }

SigChanEIsdnFramerStateEntry ::= SEQUENCE {
   sigChanEIsdnFramerAdminState
      INTEGER,
   sigChanEIsdnFramerOperationalState
      INTEGER,
   sigChanEIsdnFramerUsageState
      INTEGER }

sigChanEIsdnFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { sigChanEIsdnFramerStateEntry 1 }

sigChanEIsdnFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { sigChanEIsdnFramerStateEntry 2 }

sigChanEIsdnFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { sigChanEIsdnFramerStateEntry 3 }

sigChanEIsdnFramerStatsTable OBJECT-TYPE
   SYNTAX     SEQUENCE OF SigChanEIsdnFramerStatsEntry
   ACCESS     not-accessible
   STATUS     mandatory
   DESCRIPTION
     "This group contains the operational statistics data for a Framer 
      component."
::= { sigChanEIsdnFramer 13 }

sigChanEIsdnFramerStatsEntry OBJECT-TYPE
   SYNTAX     SigChanEIsdnFramerStatsEntry
   ACCESS     not-accessible
   STATUS     mandatory
   DESCRIPTION
     "An entry in the sigChanEIsdnFramerStatsTable."
   INDEX {
      sigChanIndex,
      sigChanEIsdnIndex,
      sigChanEIsdnFramerIndex }
::= { sigChanEIsdnFramerStatsTable 1 }

SigChanEIsdnFramerStatsEntry ::= SEQUENCE {
   sigChanEIsdnFramerFrmToIf
      Counter32,
   sigChanEIsdnFramerFrmFromIf
      Counter32,
   sigChanEIsdnFramerOctetFromIf
      Counter32,
   sigChanEIsdnFramerAborts
      Counter32,
   sigChanEIsdnFramerCrcErrors
      Counter32,
   sigChanEIsdnFramerLrcErrors
      Counter32,
   sigChanEIsdnFramerNonOctetErrors
      Counter32,
   sigChanEIsdnFramerOverruns
      Counter32,
   sigChanEIsdnFramerUnderruns
      Counter32,
   sigChanEIsdnFramerLargeFrmErrors
      Counter32 }

sigChanEIsdnFramerFrmToIf OBJECT-TYPE
   SYNTAX     Counter32 
   ACCESS     read-only
   STATUS     mandatory
   DESCRIPTION
     "This attribute counts the number of frames transmitted to the link 
      interface by the Framer.
      This count wraps to zero after exceeding its maximum value."
::= { sigChanEIsdnFramerStatsEntry 1 }

sigChanEIsdnFramerFrmFromIf OBJECT-TYPE
   SYNTAX     Counter32 
   ACCESS     read-only
   STATUS     mandatory
   DESCRIPTION
     "This attribute counts the number of frames received from the link 
      interface by the Framer.
      This count wraps to zero after exceeding its maximum value."
::= { sigChanEIsdnFramerStatsEntry 2 }

sigChanEIsdnFramerOctetFromIf OBJECT-TYPE
   SYNTAX     Counter32 
   ACCESS     read-only
   STATUS     mandatory
   DESCRIPTION
     "This attribute counts the number of bytes received from the link 
      interface by the Framer.
      This count wraps to zero after exceeding its maximum value."
::= { sigChanEIsdnFramerStatsEntry 3 }

sigChanEIsdnFramerAborts OBJECT-TYPE
   SYNTAX     Counter32 
   ACCESS     read-only
   STATUS     mandatory
   DESCRIPTION
     "This attribute counts the total number of aborts received.
      This count wraps to zero after exceeding its maximum value."
::= { sigChanEIsdnFramerStatsEntry 4 }

sigChanEIsdnFramerCrcErrors OBJECT-TYPE
   SYNTAX     Counter32 
   ACCESS     read-only
   STATUS     mandatory
   DESCRIPTION
     "This attribute counts the total number of frames with CRC errors.
      This count wraps to zero after exceeding its maximum value."
::= { sigChanEIsdnFramerStatsEntry 5 }

sigChanEIsdnFramerLrcErrors OBJECT-TYPE
   SYNTAX     Counter32 
   ACCESS     read-only
   STATUS     mandatory
   DESCRIPTION
     "This attribute counts the total number of frames with LRC errors.
      This count wraps to zero after exceeding its maximum value."
::= { sigChanEIsdnFramerStatsEntry 6 }

sigChanEIsdnFramerNonOctetErrors OBJECT-TYPE
   SYNTAX     Counter32 
   ACCESS     read-only
   STATUS     mandatory
   DESCRIPTION
     "This attribute counts the total number of frames that were non octet 
      aligned.
      This count wraps to zero after exceeding its maximum value."
::= { sigChanEIsdnFramerStatsEntry 7 }

sigChanEIsdnFramerOverruns OBJECT-TYPE
   SYNTAX     Counter32 
   ACCESS     read-only
   STATUS     mandatory
   DESCRIPTION
     "This attribute counts the total number of frames received from the 
      link for which overruns occurred.
      This count wraps to zero after exceeding its maximum value."
::= { sigChanEIsdnFramerStatsEntry 8 }

sigChanEIsdnFramerUnderruns OBJECT-TYPE
   SYNTAX     Counter32 
   ACCESS     read-only
   STATUS     mandatory
   DESCRIPTION
     "This attribute counts the total number of frames transmitted to the 
      link for which underruns occurred.
      This count wraps to zero after exceeding its maximum value."
::= { sigChanEIsdnFramerStatsEntry 9 }

sigChanEIsdnFramerLargeFrmErrors OBJECT-TYPE
   SYNTAX     Counter32 
   ACCESS     read-only
   STATUS     mandatory
   DESCRIPTION
     "This attribute counts the total number of frames received which 
      were too large (longer than 500 bytes).
      This count wraps to zero after exceeding its maximum value."
::= { sigChanEIsdnFramerStatsEntry 10 }




-- 
-- Version and Compliance statements
-- 



-- Object-Group Statement:
-- A list of all current accessible leaf objects.

-- OBJECTS { sigChanEIsdnFramerAdminState,
--           sigChanEIsdnOverlapReceiving,
--           sigChanEIsdnLifetimeServiceTimer,
--           sigChanEIsdnOperationalState,
--           sigChanEIsdnFramerFrmFromIf,
--           sigChanEIsdnT203,
--           sigChanEIsdnFramerFrmToIf,
--           sigChanEIsdnFramerOctetFromIf,
--           sigChanEIsdnFramerStorageType,
--           sigChanEIsdnDChanStatus,
--           sigChanEIsdnConnectServiceTimer,
--           sigChanEIsdnFramerUnderruns,
--           sigChanEIsdnFramerLrcErrors,
--           sigChanEIsdnFramerLargeFrmErrors,
--           sigChanEIsdnAdminState,
--           sigChanEIsdnTracing,
--           sigChanEIsdnFramerRowStatus,
--           sigChanEIsdnActiveVoiceChannels,
--           sigChanEIsdnActiveChannels,
--           sigChanEIsdnTotalCallsFromIf,
--           sigChanEIsdnRowStatus,
--           sigChanEIsdnResponseServiceTimer,
--           sigChanEIsdnT23,
--           sigChanEIsdnT310,
--           sigChanEIsdnMaxNonCallConcurrent,
--           sigChanEIsdnVariant,
--           sigChanEIsdnNonCallAssocSessionsFromIf,
--           sigChanEIsdnPeakActiveVoiceChannels,
--           sigChanEIsdnFramerNonOctetErrors,
--           sigChanEIsdnNonCallAssocSessionsToIf,
--           sigChanEIsdnFramerOverruns,
--           sigChanEIsdnFramerUsageState,
--           sigChanEIsdnFramerAborts,
--           sigChanEIsdnActiveDataChannels,
--           sigChanEIsdnFramerComponentName,
--           sigChanEIsdnUsageState,
--           sigChanEIsdnN200,
--           sigChanEIsdnSide,
--           sigChanEIsdnPeakActiveChannels,
--           sigChanEIsdnTotalCallsToIf,
--           sigChanEIsdnComponentName,
--           sigChanEIsdnCircuitSwitchedK,
--           sigChanEIsdnPeakActiveDataChannels,
--           sigChanEIsdnFramerInterfaceName,
--           sigChanEIsdnFramerCrcErrors,
--           sigChanEIsdnStorageType,
--           sigChanEIsdnFramerOperationalState,
--           sigChanEIsdnOverlapSending,
--           sigChanEIsdnT200 }
-- STATUS  mandatory
-- DESCRIPTION
--   "A list of all current accessible leaf objects."

vnetEuroIsdnGroup OBJECT IDENTIFIER ::= { vnetEuroIsdnMIB 1 }
vnetEuroIsdnGroupBE OBJECT IDENTIFIER ::= { vnetEuroIsdnGroup 5 }
vnetEuroIsdnGroupBE01 OBJECT IDENTIFIER ::= { vnetEuroIsdnGroupBE 2 }
vnetEuroIsdnGroupBE01A OBJECT IDENTIFIER ::= { vnetEuroIsdnGroupBE01 2 }



-- Agent-Capabilities Statement:

-- PRODUCT-RELEASE "Passport Release 7.0 VnetEuroIsdn."
-- STATUS          mandatory
-- DESCRIPTION     "VnetEuroIsdn MIB: MIB Version BE01A,
--                  Software Version BG00S4C."
-- SUPPORTS        Nortel-Magellan-Passport-VnetEuroIsdnMIB
--    INCLUDES     { vnetEuroIsdnGroupBE01A }

vnetEuroIsdnCapabilities OBJECT IDENTIFIER ::= { vnetEuroIsdnMIB 3 }
vnetEuroIsdnCapabilitiesBE OBJECT IDENTIFIER ::= { vnetEuroIsdnCapabilities 5 }
vnetEuroIsdnCapabilitiesBE01 OBJECT IDENTIFIER ::= { vnetEuroIsdnCapabilitiesBE 2 }
vnetEuroIsdnCapabilitiesBE01A OBJECT IDENTIFIER ::= { vnetEuroIsdnCapabilitiesBE01 2 }





END
