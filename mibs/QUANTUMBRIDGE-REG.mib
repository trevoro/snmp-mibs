QUANTUMBRIDGE-REG DEFINITIONS ::= BEGIN

IMPORTS
    MODULE-IDENTITY, enterprises, OBJECT-IDENTITY
        FROM SNMPv2-SMI
    ;

quantumBridgeRegistrations MODULE-IDENTITY
    LAST-UPDATED "9903202155Z" -- March 20, 1999
    ORGANIZATION "Quantum Bridge Communications Inc."
    CONTACT-INFO
        "mvaysman@quantumbridge.com"
    DESCRIPTION
        "This module defines the enterprises OID of Quantum Bridge and other
        company-wide definitions. The resulting top-level name space
        under the Quantum Bridge branch looks like this:

        Quantum Bridge
            quantumBridgeRegistrations - this module
            qbMibs          - MIB modules defined in .mi2 files
            qbProducts      - AGENT-CAPABILITIES modules defined 
                                 in .mib files

        This is where you reserve an OIDs for a MIB module. The values
        are defined in the appropriate .mi2/.mo files but are in
        comments here so that we can have one document under source
        control to reserve and catalog values."
    ::= { quantumBridge 1 }

quantumBridge OBJECT-IDENTITY
    STATUS      current
    DESCRIPTION
        "Quantum Bridge's node in the naming hierarchy as assigned by the
        Internet Assigned Numbers Authority (IANA)."
    ::= { enterprises 4323 }


qbMibs OBJECT-IDENTITY
    STATUS      current
    DESCRIPTION
        "A registration point under which all MIB modules
        are defined."
    ::= { quantumBridge 2 }

-- qbSysMIB           	 ::= { qbMibs 2 }
-- qbDwsMIB           	 ::= { qbMibs 3 }
-- qbCESMIB		 ::= { qbMibs 4 }
-- qbEthernetMIB	 ::= { qbMibs 5 }   
-- qbSonetMIB		 ::= { qbMibs 6 }
-- qbAtmMIB		 ::= { qbMibs 7 }
-- qbSysRptMIB		 ::= { qbMibs 8 }
-- qbSysqbVTVCMIB	 ::= { qbMibs 9 }
-- qbDs1MIB		 ::= { qbMibs 10 }
-- qbqbTimingMIB	 ::= { qbMibs 11 }
-- qbAtmSoftPvcMIB	 ::= { qbMibs 12 }

   qbProducts OBJECT-IDENTITY
    STATUS      current
    DESCRIPTION
        "A registration point under which all Quantum Bridge AGENT_CAPABILTIES
        definitions for various products(and therefore values of sysObjectId) are
        defined for various devices."
    ::= { quantumBridge 3 }

   qb5000SystemID       OBJECT IDENTIFIER ::= { qbProducts 1 }	-- Optical Access Switch (OAS) 
   qb3000SystemID       OBJECT IDENTIFIER ::= { qbProducts 2 }	-- Optical Access Switch (OAS)
   qb8000SystemID       OBJECT IDENTIFIER ::= { qbProducts 3 }	-- Optical Edge Switch (OES)
   -- Add new product OIDs below

END
