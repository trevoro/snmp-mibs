-- Wed Dec 29 21:59:36 1999
-- Build (BLD_525)
-- 
-- dellserv.mib is a composite of the following MIBs:
--    clean_basebrdd.mib
--    clean_dclra.mib
--    clean_oldbase.mib
--    clean_oldlra.mib
-- 
-- 
-- ######################################################
-- ######################################################
-- ######################################################
-- #### Start of MIB E:\HIP152\server\mibs\clean_basebrdd.mib
-- 
-- ****************************************************************
-- Modified by CleanMib for Build (BLD_525) on 12/29/99 21:59:29
-- ****************************************************************

-- MIB generated by mibgen version 1.0

BASEBRDD-MIB DEFINITIONS ::= BEGIN

IMPORTS
	enterprises, Counter64
		FROM RFC1155-SMI
	InternationalDisplayString
		FROM HOST-RESOURCES-MIB
	OBJECT-TYPE
		FROM RFC-1212
	Counter,Gauge,
	DisplayString
		FROM RFC1213-MIB
	Dmi-Date,Dmi-Integer64,
	dmiEventDateTime,dmiCompId,dmiEventSeverity,
	dmiEventStateKey,dmiEventAssociatedGroup,
	dmiEventSystem,dmiEventSubSystem
		FROM DMTF-DMI-MIB;

DmiCounter			::= Counter
DmiCounter64		::= Counter64
DmiGauge			::= Gauge
DmiInteger			::= INTEGER
DmiOctetstring		::= OCTET STRING
DmiDisplaystring	::= DisplayString
DmiCompId	::= INTEGER
DmiGroupId	::= INTEGER

dmtf                	OBJECT IDENTIFIER ::= { enterprises 412 }
dmtfStdMifs         	OBJECT IDENTIFIER ::= { dmtf 2 }
dmtfDynOids         	OBJECT IDENTIFIER ::= { dmtf 3 }

SdMTFComponentID ::= SEQUENCE { 
	manufacturerAtt1	DmiDisplaystring,
	productAtt2	DmiDisplaystring,
	versionAtt3	DmiDisplaystring,
	serialNumberAtt4	DmiDisplaystring,
	installationAtt5	Dmi-Date,
	verifyAtt6	DmiInteger
}
dmtfServiceLayerMIF	OBJECT IDENTIFIER ::= { dmtfStdMifs 1 }

dMTFComponentIDTable OBJECT-TYPE
	SYNTAX		SEQUENCE OF SdMTFComponentID
	ACCESS		not-accessible
	STATUS		mandatory
	DESCRIPTION	"This group defines the attributes common to all components.
 This group is required."
	::= { dmtfServiceLayerMIF 1 }

dMTFComponentIDEntry OBJECT-TYPE
	SYNTAX		SdMTFComponentID
	ACCESS		not-accessible
	STATUS		mandatory
	DESCRIPTION	"This group defines the attributes common to all components.
 This group is required."
	INDEX		{ DmiCompId,DmiGroupId }
	::= { dMTFComponentIDTable 1 }


manufacturerAtt1 OBJECT-TYPE
	SYNTAX		DmiDisplaystring
	ACCESS		read-only
	STATUS		mandatory
	DESCRIPTION	"Manufacturer of this system."
	REFERENCE "'DMTF|ComponentID|001' 1"
	::= { dMTFComponentIDEntry 1 }

productAtt2 OBJECT-TYPE
	SYNTAX		DmiDisplaystring
	ACCESS		read-only
	STATUS		mandatory
	DESCRIPTION	"Product name for this system."
	REFERENCE "'DMTF|ComponentID|001' 2"
	::= { dMTFComponentIDEntry 2 }

versionAtt3 OBJECT-TYPE
	SYNTAX		DmiDisplaystring
	ACCESS		read-only
	STATUS		mandatory
	DESCRIPTION	"Version number of this system."
	REFERENCE "'DMTF|ComponentID|001' 3"
	::= { dMTFComponentIDEntry 3 }

serialNumberAtt4 OBJECT-TYPE
	SYNTAX		DmiDisplaystring
	ACCESS		read-only
	STATUS		mandatory
	DESCRIPTION	"Serial number for this system."
	REFERENCE "'DMTF|ComponentID|001' 4"
	::= { dMTFComponentIDEntry 4 }

installationAtt5 OBJECT-TYPE
	SYNTAX		Dmi-Date
	ACCESS		read-only
	STATUS		mandatory
	DESCRIPTION	"The time and date when this component was installed."
	REFERENCE "'DMTF|ComponentID|001' 5"
	::= { dMTFComponentIDEntry 5 }

verifyAtt6 OBJECT-TYPE
	SYNTAX		INTEGER { 
		anErrorOccurredCheckStatusCode(0),
		thisComponentDoesNotExist(1),
		verificationIsNotSupported(2),
		reserved(3),
		thisComponentExistsButTheFunctionalityIsUntested(4),
		thisComponentExistsButTheFunctionalityIsUnknown(5),
		thisComponentExistsAndIsNotFunctioningCorrectly(6),
		thisComponentExistsAndIsFunctioningCorrectly(7)
	}
	ACCESS		read-only
	STATUS		mandatory
	DESCRIPTION	"A code that provides a level of verification that the component
is still installed and working."
	REFERENCE "'DMTF|ComponentID|001' 6"
	::= { dMTFComponentIDEntry 6 }

SdellTemperatureProbe ::= SEQUENCE { 
	dellTemperatureProbeState INTEGER,
	tempParentIndexAtt1	DmiInteger,
	tempIndexAtt2	DmiInteger,
	tempTypeAtt3	DmiInteger,
	tempStatusAtt4	DmiInteger,
	tempReadingAtt5	DmiInteger,
	tempMinWarnAtt6	DmiDisplaystring,
	tempMaxWarnAtt7	DmiDisplaystring,
	tempMinFailAtt8	DmiInteger,
	tempMaxFailAtt9	DmiInteger,
	tempLocationAtt10	DmiDisplaystring
}

dell        OBJECT IDENTIFIER ::= { enterprises 674 } 
server2        OBJECT IDENTIFIER ::= { dell 10891 } 

dellTemperatureProbeTable OBJECT-TYPE
	SYNTAX		SEQUENCE OF SdellTemperatureProbe
	ACCESS		not-accessible
	STATUS		mandatory
	DESCRIPTION	"This group defines the attributes for the temperature probes
this system."
	::= { server2 300 }

dellTemperatureProbeEntry OBJECT-TYPE
	SYNTAX		SdellTemperatureProbe
	ACCESS		not-accessible
	STATUS		mandatory
	DESCRIPTION	"This group defines the attributes for the temperature probes
this system."
	INDEX		{ DmiCompId,DmiGroupId, tempParentIndexAtt1, tempIndexAtt2 }
	::= { dellTemperatureProbeTable 1 }


dellTemperatureProbeState OBJECT-TYPE
	SYNTAX		INTEGER { 
		active(1),
		notInService(2),
		notReady(3),
		createAndGo(4),
		createAndWait(5),
		destroy(6)
	}
	ACCESS		read-write
	STATUS		mandatory
	REFERENCE "'Dell|Temperature Probe|003' 0"
	::= { dellTemperatureProbeEntry 0 }

tempParentIndexAtt1 OBJECT-TYPE
	SYNTAX		DmiInteger
	ACCESS		read-only
	STATUS		mandatory
	DESCRIPTION	"An index into the chassis table."
	REFERENCE "'Dell|Temperature Probe|003' 1"
	::= { dellTemperatureProbeEntry 1 }

tempIndexAtt2 OBJECT-TYPE
	SYNTAX		DmiInteger
	ACCESS		read-only
	STATUS		mandatory
	DESCRIPTION	"index into this temperature probe table."
	REFERENCE "'Dell|Temperature Probe|003' 2"
	::= { dellTemperatureProbeEntry 2 }

tempTypeAtt3 OBJECT-TYPE
	SYNTAX		INTEGER { 
		other(1),
		unknown(2),
		tMC(3),
		tVM(4),
		eSM(5),
		backplane(6),
		harrierBackplane(7)
	}
	ACCESS		read-only
	STATUS		mandatory
	DESCRIPTION	"Defines the type of the temperature probe."
	REFERENCE "'Dell|Temperature Probe|003' 3"
	::= { dellTemperatureProbeEntry 3 }

tempStatusAtt4 OBJECT-TYPE
	SYNTAX		INTEGER { 
		other(1),
		unknown(2),
		oK(3),
		nonCritical(4),
		critical(5),
		nonRecoverable(6)
	}
	ACCESS		read-only
	STATUS		mandatory
	DESCRIPTION	"Current status of the temperature probe."
	REFERENCE "'Dell|Temperature Probe|003' 4"
	::= { dellTemperatureProbeEntry 4 }

tempReadingAtt5 OBJECT-TYPE
	SYNTAX		DmiInteger
	ACCESS		read-only
	STATUS		mandatory
	DESCRIPTION	"The reading of the temperature probe in tenths of degrees."
	REFERENCE "'Dell|Temperature Probe|003' 5"
	::= { dellTemperatureProbeEntry 5 }

tempMinWarnAtt6 OBJECT-TYPE
	SYNTAX		DmiDisplaystring
	ACCESS		read-write
	STATUS		mandatory
	DESCRIPTION	"The lower warning threshold for the temperature probe set
by the user."
	REFERENCE "'Dell|Temperature Probe|003' 6"
	::= { dellTemperatureProbeEntry 6 }

tempMaxWarnAtt7 OBJECT-TYPE
	SYNTAX		DmiDisplaystring
	ACCESS		read-write
	STATUS		mandatory
	DESCRIPTION	"The upper warning threshold for the temperature probe set
by the user."
	REFERENCE "'Dell|Temperature Probe|003' 7"
	::= { dellTemperatureProbeEntry 7 }

tempMinFailAtt8 OBJECT-TYPE
	SYNTAX		DmiInteger
	ACCESS		read-only
	STATUS		mandatory
	DESCRIPTION	"The lower failure threshold for the temperature probe."
	REFERENCE "'Dell|Temperature Probe|003' 8"
	::= { dellTemperatureProbeEntry 8 }

tempMaxFailAtt9 OBJECT-TYPE
	SYNTAX		DmiInteger
	ACCESS		read-only
	STATUS		mandatory
	DESCRIPTION	"The upper failure threshold for the temperature probe."
	REFERENCE "'Dell|Temperature Probe|003' 9"
	::= { dellTemperatureProbeEntry 9 }

tempLocationAtt10 OBJECT-TYPE
	SYNTAX		DmiDisplaystring
	ACCESS		read-only
	STATUS		mandatory
	DESCRIPTION	"The location of this temperature probe within the system."
	REFERENCE "'Dell|Temperature Probe|003' 10"
	::= { dellTemperatureProbeEntry 10 }

SdellFanSensor ::= SEQUENCE { 
	dellFanSensorState INTEGER,
	fansParentIndexAtt1	DmiInteger,
	fansIndexAtt2	DmiInteger,
	fansTypeAtt3	DmiInteger,
	fansStatusAtt4	DmiInteger,
	fansReadingAtt5	DmiInteger,
	fansWarningMinAtt6	DmiDisplaystring,
	fansMaxWarnAtt7	DmiDisplaystring,
	fansMinFailAtt8	DmiInteger,
	fansMaxFailAtt9	DmiInteger,
	fansLocationAtt10	DmiDisplaystring
}

dellFanSensorTable OBJECT-TYPE
	SYNTAX		SEQUENCE OF SdellFanSensor
	ACCESS		not-accessible
	STATUS		mandatory
	DESCRIPTION	"This group defines the attributes for the fan probes this
system."
	::= { server2 301 }

dellFanSensorEntry OBJECT-TYPE
	SYNTAX		SdellFanSensor
	ACCESS		not-accessible
	STATUS		mandatory
	DESCRIPTION	"This group defines the attributes for the fan probes this
system."
	INDEX		{ DmiCompId,DmiGroupId, fansParentIndexAtt1, fansIndexAtt2 }
	::= { dellFanSensorTable 1 }


dellFanSensorState OBJECT-TYPE
	SYNTAX		INTEGER { 
		active(1),
		notInService(2),
		notReady(3),
		createAndGo(4),
		createAndWait(5),
		destroy(6)
	}
	ACCESS		read-write
	STATUS		mandatory
	REFERENCE "'Dell|Fan Sensor|003' 0"
	::= { dellFanSensorEntry 0 }

fansParentIndexAtt1 OBJECT-TYPE
	SYNTAX		DmiInteger
	ACCESS		read-only
	STATUS		mandatory
	DESCRIPTION	"An index into the chassis table."
	REFERENCE "'Dell|Fan Sensor|003' 1"
	::= { dellFanSensorEntry 1 }

fansIndexAtt2 OBJECT-TYPE
	SYNTAX		DmiInteger
	ACCESS		read-only
	STATUS		mandatory
	DESCRIPTION	"index into this fan probe table."
	REFERENCE "'Dell|Fan Sensor|003' 2"
	::= { dellFanSensorEntry 2 }

fansTypeAtt3 OBJECT-TYPE
	SYNTAX		INTEGER { 
		other(1),
		unknown(2),
		boolean(3),
		rPM(4)
	}
	ACCESS		read-only
	STATUS		mandatory
	DESCRIPTION	"Defines the type of the fan probe."
	REFERENCE "'Dell|Fan Sensor|003' 3"
	::= { dellFanSensorEntry 3 }

fansStatusAtt4 OBJECT-TYPE
	SYNTAX		INTEGER { 
		other(1),
		unknown(2),
		oK(3),
		nonCritical(4),
		critical(5),
		nonRecoverable(6)
	}
	ACCESS		read-only
	STATUS		mandatory
	DESCRIPTION	"Current status of the fan probe."
	REFERENCE "'Dell|Fan Sensor|003' 4"
	::= { dellFanSensorEntry 4 }

fansReadingAtt5 OBJECT-TYPE
	SYNTAX		DmiInteger
	ACCESS		read-only
	STATUS		mandatory
	DESCRIPTION	"The reading of the fan probe in RPM (or boolean)."
	REFERENCE "'Dell|Fan Sensor|003' 5"
	::= { dellFanSensorEntry 5 }

fansWarningMinAtt6 OBJECT-TYPE
	SYNTAX		DmiDisplaystring
	ACCESS		read-write
	STATUS		mandatory
	DESCRIPTION	"The lower warning threshold for the fan probe set by the
user."
	REFERENCE "'Dell|Fan Sensor|003' 6"
	::= { dellFanSensorEntry 6 }

fansMaxWarnAtt7 OBJECT-TYPE
	SYNTAX		DmiDisplaystring
	ACCESS		read-write
	STATUS		mandatory
	DESCRIPTION	"The upper warning threshold for the fan probe set by the
user."
	REFERENCE "'Dell|Fan Sensor|003' 7"
	::= { dellFanSensorEntry 7 }

fansMinFailAtt8 OBJECT-TYPE
	SYNTAX		DmiInteger
	ACCESS		read-only
	STATUS		mandatory
	DESCRIPTION	"The lower failure threshold for the fan probe."
	REFERENCE "'Dell|Fan Sensor|003' 8"
	::= { dellFanSensorEntry 8 }

fansMaxFailAtt9 OBJECT-TYPE
	SYNTAX		DmiInteger
	ACCESS		read-only
	STATUS		mandatory
	DESCRIPTION	"The upper failure threshold for the fan probe."
	REFERENCE "'Dell|Fan Sensor|003' 9"
	::= { dellFanSensorEntry 9 }

fansLocationAtt10 OBJECT-TYPE
	SYNTAX		DmiDisplaystring
	ACCESS		read-only
	STATUS		mandatory
	DESCRIPTION	"The location of this fan probe within the system."
	REFERENCE "'Dell|Fan Sensor|003' 10"
	::= { dellFanSensorEntry 10 }

SdellVoltageProbe ::= SEQUENCE { 
	dellVoltageProbeState INTEGER,
	voltParentIndexAtt1	DmiInteger,
	voltIndexAtt2	DmiInteger,
	voltTypeAtt3	DmiInteger,
	voltStatusAtt4	DmiInteger,
	voltReadingAtt5	DmiInteger,
	voltMinWarnAtt6	DmiDisplaystring,
	voltMaxWarnAtt7	DmiDisplaystring,
	voltMinFailAtt8	DmiInteger,
	voltMaxFailAtt9	DmiInteger,
	voltLocationAtt10	DmiDisplaystring
}

dellVoltageProbeTable OBJECT-TYPE
	SYNTAX		SEQUENCE OF SdellVoltageProbe
	ACCESS		not-accessible
	STATUS		mandatory
	DESCRIPTION	"The Voltage group contains the data on all the voltage probes
in a system."
	::= { server2 302 }

dellVoltageProbeEntry OBJECT-TYPE
	SYNTAX		SdellVoltageProbe
	ACCESS		not-accessible
	STATUS		mandatory
	DESCRIPTION	"The Voltage group contains the data on all the voltage probes
in a system."
	INDEX		{ DmiCompId,DmiGroupId, voltParentIndexAtt1, voltIndexAtt2 }
	::= { dellVoltageProbeTable 1 }


dellVoltageProbeState OBJECT-TYPE
	SYNTAX		INTEGER { 
		active(1),
		notInService(2),
		notReady(3),
		createAndGo(4),
		createAndWait(5),
		destroy(6)
	}
	ACCESS		read-write
	STATUS		mandatory
	REFERENCE "'Dell|Voltage Probe|002' 0"
	::= { dellVoltageProbeEntry 0 }

voltParentIndexAtt1 OBJECT-TYPE
	SYNTAX		DmiInteger
	ACCESS		read-only
	STATUS		mandatory
	DESCRIPTION	"The chassis this voltage probe is connected to."
	REFERENCE "'Dell|Voltage Probe|002' 1"
	::= { dellVoltageProbeEntry 1 }

voltIndexAtt2 OBJECT-TYPE
	SYNTAX		DmiInteger
	ACCESS		read-only
	STATUS		mandatory
	DESCRIPTION	"the index of the voltage probe within the chassis."
	REFERENCE "'Dell|Voltage Probe|002' 2"
	::= { dellVoltageProbeEntry 2 }

voltTypeAtt3 OBJECT-TYPE
	SYNTAX		INTEGER { 
		other(1),
		unknown(2),
		v33(3),
		v33-1(4),
		v5(5),
		v5-1(6),
		v12(7),
		v12-1(8),
		v15(9),
		core(10)
	}
	ACCESS		read-only
	STATUS		mandatory
	DESCRIPTION	"The type of voltage probe"
	REFERENCE "'Dell|Voltage Probe|002' 3"
	::= { dellVoltageProbeEntry 3 }

voltStatusAtt4 OBJECT-TYPE
	SYNTAX		INTEGER { 
		other(1),
		unknown(2),
		oK(3),
		nonCritical(4),
		critical(5),
		nonRecoverable(6)
	}
	ACCESS		read-only
	STATUS		mandatory
	DESCRIPTION	"Status of the voltage probe."
	REFERENCE "'Dell|Voltage Probe|002' 4"
	::= { dellVoltageProbeEntry 4 }

voltReadingAtt5 OBJECT-TYPE
	SYNTAX		DmiInteger
	ACCESS		read-only
	STATUS		mandatory
	DESCRIPTION	"Current reading of the voltage probe, in millivolts."
	REFERENCE "'Dell|Voltage Probe|002' 5"
	::= { dellVoltageProbeEntry 5 }

voltMinWarnAtt6 OBJECT-TYPE
	SYNTAX		DmiDisplaystring
	ACCESS		read-write
	STATUS		mandatory
	DESCRIPTION	"lower warning threshold value for this voltage probe."
	REFERENCE "'Dell|Voltage Probe|002' 6"
	::= { dellVoltageProbeEntry 6 }

voltMaxWarnAtt7 OBJECT-TYPE
	SYNTAX		DmiDisplaystring
	ACCESS		read-write
	STATUS		mandatory
	DESCRIPTION	"upper warning threshold value for this voltage probe."
	REFERENCE "'Dell|Voltage Probe|002' 7"
	::= { dellVoltageProbeEntry 7 }

voltMinFailAtt8 OBJECT-TYPE
	SYNTAX		DmiInteger
	ACCESS		read-only
	STATUS		mandatory
	DESCRIPTION	"lower failure threshold value for this voltage probe."
	REFERENCE "'Dell|Voltage Probe|002' 8"
	::= { dellVoltageProbeEntry 8 }

voltMaxFailAtt9 OBJECT-TYPE
	SYNTAX		DmiInteger
	ACCESS		read-only
	STATUS		mandatory
	DESCRIPTION	"upper failure threshold value for this voltage probe."
	REFERENCE "'Dell|Voltage Probe|002' 9"
	::= { dellVoltageProbeEntry 9 }

voltLocationAtt10 OBJECT-TYPE
	SYNTAX		DmiDisplaystring
	ACCESS		read-only
	STATUS		mandatory
	DESCRIPTION	"the location of this voltage probe within the system."
	REFERENCE "'Dell|Voltage Probe|002' 10"
	::= { dellVoltageProbeEntry 10 }

SdellCurrentProbe ::= SEQUENCE { 
	dellCurrentProbeState INTEGER,
	ampParentIndexAtt1	DmiInteger,
	ampIndexAtt2	DmiInteger,
	ampTypeAtt3	DmiInteger,
	ampStatusAtt4	DmiInteger,
	ampReadingAtt5	DmiInteger,
	ampMinWarnAtt6	DmiDisplaystring,
	ampMaxWarnAtt7	DmiDisplaystring,
	ampMinFailAtt8	DmiInteger,
	ampMaxFailAtt9	DmiInteger,
	ampLocationAtt10	DmiDisplaystring
}

dellCurrentProbeTable OBJECT-TYPE
	SYNTAX		SEQUENCE OF SdellCurrentProbe
	ACCESS		not-accessible
	STATUS		mandatory
	DESCRIPTION	"The Current group contains the data on all the Current probes
in a system."
	::= { server2 303 }

dellCurrentProbeEntry OBJECT-TYPE
	SYNTAX		SdellCurrentProbe
	ACCESS		not-accessible
	STATUS		mandatory
	DESCRIPTION	"The Current group contains the data on all the Current probes
in a system."
	INDEX		{ DmiCompId,DmiGroupId, ampParentIndexAtt1, ampIndexAtt2 }
	::= { dellCurrentProbeTable 1 }


dellCurrentProbeState OBJECT-TYPE
	SYNTAX		INTEGER { 
		active(1),
		notInService(2),
		notReady(3),
		createAndGo(4),
		createAndWait(5),
		destroy(6)
	}
	ACCESS		read-write
	STATUS		mandatory
	REFERENCE "'Dell|Current Probe|002' 0"
	::= { dellCurrentProbeEntry 0 }

ampParentIndexAtt1 OBJECT-TYPE
	SYNTAX		DmiInteger
	ACCESS		read-only
	STATUS		mandatory
	DESCRIPTION	"The chassis this current probe is connected to."
	REFERENCE "'Dell|Current Probe|002' 1"
	::= { dellCurrentProbeEntry 1 }

ampIndexAtt2 OBJECT-TYPE
	SYNTAX		DmiInteger
	ACCESS		read-only
	STATUS		mandatory
	DESCRIPTION	"the index of the current probe within the chassis."
	REFERENCE "'Dell|Current Probe|002' 2"
	::= { dellCurrentProbeEntry 2 }

ampTypeAtt3 OBJECT-TYPE
	SYNTAX		INTEGER { 
		other(1),
		unknown(2),
		v33(3),
		v33(4),
		v5(5),
		v5(6),
		v12(7),
		v12(8)
	}
	ACCESS		read-only
	STATUS		mandatory
	DESCRIPTION	"The type of current probe"
	REFERENCE "'Dell|Current Probe|002' 3"
	::= { dellCurrentProbeEntry 3 }

ampStatusAtt4 OBJECT-TYPE
	SYNTAX		INTEGER { 
		other(1),
		unknown(2),
		oK(3),
		nonCritical(4),
		critical(5),
		nonRecoverable(6)
	}
	ACCESS		read-only
	STATUS		mandatory
	DESCRIPTION	"Status of the current probe."
	REFERENCE "'Dell|Current Probe|002' 4"
	::= { dellCurrentProbeEntry 4 }

ampReadingAtt5 OBJECT-TYPE
	SYNTAX		DmiInteger
	ACCESS		read-only
	STATUS		mandatory
	DESCRIPTION	"Current reading of the current probe in milliamps."
	REFERENCE "'Dell|Current Probe|002' 5"
	::= { dellCurrentProbeEntry 5 }

ampMinWarnAtt6 OBJECT-TYPE
	SYNTAX		DmiDisplaystring
	ACCESS		read-write
	STATUS		mandatory
	DESCRIPTION	"lower warning threshold value for this current probe."
	REFERENCE "'Dell|Current Probe|002' 6"
	::= { dellCurrentProbeEntry 6 }

ampMaxWarnAtt7 OBJECT-TYPE
	SYNTAX		DmiDisplaystring
	ACCESS		read-write
	STATUS		mandatory
	DESCRIPTION	"upper warning threshold value for this current probe."
	REFERENCE "'Dell|Current Probe|002' 7"
	::= { dellCurrentProbeEntry 7 }

ampMinFailAtt8 OBJECT-TYPE
	SYNTAX		DmiInteger
	ACCESS		read-only
	STATUS		mandatory
	DESCRIPTION	"lower failure threshold value for this current probe."
	REFERENCE "'Dell|Current Probe|002' 8"
	::= { dellCurrentProbeEntry 8 }

ampMaxFailAtt9 OBJECT-TYPE
	SYNTAX		DmiInteger
	ACCESS		read-only
	STATUS		mandatory
	DESCRIPTION	"upper failure threshold value for this current probe."
	REFERENCE "'Dell|Current Probe|002' 9"
	::= { dellCurrentProbeEntry 9 }

ampLocationAtt10 OBJECT-TYPE
	SYNTAX		DmiDisplaystring
	ACCESS		read-only
	STATUS		mandatory
	DESCRIPTION	"the location of this current probe within the system."
	REFERENCE "'Dell|Current Probe|002' 10"
	::= { dellCurrentProbeEntry 10 }

SdellRedundantPowerSupply ::= SEQUENCE { 
	dellRedundantPowerSupplyState INTEGER,
	pwrSupplyParentIndexAtt1	DmiInteger,
	pwrSupplyIndexAtt2	DmiInteger,
	pwrSupplyTypeAtt3	DmiInteger,
	pwrSupplyStatusAtt4	DmiInteger,
	pwrSupplyOnlineAtt5	DmiDisplaystring,
	pwrLocationAtt6	DmiDisplaystring
}

dellRedundantPowerSupplyTable OBJECT-TYPE
	SYNTAX		SEQUENCE OF SdellRedundantPowerSupply
	ACCESS		not-accessible
	STATUS		mandatory
	DESCRIPTION	"The Power Supply group contains the data on all the redundant
power supplies in a system."
	::= { server2 304 }

dellRedundantPowerSupplyEntry OBJECT-TYPE
	SYNTAX		SdellRedundantPowerSupply
	ACCESS		not-accessible
	STATUS		mandatory
	DESCRIPTION	"The Power Supply group contains the data on all the redundant
power supplies in a system."
	INDEX		{ DmiCompId,DmiGroupId, pwrSupplyParentIndexAtt1, pwrSupplyIndexAtt2 }
	::= { dellRedundantPowerSupplyTable 1 }


dellRedundantPowerSupplyState OBJECT-TYPE
	SYNTAX		INTEGER { 
		active(1),
		notInService(2),
		notReady(3),
		createAndGo(4),
		createAndWait(5),
		destroy(6)
	}
	ACCESS		read-write
	STATUS		mandatory
	REFERENCE "'Dell|RedundantPowerSupply|001' 0"
	::= { dellRedundantPowerSupplyEntry 0 }

pwrSupplyParentIndexAtt1 OBJECT-TYPE
	SYNTAX		DmiInteger
	ACCESS		read-only
	STATUS		mandatory
	DESCRIPTION	"The chassis this power supply is connected to."
	REFERENCE "'Dell|RedundantPowerSupply|001' 1"
	::= { dellRedundantPowerSupplyEntry 1 }

pwrSupplyIndexAtt2 OBJECT-TYPE
	SYNTAX		DmiInteger
	ACCESS		read-only
	STATUS		mandatory
	DESCRIPTION	"The index within the chassis of this power supply."
	REFERENCE "'Dell|RedundantPowerSupply|001' 2"
	::= { dellRedundantPowerSupplyEntry 2 }

pwrSupplyTypeAtt3 OBJECT-TYPE
	SYNTAX		INTEGER { 
		other(1),
		unknown(2),
		pSPB(3),
		x230W(4),
		x500W(5),
		x700W(6),
		x320W(7),
		x275W(8)
	}
	ACCESS		read-only
	STATUS		mandatory
	DESCRIPTION	"The type of power supply."
	REFERENCE "'Dell|RedundantPowerSupply|001' 3"
	::= { dellRedundantPowerSupplyEntry 3 }

pwrSupplyStatusAtt4 OBJECT-TYPE
	SYNTAX		INTEGER { 
		other(1),
		unknown(2),
		oK(3),
		nonCritical(4),
		critical(5),
		nonRecoverable(6)
	}
	ACCESS		read-only
	STATUS		mandatory
	DESCRIPTION	"The current status of this power supply."
	REFERENCE "'Dell|RedundantPowerSupply|001' 4"
	::= { dellRedundantPowerSupplyEntry 4 }

pwrSupplyOnlineAtt5 OBJECT-TYPE
	SYNTAX		DmiDisplaystring
	ACCESS		read-write
	STATUS		mandatory
	DESCRIPTION	"The current online status of this power supply. Setting this
value to FALSE will turn off the power supply, setting it to TRUE will turn
on the power supply. "
	REFERENCE "'Dell|RedundantPowerSupply|001' 5"
	::= { dellRedundantPowerSupplyEntry 5 }

pwrLocationAtt6 OBJECT-TYPE
	SYNTAX		DmiDisplaystring
	ACCESS		read-only
	STATUS		mandatory
	DESCRIPTION	"the location of this power supply within the system."
	REFERENCE "'Dell|RedundantPowerSupply|001' 6"
	::= { dellRedundantPowerSupplyEntry 6 }

SdellGlobalPowerUnit ::= SEQUENCE { 
	dellGlobalPowerUnitState INTEGER,
	pwrUnitStatusAtt1	DmiInteger,
	pwrUnitGlobalLevelAtt2	DmiInteger,
	pwrUnitGlobalMaxWarnAtt3	DmiDisplaystring,
	pwrUnitLevel33vAtt4	DmiInteger,
	pwrUnitMaxWarn33vAtt5	DmiDisplaystring,
	pwrUnitLevel5vAtt6	DmiInteger,
	pwrUnitMaxWarn5vAtt7	DmiDisplaystring,
	pwrUnitLevel12vAtt8	DmiInteger,
	pwrUnitMaxWarn12vAtt9	DmiDisplaystring,
	pwrUnitUidAtt10	DmiDisplaystring,
	pwrUnitIndexAtt11	DmiInteger
}

dellGlobalPowerUnitTable OBJECT-TYPE
	SYNTAX		SEQUENCE OF SdellGlobalPowerUnit
	ACCESS		not-accessible
	STATUS		mandatory
	DESCRIPTION	"This group contains the global status for the power supplies
in the system."
	::= { server2 305 }

dellGlobalPowerUnitEntry OBJECT-TYPE
	SYNTAX		SdellGlobalPowerUnit
	ACCESS		not-accessible
	STATUS		mandatory
	DESCRIPTION	"This group contains the global status for the power supplies
in the system."
	INDEX		{ DmiCompId,DmiGroupId, pwrUnitIndexAtt11 }
	::= { dellGlobalPowerUnitTable 1 }


dellGlobalPowerUnitState OBJECT-TYPE
	SYNTAX		INTEGER { 
		active(1),
		notInService(2),
		notReady(3),
		createAndGo(4),
		createAndWait(5),
		destroy(6)
	}
	ACCESS		read-write
	STATUS		mandatory
	REFERENCE "'Dell|GlobalPowerUnit|003' 0"
	::= { dellGlobalPowerUnitEntry 0 }

pwrUnitStatusAtt1 OBJECT-TYPE
	SYNTAX		INTEGER { 
		other(1),
		unknown(2),
		notApplicableUnitNotRedundant(3),
		offline(4),
		fullyRedundant(5),
		degradedRedundancy(6),
		redundancyLost(7)
	}
	ACCESS		read-only
	STATUS		mandatory
	DESCRIPTION	"The current redundancy status of the power unit."
	REFERENCE "'Dell|GlobalPowerUnit|003' 1"
	::= { dellGlobalPowerUnitEntry 1 }

pwrUnitGlobalLevelAtt2 OBJECT-TYPE
	SYNTAX		DmiInteger
	ACCESS		read-only
	STATUS		mandatory
	DESCRIPTION	"The current global power level usage, in percent."
	REFERENCE "'Dell|GlobalPowerUnit|003' 2"
	::= { dellGlobalPowerUnitEntry 2 }

pwrUnitGlobalMaxWarnAtt3 OBJECT-TYPE
	SYNTAX		DmiDisplaystring
	ACCESS		read-write
	STATUS		mandatory
	DESCRIPTION	"Warning threshold, in percent"
	REFERENCE "'Dell|GlobalPowerUnit|003' 3"
	::= { dellGlobalPowerUnitEntry 3 }

pwrUnitLevel33vAtt4 OBJECT-TYPE
	SYNTAX		DmiInteger
	ACCESS		read-only
	STATUS		mandatory
	DESCRIPTION	"The current 3.3v power level usage, in percent."
	REFERENCE "'Dell|GlobalPowerUnit|003' 4"
	::= { dellGlobalPowerUnitEntry 4 }

pwrUnitMaxWarn33vAtt5 OBJECT-TYPE
	SYNTAX		DmiDisplaystring
	ACCESS		read-write
	STATUS		mandatory
	DESCRIPTION	"Warning threshold, in percent"
	REFERENCE "'Dell|GlobalPowerUnit|003' 5"
	::= { dellGlobalPowerUnitEntry 5 }

pwrUnitLevel5vAtt6 OBJECT-TYPE
	SYNTAX		DmiInteger
	ACCESS		read-only
	STATUS		mandatory
	DESCRIPTION	"The current 5v power level usage, in percent."
	REFERENCE "'Dell|GlobalPowerUnit|003' 6"
	::= { dellGlobalPowerUnitEntry 6 }

pwrUnitMaxWarn5vAtt7 OBJECT-TYPE
	SYNTAX		DmiDisplaystring
	ACCESS		read-write
	STATUS		mandatory
	DESCRIPTION	"Warning threshold, in percent"
	REFERENCE "'Dell|GlobalPowerUnit|003' 7"
	::= { dellGlobalPowerUnitEntry 7 }

pwrUnitLevel12vAtt8 OBJECT-TYPE
	SYNTAX		DmiInteger
	ACCESS		read-only
	STATUS		mandatory
	DESCRIPTION	"The current 12v power level usage, in percent."
	REFERENCE "'Dell|GlobalPowerUnit|003' 8"
	::= { dellGlobalPowerUnitEntry 8 }

pwrUnitMaxWarn12vAtt9 OBJECT-TYPE
	SYNTAX		DmiDisplaystring
	ACCESS		read-write
	STATUS		mandatory
	DESCRIPTION	"Warning threshold, in percent"
	REFERENCE "'Dell|GlobalPowerUnit|003' 9"
	::= { dellGlobalPowerUnitEntry 9 }

pwrUnitUidAtt10 OBJECT-TYPE
	SYNTAX		DmiDisplaystring
	ACCESS		read-only
	STATUS		mandatory
	DESCRIPTION	"The unique ID for this power supply unit."
	REFERENCE "'Dell|GlobalPowerUnit|003' 10"
	::= { dellGlobalPowerUnitEntry 10 }

pwrUnitIndexAtt11 OBJECT-TYPE
	SYNTAX		DmiInteger
	ACCESS		read-only
	STATUS		mandatory
	DESCRIPTION	"The index into the power supply unit table."
	REFERENCE "'Dell|GlobalPowerUnit|003' 11"
	::= { dellGlobalPowerUnitEntry 11 }

SdellSystemChassisExtension ::= SEQUENCE { 
	dellSystemChassisExtensionState INTEGER,
	chassIndexAtt1	DmiInteger,
	chassGlobStatusAtt2	DmiInteger,
	chassTempStatusAtt3	DmiInteger,
	chassTempProbesAtt4	DmiOctetstring,
	chassFansStatusAtt5	DmiInteger,
	chassFansProbesAtt6	DmiOctetstring,
	chassVoltStatusAtt7	DmiInteger,
	chassVoltProbesAtt8	DmiOctetstring,
	chassAmpStatusAtt9	DmiInteger,
	chassAmpProbesAtt10	DmiOctetstring,
	chassPsStatusAtt11	DmiInteger,
	chassPwrSuppliesAtt12	DmiOctetstring,
	chassServiceTagAtt13	DmiDisplaystring,
	chassUidAtt14	DmiDisplaystring,
	chassBackPlaneUidAtt15	DmiDisplaystring,
	chassIdentifyAtt16	DmiDisplaystring,
	chassFanControlAtt17	DmiDisplaystring,
	chassLEDConfigAtt18	DmiDisplaystring,
	chassFaultClearAtt19	DmiDisplaystring,
	chassThermalShutdownAtt20	DmiDisplaystring,
	chassMemStatusAtt21	DmiInteger,
	chassMemDevicesAtt22	DmiOctetstring
}

dellSystemChassisExtensionTable OBJECT-TYPE
	SYNTAX		SEQUENCE OF SdellSystemChassisExtension
	ACCESS		not-accessible
	STATUS		mandatory
	DESCRIPTION	"Global status of devices in chassis."
	::= { server2 306 }

dellSystemChassisExtensionEntry OBJECT-TYPE
	SYNTAX		SdellSystemChassisExtension
	ACCESS		not-accessible
	STATUS		mandatory
	DESCRIPTION	"Global status of devices in chassis."
	INDEX		{ DmiCompId,DmiGroupId, chassIndexAtt1 }
	::= { dellSystemChassisExtensionTable 1 }


dellSystemChassisExtensionState OBJECT-TYPE
	SYNTAX		INTEGER { 
		active(1),
		notInService(2),
		notReady(3),
		createAndGo(4),
		createAndWait(5),
		destroy(6)
	}
	ACCESS		read-write
	STATUS		mandatory
	REFERENCE "'Dell|SystemChassisExtension|004' 0"
	::= { dellSystemChassisExtensionEntry 0 }

chassIndexAtt1 OBJECT-TYPE
	SYNTAX		DmiInteger
	ACCESS		read-only
	STATUS		mandatory
	DESCRIPTION	"Physical container index"
	REFERENCE "'Dell|SystemChassisExtension|004' 1"
	::= { dellSystemChassisExtensionEntry 1 }

chassGlobStatusAtt2 OBJECT-TYPE
	SYNTAX		INTEGER { 
		other(1),
		unknown(2),
		oK(3),
		nonCritical(4),
		critical(5),
		nonRecoverable(6)
	}
	ACCESS		read-only
	STATUS		mandatory
	DESCRIPTION	"Global status of all devices in chassis."
	REFERENCE "'Dell|SystemChassisExtension|004' 2"
	::= { dellSystemChassisExtensionEntry 2 }

chassTempStatusAtt3 OBJECT-TYPE
	SYNTAX		INTEGER { 
		other(1),
		unknown(2),
		oK(3),
		nonCritical(4),
		critical(5),
		nonRecoverable(6)
	}
	ACCESS		read-only
	STATUS		mandatory
	DESCRIPTION	"Global status of temperature probes."
	REFERENCE "'Dell|SystemChassisExtension|004' 3"
	::= { dellSystemChassisExtensionEntry 3 }

chassTempProbesAtt4 OBJECT-TYPE
	SYNTAX		DmiOctetstring
	ACCESS		read-only
	STATUS		mandatory
	DESCRIPTION	"This contains the statuses of all temp probes in the system,
one probe per octet.  The value of each octet is the value of the status
field."
	REFERENCE "'Dell|SystemChassisExtension|004' 4"
	::= { dellSystemChassisExtensionEntry 4 }

chassFansStatusAtt5 OBJECT-TYPE
	SYNTAX		INTEGER { 
		other(1),
		unknown(2),
		oK(3),
		nonCritical(4),
		critical(5),
		nonRecoverable(6)
	}
	ACCESS		read-only
	STATUS		mandatory
	DESCRIPTION	"Global status of fan sensors."
	REFERENCE "'Dell|SystemChassisExtension|004' 5"
	::= { dellSystemChassisExtensionEntry 5 }

chassFansProbesAtt6 OBJECT-TYPE
	SYNTAX		DmiOctetstring
	ACCESS		read-only
	STATUS		mandatory
	DESCRIPTION	"This contains the statuses of all fan probes in the system,
one probe per octet.  The value of each octet is the value of the status
field."
	REFERENCE "'Dell|SystemChassisExtension|004' 6"
	::= { dellSystemChassisExtensionEntry 6 }

chassVoltStatusAtt7 OBJECT-TYPE
	SYNTAX		INTEGER { 
		other(1),
		unknown(2),
		oK(3),
		nonCritical(4),
		critical(5),
		nonRecoverable(6)
	}
	ACCESS		read-only
	STATUS		mandatory
	DESCRIPTION	"Global status of voltage probes."
	REFERENCE "'Dell|SystemChassisExtension|004' 7"
	::= { dellSystemChassisExtensionEntry 7 }

chassVoltProbesAtt8 OBJECT-TYPE
	SYNTAX		DmiOctetstring
	ACCESS		read-only
	STATUS		mandatory
	DESCRIPTION	"This contains the statuses of all volt probes in the system,
one probe per octet.  The value of each octet is the value of the status
field."
	REFERENCE "'Dell|SystemChassisExtension|004' 8"
	::= { dellSystemChassisExtensionEntry 8 }

chassAmpStatusAtt9 OBJECT-TYPE
	SYNTAX		INTEGER { 
		other(1),
		unknown(2),
		oK(3),
		nonCritical(4),
		critical(5),
		nonRecoverable(6)
	}
	ACCESS		read-only
	STATUS		mandatory
	DESCRIPTION	"Global status of current probes."
	REFERENCE "'Dell|SystemChassisExtension|004' 9"
	::= { dellSystemChassisExtensionEntry 9 }

chassAmpProbesAtt10 OBJECT-TYPE
	SYNTAX		DmiOctetstring
	ACCESS		read-only
	STATUS		mandatory
	DESCRIPTION	"This contains the statuses of all amp probes in the system,
one probe per octet.  The value of each octet is the value of the status
field."
	REFERENCE "'Dell|SystemChassisExtension|004' 10"
	::= { dellSystemChassisExtensionEntry 10 }

chassPsStatusAtt11 OBJECT-TYPE
	SYNTAX		INTEGER { 
		other(1),
		unknown(2),
		oK(3),
		nonCritical(4),
		critical(5),
		nonRecoverable(6)
	}
	ACCESS		read-only
	STATUS		mandatory
	DESCRIPTION	"Global status of power supplies."
	REFERENCE "'Dell|SystemChassisExtension|004' 11"
	::= { dellSystemChassisExtensionEntry 11 }

chassPwrSuppliesAtt12 OBJECT-TYPE
	SYNTAX		DmiOctetstring
	ACCESS		read-only
	STATUS		mandatory
	DESCRIPTION	"This contains the statuses of all power supplies in the system,
one probe per octet.  The value of each octet is the value of the status
field."
	REFERENCE "'Dell|SystemChassisExtension|004' 12"
	::= { dellSystemChassisExtensionEntry 12 }

chassServiceTagAtt13 OBJECT-TYPE
	SYNTAX		DmiDisplaystring
	ACCESS		read-only
	STATUS		mandatory
	DESCRIPTION	"This is the service tag for this chassis, if it exists."
	REFERENCE "'Dell|SystemChassisExtension|004' 13"
	::= { dellSystemChassisExtensionEntry 13 }

chassUidAtt14 OBJECT-TYPE
	SYNTAX		DmiDisplaystring
	ACCESS		read-only
	STATUS		mandatory
	DESCRIPTION	"This is the Unique ID for this chassis, if it exists."
	REFERENCE "'Dell|SystemChassisExtension|004' 14"
	::= { dellSystemChassisExtensionEntry 14 }

chassBackPlaneUidAtt15 OBJECT-TYPE
	SYNTAX		DmiDisplaystring
	ACCESS		read-only
	STATUS		mandatory
	DESCRIPTION	"This is the Unique ID for the backplane in this chassis."
	REFERENCE "'Dell|SystemChassisExtension|004' 15"
	::= { dellSystemChassisExtensionEntry 15 }

chassIdentifyAtt16 OBJECT-TYPE
	SYNTAX		DmiDisplaystring
	ACCESS		read-write
	STATUS		mandatory
	DESCRIPTION	"This attribute is used to visually identify a disk pod or
other chassis by causing its lights to flash. Setting this value to non-zero
turns on the identify, setting it back to zero turns it off."
	REFERENCE "'Dell|SystemChassisExtension|004' 16"
	::= { dellSystemChassisExtensionEntry 16 }

chassFanControlAtt17 OBJECT-TYPE
	SYNTAX		DmiDisplaystring
	ACCESS		read-write
	STATUS		mandatory
	DESCRIPTION	"This attribute is used to control the fan speed in a chassis.
 If the value is 0, then fan control is notavailable.  A value of 2 indicates
maximum cooling.  Avalue of 1 indicates minimize fan noise (and speed)."
	REFERENCE "'Dell|SystemChassisExtension|004' 17"
	::= { dellSystemChassisExtensionEntry 17 }

chassLEDConfigAtt18 OBJECT-TYPE
	SYNTAX		DmiDisplaystring
	ACCESS		read-write
	STATUS		mandatory
	DESCRIPTION	"This attribute is used to configure which fault conditionscause
the fault LED to flash.  If the value is 0, thenthis feature is not available.
 A value of 16 indicatesflash for failure conditions.  A value of 8 indicatesfla
h for failure and warning conditions."
	REFERENCE "'Dell|SystemChassisExtension|004' 18"
	::= { dellSystemChassisExtensionEntry 18 }

chassFaultClearAtt19 OBJECT-TYPE
	SYNTAX		DmiDisplaystring
	ACCESS		read-write
	STATUS		mandatory
	DESCRIPTION	"This attribute is used to clear the hard drive fault LED.If
this value is non-zero, then it is available.  Writingany value to this attribut
 will clear the hard drive faultLED."
	REFERENCE "'Dell|SystemChassisExtension|004' 19"
	::= { dellSystemChassisExtensionEntry 19 }

chassThermalShutdownAtt20 OBJECT-TYPE
	SYNTAX		DmiDisplaystring
	ACCESS		read-write
	STATUS		mandatory
	DESCRIPTION	"This attribute is used to enable thermal shutdown of a chassis.
 If the value is -1, then thermal shutdown is notenabled.  A value of 5 will
shutdown on failures, a value of 4will shutdown on failures and warnings."
	REFERENCE "'Dell|SystemChassisExtension|004' 20"
	::= { dellSystemChassisExtensionEntry 20 }

chassMemStatusAtt21 OBJECT-TYPE
	SYNTAX		INTEGER { 
		other(1),
		unknown(2),
		oK(3),
		nonCritical(4),
		critical(5),
		nonRecoverable(6)
	}
	ACCESS		read-only
	STATUS		mandatory
	DESCRIPTION	"Global status of Memory Devices."
	REFERENCE "'Dell|SystemChassisExtension|004' 21"
	::= { dellSystemChassisExtensionEntry 21 }

chassMemDevicesAtt22 OBJECT-TYPE
	SYNTAX		DmiOctetstring
	ACCESS		read-only
	STATUS		mandatory
	DESCRIPTION	"This contains the statuses of all memory devices in the system,
one device per octet.  The value of each octet is the value of the status
field."
	REFERENCE "'Dell|SystemChassisExtension|004' 22"
	::= { dellSystemChassisExtensionEntry 22 }

SdMTFPhysicalContainerGlobalTable ::= SEQUENCE { 
	dMTFPhysicalContainerGlobalTableState INTEGER,
	containerOrChassisTypeAtt1	DmiInteger,
	assetTagAtt2	DmiDisplaystring,
	chassisLockPresentAtt3	DmiInteger,
	bootupStateAtt4	DmiInteger,
	powerStateAtt5	DmiInteger,
	thermalStateAtt6	DmiInteger,
	fRUGroupIndexAtt7	DmiInteger,
	operationalGroupIndexAtt8	DmiInteger,
	containerIndexAtt9	DmiInteger,
	containerNameAtt10	DmiDisplaystring,
	containerLocationAtt11	DmiDisplaystring,
	containerSecurityStatusAtt12	DmiInteger
}
dmtfSystemsMIF	OBJECT IDENTIFIER ::= { dmtfStdMifs 4 }

dMTFPhysicalContainerGlobalTableTable OBJECT-TYPE
	SYNTAX		SEQUENCE OF SdMTFPhysicalContainerGlobalTable
	ACCESS		not-accessible
	STATUS		mandatory
	DESCRIPTION	"This group of attributes describes the fields in a row ofthe
Physical Container Global Table. This table lists all of the containers (e.g.
chassis, sub-chassis, etc.) included within the component whose structure
is being described"
	::= { dmtfSystemsMIF 63 }

dMTFPhysicalContainerGlobalTableEntry OBJECT-TYPE
	SYNTAX		SdMTFPhysicalContainerGlobalTable
	ACCESS		not-accessible
	STATUS		mandatory
	DESCRIPTION	"This group of attributes describes the fields in a row ofthe
Physical Container Global Table. This table lists all of the containers (e.g.
chassis, sub-chassis, etc.) included within the component whose structure
is being described"
	INDEX		{ DmiCompId,DmiGroupId, containerIndexAtt9 }
	::= { dMTFPhysicalContainerGlobalTableTable 1 }


dMTFPhysicalContainerGlobalTableState OBJECT-TYPE
	SYNTAX		INTEGER { 
		active(1),
		notInService(2),
		notReady(3),
		createAndGo(4),
		createAndWait(5),
		destroy(6)
	}
	ACCESS		read-write
	STATUS		mandatory
	REFERENCE "'DMTF|Physical Container Global Table|002' 0"
	::= { dMTFPhysicalContainerGlobalTableEntry 0 }

containerOrChassisTypeAtt1 OBJECT-TYPE
	SYNTAX		INTEGER { 
		other(1),
		unknown(2),
		desktop(3),
		lowProfileDesktop(4),
		pizzaBox(5),
		miniTower(6),
		tower(7),
		portable(8),
		lapTop(9),
		notebook(10),
		handHeld(11),
		dockingStation(12),
		allInOne(13),
		subNotebook(14),
		spaceSaving(15),
		lunchBox(16),
		mainSystemChassis(17),
		expansionChassis(18),
		subChassis(19),
		busExpansionChassis(20),
		peripheralChassis(21),
		rAIDChassis(22),
		rackMountChassis(23),
		sealedCasePC(24)
	}
	ACCESS		read-only
	STATUS		mandatory
	DESCRIPTION	"The type of container or chassis."
	REFERENCE "'DMTF|Physical Container Global Table|002' 1"
	::= { dMTFPhysicalContainerGlobalTableEntry 1 }

assetTagAtt2 OBJECT-TYPE
	SYNTAX		DmiDisplaystring
	ACCESS		read-write
	STATUS		mandatory
	DESCRIPTION	"The Container asset tag string. This asset tag string is
writeable by the system administrator."
	REFERENCE "'DMTF|Physical Container Global Table|002' 2"
	::= { dMTFPhysicalContainerGlobalTableEntry 2 }

chassisLockPresentAtt3 OBJECT-TYPE
	SYNTAX		INTEGER { 
		false(0),
		true(1)
	}
	ACCESS		read-only
	STATUS		mandatory
	DESCRIPTION	"If true, a chassis lock is present on the Container."
	REFERENCE "'DMTF|Physical Container Global Table|002' 3"
	::= { dMTFPhysicalContainerGlobalTableEntry 3 }

bootupStateAtt4 OBJECT-TYPE
	SYNTAX		INTEGER { 
		other(1),
		unknown(2),
		oK(3),
		warning(4),
		critical(5),
		nonRecoverable-1(6)
	}
	ACCESS		read-only
	STATUS		mandatory
	DESCRIPTION	"The current state of this system when it booted."
	REFERENCE "'DMTF|Physical Container Global Table|002' 4"
	::= { dMTFPhysicalContainerGlobalTableEntry 4 }

powerStateAtt5 OBJECT-TYPE
	SYNTAX		INTEGER { 
		other(1),
		unknown(2),
		oK(3),
		warning(4),
		critical(5),
		nonRecoverable(6)
	}
	ACCESS		read-only
	STATUS		mandatory
	DESCRIPTION	"The current state of the power supply or battery(s) for this
system."
	REFERENCE "'DMTF|Physical Container Global Table|002' 5"
	::= { dMTFPhysicalContainerGlobalTableEntry 5 }

thermalStateAtt6 OBJECT-TYPE
	SYNTAX		INTEGER { 
		other(1),
		unknown(2),
		oK(3),
		warning(4),
		critical(5),
		nonRecoverable(6)
	}
	ACCESS		read-only
	STATUS		mandatory
	DESCRIPTION	"The current thermal state of this Container."
	REFERENCE "'DMTF|Physical Container Global Table|002' 6"
	::= { dMTFPhysicalContainerGlobalTableEntry 6 }

fRUGroupIndexAtt7 OBJECT-TYPE
	SYNTAX		DmiInteger
	ACCESS		read-only
	STATUS		mandatory
	DESCRIPTION	"If this is a Field Replaceable Unit or if it is part of another
FRU, this provides an index into the FRU table; 'value = -1' indicates that
the group is not a FRU."
	REFERENCE "'DMTF|Physical Container Global Table|002' 7"
	::= { dMTFPhysicalContainerGlobalTableEntry 7 }

operationalGroupIndexAtt8 OBJECT-TYPE
	SYNTAX		DmiInteger
	ACCESS		read-only
	STATUS		mandatory
	DESCRIPTION	"The index into the Operational State table for this device
if applicable."
	REFERENCE "'DMTF|Physical Container Global Table|002' 8"
	::= { dMTFPhysicalContainerGlobalTableEntry 8 }

containerIndexAtt9 OBJECT-TYPE
	SYNTAX		DmiInteger
	ACCESS		read-only
	STATUS		mandatory
	DESCRIPTION	"A unique index for the Physical Container in Physical Container
Global Table."
	REFERENCE "'DMTF|Physical Container Global Table|002' 9"
	::= { dMTFPhysicalContainerGlobalTableEntry 9 }

containerNameAtt10 OBJECT-TYPE
	SYNTAX		DmiDisplaystring
	ACCESS		read-write
	STATUS		mandatory
	DESCRIPTION	"This is any 64-octet long name that the user or system administr
tor wishes to give this specific physical container."
	REFERENCE "'DMTF|Physical Container Global Table|002' 10"
	::= { dMTFPhysicalContainerGlobalTableEntry 10 }

containerLocationAtt11 OBJECT-TYPE
	SYNTAX		DmiDisplaystring
	ACCESS		read-write
	STATUS		mandatory
	DESCRIPTION	"This attribute is a string name for the location of the containe
.  This attribute is Read-Write and may be set to any appropriate value by
the user. The string may be 128 octets long."
	REFERENCE "'DMTF|Physical Container Global Table|002' 11"
	::= { dMTFPhysicalContainerGlobalTableEntry 11 }

containerSecurityStatusAtt12 OBJECT-TYPE
	SYNTAX		INTEGER { 
		other(1),
		unknown(2),
		noSecurityBreachDetected(3),
		containerSecurityBreachAttempted(4),
		containerSecurityBreached(5)
	}
	ACCESS		read-only
	STATUS		mandatory
	DESCRIPTION	"This attribute describes whether the Container is physically
secure or not. This includes the state of the door lock, or the boot devices
or the keyboard or mouse."
	REFERENCE "'DMTF|Physical Container Global Table|002' 12"
	::= { dMTFPhysicalContainerGlobalTableEntry 12 }

SdellSystemReset ::= SEQUENCE { 
	automaticCapabilitiesAtt1	DmiInteger,
	automaticSettingsAtt2	DmiDisplaystring,
	notificationNumberAtt3	DmiDisplaystring,
	manualCapabilitiesAtt4	DmiInteger,
	manualControlAtt5	DmiDisplaystring,
	automaticSystemResetTimerAtt6	DmiDisplaystring
}

dellSystemResetTable OBJECT-TYPE
	SYNTAX		SEQUENCE OF SdellSystemReset
	ACCESS		not-accessible
	STATUS		mandatory
	DESCRIPTION	"This group defines whether System Control functions are availabl
 and enabled."
	::= { server2 312 }

dellSystemResetEntry OBJECT-TYPE
	SYNTAX		SdellSystemReset
	ACCESS		not-accessible
	STATUS		mandatory
	DESCRIPTION	"This group defines whether System Control functions are availabl
 and enabled."
	INDEX		{ DmiCompId,DmiGroupId }
	::= { dellSystemResetTable 1 }


automaticCapabilitiesAtt1 OBJECT-TYPE
	SYNTAX		DmiInteger
	ACCESS		read-only
	STATUS		mandatory
	DESCRIPTION	"Indicates which Automatic  Capabilities are available for
the current operating system. Encoding is as follows:   0x1 = Supports Reboot
 0x2 = Supports Power Cycle  0x4 = Supports Notification  0x8 = Supports
Configurable Timer If value is nonzero, Watchdog is supported."
	REFERENCE "'Dell|System Reset|001' 1"
	::= { dellSystemResetEntry 1 }

automaticSettingsAtt2 OBJECT-TYPE
	SYNTAX		DmiDisplaystring
	ACCESS		read-write
	STATUS		mandatory
	DESCRIPTION	"Indicates which Automatic Settings are enabled by the user.
Encoding is as follows:  0x1 = Enabled w/ Reboot 0x2 = Enabled w/ Power Cycle
0x4 = Enabled w/ Notification If value is nonzero, Watchdog is Enabled."
	REFERENCE "'Dell|System Reset|001' 2"
	::= { dellSystemResetEntry 2 }

notificationNumberAtt3 OBJECT-TYPE
	SYNTAX		DmiDisplaystring
	ACCESS		read-write
	STATUS		mandatory
	DESCRIPTION	"The number to dial when the watchdog timer elapses."
	REFERENCE "'Dell|System Reset|001' 3"
	::= { dellSystemResetEntry 3 }

manualCapabilitiesAtt4 OBJECT-TYPE
	SYNTAX		DmiInteger
	ACCESS		read-only
	STATUS		mandatory
	DESCRIPTION	"Describes which system reset actions may occur.Bit encodings:
                                 0x1 = Reboot 0x2 = Power Off 0x4 = Power
Cycle 0x8 = Shutdown OS"
	REFERENCE "'Dell|System Reset|001' 4"
	::= { dellSystemResetEntry 4 }

manualControlAtt5 OBJECT-TYPE
	SYNTAX		DmiDisplaystring
	ACCESS		read-write
	STATUS		mandatory
	DESCRIPTION	"Setting this value will immediately perform one of the following
functions. Encoding as follows: Bit encoding:  0x1 = Reboot  0x2 = Power
Off  0x4 = Power Cycle  0x8 = Shutdown OS"
	REFERENCE "'Dell|System Reset|001' 5"
	::= { dellSystemResetEntry 5 }

automaticSystemResetTimerAtt6 OBJECT-TYPE
	SYNTAX		DmiDisplaystring
	ACCESS		read-write
	STATUS		mandatory
	DESCRIPTION	"Automatic System Reset Timer in seconds. Minimum value is
20 seconds."
	REFERENCE "'Dell|System Reset|001' 6"
	::= { dellSystemResetEntry 6 }

SdellEsmLog ::= SEQUENCE { 
	dellEsmLogState INTEGER,
	esmLogIndexAtt1	DmiInteger,
	esmLogDataAtt2	DmiDisplaystring
}

dellEsmLogTable OBJECT-TYPE
	SYNTAX		SEQUENCE OF SdellEsmLog
	ACCESS		not-accessible
	STATUS		mandatory
	DESCRIPTION	"ESM Event Log."
	::= { server2 307 }

dellEsmLogEntry OBJECT-TYPE
	SYNTAX		SdellEsmLog
	ACCESS		not-accessible
	STATUS		mandatory
	DESCRIPTION	"ESM Event Log."
	INDEX		{ DmiCompId,DmiGroupId, esmLogIndexAtt1 }
	::= { dellEsmLogTable 1 }


dellEsmLogState OBJECT-TYPE
	SYNTAX		INTEGER { 
		active(1),
		notInService(2),
		notReady(3),
		createAndGo(4),
		createAndWait(5),
		destroy(6)
	}
	ACCESS		read-write
	STATUS		mandatory
	REFERENCE "'Dell|EsmLog|001' 0"
	::= { dellEsmLogEntry 0 }

esmLogIndexAtt1 OBJECT-TYPE
	SYNTAX		DmiInteger
	ACCESS		read-only
	STATUS		mandatory
	DESCRIPTION	"KEY: The index to this log."
	REFERENCE "'Dell|EsmLog|001' 1"
	::= { dellEsmLogEntry 1 }

esmLogDataAtt2 OBJECT-TYPE
	SYNTAX		DmiDisplaystring
	ACCESS		read-write
	STATUS		mandatory
	DESCRIPTION	"The event log data for the ESM."
	REFERENCE "'Dell|EsmLog|001' 2"
	::= { dellEsmLogEntry 2 }

SdellPOSTLog ::= SEQUENCE { 
	dellPOSTLogState INTEGER,
	postLogIndexAtt1	DmiInteger,
	postLogDataAtt2	DmiOctetstring
}

dellPOSTLogTable OBJECT-TYPE
	SYNTAX		SEQUENCE OF SdellPOSTLog
	ACCESS		not-accessible
	STATUS		mandatory
	DESCRIPTION	"POST Codes Event Log."
	::= { server2 308 }

dellPOSTLogEntry OBJECT-TYPE
	SYNTAX		SdellPOSTLog
	ACCESS		not-accessible
	STATUS		mandatory
	DESCRIPTION	"POST Codes Event Log."
	INDEX		{ DmiCompId,DmiGroupId, postLogIndexAtt1 }
	::= { dellPOSTLogTable 1 }


dellPOSTLogState OBJECT-TYPE
	SYNTAX		INTEGER { 
		active(1),
		notInService(2),
		notReady(3),
		createAndGo(4),
		createAndWait(5),
		destroy(6)
	}
	ACCESS		read-write
	STATUS		mandatory
	REFERENCE "'Dell|POSTLog|001' 0"
	::= { dellPOSTLogEntry 0 }

postLogIndexAtt1 OBJECT-TYPE
	SYNTAX		DmiInteger
	ACCESS		read-only
	STATUS		mandatory
	DESCRIPTION	"KEY: The index into the post log."
	REFERENCE "'Dell|POSTLog|001' 1"
	::= { dellPOSTLogEntry 1 }

postLogDataAtt2 OBJECT-TYPE
	SYNTAX		DmiOctetstring
	ACCESS		read-only
	STATUS		mandatory
	DESCRIPTION	"The event log data."
	REFERENCE "'Dell|POSTLog|001' 2"
	::= { dellPOSTLogEntry 2 }

SdellSecurity ::= SEQUENCE { 
	dellSecurityState INTEGER,
	userIndexAtt1	DmiInteger,
	userNameAtt2	DmiDisplaystring,
	userControlAtt3	DmiDisplaystring,
	requestAtt4	DmiDisplaystring
}

dellSecurityTable OBJECT-TYPE
	SYNTAX		SEQUENCE OF SdellSecurity
	ACCESS		not-accessible
	STATUS		mandatory
	DESCRIPTION	"Security Group - contains user database: Used by both DSA
and Baseboard components."
	::= { server2 309 }

dellSecurityEntry OBJECT-TYPE
	SYNTAX		SdellSecurity
	ACCESS		not-accessible
	STATUS		mandatory
	DESCRIPTION	"Security Group - contains user database: Used by both DSA
and Baseboard components."
	INDEX		{ DmiCompId,DmiGroupId, userIndexAtt1 }
	::= { dellSecurityTable 1 }


dellSecurityState OBJECT-TYPE
	SYNTAX		INTEGER { 
		active(1),
		notInService(2),
		notReady(3),
		createAndGo(4),
		createAndWait(5),
		destroy(6)
	}
	ACCESS		read-write
	STATUS		mandatory
	REFERENCE "'Dell|Security|001' 0"
	::= { dellSecurityEntry 0 }

userIndexAtt1 OBJECT-TYPE
	SYNTAX		DmiInteger
	ACCESS		read-only
	STATUS		mandatory
	DESCRIPTION	"Keyed ID for this group."
	REFERENCE "'Dell|Security|001' 1"
	::= { dellSecurityEntry 1 }

userNameAtt2 OBJECT-TYPE
	SYNTAX		DmiDisplaystring
	ACCESS		read-only
	STATUS		mandatory
	DESCRIPTION	"User name. First user name is 'create', allows creation."
	REFERENCE "'Dell|Security|001' 2"
	::= { dellSecurityEntry 2 }

userControlAtt3 OBJECT-TYPE
	SYNTAX		DmiDisplaystring
	ACCESS		read-write
	STATUS		mandatory
	DESCRIPTION	"User control. Used for creating/deleting/editing users."
	REFERENCE "'Dell|Security|001' 3"
	::= { dellSecurityEntry 3 }

requestAtt4 OBJECT-TYPE
	SYNTAX		DmiDisplaystring
	ACCESS		read-write
	STATUS		mandatory
	DESCRIPTION	"Request field used for sets."
	REFERENCE "'Dell|Security|001' 4"
	::= { dellSecurityEntry 4 }

SdellDialup ::= SEQUENCE { 
	dialupCapabilityAtt1	DmiInteger,
	callbackNumberAtt2	DmiDisplaystring
}

dellDialupTable OBJECT-TYPE
	SYNTAX		SEQUENCE OF SdellDialup
	ACCESS		not-accessible
	STATUS		mandatory
	DESCRIPTION	"Dialup Control - contains information used by the ESM dialup
interface."
	::= { server2 310 }

dellDialupEntry OBJECT-TYPE
	SYNTAX		SdellDialup
	ACCESS		not-accessible
	STATUS		mandatory
	DESCRIPTION	"Dialup Control - contains information used by the ESM dialup
interface."
	INDEX		{ DmiCompId,DmiGroupId }
	::= { dellDialupTable 1 }


dialupCapabilityAtt1 OBJECT-TYPE
	SYNTAX		INTEGER { 
		false(0),
		true(1)
	}
	ACCESS		read-only
	STATUS		mandatory
	DESCRIPTION	"Specifies if this system supports dialup."
	REFERENCE "'Dell|Dialup|001' 1"
	::= { dellDialupEntry 1 }

callbackNumberAtt2 OBJECT-TYPE
	SYNTAX		DmiDisplaystring
	ACCESS		read-write
	STATUS		mandatory
	DESCRIPTION	"The number to callback when a dialup connection is established."
	REFERENCE "'Dell|Dialup|001' 2"
	::= { dellDialupEntry 2 }

SdellFirmware ::= SEQUENCE { 
	dellFirmwareState INTEGER,
	firmwareChassisIndexAtt1	DmiInteger,
	firmwareIndexAtt2	DmiInteger,
	firmwareTypeAtt3	DmiInteger,
	firmwareVersionAtt4	DmiDisplaystring,
	firmwareStatusAtt5	DmiInteger
}

dellFirmwareTable OBJECT-TYPE
	SYNTAX		SEQUENCE OF SdellFirmware
	ACCESS		not-accessible
	STATUS		mandatory
	DESCRIPTION	"Firmware Information - Contains version/status of firmware."
	::= { server2 311 }

dellFirmwareEntry OBJECT-TYPE
	SYNTAX		SdellFirmware
	ACCESS		not-accessible
	STATUS		mandatory
	DESCRIPTION	"Firmware Information - Contains version/status of firmware."
	INDEX		{ DmiCompId,DmiGroupId, firmwareChassisIndexAtt1, firmwareIndexAtt2 }
	::= { dellFirmwareTable 1 }


dellFirmwareState OBJECT-TYPE
	SYNTAX		INTEGER { 
		active(1),
		notInService(2),
		notReady(3),
		createAndGo(4),
		createAndWait(5),
		destroy(6)
	}
	ACCESS		read-write
	STATUS		mandatory
	REFERENCE "'Dell|Firmware|001' 0"
	::= { dellFirmwareEntry 0 }

firmwareChassisIndexAtt1 OBJECT-TYPE
	SYNTAX		DmiInteger
	ACCESS		read-only
	STATUS		mandatory
	DESCRIPTION	"Firmware chassis index"
	REFERENCE "'Dell|Firmware|001' 1"
	::= { dellFirmwareEntry 1 }

firmwareIndexAtt2 OBJECT-TYPE
	SYNTAX		DmiInteger
	ACCESS		read-only
	STATUS		mandatory
	DESCRIPTION	"Index into the firmware information table"
	REFERENCE "'Dell|Firmware|001' 2"
	::= { dellFirmwareEntry 2 }

firmwareTypeAtt3 OBJECT-TYPE
	SYNTAX		INTEGER { 
		other(1),
		unknown(2),
		bIOS(3),
		eSM(4),
		pSPB(5),
		backplane(6)
	}
	ACCESS		read-write
	STATUS		mandatory
	DESCRIPTION	"The type of this firmware."
	REFERENCE "'Dell|Firmware|001' 3"
	::= { dellFirmwareEntry 3 }

firmwareVersionAtt4 OBJECT-TYPE
	SYNTAX		DmiDisplaystring
	ACCESS		read-only
	STATUS		mandatory
	DESCRIPTION	"Version level of this firmware"
	REFERENCE "'Dell|Firmware|001' 4"
	::= { dellFirmwareEntry 4 }

firmwareStatusAtt5 OBJECT-TYPE
	SYNTAX		INTEGER { 
		other(1),
		unknown(2),
		oK(3),
		nonCritical(4),
		critical(5),
		nonRecoverable(6)
	}
	ACCESS		read-only
	STATUS		mandatory
	DESCRIPTION	"Current status of this firmware, if applicable"
	REFERENCE "'Dell|Firmware|001' 5"
	::= { dellFirmwareEntry 5 }

SdMTFCoolingDevice ::= SEQUENCE { 
	dMTFCoolingDeviceState INTEGER,
	coolingDeviceTableIndexAtt1	DmiInteger,
	fRUGroupIndexAtt2	DmiInteger,
	operationalGroupIndexAtt3	DmiInteger,
	coolingUnitIndexAtt4	DmiInteger,
	coolingDeviceTypeAtt5	DmiInteger,
	temperatureProbeIndexAtt6	DmiInteger
}

dMTFCoolingDeviceTable OBJECT-TYPE
	SYNTAX		SEQUENCE OF SdMTFCoolingDevice
	ACCESS		not-accessible
	STATUS		mandatory
	DESCRIPTION	"This group defines various attributes for cooling devices
in this system."
	::= { dmtfSystemsMIF 17 }

dMTFCoolingDeviceEntry OBJECT-TYPE
	SYNTAX		SdMTFCoolingDevice
	ACCESS		not-accessible
	STATUS		mandatory
	DESCRIPTION	"This group defines various attributes for cooling devices
in this system."
	INDEX		{ DmiCompId,DmiGroupId, coolingDeviceTableIndexAtt1 }
	::= { dMTFCoolingDeviceTable 1 }


dMTFCoolingDeviceState OBJECT-TYPE
	SYNTAX		INTEGER { 
		active(1),
		notInService(2),
		notReady(3),
		createAndGo(4),
		createAndWait(5),
		destroy(6)
	}
	ACCESS		read-write
	STATUS		mandatory
	REFERENCE "'DMTF|Cooling Device|002' 0"
	::= { dMTFCoolingDeviceEntry 0 }

coolingDeviceTableIndexAtt1 OBJECT-TYPE
	SYNTAX		DmiInteger
	ACCESS		read-only
	STATUS		mandatory
	DESCRIPTION	"An index into the cooling device table."
	REFERENCE "'DMTF|Cooling Device|002' 1"
	::= { dMTFCoolingDeviceEntry 1 }

fRUGroupIndexAtt2 OBJECT-TYPE
	SYNTAX		DmiInteger
	ACCESS		read-only
	STATUS		mandatory
	DESCRIPTION	"If this is a Field Replaceable Unit or if it is part of another
FRU, this provides an index into the FRU table; 'value = -1' indicates that
the group is not a FRU."
	REFERENCE "'DMTF|Cooling Device|002' 2"
	::= { dMTFCoolingDeviceEntry 2 }

operationalGroupIndexAtt3 OBJECT-TYPE
	SYNTAX		DmiInteger
	ACCESS		read-only
	STATUS		mandatory
	DESCRIPTION	"The index into the Operational State table for this device."
	REFERENCE "'DMTF|Cooling Device|002' 3"
	::= { dMTFCoolingDeviceEntry 3 }

coolingUnitIndexAtt4 OBJECT-TYPE
	SYNTAX		DmiInteger
	ACCESS		read-only
	STATUS		mandatory
	DESCRIPTION	"This is the ID of the Cooling Unit (logical cooling device)
of which this Cooling Device is a part. This value matches up with the Cooling
Unit Table Index attribute defined in the Cooling Unit Global Table."
	REFERENCE "'DMTF|Cooling Device|002' 4"
	::= { dMTFCoolingDeviceEntry 4 }

coolingDeviceTypeAtt5 OBJECT-TYPE
	SYNTAX		INTEGER { 
		other(1),
		unknown(2),
		fan(3),
		centrifugalBlower(4),
		chipFan(5),
		cabinetFan(6),
		powerSupplyFan(7),
		heatPipe(8),
		integratedRefrigeration(9),
		activeCooling(32),
		passiveCooling(33)
	}
	ACCESS		read-only
	STATUS		mandatory
	DESCRIPTION	"The type of Cooling Device that this is e.g. Fan, Heat Pipe,
etc."
	REFERENCE "'DMTF|Cooling Device|002' 5"
	::= { dMTFCoolingDeviceEntry 5 }

temperatureProbeIndexAtt6 OBJECT-TYPE
	SYNTAX		DmiInteger
	ACCESS		read-only
	STATUS		mandatory
	DESCRIPTION	"Index into the Temperature Probe table identifying the temperatu
e probe monitoring this cooling device. 0 indicates no probe provided."
	REFERENCE "'DMTF|Cooling Device|002' 6"
	::= { dMTFCoolingDeviceEntry 6 }

SdMTFElectricalCurrentProbe ::= SEQUENCE { 
	dMTFElectricalCurrentProbeState INTEGER,
	electricalCurrentProbeTableIndexAtt1	DmiInteger,
	electricalCurrentProbeLocationAtt2	DmiInteger,
	electricalCurrentProbeDescriptionAtt3	DmiDisplaystring,
	electricalCurrentStatusAtt4	DmiInteger,
	electricalCurrentProbeReadingAtt5	DmiInteger,
	monitoredElectricalCurrentNominalReadingAtt6	DmiInteger,
	monitoredElectricalCurrentNormalMaximumAtt7	DmiInteger,
	monitoredElectricalCurrentNormalMinimumAtt8	DmiInteger,
	electricalCurrentProbeMaximumAtt9	DmiInteger,
	electricalCurrentProbeMinimumAtt10	DmiInteger,
	electricalCurrentReadingLowerThresholdNonCriticalAtt11	DmiInteger,
	electricalCurrentReadingUpperThresholdNonCriticalAtt12	DmiInteger,
	electricalCurrentReadingLowerThresholdCriticalAtt13	DmiInteger,
	currentReadingUpperThresholdCriticalAtt14	DmiInteger,
	electricalCurrentReadingLowerThresholdNonRecoverabAtt15	DmiInteger,
	electricalCurrentReadingUpperThresholdNonRecoverabAtt16	DmiInteger,
	electricalCurrentProbeResolutionAtt17	DmiInteger,
	electricalCurrentProbeToleranceAtt18	DmiInteger,
	electricalCurrentProbeAccuracyAtt19	DmiInteger,
	fRUGroupIndex-1Att20	DmiInteger,
	operationalGroupIndex-1Att21	DmiInteger
}

dMTFElectricalCurrentProbeTable OBJECT-TYPE
	SYNTAX		SEQUENCE OF SdMTFElectricalCurrentProbe
	ACCESS		not-accessible
	STATUS		mandatory
	DESCRIPTION	"This group defines the attributes for the current probes
in this system."
	::= { dmtfSystemsMIF 55 }

dMTFElectricalCurrentProbeEntry OBJECT-TYPE
	SYNTAX		SdMTFElectricalCurrentProbe
	ACCESS		not-accessible
	STATUS		mandatory
	DESCRIPTION	"This group defines the attributes for the current probes
in this system."
	INDEX		{ DmiCompId,DmiGroupId, electricalCurrentProbeTableIndexAtt1 }
	::= { dMTFElectricalCurrentProbeTable 1 }


dMTFElectricalCurrentProbeState OBJECT-TYPE
	SYNTAX		INTEGER { 
		active(1),
		notInService(2),
		notReady(3),
		createAndGo(4),
		createAndWait(5),
		destroy(6)
	}
	ACCESS		read-write
	STATUS		mandatory
	REFERENCE "'DMTF|Electrical Current Probe|001' 0"
	::= { dMTFElectricalCurrentProbeEntry 0 }

electricalCurrentProbeTableIndexAtt1 OBJECT-TYPE
	SYNTAX		DmiInteger
	ACCESS		read-only
	STATUS		mandatory
	DESCRIPTION	"Index into this electrical current probe table."
	REFERENCE "'DMTF|Electrical Current Probe|001' 1"
	::= { dMTFElectricalCurrentProbeEntry 1 }

electricalCurrentProbeLocationAtt2 OBJECT-TYPE
	SYNTAX		INTEGER { 
		other(1),
		unknown(2),
		processor(3),
		disk(4),
		peripheralBay(5),
		sMBMaster(6),
		motherboard(7),
		memoryModule(8),
		processorModule(9),
		powerUnit(10),
		addInCard(11)
	}
	ACCESS		read-only
	STATUS		mandatory
	DESCRIPTION	"Identifies the physical location of the electrical current
probe."
	REFERENCE "'DMTF|Electrical Current Probe|001' 2"
	::= { dMTFElectricalCurrentProbeEntry 2 }

electricalCurrentProbeDescriptionAtt3 OBJECT-TYPE
	SYNTAX		DmiDisplaystring
	ACCESS		read-only
	STATUS		mandatory
	DESCRIPTION	"Additional descriptive information about the electrical current
probe or probe's location."
	REFERENCE "'DMTF|Electrical Current Probe|001' 3"
	::= { dMTFElectricalCurrentProbeEntry 3 }

electricalCurrentStatusAtt4 OBJECT-TYPE
	SYNTAX		INTEGER { 
		other(1),
		unknown(2),
		oK(3),
		nonCritical(4),
		critical(5),
		nonRecoverable(6)
	}
	ACCESS		read-only
	STATUS		mandatory
	DESCRIPTION	"Defines the status of the electrical current monitored by
this electrical current probe."
	REFERENCE "'DMTF|Electrical Current Probe|001' 4"
	::= { dMTFElectricalCurrentProbeEntry 4 }

electricalCurrentProbeReadingAtt5 OBJECT-TYPE
	SYNTAX		DmiInteger
	ACCESS		read-only
	STATUS		mandatory
	DESCRIPTION	"The present electrical current reading of this probe in milliamp
. 0x8000000 denotes 'unknown'."
	REFERENCE "'DMTF|Electrical Current Probe|001' 5"
	::= { dMTFElectricalCurrentProbeEntry 5 }

monitoredElectricalCurrentNominalReadingAtt6 OBJECT-TYPE
	SYNTAX		DmiInteger
	ACCESS		read-only
	STATUS		mandatory
	DESCRIPTION	"The nominal electrical current reading of the current monitored
by this probe in milliamps. 0x80000000 denotes 'unknown'."
	REFERENCE "'DMTF|Electrical Current Probe|001' 6"
	::= { dMTFElectricalCurrentProbeEntry 6 }

monitoredElectricalCurrentNormalMaximumAtt7 OBJECT-TYPE
	SYNTAX		DmiInteger
	ACCESS		read-only
	STATUS		mandatory
	DESCRIPTION	"The normal maximum electrical current reading of the current
monitored by this probe in milliamps. 0x80000000 denotes 'unknown'."
	REFERENCE "'DMTF|Electrical Current Probe|001' 7"
	::= { dMTFElectricalCurrentProbeEntry 7 }

monitoredElectricalCurrentNormalMinimumAtt8 OBJECT-TYPE
	SYNTAX		DmiInteger
	ACCESS		read-only
	STATUS		mandatory
	DESCRIPTION	"The normal minimum electrical current reading of the current
monitored by this probe in milliamps. 0x80000000 denotes 'unknown'."
	REFERENCE "'DMTF|Electrical Current Probe|001' 8"
	::= { dMTFElectricalCurrentProbeEntry 8 }

electricalCurrentProbeMaximumAtt9 OBJECT-TYPE
	SYNTAX		DmiInteger
	ACCESS		read-only
	STATUS		mandatory
	DESCRIPTION	"The maximum electrical current reading specified to be readable
by this probe in milliamps. 0x80000000 denotes 'unknown'."
	REFERENCE "'DMTF|Electrical Current Probe|001' 9"
	::= { dMTFElectricalCurrentProbeEntry 9 }

electricalCurrentProbeMinimumAtt10 OBJECT-TYPE
	SYNTAX		DmiInteger
	ACCESS		read-only
	STATUS		mandatory
	DESCRIPTION	"The minimum electrical current reading specified to be readable
by this probe in milliamps. 0x80000000 denotes 'unknown'."
	REFERENCE "'DMTF|Electrical Current Probe|001' 10"
	::= { dMTFElectricalCurrentProbeEntry 10 }

electricalCurrentReadingLowerThresholdNonCriticalAtt11 OBJECT-TYPE
	SYNTAX		DmiInteger
	ACCESS		read-write
	STATUS		mandatory
	DESCRIPTION	"The lower non-critical threshold for the electrical current
reading set by the user, in milliamps. 0x80000000 denotes 'unknown'."
	REFERENCE "'DMTF|Electrical Current Probe|001' 11"
	::= { dMTFElectricalCurrentProbeEntry 11 }

electricalCurrentReadingUpperThresholdNonCriticalAtt12 OBJECT-TYPE
	SYNTAX		DmiInteger
	ACCESS		read-write
	STATUS		mandatory
	DESCRIPTION	"The upper non-critical threshold for the electrical current
reading, in milliamps. 0x80000000 denotes 'unknown'."
	REFERENCE "'DMTF|Electrical Current Probe|001' 12"
	::= { dMTFElectricalCurrentProbeEntry 12 }

electricalCurrentReadingLowerThresholdCriticalAtt13 OBJECT-TYPE
	SYNTAX		DmiInteger
	ACCESS		read-write
	STATUS		mandatory
	DESCRIPTION	"The lower critical threshold for the electrical current probe,
in milliamps. 0x80000000 denotes 'unknown'."
	REFERENCE "'DMTF|Electrical Current Probe|001' 13"
	::= { dMTFElectricalCurrentProbeEntry 13 }

currentReadingUpperThresholdCriticalAtt14 OBJECT-TYPE
	SYNTAX		DmiInteger
	ACCESS		read-write
	STATUS		mandatory
	DESCRIPTION	"The upper critical threshold for the electrical current probe,
in milliamps. 0x80000000 denotes 'unknown'."
	REFERENCE "'DMTF|Electrical Current Probe|001' 14"
	::= { dMTFElectricalCurrentProbeEntry 14 }

electricalCurrentReadingLowerThresholdNonRecoverabAtt15 OBJECT-TYPE
	SYNTAX		DmiInteger
	ACCESS		read-write
	STATUS		mandatory
	DESCRIPTION	"The lower non-recoverable threshold for the electrical current
probe, in milliamps. 0x80000000 denotes 'unknown'."
	REFERENCE "'DMTF|Electrical Current Probe|001' 15"
	::= { dMTFElectricalCurrentProbeEntry 15 }

electricalCurrentReadingUpperThresholdNonRecoverabAtt16 OBJECT-TYPE
	SYNTAX		DmiInteger
	ACCESS		read-write
	STATUS		mandatory
	DESCRIPTION	"The upper non-recoverable threshold for the electrical current
probe, in milliamps. 0x80000000 denotes 'unknown'."
	REFERENCE "'DMTF|Electrical Current Probe|001' 16"
	::= { dMTFElectricalCurrentProbeEntry 16 }

electricalCurrentProbeResolutionAtt17 OBJECT-TYPE
	SYNTAX		DmiInteger
	ACCESS		read-write
	STATUS		mandatory
	DESCRIPTION	"The resolution for the reading from this electrical current
probe, in tenths of milliamps. '0x80000000 denotes 'unknown'."
	REFERENCE "'DMTF|Electrical Current Probe|001' 17"
	::= { dMTFElectricalCurrentProbeEntry 17 }

electricalCurrentProbeToleranceAtt18 OBJECT-TYPE
	SYNTAX		DmiInteger
	ACCESS		read-write
	STATUS		mandatory
	DESCRIPTION	"The tolerance for the reading from this electrical current
probe, in plus/minus milliamps. 0x80000000 denotes 'unknown'."
	REFERENCE "'DMTF|Electrical Current Probe|001' 18"
	::= { dMTFElectricalCurrentProbeEntry 18 }

electricalCurrentProbeAccuracyAtt19 OBJECT-TYPE
	SYNTAX		DmiInteger
	ACCESS		read-write
	STATUS		mandatory
	DESCRIPTION	"The accuracy for the reading from this electrical current
probe, in plus/minus hundredths of a percent. 0x80000000 denotes 'unknown'."
	REFERENCE "'DMTF|Electrical Current Probe|001' 19"
	::= { dMTFElectricalCurrentProbeEntry 19 }

fRUGroupIndexAtt20 OBJECT-TYPE
	SYNTAX		DmiInteger
	ACCESS		read-only
	STATUS		mandatory
	DESCRIPTION	"Index into the FRU table"
	REFERENCE "'DMTF|Electrical Current Probe|001' 20"
	::= { dMTFElectricalCurrentProbeEntry 20 }

operationalGroupIndexAtt21 OBJECT-TYPE
	SYNTAX		DmiInteger
	ACCESS		read-only
	STATUS		mandatory
	DESCRIPTION	"Index into the Operational State table"
	REFERENCE "'DMTF|Electrical Current Probe|001' 21"
	::= { dMTFElectricalCurrentProbeEntry 21 }

SdMTFFRU ::= SEQUENCE { 
	dMTFFRUState INTEGER,
	fRUIndexAtt1	DmiInteger,
	deviceGroupIndexAtt2	DmiInteger,
	descriptionAtt3	DmiDisplaystring,
	manufacturerAtt4	DmiDisplaystring,
	modelAtt5	DmiDisplaystring,
	partNumberAtt6	DmiDisplaystring,
	fRUSerialNumberAtt7	DmiDisplaystring,
	revisionLevelAtt8	DmiDisplaystring,
	warrantyStartDateAtt9	Dmi-Date,
	warrantyDurationAtt10	DmiInteger,
	supportPhoneNumberAtt11	DmiDisplaystring,
	fRUInternetUniformResourceLocatorAtt12	DmiDisplaystring
}

dMTFFRUTable OBJECT-TYPE
	SYNTAX		SEQUENCE OF SdMTFFRU
	ACCESS		not-accessible
	STATUS		mandatory
	DESCRIPTION	"A Field Replaceable Unit (FRU), is defined as a hardware
component which is designed to be separately removable for replacement or
repair. For the purposes of this definition, a motherboard and a fixed hard
disk are FRUs, whereas a fixed hard disk platter or a chip fixed in place
on the motherboard are not FRUs since they are not designed to be separately
removable. Each instance within the FRU table should contain the device group
and instance data for the associated hardware component."
	::= { dmtfSystemsMIF 29 }

dMTFFRUEntry OBJECT-TYPE
	SYNTAX		SdMTFFRU
	ACCESS		not-accessible
	STATUS		mandatory
	DESCRIPTION	"A Field Replaceable Unit (FRU), is defined as a hardware
component which is designed to be separately removable for replacement or
repair. For the purposes of this definition, a motherboard and a fixed hard
disk are FRUs, whereas a fixed hard disk platter or a chip fixed in place
on the motherboard are not FRUs since they are not designed to be separately
removable. Each instance within the FRU table should contain the device group
and instance data for the associated hardware component."
	INDEX		{ DmiCompId,DmiGroupId, fRUIndexAtt1 }
	::= { dMTFFRUTable 1 }


dMTFFRUState OBJECT-TYPE
	SYNTAX		INTEGER { 
		active(1),
		notInService(2),
		notReady(3),
		createAndGo(4),
		createAndWait(5),
		destroy(6)
	}
	ACCESS		read-write
	STATUS		mandatory
	REFERENCE "'DMTF|FRU|002' 0"
	::= { dMTFFRUEntry 0 }

fRUIndexAtt1 OBJECT-TYPE
	SYNTAX		DmiInteger
	ACCESS		read-only
	STATUS		mandatory
	DESCRIPTION	"The index into the Field Replaceable Unit table."
	REFERENCE "'DMTF|FRU|002' 1"
	::= { dMTFFRUEntry 1 }

deviceGroupIndexAtt2 OBJECT-TYPE
	SYNTAX		DmiInteger
	ACCESS		read-only
	STATUS		mandatory
	DESCRIPTION	"The group ID of the group referencing this Field Replaceable
Unit instance."
	REFERENCE "'DMTF|FRU|002' 2"
	::= { dMTFFRUEntry 2 }

descriptionAtt3 OBJECT-TYPE
	SYNTAX		DmiDisplaystring
	ACCESS		read-only
	STATUS		mandatory
	DESCRIPTION	"A clear description of this Field Replaceable Unit."
	REFERENCE "'DMTF|FRU|002' 3"
	::= { dMTFFRUEntry 3 }

manufacturerAtt4 OBJECT-TYPE
	SYNTAX		DmiDisplaystring
	ACCESS		read-only
	STATUS		mandatory
	DESCRIPTION	"The name of the company manufacturing or providing this Field
Replaceable Unit."
	REFERENCE "'DMTF|FRU|002' 4"
	::= { dMTFFRUEntry 4 }

modelAtt5 OBJECT-TYPE
	SYNTAX		DmiDisplaystring
	ACCESS		read-only
	STATUS		mandatory
	DESCRIPTION	"The manufacturer's model number for this Field Replaceable
Unit."
	REFERENCE "'DMTF|FRU|002' 5"
	::= { dMTFFRUEntry 5 }

partNumberAtt6 OBJECT-TYPE
	SYNTAX		DmiDisplaystring
	ACCESS		read-only
	STATUS		mandatory
	DESCRIPTION	"A part number by which a replacement part can be ordered
for this Field Replaceable Unit."
	REFERENCE "'DMTF|FRU|002' 6"
	::= { dMTFFRUEntry 6 }

fRUSerialNumberAtt7 OBJECT-TYPE
	SYNTAX		DmiDisplaystring
	ACCESS		read-only
	STATUS		mandatory
	DESCRIPTION	"The manufacturer's serial number for this Field Replaceable
Unit."
	REFERENCE "'DMTF|FRU|002' 7"
	::= { dMTFFRUEntry 7 }

revisionLevelAtt8 OBJECT-TYPE
	SYNTAX		DmiDisplaystring
	ACCESS		read-only
	STATUS		mandatory
	DESCRIPTION	"The revision level of this Field Replaceable Unit."
	REFERENCE "'DMTF|FRU|002' 8"
	::= { dMTFFRUEntry 8 }

warrantyStartDateAtt9 OBJECT-TYPE
	SYNTAX		Dmi-Date
	ACCESS		read-only
	STATUS		mandatory
	DESCRIPTION	"The start date of the service warranty for this Field Replaceabl
 Unit."
	REFERENCE "'DMTF|FRU|002' 9"
	::= { dMTFFRUEntry 9 }

warrantyDurationAtt10 OBJECT-TYPE
	SYNTAX		DmiInteger
	ACCESS		read-only
	STATUS		mandatory
	DESCRIPTION	"The total duration of this Field Replaceable Unit warranty
in months."
	REFERENCE "'DMTF|FRU|002' 10"
	::= { dMTFFRUEntry 10 }

supportPhoneNumberAtt11 OBJECT-TYPE
	SYNTAX		DmiDisplaystring
	ACCESS		read-only
	STATUS		mandatory
	DESCRIPTION	"The phone number(s) for support for this Field Replaceable
Unit."
	REFERENCE "'DMTF|FRU|002' 11"
	::= { dMTFFRUEntry 11 }

fRUInternetUniformResourceLocatorAtt12 OBJECT-TYPE
	SYNTAX		DmiDisplaystring
	ACCESS		read-only
	STATUS		mandatory
	DESCRIPTION	"The Internet Uniform Resource Locator string that can be
used through a World Wide Web browser to obtain further information about
this FRU"
	REFERENCE "'DMTF|FRU|002' 12"
	::= { dMTFFRUEntry 12 }

SdMTFGeneralInformation ::= SEQUENCE { 
	systemNameAtt1	DmiDisplaystring,
	systemLocationAtt2	DmiDisplaystring,
	systemPrimaryUserNameAtt3	DmiDisplaystring,
	systemPrimaryUserPhoneAtt4	DmiDisplaystring,
	systemBootupTimeAtt5	Dmi-Date,
	systemDateTimeAtt6	Dmi-Date
}

dMTFGeneralInformationTable OBJECT-TYPE
	SYNTAX		SEQUENCE OF SdMTFGeneralInformation
	ACCESS		not-accessible
	STATUS		mandatory
	DESCRIPTION	"This group defines general information about this system."
	::= { dmtfSystemsMIF 1 }

dMTFGeneralInformationEntry OBJECT-TYPE
	SYNTAX		SdMTFGeneralInformation
	ACCESS		not-accessible
	STATUS		mandatory
	DESCRIPTION	"This group defines general information about this system."
	INDEX		{ DmiCompId,DmiGroupId }
	::= { dMTFGeneralInformationTable 1 }


systemNameAtt1 OBJECT-TYPE
	SYNTAX		DmiDisplaystring
	ACCESS		read-write
	STATUS		mandatory
	DESCRIPTION	"A name to identify this system."
	REFERENCE "'DMTF|General Information|001' 1"
	::= { dMTFGeneralInformationEntry 1 }

systemLocationAtt2 OBJECT-TYPE
	SYNTAX		DmiDisplaystring
	ACCESS		read-write
	STATUS		mandatory
	DESCRIPTION	"The physical location of this system."
	REFERENCE "'DMTF|General Information|001' 2"
	::= { dMTFGeneralInformationEntry 2 }

systemPrimaryUserNameAtt3 OBJECT-TYPE
	SYNTAX		DmiDisplaystring
	ACCESS		read-write
	STATUS		mandatory
	DESCRIPTION	"The name of the primary user or owner of this system."
	REFERENCE "'DMTF|General Information|001' 3"
	::= { dMTFGeneralInformationEntry 3 }

systemPrimaryUserPhoneAtt4 OBJECT-TYPE
	SYNTAX		DmiDisplaystring
	ACCESS		read-write
	STATUS		mandatory
	DESCRIPTION	"The phone number of the primary user of this system."
	REFERENCE "'DMTF|General Information|001' 4"
	::= { dMTFGeneralInformationEntry 4 }

systemBootupTimeAtt5 OBJECT-TYPE
	SYNTAX		Dmi-Date
	ACCESS		read-only
	STATUS		mandatory
	DESCRIPTION	"The time at which the system was last booted."
	REFERENCE "'DMTF|General Information|001' 5"
	::= { dMTFGeneralInformationEntry 5 }

systemDateTimeAtt6 OBJECT-TYPE
	SYNTAX		Dmi-Date
	ACCESS		read-write
	STATUS		mandatory
	DESCRIPTION	"The actual system date and time."
	REFERENCE "'DMTF|General Information|001' 6"
	::= { dMTFGeneralInformationEntry 6 }

SdMTFMemoryArrayMappedAddresses ::= SEQUENCE { 
	dMTFMemoryArrayMappedAddressesState INTEGER,
	memoryArrayMappedAddressesTableIndexAtt1	DmiInteger,
	memoryArrayIndexAtt2	DmiInteger,
	mappedRangeStartingAddressAtt3	DmiInteger,
	mappedRangeEndingAddressAtt4	DmiInteger,
	partitionIDAtt5	DmiInteger,
	partitionWidthAtt6	DmiInteger,
	operationalGroupIndexAtt7	DmiInteger
}

dMTFMemoryArrayMappedAddressesTable OBJECT-TYPE
	SYNTAX		SEQUENCE OF SdMTFMemoryArrayMappedAddresses
	ACCESS		not-accessible
	STATUS		mandatory
	DESCRIPTION	"This table presents ranges of physical addresses that are
mapped to a given Memory Array."
	::= { dmtfSystemsMIF 34 }

dMTFMemoryArrayMappedAddressesEntry OBJECT-TYPE
	SYNTAX		SdMTFMemoryArrayMappedAddresses
	ACCESS		not-accessible
	STATUS		mandatory
	DESCRIPTION	"This table presents ranges of physical addresses that are
mapped to a given Memory Array."
	INDEX		{ DmiCompId,DmiGroupId, memoryArrayMappedAddressesTableIndexAtt1 }
	::= { dMTFMemoryArrayMappedAddressesTable 1 }


dMTFMemoryArrayMappedAddressesState OBJECT-TYPE
	SYNTAX		INTEGER { 
		active(1),
		notInService(2),
		notReady(3),
		createAndGo(4),
		createAndWait(5),
		destroy(6)
	}
	ACCESS		read-write
	STATUS		mandatory
	REFERENCE "'DMTF|Memory Array Mapped Addresses|001' 0"
	::= { dMTFMemoryArrayMappedAddressesEntry 0 }

memoryArrayMappedAddressesTableIndexAtt1 OBJECT-TYPE
	SYNTAX		DmiInteger
	ACCESS		read-only
	STATUS		mandatory
	DESCRIPTION	"A unique number that identifies this row."
	REFERENCE "'DMTF|Memory Array Mapped Addresses|001' 1"
	::= { dMTFMemoryArrayMappedAddressesEntry 1 }

memoryArrayIndexAtt2 OBJECT-TYPE
	SYNTAX		DmiInteger
	ACCESS		read-only
	STATUS		mandatory
	DESCRIPTION	"The ID of the Memory Array that this address range is mapped
to.  Multiple address ranges may be mapped to a Memory Array."
	REFERENCE "'DMTF|Memory Array Mapped Addresses|001' 2"
	::= { dMTFMemoryArrayMappedAddressesEntry 2 }

mappedRangeStartingAddressAtt3 OBJECT-TYPE
	SYNTAX		DmiInteger
	ACCESS		read-only
	STATUS		mandatory
	DESCRIPTION	"The physical starting address, in kilobytes, of a range of
memory mapped to the specified Memory Array. 0x80000000 denotes 'unknown'."
	REFERENCE "'DMTF|Memory Array Mapped Addresses|001' 3"
	::= { dMTFMemoryArrayMappedAddressesEntry 3 }

mappedRangeEndingAddressAtt4 OBJECT-TYPE
	SYNTAX		DmiInteger
	ACCESS		read-only
	STATUS		mandatory
	DESCRIPTION	"The physical ending address of the last kilobyte of a range
of addresses mapped to the specified Memory Array. 0x80000000 denotes 'unknown'."
	REFERENCE "'DMTF|Memory Array Mapped Addresses|001' 4"
	::= { dMTFMemoryArrayMappedAddressesEntry 4 }

partitionIDAtt5 OBJECT-TYPE
	SYNTAX		DmiInteger
	ACCESS		read-only
	STATUS		mandatory
	DESCRIPTION	"Identifies a Memory Partition associated with the Memory
Array specified by Memory Array Table Index. 0x80000000 denotes 'unknown'."
	REFERENCE "'DMTF|Memory Array Mapped Addresses|001' 5"
	::= { dMTFMemoryArrayMappedAddressesEntry 5 }

partitionWidthAtt6 OBJECT-TYPE
	SYNTAX		DmiInteger
	ACCESS		read-only
	STATUS		mandatory
	DESCRIPTION	"The number of Memory Devices that form a single row of memory
for the partition. 0x80000000 denotes 'unknown'."
	REFERENCE "'DMTF|Memory Array Mapped Addresses|001' 6"
	::= { dMTFMemoryArrayMappedAddressesEntry 6 }

operationalGroupIndexAtt7 OBJECT-TYPE
	SYNTAX		DmiInteger
	ACCESS		read-only
	STATUS		mandatory
	DESCRIPTION	"The index into the Operational State Table for this Memory
Range.  Generally, there will be a 1:1 correspondence between a mapped range
and a partition.  In which case, the Operational State will be for the partition
as well. In the case that there is more than one mapped range for a partion,
it will be necessary to check the Operational State entries for each range
to determine the overall status of the partition."
	REFERENCE "'DMTF|Memory Array Mapped Addresses|001' 7"
	::= { dMTFMemoryArrayMappedAddressesEntry 7 }

SdMTFMemoryDeviceMappedAddresses ::= SEQUENCE { 
	dMTFMemoryDeviceMappedAddressesState INTEGER,
	memoryDeviceMappedAddressesTableIndexAtt1	DmiInteger,
	memoryDeviceSetIDAtt2	DmiInteger,
	partitionAtt3	DmiInteger,
	mappedRangeStartingAddressAtt4	DmiInteger,
	mappedRangeEndingAddressAtt5	DmiInteger,
	partitionRowPositionAtt6	DmiInteger,
	interleavePositionAtt7	DmiInteger,
	dataDepthAtt8	DmiInteger
}

dMTFMemoryDeviceMappedAddressesTable OBJECT-TYPE
	SYNTAX		SEQUENCE OF SdMTFMemoryDeviceMappedAddresses
	ACCESS		not-accessible
	STATUS		mandatory
	DESCRIPTION	"This table presents ranges of physical addresses that are
mapped to a given Memory Device Set."
	::= { dmtfSystemsMIF 36 }

dMTFMemoryDeviceMappedAddressesEntry OBJECT-TYPE
	SYNTAX		SdMTFMemoryDeviceMappedAddresses
	ACCESS		not-accessible
	STATUS		mandatory
	DESCRIPTION	"This table presents ranges of physical addresses that are
mapped to a given Memory Device Set."
	INDEX		{ DmiCompId,DmiGroupId, memoryDeviceMappedAddressesTableIndexAtt1 }
	::= { dMTFMemoryDeviceMappedAddressesTable 1 }


dMTFMemoryDeviceMappedAddressesState OBJECT-TYPE
	SYNTAX		INTEGER { 
		active(1),
		notInService(2),
		notReady(3),
		createAndGo(4),
		createAndWait(5),
		destroy(6)
	}
	ACCESS		read-write
	STATUS		mandatory
	REFERENCE "'DMTF|Memory Device Mapped Addresses|001' 0"
	::= { dMTFMemoryDeviceMappedAddressesEntry 0 }

memoryDeviceMappedAddressesTableIndexAtt1 OBJECT-TYPE
	SYNTAX		DmiInteger
	ACCESS		read-only
	STATUS		mandatory
	DESCRIPTION	"A unique number that identifies this row."
	REFERENCE "'DMTF|Memory Device Mapped Addresses|001' 1"
	::= { dMTFMemoryDeviceMappedAddressesEntry 1 }

memoryDeviceSetIDAtt2 OBJECT-TYPE
	SYNTAX		DmiInteger
	ACCESS		read-only
	STATUS		mandatory
	DESCRIPTION	"The row in the Memory Device table that this address range
is for.  This matches with a Memory Device Table Index. There may be multiple
rows in Memory Device Mapped addresses for a single Memory Device."
	REFERENCE "'DMTF|Memory Device Mapped Addresses|001' 2"
	::= { dMTFMemoryDeviceMappedAddressesEntry 2 }

partitionAtt3 OBJECT-TYPE
	SYNTAX		DmiInteger
	ACCESS		read-only
	STATUS		mandatory
	DESCRIPTION	"Identifies the Memory partition in the Memory Array Mapped
Addresses table that this Memory Device is part of. Partition number should
be positive.  0x80000000 denotes 'unknown'."
	REFERENCE "'DMTF|Memory Device Mapped Addresses|001' 3"
	::= { dMTFMemoryDeviceMappedAddressesEntry 3 }

mappedRangeStartingAddressAtt4 OBJECT-TYPE
	SYNTAX		DmiInteger
	ACCESS		read-only
	STATUS		mandatory
	DESCRIPTION	"The physical starting address, in kilobytes, of a range of
memory mapped to the specified Memory Device set. The address is specified
relative to the bus that the device is connected to. 0x80000000 denotes 'unknown
."
	REFERENCE "'DMTF|Memory Device Mapped Addresses|001' 4"
	::= { dMTFMemoryDeviceMappedAddressesEntry 4 }

mappedRangeEndingAddressAtt5 OBJECT-TYPE
	SYNTAX		DmiInteger
	ACCESS		read-only
	STATUS		mandatory
	DESCRIPTION	"The physical ending address of the last kilobyte of a range
of addresses mapped to the specified Memory Device. The address is specified
relative to the bus that the device is connected to. 0x80000000 denotes 'unknown
."
	REFERENCE "'DMTF|Memory Device Mapped Addresses|001' 5"
	::= { dMTFMemoryDeviceMappedAddressesEntry 5 }

partitionRowPositionAtt6 OBJECT-TYPE
	SYNTAX		DmiInteger
	ACCESS		read-only
	STATUS		mandatory
	DESCRIPTION	"This specifies the position of the device in a row of the
partition. For example, if it takes two 8-bit memory devices to form a 16-bit
row, then a value of '2'in this attribute means the device is the second
device. 0 is an invalid return value.  0x80000000 denotes 'unknown'."
	REFERENCE "'DMTF|Memory Device Mapped Addresses|001' 6"
	::= { dMTFMemoryDeviceMappedAddressesEntry 6 }

interleavePositionAtt7 OBJECT-TYPE
	SYNTAX		DmiInteger
	ACCESS		read-only
	STATUS		mandatory
	DESCRIPTION	"The position of this device in an interleave. 0 indicates
non-interleaved. 1 indicates the first position 2 the second, and so on.
For example, in a 2:1 interleave, a value of '1' would indicate the device
is in the 'even' position, in a 4:1 interleave this would be the first of
four possible positions).  0x80000000 denotes 'unknown' or'unsupported'."
	REFERENCE "'DMTF|Memory Device Mapped Addresses|001' 7"
	::= { dMTFMemoryDeviceMappedAddressesEntry 7 }

dataDepthAtt8 OBJECT-TYPE
	SYNTAX		DmiInteger
	ACCESS		read-only
	STATUS		mandatory
	DESCRIPTION	"The maximum number of consecutive rows accessed from this
device in a single interleaved transfer. For example, if a device transfers
two rows each time it is read, its Interleaved Data Depth would be 2. If
that device is 2:1 interleaved and in Interleave Position '1', then the rows
mapped to that device would be rows 1,2,5,6,9,10, etc. If the device is not
part of an interleave, this value should be 0.  0x80000000 denotes 'unknown'."
	REFERENCE "'DMTF|Memory Device Mapped Addresses|001' 8"
	::= { dMTFMemoryDeviceMappedAddressesEntry 8 }

SdMTFMemoryDevice ::= SEQUENCE { 
	dMTFMemoryDeviceState INTEGER,
	memoryDeviceTableIndexAtt1	DmiInteger,
	memoryArrayIndexAtt2-1	DmiInteger,
	deviceLocatorAtt3	DmiDisplaystring,
	bankLocatorAtt4	DmiDisplaystring,
	sizeAtt5	DmiInteger,
	formFactorAtt6	DmiInteger,
	totalWidthAtt7	DmiInteger,
	dataWidthAtt8	DmiInteger,
	memoryTypeAtt9	DmiInteger,
	typeDetailAtt10	DmiInteger,
	deviceSetAtt11	DmiInteger,
	deviceErrorTypeAtt12	DmiInteger,
	errorGranularityAtt13	DmiInteger,
	lastErrorUpdateAtt14	DmiInteger,
	errorOperationAtt15	DmiInteger,
	errorDataSizeAtt16	DmiInteger,
	errorDataAtt17	DmiOctetstring,
	vendorSyndromeAtt18	DmiOctetstring,
	deviceErrorAddressAtt19	DmiInteger,
	arrayErrorAddressAtt20	DmiInteger,
	errorResolutionAtt21	DmiInteger,
	fRUGroupIndexAtt22	DmiInteger,
	operationalGroupIndexAtt23	DmiInteger
}

dMTFMemoryDeviceTable OBJECT-TYPE
	SYNTAX		SEQUENCE OF SdMTFMemoryDevice
	ACCESS		not-accessible
	STATUS		mandatory
	DESCRIPTION	"This group presents information about individual memory devices
in the system. A memory device can be a SIMM, a SIPP, or a single chip, or
an entire card-based on the resolution to which a memory error can be determined
and whether the device is replaceable as a unit."
	::= { dmtfSystemsMIF 35 }

dMTFMemoryDeviceEntry OBJECT-TYPE
	SYNTAX		SdMTFMemoryDevice
	ACCESS		not-accessible
	STATUS		mandatory
	DESCRIPTION	"This group presents information about individual memory devices
in the system. A memory device can be a SIMM, a SIPP, or a single chip, or
an entire card-based on the resolution to which a memory error can be determined
and whether the device is replaceable as a unit."
	INDEX		{ DmiCompId,DmiGroupId, memoryDeviceTableIndexAtt1 }
	::= { dMTFMemoryDeviceTable 1 }


dMTFMemoryDeviceState OBJECT-TYPE
	SYNTAX		INTEGER { 
		active(1),
		notInService(2),
		notReady(3),
		createAndGo(4),
		createAndWait(5),
		destroy(6)
	}
	ACCESS		read-write
	STATUS		mandatory
	REFERENCE "'DMTF|Memory Device|001' 0"
	::= { dMTFMemoryDeviceEntry 0 }

memoryDeviceTableIndexAtt1 OBJECT-TYPE
	SYNTAX		DmiInteger
	ACCESS		read-only
	STATUS		mandatory
	DESCRIPTION	"A unique number that identifies this row."
	REFERENCE "'DMTF|Memory Device|001' 1"
	::= { dMTFMemoryDeviceEntry 1 }

memoryArrayIndexAtt2-1 OBJECT-TYPE
	SYNTAX		DmiInteger
	ACCESS		read-only
	STATUS		mandatory
	DESCRIPTION	"The ID of the Memory Array that this Memory Device is a part
of."
	REFERENCE "'DMTF|Memory Device|001' 2"
	::= { dMTFMemoryDeviceEntry 2 }

deviceLocatorAtt3 OBJECT-TYPE
	SYNTAX		DmiDisplaystring
	ACCESS		read-only
	STATUS		mandatory
	DESCRIPTION	"A string identifying the physically labeled socket or board
position where the memory device is located. Eg. 'SIMM 3' or 'IC12'."
	REFERENCE "'DMTF|Memory Device|001' 3"
	::= { dMTFMemoryDeviceEntry 3 }

bankLocatorAtt4 OBJECT-TYPE
	SYNTAX		DmiDisplaystring
	ACCESS		read-only
	STATUS		mandatory
	DESCRIPTION	"A string identifying the physically labeled bank where the
memory device is located. Eg. 'Bank 0' or 'A'."
	REFERENCE "'DMTF|Memory Device|001' 4"
	::= { dMTFMemoryDeviceEntry 4 }

sizeAtt5 OBJECT-TYPE
	SYNTAX		DmiInteger
	ACCESS		read-only
	STATUS		mandatory
	DESCRIPTION	"Size of this memory device, in bytes."
	REFERENCE "'DMTF|Memory Device|001' 5"
	::= { dMTFMemoryDeviceEntry 5 }

formFactorAtt6 OBJECT-TYPE
	SYNTAX		INTEGER { 
		other(1),
		unknown(2),
		sIMM(3),
		sIP(4),
		chip(5),
		dIP(6),
		zIP(7),
		proprietaryCard(8),
		dIMM(9),
		tSOP(10),
		rowOfChips(11)
	}
	ACCESS		read-only
	STATUS		mandatory
	DESCRIPTION	"Implementation form factor for this memory device."
	REFERENCE "'DMTF|Memory Device|001' 6"
	::= { dMTFMemoryDeviceEntry 6 }

totalWidthAtt7 OBJECT-TYPE
	SYNTAX		DmiInteger
	ACCESS		read-only
	STATUS		mandatory
	DESCRIPTION	"Total width of this memory device, including check or error
correction bits, in bits. If there are no error correction bits, the value
in this attribute should match that specified in Data Width.  0x80000000
denotes 'unknown'."
	REFERENCE "'DMTF|Memory Device|001' 7"
	::= { dMTFMemoryDeviceEntry 7 }

dataWidthAtt8 OBJECT-TYPE
	SYNTAX		DmiInteger
	ACCESS		read-only
	STATUS		mandatory
	DESCRIPTION	"Data width of this memory device, in bits. A data width of
0 and a Total Width of 8 would indicate that the device is solely being used
to provide eight error correction bits. 0x80000000 denotes 'unknown'."
	REFERENCE "'DMTF|Memory Device|001' 8"
	::= { dMTFMemoryDeviceEntry 8 }

memoryTypeAtt9 OBJECT-TYPE
	SYNTAX		INTEGER { 
		other(1),
		unknown(2),
		dRAM(3),
		eDRAM(4),
		vRAM(5),
		sRAM(6),
		rAM(7),
		rOM(8),
		fLASH(9),
		eEPROM(10),
		fEPROM(11),
		ePROM(12)
	}
	ACCESS		read-only
	STATUS		mandatory
	DESCRIPTION	"Type of memory used in this memory device."
	REFERENCE "'DMTF|Memory Device|001' 9"
	::= { dMTFMemoryDeviceEntry 9 }

typeDetailAtt10 OBJECT-TYPE
	SYNTAX		INTEGER { 
		other(1),
		unknown(2),
		fastPaged(3),
		staticColumn(4),
		pseudoStatic(5),
		rAMBUS(6),
		synchronous(7),
		cMOS(8),
		eDO(9),
		windowDRAM(10),
		cacheDRAM(11),
		nonVolatile(12)
	}
	ACCESS		read-only
	STATUS		mandatory
	DESCRIPTION	"Additional detail on the device type."
	REFERENCE "'DMTF|Memory Device|001' 10"
	::= { dMTFMemoryDeviceEntry 10 }

deviceSetAtt11 OBJECT-TYPE
	SYNTAX		DmiInteger
	ACCESS		read-only
	STATUS		mandatory
	DESCRIPTION	"This attribute is used to identify when the Memory Device
is one of a set of Memory Devices that must be populated with all devices
of the same type and size, and which set the device belongs to.  For example,
when one SIMM belongs to a set of four. 0 indicates the Memory Device isn't
part of a set. 0x80000000 denotes 'unknown'."
	REFERENCE "'DMTF|Memory Device|001' 11"
	::= { dMTFMemoryDeviceEntry 11 }

deviceErrorTypeAtt12 OBJECT-TYPE
	SYNTAX		INTEGER { 
		other(1),
		unknown(2),
		oK(3),
		badRead(4),
		parityError(5),
		singleBitError(6),
		doubleBitError(7),
		multiBitError(8),
		nibbleError(9),
		checksumError(10),
		cRCError(11),
		correctedSingleBitError(12),
		correctedError(13),
		uncorrectableError(14)
	}
	ACCESS		read-only
	STATUS		mandatory
	DESCRIPTION	"The type of error that is associated with the current status
reported in Operational State for this Memory Device."
	REFERENCE "'DMTF|Memory Device|001' 12"
	::= { dMTFMemoryDeviceEntry 12 }

errorGranularityAtt13 OBJECT-TYPE
	SYNTAX		INTEGER { 
		other(1),
		unknown(2),
		deviceLevel(3),
		memoryPartitionLevel(4)
	}
	ACCESS		read-only
	STATUS		mandatory
	DESCRIPTION	"Specifies whether the current error's location can be resolved
to the partition or device level."
	REFERENCE "'DMTF|Memory Device|001' 13"
	::= { dMTFMemoryDeviceEntry 13 }

lastErrorUpdateAtt14 OBJECT-TYPE
	SYNTAX		INTEGER { 
		other(1),
		unknown(2),
		noUpdateSinceLastInstrumentationStart(3),
		updatedFromInformationObtainedPriorToInstrumentati(4),
		updatedDuringInstrumentationRunTime(5)
	}
	ACCESS		read-only
	STATUS		mandatory
	DESCRIPTION	"System state during which the last error update was collected."
	REFERENCE "'DMTF|Memory Device|001' 14"
	::= { dMTFMemoryDeviceEntry 14 }

errorOperationAtt15 OBJECT-TYPE
	SYNTAX		INTEGER { 
		other(1),
		unknown(2),
		read(3),
		write(4),
		partialWrite(5)
	}
	ACCESS		read-only
	STATUS		mandatory
	DESCRIPTION	"The memory access operation that caused the current error."
	REFERENCE "'DMTF|Memory Device|001' 15"
	::= { dMTFMemoryDeviceEntry 15 }

errorDataSizeAtt16 OBJECT-TYPE
	SYNTAX		DmiInteger
	ACCESS		read-only
	STATUS		mandatory
	DESCRIPTION	"The size of the data transfer that caused the error,in bits.
Zero indicates no error, 0x80000000 denotes 'unknown'."
	REFERENCE "'DMTF|Memory Device|001' 16"
	::= { dMTFMemoryDeviceEntry 16 }

errorDataAtt17 OBJECT-TYPE
	SYNTAX		DmiOctetstring
	ACCESS		read-only
	STATUS		mandatory
	DESCRIPTION	"Data captured during the erroneous Memory Array access. The
data occupies the first n bytes of the octet string required to hold 'Error
Data Size' bits of the data. Data is stored least-significant byte first."
	REFERENCE "'DMTF|Memory Device|001' 17"
	::= { dMTFMemoryDeviceEntry 17 }

vendorSyndromeAtt18 OBJECT-TYPE
	SYNTAX		DmiOctetstring
	ACCESS		read-only
	STATUS		mandatory
	DESCRIPTION	"Vendor-specific syndrome or CRC data associated with the
erroneous access."
	REFERENCE "'DMTF|Memory Device|001' 18"
	::= { dMTFMemoryDeviceEntry 18 }

deviceErrorAddressAtt19 OBJECT-TYPE
	SYNTAX		DmiInteger
	ACCESS		read-only
	STATUS		mandatory
	DESCRIPTION	"Physical address of the error relative to the start of the
device, in bytes.  0x80000000 denotes 'unknown'."
	REFERENCE "'DMTF|Memory Device|001' 19"
	::= { dMTFMemoryDeviceEntry 19 }

arrayErrorAddressAtt20 OBJECT-TYPE
	SYNTAX		DmiInteger
	ACCESS		read-only
	STATUS		mandatory
	DESCRIPTION	"Physical address of the kilobyte where the error is located,
relative to the bus for the Memory Array. 0x80000000 denotes 'unknown'."
	REFERENCE "'DMTF|Memory Device|001' 20"
	::= { dMTFMemoryDeviceEntry 20 }

errorResolutionAtt21 OBJECT-TYPE
	SYNTAX		DmiInteger
	ACCESS		read-only
	STATUS		mandatory
	DESCRIPTION	"Range in bytes that the error can be determined to be within,whe
 an Error Address is given. 0x80000000 denotes 'unknown'."
	REFERENCE "'DMTF|Memory Device|001' 21"
	::= { dMTFMemoryDeviceEntry 21 }

fRUGroupIndexAtt22 OBJECT-TYPE
	SYNTAX		DmiInteger
	ACCESS		read-only
	STATUS		mandatory
	DESCRIPTION	"If this is a Field Replaceable Unit or if it is part of another
FRU, this provides an index into the FRU table; 'value = -1' indicates that
the group is not a FRU."
	REFERENCE "'DMTF|Memory Device|001' 22"
	::= { dMTFMemoryDeviceEntry 22 }

operationalGroupIndexAtt23 OBJECT-TYPE
	SYNTAX		DmiInteger
	ACCESS		read-only
	STATUS		mandatory
	DESCRIPTION	"The index into the Operational State Table for this device."
	REFERENCE "'DMTF|Memory Device|001' 23"
	::= { dMTFMemoryDeviceEntry 23 }

SdMTFOperatingSystem ::= SEQUENCE { 
	dMTFOperatingSystemState INTEGER,
	operatingSystemIndexAtt1	DmiInteger,
	operatingSystemNameAtt2	DmiDisplaystring,
	operatingSystemVersionAtt3	DmiDisplaystring,
	primaryOperatingSystemAtt4	DmiInteger,
	operatingSystemBootDeviceStorageTypeAtt5	DmiInteger,
	operatingSystemBootDeviceIndexAtt6	DmiInteger,
	operatingSystemBootPartitionIndexAtt7	DmiInteger,
	operatingSystemDescriptionAtt8	DmiDisplaystring
}

dMTFOperatingSystemTable OBJECT-TYPE
	SYNTAX		SEQUENCE OF SdMTFOperatingSystem
	ACCESS		not-accessible
	STATUS		mandatory
	DESCRIPTION	"This group defines general information about operating systems
installed on this system."
	::= { dmtfSystemsMIF 2 }

dMTFOperatingSystemEntry OBJECT-TYPE
	SYNTAX		SdMTFOperatingSystem
	ACCESS		not-accessible
	STATUS		mandatory
	DESCRIPTION	"This group defines general information about operating systems
installed on this system."
	INDEX		{ DmiCompId,DmiGroupId, operatingSystemIndexAtt1 }
	::= { dMTFOperatingSystemTable 1 }


dMTFOperatingSystemState OBJECT-TYPE
	SYNTAX		INTEGER { 
		active(1),
		notInService(2),
		notReady(3),
		createAndGo(4),
		createAndWait(5),
		destroy(6)
	}
	ACCESS		read-write
	STATUS		mandatory
	REFERENCE "'DMTF|Operating System|001' 0"
	::= { dMTFOperatingSystemEntry 0 }

operatingSystemIndexAtt1 OBJECT-TYPE
	SYNTAX		DmiInteger
	ACCESS		read-only
	STATUS		mandatory
	DESCRIPTION	"The index into the operating system table."
	REFERENCE "'DMTF|Operating System|001' 1"
	::= { dMTFOperatingSystemEntry 1 }

operatingSystemNameAtt2 OBJECT-TYPE
	SYNTAX		DmiDisplaystring
	ACCESS		read-only
	STATUS		mandatory
	DESCRIPTION	"The name of this operating system."
	REFERENCE "'DMTF|Operating System|001' 2"
	::= { dMTFOperatingSystemEntry 2 }

operatingSystemVersionAtt3 OBJECT-TYPE
	SYNTAX		DmiDisplaystring
	ACCESS		read-only
	STATUS		mandatory
	DESCRIPTION	"The version number of this operating system."
	REFERENCE "'DMTF|Operating System|001' 3"
	::= { dMTFOperatingSystemEntry 3 }

primaryOperatingSystemAtt4 OBJECT-TYPE
	SYNTAX		INTEGER { 
		false(0),
		true(1)
	}
	ACCESS		read-only
	STATUS		mandatory
	DESCRIPTION	"If true, this is the primary operating system."
	REFERENCE "'DMTF|Operating System|001' 4"
	::= { dMTFOperatingSystemEntry 4 }

operatingSystemBootDeviceStorageTypeAtt5 OBJECT-TYPE
	SYNTAX		INTEGER { 
		other(1),
		unknown(2),
		hardDisk(3),
		floppyDisk(4),
		opticalROM(5),
		opticalWORM(6),
		opticalRW(7),
		compactDisk(8),
		flashDisk(9),
		bernoulli(10),
		opticalFloppyDisk(11)
	}
	ACCESS		read-only
	STATUS		mandatory
	DESCRIPTION	"An index into the Disks Table to indicate the device from
which this operating system was booted. To fully access the Disks Table,
this index must be combined with the attribute Boot Device Index."
	REFERENCE "'DMTF|Operating System|001' 5"
	::= { dMTFOperatingSystemEntry 5 }

operatingSystemBootDeviceIndexAtt6 OBJECT-TYPE
	SYNTAX		DmiInteger
	ACCESS		read-only
	STATUS		mandatory
	DESCRIPTION	"An index into the Disks Table."
	REFERENCE "'DMTF|Operating System|001' 6"
	::= { dMTFOperatingSystemEntry 6 }

operatingSystemBootPartitionIndexAtt7 OBJECT-TYPE
	SYNTAX		DmiInteger
	ACCESS		read-only
	STATUS		mandatory
	DESCRIPTION	"An index into the Partition table indicating the partition
from which this operating system booted."
	REFERENCE "'DMTF|Operating System|001' 7"
	::= { dMTFOperatingSystemEntry 7 }

operatingSystemDescriptionAtt8 OBJECT-TYPE
	SYNTAX		DmiDisplaystring
	ACCESS		read-only
	STATUS		mandatory
	DESCRIPTION	"A description of this operating system."
	REFERENCE "'DMTF|Operating System|001' 8"
	::= { dMTFOperatingSystemEntry 8 }

SdMTFOperationalState ::= SEQUENCE { 
	dMTFOperationalStateState INTEGER,
	operationalStateInstanceIndexAtt1	DmiInteger,
	deviceGroupIndexAtt2-1	DmiInteger,
	operationalStatusAtt3	DmiInteger,
	usageStateAtt4	DmiInteger,
	availabilityStatusAtt5	DmiInteger,
	administrativeStateAtt6	DmiInteger,
	fatalErrorCountAtt7	DmiCounter,
	majorErrorCountAtt8	DmiCounter,
	warningErrorCountAtt9	DmiCounter,
	currentErrorStatusAtt10	DmiInteger,
	devicePredictedFailureStatusAtt11	DmiInteger
}

dMTFOperationalStateTable OBJECT-TYPE
	SYNTAX		SEQUENCE OF SdMTFOperationalState
	ACCESS		not-accessible
	STATUS		mandatory
	DESCRIPTION	"This group provides the operational state, usage, and availabili
y status,and administrative state indicators for specific Device Group instances
"
	::= { dmtfSystemsMIF 30 }

dMTFOperationalStateEntry OBJECT-TYPE
	SYNTAX		SdMTFOperationalState
	ACCESS		not-accessible
	STATUS		mandatory
	DESCRIPTION	"This group provides the operational state, usage, and availabili
y status,and administrative state indicators for specific Device Group instances
"
	INDEX		{ DmiCompId,DmiGroupId, operationalStateInstanceIndexAtt1 }
	::= { dMTFOperationalStateTable 1 }


dMTFOperationalStateState OBJECT-TYPE
	SYNTAX		INTEGER { 
		active(1),
		notInService(2),
		notReady(3),
		createAndGo(4),
		createAndWait(5),
		destroy(6)
	}
	ACCESS		read-write
	STATUS		mandatory
	REFERENCE "'DMTF|Operational State|003' 0"
	::= { dMTFOperationalStateEntry 0 }

operationalStateInstanceIndexAtt1 OBJECT-TYPE
	SYNTAX		DmiInteger
	ACCESS		read-only
	STATUS		mandatory
	DESCRIPTION	"The Index into the Operational State table."
	REFERENCE "'DMTF|Operational State|003' 1"
	::= { dMTFOperationalStateEntry 1 }

deviceGroupIndexAtt2-1 OBJECT-TYPE
	SYNTAX		DmiInteger
	ACCESS		read-only
	STATUS		mandatory
	DESCRIPTION	"The group ID of the group referencing this instance."
	REFERENCE "'DMTF|Operational State|003' 2"
	::= { dMTFOperationalStateEntry 2 }

operationalStatusAtt3 OBJECT-TYPE
	SYNTAX		INTEGER { 
		other(1),
		unknown(2),
		enabled(3),
		disabled(4),
		notApplicable(5)
	}
	ACCESS		read-only
	STATUS		mandatory
	DESCRIPTION	"The operational status of the Device Group instance."
	REFERENCE "'DMTF|Operational State|003' 3"
	::= { dMTFOperationalStateEntry 3 }

usageStateAtt4 OBJECT-TYPE
	SYNTAX		INTEGER { 
		other(1),
		unknown(2),
		idle(3),
		active(4),
		busy(5),
		notApplicable(6)
	}
	ACCESS		read-only
	STATUS		mandatory
	DESCRIPTION	"The usage state of the Device Group instance."
	REFERENCE "'DMTF|Operational State|003' 4"
	::= { dMTFOperationalStateEntry 4 }

availabilityStatusAtt5 OBJECT-TYPE
	SYNTAX		INTEGER { 
		other(1),
		unknown(2),
		running(3),
		warning(4),
		inTest(5),
		notApplicable(6),
		powerOff(7),
		offLine(8),
		offDuty(9),
		degraded(10),
		notInstalled(11),
		installError(12),
		powerSave(13)
	}
	ACCESS		read-only
	STATUS		mandatory
	DESCRIPTION	"The availability status of the Device Group instance."
	REFERENCE "'DMTF|Operational State|003' 5"
	::= { dMTFOperationalStateEntry 5 }

administrativeStateAtt6 OBJECT-TYPE
	SYNTAX		INTEGER { 
		other(1),
		unknown(2),
		locked(3),
		unlocked(4),
		notApplicable(5),
		shuttingDown(6)
	}
	ACCESS		read-only
	STATUS		mandatory
	DESCRIPTION	"The administrative state of the Device Group instance."
	REFERENCE "'DMTF|Operational State|003' 6"
	::= { dMTFOperationalStateEntry 6 }

fatalErrorCountAtt7 OBJECT-TYPE
	SYNTAX		DmiCounter
	ACCESS		read-only
	STATUS		mandatory
	DESCRIPTION	"The accumulated Fatal or Non-recoverable error count for
this Device Group instance."
	REFERENCE "'DMTF|Operational State|003' 7"
	::= { dMTFOperationalStateEntry 7 }

majorErrorCountAtt8 OBJECT-TYPE
	SYNTAX		DmiCounter
	ACCESS		read-only
	STATUS		mandatory
	DESCRIPTION	"The accumulated Major or Critical error count for this Device
Group instance."
	REFERENCE "'DMTF|Operational State|003' 8"
	::= { dMTFOperationalStateEntry 8 }

warningErrorCountAtt9 OBJECT-TYPE
	SYNTAX		DmiCounter
	ACCESS		read-only
	STATUS		mandatory
	DESCRIPTION	"The accumulated Warning or Non-Critical error count for this
Device Group instance."
	REFERENCE "'DMTF|Operational State|003' 9"
	::= { dMTFOperationalStateEntry 9 }

currentErrorStatusAtt10 OBJECT-TYPE
	SYNTAX		INTEGER { 
		other(1),
		unknown(2),
		oK(3),
		nonCritical(4),
		critical(5),
		nonRecoverable(6)
	}
	ACCESS		read-only
	STATUS		mandatory
	DESCRIPTION	"This attribute presents the current error status for this
Device Group instance.  The most critical error status in effect should be
presented. I.e. if a part of the Device Group instance is 'Critical', while
other status is 'Non-critical' then the status'Critical' should be reported."
	REFERENCE "'DMTF|Operational State|003' 10"
	::= { dMTFOperationalStateEntry 10 }

devicePredictedFailureStatusAtt11 OBJECT-TYPE
	SYNTAX		INTEGER { 
		other(1),
		unknown(2),
		notSupportedByThisDevice(3),
		noFailurePredictedByTheDevice(4),
		deviceFailurePredictedByTheDevice(5),
		mediaFailurePredictedByTheDevice(6)
	}
	ACCESS		read-only
	STATUS		mandatory
	DESCRIPTION	"Enumeration describing the current Device Predicted Failure
Status (e.g.: the S.M.A.R.T. status of the device)."
	REFERENCE "'DMTF|Operational State|003' 11"
	::= { dMTFOperationalStateEntry 11 }

SiNTELMIFTOMIB ::= SEQUENCE { 
	dellBaseBoardMIBAtt1	DmiDisplaystring,
	mIBOIDAtt2	DmiDisplaystring,
	disableTrapsAtt3	DmiInteger
}

dmiDynOid386845712        OBJECT IDENTIFIER ::= { dmtfDynOids 386845712 } 
dmiDynOid73111109        OBJECT IDENTIFIER ::= { dmiDynOid386845712 73111109 } 
dmiDynOid3922453424        OBJECT IDENTIFIER ::= { dmiDynOid73111109 3922453424 } 

iNTELMIFTOMIBTable OBJECT-TYPE
	SYNTAX		SEQUENCE OF SiNTELMIFTOMIB
	ACCESS		not-accessible
	STATUS		mandatory
	DESCRIPTION	"This group maps the DMI attributes to SNMP."
	::= { dmiDynOid3922453424 1737102472 }

iNTELMIFTOMIBEntry OBJECT-TYPE
	SYNTAX		SiNTELMIFTOMIB
	ACCESS		not-accessible
	STATUS		mandatory
	DESCRIPTION	"This group maps the DMI attributes to SNMP."
	INDEX		{ DmiCompId,DmiGroupId }
	::= { iNTELMIFTOMIBTable 1 }


dellBaseBoardMIBAtt1 OBJECT-TYPE
	SYNTAX		DmiDisplaystring
	ACCESS		read-only
	STATUS		mandatory
	DESCRIPTION	"The MIB name that defines this MIF"
	REFERENCE "'INTEL|MIFTOMIB|1.0' 1"
	::= { iNTELMIFTOMIBEntry 1 }

mIBOIDAtt2 OBJECT-TYPE
	SYNTAX		DmiDisplaystring
	ACCESS		read-only
	STATUS		mandatory
	DESCRIPTION	"The MIB OID that corresponds to this MIF"
	REFERENCE "'INTEL|MIFTOMIB|1.0' 2"
	::= { iNTELMIFTOMIBEntry 2 }

disableTrapsAtt3 OBJECT-TYPE
	SYNTAX		DmiInteger
	ACCESS		read-only
	STATUS		mandatory
	DESCRIPTION	"Setting this value to 1 disables trap generation."
	REFERENCE "'INTEL|MIFTOMIB|1.0' 3"
	::= { iNTELMIFTOMIBEntry 3 }

SdMTFPowerSupply ::= SEQUENCE { 
	dMTFPowerSupplyState INTEGER,
	powerSupplyIndexAtt1	DmiInteger,
	fRUGroupIndexAtt2-1	DmiInteger,
	operationalGroupIndexAtt3-1	DmiInteger,
	powerUnitIndexAtt4	DmiInteger,
	powerSupplyTypeAtt5	DmiInteger,
	inputVoltageCapabilityDescriptionAtt6	DmiDisplaystring,
	range1InputVoltageLowAtt7	DmiInteger,
	range1InputVoltageHighAtt8	DmiInteger,
	range1VoltageProbeIndexAtt9	DmiInteger,
	range1ElectricalCurrentProbeIndexAtt10	DmiInteger,
	range2InputVoltageLowAtt11	DmiInteger,
	range2InputVoltageHighAtt12	DmiInteger,
	range2VoltageProbeIndexAtt13	DmiInteger,
	range2CurrentProbeIndexAtt14	DmiInteger,
	activeInputVoltageRangeAtt15	DmiInteger,
	inputVoltageRangeSwitchingAtt16	DmiInteger,
	range1InputFrequencyLowAtt17	DmiInteger,
	range1InputFrequencyHighAtt18	DmiInteger,
	range2InputFrequencyLowAtt19	DmiInteger,
	range2InputFrequencyHighAtt20	DmiInteger,
	totalOutputPowerAtt21	DmiInteger
}

dMTFPowerSupplyTable OBJECT-TYPE
	SYNTAX		SEQUENCE OF SdMTFPowerSupply
	ACCESS		not-accessible
	STATUS		mandatory
	DESCRIPTION	"This group defines various attributes for power supplies
in this system."
	::= { dmtfSystemsMIF 16 }

dMTFPowerSupplyEntry OBJECT-TYPE
	SYNTAX		SdMTFPowerSupply
	ACCESS		not-accessible
	STATUS		mandatory
	DESCRIPTION	"This group defines various attributes for power supplies
in this system."
	INDEX		{ DmiCompId,DmiGroupId, powerSupplyIndexAtt1 }
	::= { dMTFPowerSupplyTable 1 }


dMTFPowerSupplyState OBJECT-TYPE
	SYNTAX		INTEGER { 
		active(1),
		notInService(2),
		notReady(3),
		createAndGo(4),
		createAndWait(5),
		destroy(6)
	}
	ACCESS		read-write
	STATUS		mandatory
	REFERENCE "'DMTF|Power Supply|002' 0"
	::= { dMTFPowerSupplyEntry 0 }

powerSupplyIndexAtt1 OBJECT-TYPE
	SYNTAX		DmiInteger
	ACCESS		read-only
	STATUS		mandatory
	DESCRIPTION	"The index number of the current power supply."
	REFERENCE "'DMTF|Power Supply|002' 1"
	::= { dMTFPowerSupplyEntry 1 }

fRUGroupIndexAtt2-1 OBJECT-TYPE
	SYNTAX		DmiInteger
	ACCESS		read-only
	STATUS		mandatory
	DESCRIPTION	"If this is a Field Replaceable Unit or if it is part of another
FRU, this provides an index into the FRU table; 'value = -1' indicates that
the group is not a FRU."
	REFERENCE "'DMTF|Power Supply|002' 2"
	::= { dMTFPowerSupplyEntry 2 }

operationalGroupIndexAtt3-1 OBJECT-TYPE
	SYNTAX		DmiInteger
	ACCESS		read-only
	STATUS		mandatory
	DESCRIPTION	"The index into the Operational State table for this device."
	REFERENCE "'DMTF|Power Supply|002' 3"
	::= { dMTFPowerSupplyEntry 3 }

powerUnitIndexAtt4 OBJECT-TYPE
	SYNTAX		DmiInteger
	ACCESS		read-only
	STATUS		mandatory
	DESCRIPTION	"This is the ID of the Power Unit (logical power supply) to
which this Power Supply belongs. This value matches up with the Power Unit
Table Index attribute defined in the Power Unit Global Table."
	REFERENCE "'DMTF|Power Supply|002' 4"
	::= { dMTFPowerSupplyEntry 4 }

powerSupplyTypeAtt5 OBJECT-TYPE
	SYNTAX		INTEGER { 
		other(1),
		unknown(2),
		linear(3),
		switching(4),
		battery(5),
		uPS(6),
		converter(7),
		regulator(8)
	}
	ACCESS		read-only
	STATUS		mandatory
	DESCRIPTION	"This attribute describes the type of Power Supply, e.g. Linear,
Switching, Battery, etc."
	REFERENCE "'DMTF|Power Supply|002' 5"
	::= { dMTFPowerSupplyEntry 5 }

inputVoltageCapabilityDescriptionAtt6 OBJECT-TYPE
	SYNTAX		DmiDisplaystring
	ACCESS		read-only
	STATUS		mandatory
	DESCRIPTION	"An expanded description of the Input Voltage Capability for
this Power Supply."
	REFERENCE "'DMTF|Power Supply|002' 6"
	::= { dMTFPowerSupplyEntry 6 }

range1InputVoltageLowAtt7 OBJECT-TYPE
	SYNTAX		DmiInteger
	ACCESS		read-only
	STATUS		mandatory
	DESCRIPTION	"The low voltage of Input Voltage Range 1 for this Power Supply,
in millivolts. A value of 0x80000000 denotes 'unknown'."
	REFERENCE "'DMTF|Power Supply|002' 7"
	::= { dMTFPowerSupplyEntry 7 }

range1InputVoltageHighAtt8 OBJECT-TYPE
	SYNTAX		DmiInteger
	ACCESS		read-only
	STATUS		mandatory
	DESCRIPTION	"The high voltage of Input Voltage Range 1 for this Power
Supply, in millivolts. A value of 0x80000000 denotes 'unknown'."
	REFERENCE "'DMTF|Power Supply|002' 8"
	::= { dMTFPowerSupplyEntry 8 }

range1VoltageProbeIndexAtt9 OBJECT-TYPE
	SYNTAX		DmiInteger
	ACCESS		read-only
	STATUS		mandatory
	DESCRIPTION	"Index into the Voltage Probe table identifying the voltage
probe monitoring this input range. 0 indicates no probe provided."
	REFERENCE "'DMTF|Power Supply|002' 9"
	::= { dMTFPowerSupplyEntry 9 }

range1ElectricalCurrentProbeIndexAtt10 OBJECT-TYPE
	SYNTAX		DmiInteger
	ACCESS		read-only
	STATUS		mandatory
	DESCRIPTION	"Index into the Elelctrical Current Probe table identifying
the Electrical current probe monitoring this input range. 0 indicates no
probe provided."
	REFERENCE "'DMTF|Power Supply|002' 10"
	::= { dMTFPowerSupplyEntry 10 }

range2InputVoltageLowAtt11 OBJECT-TYPE
	SYNTAX		DmiInteger
	ACCESS		read-only
	STATUS		mandatory
	DESCRIPTION	"The low voltage of Input Voltage Range 2 for this Power Supply,
in millivolts. A value of 0x80000000 denotes 'unknown'."
	REFERENCE "'DMTF|Power Supply|002' 11"
	::= { dMTFPowerSupplyEntry 11 }

range2InputVoltageHighAtt12 OBJECT-TYPE
	SYNTAX		DmiInteger
	ACCESS		read-only
	STATUS		mandatory
	DESCRIPTION	"The high voltage of Input Voltage Range 2 for this Power
Supply, in millivolts. A value of 0x80000000 denotes 'unknown'"
	REFERENCE "'DMTF|Power Supply|002' 12"
	::= { dMTFPowerSupplyEntry 12 }

range2VoltageProbeIndexAtt13 OBJECT-TYPE
	SYNTAX		DmiInteger
	ACCESS		read-only
	STATUS		mandatory
	DESCRIPTION	"Index into the Voltage Probe table identifying the voltage
probe monitoring this input range. 0 indicates no probe provided."
	REFERENCE "'DMTF|Power Supply|002' 13"
	::= { dMTFPowerSupplyEntry 13 }

range2CurrentProbeIndexAtt14 OBJECT-TYPE
	SYNTAX		DmiInteger
	ACCESS		read-only
	STATUS		mandatory
	DESCRIPTION	"Index into the Current Probe table identifying the current
probe monitoring this input range. 0 indicates no probe provided."
	REFERENCE "'DMTF|Power Supply|002' 14"
	::= { dMTFPowerSupplyEntry 14 }

activeInputVoltageRangeAtt15 OBJECT-TYPE
	SYNTAX		INTEGER { 
		other(1),
		unknown(2),
		range1(3),
		range2(4),
		both(5)
	}
	ACCESS		read-only
	STATUS		mandatory
	DESCRIPTION	"The value of this attribute indicates which input voltage
range of this Power Supply is currently active."
	REFERENCE "'DMTF|Power Supply|002' 15"
	::= { dMTFPowerSupplyEntry 15 }

inputVoltageRangeSwitchingAtt16 OBJECT-TYPE
	SYNTAX		INTEGER { 
		other(1),
		unknown(2),
		manual(3),
		autoswitch(4),
		wideRange(5),
		notApplicable(6)
	}
	ACCESS		read-only
	STATUS		mandatory
	DESCRIPTION	"This attribute describes the kind of input voltage range
switching that is implemented in this power supply."
	REFERENCE "'DMTF|Power Supply|002' 16"
	::= { dMTFPowerSupplyEntry 16 }

range1InputFrequencyLowAtt17 OBJECT-TYPE
	SYNTAX		DmiInteger
	ACCESS		read-only
	STATUS		mandatory
	DESCRIPTION	"The frequency at the low end of this power supply's Input
Frequency Range 1. A value of zero implies DC. A value of 0x80000000 denotes
'unknown'"
	REFERENCE "'DMTF|Power Supply|002' 17"
	::= { dMTFPowerSupplyEntry 17 }

range1InputFrequencyHighAtt18 OBJECT-TYPE
	SYNTAX		DmiInteger
	ACCESS		read-only
	STATUS		mandatory
	DESCRIPTION	"The frequency at the high end of this power supply's Input
Frequency Range 1. A value of zero implies DC. A value of 0x80000000 denotes
'unknown'"
	REFERENCE "'DMTF|Power Supply|002' 18"
	::= { dMTFPowerSupplyEntry 18 }

range2InputFrequencyLowAtt19 OBJECT-TYPE
	SYNTAX		DmiInteger
	ACCESS		read-only
	STATUS		mandatory
	DESCRIPTION	"The frequency at the low end of this power supply's Input
Frequency Range 2. A value of zero implies DC. A value of 0x80000000 denotes
'unknown'"
	REFERENCE "'DMTF|Power Supply|002' 19"
	::= { dMTFPowerSupplyEntry 19 }

range2InputFrequencyHighAtt20 OBJECT-TYPE
	SYNTAX		DmiInteger
	ACCESS		read-only
	STATUS		mandatory
	DESCRIPTION	"The frequency at the high end of this power supply's Input
Frequency Range 2. A value of zero implies DC. A value of 0x80000000 denotes
'unknown'"
	REFERENCE "'DMTF|Power Supply|002' 20"
	::= { dMTFPowerSupplyEntry 20 }

totalOutputPowerAtt21 OBJECT-TYPE
	SYNTAX		DmiInteger
	ACCESS		read-only
	STATUS		mandatory
	DESCRIPTION	"This attribute value represents the total output power of
this power supply in milliWatts. 0x80000000 denotes 'unknown'"
	REFERENCE "'DMTF|Power Supply|002' 21"
	::= { dMTFPowerSupplyEntry 21 }

SdMTFPowerUnitGlobalTable ::= SEQUENCE { 
	dMTFPowerUnitGlobalTableState INTEGER,
	powerUnitIndexAtt1	DmiInteger,
	powerUnitRedundancyStatusAtt2	DmiInteger
}

dMTFPowerUnitGlobalTableTable OBJECT-TYPE
	SYNTAX		SEQUENCE OF SdMTFPowerUnitGlobalTable
	ACCESS		not-accessible
	STATUS		mandatory
	DESCRIPTION	"This global table describes all of the Power Units in this
system component. The unique index of each Power Unit is the key into this
table. A Power Unit is composed of potentially more than one Power Supply
in a redundant configuration. Individual power supplies are described in
the 'Power Supply' standard group. In that group, each individual power supply
entry will point to a Power Unit in this table by using the index of the
row in this table that describes the Power Unit. If a Power Unit is redunda"
	::= { dmtfSystemsMIF 66 }

dMTFPowerUnitGlobalTableEntry OBJECT-TYPE
	SYNTAX		SdMTFPowerUnitGlobalTable
	ACCESS		not-accessible
	STATUS		mandatory
	DESCRIPTION	"This global table describes all of the Power Units in this
system component. The unique index of each Power Unit is the key into this
table. A Power Unit is composed of potentially more than one Power Supply
in a redundant configuration. Individual power supplies are described in
the 'Power Supply' standard group. In that group, each individual power supply
entry will point to a Power Unit in this table by using the index of the
row in this table that describes the Power Unit. If a Power Unit is redunda"
	INDEX		{ DmiCompId,DmiGroupId, powerUnitIndexAtt1 }
	::= { dMTFPowerUnitGlobalTableTable 1 }


dMTFPowerUnitGlobalTableState OBJECT-TYPE
	SYNTAX		INTEGER { 
		active(1),
		notInService(2),
		notReady(3),
		createAndGo(4),
		createAndWait(5),
		destroy(6)
	}
	ACCESS		read-write
	STATUS		mandatory
	REFERENCE "'DMTF|Power Unit Global Table|001' 0"
	::= { dMTFPowerUnitGlobalTableEntry 0 }

powerUnitIndexAtt1 OBJECT-TYPE
	SYNTAX		DmiInteger
	ACCESS		read-only
	STATUS		mandatory
	DESCRIPTION	"The unique index given to each Power Unit being described
by this table. This unique index is the key into this table."
	REFERENCE "'DMTF|Power Unit Global Table|001' 1"
	::= { dMTFPowerUnitGlobalTableEntry 1 }

powerUnitRedundancyStatusAtt2 OBJECT-TYPE
	SYNTAX		INTEGER { 
		other(1),
		unknown(2),
		notApplicableUnitNotRedundant-1(3),
		offline(4),
		fullyRedundant-1(5),
		degradedRedundancy(6),
		redundancyLost(7)
	}
	ACCESS		read-only
	STATUS		mandatory
	DESCRIPTION	"Gives the redundancy status of the Power Unit.  'Fully Redundant
 means that all of the configured redundancy is still available; 'Degraded
Redundancy' means that some failures have been experienced but some reduced
amount of redundancy is still available; 'Redundancy Lost' means that a sufficie
t number of failures have been experienced that no redundancy is available
and the next failure experienced within the Power Unit will cause overall
Power Unit failure. "
	REFERENCE "'DMTF|Power Unit Global Table|001' 2"
	::= { dMTFPowerUnitGlobalTableEntry 2 }

SdMTFProcessor ::= SEQUENCE { 
	dMTFProcessorState INTEGER,
	processorIndexAtt1	DmiInteger,
	processorTypeAtt2	DmiInteger,
	processorFamilyAtt3	DmiInteger,
	processorVersionInformationAtt4	DmiDisplaystring,
	maximumSpeedAtt5	DmiInteger,
	currentSpeedAtt6	DmiInteger,
	processorUpgradeAtt7	DmiInteger,
	fRUGroupIndexAtt8	DmiInteger,
	operationalGroupIndexAtt9	DmiInteger,
	level1CacheIndexAtt10	DmiInteger,
	level2CacheIndexAtt11	DmiInteger,
	level3CacheIndexAtt12	DmiInteger
}

dMTFProcessorTable OBJECT-TYPE
	SYNTAX		SEQUENCE OF SdMTFProcessor
	ACCESS		not-accessible
	STATUS		mandatory
	DESCRIPTION	"This group defines the attributes for each and every processor
installed in this system."
	::= { dmtfSystemsMIF 5 }

dMTFProcessorEntry OBJECT-TYPE
	SYNTAX		SdMTFProcessor
	ACCESS		not-accessible
	STATUS		mandatory
	DESCRIPTION	"This group defines the attributes for each and every processor
installed in this system."
	INDEX		{ DmiCompId,DmiGroupId, processorIndexAtt1 }
	::= { dMTFProcessorTable 1 }


dMTFProcessorState OBJECT-TYPE
	SYNTAX		INTEGER { 
		active(1),
		notInService(2),
		notReady(3),
		createAndGo(4),
		createAndWait(5),
		destroy(6)
	}
	ACCESS		read-write
	STATUS		mandatory
	REFERENCE "'DMTF|Processor|006' 0"
	::= { dMTFProcessorEntry 0 }

processorIndexAtt1 OBJECT-TYPE
	SYNTAX		DmiInteger
	ACCESS		read-only
	STATUS		mandatory
	DESCRIPTION	"An index into the processor table."
	REFERENCE "'DMTF|Processor|006' 1"
	::= { dMTFProcessorEntry 1 }

processorTypeAtt2 OBJECT-TYPE
	SYNTAX		INTEGER { 
		other(1),
		unknown(2),
		centralProcessor(3),
		mathProcessor(4),
		dSPProcessor(5),
		videoProcessor(6)
	}
	ACCESS		read-only
	STATUS		mandatory
	DESCRIPTION	"The type of processor currently in the system."
	REFERENCE "'DMTF|Processor|006' 2"
	::= { dMTFProcessorEntry 2 }

processorFamilyAtt3 OBJECT-TYPE
	SYNTAX		INTEGER { 
		other(1),
		unknown(2),
		x8086(3),
		x80286(4),
		x80386(5),
		x80486(6),
		x8087(7),
		x80287(8),
		x80387(9),
		x80487(10),
		pentiumFamily(11),
		pentiumPro(12),
		pentiumII(13),
		pentiumMMX(14),
		celeron(15),
		xeon(16),
		m1Family(18),
		m2Family(19),
		k5Family(25),
		k6Family(26),
		powerPCFamily(32),
		powerPC601(33),
		powerPC603(34),
		powerPC603-1(35),
		powerPC604(36),
		alphaFamily(48),
		mIPSFamily(64),
		sPARCFamily(80),
		x68040(96),
		x68xxxFamily(97),
		x68000(98),
		x68010(99),
		x68020(100),
		x68030(101),
		hobbitFamily(112),
		weitek(128),
		pARISCFamily(144),
		v30Family(160)
	}
	ACCESS		read-only
	STATUS		mandatory
	DESCRIPTION	"The family of processors to which this processor belongs."
	REFERENCE "'DMTF|Processor|006' 3"
	::= { dMTFProcessorEntry 3 }

processorVersionInformationAtt4 OBJECT-TYPE
	SYNTAX		DmiDisplaystring
	ACCESS		read-only
	STATUS		mandatory
	DESCRIPTION	"The version number or string for this processor."
	REFERENCE "'DMTF|Processor|006' 4"
	::= { dMTFProcessorEntry 4 }

maximumSpeedAtt5 OBJECT-TYPE
	SYNTAX		DmiInteger
	ACCESS		read-only
	STATUS		mandatory
	DESCRIPTION	"The maximum processor speed supported by this system in MHz."
	REFERENCE "'DMTF|Processor|006' 5"
	::= { dMTFProcessorEntry 5 }

currentSpeedAtt6 OBJECT-TYPE
	SYNTAX		DmiInteger
	ACCESS		read-only
	STATUS		mandatory
	DESCRIPTION	"The current speed (in MHz) of this processor."
	REFERENCE "'DMTF|Processor|006' 6"
	::= { dMTFProcessorEntry 6 }

processorUpgradeAtt7 OBJECT-TYPE
	SYNTAX		INTEGER { 
		other(1),
		unknown(2),
		daughterBoard(3),
		zIFSocket(4),
		replacementPiggyBack(5),
		none(6),
		lIFSocket(7),
		slot1(8),
		slot2(9)
	}
	ACCESS		read-only
	STATUS		mandatory
	DESCRIPTION	"The method by which this processor can be upgraded, if upgrades
are supported."
	REFERENCE "'DMTF|Processor|006' 7"
	::= { dMTFProcessorEntry 7 }

fRUGroupIndexAtt8 OBJECT-TYPE
	SYNTAX		DmiInteger
	ACCESS		read-only
	STATUS		mandatory
	DESCRIPTION	"If this is a Field Replaceable Unit or if it is part of another
FRU, this provides an index into the FRU table; 'value = -1' indicates that
the group is not a FRU."
	REFERENCE "'DMTF|Processor|006' 8"
	::= { dMTFProcessorEntry 8 }

operationalGroupIndexAtt9 OBJECT-TYPE
	SYNTAX		DmiInteger
	ACCESS		read-only
	STATUS		mandatory
	DESCRIPTION	"The index into the Operational State Table for this device
if applicable."
	REFERENCE "'DMTF|Processor|006' 9"
	::= { dMTFProcessorEntry 9 }

level1CacheIndexAtt10 OBJECT-TYPE
	SYNTAX		DmiInteger
	ACCESS		read-only
	STATUS		mandatory
	DESCRIPTION	"An index into the System Cache table that identifies the
entry that describes the L1 cache for this processor. If more than one processor
points to the same cache entry this means they share that cache."
	REFERENCE "'DMTF|Processor|006' 10"
	::= { dMTFProcessorEntry 10 }

level2CacheIndexAtt11 OBJECT-TYPE
	SYNTAX		DmiInteger
	ACCESS		read-only
	STATUS		mandatory
	DESCRIPTION	"An index into the System Cache table that identifies the
entry that describes the L2 cache for this processor If more than one processor
points to the same cache entry this means they share that cache."
	REFERENCE "'DMTF|Processor|006' 11"
	::= { dMTFProcessorEntry 11 }

level3CacheIndexAtt12 OBJECT-TYPE
	SYNTAX		DmiInteger
	ACCESS		read-only
	STATUS		mandatory
	DESCRIPTION	"An index into the System Cache table that identifies the
entry that describes the L3 cache for this processor. If more than one processor
points to the same cache entry this means they share that cache."
	REFERENCE "'DMTF|Processor|006' 12"
	::= { dMTFProcessorEntry 12 }

SdMTFSerialPorts ::= SEQUENCE { 
	dMTFSerialPortsState INTEGER,
	serialPortIndexAtt1	DmiInteger,
	serialBaseIOAddressAtt2	Dmi-Integer64,
	iRQUsedAtt3	DmiInteger,
	logicalNameAtt4	DmiDisplaystring,
	connectorTypeAtt5	DmiInteger,
	maximumSpeedAtt6	DmiInteger,
	serialPortCapabilitiesAtt7	DmiInteger,
	operationalGroupIndexAtt8-1	DmiInteger,
	serialPortSecuritySettingsAtt9	DmiInteger
}

dMTFSerialPortsTable OBJECT-TYPE
	SYNTAX		SEQUENCE OF SdMTFSerialPorts
	ACCESS		not-accessible
	STATUS		mandatory
	DESCRIPTION	"This group defines the attributes for serial ports in this
system."
	::= { dmtfSystemsMIF 11 }

dMTFSerialPortsEntry OBJECT-TYPE
	SYNTAX		SdMTFSerialPorts
	ACCESS		not-accessible
	STATUS		mandatory
	DESCRIPTION	"This group defines the attributes for serial ports in this
system."
	INDEX		{ DmiCompId,DmiGroupId, serialPortIndexAtt1 }
	::= { dMTFSerialPortsTable 1 }


dMTFSerialPortsState OBJECT-TYPE
	SYNTAX		INTEGER { 
		active(1),
		notInService(2),
		notReady(3),
		createAndGo(4),
		createAndWait(5),
		destroy(6)
	}
	ACCESS		read-write
	STATUS		mandatory
	REFERENCE "'DMTF|Serial Ports|003' 0"
	::= { dMTFSerialPortsEntry 0 }

serialPortIndexAtt1 OBJECT-TYPE
	SYNTAX		DmiInteger
	ACCESS		read-only
	STATUS		mandatory
	DESCRIPTION	"An index into the serial ports table."
	REFERENCE "'DMTF|Serial Ports|003' 1"
	::= { dMTFSerialPortsEntry 1 }

serialBaseIOAddressAtt2 OBJECT-TYPE
	SYNTAX		Dmi-Integer64
	ACCESS		read-only
	STATUS		mandatory
	DESCRIPTION	"Base I/O address for this serial port."
	REFERENCE "'DMTF|Serial Ports|003' 2"
	::= { dMTFSerialPortsEntry 2 }

iRQUsedAtt3 OBJECT-TYPE
	SYNTAX		DmiInteger
	ACCESS		read-only
	STATUS		mandatory
	DESCRIPTION	"IRQ number that is being used by this serial port."
	REFERENCE "'DMTF|Serial Ports|003' 3"
	::= { dMTFSerialPortsEntry 3 }

logicalNameAtt4 OBJECT-TYPE
	SYNTAX		DmiDisplaystring
	ACCESS		read-only
	STATUS		mandatory
	DESCRIPTION	"The logical name of this serial port under this operating
environment."
	REFERENCE "'DMTF|Serial Ports|003' 4"
	::= { dMTFSerialPortsEntry 4 }

connectorTypeAtt5 OBJECT-TYPE
	SYNTAX		INTEGER { 
		other(1),
		unknown(2),
		dB9PinMale(3),
		dB9PinFemale(4),
		dB25PinMale(5),
		dB25PinFemale(6),
		rJ11(7),
		rJ45(8),
		proprietary(9),
		circularDIN8Male(10),
		circularDIN8Female(11),
		miniCentronicsType14(160),
		miniCentronicsType26(161)
	}
	ACCESS		read-only
	STATUS		mandatory
	DESCRIPTION	"The connector used to interface with the I/O device on this
serial port."
	REFERENCE "'DMTF|Serial Ports|003' 5"
	::= { dMTFSerialPortsEntry 5 }

maximumSpeedAtt6 OBJECT-TYPE
	SYNTAX		DmiInteger
	ACCESS		read-only
	STATUS		mandatory
	DESCRIPTION	"Maximum transfer speed of the device on this serial port
in bits per second."
	REFERENCE "'DMTF|Serial Ports|003' 6"
	::= { dMTFSerialPortsEntry 6 }

serialPortCapabilitiesAtt7 OBJECT-TYPE
	SYNTAX		INTEGER { 
		other(1),
		unknown(2),
		xTATCompatible(3),
		x16450Compatible(4),
		x16550Compatible(5),
		x16550ACompatible(6),
		x8251Compatible(160),
		x8251FIFOCompatible(161)
	}
	ACCESS		read-only
	STATUS		mandatory
	DESCRIPTION	"The capabilities of this Serial port."
	REFERENCE "'DMTF|Serial Ports|003' 7"
	::= { dMTFSerialPortsEntry 7 }

operationalGroupIndexAtt8-1 OBJECT-TYPE
	SYNTAX		DmiInteger
	ACCESS		read-only
	STATUS		mandatory
	DESCRIPTION	"The index into the Operational State Table for this device."
	REFERENCE "'DMTF|Serial Ports|003' 8"
	::= { dMTFSerialPortsEntry 8 }

serialPortSecuritySettingsAtt9 OBJECT-TYPE
	SYNTAX		INTEGER { 
		other(1),
		unknown(2),
		none(3),
		externalInterfaceLockedOut(4),
		externalInterfaceEnabled(5),
		bootBypass(6)
	}
	ACCESS		read-only
	STATUS		mandatory
	DESCRIPTION	"Attribute describing the current hardware security settings
on this device"
	REFERENCE "'DMTF|Serial Ports|003' 9"
	::= { dMTFSerialPortsEntry 9 }

SdMTFSystemBIOS ::= SEQUENCE { 
	dMTFSystemBIOSState INTEGER,
	bIOSIndexAtt1	DmiInteger,
	bIOSManufacturerAtt2	DmiDisplaystring,
	bIOSVersionAtt3	DmiDisplaystring,
	bIOSROMSizeAtt4	DmiInteger,
	bIOSStartingAddressAtt5	Dmi-Integer64,
	bIOSEndingAddressAtt6	Dmi-Integer64,
	bIOSLoaderVersionAtt7	DmiDisplaystring,
	bIOSReleaseDateAtt8	Dmi-Date,
	primaryBIOSAtt9	DmiInteger
}

dMTFSystemBIOSTable OBJECT-TYPE
	SYNTAX		SEQUENCE OF SdMTFSystemBIOS
	ACCESS		not-accessible
	STATUS		mandatory
	DESCRIPTION	"This group defines the attributes for the System BIOS."
	::= { dmtfSystemsMIF 3 }

dMTFSystemBIOSEntry OBJECT-TYPE
	SYNTAX		SdMTFSystemBIOS
	ACCESS		not-accessible
	STATUS		mandatory
	DESCRIPTION	"This group defines the attributes for the System BIOS."
	INDEX		{ DmiCompId,DmiGroupId, bIOSIndexAtt1 }
	::= { dMTFSystemBIOSTable 1 }


dMTFSystemBIOSState OBJECT-TYPE
	SYNTAX		INTEGER { 
		active(1),
		notInService(2),
		notReady(3),
		createAndGo(4),
		createAndWait(5),
		destroy(6)
	}
	ACCESS		read-write
	STATUS		mandatory
	REFERENCE "'DMTF|System BIOS|001' 0"
	::= { dMTFSystemBIOSEntry 0 }

bIOSIndexAtt1 OBJECT-TYPE
	SYNTAX		DmiInteger
	ACCESS		read-only
	STATUS		mandatory
	DESCRIPTION	"The index into the system BIOS table."
	REFERENCE "'DMTF|System BIOS|001' 1"
	::= { dMTFSystemBIOSEntry 1 }

bIOSManufacturerAtt2 OBJECT-TYPE
	SYNTAX		DmiDisplaystring
	ACCESS		read-only
	STATUS		mandatory
	DESCRIPTION	"The name of the company that wrote this System BIOS."
	REFERENCE "'DMTF|System BIOS|001' 2"
	::= { dMTFSystemBIOSEntry 2 }

bIOSVersionAtt3 OBJECT-TYPE
	SYNTAX		DmiDisplaystring
	ACCESS		read-only
	STATUS		mandatory
	DESCRIPTION	"The version number or version string of this BIOS."
	REFERENCE "'DMTF|System BIOS|001' 3"
	::= { dMTFSystemBIOSEntry 3 }

bIOSROMSizeAtt4 OBJECT-TYPE
	SYNTAX		DmiInteger
	ACCESS		read-only
	STATUS		mandatory
	DESCRIPTION	"The physical size of this BIOS ROM device in kilobytes."
	REFERENCE "'DMTF|System BIOS|001' 4"
	::= { dMTFSystemBIOSEntry 4 }

bIOSStartingAddressAtt5 OBJECT-TYPE
	SYNTAX		Dmi-Integer64
	ACCESS		read-only
	STATUS		mandatory
	DESCRIPTION	"The starting physical address for the memory which the BIOS
occupies."
	REFERENCE "'DMTF|System BIOS|001' 5"
	::= { dMTFSystemBIOSEntry 5 }

bIOSEndingAddressAtt6 OBJECT-TYPE
	SYNTAX		Dmi-Integer64
	ACCESS		read-only
	STATUS		mandatory
	DESCRIPTION	"The ending physical address for the memory which the BIOS
occupies."
	REFERENCE "'DMTF|System BIOS|001' 6"
	::= { dMTFSystemBIOSEntry 6 }

bIOSLoaderVersionAtt7 OBJECT-TYPE
	SYNTAX		DmiDisplaystring
	ACCESS		read-only
	STATUS		mandatory
	DESCRIPTION	"The BIOS flash loader version number or string."
	REFERENCE "'DMTF|System BIOS|001' 7"
	::= { dMTFSystemBIOSEntry 7 }

bIOSReleaseDateAtt8 OBJECT-TYPE
	SYNTAX		Dmi-Date
	ACCESS		read-only
	STATUS		mandatory
	DESCRIPTION	"The BIOS release date."
	REFERENCE "'DMTF|System BIOS|001' 8"
	::= { dMTFSystemBIOSEntry 8 }

primaryBIOSAtt9 OBJECT-TYPE
	SYNTAX		INTEGER { 
		false(0),
		true(1)
	}
	ACCESS		read-only
	STATUS		mandatory
	DESCRIPTION	"If true, this is the primary System BIOS."
	REFERENCE "'DMTF|System BIOS|001' 9"
	::= { dMTFSystemBIOSEntry 9 }

SdMTFSystemCache ::= SEQUENCE { 
	dMTFSystemCacheState INTEGER,
	systemCacheIndexAtt1	DmiInteger,
	systemCacheLevelAtt2	DmiInteger,
	systemCacheSpeedAtt3	DmiInteger,
	systemCacheSizeAtt4	DmiInteger,
	systemCacheWritePolicyAtt5	DmiInteger,
	systemCacheErrorCorrectionAtt6	DmiInteger,
	fRUGroupIndexAtt7-1	DmiInteger,
	operationalGroupIndexAtt8-2	DmiInteger,
	systemCacheTypeAtt9	DmiInteger,
	lineSizeAtt10	DmiInteger,
	volatilityAtt11	DmiInteger,
	replacementPolicyAtt12	DmiInteger,
	readPolicyAtt13	DmiInteger,
	flushTimerAtt14	DmiInteger,
	associativityAtt15	DmiInteger
}

dMTFSystemCacheTable OBJECT-TYPE
	SYNTAX		SEQUENCE OF SdMTFSystemCache
	ACCESS		not-accessible
	STATUS		mandatory
	DESCRIPTION	"This group defines the attributes for different System Caches
installed in this system."
	::= { dmtfSystemsMIF 9 }

dMTFSystemCacheEntry OBJECT-TYPE
	SYNTAX		SdMTFSystemCache
	ACCESS		not-accessible
	STATUS		mandatory
	DESCRIPTION	"This group defines the attributes for different System Caches
installed in this system."
	INDEX		{ DmiCompId,DmiGroupId, systemCacheIndexAtt1 }
	::= { dMTFSystemCacheTable 1 }


dMTFSystemCacheState OBJECT-TYPE
	SYNTAX		INTEGER { 
		active(1),
		notInService(2),
		notReady(3),
		createAndGo(4),
		createAndWait(5),
		destroy(6)
	}
	ACCESS		read-write
	STATUS		mandatory
	REFERENCE "'DMTF|System Cache|003' 0"
	::= { dMTFSystemCacheEntry 0 }

systemCacheIndexAtt1 OBJECT-TYPE
	SYNTAX		DmiInteger
	ACCESS		read-only
	STATUS		mandatory
	DESCRIPTION	"An index into the System Cache table."
	REFERENCE "'DMTF|System Cache|003' 1"
	::= { dMTFSystemCacheEntry 1 }

systemCacheLevelAtt2 OBJECT-TYPE
	SYNTAX		INTEGER { 
		other(1),
		unknown(2),
		primary(3),
		secondary(4),
		tertiary(5)
	}
	ACCESS		read-only
	STATUS		mandatory
	DESCRIPTION	"Is this the primary System Cache, or a subsidiary cache?"
	REFERENCE "'DMTF|System Cache|003' 2"
	::= { dMTFSystemCacheEntry 2 }

systemCacheSpeedAtt3 OBJECT-TYPE
	SYNTAX		DmiInteger
	ACCESS		read-only
	STATUS		mandatory
	DESCRIPTION	"The speed of this System Cache module in nanoseconds."
	REFERENCE "'DMTF|System Cache|003' 3"
	::= { dMTFSystemCacheEntry 3 }

systemCacheSizeAtt4 OBJECT-TYPE
	SYNTAX		DmiInteger
	ACCESS		read-only
	STATUS		mandatory
	DESCRIPTION	"The size of this System Cache module in kilobytes."
	REFERENCE "'DMTF|System Cache|003' 4"
	::= { dMTFSystemCacheEntry 4 }

systemCacheWritePolicyAtt5 OBJECT-TYPE
	SYNTAX		INTEGER { 
		other(1),
		unknown(2),
		writeBack(3),
		writeThrough(4),
		variesWithAddress(5)
	}
	ACCESS		read-only
	STATUS		mandatory
	DESCRIPTION	"Is this a write-back or a write-through cache?"
	REFERENCE "'DMTF|System Cache|003' 5"
	::= { dMTFSystemCacheEntry 5 }

systemCacheErrorCorrectionAtt6 OBJECT-TYPE
	SYNTAX		INTEGER { 
		other(1),
		unknown(2),
		none(3),
		parity(4),
		singleBitECC(5),
		multiBitECC(6)
	}
	ACCESS		read-only
	STATUS		mandatory
	DESCRIPTION	"The error correction scheme supported by this cache component."
	REFERENCE "'DMTF|System Cache|003' 6"
	::= { dMTFSystemCacheEntry 6 }

fRUGroupIndexAtt7-1 OBJECT-TYPE
	SYNTAX		DmiInteger
	ACCESS		read-only
	STATUS		mandatory
	DESCRIPTION	"If this is a Field Replaceable Unit or if it is part of another
FRU, this provides an index into the FRU table; 'value = -1' indicates that
the group is not a FRU."
	REFERENCE "'DMTF|System Cache|003' 7"
	::= { dMTFSystemCacheEntry 7 }

operationalGroupIndexAtt8-2 OBJECT-TYPE
	SYNTAX		DmiInteger
	ACCESS		read-only
	STATUS		mandatory
	DESCRIPTION	"The index into the Operational State Table for this device."
	REFERENCE "'DMTF|System Cache|003' 8"
	::= { dMTFSystemCacheEntry 8 }

systemCacheTypeAtt9 OBJECT-TYPE
	SYNTAX		INTEGER { 
		other(1),
		unknown(2),
		instruction(3),
		data(4),
		unified(5)
	}
	ACCESS		read-only
	STATUS		mandatory
	DESCRIPTION	"This defines the system cache type."
	REFERENCE "'DMTF|System Cache|003' 9"
	::= { dMTFSystemCacheEntry 9 }

lineSizeAtt10 OBJECT-TYPE
	SYNTAX		DmiInteger
	ACCESS		read-only
	STATUS		mandatory
	DESCRIPTION	"The size, in bytes, of a single cache bucket or line."
	REFERENCE "'DMTF|System Cache|003' 10"
	::= { dMTFSystemCacheEntry 10 }

volatilityAtt11 OBJECT-TYPE
	SYNTAX		INTEGER { 
		other(1),
		unknown(2),
		temporaryVolatile(3),
		volatile(4),
		permanentNonVolatile(5),
		temporaryNonVolatile(6),
		uPSNonVolatile(7)
	}
	ACCESS		read-only
	STATUS		mandatory
	DESCRIPTION	"This defines the volatility of the cache."
	REFERENCE "'DMTF|System Cache|003' 11"
	::= { dMTFSystemCacheEntry 11 }

replacementPolicyAtt12 OBJECT-TYPE
	SYNTAX		INTEGER { 
		other(1),
		unknown(2),
		leastRecentlyUsedLRU(3),
		firstInFirstOutFIFO(4),
		lastInFirstOutLIFO(5),
		leastFrequentlyUsedLFU(6),
		mostFrequentlyUsedMFU(7)
	}
	ACCESS		read-only
	STATUS		mandatory
	DESCRIPTION	"The algorithm used by the cache to determine which cache
lines or buckets should be re-used."
	REFERENCE "'DMTF|System Cache|003' 12"
	::= { dMTFSystemCacheEntry 12 }

readPolicyAtt13 OBJECT-TYPE
	SYNTAX		INTEGER { 
		other(1),
		unknown(2),
		read(3),
		readAhead(4),
		readAndReadAhead(5)
	}
	ACCESS		read-only
	STATUS		mandatory
	DESCRIPTION	"The policy that shall be employed by the cache for handling
read requests."
	REFERENCE "'DMTF|System Cache|003' 13"
	::= { dMTFSystemCacheEntry 13 }

flushTimerAtt14 OBJECT-TYPE
	SYNTAX		DmiInteger
	ACCESS		read-only
	STATUS		mandatory
	DESCRIPTION	"The maximum amount of time, in seconds, dirty lines or buckets
may remain in the cache before they are flushed. A value of zero indicated
that a cache flush is not controlled by a flushing timer."
	REFERENCE "'DMTF|System Cache|003' 14"
	::= { dMTFSystemCacheEntry 14 }

associativityAtt15 OBJECT-TYPE
	SYNTAX		INTEGER { 
		other(1),
		unknown(2),
		directMapped(3),
		x2WaySetAssociative(4),
		x4WaySetAssociative(5),
		fullyAssociative(6)
	}
	ACCESS		read-only
	STATUS		mandatory
	DESCRIPTION	"This defines the system cache associativity (direct-mapped,
2-way, 4-way, etc)."
	REFERENCE "'DMTF|System Cache|003' 15"
	::= { dMTFSystemCacheEntry 15 }

SdMTFSystemHardwareSecurity ::= SEQUENCE { 
	powerOnPasswordStatusAtt1	DmiInteger,
	keyboardPasswordStatusAtt2	DmiInteger,
	administratorPasswordStatisAtt3	DmiInteger,
	frontPanelResetStatusAtt4	DmiInteger
}

dMTFSystemHardwareSecurityTable OBJECT-TYPE
	SYNTAX		SEQUENCE OF SdMTFSystemHardwareSecurity
	ACCESS		not-accessible
	STATUS		mandatory
	DESCRIPTION	"This group describes the system-wide hardware security settings."
	::= { dmtfSystemsMIF 49 }

dMTFSystemHardwareSecurityEntry OBJECT-TYPE
	SYNTAX		SdMTFSystemHardwareSecurity
	ACCESS		not-accessible
	STATUS		mandatory
	DESCRIPTION	"This group describes the system-wide hardware security settings."
	INDEX		{ DmiCompId,DmiGroupId }
	::= { dMTFSystemHardwareSecurityTable 1 }


powerOnPasswordStatusAtt1 OBJECT-TYPE
	SYNTAX		INTEGER { 
		other(1),
		unknown(2),
		disabled(3),
		enabled(4),
		notImplemented(5)
	}
	ACCESS		read-only
	STATUS		mandatory
	DESCRIPTION	"The current power-on password setting on the system."
	REFERENCE "'DMTF|System Hardware Security|001' 1"
	::= { dMTFSystemHardwareSecurityEntry 1 }

keyboardPasswordStatusAtt2 OBJECT-TYPE
	SYNTAX		INTEGER { 
		other(1),
		unknown(2),
		disabled(3),
		enabled(4),
		notImplemented(5)
	}
	ACCESS		read-only
	STATUS		mandatory
	DESCRIPTION	"The current keyboard password setting on the system"
	REFERENCE "'DMTF|System Hardware Security|001' 2"
	::= { dMTFSystemHardwareSecurityEntry 2 }

administratorPasswordStatisAtt3 OBJECT-TYPE
	SYNTAX		INTEGER { 
		other(1),
		unknown(2),
		disabled(3),
		enabled(4),
		notImplemented(5)
	}
	ACCESS		read-only
	STATUS		mandatory
	DESCRIPTION	"The current administrator password setting on the system.
This password is required to make hardware configuration changes to the system."
	REFERENCE "'DMTF|System Hardware Security|001' 3"
	::= { dMTFSystemHardwareSecurityEntry 3 }

frontPanelResetStatusAtt4 OBJECT-TYPE
	SYNTAX		INTEGER { 
		other(1),
		unknown(2),
		disabled(3),
		enabled(4),
		notImplemented(5)
	}
	ACCESS		read-only
	STATUS		mandatory
	DESCRIPTION	"The present status of the front panel reset button capability.
If Enabled, the machine can be reset via the front panel reset button. If
Disabled, the reset button, if available, is inoperative."
	REFERENCE "'DMTF|System Hardware Security|001' 4"
	::= { dMTFSystemHardwareSecurityEntry 4 }

SdMTFSystemPowerControls ::= SEQUENCE { 
	powerControlRequestAtt1	DmiInteger,
	timedPowerOnAvailableAtt2	DmiInteger,
	timeToNextScheduledPowerOnAtt3	DmiInteger
}

dMTFSystemPowerControlsTable OBJECT-TYPE
	SYNTAX		SEQUENCE OF SdMTFSystemPowerControls
	ACCESS		not-accessible
	STATUS		mandatory
	DESCRIPTION	"This group defines attributes for controlling the main power
supply to the system."
	::= { dmtfSystemsMIF 51 }

dMTFSystemPowerControlsEntry OBJECT-TYPE
	SYNTAX		SdMTFSystemPowerControls
	ACCESS		not-accessible
	STATUS		mandatory
	DESCRIPTION	"This group defines attributes for controlling the main power
supply to the system."
	INDEX		{ DmiCompId,DmiGroupId }
	::= { dMTFSystemPowerControlsTable 1 }


powerControlRequestAtt1 OBJECT-TYPE
	SYNTAX		INTEGER { 
		other(1),
		unknown(2),
		powerOff(3),
		powerOffThenOnAgain(4),
		enterStandbyMode(5),
		enterSuspendMode(6),
		enterHibernationMode(7)
	}
	ACCESS		read-write
	STATUS		mandatory
	DESCRIPTION	"Reading the value of this attribute gives the value of the
last valid power control request that was written into it. Writing a valid
value into it causes the appropriate power control action to be executed
immediately. Writing an invalid or unimplemented value causes no change."
	REFERENCE "'DMTF|System Power Controls|001' 1"
	::= { dMTFSystemPowerControlsEntry 1 }

timedPowerOnAvailableAtt2 OBJECT-TYPE
	SYNTAX		INTEGER { 
		false(0),
		true(1),
		unknown(2)
	}
	ACCESS		read-only
	STATUS		mandatory
	DESCRIPTION	"Defines whether a timed power-on facility is available."
	REFERENCE "'DMTF|System Power Controls|001' 2"
	::= { dMTFSystemPowerControlsEntry 2 }

timeToNextScheduledPowerOnAtt3 OBJECT-TYPE
	SYNTAX		DmiInteger
	ACCESS		read-write
	STATUS		mandatory
	DESCRIPTION	"The number of seconds until the next timed power-on is scheduled
to occur. A value of 0 means that if the system is powered off, no automatic
timed poweron will occur. A value of 0x80000000 denotes 'unknown'."
	REFERENCE "'DMTF|System Power Controls|001' 3"
	::= { dMTFSystemPowerControlsEntry 3 }

SdMTFSystemResourceDMAInfo ::= SEQUENCE { 
	dMTFSystemResourceDMAInfoState INTEGER,
	systemResourceDMAInfoIndexAtt1	DmiInteger,
	dMATransferWidthAtt2	DmiInteger,
	dMAAddressSizeAtt3	DmiInteger,
	dMAMaximumTransferSizeAtt4	DmiInteger,
	dMATransferPreferenceAtt5	DmiInteger,
	busMasterAtt6	DmiInteger,
	byteModeAtt7	DmiInteger,
	wordModeAtt8	DmiInteger,
	channelTimingAtt9	DmiInteger,
	typeCTimingAtt10	DmiInteger
}

dMTFSystemResourceDMAInfoTable OBJECT-TYPE
	SYNTAX		SEQUENCE OF SdMTFSystemResourceDMAInfo
	ACCESS		not-accessible
	STATUS		mandatory
	DESCRIPTION	"This group presents additional information about DMA resources
that have been defined in the System Resources table."
	::= { dmtfSystemsMIF 42 }

dMTFSystemResourceDMAInfoEntry OBJECT-TYPE
	SYNTAX		SdMTFSystemResourceDMAInfo
	ACCESS		not-accessible
	STATUS		mandatory
	DESCRIPTION	"This group presents additional information about DMA resources
that have been defined in the System Resources table."
	INDEX		{ DmiCompId,DmiGroupId, systemResourceDMAInfoIndexAtt1 }
	::= { dMTFSystemResourceDMAInfoTable 1 }


dMTFSystemResourceDMAInfoState OBJECT-TYPE
	SYNTAX		INTEGER { 
		active(1),
		notInService(2),
		notReady(3),
		createAndGo(4),
		createAndWait(5),
		destroy(6)
	}
	ACCESS		read-write
	STATUS		mandatory
	REFERENCE "'DMTF|System Resource DMA Info|001' 0"
	::= { dMTFSystemResourceDMAInfoEntry 0 }

systemResourceDMAInfoIndexAtt1 OBJECT-TYPE
	SYNTAX		DmiInteger
	ACCESS		read-only
	STATUS		mandatory
	DESCRIPTION	"A number the uniquely identifies rows in this table."
	REFERENCE "'DMTF|System Resource DMA Info|001' 1"
	::= { dMTFSystemResourceDMAInfoEntry 1 }

dMATransferWidthAtt2 OBJECT-TYPE
	SYNTAX		INTEGER { 
		other(1),
		unknown(2),
		x8Bit(3),
		x8And16Bit(4),
		x16Bit(5),
		x32Bit(6),
		x64Bit(7),
		x128Bit(8)
	}
	ACCESS		read-only
	STATUS		mandatory
	DESCRIPTION	"Width of DMA transfers supported"
	REFERENCE "'DMTF|System Resource DMA Info|001' 2"
	::= { dMTFSystemResourceDMAInfoEntry 2 }

dMAAddressSizeAtt3 OBJECT-TYPE
	SYNTAX		INTEGER { 
		other(1),
		unknown(2),
		x8Bit(3),
		x16Bit(5),
		x32Bit(6),
		x64Bit(7)
	}
	ACCESS		read-only
	STATUS		mandatory
	DESCRIPTION	"The width of the DMA address."
	REFERENCE "'DMTF|System Resource DMA Info|001' 3"
	::= { dMTFSystemResourceDMAInfoEntry 3 }

dMAMaximumTransferSizeAtt4 OBJECT-TYPE
	SYNTAX		DmiInteger
	ACCESS		read-only
	STATUS		mandatory
	DESCRIPTION	"The maximum number of bytes that can be transferred by this
DMA Channel."
	REFERENCE "'DMTF|System Resource DMA Info|001' 4"
	::= { dMTFSystemResourceDMAInfoEntry 4 }

dMATransferPreferenceAtt5 OBJECT-TYPE
	SYNTAX		INTEGER { 
		other(1),
		unknown(2),
		x8Bit(3),
		x8And16Bit(4),
		x16Bit(5),
		x32Bit(6),
		x64Bit(7)
	}
	ACCESS		read-only
	STATUS		mandatory
	DESCRIPTION	"DMA transfer type preference."
	REFERENCE "'DMTF|System Resource DMA Info|001' 5"
	::= { dMTFSystemResourceDMAInfoEntry 5 }

busMasterAtt6 OBJECT-TYPE
	SYNTAX		INTEGER { 
		other(1),
		unknown(2),
		logicalDeviceIsNotABusMaster(3),
		logicalDeviceIsABusMaster(4)
	}
	ACCESS		read-only
	STATUS		mandatory
	DESCRIPTION	"Indicates whether the device is using DMA is a bus master."
	REFERENCE "'DMTF|System Resource DMA Info|001' 6"
	::= { dMTFSystemResourceDMAInfoEntry 6 }

byteModeAtt7 OBJECT-TYPE
	SYNTAX		INTEGER { 
		other(1),
		unknown(2),
		dMAMayNotExecuteInCountByByteMode(3),
		dMAMayExecuteInCountByByteMode(4)
	}
	ACCESS		read-only
	STATUS		mandatory
	DESCRIPTION	"Indicates whether DMA may execute in 'count by byte' mode."
	REFERENCE "'DMTF|System Resource DMA Info|001' 7"
	::= { dMTFSystemResourceDMAInfoEntry 7 }

wordModeAtt8 OBJECT-TYPE
	SYNTAX		INTEGER { 
		other(1),
		unknown(2),
		dMAMayNotExecuteInCountByWordMode(3),
		dMAMayExecuteInCountByWordMode(4)
	}
	ACCESS		read-only
	STATUS		mandatory
	DESCRIPTION	"Indicates whether DMA may execute in 'count by word' mode."
	REFERENCE "'DMTF|System Resource DMA Info|001' 8"
	::= { dMTFSystemResourceDMAInfoEntry 8 }

channelTimingAtt9 OBJECT-TYPE
	SYNTAX		INTEGER { 
		other(1),
		unknown(2),
		iSACompatible(3),
		typeA(4),
		typeB(5),
		typeF(6)
	}
	ACCESS		read-only
	STATUS		mandatory
	DESCRIPTION	"DMA channel speed support."
	REFERENCE "'DMTF|System Resource DMA Info|001' 9"
	::= { dMTFSystemResourceDMAInfoEntry 9 }

typeCTimingAtt10 OBJECT-TYPE
	SYNTAX		INTEGER { 
		other(1),
		unknown(2),
		iSACompatible(3),
		cTypeTimingIsNotSupported(4),
		cTypeTimingIsSupported(5)
	}
	ACCESS		read-only
	STATUS		mandatory
	DESCRIPTION	"Indicates whether C type (burst) timing is supported."
	REFERENCE "'DMTF|System Resource DMA Info|001' 10"
	::= { dMTFSystemResourceDMAInfoEntry 10 }

SdMTFSystemResourceDeviceInfo ::= SEQUENCE { 
	dMTFSystemResourceDeviceInfoState INTEGER,
	resourceUserAtt1	DmiInteger,
	deviceIDAtt2	DmiInteger,
	deviceSerialNumberAtt3	DmiInteger,
	logicalDeviceIDClassCodeAtt4	DmiInteger,
	deviceFlagsAtt5	DmiInteger,
	deviceNumberAtt6	DmiInteger,
	functionNumberAtt7	DmiInteger,
	busTypeAtt8	DmiInteger,
	cMReservedAtt9	DmiInteger
}

dMTFSystemResourceDeviceInfoTable OBJECT-TYPE
	SYNTAX		SEQUENCE OF SdMTFSystemResourceDeviceInfo
	ACCESS		not-accessible
	STATUS		mandatory
	DESCRIPTION	"This group describes the base level of Memory, I/O, DMA,
and INT (interrupt) resources that are used by a device in the system."
	::= { dmtfSystemsMIF 38 }

dMTFSystemResourceDeviceInfoEntry OBJECT-TYPE
	SYNTAX		SdMTFSystemResourceDeviceInfo
	ACCESS		not-accessible
	STATUS		mandatory
	DESCRIPTION	"This group describes the base level of Memory, I/O, DMA,
and INT (interrupt) resources that are used by a device in the system."
	INDEX		{ DmiCompId,DmiGroupId, resourceUserAtt1 }
	::= { dMTFSystemResourceDeviceInfoTable 1 }


dMTFSystemResourceDeviceInfoState OBJECT-TYPE
	SYNTAX		INTEGER { 
		active(1),
		notInService(2),
		notReady(3),
		createAndGo(4),
		createAndWait(5),
		destroy(6)
	}
	ACCESS		read-write
	STATUS		mandatory
	REFERENCE "'DMTF|System Resource Device Info|001' 0"
	::= { dMTFSystemResourceDeviceInfoEntry 0 }

resourceUserAtt1 OBJECT-TYPE
	SYNTAX		DmiInteger
	ACCESS		read-only
	STATUS		mandatory
	DESCRIPTION	"A number that uniquely identifies this device. This number
may be derived from the 'device number' that is assigned by 'Plug N Play',
or may be uniquely assigned by the component instrumentation."
	REFERENCE "'DMTF|System Resource Device Info|001' 1"
	::= { dMTFSystemResourceDeviceInfoEntry 1 }

deviceIDAtt2 OBJECT-TYPE
	SYNTAX		DmiInteger
	ACCESS		read-only
	STATUS		mandatory
	DESCRIPTION	"Physical Device ID from Config manager info. Equal to the
CISTPL-MANFID field for PCMCIA devices. 0xFFFFFFFF = Unknown"
	REFERENCE "'DMTF|System Resource Device Info|001' 2"
	::= { dMTFSystemResourceDeviceInfoEntry 2 }

deviceSerialNumberAtt3 OBJECT-TYPE
	SYNTAX		DmiInteger
	ACCESS		read-only
	STATUS		mandatory
	DESCRIPTION	"Device Serial Number from Config manager info. 0 = Undefined"
	REFERENCE "'DMTF|System Resource Device Info|001' 3"
	::= { dMTFSystemResourceDeviceInfoEntry 3 }

logicalDeviceIDClassCodeAtt4 OBJECT-TYPE
	SYNTAX		DmiInteger
	ACCESS		read-only
	STATUS		mandatory
	DESCRIPTION	"Logical device ID for PnP ISA devices, Class code for PCI
devices, CISTPL-FUNCID for PCMCIA devices. 0xFFFFFFFF = Undefined, 0 = reserved"
	REFERENCE "'DMTF|System Resource Device Info|001' 4"
	::= { dMTFSystemResourceDeviceInfoEntry 4 }

deviceFlagsAtt5 OBJECT-TYPE
	SYNTAX		DmiInteger
	ACCESS		read-only
	STATUS		mandatory
	DESCRIPTION	"Device flags from config manager info. Bit 0: 1 = device
has been initialized, 
 Bit 1: 1 = device is enabled, 
 Bit 2: 1 = device
config has been locked, 
 Bit 3: 1 = device has temporary config resources
assigned, 
 Bit 4: 1 = device is reconfigurable"
	REFERENCE "'DMTF|System Resource Device Info|001' 5"
	::= { dMTFSystemResourceDeviceInfoEntry 5 }

deviceNumberAtt6 OBJECT-TYPE
	SYNTAX		DmiInteger
	ACCESS		read-only
	STATUS		mandatory
	DESCRIPTION	"Device Number for PCI Devices, Logical Device number for
PnP Devices. 0 otherwise."
	REFERENCE "'DMTF|System Resource Device Info|001' 6"
	::= { dMTFSystemResourceDeviceInfoEntry 6 }

functionNumberAtt7 OBJECT-TYPE
	SYNTAX		DmiInteger
	ACCESS		read-only
	STATUS		mandatory
	DESCRIPTION	"Function Number for PCI & EISA Devices. 0 otherwise."
	REFERENCE "'DMTF|System Resource Device Info|001' 7"
	::= { dMTFSystemResourceDeviceInfoEntry 7 }

busTypeAtt8 OBJECT-TYPE
	SYNTAX		DmiInteger
	ACCESS		read-only
	STATUS		mandatory
	DESCRIPTION	"Bus number (0-255) for PCI Devices, Slot number for EISA
and PnP Devices, Card logical socket number for PCMCIA devices. Zero otherwise."
	REFERENCE "'DMTF|System Resource Device Info|001' 8"
	::= { dMTFSystemResourceDeviceInfoEntry 8 }

cMReservedAtt9 OBJECT-TYPE
	SYNTAX		DmiInteger
	ACCESS		read-only
	STATUS		mandatory
	DESCRIPTION	"Data from the Reserved field of the Configuration Manager
bus access structure, or 0."
	REFERENCE "'DMTF|System Resource Device Info|001' 9"
	::= { dMTFSystemResourceDeviceInfoEntry 9 }

SdMTFSystemResourceIOInfo ::= SEQUENCE { 
	dMTFSystemResourceIOInfoState INTEGER,
	systemResourceIOInfoIndexAtt1	DmiInteger,
	iODecodeAtt2	DmiInteger
}

dMTFSystemResourceIOInfoTable OBJECT-TYPE
	SYNTAX		SEQUENCE OF SdMTFSystemResourceIOInfo
	ACCESS		not-accessible
	STATUS		mandatory
	DESCRIPTION	"This group presents additional information about I/O resources
that have been defined in the System Resources table."
	::= { dmtfSystemsMIF 40 }

dMTFSystemResourceIOInfoEntry OBJECT-TYPE
	SYNTAX		SdMTFSystemResourceIOInfo
	ACCESS		not-accessible
	STATUS		mandatory
	DESCRIPTION	"This group presents additional information about I/O resources
that have been defined in the System Resources table."
	INDEX		{ DmiCompId,DmiGroupId, systemResourceIOInfoIndexAtt1 }
	::= { dMTFSystemResourceIOInfoTable 1 }


dMTFSystemResourceIOInfoState OBJECT-TYPE
	SYNTAX		INTEGER { 
		active(1),
		notInService(2),
		notReady(3),
		createAndGo(4),
		createAndWait(5),
		destroy(6)
	}
	ACCESS		read-write
	STATUS		mandatory
	REFERENCE "'DMTF|System Resource I/O Info|001' 0"
	::= { dMTFSystemResourceIOInfoEntry 0 }

systemResourceIOInfoIndexAtt1 OBJECT-TYPE
	SYNTAX		DmiInteger
	ACCESS		read-only
	STATUS		mandatory
	DESCRIPTION	"A number the uniquely identifies rows in this table."
	REFERENCE "'DMTF|System Resource I/O Info|001' 1"
	::= { dMTFSystemResourceIOInfoEntry 1 }

iODecodeAtt2 OBJECT-TYPE
	SYNTAX		INTEGER { 
		other(1),
		unknown(2),
		x10Bits(3),
		x16Bits(4)
	}
	ACCESS		read-only
	STATUS		mandatory
	DESCRIPTION	"Number of bits used for I/O decode"
	REFERENCE "'DMTF|System Resource I/O Info|001' 2"
	::= { dMTFSystemResourceIOInfoEntry 2 }

SdMTFSystemResourceIRQInfo ::= SEQUENCE { 
	dMTFSystemResourceIRQInfoState INTEGER,
	systemResourceIRQInfoIndexAtt1	DmiInteger,
	triggerTypeAtt2	DmiInteger,
	triggerLevelAtt3	DmiInteger
}

dMTFSystemResourceIRQInfoTable OBJECT-TYPE
	SYNTAX		SEQUENCE OF SdMTFSystemResourceIRQInfo
	ACCESS		not-accessible
	STATUS		mandatory
	DESCRIPTION	"This group presents additional information about I/O resources
that have been defined in the System Resources table."
	::= { dmtfSystemsMIF 41 }

dMTFSystemResourceIRQInfoEntry OBJECT-TYPE
	SYNTAX		SdMTFSystemResourceIRQInfo
	ACCESS		not-accessible
	STATUS		mandatory
	DESCRIPTION	"This group presents additional information about I/O resources
that have been defined in the System Resources table."
	INDEX		{ DmiCompId,DmiGroupId, systemResourceIRQInfoIndexAtt1 }
	::= { dMTFSystemResourceIRQInfoTable 1 }


dMTFSystemResourceIRQInfoState OBJECT-TYPE
	SYNTAX		INTEGER { 
		active(1),
		notInService(2),
		notReady(3),
		createAndGo(4),
		createAndWait(5),
		destroy(6)
	}
	ACCESS		read-write
	STATUS		mandatory
	REFERENCE "'DMTF|System Resource IRQ Info|001' 0"
	::= { dMTFSystemResourceIRQInfoEntry 0 }

systemResourceIRQInfoIndexAtt1 OBJECT-TYPE
	SYNTAX		DmiInteger
	ACCESS		read-only
	STATUS		mandatory
	DESCRIPTION	"A number the uniquely identifies rows in this table."
	REFERENCE "'DMTF|System Resource IRQ Info|001' 1"
	::= { dMTFSystemResourceIRQInfoEntry 1 }

triggerTypeAtt2 OBJECT-TYPE
	SYNTAX		INTEGER { 
		other(1),
		unknown(2),
		level(3),
		edge(4)
	}
	ACCESS		read-only
	STATUS		mandatory
	DESCRIPTION	"The trigger type for this interrupt."
	REFERENCE "'DMTF|System Resource IRQ Info|001' 2"
	::= { dMTFSystemResourceIRQInfoEntry 2 }

triggerLevelAtt3 OBJECT-TYPE
	SYNTAX		INTEGER { 
		other(1),
		unknown(2),
		activeLow(3),
		activeHigh(4)
	}
	ACCESS		read-only
	STATUS		mandatory
	DESCRIPTION	"The trigger level for this interrupt."
	REFERENCE "'DMTF|System Resource IRQ Info|001' 3"
	::= { dMTFSystemResourceIRQInfoEntry 3 }

SdMTFSystemResourceMemoryInfo ::= SEQUENCE { 
	dMTFSystemResourceMemoryInfoState INTEGER,
	systemResourceMemoryInfoIndexAtt1	DmiInteger,
	iSAPCMCIARangeDescriptorAtt2	DmiInteger,
	eISARangeDescriptorAtt3	DmiInteger,
	decodeSupportAtt4	DmiInteger,
	cacheableAtt5	DmiInteger,
	cacheTypeAtt6	DmiInteger,
	readWriteAtt7	DmiInteger
}

dMTFSystemResourceMemoryInfoTable OBJECT-TYPE
	SYNTAX		SEQUENCE OF SdMTFSystemResourceMemoryInfo
	ACCESS		not-accessible
	STATUS		mandatory
	DESCRIPTION	"This group presents additional information about memory resource
 that have been defined in the System Resources table."
	::= { dmtfSystemsMIF 39 }

dMTFSystemResourceMemoryInfoEntry OBJECT-TYPE
	SYNTAX		SdMTFSystemResourceMemoryInfo
	ACCESS		not-accessible
	STATUS		mandatory
	DESCRIPTION	"This group presents additional information about memory resource
 that have been defined in the System Resources table."
	INDEX		{ DmiCompId,DmiGroupId, systemResourceMemoryInfoIndexAtt1 }
	::= { dMTFSystemResourceMemoryInfoTable 1 }


dMTFSystemResourceMemoryInfoState OBJECT-TYPE
	SYNTAX		INTEGER { 
		active(1),
		notInService(2),
		notReady(3),
		createAndGo(4),
		createAndWait(5),
		destroy(6)
	}
	ACCESS		read-write
	STATUS		mandatory
	REFERENCE "'DMTF|System Resource Memory Info|001' 0"
	::= { dMTFSystemResourceMemoryInfoEntry 0 }

systemResourceMemoryInfoIndexAtt1 OBJECT-TYPE
	SYNTAX		DmiInteger
	ACCESS		read-only
	STATUS		mandatory
	DESCRIPTION	"A number the uniquely identifies rows in this table."
	REFERENCE "'DMTF|System Resource Memory Info|001' 1"
	::= { dMTFSystemResourceMemoryInfoEntry 1 }

iSAPCMCIARangeDescriptorAtt2 OBJECT-TYPE
	SYNTAX		INTEGER { 
		other(1),
		unknown(2),
		x8BitMemoryOnly(3),
		x16BitMemoryOnly(4),
		x8And16BitMemorySupported(5),
		x32BitMemoryOnly(6)
	}
	ACCESS		read-only
	STATUS		mandatory
	DESCRIPTION	"For PnP ISA/PCMCIA memory range descriptor compatibility."
	REFERENCE "'DMTF|System Resource Memory Info|001' 2"
	::= { dMTFSystemResourceMemoryInfoEntry 2 }

eISARangeDescriptorAtt3 OBJECT-TYPE
	SYNTAX		INTEGER { 
		other(1),
		unknown(2),
		x8BitMemoryOnly(3),
		x16BitMemoryOnly(4),
		x8And16BitMemorySupported(5),
		x32BitMemoryOnly(6)
	}
	ACCESS		read-only
	STATUS		mandatory
	DESCRIPTION	"For PnP EISA memory range descriptor compatibility."
	REFERENCE "'DMTF|System Resource Memory Info|001' 3"
	::= { dMTFSystemResourceMemoryInfoEntry 3 }

decodeSupportAtt4 OBJECT-TYPE
	SYNTAX		INTEGER { 
		other(1),
		unknown(2),
		decodeSupportsHighAddress(3),
		decodeSupportsRangeLength(4)
	}
	ACCESS		read-only
	STATUS		mandatory
	DESCRIPTION	"For PnP memory range descriptor compatibility."
	REFERENCE "'DMTF|System Resource Memory Info|001' 4"
	::= { dMTFSystemResourceMemoryInfoEntry 4 }

cacheableAtt5 OBJECT-TYPE
	SYNTAX		INTEGER { 
		false(0),
		true(1),
		unknown(2)
	}
	ACCESS		read-only
	STATUS		mandatory
	DESCRIPTION	"Indicates whether it is allowable for this memory range to
be cached or not."
	REFERENCE "'DMTF|System Resource Memory Info|001' 5"
	::= { dMTFSystemResourceMemoryInfoEntry 5 }

cacheTypeAtt6 OBJECT-TYPE
	SYNTAX		INTEGER { 
		other(1),
		unknown(2),
		writeBack-1(3),
		writeThrough-1(4)
	}
	ACCESS		read-only
	STATUS		mandatory
	DESCRIPTION	"Indicates Cache Type that is compatible with this resource."
	REFERENCE "'DMTF|System Resource Memory Info|001' 6"
	::= { dMTFSystemResourceMemoryInfoEntry 6 }

readWriteAtt7 OBJECT-TYPE
	SYNTAX		INTEGER { 
		other(1),
		unknown(2),
		rOMReadOnly(3),
		rAMReadwrite(4)
	}
	ACCESS		read-only
	STATUS		mandatory
	DESCRIPTION	"Indicates the read-write accessibility of this memory resource."
	REFERENCE "'DMTF|System Resource Memory Info|001' 7"
	::= { dMTFSystemResourceMemoryInfoEntry 7 }

SdMTFSystemResources2 ::= SEQUENCE { 
	dMTFSystemResources2State INTEGER,
	systemResourcesIndexAtt1	DmiInteger,
	resourceUserAtt2	DmiInteger,
	resourceSetAtt3	DmiInteger,
	resourceAssignmentAtt4	DmiInteger,
	resourceTypeAtt5	DmiInteger,
	resourceNumberAtt6	DmiInteger,
	resourceInfoIDAtt7	DmiInteger,
	startAddressAtt8	Dmi-Integer64,
	endAddressAtt9	Dmi-Integer64,
	resourceSizeAtt10	DmiInteger,
	baseAlignmentAtt11	DmiInteger,
	shareableAtt12	DmiInteger,
	sharedAtt13	DmiInteger
}

dMTFSystemResources2Table OBJECT-TYPE
	SYNTAX		SEQUENCE OF SdMTFSystemResources2
	ACCESS		not-accessible
	STATUS		mandatory
	DESCRIPTION	"This group describes the base level of Memory, I/O, DMA,
and INT (interrupt) resources that are used by a device in the system."
	::= { dmtfSystemsMIF 37 }

dMTFSystemResources2Entry OBJECT-TYPE
	SYNTAX		SdMTFSystemResources2
	ACCESS		not-accessible
	STATUS		mandatory
	DESCRIPTION	"This group describes the base level of Memory, I/O, DMA,
and INT (interrupt) resources that are used by a device in the system."
	INDEX		{ DmiCompId,DmiGroupId, systemResourcesIndexAtt1 }
	::= { dMTFSystemResources2Table 1 }


dMTFSystemResources2State OBJECT-TYPE
	SYNTAX		INTEGER { 
		active(1),
		notInService(2),
		notReady(3),
		createAndGo(4),
		createAndWait(5),
		destroy(6)
	}
	ACCESS		read-write
	STATUS		mandatory
	REFERENCE "'DMTF|System Resources 2|001' 0"
	::= { dMTFSystemResources2Entry 0 }

systemResourcesIndexAtt1 OBJECT-TYPE
	SYNTAX		DmiInteger
	ACCESS		read-only
	STATUS		mandatory
	DESCRIPTION	"A number that uniquely identifies the rows in this table."
	REFERENCE "'DMTF|System Resources 2|001' 1"
	::= { dMTFSystemResources2Entry 1 }

resourceUserAtt2 OBJECT-TYPE
	SYNTAX		DmiInteger
	ACCESS		read-only
	STATUS		mandatory
	DESCRIPTION	"A unique number for each different 'resource user' that has
resources specified in this table."
	REFERENCE "'DMTF|System Resources 2|001' 2"
	::= { dMTFSystemResources2Entry 2 }

resourceSetAtt3 OBJECT-TYPE
	SYNTAX		DmiInteger
	ACCESS		read-only
	STATUS		mandatory
	DESCRIPTION	"A number used as the ID of a set of Memory, I/O, DMA and/or
INT resources for the resource user."
	REFERENCE "'DMTF|System Resources 2|001' 3"
	::= { dMTFSystemResources2Entry 3 }

resourceAssignmentAtt4 OBJECT-TYPE
	SYNTAX		INTEGER { 
		other(1),
		unknown(2),
		allocated(3),
		assignable(4),
		temporaryAssignment(5)
	}
	ACCESS		read-only
	STATUS		mandatory
	DESCRIPTION	"Describes the state of the assignment of this set of resources.
(Note: This value must be the same for all resources within a given set.)"
	REFERENCE "'DMTF|System Resources 2|001' 4"
	::= { dMTFSystemResources2Entry 4 }

resourceTypeAtt5 OBJECT-TYPE
	SYNTAX		INTEGER { 
		other(1),
		unknown(2),
		memory(3),
		iO(4),
		iRQ(5),
		dMA(6)
	}
	ACCESS		read-only
	STATUS		mandatory
	DESCRIPTION	"The type of resource described by this row."
	REFERENCE "'DMTF|System Resources 2|001' 5"
	::= { dMTFSystemResources2Entry 5 }

resourceNumberAtt6 OBJECT-TYPE
	SYNTAX		DmiInteger
	ACCESS		read-only
	STATUS		mandatory
	DESCRIPTION	"DMA or IRQ number - 0 for Memory and I/O ranges. This is
the interrupt or DMA number relative to the bus that the interrupt is sourced
from."
	REFERENCE "'DMTF|System Resources 2|001' 6"
	::= { dMTFSystemResources2Entry 6 }

resourceInfoIDAtt7 OBJECT-TYPE
	SYNTAX		DmiInteger
	ACCESS		read-only
	STATUS		mandatory
	DESCRIPTION	"ID of the row in the 'Info' table for this type of system
resource. E.g. if this Resource Type is 'I/O' then this would be an index
into the 'System Resource I/O Info' table."
	REFERENCE "'DMTF|System Resources 2|001' 7"
	::= { dMTFSystemResources2Entry 7 }

startAddressAtt8 OBJECT-TYPE
	SYNTAX		Dmi-Integer64
	ACCESS		read-only
	STATUS		mandatory
	DESCRIPTION	"Starting physical address for this memory range, or the minimum
base address if this attribute is being used to describe a programmable range.
0 for IRQ and DMA resources."
	REFERENCE "'DMTF|System Resources 2|001' 8"
	::= { dMTFSystemResources2Entry 8 }

endAddressAtt9 OBJECT-TYPE
	SYNTAX		Dmi-Integer64
	ACCESS		read-only
	STATUS		mandatory
	DESCRIPTION	"Ending physical address (address of last byte) for this memory
range, or the maximum configurable base address if this attribute is being
used to describe a programmable range. 0 for IRQ and DMA resources."
	REFERENCE "'DMTF|System Resources 2|001' 9"
	::= { dMTFSystemResources2Entry 9 }

resourceSizeAtt10 OBJECT-TYPE
	SYNTAX		DmiInteger
	ACCESS		read-only
	STATUS		mandatory
	DESCRIPTION	"jNumber of consecutive bytes that a memory or I/O resource
consumes. 0 for IRQ and DMA resources."
	REFERENCE "'DMTF|System Resources 2|001' 10"
	::= { dMTFSystemResources2Entry 10 }

baseAlignmentAtt11 OBJECT-TYPE
	SYNTAX		DmiInteger
	ACCESS		read-only
	STATUS		mandatory
	DESCRIPTION	"Alignment of Start Address, in bytes. Indicates the granularity
of the increments in which a programmable range can be set."
	REFERENCE "'DMTF|System Resources 2|001' 11"
	::= { dMTFSystemResources2Entry 11 }

shareableAtt12 OBJECT-TYPE
	SYNTAX		INTEGER { 
		false(0),
		true(1),
		unknown(2)
	}
	ACCESS		read-only
	STATUS		mandatory
	DESCRIPTION	"Indicates whether the resource is shareable."
	REFERENCE "'DMTF|System Resources 2|001' 12"
	::= { dMTFSystemResources2Entry 12 }

sharedAtt13 OBJECT-TYPE
	SYNTAX		INTEGER { 
		false(0),
		true(1),
		unknown(2)
	}
	ACCESS		read-only
	STATUS		mandatory
	DESCRIPTION	"Indicates whether this resource, or a portion of this resource,
is shared with another device."
	REFERENCE "'DMTF|System Resources 2|001' 13"
	::= { dMTFSystemResources2Entry 13 }

SdMTFSystemSlots ::= SEQUENCE { 
	dMTFSystemSlotsState INTEGER,
	slotIndexAtt1	DmiInteger,
	slotTypeAtt2	Dmi-Integer64,
	slotWidthAtt3	DmiInteger,
	currentUsageAtt4	DmiInteger,
	slotDescriptionAtt5	DmiDisplaystring,
	slotCategoryAtt6	DmiInteger,
	virtualSlotAtt7	DmiInteger,
	resourceUserIDAtt8	DmiInteger
}

dMTFSystemSlotsTable OBJECT-TYPE
	SYNTAX		SEQUENCE OF SdMTFSystemSlots
	ACCESS		not-accessible
	STATUS		mandatory
	DESCRIPTION	"This group defines the attributes for the different system
expansion slots supported in this system."
	::= { dmtfSystemsMIF 18 }

dMTFSystemSlotsEntry OBJECT-TYPE
	SYNTAX		SdMTFSystemSlots
	ACCESS		not-accessible
	STATUS		mandatory
	DESCRIPTION	"This group defines the attributes for the different system
expansion slots supported in this system."
	INDEX		{ DmiCompId,DmiGroupId, slotIndexAtt1 }
	::= { dMTFSystemSlotsTable 1 }


dMTFSystemSlotsState OBJECT-TYPE
	SYNTAX		INTEGER { 
		active(1),
		notInService(2),
		notReady(3),
		createAndGo(4),
		createAndWait(5),
		destroy(6)
	}
	ACCESS		read-write
	STATUS		mandatory
	REFERENCE "'DMTF|System Slots|003' 0"
	::= { dMTFSystemSlotsEntry 0 }

slotIndexAtt1 OBJECT-TYPE
	SYNTAX		DmiInteger
	ACCESS		read-only
	STATUS		mandatory
	DESCRIPTION	"An index into the system slot table. This is the hardware
ID number for each expansion slot, whether it is occupied or not (starting
with 1)."
	REFERENCE "'DMTF|System Slots|003' 1"
	::= { dMTFSystemSlotsEntry 1 }

slotTypeAtt2 OBJECT-TYPE
	SYNTAX		Dmi-Integer64
	ACCESS		read-only
	STATUS		mandatory
	DESCRIPTION	"The bus type supported in this slot. This is a bit field
with the following definitions: 
 Bit 0 (2^0), if 1, it is a long-length
card; 
     if 0, it is a short-length card, 
 Bit 1 (2^1) if set, indicates
ISA, 
 Bit 2 (2^2) indicates EISA, 
 Bit 3 (2^3) indicates MCA, 
 Bit 4 (2^4)
indicates PCI, 
 Bit 5 (2^5) indicates VL, 
 Bit 6 (2^6) indicates PCMCIA,

 Bit 7 (2^7) refers to NuBus, 
 Bit 8 (2^8) indicates PC-98/C20, 
 Bit 9
(2^9) indicates PC-98/C24, 
 Bit 10 (2^10) indicates PC-98/E, 
 Bit 11 (2^"
	REFERENCE "'DMTF|System Slots|003' 2"
	::= { dMTFSystemSlotsEntry 2 }

slotWidthAtt3 OBJECT-TYPE
	SYNTAX		INTEGER { 
		other(1),
		unknown(2),
		x8BitCard(3),
		x16BitCard(4),
		x32BitCard(5),
		x64BitCard(6),
		x128BitCard(7)
	}
	ACCESS		read-only
	STATUS		mandatory
	DESCRIPTION	"The maximum bus width of cards accepted in this slot."
	REFERENCE "'DMTF|System Slots|003' 3"
	::= { dMTFSystemSlotsEntry 3 }

currentUsageAtt4 OBJECT-TYPE
	SYNTAX		INTEGER { 
		other(1),
		unknown(2),
		available(3),
		inUse(4)
	}
	ACCESS		read-only
	STATUS		mandatory
	DESCRIPTION	"Is this slot is currently in use?"
	REFERENCE "'DMTF|System Slots|003' 4"
	::= { dMTFSystemSlotsEntry 4 }

slotDescriptionAtt5 OBJECT-TYPE
	SYNTAX		DmiDisplaystring
	ACCESS		read-only
	STATUS		mandatory
	DESCRIPTION	"The card currently occupying this slot."
	REFERENCE "'DMTF|System Slots|003' 5"
	::= { dMTFSystemSlotsEntry 5 }

slotCategoryAtt6 OBJECT-TYPE
	SYNTAX		INTEGER { 
		other(1),
		unknown(2),
		busConnector(3),
		pCMCIASlot(4),
		motherboard(5)
	}
	ACCESS		read-only
	STATUS		mandatory
	DESCRIPTION	"The word 'slot' is used to refer to bus slots. The last case
(motherboard) refers to situations where a functional element is integrated
onto, say, a motherboard and connects to a bus without a connector. It still
takes up an expansion site on the bus but this is termed a 'virtual slot'
as opposed to a physical slot (see the attribute 'Virtual Slot'). Virtual
slots are in effect permanently occupied expansion sites. This attribute
establishes which category of physical slot this table entry is defining."
	REFERENCE "'DMTF|System Slots|003' 6"
	::= { dMTFSystemSlotsEntry 6 }

virtualSlotAtt7 OBJECT-TYPE
	SYNTAX		INTEGER { 
		false(0),
		true(1),
		unknown(2)
	}
	ACCESS		read-only
	STATUS		mandatory
	DESCRIPTION	"This attribute indicates whether this is a 'virtual slot'
or not. A 'virtual slot' is an expansion site that is permanently occupied
because of the level of integration of an expandable component. An example
of a virtual slot is an I/O bus position taken up by a LAN controller that
is integrated onto a motherboard. A slot with the 'Slot Category' of Motherboard
is typically a Virtual Slot."
	REFERENCE "'DMTF|System Slots|003' 7"
	::= { dMTFSystemSlotsEntry 7 }

resourceUserIDAtt8 OBJECT-TYPE
	SYNTAX		DmiInteger
	ACCESS		read-only
	STATUS		mandatory
	DESCRIPTION	"Value used to locate the rows in the System Resources 2 table
for the resources associated with this slot or expansion site.  0 = 'unspecified
."
	REFERENCE "'DMTF|System Slots|003' 8"
	::= { dMTFSystemSlotsEntry 8 }

SdMTFTemperatureProbe ::= SEQUENCE { 
	dMTFTemperatureProbeState INTEGER,
	temperatureProbeTableIndexAtt1	DmiInteger,
	temperatureProbeLocationAtt2	DmiInteger,
	temperatureProbeDescriptionAtt3	DmiDisplaystring,
	temperatureStatusAtt4	DmiInteger,
	temperatureProbeTemperatureReadingAtt5	DmiInteger,
	monitoredTemperatureNominalReadingAtt6	DmiInteger,
	monitoredTemperatureNormalMaximumAtt7	DmiInteger,
	monitoredTemperatureNormalMinimumAtt8	DmiInteger,
	temperatureProbeMaximumAtt9	DmiInteger,
	temperatureProbeMinimumAtt10	DmiInteger,
	temperatureReadingLowerThresholdNonCriticalAtt11	DmiInteger,
	temperatureReadingUpperThresholdNonCriticalAtt12	DmiInteger,
	temperatureReadingLowerThresholdCriticalAtt13	DmiInteger,
	temperatureReadingUpperThresholdCriticalAtt14	DmiInteger,
	temperatureReadingLowerThresholdNonRecoverableAtt15	DmiInteger,
	temperatureReadingUpperThresholdNonRecoverableAtt16	DmiInteger,
	temperatureProbeResolutionAtt17	DmiInteger,
	temperatureProbeToleranceAtt18	DmiInteger,
	temperatureProbeAccuracyAtt19	DmiInteger,
	fRUGroupIndexAtt20-1	DmiInteger,
	operationalGroupIndexAtt21-1	DmiInteger
}

dMTFTemperatureProbeTable OBJECT-TYPE
	SYNTAX		SEQUENCE OF SdMTFTemperatureProbe
	ACCESS		not-accessible
	STATUS		mandatory
	DESCRIPTION	"This group defines the attributes for the temperature probes
in this system."
	::= { dmtfSystemsMIF 54 }

dMTFTemperatureProbeEntry OBJECT-TYPE
	SYNTAX		SdMTFTemperatureProbe
	ACCESS		not-accessible
	STATUS		mandatory
	DESCRIPTION	"This group defines the attributes for the temperature probes
in this system."
	INDEX		{ DmiCompId,DmiGroupId, temperatureProbeTableIndexAtt1 }
	::= { dMTFTemperatureProbeTable 1 }


dMTFTemperatureProbeState OBJECT-TYPE
	SYNTAX		INTEGER { 
		active(1),
		notInService(2),
		notReady(3),
		createAndGo(4),
		createAndWait(5),
		destroy(6)
	}
	ACCESS		read-write
	STATUS		mandatory
	REFERENCE "'DMTF|Temperature Probe|001' 0"
	::= { dMTFTemperatureProbeEntry 0 }

temperatureProbeTableIndexAtt1 OBJECT-TYPE
	SYNTAX		DmiInteger
	ACCESS		read-only
	STATUS		mandatory
	DESCRIPTION	"Index into this temperature probe table."
	REFERENCE "'DMTF|Temperature Probe|001' 1"
	::= { dMTFTemperatureProbeEntry 1 }

temperatureProbeLocationAtt2 OBJECT-TYPE
	SYNTAX		INTEGER { 
		other(1),
		unknown(2),
		processor(3),
		disk(4),
		peripheralBay(5),
		sMBMaster(6),
		motherboard(7),
		memoryModule(8),
		processorModule(9),
		powerUnit(10),
		addInCard(11)
	}
	ACCESS		read-only
	STATUS		mandatory
	DESCRIPTION	"Identifies the physical location of the temperature probe."
	REFERENCE "'DMTF|Temperature Probe|001' 2"
	::= { dMTFTemperatureProbeEntry 2 }

temperatureProbeDescriptionAtt3 OBJECT-TYPE
	SYNTAX		DmiDisplaystring
	ACCESS		read-only
	STATUS		mandatory
	DESCRIPTION	"Additional descriptive information about the temperature
probe or probe's location."
	REFERENCE "'DMTF|Temperature Probe|001' 3"
	::= { dMTFTemperatureProbeEntry 3 }

temperatureStatusAtt4 OBJECT-TYPE
	SYNTAX		INTEGER { 
		other(1),
		unknown(2),
		oK(3),
		nonCritical(4),
		critical(5),
		nonRecoverable(6)
	}
	ACCESS		read-only
	STATUS		mandatory
	DESCRIPTION	"Defines the status of the temperature monitored by this temperat
re probe."
	REFERENCE "'DMTF|Temperature Probe|001' 4"
	::= { dMTFTemperatureProbeEntry 4 }

temperatureProbeTemperatureReadingAtt5 OBJECT-TYPE
	SYNTAX		DmiInteger
	ACCESS		read-only
	STATUS		mandatory
	DESCRIPTION	"The present temperature reading of this temperature probe
in 1/10th degrees C. 0x8000000 denotes 'unknown'."
	REFERENCE "'DMTF|Temperature Probe|001' 5"
	::= { dMTFTemperatureProbeEntry 5 }

monitoredTemperatureNominalReadingAtt6 OBJECT-TYPE
	SYNTAX		DmiInteger
	ACCESS		read-only
	STATUS		mandatory
	DESCRIPTION	"The nominal temperature reading of the temperature monitored
by this probe in 1/10th degrees C. 0x80000000 denotes 'unknown'."
	REFERENCE "'DMTF|Temperature Probe|001' 6"
	::= { dMTFTemperatureProbeEntry 6 }

monitoredTemperatureNormalMaximumAtt7 OBJECT-TYPE
	SYNTAX		DmiInteger
	ACCESS		read-only
	STATUS		mandatory
	DESCRIPTION	"The normal maximum temperature reading of the temperature
monitored by this probe in 1/10th degrees C. 0x80000000 denotes 'unknown'."
	REFERENCE "'DMTF|Temperature Probe|001' 7"
	::= { dMTFTemperatureProbeEntry 7 }

monitoredTemperatureNormalMinimumAtt8 OBJECT-TYPE
	SYNTAX		DmiInteger
	ACCESS		read-only
	STATUS		mandatory
	DESCRIPTION	"The normal minimum temperature reading of the temperature
monitored by this probe in 1/10th degrees C. 0x80000000 denotes 'unknown'."
	REFERENCE "'DMTF|Temperature Probe|001' 8"
	::= { dMTFTemperatureProbeEntry 8 }

temperatureProbeMaximumAtt9 OBJECT-TYPE
	SYNTAX		DmiInteger
	ACCESS		read-only
	STATUS		mandatory
	DESCRIPTION	"The maximum temperature reading specified to be readable
by this probe in 1/10th degrees C. 0x80000000 denotes 'unknown'."
	REFERENCE "'DMTF|Temperature Probe|001' 9"
	::= { dMTFTemperatureProbeEntry 9 }

temperatureProbeMinimumAtt10 OBJECT-TYPE
	SYNTAX		DmiInteger
	ACCESS		read-only
	STATUS		mandatory
	DESCRIPTION	"The minimum temperature reading specified to be readable
by this probe in 1/10th degrees C. 0x80000000 denotes 'unknown'."
	REFERENCE "'DMTF|Temperature Probe|001' 10"
	::= { dMTFTemperatureProbeEntry 10 }

temperatureReadingLowerThresholdNonCriticalAtt11 OBJECT-TYPE
	SYNTAX		DmiInteger
	ACCESS		read-write
	STATUS		mandatory
	DESCRIPTION	"The lower non-critical threshold for the temperature reading
set by the user, in 1/10th degrees C. 0x80000000 denotes 'unknown'."
	REFERENCE "'DMTF|Temperature Probe|001' 11"
	::= { dMTFTemperatureProbeEntry 11 }

temperatureReadingUpperThresholdNonCriticalAtt12 OBJECT-TYPE
	SYNTAX		DmiInteger
	ACCESS		read-write
	STATUS		mandatory
	DESCRIPTION	"The upper non-critical threshold for the temperature probe,
in 1/10th degrees C. 0x80000000 denotes 'unknown'."
	REFERENCE "'DMTF|Temperature Probe|001' 12"
	::= { dMTFTemperatureProbeEntry 12 }

temperatureReadingLowerThresholdCriticalAtt13 OBJECT-TYPE
	SYNTAX		DmiInteger
	ACCESS		read-write
	STATUS		mandatory
	DESCRIPTION	"The lower critical threshold for the temperature probe, in
1/10 degrees C. 0x80000000 denotes 'unknown'."
	REFERENCE "'DMTF|Temperature Probe|001' 13"
	::= { dMTFTemperatureProbeEntry 13 }

temperatureReadingUpperThresholdCriticalAtt14 OBJECT-TYPE
	SYNTAX		DmiInteger
	ACCESS		read-write
	STATUS		mandatory
	DESCRIPTION	"The upper critical threshold for the temperature probe, in
/10th degrees C. 0x80000000 denotes 'unknown'."
	REFERENCE "'DMTF|Temperature Probe|001' 14"
	::= { dMTFTemperatureProbeEntry 14 }

temperatureReadingLowerThresholdNonRecoverableAtt15 OBJECT-TYPE
	SYNTAX		DmiInteger
	ACCESS		read-write
	STATUS		mandatory
	DESCRIPTION	"The lower non-recoverable threshold for the temperature probe,
in 1/10th degrees C. 0x80000000 denotes 'unknown'."
	REFERENCE "'DMTF|Temperature Probe|001' 15"
	::= { dMTFTemperatureProbeEntry 15 }

temperatureReadingUpperThresholdNonRecoverableAtt16 OBJECT-TYPE
	SYNTAX		DmiInteger
	ACCESS		read-write
	STATUS		mandatory
	DESCRIPTION	"The upper non-recoverable threshold for the temperature probe,
in 1/10th degrees C. 0x80000000 denotes 'unknown'."
	REFERENCE "'DMTF|Temperature Probe|001' 16"
	::= { dMTFTemperatureProbeEntry 16 }

temperatureProbeResolutionAtt17 OBJECT-TYPE
	SYNTAX		DmiInteger
	ACCESS		read-write
	STATUS		mandatory
	DESCRIPTION	"The resolution for the reading from this temperature probe,
in tenths of 1/10th degrees C. '0x80000000 denotes 'unknown'."
	REFERENCE "'DMTF|Temperature Probe|001' 17"
	::= { dMTFTemperatureProbeEntry 17 }

temperatureProbeToleranceAtt18 OBJECT-TYPE
	SYNTAX		DmiInteger
	ACCESS		read-write
	STATUS		mandatory
	DESCRIPTION	"The tolerance for the reading from this temperature probe,
in plus/minus 1/10 degrees C. 0x80000000 denotes 'unknown'."
	REFERENCE "'DMTF|Temperature Probe|001' 18"
	::= { dMTFTemperatureProbeEntry 18 }

temperatureProbeAccuracyAtt19 OBJECT-TYPE
	SYNTAX		DmiInteger
	ACCESS		read-write
	STATUS		mandatory
	DESCRIPTION	"The accuracy for the reading from this temperature probe,
in plus/minus hundredths of a percent. 0x80000000 denotes 'unknown' or'unsupport
d'."
	REFERENCE "'DMTF|Temperature Probe|001' 19"
	::= { dMTFTemperatureProbeEntry 19 }

fRUGroupIndexAtt20-1 OBJECT-TYPE
	SYNTAX		DmiInteger
	ACCESS		read-only
	STATUS		mandatory
	DESCRIPTION	"Index into the FRU table. A value of -1 indicates that this
device is not an FRU."
	REFERENCE "'DMTF|Temperature Probe|001' 20"
	::= { dMTFTemperatureProbeEntry 20 }

operationalGroupIndexAtt21-1 OBJECT-TYPE
	SYNTAX		DmiInteger
	ACCESS		read-only
	STATUS		mandatory
	DESCRIPTION	"Index into the Operational State table"
	REFERENCE "'DMTF|Temperature Probe|001' 21"
	::= { dMTFTemperatureProbeEntry 21 }

SdMTFVoltageProbe ::= SEQUENCE { 
	dMTFVoltageProbeState INTEGER,
	voltageProbeIndexAtt1	DmiInteger,
	voltageProbeLocationAtt2	DmiInteger,
	voltageProbeDescriptionAtt3	DmiDisplaystring,
	voltageStatusAtt4	DmiInteger,
	voltageProbeVoltageLevelAtt5	DmiInteger,
	monitoredVoltageNominalLevelAtt6	DmiInteger,
	monitoredVoltageNormalMaximumAtt7	DmiInteger,
	monitoredVoltageNormalMinimumAtt8	DmiInteger,
	voltageProbeMaximumAtt9	DmiInteger,
	voltageProbeMinimumAtt10	DmiInteger,
	voltageLevelLowerThresholdNonCriticalAtt11	DmiInteger,
	voltageLevelUpperThresholdNonCriticalAtt12	DmiInteger,
	voltageLevelLowerThresholdCriticalAtt13	DmiInteger,
	voltageLevelUpperThresholdCriticalAtt14	DmiInteger,
	voltageLevelLowerThresholdNonRecoverableAtt15	DmiInteger,
	voltageLevelUpperThresholdNonRecoverableAtt16	DmiInteger,
	voltageProbeResolutionAtt17	DmiInteger,
	voltageProbeToleranceAtt18	DmiInteger,
	voltageProbeAccuracyAtt19	DmiInteger,
	fRUGroupIndexAtt20-2	DmiInteger,
	operationalGroupIndexAtt21-2	DmiInteger
}

dMTFVoltageProbeTable OBJECT-TYPE
	SYNTAX		SEQUENCE OF SdMTFVoltageProbe
	ACCESS		not-accessible
	STATUS		mandatory
	DESCRIPTION	"This group defines the attributes for the voltage probes
in this system."
	::= { dmtfSystemsMIF 53 }

dMTFVoltageProbeEntry OBJECT-TYPE
	SYNTAX		SdMTFVoltageProbe
	ACCESS		not-accessible
	STATUS		mandatory
	DESCRIPTION	"This group defines the attributes for the voltage probes
in this system."
	INDEX		{ DmiCompId,DmiGroupId, voltageProbeIndexAtt1 }
	::= { dMTFVoltageProbeTable 1 }


dMTFVoltageProbeState OBJECT-TYPE
	SYNTAX		INTEGER { 
		active(1),
		notInService(2),
		notReady(3),
		createAndGo(4),
		createAndWait(5),
		destroy(6)
	}
	ACCESS		read-write
	STATUS		mandatory
	REFERENCE "'DMTF|Voltage Probe|001' 0"
	::= { dMTFVoltageProbeEntry 0 }

voltageProbeIndexAtt1 OBJECT-TYPE
	SYNTAX		DmiInteger
	ACCESS		read-only
	STATUS		mandatory
	DESCRIPTION	"Index into this voltage probe table."
	REFERENCE "'DMTF|Voltage Probe|001' 1"
	::= { dMTFVoltageProbeEntry 1 }

voltageProbeLocationAtt2 OBJECT-TYPE
	SYNTAX		INTEGER { 
		other(1),
		unknown(2),
		processor(3),
		disk(4),
		peripheralBay(5),
		systemManagementModule(6),
		motherboard(7),
		memoryModule(8),
		processorModule(9),
		powerUnit(10),
		addInCard(11)
	}
	ACCESS		read-only
	STATUS		mandatory
	DESCRIPTION	"Identifies the physical location of the voltage probe."
	REFERENCE "'DMTF|Voltage Probe|001' 2"
	::= { dMTFVoltageProbeEntry 2 }

voltageProbeDescriptionAtt3 OBJECT-TYPE
	SYNTAX		DmiDisplaystring
	ACCESS		read-only
	STATUS		mandatory
	DESCRIPTION	"Additional descriptive information about the voltage probe
or probe's location."
	REFERENCE "'DMTF|Voltage Probe|001' 3"
	::= { dMTFVoltageProbeEntry 3 }

voltageStatusAtt4 OBJECT-TYPE
	SYNTAX		INTEGER { 
		other(1),
		unknown(2),
		oK(3),
		nonCritical(4),
		critical(5),
		nonRecoverable(6)
	}
	ACCESS		read-only
	STATUS		mandatory
	DESCRIPTION	"Defines the status of the voltage monitored by this voltage
probe."
	REFERENCE "'DMTF|Voltage Probe|001' 4"
	::= { dMTFVoltageProbeEntry 4 }

voltageProbeVoltageLevelAtt5 OBJECT-TYPE
	SYNTAX		DmiInteger
	ACCESS		read-only
	STATUS		mandatory
	DESCRIPTION	"The current voltage level of this voltage probe in millivolts.
0x8000000 denotes 'unknown'."
	REFERENCE "'DMTF|Voltage Probe|001' 5"
	::= { dMTFVoltageProbeEntry 5 }

monitoredVoltageNominalLevelAtt6 OBJECT-TYPE
	SYNTAX		DmiInteger
	ACCESS		read-only
	STATUS		mandatory
	DESCRIPTION	"The nominal voltage level of the voltage monitored by this
probe in millivolts. 0x80000000 denotes 'unknown'."
	REFERENCE "'DMTF|Voltage Probe|001' 6"
	::= { dMTFVoltageProbeEntry 6 }

monitoredVoltageNormalMaximumAtt7 OBJECT-TYPE
	SYNTAX		DmiInteger
	ACCESS		read-only
	STATUS		mandatory
	DESCRIPTION	"The normal maximum voltage level of the voltage monitored
by this probe in millivolts. 0x80000000 denotes 'unknown'."
	REFERENCE "'DMTF|Voltage Probe|001' 7"
	::= { dMTFVoltageProbeEntry 7 }

monitoredVoltageNormalMinimumAtt8 OBJECT-TYPE
	SYNTAX		DmiInteger
	ACCESS		read-only
	STATUS		mandatory
	DESCRIPTION	"The normal minimum voltage level of the voltage monitored
by this probe in millivolts. 0x80000000 denotes 'unknown'."
	REFERENCE "'DMTF|Voltage Probe|001' 8"
	::= { dMTFVoltageProbeEntry 8 }

voltageProbeMaximumAtt9 OBJECT-TYPE
	SYNTAX		DmiInteger
	ACCESS		read-only
	STATUS		mandatory
	DESCRIPTION	"The maximum voltage level specified to be readable by this
probe in millivolts. 0x80000000 denotes 'unknown'."
	REFERENCE "'DMTF|Voltage Probe|001' 9"
	::= { dMTFVoltageProbeEntry 9 }

voltageProbeMinimumAtt10 OBJECT-TYPE
	SYNTAX		DmiInteger
	ACCESS		read-only
	STATUS		mandatory
	DESCRIPTION	"The minimum voltage level specified to be readable by this
probe in millivolts. 0x80000000 denotes 'unknown'."
	REFERENCE "'DMTF|Voltage Probe|001' 10"
	::= { dMTFVoltageProbeEntry 10 }

voltageLevelLowerThresholdNonCriticalAtt11 OBJECT-TYPE
	SYNTAX		DmiInteger
	ACCESS		read-write
	STATUS		mandatory
	DESCRIPTION	"The lower non-critical threshold for the voltage level set
by the user, in millivolts. 0x80000000 denotes 'unknown'."
	REFERENCE "'DMTF|Voltage Probe|001' 11"
	::= { dMTFVoltageProbeEntry 11 }

voltageLevelUpperThresholdNonCriticalAtt12 OBJECT-TYPE
	SYNTAX		DmiInteger
	ACCESS		read-write
	STATUS		mandatory
	DESCRIPTION	"The upper non-critical threshold for the voltage probe, in
millivolts.  0x80000000 denotes 'unknown'."
	REFERENCE "'DMTF|Voltage Probe|001' 12"
	::= { dMTFVoltageProbeEntry 12 }

voltageLevelLowerThresholdCriticalAtt13 OBJECT-TYPE
	SYNTAX		DmiInteger
	ACCESS		read-write
	STATUS		mandatory
	DESCRIPTION	"The lower critical threshold for the voltage probe, in millivolt
.  0x80000000 denotes 'unknown'."
	REFERENCE "'DMTF|Voltage Probe|001' 13"
	::= { dMTFVoltageProbeEntry 13 }

voltageLevelUpperThresholdCriticalAtt14 OBJECT-TYPE
	SYNTAX		DmiInteger
	ACCESS		read-write
	STATUS		mandatory
	DESCRIPTION	"The upper critical threshold for the voltage probe, in millivolt
.  0x80000000 denotes 'unknown'."
	REFERENCE "'DMTF|Voltage Probe|001' 14"
	::= { dMTFVoltageProbeEntry 14 }

voltageLevelLowerThresholdNonRecoverableAtt15 OBJECT-TYPE
	SYNTAX		DmiInteger
	ACCESS		read-write
	STATUS		mandatory
	DESCRIPTION	"The lower non-recoverable threshold for the voltage probe,
in millivolts.  0x80000000 denotes 'unknown'."
	REFERENCE "'DMTF|Voltage Probe|001' 15"
	::= { dMTFVoltageProbeEntry 15 }

voltageLevelUpperThresholdNonRecoverableAtt16 OBJECT-TYPE
	SYNTAX		DmiInteger
	ACCESS		read-write
	STATUS		mandatory
	DESCRIPTION	"The upper non-recoverable threshold for the voltage probe,
in millivolts. 0x80000000 denotes 'unknown'."
	REFERENCE "'DMTF|Voltage Probe|001' 16"
	::= { dMTFVoltageProbeEntry 16 }

voltageProbeResolutionAtt17 OBJECT-TYPE
	SYNTAX		DmiInteger
	ACCESS		read-write
	STATUS		mandatory
	DESCRIPTION	"The resolution for the reading from this voltage probe, in
tenths of millivolts. '0x80000000 denotes 'unknown'."
	REFERENCE "'DMTF|Voltage Probe|001' 17"
	::= { dMTFVoltageProbeEntry 17 }

voltageProbeToleranceAtt18 OBJECT-TYPE
	SYNTAX		DmiInteger
	ACCESS		read-write
	STATUS		mandatory
	DESCRIPTION	"The tolerance for the reading from this voltage probe, in
plus/minus millivolts. 0x80000000 denotes 'unknown'."
	REFERENCE "'DMTF|Voltage Probe|001' 18"
	::= { dMTFVoltageProbeEntry 18 }

voltageProbeAccuracyAtt19 OBJECT-TYPE
	SYNTAX		DmiInteger
	ACCESS		read-write
	STATUS		mandatory
	DESCRIPTION	"The accuracy for the reading from this voltage probe, in
plus/minus hundredths of a percent. 0x80000000 denotes 'unknown'."
	REFERENCE "'DMTF|Voltage Probe|001' 19"
	::= { dMTFVoltageProbeEntry 19 }

fRUGroupIndexAtt20-2 OBJECT-TYPE
	SYNTAX		DmiInteger
	ACCESS		read-only
	STATUS		mandatory
	DESCRIPTION	"Index into the FRU table"
	REFERENCE "'DMTF|Voltage Probe|001' 20"
	::= { dMTFVoltageProbeEntry 20 }

operationalGroupIndexAtt21-2 OBJECT-TYPE
	SYNTAX		DmiInteger
	ACCESS		read-only
	STATUS		mandatory
	DESCRIPTION	"Index into the Operational State table"
	REFERENCE "'DMTF|Voltage Probe|001' 21"
	::= { dMTFVoltageProbeEntry 21 }

SdMTFPhysicalMemoryArray ::= SEQUENCE { 
	dMTFPhysicalMemoryArrayState INTEGER,
	memoryArrayTableIndexAtt1	DmiInteger,
	memoryArrayLocationAtt2	DmiInteger,
	memoryArrayUseAtt3	DmiInteger,
	maximumMemoryCapacityAtt4	DmiInteger,
	numberOfMemoryDeviceSocketsAtt5	DmiInteger,
	numberOfMemoryDeviceSocketsUsedAtt6	DmiInteger,
	memoryErrorCorrectionAtt7	DmiInteger,
	arrayErrorTypeAtt8	DmiInteger,
	lastErrorUpdateAtt9	DmiInteger,
	errorOperationAtt10	DmiInteger,
	errorDataSizeAtt11	DmiInteger,
	errorDataAtt12	DmiOctetstring,
	vendorSyndromeAtt13	DmiOctetstring,
	errorAddressAtt14	Dmi-Integer64,
	errorResolutionAtt15	DmiInteger,
	fRUGroupIndexAtt16	DmiInteger,
	operationalGroupIndexAtt17	DmiInteger
}

dMTFPhysicalMemoryArrayTable OBJECT-TYPE
	SYNTAX		SEQUENCE OF SdMTFPhysicalMemoryArray
	ACCESS		not-accessible
	STATUS		mandatory
	DESCRIPTION	"This group represents an array of physical memory as a collectio
 of one or more Memory Devices associated in sets and partitions."
	::= { dmtfSystemsMIF 33 }

dMTFPhysicalMemoryArrayEntry OBJECT-TYPE
	SYNTAX		SdMTFPhysicalMemoryArray
	ACCESS		not-accessible
	STATUS		mandatory
	DESCRIPTION	"This group represents an array of physical memory as a collectio
 of one or more Memory Devices associated in sets and partitions."
	INDEX		{ DmiCompId,DmiGroupId, memoryArrayTableIndexAtt1 }
	::= { dMTFPhysicalMemoryArrayTable 1 }


dMTFPhysicalMemoryArrayState OBJECT-TYPE
	SYNTAX		INTEGER { 
		active(1),
		notInService(2),
		notReady(3),
		createAndGo(4),
		createAndWait(5),
		destroy(6)
	}
	ACCESS		read-write
	STATUS		mandatory
	REFERENCE "'DMTF|Physical Memory Array|001' 0"
	::= { dMTFPhysicalMemoryArrayEntry 0 }

memoryArrayTableIndexAtt1 OBJECT-TYPE
	SYNTAX		DmiInteger
	ACCESS		read-only
	STATUS		mandatory
	DESCRIPTION	"A unique number that identifies this row."
	REFERENCE "'DMTF|Physical Memory Array|001' 1"
	::= { dMTFPhysicalMemoryArrayEntry 1 }

memoryArrayLocationAtt2 OBJECT-TYPE
	SYNTAX		INTEGER { 
		other(1),
		unknown(2),
		systemBoardOrMotherboard(3),
		iSAAddOnCard(4),
		eISAAddOnCard(5),
		pCIAddOnCard(6),
		mCAAddOnCard(7),
		pCMCIAAddOnCard(8),
		proprietaryAddOnCard(9),
		nuBus(16),
		pC98C20AddOnCard(160),
		pC98C24AddOnCard(161),
		pC98EAddOnCard(162),
		pC98LocalBusAddOnCard(163),
		pC98CardSlotAddOnCard(164)
	}
	ACCESS		read-only
	STATUS		mandatory
	DESCRIPTION	"The physical location of the Memory Array, whether on the
system board or an add-on board."
	REFERENCE "'DMTF|Physical Memory Array|001' 2"
	::= { dMTFPhysicalMemoryArrayEntry 2 }

memoryArrayUseAtt3 OBJECT-TYPE
	SYNTAX		INTEGER { 
		other(1),
		unknown(2),
		systemMemory(3),
		videoMemory(4),
		flashMemory(5),
		nonVolatileRAM(6),
		cacheMemory(7)
	}
	ACCESS		read-only
	STATUS		mandatory
	DESCRIPTION	"What this Memory Array is used for."
	REFERENCE "'DMTF|Physical Memory Array|001' 3"
	::= { dMTFPhysicalMemoryArrayEntry 3 }

maximumMemoryCapacityAtt4 OBJECT-TYPE
	SYNTAX		DmiInteger
	ACCESS		read-only
	STATUS		mandatory
	DESCRIPTION	"The maximum memory capacity, in kilobytes, on this array.
0x80000000denotes 'unknown'."
	REFERENCE "'DMTF|Physical Memory Array|001' 4"
	::= { dMTFPhysicalMemoryArrayEntry 4 }

numberOfMemoryDeviceSocketsAtt5 OBJECT-TYPE
	SYNTAX		DmiInteger
	ACCESS		read-only
	STATUS		mandatory
	DESCRIPTION	"The number of SIMM slots or sockets available for Memory
Devices in this array. 0x80000000 denotes 'unknown'. "
	REFERENCE "'DMTF|Physical Memory Array|001' 5"
	::= { dMTFPhysicalMemoryArrayEntry 5 }

numberOfMemoryDeviceSocketsUsedAtt6 OBJECT-TYPE
	SYNTAX		DmiInteger
	ACCESS		read-only
	STATUS		mandatory
	DESCRIPTION	"The number of SIMM slots or sockets in use for Memory Devices
in this array. 0x80000000 denotes 'unknown'."
	REFERENCE "'DMTF|Physical Memory Array|001' 6"
	::= { dMTFPhysicalMemoryArrayEntry 6 }

memoryErrorCorrectionAtt7 OBJECT-TYPE
	SYNTAX		INTEGER { 
		other(1),
		unknown(2),
		none(3),
		parity(4),
		singleBitECC(5),
		multiBitECC(6),
		cRC(7)
	}
	ACCESS		read-only
	STATUS		mandatory
	DESCRIPTION	"The main hardware error correction or detection method supported
by this Memory Array."
	REFERENCE "'DMTF|Physical Memory Array|001' 7"
	::= { dMTFPhysicalMemoryArrayEntry 7 }

arrayErrorTypeAtt8 OBJECT-TYPE
	SYNTAX		INTEGER { 
		other(1),
		unknown(2),
		oK(3),
		badRead(4),
		parityError(5),
		singleBitError(6),
		doubleBitError(7),
		multiBitError(8),
		nibbleError(9),
		checksumError(10),
		cRCError(11),
		correctedSingleBitError(12),
		correctedError(13),
		uncorrectableError(14)
	}
	ACCESS		read-only
	STATUS		mandatory
	DESCRIPTION	"The type of error that is associated with the current status
reported in Operational State for this Memory Array."
	REFERENCE "'DMTF|Physical Memory Array|001' 8"
	::= { dMTFPhysicalMemoryArrayEntry 8 }

lastErrorUpdateAtt9 OBJECT-TYPE
	SYNTAX		INTEGER { 
		other(1),
		unknown(2),
		noUpdateSinceLastInstrumentationStart(3),
		updatedFromInformationObtainedPriorToInstrumentati(4),
		updatedDuringInstrumentationRunTime(5)
	}
	ACCESS		read-only
	STATUS		mandatory
	DESCRIPTION	"System state during which last error status was collected."
	REFERENCE "'DMTF|Physical Memory Array|001' 9"
	::= { dMTFPhysicalMemoryArrayEntry 9 }

errorOperationAtt10 OBJECT-TYPE
	SYNTAX		INTEGER { 
		other(1),
		unknown(2),
		read(3),
		write(4),
		partialWrite(5)
	}
	ACCESS		read-only
	STATUS		mandatory
	DESCRIPTION	"The memory access operation that caused the current error."
	REFERENCE "'DMTF|Physical Memory Array|001' 10"
	::= { dMTFPhysicalMemoryArrayEntry 10 }

errorDataSizeAtt11 OBJECT-TYPE
	SYNTAX		DmiInteger
	ACCESS		read-only
	STATUS		mandatory
	DESCRIPTION	"The size of the data transfer that caused the error, in bits.
Zero indicates no error, 0x80000000 denotes 'unknown'."
	REFERENCE "'DMTF|Physical Memory Array|001' 11"
	::= { dMTFPhysicalMemoryArrayEntry 11 }

errorDataAtt12 OBJECT-TYPE
	SYNTAX		DmiOctetstring
	ACCESS		read-only
	STATUS		mandatory
	DESCRIPTION	"Data captured during the erroneous Memory Array access. The
data occupy the first n bytes of the octet string required to hold 'Error
Data Size' bits of the data. Data are stored least-significant byte first."
	REFERENCE "'DMTF|Physical Memory Array|001' 12"
	::= { dMTFPhysicalMemoryArrayEntry 12 }

vendorSyndromeAtt13 OBJECT-TYPE
	SYNTAX		DmiOctetstring
	ACCESS		read-only
	STATUS		mandatory
	DESCRIPTION	"Vendor-specific syndrome or CRC data associated with the
erroneous access. "
	REFERENCE "'DMTF|Physical Memory Array|001' 13"
	::= { dMTFPhysicalMemoryArrayEntry 13 }

errorAddressAtt14 OBJECT-TYPE
	SYNTAX		Dmi-Integer64
	ACCESS		read-only
	STATUS		mandatory
	DESCRIPTION	"Physical address of the error based on the addressing of
the bus that the Memory Array is connected to. 0x8000 0000 0000 0000 denotes
'unknown'."
	REFERENCE "'DMTF|Physical Memory Array|001' 14"
	::= { dMTFPhysicalMemoryArrayEntry 14 }

errorResolutionAtt15 OBJECT-TYPE
	SYNTAX		DmiInteger
	ACCESS		read-only
	STATUS		mandatory
	DESCRIPTION	"Range in bytes that the error can be determined to be within,
when an Error Address is given. 0x80000000 denotes 'unknown'."
	REFERENCE "'DMTF|Physical Memory Array|001' 15"
	::= { dMTFPhysicalMemoryArrayEntry 15 }

fRUGroupIndexAtt16 OBJECT-TYPE
	SYNTAX		DmiInteger
	ACCESS		read-only
	STATUS		mandatory
	DESCRIPTION	"If this is a Field Replaceable Unit or if it is part of another
FRU, this provides an index into the FRU table; 'value = -1' indicates that
the group is not a FRU."
	REFERENCE "'DMTF|Physical Memory Array|001' 16"
	::= { dMTFPhysicalMemoryArrayEntry 16 }

operationalGroupIndexAtt17 OBJECT-TYPE
	SYNTAX		DmiInteger
	ACCESS		read-only
	STATUS		mandatory
	DESCRIPTION	"The index into the Operational State Table for this Memory
Array. The Operational State row is used to hold the overall error count
and error status for this array."
	REFERENCE "'DMTF|Physical Memory Array|001' 17"
	::= { dMTFPhysicalMemoryArrayEntry 17 }

SdMTFParallelPorts ::= SEQUENCE { 
	dMTFParallelPortsState INTEGER,
	parallelPortIndexAtt1	DmiInteger,
	parallelBaseIOAddressAtt2	Dmi-Integer64,
	iRQUsedAtt3-1	DmiInteger,
	logicalNameAtt4-1	DmiDisplaystring,
	connectorTypeAtt5-1	DmiInteger,
	connectorPinoutAtt6	DmiInteger,
	dMASupportAtt7	DmiInteger,
	parallelPortCapabilitiesAtt8	DmiInteger,
	operationalGroupIndexAtt9-1	DmiInteger,
	parallelPortSecuritySettingsAtt10	DmiInteger
}

dMTFParallelPortsTable OBJECT-TYPE
	SYNTAX		SEQUENCE OF SdMTFParallelPorts
	ACCESS		not-accessible
	STATUS		mandatory
	DESCRIPTION	"This group defines the attributes for parallel ports in this
system."
	::= { dmtfSystemsMIF 10 }

dMTFParallelPortsEntry OBJECT-TYPE
	SYNTAX		SdMTFParallelPorts
	ACCESS		not-accessible
	STATUS		mandatory
	DESCRIPTION	"This group defines the attributes for parallel ports in this
system."
	INDEX		{ DmiCompId,DmiGroupId, parallelPortIndexAtt1 }
	::= { dMTFParallelPortsTable 1 }


dMTFParallelPortsState OBJECT-TYPE
	SYNTAX		INTEGER { 
		active(1),
		notInService(2),
		notReady(3),
		createAndGo(4),
		createAndWait(5),
		destroy(6)
	}
	ACCESS		read-write
	STATUS		mandatory
	REFERENCE "'DMTF|Parallel Ports|003' 0"
	::= { dMTFParallelPortsEntry 0 }

parallelPortIndexAtt1 OBJECT-TYPE
	SYNTAX		DmiInteger
	ACCESS		read-only
	STATUS		mandatory
	DESCRIPTION	"An index into the parallel ports table."
	REFERENCE "'DMTF|Parallel Ports|003' 1"
	::= { dMTFParallelPortsEntry 1 }

parallelBaseIOAddressAtt2 OBJECT-TYPE
	SYNTAX		Dmi-Integer64
	ACCESS		read-only
	STATUS		mandatory
	DESCRIPTION	"Base I/O address for this parallel port."
	REFERENCE "'DMTF|Parallel Ports|003' 2"
	::= { dMTFParallelPortsEntry 2 }

iRQUsedAtt3-1 OBJECT-TYPE
	SYNTAX		DmiInteger
	ACCESS		read-only
	STATUS		mandatory
	DESCRIPTION	"IRQ number that is being used by this parallel port."
	REFERENCE "'DMTF|Parallel Ports|003' 3"
	::= { dMTFParallelPortsEntry 3 }

logicalNameAtt4-1 OBJECT-TYPE
	SYNTAX		DmiDisplaystring
	ACCESS		read-only
	STATUS		mandatory
	DESCRIPTION	"The logical name of the I/O device on this parallel port,
under this operating environment."
	REFERENCE "'DMTF|Parallel Ports|003' 4"
	::= { dMTFParallelPortsEntry 4 }

connectorTypeAtt5-1 OBJECT-TYPE
	SYNTAX		INTEGER { 
		other(1),
		unknown(2),
		dB25Female(3),
		dB25Male(4),
		centronics(5),
		miniCentronics(6),
		proprietary(7),
		centronics14(160),
		dB36Female(161),
		miniCentronics20(162)
	}
	ACCESS		read-only
	STATUS		mandatory
	DESCRIPTION	"The connector used to interface with the I/O device on this
parallel port."
	REFERENCE "'DMTF|Parallel Ports|003' 5"
	::= { dMTFParallelPortsEntry 5 }

connectorPinoutAtt6 OBJECT-TYPE
	SYNTAX		INTEGER { 
		other(1),
		unknown(2),
		xTAT(3),
		pS2(4),
		iEEE1284(5),
		proprietary(6),
		pC98(160),
		pC98Hireso(161),
		pCH98(162),
		pC98Note(163),
		pC98Full(164)
	}
	ACCESS		read-only
	STATUS		mandatory
	DESCRIPTION	"The pinout used by the I/O device on this parallel port."
	REFERENCE "'DMTF|Parallel Ports|003' 6"
	::= { dMTFParallelPortsEntry 6 }

dMASupportAtt7 OBJECT-TYPE
	SYNTAX		INTEGER { 
		false(0),
		true(1)
	}
	ACCESS		read-only
	STATUS		mandatory
	DESCRIPTION	"If true, DMA is supported."
	REFERENCE "'DMTF|Parallel Ports|003' 7"
	::= { dMTFParallelPortsEntry 7 }

parallelPortCapabilitiesAtt8 OBJECT-TYPE
	SYNTAX		DmiInteger
	ACCESS		read-only
	STATUS		mandatory
	DESCRIPTION	"Capabilities of this parallel port. This is a bit field mask
with the bits defined as follows: 
 Bit 0 (2^0) set = XT/AT compatible, 

Bit 1 (2^1) set = PS/2 compatible, 
 Bit 2 (2^2) set = ECP, 
 Bit 3 (2^3)
set = EPP, 
 Bit 4 (2^4) set = PC-98, 
 Bit 5 (2^5) set = PC-98-Hireso, 

Bit 6 (2^6) set = PC-H98"
	REFERENCE "'DMTF|Parallel Ports|003' 8"
	::= { dMTFParallelPortsEntry 8 }

operationalGroupIndexAtt9-1 OBJECT-TYPE
	SYNTAX		DmiInteger
	ACCESS		read-only
	STATUS		mandatory
	DESCRIPTION	"The index into the Operational State Table for this device."
	REFERENCE "'DMTF|Parallel Ports|003' 9"
	::= { dMTFParallelPortsEntry 9 }

parallelPortSecuritySettingsAtt10 OBJECT-TYPE
	SYNTAX		INTEGER { 
		other(1),
		unknown(2),
		none(3),
		externalInterfaceLockedOut(4),
		externalInterfaceEnabled(5),
		bootBypass(6)
	}
	ACCESS		read-only
	STATUS		mandatory
	DESCRIPTION	"Attribute describing the current hardware security settings
on this device"
	REFERENCE "'DMTF|Parallel Ports|003' 10"
	::= { dMTFParallelPortsEntry 10 }

SdELLSystemsManagementSoftware ::= SEQUENCE { 
	productAtt1	DmiDisplaystring,
	versionAtt2	DmiDisplaystring,
	buildNumberAtt3	DmiInteger,
	descriptionAtt4	DmiDisplaystring,
	supportedProtocolsAtt5	DmiInteger,
	preferredProtocolAtt6	DmiInteger,
	dMIRPCTypesAtt7	DmiDisplaystring
}

dELLSystemsManagementSoftwareTable OBJECT-TYPE
	SYNTAX		SEQUENCE OF SdELLSystemsManagementSoftware
	ACCESS		not-accessible
	STATUS		mandatory
	DESCRIPTION	"This group defines the attributes of the management software
which instruments this component."
	::= { server2 400 }

dELLSystemsManagementSoftwareEntry OBJECT-TYPE
	SYNTAX		SdELLSystemsManagementSoftware
	ACCESS		not-accessible
	STATUS		mandatory
	DESCRIPTION	"This group defines the attributes of the management software
which instruments this component."
	INDEX		{ DmiCompId,DmiGroupId }
	::= { dELLSystemsManagementSoftwareTable 1 }


productAtt1 OBJECT-TYPE
	SYNTAX		DmiDisplaystring
	ACCESS		read-only
	STATUS		mandatory
	DESCRIPTION	"The name of the Systems Management Software product that
instruments this component."
	REFERENCE "'DELL|Systems Management Software|001' 1"
	::= { dELLSystemsManagementSoftwareEntry 1 }

versionAtt2 OBJECT-TYPE
	SYNTAX		DmiDisplaystring
	ACCESS		read-only
	STATUS		mandatory
	DESCRIPTION	"The version for the Systems Management Software."
	REFERENCE "'DELL|Systems Management Software|001' 2"
	::= { dELLSystemsManagementSoftwareEntry 2 }

buildNumberAtt3 OBJECT-TYPE
	SYNTAX		DmiInteger
	ACCESS		read-only
	STATUS		mandatory
	DESCRIPTION	"The build number of this Systems Management Software product."
	REFERENCE "'DELL|Systems Management Software|001' 3"
	::= { dELLSystemsManagementSoftwareEntry 3 }

descriptionAtt4 OBJECT-TYPE
	SYNTAX		DmiDisplaystring
	ACCESS		read-only
	STATUS		mandatory
	DESCRIPTION	"A description of this Systems Management Software product."
	REFERENCE "'DELL|Systems Management Software|001' 4"
	::= { dELLSystemsManagementSoftwareEntry 4 }

supportedProtocolsAtt5 OBJECT-TYPE
	SYNTAX		DmiInteger
	ACCESS		read-only
	STATUS		mandatory
	DESCRIPTION	"This is a bit map field which is used to list protocols which
can be used to access the systems management information.  This is a bit
map where a value of 1 indicates that the protocol is supported.  Values
are based on the Protocol-Type enum. Mappers will be listed in this list,
but not as preferred protocols."
	REFERENCE "'DELL|Systems Management Software|001' 5"
	::= { dELLSystemsManagementSoftwareEntry 5 }

preferredProtocolAtt6 OBJECT-TYPE
	SYNTAX		INTEGER { 
		sNMP(1),
		dMIRPC(2),
		cIMOM(4)
	}
	ACCESS		read-only
	STATUS		mandatory
	DESCRIPTION	"This is a field which is used to indicate which protocol
is the preferred method for gathering management information.  This is value
is set by the instrumentation based on performance and features of protocols
available."
	REFERENCE "'DELL|Systems Management Software|001' 6"
	::= { dELLSystemsManagementSoftwareEntry 6 }

dMIRPCTypesAtt7 OBJECT-TYPE
	SYNTAX		DmiDisplaystring
	ACCESS		read-only
	STATUS		mandatory
	DESCRIPTION	"This field describes the RPC type, if any, for instance DCE:ncac
-ip-tcp or ONC:tcpip. A semi-colon may seperate multiple supports, such as
DCE:ncasn-ip-tcp;ONC:tcpip. This field should be empty if DMI RPC is not
supported."
	REFERENCE "'DELL|Systems Management Software|001' 7"
	::= { dELLSystemsManagementSoftwareEntry 7 }

SdELLSystemsSummaryInformation ::= SEQUENCE { 
	operatingSystemAtt1	DmiInteger,
	systemClassAtt2	DmiInteger
}

dELLSystemsSummaryInformationTable OBJECT-TYPE
	SYNTAX		SEQUENCE OF SdELLSystemsSummaryInformation
	ACCESS		not-accessible
	STATUS		mandatory
	DESCRIPTION	"This group provides minimal summarization information about
a system."
	::= { server2 402 }

dELLSystemsSummaryInformationEntry OBJECT-TYPE
	SYNTAX		SdELLSystemsSummaryInformation
	ACCESS		not-accessible
	STATUS		mandatory
	DESCRIPTION	"This group provides minimal summarization information about
a system."
	INDEX		{ DmiCompId,DmiGroupId }
	::= { dELLSystemsSummaryInformationTable 1 }


operatingSystemAtt1 OBJECT-TYPE
	SYNTAX		INTEGER { 
		other(1),
		unknown(2),
		windowsNT(3),
		windows9x(4),
		iBMOS2(5),
		sCOUNIX(6),
		netware(7)
	}
	ACCESS		read-only
	STATUS		mandatory
	DESCRIPTION	"This is the operating system which is installed and running
on the system."
	REFERENCE "'DELL|Systems Summary Information|001' 1"
	::= { dELLSystemsSummaryInformationEntry 1 }

systemClassAtt2 OBJECT-TYPE
	SYNTAX		INTEGER { 
		other(1),
		unknown(2),
		workstation(3),
		server(4),
		desktop(5),
		portable(6),
		netPC(7)
	}
	ACCESS		read-only
	STATUS		mandatory
	DESCRIPTION	"This is the system type which is installed and running the
instrumentation."
	REFERENCE "'DELL|Systems Summary Information|001' 2"
	::= { dELLSystemsSummaryInformationEntry 2 }

SdellMemoryPrefailure ::= SEQUENCE { 
	dellMemoryPrefailureState INTEGER,
	memoryDeviceIndexAtt1	DmiInteger,
	resetMemoryDeviceErrorCountAndPrefailureStatusAtt2	DmiInteger
}

dellMemoryPrefailureTable OBJECT-TYPE
	SYNTAX		SEQUENCE OF SdellMemoryPrefailure
	ACCESS		not-accessible
	STATUS		mandatory
	DESCRIPTION	"This group provides information about a memory prefailure
condition described in the operational state of the memory device."
	::= { server2 403 }

dellMemoryPrefailureEntry OBJECT-TYPE
	SYNTAX		SdellMemoryPrefailure
	ACCESS		not-accessible
	STATUS		mandatory
	DESCRIPTION	"This group provides information about a memory prefailure
condition described in the operational state of the memory device."
	INDEX		{ DmiCompId,DmiGroupId, memoryDeviceIndexAtt1 }
	::= { dellMemoryPrefailureTable 1 }


dellMemoryPrefailureState OBJECT-TYPE
	SYNTAX		INTEGER { 
		active(1),
		notInService(2),
		notReady(3),
		createAndGo(4),
		createAndWait(5),
		destroy(6)
	}
	ACCESS		read-write
	STATUS		mandatory
	REFERENCE "'Dell|Memory Prefailure|001' 0"
	::= { dellMemoryPrefailureEntry 0 }

memoryDeviceIndexAtt1 OBJECT-TYPE
	SYNTAX		DmiInteger
	ACCESS		read-only
	STATUS		mandatory
	DESCRIPTION	"This is the index into the memory device table."
	REFERENCE "'Dell|Memory Prefailure|001' 1"
	::= { dellMemoryPrefailureEntry 1 }

resetMemoryDeviceErrorCountAndPrefailureStatusAtt2 OBJECT-TYPE
	SYNTAX		DmiInteger
	ACCESS		read-write
	STATUS		mandatory
	DESCRIPTION	"Writing a non-zero value to this field will reset the memory
device prefailure status and error count."
	REFERENCE "'Dell|Memory Prefailure|001' 2"
	::= { dellMemoryPrefailureEntry 2 }

dellTemperatureProbeEvSys OBJECT-TYPE
	SYNTAX		INTEGER { 
		other(0),
		unknown(1)
	}
	ACCESS		not-accessible
	STATUS		mandatory
	DESCRIPTION	""
	::= { dellTemperatureProbeTable 6 }

dellTemperatureProbeEvSub OBJECT-TYPE
	SYNTAX		INTEGER { 
		other(0),
		unknown(1)
	}
	ACCESS		not-accessible
	STATUS		mandatory
	DESCRIPTION	""
	::= { dellTemperatureProbeTable 7 }

dellTemperatureProbeEvSol OBJECT-TYPE
	SYNTAX		INTEGER { 
		other(1),
		unknown(2)
	}
	ACCESS		not-accessible
	STATUS		mandatory
	DESCRIPTION	""
	::= { dellTemperatureProbeTable 8 }

dellTemperatureProbeEvt1 TRAP-TYPE
	ENTERPRISE dellTemperatureProbeTable
	VARIABLES { 
		dmiEventDateTime,
		dmiCompId,
		dmiEventSeverity,
		dmiEventStateKey,
		dmiEventAssociatedGroup
,		dellTemperatureProbeEvSys
,		dellTemperatureProbeEvSub
,		dellTemperatureProbeEvSol
		}
	DESCRIPTION "coolingDeviceStatusChange"
	REFERENCE "'Dell|Temperature Probe|003' 1"
	::= 1

dellFanSensorEvSys OBJECT-TYPE
	SYNTAX		INTEGER { 
		other(0),
		unknown(1)
	}
	ACCESS		not-accessible
	STATUS		mandatory
	DESCRIPTION	""
	::= { dellFanSensorTable 6 }

dellFanSensorEvSub OBJECT-TYPE
	SYNTAX		INTEGER { 
		other(0),
		unknown(1)
	}
	ACCESS		not-accessible
	STATUS		mandatory
	DESCRIPTION	""
	::= { dellFanSensorTable 7 }

dellFanSensorEvSol OBJECT-TYPE
	SYNTAX		INTEGER { 
		other(1),
		unknown(2)
	}
	ACCESS		not-accessible
	STATUS		mandatory
	DESCRIPTION	""
	::= { dellFanSensorTable 8 }

dellFanSensorEvt1 TRAP-TYPE
	ENTERPRISE dellFanSensorTable
	VARIABLES { 
		dmiEventDateTime,
		dmiCompId,
		dmiEventSeverity,
		dmiEventStateKey,
		dmiEventAssociatedGroup
,		dellFanSensorEvSys
,		dellFanSensorEvSub
,		dellFanSensorEvSol
		}
	DESCRIPTION "coolingDeviceStatusChange"
	REFERENCE "'Dell|Fan Sensor|003' 1"
	::= 1

dellVoltageProbeEvSys OBJECT-TYPE
	SYNTAX		INTEGER { 
		other(0),
		unknown(1)
	}
	ACCESS		not-accessible
	STATUS		mandatory
	DESCRIPTION	""
	::= { dellVoltageProbeTable 6 }

dellVoltageProbeEvSub OBJECT-TYPE
	SYNTAX		INTEGER { 
		other(0),
		unknown(1)
	}
	ACCESS		not-accessible
	STATUS		mandatory
	DESCRIPTION	""
	::= { dellVoltageProbeTable 7 }

dellVoltageProbeEvSol OBJECT-TYPE
	SYNTAX		INTEGER { 
		other(1),
		unknown(2)
	}
	ACCESS		not-accessible
	STATUS		mandatory
	DESCRIPTION	""
	::= { dellVoltageProbeTable 8 }

dellVoltageProbeEvt1 TRAP-TYPE
	ENTERPRISE dellVoltageProbeTable
	VARIABLES { 
		dmiEventDateTime,
		dmiCompId,
		dmiEventSeverity,
		dmiEventStateKey,
		dmiEventAssociatedGroup
,		dellVoltageProbeEvSys
,		dellVoltageProbeEvSub
,		dellVoltageProbeEvSol
		}
	DESCRIPTION "powerSupplyStatusChange"
	REFERENCE "'Dell|Voltage Probe|002' 1"
	::= 1

dellCurrentProbeEvSys OBJECT-TYPE
	SYNTAX		INTEGER { 
		other(0),
		unknown(1)
	}
	ACCESS		not-accessible
	STATUS		mandatory
	DESCRIPTION	""
	::= { dellCurrentProbeTable 6 }

dellCurrentProbeEvSub OBJECT-TYPE
	SYNTAX		INTEGER { 
		other(0),
		unknown(1)
	}
	ACCESS		not-accessible
	STATUS		mandatory
	DESCRIPTION	""
	::= { dellCurrentProbeTable 7 }

dellCurrentProbeEvSol OBJECT-TYPE
	SYNTAX		INTEGER { 
		other(1),
		unknown(2)
	}
	ACCESS		not-accessible
	STATUS		mandatory
	DESCRIPTION	""
	::= { dellCurrentProbeTable 8 }

dellCurrentProbeEvt1 TRAP-TYPE
	ENTERPRISE dellCurrentProbeTable
	VARIABLES { 
		dmiEventDateTime,
		dmiCompId,
		dmiEventSeverity,
		dmiEventStateKey,
		dmiEventAssociatedGroup
,		dellCurrentProbeEvSys
,		dellCurrentProbeEvSub
,		dellCurrentProbeEvSol
		}
	DESCRIPTION "powerSupplyStatusChange"
	REFERENCE "'Dell|Current Probe|002' 1"
	::= 1

dellGlobalPowerUnitEvSys OBJECT-TYPE
	SYNTAX		INTEGER { 
		other(0),
		unknown(1)
	}
	ACCESS		not-accessible
	STATUS		mandatory
	DESCRIPTION	""
	::= { dellGlobalPowerUnitTable 6 }

dellGlobalPowerUnitEvSub OBJECT-TYPE
	SYNTAX		INTEGER { 
		other(0),
		unknown(1)
	}
	ACCESS		not-accessible
	STATUS		mandatory
	DESCRIPTION	""
	::= { dellGlobalPowerUnitTable 7 }

dellGlobalPowerUnitEvSol OBJECT-TYPE
	SYNTAX		INTEGER { 
		other(1),
		unknown(2)
	}
	ACCESS		not-accessible
	STATUS		mandatory
	DESCRIPTION	""
	::= { dellGlobalPowerUnitTable 8 }

dellGlobalPowerUnitEvt1 TRAP-TYPE
	ENTERPRISE dellGlobalPowerUnitTable
	VARIABLES { 
		dmiEventDateTime,
		dmiCompId,
		dmiEventSeverity,
		dmiEventStateKey,
		dmiEventAssociatedGroup
,		dellGlobalPowerUnitEvSys
,		dellGlobalPowerUnitEvSub
,		dellGlobalPowerUnitEvSol
		}
	DESCRIPTION "powerSupplyRedundancyChange"
	REFERENCE "'Dell|GlobalPowerUnit|003' 1"
	::= 1

dellGlobalPowerUnitEvt2 TRAP-TYPE
	ENTERPRISE dellGlobalPowerUnitTable
	VARIABLES { 
		dmiEventDateTime,
		dmiCompId,
		dmiEventSeverity,
		dmiEventStateKey,
		dmiEventAssociatedGroup
,		dellGlobalPowerUnitEvSys
,		dellGlobalPowerUnitEvSub
,		dellGlobalPowerUnitEvSol
		}
	DESCRIPTION "powerSupplyStatusChange"
	REFERENCE "'Dell|GlobalPowerUnit|003' 2"
	::= 2

dellSystemChassisExtensionEvSys OBJECT-TYPE
	SYNTAX		INTEGER { 
		other(0),
		unknown(1)
	}
	ACCESS		not-accessible
	STATUS		mandatory
	DESCRIPTION	""
	::= { dellSystemChassisExtensionTable 6 }

dellSystemChassisExtensionEvSub OBJECT-TYPE
	SYNTAX		INTEGER { 
		other(0),
		unknown(1)
	}
	ACCESS		not-accessible
	STATUS		mandatory
	DESCRIPTION	""
	::= { dellSystemChassisExtensionTable 7 }

dellSystemChassisExtensionEvSol OBJECT-TYPE
	SYNTAX		INTEGER { 
		other(1),
		unknown(2)
	}
	ACCESS		not-accessible
	STATUS		mandatory
	DESCRIPTION	""
	::= { dellSystemChassisExtensionTable 8 }

dellSystemChassisExtensionEvt1 TRAP-TYPE
	ENTERPRISE dellSystemChassisExtensionTable
	VARIABLES { 
		dmiEventDateTime,
		dmiCompId,
		dmiEventSeverity,
		dmiEventStateKey,
		dmiEventAssociatedGroup
,		dellSystemChassisExtensionEvSys
,		dellSystemChassisExtensionEvSub
,		dellSystemChassisExtensionEvSol
		}
	DESCRIPTION "memoryECCError"
	REFERENCE "'Dell|SystemChassisExtension|004' 1"
	::= 1

dMTFPhysicalContainerGlobalTableEvSys OBJECT-TYPE
	SYNTAX		INTEGER { 
		other(0),
		unknown(1)
	}
	ACCESS		not-accessible
	STATUS		mandatory
	DESCRIPTION	"The major functional aspect of the product causing the fault."
	::= { dMTFPhysicalContainerGlobalTableTable 6 }

dMTFPhysicalContainerGlobalTableEvSub OBJECT-TYPE
	SYNTAX		INTEGER { 
		other(0),
		unknown(1)
	}
	ACCESS		not-accessible
	STATUS		mandatory
	DESCRIPTION	"The minor functional aspect of the product causing the fault."
	::= { dMTFPhysicalContainerGlobalTableTable 7 }

dMTFPhysicalContainerGlobalTableEvt1 TRAP-TYPE
	ENTERPRISE dMTFPhysicalContainerGlobalTableTable
	VARIABLES { 
		dmiEventDateTime,
		dmiCompId,
		dmiEventSeverity,
		dmiEventStateKey,
		dmiEventAssociatedGroup
,		dMTFPhysicalContainerGlobalTableEvSys
,		dMTFPhysicalContainerGlobalTableEvSub
		}
	DESCRIPTION "securitySettingsChange"
	REFERENCE "'DMTF|Physical Container Global Table|002' 1"
	::= 1

dMTFPhysicalContainerGlobalTableEvt2 TRAP-TYPE
	ENTERPRISE dMTFPhysicalContainerGlobalTableTable
	VARIABLES { 
		dmiEventDateTime,
		dmiCompId,
		dmiEventSeverity,
		dmiEventStateKey,
		dmiEventAssociatedGroup
,		dMTFPhysicalContainerGlobalTableEvSys
,		dMTFPhysicalContainerGlobalTableEvSub
		}
	DESCRIPTION "powerSupplyStatusChange"
	REFERENCE "'DMTF|Physical Container Global Table|002' 2"
	::= 2

dMTFPhysicalContainerGlobalTableEvt3 TRAP-TYPE
	ENTERPRISE dMTFPhysicalContainerGlobalTableTable
	VARIABLES { 
		dmiEventDateTime,
		dmiCompId,
		dmiEventSeverity,
		dmiEventStateKey,
		dmiEventAssociatedGroup
,		dMTFPhysicalContainerGlobalTableEvSys
,		dMTFPhysicalContainerGlobalTableEvSub
		}
	DESCRIPTION "coolingDeviceStatusChange"
	REFERENCE "'DMTF|Physical Container Global Table|002' 3"
	::= 3

dMTFPhysicalContainerGlobalTableEvt4 TRAP-TYPE
	ENTERPRISE dMTFPhysicalContainerGlobalTableTable
	VARIABLES { 
		dmiEventDateTime,
		dmiCompId,
		dmiEventSeverity,
		dmiEventStateKey,
		dmiEventAssociatedGroup
,		dMTFPhysicalContainerGlobalTableEvSys
,		dMTFPhysicalContainerGlobalTableEvSub
		}
	DESCRIPTION "physicalDeviceStatusChange"
	REFERENCE "'DMTF|Physical Container Global Table|002' 4"
	::= 4

dMTFPhysicalContainerGlobalTableEvt5 TRAP-TYPE
	ENTERPRISE dMTFPhysicalContainerGlobalTableTable
	VARIABLES { 
		dmiEventDateTime,
		dmiCompId,
		dmiEventSeverity,
		dmiEventStateKey,
		dmiEventAssociatedGroup
,		dMTFPhysicalContainerGlobalTableEvSys
,		dMTFPhysicalContainerGlobalTableEvSub
		}
	DESCRIPTION "logicalDeviceStatusChange"
	REFERENCE "'DMTF|Physical Container Global Table|002' 5"
	::= 5

dMTFPhysicalContainerGlobalTableEvt6 TRAP-TYPE
	ENTERPRISE dMTFPhysicalContainerGlobalTableTable
	VARIABLES { 
		dmiEventDateTime,
		dmiCompId,
		dmiEventSeverity,
		dmiEventStateKey,
		dmiEventAssociatedGroup
,		dMTFPhysicalContainerGlobalTableEvSys
,		dMTFPhysicalContainerGlobalTableEvSub
		}
	DESCRIPTION "containerSecurityBreach"
	REFERENCE "'DMTF|Physical Container Global Table|002' 6"
	::= 6

dMTFPhysicalContainerGlobalTableEvt7 TRAP-TYPE
	ENTERPRISE dMTFPhysicalContainerGlobalTableTable
	VARIABLES { 
		dmiEventDateTime,
		dmiCompId,
		dmiEventSeverity,
		dmiEventStateKey,
		dmiEventAssociatedGroup
,		dMTFPhysicalContainerGlobalTableEvSys
,		dMTFPhysicalContainerGlobalTableEvSub
		}
	DESCRIPTION "configurationError"
	REFERENCE "'DMTF|Physical Container Global Table|002' 7"
	::= 7

dellSystemResetEvSys OBJECT-TYPE
	SYNTAX		INTEGER { 
		other(0),
		unknown(1)
	}
	ACCESS		not-accessible
	STATUS		mandatory
	DESCRIPTION	""
	::= { dellSystemResetTable 6 }

dellSystemResetEvSub OBJECT-TYPE
	SYNTAX		INTEGER { 
		other(0),
		unknown(1)
	}
	ACCESS		not-accessible
	STATUS		mandatory
	DESCRIPTION	""
	::= { dellSystemResetTable 7 }

dellSystemResetEvSol OBJECT-TYPE
	SYNTAX		INTEGER { 
		other(1),
		unknown(2)
	}
	ACCESS		not-accessible
	STATUS		mandatory
	DESCRIPTION	""
	::= { dellSystemResetTable 8 }

dellSystemResetEvt1 TRAP-TYPE
	ENTERPRISE dellSystemResetTable
	VARIABLES { 
		dmiEventDateTime,
		dmiCompId,
		dmiEventSeverity,
		dmiEventStateKey,
		dmiEventAssociatedGroup
,		dellSystemResetEvSys
,		dellSystemResetEvSub
,		dellSystemResetEvSol
		}
	DESCRIPTION "systemUp"
	REFERENCE "'Dell|System Reset|001' 1"
	::= 1

dMTFCoolingDeviceEvSys OBJECT-TYPE
	SYNTAX		INTEGER { 
		other(0),
		unknown(1)
	}
	ACCESS		not-accessible
	STATUS		mandatory
	DESCRIPTION	"The major functional aspect of the product causing the fault."
	::= { dMTFCoolingDeviceTable 6 }

dMTFCoolingDeviceEvSub OBJECT-TYPE
	SYNTAX		INTEGER { 
		other(0),
		unknown(1)
	}
	ACCESS		not-accessible
	STATUS		mandatory
	DESCRIPTION	"The minor functional aspect of the product causing the fault."
	::= { dMTFCoolingDeviceTable 7 }

dMTFCoolingDeviceEvt1 TRAP-TYPE
	ENTERPRISE dMTFCoolingDeviceTable
	VARIABLES { 
		dmiEventDateTime,
		dmiCompId,
		dmiEventSeverity,
		dmiEventStateKey,
		dmiEventAssociatedGroup
,		dMTFCoolingDeviceEvSys
,		dMTFCoolingDeviceEvSub
		}
	DESCRIPTION "coolingDeviceStatusChange"
	REFERENCE "'DMTF|Cooling Device|002' 1"
	::= 1

dMTFCoolingDeviceEvt2 TRAP-TYPE
	ENTERPRISE dMTFCoolingDeviceTable
	VARIABLES { 
		dmiEventDateTime,
		dmiCompId,
		dmiEventSeverity,
		dmiEventStateKey,
		dmiEventAssociatedGroup
,		dMTFCoolingDeviceEvSys
,		dMTFCoolingDeviceEvSub
		}
	DESCRIPTION "temperatureFault"
	REFERENCE "'DMTF|Cooling Device|002' 2"
	::= 2

dMTFElectricalCurrentProbeEvSys OBJECT-TYPE
	SYNTAX		INTEGER { 
		other(0),
		unknown(1)
	}
	ACCESS		not-accessible
	STATUS		mandatory
	DESCRIPTION	"The major functional aspect of the product causing the fault."
	::= { dMTFElectricalCurrentProbeTable 6 }

dMTFElectricalCurrentProbeEvSub OBJECT-TYPE
	SYNTAX		INTEGER { 
		other(0),
		unknown(1)
	}
	ACCESS		not-accessible
	STATUS		mandatory
	DESCRIPTION	"The minor functional aspect of the product causing the fault."
	::= { dMTFElectricalCurrentProbeTable 7 }

dMTFElectricalCurrentProbeEvt1 TRAP-TYPE
	ENTERPRISE dMTFElectricalCurrentProbeTable
	VARIABLES { 
		dmiEventDateTime,
		dmiCompId,
		dmiEventSeverity,
		dmiEventStateKey,
		dmiEventAssociatedGroup
,		dMTFElectricalCurrentProbeEvSys
,		dMTFElectricalCurrentProbeEvSub
		}
	DESCRIPTION "powerSupplyStatusChange"
	REFERENCE "'DMTF|Electrical Current Probe|001' 1"
	::= 1

dMTFElectricalCurrentProbeEvt2 TRAP-TYPE
	ENTERPRISE dMTFElectricalCurrentProbeTable
	VARIABLES { 
		dmiEventDateTime,
		dmiCompId,
		dmiEventSeverity,
		dmiEventStateKey,
		dmiEventAssociatedGroup
,		dMTFElectricalCurrentProbeEvSys
,		dMTFElectricalCurrentProbeEvSub
		}
	DESCRIPTION "coolingDeviceStatusChange"
	REFERENCE "'DMTF|Electrical Current Probe|001' 2"
	::= 2

dMTFPhysicalMemoryArrayEvSys OBJECT-TYPE
	SYNTAX		INTEGER { 
		other(0),
		unknown(1)
	}
	ACCESS		not-accessible
	STATUS		mandatory
	DESCRIPTION	"The major functional aspect of the product causing the fault."
	::= { dMTFPhysicalMemoryArrayTable 6 }

dMTFPhysicalMemoryArrayEvSub OBJECT-TYPE
	SYNTAX		INTEGER { 
		other(0),
		unknown(1)
	}
	ACCESS		not-accessible
	STATUS		mandatory
	DESCRIPTION	"The minor functional aspect of the product causing the fault."
	::= { dMTFPhysicalMemoryArrayTable 7 }

dMTFPhysicalMemoryArrayEvt1 TRAP-TYPE
	ENTERPRISE dMTFPhysicalMemoryArrayTable
	VARIABLES { 
		dmiEventDateTime,
		dmiCompId,
		dmiEventSeverity,
		dmiEventStateKey,
		dmiEventAssociatedGroup
,		dMTFPhysicalMemoryArrayEvSys
,		dMTFPhysicalMemoryArrayEvSub
		}
	DESCRIPTION "memoryError"
	REFERENCE "'DMTF|Physical Memory Array|001' 1"
	::= 1

dMTFPhysicalMemoryArrayEvt2 TRAP-TYPE
	ENTERPRISE dMTFPhysicalMemoryArrayTable
	VARIABLES { 
		dmiEventDateTime,
		dmiCompId,
		dmiEventSeverity,
		dmiEventStateKey,
		dmiEventAssociatedGroup
,		dMTFPhysicalMemoryArrayEvSys
,		dMTFPhysicalMemoryArrayEvSub
		}
	DESCRIPTION "initializationFailure"
	REFERENCE "'DMTF|Physical Memory Array|001' 2"
	::= 2

dMTFPowerSupplyEvSys OBJECT-TYPE
	SYNTAX		INTEGER { 
		other(0),
		unknown(1)
	}
	ACCESS		not-accessible
	STATUS		mandatory
	DESCRIPTION	"The major functional aspect of the product causing the fault."
	::= { dMTFPowerSupplyTable 6 }

dMTFPowerSupplyEvSub OBJECT-TYPE
	SYNTAX		INTEGER { 
		other(0),
		unknown(1)
	}
	ACCESS		not-accessible
	STATUS		mandatory
	DESCRIPTION	"The minor functional aspect of the product causing the fault."
	::= { dMTFPowerSupplyTable 7 }

dMTFPowerSupplyEvt1 TRAP-TYPE
	ENTERPRISE dMTFPowerSupplyTable
	VARIABLES { 
		dmiEventDateTime,
		dmiCompId,
		dmiEventSeverity,
		dmiEventStateKey,
		dmiEventAssociatedGroup
,		dMTFPowerSupplyEvSys
,		dMTFPowerSupplyEvSub
		}
	DESCRIPTION "powerSupplyStatusChange"
	REFERENCE "'DMTF|Power Supply|002' 1"
	::= 1

dMTFPowerSupplyEvt2 TRAP-TYPE
	ENTERPRISE dMTFPowerSupplyTable
	VARIABLES { 
		dmiEventDateTime,
		dmiCompId,
		dmiEventSeverity,
		dmiEventStateKey,
		dmiEventAssociatedGroup
,		dMTFPowerSupplyEvSys
,		dMTFPowerSupplyEvSub
		}
	DESCRIPTION "powerControlRequest"
	REFERENCE "'DMTF|Power Supply|002' 2"
	::= 2

dMTFTemperatureProbeEvSys OBJECT-TYPE
	SYNTAX		INTEGER { 
		other(0),
		unknown(1)
	}
	ACCESS		not-accessible
	STATUS		mandatory
	DESCRIPTION	"The major functional aspect of the product causing the fault."
	::= { dMTFTemperatureProbeTable 6 }

dMTFTemperatureProbeEvSub OBJECT-TYPE
	SYNTAX		INTEGER { 
		other(0),
		unknown(1)
	}
	ACCESS		not-accessible
	STATUS		mandatory
	DESCRIPTION	"The minor functional aspect of the product causing the fault."
	::= { dMTFTemperatureProbeTable 7 }

dMTFTemperatureProbeEvt1 TRAP-TYPE
	ENTERPRISE dMTFTemperatureProbeTable
	VARIABLES { 
		dmiEventDateTime,
		dmiCompId,
		dmiEventSeverity,
		dmiEventStateKey,
		dmiEventAssociatedGroup
,		dMTFTemperatureProbeEvSys
,		dMTFTemperatureProbeEvSub
		}
	DESCRIPTION "coolingDeviceStatusChange"
	REFERENCE "'DMTF|Temperature Probe|001' 1"
	::= 1

dMTFVoltageProbeEvSys OBJECT-TYPE
	SYNTAX		INTEGER { 
		other(0),
		unknown(1)
	}
	ACCESS		not-accessible
	STATUS		mandatory
	DESCRIPTION	"The major functional aspect of the product causing the fault."
	::= { dMTFVoltageProbeTable 6 }

dMTFVoltageProbeEvSub OBJECT-TYPE
	SYNTAX		INTEGER { 
		other(0),
		unknown(1)
	}
	ACCESS		not-accessible
	STATUS		mandatory
	DESCRIPTION	"The minor functional aspect of the product causing the fault."
	::= { dMTFVoltageProbeTable 7 }

dMTFVoltageProbeEvt1 TRAP-TYPE
	ENTERPRISE dMTFVoltageProbeTable
	VARIABLES { 
		dmiEventDateTime,
		dmiCompId,
		dmiEventSeverity,
		dmiEventStateKey,
		dmiEventAssociatedGroup
,		dMTFVoltageProbeEvSys
,		dMTFVoltageProbeEvSub
		}
	DESCRIPTION "powerSupplyStatusChange"
	REFERENCE "'DMTF|Voltage Probe|001' 1"
	::= 1

END
