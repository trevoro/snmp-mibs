-- 	$Id: shiva-mlog.asn,v 1.4 1996/01/16 16:43:34 dfox Exp $

--
-- 	Copyright 1992, 1993, 1995, 1996 Shiva Corporation
--

-- This MIB has been replaced by the "LOG" MIB.
-- It is not included in LanRover/Access Switch and subsequent products.

SHIVA-MLOG-MIB DEFINITIONS ::= BEGIN

IMPORTS
      	TimeTicks
  		FROM RFC1155-SMI
    	DisplayString
    		FROM RFC1213-MIB
    	OBJECT-TYPE
    		FROM RFC-1212		-- Concise MIB Definitions
    	messageLog
    		FROM SHIVA-MIB;


--	The message log holds a list of ASCII strings
--	which correspond to the last N diagnostic messages
--	generated by the device.

    mLogEntryCount OBJECT-TYPE
	SYNTAX	INTEGER
	ACCESS  read-only
	STATUS  deprecated
	DESCRIPTION
		"The number of entries currently in the message log buffer."
	::= { messageLog 1 }

    mLogNewMessageTrapEnable OBJECT-TYPE
	SYNTAX	INTEGER {
		disabled(1),
		emerg(2),	-- system is unusable
		alert(3),	-- action must be taken immediately
		crit(4),	-- critical conditions
		err(5),		-- error conditions
		warning(6),	-- warning conditions
		notice(7),	-- normal but significant condition
		info(8),	-- informational
		debug(9)	-- debug-level messages
	}
	ACCESS  read-write
	STATUS  deprecated	--  unimplemented in K-STAR 9.0, 9.1, 9.2
	DESCRIPTION
		"Enables or disables the generation of mLogNewMessage Traps
		 of a priority numerically equal or lower than the value of 
		 this variable."
	DEFVAL { disabled }
	::= { messageLog 2 }

    mLogBuffer OBJECT-TYPE
	SYNTAX	SEQUENCE OF MLogEntry
	ACCESS  not-accessible
	STATUS  deprecated
	DESCRIPTION
		"A list of message log entries."
	::= { messageLog 3 }

    mLogMessage OBJECT-TYPE
	SYNTAX	MLogEntry
	ACCESS  not-accessible
	STATUS  deprecated
	DESCRIPTION
		"An entry in the message log.  Entries are indexed by
		counting integers.  Since the earliest messages are dropped
		from the log when it overflows, the first row in the table
		is not necessarily row 1.  Therefore, a Get-Next request
		should be issued to determine the index of the first row."
	INDEX	{ INTEGER }
	::= { mLogBuffer 1 }

    MLogEntry ::= SEQUENCE {
	mLogTimeStamp	TimeTicks,
	mLogPriority	INTEGER,
	mLogMessageText	DisplayString,
	mLogTimeOfDay	INTEGER
    }

    mLogTimeStamp OBJECT-TYPE
	SYNTAX	TimeTicks
	ACCESS  read-only
	STATUS  deprecated
	DESCRIPTION
		"The time the message was generated, measured in number of
		ticks since the device started."
	::= { mLogMessage 1 }

    mLogPriority OBJECT-TYPE
	SYNTAX	INTEGER {
		not-possible(1),
		emerg(2),	-- system is unusable
		alert(3),	-- action must be taken immediately
		crit(4),	-- critical conditions
		err(5),		-- error conditions
		warning(6),	-- warning conditions
		notice(7),	-- normal but significant condition
		info(8),	-- informational
		debug(9)	-- debug-level messages
	}
	ACCESS  read-only
	STATUS  deprecated
	DESCRIPTION
		"The priority of the log message.
		This field is for future use. All messages are
		currently logged at priority 'notice'"
	::= { mLogMessage 2 }

    mLogMessageText OBJECT-TYPE
	SYNTAX	DisplayString
	ACCESS  read-only
	STATUS  deprecated
	DESCRIPTION
		"The text of the log message."
	::= { mLogMessage 3 }

    mLogTimeOfDay OBJECT-TYPE
	SYNTAX	INTEGER
	ACCESS  read-only
	STATUS  deprecated
	DESCRIPTION
		"The time of day at which the message is logged.  This is
		expressed in seconds."
	::= { mLogMessage 4 }

END
