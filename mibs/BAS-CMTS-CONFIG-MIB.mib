BAS-CMTS-CONFIG-MIB DEFINITIONS ::= BEGIN

IMPORTS
	MODULE-IDENTITY, OBJECT-TYPE,
        IpAddress, Counter32, Unsigned32, 
	Integer32, TimeTicks					FROM SNMPv2-SMI
	TEXTUAL-CONVENTION,
        MacAddress,  
	TruthValue						FROM SNMPv2-TC
	ifIndex							FROM IF-MIB
	docsIfCmtsModulationEntry,
	docsIfDownstreamChannelEntry,
        docsIfCmtsServiceEntry,
	docsIfUpstreamChannelEntry,
	docsIfCmtsCmStatusEntry					FROM DOCS-IF-MIB
	basDocsIfCmtsCmStatusEntry				FROM BAS-ALIAS-DOCS-IF-MIB
	basExtCmts						FROM BAS-MIB;


basCmtsConfigMib MODULE-IDENTITY
	LAST-UPDATED "9810071415Z"
	ORGANIZATION "Broadband Access Systems"
	CONTACT-INFO
		" Tech Support
		  Broadband Access Systems
		  201 Forest Street
		  Marlboro, MA  01752
		  U.S.A.
		  
		  508-485-8200
		  support@basystems.com"
	DESCRIPTION
		"This MIB module defines the configuration MIB objects
		 for a Broadband Access System CMTS."
	::= { basExtCmts 1 }


   basCmtsConfigObjects OBJECT IDENTIFIER ::= { basCmtsConfigMib 1 }
   basCmtsDecodeObjects OBJECT IDENTIFIER ::= { basCmtsConfigMib 2 }
   basCmtsMacToSidObjects OBJECT IDENTIFIER ::= { basCmtsConfigMib 3 }


   BasCmtsInt8 ::= TEXTUAL-CONVENTION
       DISPLAY-HINT "d"
       STATUS      current
       DESCRIPTION
           "Range of INTEGER(-127..128)."
       SYNTAX      Integer32 (-127..128)

   BasCmtsUInt8 ::= TEXTUAL-CONVENTION
       DISPLAY-HINT "d"
       STATUS      current
       DESCRIPTION
           "Range of INTEGER(0..255)."
       SYNTAX      Integer32 (0..255)

   BasCmtsByte ::= TEXTUAL-CONVENTION
       DISPLAY-HINT "d"
       STATUS      current
       DESCRIPTION
           "Range of INTEGER(0..255)."
       SYNTAX      BasCmtsUInt8

   BasCmtsInt16 ::= TEXTUAL-CONVENTION
       DISPLAY-HINT "d"
       STATUS      current
       DESCRIPTION
           "Range of INTEGER(-32768..32767)."
       SYNTAX      Integer32 (-32768..32767)

   BasCmtsUInt16 ::= TEXTUAL-CONVENTION
       DISPLAY-HINT "d"
       STATUS      current
       DESCRIPTION
           "Range of INTEGER(0..0x7fff)."
       SYNTAX      Integer32 (0..'ffff'h)

   BasCmtsInt32 ::= TEXTUAL-CONVENTION
       DISPLAY-HINT "d"
       STATUS      current
       DESCRIPTION
           "Range of Integer32"
       SYNTAX      Integer32 

   BasCmtsUInt32 ::= TEXTUAL-CONVENTION
       DISPLAY-HINT "d"
       STATUS      current
       DESCRIPTION
           "Range of INTEGER(0..0x7fffffff)."
       SYNTAX      Integer32 (0..'7fffffff'h)

   BasCmtsRowAction ::= TEXTUAL-CONVENTION
       DISPLAY-HINT "d"
       STATUS      current
       DESCRIPTION
           "Defines Bas Cmts row action."
       SYNTAX      INTEGER {
           basCmtsRowActionNone(1),
           basCmtsRowActionApply(2)
        }

   TenthdBmV ::= TEXTUAL-CONVENTION
        DISPLAY-HINT "d-1"
        STATUS       current
        DESCRIPTION
            "This data type represents power levels that are normally
             expressed in dBmV. Units are in tenths of a dBmV;
             for example, 5.1 dBmV will be represented as 51."
        SYNTAX       Integer32

   --
   -- ----------------------------------------------------------------------
   --
   -- Bas HeadEndMgr Configuration Object
   --
   -- ----------------------------------------------------------------------
   --

   BasCmtsHeadEndMapMode ::= TEXTUAL-CONVENTION
       DISPLAY-HINT "d"
       STATUS      current
       DESCRIPTION
           "HeadEndMgr map mode.  
              0  = Normal, free running maps.
              99 = Scripted maps for test and debug."
       SYNTAX      Integer32 (0 | 99)

   BasCmtsHeadEndMacAddr ::= TEXTUAL-CONVENTION
       DISPLAY-HINT "d"
       STATUS      current
       DESCRIPTION
           "HeadEndMgr MacAddress."
       SYNTAX      OCTET STRING (SIZE(0..5))

   BasCmtsHeadEndAuthString ::= TEXTUAL-CONVENTION
       DISPLAY-HINT "d"
       STATUS      current
       DESCRIPTION
           "HeadEndMgr Authorization String."
       SYNTAX      OCTET STRING (SIZE(0..255))

   basCmtsHeadEndTable OBJECT-TYPE
       SYNTAX      SEQUENCE OF BasCmtsHeadEndEntry
       MAX-ACCESS  not-accessible
       STATUS      current
       DESCRIPTION
               "A list of HeadEndMgr settings.  The number of entries
               is given by the value of ifNumber."
       ::= { basCmtsConfigObjects 1 }

   basCmtsHeadEndEntry OBJECT-TYPE
       SYNTAX      BasCmtsHeadEndEntry
       MAX-ACCESS  not-accessible
       STATUS      current
       DESCRIPTION
               "An entry containing HeadEndMgr configuration settings.
                An entry in this table exists for each ifEntry with an 
                ifType of docsCableMacLayer(127)."
       INDEX   { ifIndex }
       ::= { basCmtsHeadEndTable 1 }

   BasCmtsHeadEndEntry ::=
       SEQUENCE {
           basCmtsHeDsChanId                  BasCmtsByte,
           basCmtsHeHwMapTimerPeriodMicrosec  BasCmtsUInt16,
           basCmtsHeImMapTimerPeriodMillisec  BasCmtsUInt16,
           basCmtsHePerRngTimerPeriodSec      BasCmtsUInt16,
           basCmtsHeUcdTimerPerMillisec       BasCmtsUInt16,
           basCmtsHeMapMode                   BasCmtsHeadEndMapMode,
           basCmtsHeMacAddr                   BasCmtsHeadEndMacAddr,
           basCmtsHeLenAuthString             BasCmtsByte,
           basCmtsHeAuthString                BasCmtsHeadEndAuthString,
           basCmtsHeRowAction                 BasCmtsRowAction,
           basCmtsHePlantPropDelay            BasCmtsUInt32,
           basCmtsHeSupplMapLeadDelay         BasCmtsInt32
       }

   basCmtsHeDsChanId OBJECT-TYPE
       SYNTAX      BasCmtsByte
       MAX-ACCESS  read-write
       STATUS      current
       DESCRIPTION
               "CMTS downstream channel ID."
       DEFVAL { 0 }
       ::= { basCmtsHeadEndEntry 1 }

   basCmtsHeHwMapTimerPeriodMicrosec OBJECT-TYPE
       SYNTAX      BasCmtsUInt16
       MAX-ACCESS  read-write
       STATUS      current
       DESCRIPTION
               "CMTS hardware Map timer period interval, in microseconds."
       DEFVAL { 2000 }
       ::= { basCmtsHeadEndEntry 2 }

   basCmtsHeImMapTimerPeriodMillisec OBJECT-TYPE
       SYNTAX      BasCmtsUInt16
       MAX-ACCESS  read-write
       STATUS      current
       DESCRIPTION
               "CMTS initial maintenance timer period interval, in milliseconds."
       DEFVAL { 2000 }
       ::= { basCmtsHeadEndEntry 3 }

   basCmtsHePerRngTimerPeriodSec OBJECT-TYPE
       SYNTAX      BasCmtsUInt16
       MAX-ACCESS  read-write
       STATUS      current
       DESCRIPTION
               "CMTS periodic ranging timer period interval, in seconds."
       ::= { basCmtsHeadEndEntry 4 }

   basCmtsHeUcdTimerPerMillisec OBJECT-TYPE
       SYNTAX      BasCmtsUInt16
       MAX-ACCESS  read-write
       STATUS      current
       DESCRIPTION
               "CMTS UCD periodic timer period interval, in milliseconds."
       DEFVAL { 2000 }
       ::= { basCmtsHeadEndEntry 5 }

   basCmtsHeMapMode OBJECT-TYPE
       SYNTAX      BasCmtsHeadEndMapMode
       MAX-ACCESS  read-write
       STATUS      current
       DESCRIPTION
               "CMTS mape mode, either Normal or Scripted maps for test mode.
                Defaults to normal, free-running mode."
       DEFVAL { 0 }
       ::= { basCmtsHeadEndEntry 6 }

   basCmtsHeMacAddr OBJECT-TYPE
       SYNTAX      BasCmtsHeadEndMacAddr
       MAX-ACCESS  read-only
       STATUS      current
       DESCRIPTION
               "CMTS HeadEndMgr Mac address."
       ::= { basCmtsHeadEndEntry 7 }

   basCmtsHeLenAuthString OBJECT-TYPE
       SYNTAX      BasCmtsByte
       MAX-ACCESS  read-write
       STATUS      current
       DESCRIPTION
               "CMTS HeadEndMgr authorization string length."
       DEFVAL { 0 }
       ::= { basCmtsHeadEndEntry 8 }

   basCmtsHeAuthString OBJECT-TYPE
       SYNTAX      BasCmtsHeadEndAuthString
       MAX-ACCESS  read-write
       STATUS      current
       DESCRIPTION
               "CMTS HeadEndMgr authorization string."
       DEFVAL { '0'b }
       ::= { basCmtsHeadEndEntry 9 }

   basCmtsHeRowAction OBJECT-TYPE
       SYNTAX      BasCmtsRowAction
       MAX-ACCESS  read-write
       STATUS      current
       DESCRIPTION
               "An action object used to effect an action."
       ::= { basCmtsHeadEndEntry 10 }

   basCmtsHePlantPropDelay OBJECT-TYPE
       SYNTAX      BasCmtsUInt32
       MAX-ACCESS  read-write
       STATUS      current
       DESCRIPTION
               "Plant propagation delay in microseconds."
       ::= { basCmtsHeadEndEntry 11 }

   basCmtsHeSupplMapLeadDelay OBJECT-TYPE
       SYNTAX      BasCmtsInt32
       MAX-ACCESS  read-write
       STATUS      current
       DESCRIPTION
               "Supplemental map lead delay."
       ::= { basCmtsHeadEndEntry 12 }

   --
   -- ----------------------------------------------------------------------
   --
   -- Bas Mac Configuration Object
   --
   -- ----------------------------------------------------------------------
   --

   basCmtsMacTable OBJECT-TYPE
       SYNTAX      SEQUENCE OF BasCmtsMacEntry
       MAX-ACCESS  not-accessible
       STATUS      current
       DESCRIPTION
               "A list of BAS Mac settings. "
       ::= { basCmtsConfigObjects 2 }

   basCmtsMacEntry OBJECT-TYPE
       SYNTAX      BasCmtsMacEntry
       MAX-ACCESS  not-accessible
       STATUS      current
       DESCRIPTION
               "An entry containing BAS Mac configuration settings.
                An entry in this table exists for each ifEntry with an 
                ifType of docsCableMacLayer(127)."
       INDEX   { ifIndex }
       ::= { basCmtsMacTable 1 }

   BasCmtsMacEntry ::=
       SEQUENCE {
           basCmtsMacNumUsBds                        BasCmtsUInt16 (1..64),
           basCmtsMacNumDsMsgBds                     BasCmtsUInt16 (1..64),
           basCmtsMacNumDsDataBds                    BasCmtsUInt16 (1..64),
           basCmtsMacNumIpBuffers                    BasCmtsUInt16 (1..128),
           basCmtsMacPciDmaSize                      BasCmtsByte,
           basCmtsMacUpdateFirstParticleLast         TruthValue,
           basCmtsMacDirectModeDma                   TruthValue,
           basCmtsMacPackedPart                      TruthValue,
           basCmtsMacPackedPartOffset                BasCmtsUInt16,
           basCmtsMacSpiClkDivider                   BasCmtsByte,
           basCmtsMacSyncRate                        BasCmtsUInt32,
           basCmtsMacRowAction                       BasCmtsRowAction
       }

   basCmtsMacNumUsBds OBJECT-TYPE
       SYNTAX      BasCmtsUInt16 (1..64)
       MAX-ACCESS  read-write
       STATUS      current
       DESCRIPTION
               "Number of buffers allocated to handle upstream cable modem traffic,
                both control message and data message traffic."
       DEFVAL { 32 }
       ::= { basCmtsMacEntry 1 }

   basCmtsMacNumDsMsgBds OBJECT-TYPE
       SYNTAX      BasCmtsUInt16 (1..64)
       MAX-ACCESS  read-write
       STATUS      current
       DESCRIPTION
               "Number of buffers allocated to handle downstream cable modem 
                control message traffic."
       DEFVAL { 32 }
       ::= { basCmtsMacEntry 2 }

   basCmtsMacNumDsDataBds OBJECT-TYPE
       SYNTAX      BasCmtsUInt16 (1..64)
       MAX-ACCESS  read-write
       STATUS      current
       DESCRIPTION
               "Number of buffers allocated to handle downstream cable modem 
                data message traffic."
       DEFVAL { 32 }
       ::= { basCmtsMacEntry 3 }

   basCmtsMacNumIpBuffers OBJECT-TYPE
       SYNTAX      BasCmtsUInt16 (1..128)
       MAX-ACCESS  read-write
       STATUS      current
       DESCRIPTION
               "Number of buffers allocated to handle downstream cable modem 
                data message traffic.
                If an IP packet is addressed to the CMTS Mac address, 
                an IP Buffer is allocated to send the data to the local host IP stack
                (bcmnet_fd). 
                TBD - We probably don't need this."
       DEFVAL { 32 }
       ::= { basCmtsMacEntry 4 }


   basCmtsMacPciDmaSize OBJECT-TYPE
       SYNTAX      BasCmtsByte 
       MAX-ACCESS  read-write
       STATUS      current
       DESCRIPTION
               "Maximum size of PCI bus DMA transaction, required by 
                BCM3210.  "
       DEFVAL { '80'h }
       ::= { basCmtsMacEntry 5 }

   basCmtsMacUpdateFirstParticleLast OBJECT-TYPE
       SYNTAX      TruthValue
       MAX-ACCESS  read-write
       STATUS      current
       DESCRIPTION

               "MAC control register option flag: if true, then update 
                first particle last."
       DEFVAL { true }
       ::= { basCmtsMacEntry 6 }

   basCmtsMacDirectModeDma OBJECT-TYPE
       SYNTAX      TruthValue
       MAX-ACCESS  read-write
       STATUS      current
       DESCRIPTION
               "MAC control register option flag: if true, then enable 
                direct mode DMA."
       DEFVAL { true }
       ::= { basCmtsMacEntry 7 }

   basCmtsMacPackedPart OBJECT-TYPE
       SYNTAX      TruthValue
       MAX-ACCESS  read-write
       STATUS      current
       DESCRIPTION
               "Packed particle boolean, FALSE indicates 1 particle per packet."
       DEFVAL { true }
       ::= { basCmtsMacEntry 8 }

   basCmtsMacPackedPartOffset OBJECT-TYPE
       SYNTAX      BasCmtsUInt16
       MAX-ACCESS  read-write
       STATUS      current
       DESCRIPTION
               "Packed particle offset, offset for header length in packed 
                particle."
       DEFVAL { 12 }
       ::= { basCmtsMacEntry 9 }

   basCmtsMacSpiClkDivider OBJECT-TYPE
       SYNTAX      BasCmtsByte
       MAX-ACCESS  read-write
       STATUS      current
       DESCRIPTION
               "Specifies the SPI Clock Divider."
       DEFVAL { '10'h }
       ::= { basCmtsMacEntry 10 }

   basCmtsMacSyncRate OBJECT-TYPE
       SYNTAX      BasCmtsUInt32
       MAX-ACCESS  read-write
       STATUS      current
       DESCRIPTION
               "Specifies the downstream Sync control message interval.
                Units are millisec.  Default rate is 10 millisec."
       DEFVAL { 10 }
       ::= { basCmtsMacEntry 11 }

   basCmtsMacRowAction OBJECT-TYPE
       SYNTAX      BasCmtsRowAction
       MAX-ACCESS  read-write
       STATUS      current
       DESCRIPTION
               "Row status."
       ::= { basCmtsMacEntry 12 }

   --
   -- ----------------------------------------------------------------------
   --
   -- BAS Mac DsHw Settings
   --
   -- ----------------------------------------------------------------------
   --

   basCmtsMacDsHwTable OBJECT-TYPE
       SYNTAX      SEQUENCE OF BasCmtsMacDsHwEntry
       MAX-ACCESS  not-accessible
       STATUS      current
       DESCRIPTION
               "A list of Bas Downstream settings."
       ::= { basCmtsConfigObjects 3 }

   basCmtsMacDsHwEntry OBJECT-TYPE
       SYNTAX      BasCmtsMacDsHwEntry
       MAX-ACCESS  not-accessible
       STATUS      current
       DESCRIPTION
               "An entry containing Bas Mac DsHw configuration settings.
                An entry in this table exists for each ifEntry with an 
                ifType of docsCableMacLayer(127)."
       AUGMENTS { basCmtsMacEntry }
       ::= { basCmtsMacDsHwTable 1 }

   BasCmtsMacDsHwEntry ::=
       SEQUENCE {
           basCmtsMacDsHwInterleaverDepth          INTEGER,
           basCmtsMacDsHwQamctl                    INTEGER,
           basCmtsMacDsHwSymbolRate                BasCmtsUInt32,
           basCmtsMacDsHwIfFreq                    BasCmtsUInt32,
           basCmtsMacDsHwRefFreq                   BasCmtsUInt32,
           basCmtsMacDsHwOscMultFactor             BasCmtsByte
       }

   basCmtsMacDsHwInterleaverDepth OBJECT-TYPE
       SYNTAX      INTEGER {
                     basCmtsMacDsHwIntDepth8(8),
                     basCmtsMacDsHwIntDepth16(16),
                     basCmtsMacDsHwIntDepth32(32),
                     basCmtsMacDsHwIntDepth64(64),
                     basCmtsMacDsHwIntDepth128(128)
                   }
       MAX-ACCESS  read-write
       STATUS      current
       DESCRIPTION
               "Specifies Mac DsHw interleaver depth."
       DEFVAL { 128 }
       ::= { basCmtsMacDsHwEntry 1 }

   basCmtsMacDsHwQamctl OBJECT-TYPE
       SYNTAX      INTEGER {
                     basCmtsMacDsHwQamctl64QAM(3),
                     basCmtsMacDsHwQamctl256QAM(5)
                   }
       MAX-ACCESS  read-write
       STATUS      current
       DESCRIPTION
               "Specifies Mac DsHw QAM control.
                  0x03 = 64 QAM
                  0x05 = 256 QAM."
       DEFVAL { 3 }
       ::= { basCmtsMacDsHwEntry 2 }

   basCmtsMacDsHwSymbolRate OBJECT-TYPE
       SYNTAX      BasCmtsUInt32
       MAX-ACCESS  read-write
       STATUS      current
       DESCRIPTION
               "Specifies Mac DsHw symbol rate, in Units Baud.
                Typical values:
                   64 QAM - 5056941 baud (default)
                  256 QAM - 5360537 baud"
       DEFVAL { 5056941 }
       ::= { basCmtsMacDsHwEntry 3 }

   basCmtsMacDsHwIfFreq OBJECT-TYPE
       SYNTAX      BasCmtsUInt32 
       MAX-ACCESS  read-write
       STATUS      current
       DESCRIPTION
               "Specifies Mac DsHw downstream channel frequency, in Hz."
       DEFVAL { 43750000 }
       ::= { basCmtsMacDsHwEntry 4 }

   basCmtsMacDsHwRefFreq OBJECT-TYPE
       SYNTAX      BasCmtsUInt32 
       MAX-ACCESS  read-write
       STATUS      current
       DESCRIPTION
               "Specifies Mac DsHw reference frequency, in Hz."
       DEFVAL { 28500000 }
       ::= { basCmtsMacDsHwEntry 5 }

   basCmtsMacDsHwOscMultFactor OBJECT-TYPE
       SYNTAX      BasCmtsByte
       MAX-ACCESS  read-write
       STATUS      current
       DESCRIPTION
               "Specifies Mac DsHw Osc Mult Factor.
                For Bcm3210, use:
                  refFreq (MHz)        MultFactor
                  -------------        ----------
                   114.0               1
                   28.5                4
                   28.322              4
                   20.48               6
                   "
       DEFVAL { 4 }
       ::= { basCmtsMacDsHwEntry 6 }

   --
   -- ----------------------------------------------------------------------
   --
   -- Bas Upstream Channel Settings
   --
   -- ----------------------------------------------------------------------
   --

   BasCmtsUpChannelPreamblePattern ::= TEXTUAL-CONVENTION
       DISPLAY-HINT "d"
       STATUS      current
       DESCRIPTION
           "Bas Upstream Channel Preamble Pattern."
       SYNTAX      OCTET STRING (SIZE(0..127))

   basCmtsUpstreamChannelTable OBJECT-TYPE
       SYNTAX      SEQUENCE OF BasCmtsUpstreamChannelEntry
       MAX-ACCESS  not-accessible
       STATUS      current
       DESCRIPTION
               "A list of HeadEndMgr settings.  The number of entries
               is given by the value of ifNumber."
       ::= { basCmtsConfigObjects 4 }

   basCmtsUpstreamChannelEntry OBJECT-TYPE
       SYNTAX      BasCmtsUpstreamChannelEntry
       MAX-ACCESS  not-accessible
       STATUS      current
       DESCRIPTION
               "An entry containing HeadEndMgr configuration settings.
                An entry in this table exists for each ifEntry with an 
                ifType of docsCableUpstream(129)."
       AUGMENTS { docsIfUpstreamChannelEntry }
       ::= { basCmtsUpstreamChannelTable 1 }

   BasCmtsUpstreamChannelEntry ::=
       SEQUENCE {
         basCmtsUpChannelMslotPerTick               BasCmtsByte,  
         basCmtsUpChannelSymbolRate160KSymPerSec    BasCmtsByte,
         basCmtsUpChannelLenPreamblePattern         BasCmtsByte,
         basCmtsUpChannelPreamblePattern            BasCmtsUpChannelPreamblePattern,
         basCmtsUpChannelRowAction                  BasCmtsRowAction,
         basCmtsUpChannelReceivePower               TenthdBmV
       }

   basCmtsUpChannelMslotPerTick OBJECT-TYPE
       SYNTAX      BasCmtsByte
       MAX-ACCESS  read-write
       STATUS      current
       DESCRIPTION
               "Minislot period, in ticks."
       DEFVAL { 4 }
       ::= { basCmtsUpstreamChannelEntry 1 }

   basCmtsUpChannelSymbolRate160KSymPerSec OBJECT-TYPE
       SYNTAX      BasCmtsByte
       MAX-ACCESS  read-write
       STATUS      current
       DESCRIPTION
               "Upstream channel symbol rate, in 1609KSym/second."
       DEFVAL { 8 }
       ::= { basCmtsUpstreamChannelEntry 2 }

   basCmtsUpChannelLenPreamblePattern OBJECT-TYPE
       SYNTAX      BasCmtsByte
       MAX-ACCESS  read-only
       STATUS      current
       DESCRIPTION
               "Upstream channel preamble pattern length."
       DEFVAL { 16 }
       ::= { basCmtsUpstreamChannelEntry 3 }

   basCmtsUpChannelPreamblePattern OBJECT-TYPE
       SYNTAX      BasCmtsUpChannelPreamblePattern
       MAX-ACCESS  read-only
       STATUS      current
       DESCRIPTION
               "Upstream channel preamble pattern."
       DEFVAL { 'CCCCCCCCCCCCCCCCCCCCCCCCCCCC0D0D'h }
       ::= { basCmtsUpstreamChannelEntry 4 }

   basCmtsUpChannelRowAction OBJECT-TYPE
       SYNTAX      BasCmtsRowAction
       MAX-ACCESS  read-write
       STATUS      current
       DESCRIPTION
               "Row status."
       ::= { basCmtsUpstreamChannelEntry 5 }

   basCmtsUpChannelReceivePower OBJECT-TYPE
       SYNTAX      TenthdBmV
       MAX-ACCESS  read-write
       STATUS      current
       DESCRIPTION
               "Receive Power level that is desired at the CMTS in TenthdbMV"
       ::= { basCmtsUpstreamChannelEntry 6 }

   --
   -- ----------------------------------------------------------------------
   --
   -- Bas Upstream Channel Burst Descriptor
   --
   -- ----------------------------------------------------------------------
   --

   BasCmtsModulationWsPattern ::= TEXTUAL-CONVENTION
       DISPLAY-HINT "d"
       STATUS      current
       DESCRIPTION
           "Bas upstream channel burst descriptor unique word pattern."
       SYNTAX      OCTET STRING (SIZE(0..127))

   basCmtsModulationTable OBJECT-TYPE
       SYNTAX      SEQUENCE OF BasCmtsModulationEntry
       MAX-ACCESS  not-accessible
       STATUS      current
       DESCRIPTION
               "A list of HeadEndMgr settings.  The number of entries
               is given by the value of ifNumber."
       ::= { basCmtsConfigObjects 5 }

   basCmtsModulationEntry OBJECT-TYPE
       SYNTAX      BasCmtsModulationEntry
       MAX-ACCESS  not-accessible
       STATUS      current
       DESCRIPTION
               "An entry containing HeadEndMgr configuration settings."
       AUGMENTS { docsIfCmtsModulationEntry }

       ::= { basCmtsModulationTable 1 }

   BasCmtsModulationEntry ::=
       SEQUENCE {
          basCmtsModUwLenBytes                      BasCmtsByte,
          basCmtsModUwPattern                       BasCmtsModulationWsPattern,
          basCmtsModUwDetectionWindow               BasCmtsByte,
          basCmtsModUwMismatchThresholdBits         BasCmtsByte,
          basCmtsModPreambleValueOffset             BasCmtsUInt16
       }


   basCmtsModUwLenBytes OBJECT-TYPE
       SYNTAX      BasCmtsByte
       MAX-ACCESS  read-write
       STATUS      current
       DESCRIPTION
               "Length of unique word pattern, in bytes.
                [Note = Supported values are 1-3 for BCM3137.
                Default value is 1, equal to 4 symbols."
       DEFVAL { 2 }
       ::= { basCmtsModulationEntry 1 }

   basCmtsModUwPattern OBJECT-TYPE
       SYNTAX      BasCmtsModulationWsPattern
       MAX-ACCESS  read-write
       STATUS      current
       DESCRIPTION
               "Content of unique word pattern.
                The number of bytes in the unique word pattern which are
                relevant is determined by basCmtsModUwLenBytes."
       DEFVAL { '0d0d'h }
       ::= { basCmtsModulationEntry 2 }

   basCmtsModUwDetectionWindow OBJECT-TYPE
       SYNTAX      BasCmtsByte
       MAX-ACCESS  read-write
       STATUS      current
       DESCRIPTION
               "Time window around a nominal detection time in
                which the UW detector is enabled."
       DEFVAL { '04'h }
       ::= { basCmtsModulationEntry 3 }

   basCmtsModUwMismatchThresholdBits OBJECT-TYPE
       SYNTAX      BasCmtsByte
       MAX-ACCESS  read-write
       STATUS      current
       DESCRIPTION
               "Specifies precision of match between unique word
                pattern and incoming burst by specifying the number 
                of bits which are allowed to NOT match."
       DEFVAL { 1 }
       ::= { basCmtsModulationEntry 4 }

   basCmtsModPreambleValueOffset OBJECT-TYPE
       SYNTAX      BasCmtsUInt16
       MAX-ACCESS  read-only
       STATUS      current
       DESCRIPTION
               "Offset into preamble where value bits, or pattern, begins."
       ::= { basCmtsModulationEntry 5 }

   --
   -- ----------------------------------------------------------------------
   --
   -- Bas Upstream Channel Bcm3137 Settings
   --
   -- ----------------------------------------------------------------------
   --

   basCmtsUsHwTable OBJECT-TYPE
       SYNTAX      SEQUENCE OF BasCmtsUsHwEntry
       MAX-ACCESS  not-accessible
       STATUS      current
       DESCRIPTION
               "A list of HeadEndMgr settings.  The number of entries
               is given by the value of ifNumber."
       ::= { basCmtsConfigObjects 6 }

   basCmtsUsHwEntry OBJECT-TYPE
       SYNTAX      BasCmtsUsHwEntry
       MAX-ACCESS  not-accessible
       STATUS      current
       DESCRIPTION
               "An entry containing HeadEndMgr configuration settings."
       AUGMENTS { basCmtsUpstreamChannelEntry }
       ::= { basCmtsUsHwTable 1 }

   BasCmtsUsHwEntry ::=
       SEQUENCE {
          basCmtsUsHwTestProbe             BasCmtsByte,
          basCmtsUsHwGenCfg1               BasCmtsByte,
          basCmtsUsHwGenCfg2               BasCmtsByte,
          basCmtsUsHwPreambleCtl           BasCmtsByte,
          basCmtsUsHwCarrAcf               BasCmtsByte,
          basCmtsUsHwCarrTcf               BasCmtsByte,
          basCmtsUsHwBaudAtcf              BasCmtsByte,
          basCmtsUsHwBaudIntcf             BasCmtsByte,
          basCmtsUsHwMaxPwrThr             BasCmtsByte,
          basCmtsUsHwMinPwrThr             BasCmtsUInt16,
          basCmtsUsHwTimeErrThr            BasCmtsUInt16,
          basCmtsUsHwAdcClipCtl            BasCmtsByte,
          basCmtsUsHwLoopCheck             BasCmtsByte,
          basCmtsUsHwSlcrErrThr            BasCmtsByte,
          basCmtsUsHwAfltSelThr            BasCmtsByte,
          basCmtsUsHwBurstGain             BasCmtsUInt16,
          basCmtsUsHwLoopCtl               BasCmtsByte,
          basCmtsUsHwEqRsCtl               BasCmtsByte,
          basCmtsUsHwEqSteps               BasCmtsByte
       }

   basCmtsUsHwTestProbe OBJECT-TYPE
       SYNTAX      BasCmtsByte
       MAX-ACCESS  read-write
       STATUS      current
       DESCRIPTION
               "Bas Bcm3137 test/probe mode register."
       DEFVAL { '06'h }
       ::= { basCmtsUsHwEntry 1 }

   basCmtsUsHwGenCfg1 OBJECT-TYPE
       SYNTAX      BasCmtsByte
       MAX-ACCESS  read-write
       STATUS      current
       DESCRIPTION
               "Bas Bcm3137 general configuration register 1."
       DEFVAL { '03'h }
       ::= { basCmtsUsHwEntry 2 }

   basCmtsUsHwGenCfg2 OBJECT-TYPE
       SYNTAX      BasCmtsByte
       MAX-ACCESS  read-write
       STATUS      current
       DESCRIPTION
               "Bas Bcm3137 general configuration register 2."
       DEFVAL { '3D'h }
       ::= { basCmtsUsHwEntry 3 }

   basCmtsUsHwPreambleCtl OBJECT-TYPE
       SYNTAX      BasCmtsByte
       MAX-ACCESS  read-write
       STATUS      current
       DESCRIPTION
               "Bas Bcm3137 preamble process control register."
       DEFVAL { '7D'h }
       ::= { basCmtsUsHwEntry 4 }

   basCmtsUsHwCarrAcf OBJECT-TYPE
       SYNTAX      BasCmtsByte
       MAX-ACCESS  read-write
       STATUS      current
       DESCRIPTION
               "Bas Bcm3137 carrier acquisition loop coefficients."
       DEFVAL { '23'h }
       ::= { basCmtsUsHwEntry 5 }

   basCmtsUsHwCarrTcf OBJECT-TYPE
       SYNTAX      BasCmtsByte
       MAX-ACCESS  read-write
       STATUS      current
       DESCRIPTION
               "Bas Bcm3137 carrier tracking loop coefficients."
       DEFVAL { '33'h }
       ::= { basCmtsUsHwEntry 6 }

   basCmtsUsHwBaudAtcf OBJECT-TYPE
       SYNTAX      BasCmtsByte
       MAX-ACCESS  read-write
       STATUS      current
       DESCRIPTION
               "Bas Bcm3137 baud loop acquisition/tracking coefficients."
       DEFVAL { '33'h }
       ::= { basCmtsUsHwEntry 7 }

   basCmtsUsHwBaudIntcf OBJECT-TYPE
       SYNTAX      BasCmtsByte
       MAX-ACCESS  read-write
       STATUS      current
       DESCRIPTION
               "Bas Bcm3137 baud loop integrator coefficients."
       DEFVAL { '01'h }
       ::= { basCmtsUsHwEntry 8 }

   basCmtsUsHwMaxPwrThr OBJECT-TYPE
       SYNTAX      BasCmtsByte
       MAX-ACCESS  read-write
       STATUS      current
       DESCRIPTION
               "Bas Bcm3137 maximum power level threshold."
       DEFVAL { '40'h }
       ::= { basCmtsUsHwEntry 9 }

   basCmtsUsHwMinPwrThr OBJECT-TYPE
       SYNTAX      BasCmtsUInt16
       MAX-ACCESS  read-write
       STATUS      current
       DESCRIPTION
               "Bas Bcm3137 minimum power level threshold."
       DEFVAL { '0080'h }
       ::= { basCmtsUsHwEntry 10 }

   basCmtsUsHwTimeErrThr OBJECT-TYPE
       SYNTAX      BasCmtsUInt16
       MAX-ACCESS  read-write
       STATUS      current
       DESCRIPTION
               "Bas Bcm3137 burst timing error threshold."
       DEFVAL { '0008'h }
       ::= { basCmtsUsHwEntry 11 }

   basCmtsUsHwAdcClipCtl OBJECT-TYPE
       SYNTAX      BasCmtsByte
       MAX-ACCESS  read-write
       STATUS      current
       DESCRIPTION
               "Bas Bcm3137 ADC clipping detection control register."
       DEFVAL { '08'h }
       ::= { basCmtsUsHwEntry 12 }

   basCmtsUsHwLoopCheck OBJECT-TYPE
       SYNTAX      BasCmtsByte
       MAX-ACCESS  read-write
       STATUS      current
       DESCRIPTION
               "Bas Bcm3137 loop checking detection control register."
       DEFVAL { '00'h }
       ::= { basCmtsUsHwEntry 13 }

   basCmtsUsHwSlcrErrThr OBJECT-TYPE
       SYNTAX      BasCmtsByte
       MAX-ACCESS  read-write
       STATUS      current
       DESCRIPTION
               "Bas Bcm3137 slicer error threshold."
       DEFVAL { '08'h }
       ::= { basCmtsUsHwEntry 14 }

   basCmtsUsHwAfltSelThr OBJECT-TYPE
       SYNTAX      BasCmtsByte
       MAX-ACCESS  read-write
       STATUS      current
       DESCRIPTION
               "Bas Bcm3137 amplitude filter selection threshold."
       DEFVAL { '1C'h }
       ::= { basCmtsUsHwEntry 15 }

   basCmtsUsHwBurstGain OBJECT-TYPE
       SYNTAX      BasCmtsUInt16
       MAX-ACCESS  read-write
       STATUS      current
       DESCRIPTION
               "Bas Bcm3137 burst gain adjusting factor register."
       DEFVAL { '0100'h }
       ::= { basCmtsUsHwEntry 16 }

   basCmtsUsHwLoopCtl OBJECT-TYPE
       SYNTAX      BasCmtsByte
       MAX-ACCESS  read-write
       STATUS      current
       DESCRIPTION
               "Bas Bcm3137 loop control register."
       DEFVAL { '14'h }
       ::= { basCmtsUsHwEntry 17 }

   basCmtsUsHwEqRsCtl OBJECT-TYPE
       SYNTAX      BasCmtsByte
       MAX-ACCESS  read-write
       STATUS      current
       DESCRIPTION
               "Bas Bcm3137 equalizer/RS decoder control register."
       DEFVAL { '10'h }
       ::= { basCmtsUsHwEntry 18 }

   basCmtsUsHwEqSteps OBJECT-TYPE
       SYNTAX      BasCmtsByte
       MAX-ACCESS  read-write
       STATUS      current
       DESCRIPTION
               "Bas Bcm3137 equalizer adaptation step size register."
       DEFVAL { '21'h }
       ::= { basCmtsUsHwEntry 19 }

   --
   -- ----------------------------------------------------------------------
   --
   -- Bas MapMaker Settings
   --
   -- ----------------------------------------------------------------------
   --


   basCmtsUsMapTable OBJECT-TYPE
       SYNTAX      SEQUENCE OF BasCmtsUsMapEntry
       MAX-ACCESS  not-accessible
       STATUS      current
       DESCRIPTION
               "A Upstream Channel Map Maker Settings."  
       ::= { basCmtsConfigObjects 7 }

   basCmtsUsMapEntry OBJECT-TYPE
       SYNTAX      BasCmtsUsMapEntry
       MAX-ACCESS  not-accessible
       STATUS      current
       DESCRIPTION
               "An entry containing Upstream Channel Map Maker configuration settings."
       AUGMENTS { basCmtsUpstreamChannelEntry }
       ::= { basCmtsUsMapTable 1 }

   BasCmtsUsMapEntry ::=
       SEQUENCE {
          basCmtsUsMapMaxMapLenHwMapPeriods           BasCmtsUInt16,
          basCmtsUsMapInitMainRegionSizeMicrosec      BasCmtsUInt16,
          basCmtsUsMapNewUcdGrantSizeMicrosec         BasCmtsUInt16,
          basCmtsUsMapMaxDeferredRngIE                BasCmtsUInt16,
          basCmtsUsMapMapLeadTimeMillisec             BasCmtsUInt16,
          basCmtsUsMapRequestLimitMslot               BasCmtsUInt16,
          basCmtsUsMapMapLeadTime                     BasCmtsUInt16
       }

   basCmtsUsMapMaxMapLenHwMapPeriods OBJECT-TYPE
       SYNTAX      BasCmtsUInt16
       MAX-ACCESS  read-write
       STATUS      current
       DESCRIPTION
               "Bas Upstream Channel MapMaker maximum map length, in units 
                of hardware map timer periods.
                [Note: Set this value large enough to handle large packets, 
                but small enough to not let latency get too large when 
                channel is busy.]"
       DEFVAL { 4 }
       ::= { basCmtsUsMapEntry 1 }

   basCmtsUsMapInitMainRegionSizeMicrosec OBJECT-TYPE
       SYNTAX      BasCmtsUInt16
       MAX-ACCESS  read-write
       STATUS      current
       DESCRIPTION
               "Bas Upstream Channel MapMaker size of Initial Maint 
                contention region, in microseconds. 
                [Note: Maps with Initial Maint regions are sent
                periodically.  Most maps do not have an Initial Maint region.]"
       DEFVAL { 2000 }
       ::= { basCmtsUsMapEntry 2 }

   basCmtsUsMapNewUcdGrantSizeMicrosec OBJECT-TYPE
       SYNTAX      BasCmtsUInt16
       MAX-ACCESS  read-write
       STATUS      current
       DESCRIPTION
               "Bas Upstream Channel MapMaker new UCD grant size.
                After a UCD change, this specifies the size of grant 
                to null sid (which functions as a delay for CM's to 
                digest the new UCD), in microseconds. "
       DEFVAL { 3000 }
       ::= { basCmtsUsMapEntry 3 }

   basCmtsUsMapMaxDeferredRngIE OBJECT-TYPE
       SYNTAX      BasCmtsUInt16
       MAX-ACCESS  read-write
       STATUS      current
       DESCRIPTION
               "Bas Upstream Channel MapMaker maximum number of deferred 
                ranging invitations per map."
       DEFVAL { 4 }
       ::= { basCmtsUsMapEntry 4 }

   basCmtsUsMapMapLeadTimeMillisec OBJECT-TYPE
       SYNTAX      BasCmtsUInt16
       MAX-ACCESS  read-only
       STATUS      deprecated
       DESCRIPTION
               "Bas Upstream Channel MapMaker map lead time, in 
                milliseconds."
       DEFVAL { 6 }
       ::= { basCmtsUsMapEntry 5 }

   basCmtsUsMapRequestLimitMslot OBJECT-TYPE
       SYNTAX      BasCmtsUInt16
       MAX-ACCESS  read-write
       STATUS      current
       DESCRIPTION
               "Bas Upstream Channel MapMaker maximum size for 
                request contention region, in mini-slots."
       DEFVAL { 20 }
       ::= { basCmtsUsMapEntry 6 }

   basCmtsUsMapMapLeadTime OBJECT-TYPE
       SYNTAX      BasCmtsUInt16
       MAX-ACCESS  read-only
       STATUS      current
       DESCRIPTION
               "Bas Upstream Channel MapMaker map lead time, in 
                microseconds."
       ::= { basCmtsUsMapEntry 7 }

   --
   -- ----------------------------------------------------------------------
   --
   -- Bas RangeFinder Settings
   --
   -- ----------------------------------------------------------------------
   --

   basCmtsUsRngTable OBJECT-TYPE
       SYNTAX      SEQUENCE OF BasCmtsUsRngEntry
       MAX-ACCESS  not-accessible
       STATUS      current
       DESCRIPTION
               "A Upstream Channel Range Finder Settings."  
       ::= { basCmtsConfigObjects 8 }

   basCmtsUsRngEntry OBJECT-TYPE
       SYNTAX      BasCmtsUsRngEntry
       MAX-ACCESS  not-accessible
       STATUS      current
       DESCRIPTION
               "An entry containing Upstream Channel Range Finder configuration 
                settings."
       AUGMENTS { basCmtsUpstreamChannelEntry }
       ::= { basCmtsUsRngTable 1 }

   BasCmtsUsRngEntry ::=
       SEQUENCE {
          basCmtsUsRngTimingOffsetThr            BasCmtsUInt32,
          basCmtsUsRngFreqOffsetThr              BasCmtsUInt16,
          basCmtsUsRngPowerOffsetThr             BasCmtsByte,
          basCmtsUsRngPowerDesired               BasCmtsUInt16,
          basCmtsUsRngMaxIgnoredInvitations      BasCmtsUInt16,
          basCmtsUsRngCmRngInviteTimeout         BasCmtsUInt16,
          basCmtsUsRngMaxPowerAdjQtrdb           BasCmtsByte,
          basCmtsUsRngZeroPowerAdj               TruthValue,
          basCmtsUsRngZeroTimingAdj              TruthValue,
          basCmtsUsRngZeroFreqAdj                TruthValue,
          basCmtsUsRngRefPowerLevel              Unsigned32,
          basCmtsUsRngCmPeriodicRngInviteTimeout BasCmtsUInt16
       }

   basCmtsUsRngTimingOffsetThr OBJECT-TYPE
       SYNTAX      BasCmtsUInt32
       MAX-ACCESS  read-write
       STATUS      current
       DESCRIPTION
               "Bas Upstream Channel RangeFinder timing offset threshold.
                If timing offset reported by MAC chip is <= this threshold 
                value, then timing adjustment may be stopped.  
                Units are 10.24 MHz clock cycles."
       DEFVAL { 2 }
       ::= { basCmtsUsRngEntry 1 }

   basCmtsUsRngFreqOffsetThr OBJECT-TYPE
       SYNTAX      BasCmtsUInt16
       MAX-ACCESS  read-write
       STATUS      current
       DESCRIPTION
               "Bas Upstream Channel RangeFinder frequency offset threshold.
                If frequency offset reported by MAC chip is <= this threshold 
                value, then frequency adjustment may be stopped. (Hz units)."
       DEFVAL { 3200 }
       ::= { basCmtsUsRngEntry 2 }

   basCmtsUsRngPowerOffsetThr OBJECT-TYPE
       SYNTAX      BasCmtsByte
       MAX-ACCESS  read-write
       STATUS      current
       DESCRIPTION
               "Bas Upstream Channel RangeFinder power offset threshold.
                If power level offset reported by MAC chip is <= this 
                threshold value, then power level adjustment may be stopped.
                (1/4 dB units)."
       DEFVAL { 8 }
       ::= { basCmtsUsRngEntry 3 }

   basCmtsUsRngPowerDesired OBJECT-TYPE
       SYNTAX      BasCmtsUInt16
       MAX-ACCESS  read-write
       STATUS      current
       DESCRIPTION
               "Bas Upstream Channel RangeFinder power desired.
                Desired linear power level.  Used as reference
                when computing power adjustment.  Units are a 
                Broadcom defined (16) bit linear scale."
       DEFVAL { 4096 }
       ::= { basCmtsUsRngEntry 4 }

   basCmtsUsRngMaxIgnoredInvitations OBJECT-TYPE
       SYNTAX      BasCmtsUInt16
       MAX-ACCESS  read-only
       STATUS      current
       DESCRIPTION
               "Bas Upstream Channel RangeFinder maximum ignored
                invitations.  Maximum ranging invitations that a 
                CM may ignore before being considered quiet."
       DEFVAL { 20 }
       ::= { basCmtsUsRngEntry 5 }

   basCmtsUsRngCmRngInviteTimeout OBJECT-TYPE
       SYNTAX      BasCmtsUInt16
       MAX-ACCESS  read-write
       STATUS      current
       DESCRIPTION
               "Bas Upstream Channel RangeFinder cable modem range
                invite timeout.  Minimum time allowed for a CM 
                following receipt of a RNG-RSP before it is expected 
                to reply to an invitation to range request, in 
                milliseconds."
       DEFVAL { 100 }
       ::= { basCmtsUsRngEntry 6 }

   basCmtsUsRngMaxPowerAdjQtrdb OBJECT-TYPE
       SYNTAX      BasCmtsByte
       MAX-ACCESS  read-write
       STATUS      current
       DESCRIPTION
               "Bas Upstream Channel RangeFinder maximum power 
                adjustment for a particular RNG-RSP message, 
                in 1/4dB units."
       DEFVAL { 8 }
       ::= { basCmtsUsRngEntry 7 }

   basCmtsUsRngZeroPowerAdj OBJECT-TYPE
       SYNTAX      TruthValue
       MAX-ACCESS  read-write
       STATUS      current
       DESCRIPTION
               "Bas Upstream Channel RangeFinder zero power adjustment.
                If true, power adjustment item in range response
                message will be unconditionally set to 0.  Useful for 
                debugging."
       DEFVAL { false }
       ::= { basCmtsUsRngEntry 8 }

   basCmtsUsRngZeroTimingAdj OBJECT-TYPE
       SYNTAX      TruthValue
       MAX-ACCESS  read-write
       STATUS      current
       DESCRIPTION
               "Bas Upstream Channel RangeFinder zero timing adjustment.
                If true, timing adjustment item in range response 
                message will be unconditionally set to 0.  Useful for 
                debugging." 
       DEFVAL { false }
       ::= { basCmtsUsRngEntry 9 }

   basCmtsUsRngZeroFreqAdj OBJECT-TYPE
       SYNTAX      TruthValue
       MAX-ACCESS  read-write
       STATUS      current
       DESCRIPTION
               "Bas Upstream Channel RangeFinder zero frequency adjustment.
                If true, frequency adjustment item in range response
                message will be unconditionally set to 0.  Useful for 
                debugging." 
       DEFVAL { true }
       ::= { basCmtsUsRngEntry 10 }

   basCmtsUsRngRefPowerLevel OBJECT-TYPE
       SYNTAX      Unsigned32
       MAX-ACCESS  read-write
       STATUS      current
       DESCRIPTION
               "Reference power level for this upstream channel."
       ::= { basCmtsUsRngEntry 11 }

   basCmtsUsRngCmPeriodicRngInviteTimeout OBJECT-TYPE
       SYNTAX      BasCmtsUInt16
       MAX-ACCESS  read-write
       STATUS      current
       DESCRIPTION
               "Used to space the ranging invitations, if the modem
                has completed ranging."
       ::= { basCmtsUsRngEntry 12 }

   --
   -- ----------------------------------------------------------------------
   --
   -- Bas Upstream Stats Table 
   --
   -- ----------------------------------------------------------------------
   --

   basCmtsUsStatsTable OBJECT-TYPE
       SYNTAX      SEQUENCE OF BasCmtsUsStatsEntry
       MAX-ACCESS  not-accessible
       STATUS      current
       DESCRIPTION
               "Contains statistics for each upstream channel."  
       ::= { basCmtsConfigObjects 13 }

   basCmtsUsStatsEntry OBJECT-TYPE
       SYNTAX      BasCmtsUsStatsEntry
       MAX-ACCESS  not-accessible
       STATUS      current
       DESCRIPTION
               "An entry containing statistics for each upstream channel."
       AUGMENTS { basCmtsUpstreamChannelEntry }
       ::= { basCmtsUsStatsTable 1 }

   BasCmtsUsStatsEntry ::=
       SEQUENCE {
          basCmtsUsStatsClearFlag                BasCmtsUInt32,
          basCmtsUsStatsUSSlots                  BasCmtsUInt32,
          basCmtsUsStatsNoUW                     BasCmtsUInt32,
          basCmtsUsStatsDataFECorHCSErr          BasCmtsUInt32,
          basCmtsUsStatsRequests                 BasCmtsUInt32,
          basCmtsUsStatsRequestColl              BasCmtsUInt32,
          basCmtsUsStatsReqFECorHCSErr           BasCmtsUInt32,
          basCmtsUsStatsReqNoEnergy              BasCmtsUInt32,
          basCmtsUsStatsReqData                  BasCmtsUInt32,
          basCmtsUsStatsReqDataColl              BasCmtsUInt32,
          basCmtsUsStatsReqDataFECorHCSErr       BasCmtsUInt32,
          basCmtsUsStatsReqDataNoEnergy          BasCmtsUInt32,
          basCmtsUsStatsRanging                  BasCmtsUInt32,
          basCmtsUsStatsRangeFECorHCSErr         BasCmtsUInt32,
          basCmtsUsStatsMapsTooLate              BasCmtsUInt32
       }

   basCmtsUsStatsClearFlag OBJECT-TYPE
       SYNTAX      BasCmtsUInt32
       MAX-ACCESS  read-write
       STATUS      current
       DESCRIPTION
               "Writing any value to this mib clears all stats in this table."
       ::= { basCmtsUsStatsEntry 1 }

   basCmtsUsStatsUSSlots OBJECT-TYPE
       SYNTAX      BasCmtsUInt32
       MAX-ACCESS  read-only
       STATUS      current
       DESCRIPTION
               "Number upstream data information elements in Maps."
       ::= { basCmtsUsStatsEntry 2 }

   basCmtsUsStatsNoUW OBJECT-TYPE
       SYNTAX      BasCmtsUInt32
       MAX-ACCESS  read-only
       STATUS      current
       DESCRIPTION
               "Number upstream data packets with FEC No Unique Word."
       ::= { basCmtsUsStatsEntry 3 }


   basCmtsUsStatsDataFECorHCSErr OBJECT-TYPE
       SYNTAX      BasCmtsUInt32
       MAX-ACCESS  read-only
       STATUS      current
       DESCRIPTION
               "Number upstream data packets with FEC or HCS Error."
       ::= { basCmtsUsStatsEntry 4 }


   basCmtsUsStatsRequests OBJECT-TYPE
       SYNTAX      BasCmtsUInt32
       MAX-ACCESS  read-only
       STATUS      current
       DESCRIPTION
               "Number request slots allocated."
       ::= { basCmtsUsStatsEntry 5 }

   basCmtsUsStatsRequestColl OBJECT-TYPE
       SYNTAX      BasCmtsUInt32
       MAX-ACCESS  read-only
       STATUS      current
       DESCRIPTION
               "Number request slots with collisions."
       ::= { basCmtsUsStatsEntry 6 }

   basCmtsUsStatsReqFECorHCSErr OBJECT-TYPE
       SYNTAX      BasCmtsUInt32
       MAX-ACCESS  read-only
       STATUS      current
       DESCRIPTION
               "Number request slots corrupted by bad FEC or HCS."
       ::= { basCmtsUsStatsEntry 7 }

   basCmtsUsStatsReqNoEnergy OBJECT-TYPE
       SYNTAX      BasCmtsUInt32
       MAX-ACCESS  read-only
       STATUS      current
       DESCRIPTION
               "Number request slots with no energy."
       ::= { basCmtsUsStatsEntry 8 }

   basCmtsUsStatsReqData OBJECT-TYPE
       SYNTAX      BasCmtsUInt32
       MAX-ACCESS  read-only
       STATUS      current
       DESCRIPTION
               "Number request/data slots allocated."
       ::= { basCmtsUsStatsEntry 9 }

   basCmtsUsStatsReqDataColl OBJECT-TYPE
       SYNTAX      BasCmtsUInt32
       MAX-ACCESS  read-only
       STATUS      current
       DESCRIPTION
               "Number request/data slots with collisions."
       ::= { basCmtsUsStatsEntry 10 }

   basCmtsUsStatsReqDataFECorHCSErr OBJECT-TYPE
       SYNTAX      BasCmtsUInt32
       MAX-ACCESS  read-only
       STATUS      current
       DESCRIPTION
               "Number request/data slots with FEC or HCS errors."
       ::= { basCmtsUsStatsEntry 11 }

   basCmtsUsStatsReqDataNoEnergy OBJECT-TYPE
       SYNTAX      BasCmtsUInt32
       MAX-ACCESS  read-only
       STATUS      current
       DESCRIPTION
               "Number request/data slots with no energy."
       ::= { basCmtsUsStatsEntry 12 }

   basCmtsUsStatsRanging OBJECT-TYPE
       SYNTAX      BasCmtsUInt32
       MAX-ACCESS  read-only
       STATUS      current
       DESCRIPTION
               "Number upstream ranging packets received."
       ::= { basCmtsUsStatsEntry 13 }

   basCmtsUsStatsRangeFECorHCSErr OBJECT-TYPE
       SYNTAX      BasCmtsUInt32
       MAX-ACCESS  read-only
       STATUS      current
       DESCRIPTION
               "Number ranging slots with FEC or HCS errors."
       ::= { basCmtsUsStatsEntry 14 }

   basCmtsUsStatsMapsTooLate OBJECT-TYPE
       SYNTAX      BasCmtsUInt32
       MAX-ACCESS  read-only
       STATUS      current
       DESCRIPTION
               "Number of Maps too late detected."
       ::= { basCmtsUsStatsEntry 15 }

   --
   -- ----------------------------------------------------------------------
   --
   --
   --
   -- ----------------------------------------------------------------------
   --

-- Bas Cmts Service Entry Table
   basCmtsServiceTable OBJECT-TYPE
       SYNTAX      SEQUENCE OF BasCmtsServiceEntry
       MAX-ACCESS  not-accessible
       STATUS      current
       DESCRIPTION
               " The Service Table per MAC IF"  
       ::= { basCmtsConfigObjects 9 }

   basCmtsServiceEntry OBJECT-TYPE
       SYNTAX      BasCmtsServiceEntry
       MAX-ACCESS  not-accessible
       STATUS      current
       DESCRIPTION
               "An entry containing information for a particular SID"
       AUGMENTS { docsIfCmtsServiceEntry }
       ::= { basCmtsServiceTable 1 }

   BasCmtsServiceEntry ::=
       SEQUENCE {
          
          basCmtsServiceMacAddress              MacAddress,
	  basCmtsServiceIpAddress		IpAddress,
          basCmtsServiceAuthState               INTEGER,
          basCmtsServiceFilter                  BasCmtsUInt16,
          basCmtsServiceCurrentNumHost          BasCmtsUInt32,
          basCmtsServiceMaxNumHost              BasCmtsUInt32,
          basCmtsServiceOutOctets               BasCmtsUInt32,
          basCmtsServiceOutPackets              BasCmtsUInt32,
          basCmtsServiceInDiscards              BasCmtsUInt32,
          basCmtsServiceOutDiscards             BasCmtsUInt32,
          basCmtsServiceBwReqCount              BasCmtsUInt32,
          basCmtsServiceDataGrantCount          BasCmtsUInt32
	}

basCmtsServiceMacAddress OBJECT-TYPE
        SYNTAX      MacAddress
        MAX-ACCESS  read-only
        STATUS      current
        DESCRIPTION
            "MAC address of this Cable Modem. If the Cable Modem has
             multiple MAC addresses, this is the MAC address associated
             with the Cable interface."
        ::= { basCmtsServiceEntry 1 }

basCmtsServiceIpAddress OBJECT-TYPE
        SYNTAX      IpAddress
        MAX-ACCESS  read-only
        STATUS      current
        DESCRIPTION
            "IP address of The CMTS. "
	::= { basCmtsServiceEntry 2 }

basCmtsServiceAuthState	OBJECT-TYPE
SYNTAX			INTEGER	{
				initial(1),
				temporary(2),
				permanent(3),
				auth(4),
				max(5)
			}
	MAX-ACCESS		read-only
	STATUS			current
	DESCRIPTION
	" Auth State Object."
	::= { basCmtsServiceEntry 3 }

basCmtsServiceFilter OBJECT-TYPE
        SYNTAX      BasCmtsUInt16
        MAX-ACCESS  read-write
        STATUS      current
        DESCRIPTION
            "The Service Filter Object"
        ::= { basCmtsServiceEntry 4 }

basCmtsServiceCurrentNumHost OBJECT-TYPE
        SYNTAX      BasCmtsUInt32
        MAX-ACCESS  read-only
        STATUS      current
        DESCRIPTION
            "The Current number of host."
        ::= { basCmtsServiceEntry 5 }

basCmtsServiceMaxNumHost OBJECT-TYPE
        SYNTAX      BasCmtsUInt32
        MAX-ACCESS  read-only
        STATUS      current
        DESCRIPTION
            "The max number of host" 
        ::= { basCmtsServiceEntry 6 }

basCmtsServiceOutOctets OBJECT-TYPE
        SYNTAX      BasCmtsUInt32
        MAX-ACCESS  read-only
        STATUS      current
        DESCRIPTION
            "The number of service out octets." 
        ::= { basCmtsServiceEntry 7 }

basCmtsServiceOutPackets OBJECT-TYPE
        SYNTAX      BasCmtsUInt32
        MAX-ACCESS  read-only
        STATUS      current
        DESCRIPTION
            "The number of service out packets." 
        ::= { basCmtsServiceEntry 8 }

basCmtsServiceInDiscards OBJECT-TYPE
        SYNTAX      BasCmtsUInt32
        MAX-ACCESS  read-only
        STATUS      current
        DESCRIPTION
            "The number of input packets discarded." 
        ::= { basCmtsServiceEntry 9 }

basCmtsServiceOutDiscards OBJECT-TYPE
        SYNTAX      BasCmtsUInt32
        MAX-ACCESS  read-only
        STATUS      current
        DESCRIPTION
            "The number of output packets discarded." 
        ::= { basCmtsServiceEntry 10 }

basCmtsServiceBwReqCount OBJECT-TYPE
        SYNTAX      BasCmtsUInt32
        MAX-ACCESS  read-only
        STATUS      current
        DESCRIPTION
            "The bandwidth request count for this service." 
        ::= { basCmtsServiceEntry 11 }

basCmtsServiceDataGrantCount OBJECT-TYPE
        SYNTAX      BasCmtsUInt32
        MAX-ACCESS  read-only
        STATUS      current
        DESCRIPTION
            "The data grant count for this service." 
        ::= { basCmtsServiceEntry 12 }

   --
   -- ----------------------------------------------------------------------
   --
   -- Bas Flap Table
   --
   -- ----------------------------------------------------------------------
   --

   basFlapControlTable OBJECT-TYPE
       SYNTAX      SEQUENCE OF BasFlapControlEntry
       MAX-ACCESS  not-accessible
       STATUS      current
       DESCRIPTION
               "Defines the flap table control settings per MAC IF.
                A flap-list is a table maintained for every modem 
                (active or not) that is having communication difficulties.  
                Flapping refers to the rapid disconneting and reconneting of 
                a cable modem that is having problems holding a connection.  
                The flap list contains modem MAC addresses and logs the 
                time of the most recent activity.  The size and entry 
                thresholds for the flap list can be configured."  
       ::= { basCmtsConfigObjects 10 }

   basFlapControlEntry OBJECT-TYPE
       SYNTAX      BasFlapControlEntry
       MAX-ACCESS  not-accessible
       STATUS      current
       DESCRIPTION
               "Defines the flap table control settings.
                An entry in this table exists for each ifEntry with an 
                ifType of docsCableMacLayer(127)."
       INDEX   { ifIndex }
       ::= { basFlapControlTable 1 }

   BasFlapControlEntry ::=
       SEQUENCE {
           basFlapCtlClearFlag                Integer32,
           basFlapCtlMaxTableSize             Integer32,
           basFlapCtlAgingThresh              Integer32,
           basFlapCtlInsTimeThresh            Integer32,
           basFlapCtlPowerAdjThresh           Integer32
       }

   basFlapCtlClearFlag OBJECT-TYPE
       SYNTAX      Integer32
       MAX-ACCESS  read-write
       STATUS      current
       DESCRIPTION
               "Flap list clear control flag.  Setting this flag to 1
                empties the flap-list table."
       ::= { basFlapControlEntry 1 }

   basFlapCtlMaxTableSize OBJECT-TYPE
       SYNTAX      Integer32 (0..8191)
       MAX-ACCESS  read-write
       STATUS      current
       DESCRIPTION
               "Specifies the max size of the flap-list table.
                Setting table size to 0 disables flap-list table maintenance."
       ::= { basFlapControlEntry 2 }

   basFlapCtlAgingThresh OBJECT-TYPE
       SYNTAX      Integer32 (0..60)
       MAX-ACCESS  read-write
       STATUS      current
       DESCRIPTION
               "Specifies the number of days to age the cable modem from 
                the flap list table.  Setting the aging threshold to 0 
                results in modems never being aged from the table."
       ::= { basFlapControlEntry 3 }

   basFlapCtlInsTimeThresh OBJECT-TYPE
       SYNTAX      Integer32 (0..604800)
       MAX-ACCESS  read-write
       STATUS      current
       DESCRIPTION
               "Specifies the insertion time threshold, in seconds.
                This threshold controls the operation of a flapping modem 
                detector.  When the link establishment rate of a modem is 
                shorter than the period defined by this parameter, the modem 
                is placed in the flap list.  Setting this parameter to 0
                results in modems never being inserted in the flap list table
                due to short link establishment times."
       ::= { basFlapControlEntry 4 }

   basFlapCtlPowerAdjThresh OBJECT-TYPE
       SYNTAX      Integer32 (0..10)
       MAX-ACCESS  read-write
       STATUS      current
       DESCRIPTION
               "Specifies the power-adjust threshold for recording a flap
                list event.  When the power adjustment of a modem exceeds 
                the threshold, the modem is placed in the flap list.  
                Setting this parameter to 0 results in modems never being 
                inserted in the flap list table due to power adjustments."
       ::= { basFlapControlEntry 5 }

   basFlapTable OBJECT-TYPE
       SYNTAX      SEQUENCE OF BasFlapEntry
       MAX-ACCESS  not-accessible
       STATUS      current
       DESCRIPTION
               "Defines the flap table per MAC IF and MacAddr.
                A flap-list is a table maintained for every modem 
                (active or not) that is having communication difficulties.  
                Flapping refers to the rapid disconnetin and reconneting of 
                a cable modem that is having problems holding a connection.  
                The flap list contains modem MAC addresses and logs the 
                time of the most recent activity.  The size and entry 
                thresholds for the flap list can be configured."  
       ::= { basCmtsConfigObjects 11 }

   basFlapEntry OBJECT-TYPE
       SYNTAX      BasFlapEntry
       MAX-ACCESS  not-accessible
       STATUS      current
       DESCRIPTION
               "Defines the flap table entries.
                An entry in this table exists for each ifEntry with an 
                ifType of docsCableMacLayer(127) and for every MacAddress."
       INDEX   { ifIndex, basFlapEntryMacAddress }
       ::= { basFlapTable 1 }

   BasFlapEntry ::=
       SEQUENCE {
           basFlapEntryMacAddress             MacAddress,
           basFlapEntryUsChan                 Counter32,
           basFlapEntryInsertCount            Counter32,
           basFlapEntryHitCount               Counter32,
           basFlapEntryMissCount              Counter32,
           basFlapEntryCRCErrCount            Counter32,
           basFlapEntryPAdjCount              Counter32,
           basFlapEntryFlapCount              Counter32,
           basFlapEntryLastModemState         INTEGER,
           basFlapEntryInsertTime             TimeTicks,
           basFlapEntryRemoveTime             TimeTicks,
           basFlapEntryLastBasModemState      INTEGER
       }

   basFlapEntryMacAddress OBJECT-TYPE
       SYNTAX      MacAddress
       MAX-ACCESS  read-only
       STATUS      current
       DESCRIPTION
               ""
    ::= { basFlapEntry 1 }

   basFlapEntryUsChan OBJECT-TYPE
       SYNTAX      Counter32
       MAX-ACCESS  read-only
       STATUS      current
       DESCRIPTION
               "Specifies the upstream channel the specified modem is 
                currently using."
       ::= { basFlapEntry 2 }

   basFlapEntryInsertCount OBJECT-TYPE
       SYNTAX      Counter32
       MAX-ACCESS  read-only
       STATUS      current
       DESCRIPTION
               "Specifies the number of time the modem comes up and inserts 
                itself into the network.  It can indicate intermittent 
                downstream sync loss or DHCP or modem registration problems."
       ::= { basFlapEntry 3 }

   basFlapEntryHitCount OBJECT-TYPE
       SYNTAX      Counter32
       MAX-ACCESS  read-only
       STATUS      current
       DESCRIPTION
               "Specifies the number of time the modem responds to MAC 
                layer keep alive messages.  It can indicate intermittent 
                upstream, laser clipping, or common-path distortion."
       ::= { basFlapEntry 4 }

   basFlapEntryMissCount OBJECT-TYPE
       SYNTAX      Counter32
       MAX-ACCESS  read-only
       STATUS      current
       DESCRIPTION
               "Specifies the number of time the modem misses the MAC 
                layer keep alive messages.  It can indicate intermittent 
                upstream, laser clipping, or common-path distortion."
       ::= { basFlapEntry 5 }

   basFlapEntryCRCErrCount OBJECT-TYPE
       SYNTAX      Counter32
       MAX-ACCESS  read-only
       STATUS      current
       DESCRIPTION
               "Specifies the number of Cyclic Redundancy Check errors 
                from this modem.  It can indicate intermittent 
                upstream, laser clipping, or common-path distortion."
       ::= { basFlapEntry 6 }

   basFlapEntryPAdjCount OBJECT-TYPE
       SYNTAX      Counter32
       MAX-ACCESS  read-only
       STATUS      current
       DESCRIPTION
               "Specifies the number of times the headend instructed the 
                modem to adjust transmit power more than the 
                threshold-specified number of dB.  It can indicate amplifier 
                degradation, poor connections, or thermal sensitivity."
       ::= { basFlapEntry 7 }

   basFlapEntryFlapCount OBJECT-TYPE
       SYNTAX      Counter32
       MAX-ACCESS  read-only
       STATUS      current
       DESCRIPTION
               "Specifies the sum of basFlapEntryPAdjCount and 
                basFlapEntryInsertCount."
       ::= { basFlapEntry 8 }

   basFlapEntryLastModemState OBJECT-TYPE
       SYNTAX      INTEGER {
            other(1),
            ranging(2),
            rangingAborted(3),
            rangingComplete(4),
            ipComplete(5),
            registrationComplete(6),
            accessDenied(7)
       }
       MAX-ACCESS  read-only
       STATUS      current
       DESCRIPTION
               "Specifies the modem state when this modem last flapped.
                State is as specified in the RF Interface 
                Specification, and indicates the following events:
                other(1)
                   Any state other than below.
                ranging(2)
                   The CMTS has received an Initial Ranging Request
                   message from the CM, and the ranging process is not
                   yet complete.
                rangingAborted(3)
                   The CMTS has sent a Ranging Abort message to the CM.
                rangingComplete(4)
                   The CMTS has sent a Ranging Complete message to the CM.
                ipComplete(5)
                   The CMTS has received a DHCP reply message and forwarded
                   it to the CM.
                registrationComplete(6)
                   The CMTS has sent a Registration Response mesage to
                   the CM.
                accessDenied(7)
                   The CMTS has sent a Registration Aborted message
                   to the CM."
       ::= { basFlapEntry 9 }

   basFlapEntryInsertTime OBJECT-TYPE
       SYNTAX      TimeTicks
       MAX-ACCESS  read-only
       STATUS      current
       DESCRIPTION
               "Specifies the most recent time that the modem was inserted
                in the network."
       ::= { basFlapEntry 10 }

   basFlapEntryRemoveTime OBJECT-TYPE
       SYNTAX      TimeTicks
       MAX-ACCESS  read-only
       STATUS      current
       DESCRIPTION
               "Specifies the most recent time that the modem dropped the 
                connection."
       ::= { basFlapEntry 11 }

   basFlapEntryLastBasModemState OBJECT-TYPE
       SYNTAX      INTEGER {
            basModemOffline(1),
            basInitRngRcvd(2),
            basRanging(3),
            basRangingComplete(4),
            basDhcpDiscoverRcvd(5),
            basDhcpRequestRcvd(6),
            basTimeReqRcvd(7),
            basTftpReqRcvd(8),
            basRegisteredNetAccessEnabled(9),
            basRegisteredNetAccessDisabled(10),
            basRegisteredBPIKekAssigned(11),
            basRegisteredBPITekAssigned(12),
            basRegFailBadCMTSMic(13),
            basRegFailBadCOS(14),
            basRegFailAuthFailure(15),
            basKekReject(16),
            basTekReject(17)
       }
       MAX-ACCESS  read-only
       STATUS      current
       DESCRIPTION
               "Specifies the modem state when this modem last flapped.
                State is as specified in the basCmtsCmStatusValue mib."
       ::= { basFlapEntry 12 }

   --
   -- ----------------------------------------------------------------------
   --
   -- Bas CMTS CM Status settings
   --
   -- ----------------------------------------------------------------------
   --

   basCmtsCmStatusTable OBJECT-TYPE
       SYNTAX      SEQUENCE OF BasCmtsCmStatusEntry
       MAX-ACCESS  not-accessible
       STATUS      current
       DESCRIPTION
               "A list of CMTS CM status settings."
       ::= { basCmtsConfigObjects 12 }

   basCmtsCmStatusEntry OBJECT-TYPE
       SYNTAX      BasCmtsCmStatusEntry
       MAX-ACCESS  not-accessible
       STATUS      current
       DESCRIPTION
               "An entry in this table exists for each entry in the
                docsIfCmtsCmStatusTable."
       AUGMENTS { basDocsIfCmtsCmStatusEntry }
       ::= { basCmtsCmStatusTable 1 }

   BasCmtsCmStatusEntry ::=
       SEQUENCE {
         basCmtsCmStatusAbortFlag         Integer32,
         basCmtsCmStatusPrimarySid        Integer32,
         basCmtsCmStatusValue             INTEGER
   
       }

   basCmtsCmStatusAbortFlag     OBJECT-TYPE
       SYNTAX      Integer32
       MAX-ACCESS  read-write
       STATUS      current
       DESCRIPTION
               "CMTS CM status clear control flag.  Setting this flag to 1
                causes a Range-Abort message to be sent to the cable modem."
       ::= { basCmtsCmStatusEntry 1 }

   basCmtsCmStatusPrimarySid    OBJECT-TYPE
       SYNTAX      Integer32
       MAX-ACCESS  read-only
       STATUS      current
       DESCRIPTION
               "Primary SID of this modem.  "
       ::= { basCmtsCmStatusEntry 2 }

   basCmtsCmStatusValue OBJECT-TYPE
       SYNTAX      INTEGER {
            basModemOffline(1),
            basInitRngRcvd(2),
            basRanging(3),
            basRangingComplete(4),
            basDhcpDiscoverRcvd(5),
            basDhcpRequestRcvd(6),
            basTimeReqRcvd(7),
            basTftpReqRcvd(8),
            basRegisteredNetAccessEnabled(9),
            basRegisteredNetAccessDisabled(10),
            basRegisteredBPIKekAssigned(11),
            basRegisteredBPITekAssigned(12),
            basRegFailBadCMTSMic(13),
            basRegFailBadCOS(14),
            basRegFailAuthFailure(15),
            basKekReject(16),
            basTekReject(17)
        }
       MAX-ACCESS  read-only
       STATUS      current
       DESCRIPTION
               "Specifies the modem state.  "
       ::= { basCmtsCmStatusEntry 3 }

   --
   -- ----------------------------------------------------------------------
   --
   -- Bas CMTS Packet Decode Control Objects
   --
   -- ----------------------------------------------------------------------
   --

   basCmtsPktDecodeControlTable OBJECT-TYPE
       SYNTAX      SEQUENCE OF BasCmtsPktDecodeControlEntry
       MAX-ACCESS  not-accessible
       STATUS      current
       DESCRIPTION
               "A list of BAS cmts packet decode control objects. "
       ::= { basCmtsDecodeObjects 1 }

   basCmtsPktDecodeControlEntry OBJECT-TYPE
       SYNTAX      BasCmtsPktDecodeControlEntry
       MAX-ACCESS  not-accessible
       STATUS      current
       DESCRIPTION
               "An entry containing BAS Packet decode control settings.
                An entry in this table exists for each ifEntry with an 
                ifType of docsCableMacLayer(127)."
       INDEX   { ifIndex }
       ::= { basCmtsPktDecodeControlTable 1 }

   BasCmtsPktDecodeControlEntry ::=
       SEQUENCE {
           basCmtsPktDecodeControlShowRx             TruthValue,
           basCmtsPktDecodeControlShowTx             TruthValue,
           basCmtsPktDecodeControlAnalyzeLevel       INTEGER,
           basCmtsPktDecodeControlFilterUcd          TruthValue,
           basCmtsPktDecodeControlFilterMap          TruthValue,
           basCmtsPktDecodeControlFilterRngReq       TruthValue,
           basCmtsPktDecodeControlFilterRngRsp       TruthValue,
           basCmtsPktDecodeControlFilterRegReq       TruthValue,
           basCmtsPktDecodeControlFilterRegRsp       TruthValue,
           basCmtsPktDecodeControlFilterUccReq       TruthValue,
           basCmtsPktDecodeControlFilterUccRsp       TruthValue,
           basCmtsPktDecodeControlFilterBpkmReq      TruthValue,
           basCmtsPktDecodeControlFilterBpkmRsp      TruthValue,
           basCmtsPktDecodeControlFilterPdu          TruthValue,
	     basCmtsPktDecodeControlFilterBwReq        TruthValue
       }

   basCmtsPktDecodeControlShowRx OBJECT-TYPE
       SYNTAX      TruthValue
       MAX-ACCESS  read-write
       STATUS      current
       DESCRIPTION
               "Decode control on/off."
       DEFVAL { false }
       ::= { basCmtsPktDecodeControlEntry 1 }

   basCmtsPktDecodeControlShowTx OBJECT-TYPE
       SYNTAX      TruthValue
       MAX-ACCESS  read-write
       STATUS      current
       DESCRIPTION
               "Decode control on/off."
       DEFVAL { false }
       ::= { basCmtsPktDecodeControlEntry 2 }


   basCmtsPktDecodeControlAnalyzeLevel OBJECT-TYPE
       SYNTAX      INTEGER {
			        lowLevel (1),
				mediumLevel (2),
				highLevel (3),
				levelFour (4)
			}
       MAX-ACCESS  read-write
       STATUS      current
       DESCRIPTION
               "Decode control on/off."
       DEFVAL { lowLevel }
       ::= { basCmtsPktDecodeControlEntry 3 }

   basCmtsPktDecodeControlFilterUcd OBJECT-TYPE
       SYNTAX      TruthValue
       MAX-ACCESS  read-write
       STATUS      current
       DESCRIPTION
               "Decode control on/off."
       DEFVAL { false }
       ::= { basCmtsPktDecodeControlEntry 4 }

   basCmtsPktDecodeControlFilterMap OBJECT-TYPE
       SYNTAX      TruthValue
       MAX-ACCESS  read-write
       STATUS      current
       DESCRIPTION
               "Decode control on/off."
       DEFVAL { false }
       ::= { basCmtsPktDecodeControlEntry 5 }

   basCmtsPktDecodeControlFilterRngReq OBJECT-TYPE
       SYNTAX      TruthValue
       MAX-ACCESS  read-write
       STATUS      current
       DESCRIPTION
               "Decode control on/off."
       DEFVAL { false }
       ::= { basCmtsPktDecodeControlEntry 6 }

   basCmtsPktDecodeControlFilterRngRsp OBJECT-TYPE
       SYNTAX      TruthValue
       MAX-ACCESS  read-write
       STATUS      current
       DESCRIPTION
               "Decode control on/off."
       DEFVAL { false }
       ::= { basCmtsPktDecodeControlEntry 7 }

   basCmtsPktDecodeControlFilterRegReq OBJECT-TYPE
       SYNTAX      TruthValue
       MAX-ACCESS  read-write
       STATUS      current
       DESCRIPTION
               "Decode control on/off."
       DEFVAL { false }
       ::= { basCmtsPktDecodeControlEntry 8 }

   basCmtsPktDecodeControlFilterRegRsp OBJECT-TYPE
       SYNTAX      TruthValue
       MAX-ACCESS  read-write
       STATUS      current
       DESCRIPTION
               "Decode control on/off."
       DEFVAL { false }
       ::= { basCmtsPktDecodeControlEntry 9 }

   basCmtsPktDecodeControlFilterUccReq OBJECT-TYPE
       SYNTAX      TruthValue
       MAX-ACCESS  read-write
       STATUS      current
       DESCRIPTION
               "Decode control on/off."
       DEFVAL { false }
       ::= { basCmtsPktDecodeControlEntry 10 }

   basCmtsPktDecodeControlFilterUccRsp OBJECT-TYPE
       SYNTAX      TruthValue
       MAX-ACCESS  read-write
       STATUS      current
       DESCRIPTION
               "Decode control on/off."
       DEFVAL { false }
       ::= { basCmtsPktDecodeControlEntry 11 }

   basCmtsPktDecodeControlFilterBpkmReq OBJECT-TYPE
       SYNTAX      TruthValue
       MAX-ACCESS  read-write
       STATUS      current
       DESCRIPTION
               "Decode control on/off."
       DEFVAL { false }
       ::= { basCmtsPktDecodeControlEntry 12 }

   basCmtsPktDecodeControlFilterBpkmRsp OBJECT-TYPE
       SYNTAX      TruthValue
       MAX-ACCESS  read-write
       STATUS      current
       DESCRIPTION
               "Decode control on/off."
       DEFVAL { false }
       ::= { basCmtsPktDecodeControlEntry 13 }

   basCmtsPktDecodeControlFilterPdu OBJECT-TYPE
       SYNTAX      TruthValue
       MAX-ACCESS  read-write
       STATUS      current
       DESCRIPTION
               "Decode control on/off."
       DEFVAL { false }
       ::= { basCmtsPktDecodeControlEntry 14 }

   basCmtsPktDecodeControlFilterBwReq OBJECT-TYPE
       SYNTAX      TruthValue
       MAX-ACCESS  read-write
       STATUS      current
       DESCRIPTION
               "Decode control on/off."
       DEFVAL { false }
       ::= { basCmtsPktDecodeControlEntry 15 }



 --
   -- ----------------------------------------------------------------------
   --
   -- Bas CMTS MAP Decode Control Objects
   --
   -- ----------------------------------------------------------------------
   --

   basCmtsMapDecodeControlTable OBJECT-TYPE
       SYNTAX      SEQUENCE OF BasCmtsMapDecodeControlEntry
       MAX-ACCESS  not-accessible
       STATUS      current
       DESCRIPTION
               "A list of BAS cmts map decode control objects. "
       ::= { basCmtsDecodeObjects 2 }

   basCmtsMapDecodeControlEntry OBJECT-TYPE
       SYNTAX      BasCmtsMapDecodeControlEntry
       MAX-ACCESS  not-accessible
       STATUS      current
       DESCRIPTION
               "An entry containing BAS MAP decode control settings.
                An entry in this table exists for each ifEntry with an 
                ifType of docsCableMacLayer(127)."
       INDEX   { ifIndex }
       ::= { basCmtsMapDecodeControlTable 1 }

   BasCmtsMapDecodeControlEntry ::=
       SEQUENCE {
           basCmtsMapDecodeControlTriggerMapPktCount  INTEGER,
           basCmtsMapDecodeControlTriggerDataGrant    INTEGER,
           basCmtsMapDecodeControlTriggerUcdChange    INTEGER,
           basCmtsMapDecodeControlTriggerShortGrant   INTEGER,
           basCmtsMapDecodeControlTriggerLongGrant    INTEGER,
           basCmtsMapDecodeControlTriggerInitMaint    INTEGER,
           basCmtsMapDecodeControlTriggerStationMaint INTEGER,
           basCmtsMapDecodeControlTriggerRequestIe    INTEGER
       }

   basCmtsMapDecodeControlTriggerMapPktCount OBJECT-TYPE
       SYNTAX      INTEGER (0..255)
       MAX-ACCESS  read-write
       STATUS      current
       DESCRIPTION
               "Data trigger."
       DEFVAL { 0 }
       ::= { basCmtsMapDecodeControlEntry 1 }

   basCmtsMapDecodeControlTriggerDataGrant OBJECT-TYPE
       SYNTAX      INTEGER {
					triggerOn (1),
			            triggerOff (2)
				   }
       MAX-ACCESS  read-write
       STATUS      current
       DESCRIPTION
               "Data trigger."
       DEFVAL { triggerOff }
       ::= { basCmtsMapDecodeControlEntry 2 }


   basCmtsMapDecodeControlTriggerUcdChange OBJECT-TYPE
       SYNTAX      INTEGER {
					triggerOn (1),
			            triggerOff (2)
				   }
       MAX-ACCESS  read-write
       STATUS      current
       DESCRIPTION
               "Data trigger."
       DEFVAL { triggerOff }
       ::= { basCmtsMapDecodeControlEntry 3 }

   basCmtsMapDecodeControlTriggerShortGrant OBJECT-TYPE
       SYNTAX      INTEGER {
					triggerOn (1),
			            triggerOff (2)
				   }
       MAX-ACCESS  read-write
       STATUS      current
       DESCRIPTION
               "Data trigger."
       DEFVAL { triggerOff }
       ::= { basCmtsMapDecodeControlEntry 4 }

   basCmtsMapDecodeControlTriggerLongGrant OBJECT-TYPE
       SYNTAX      INTEGER {
					triggerOn (1),
			            triggerOff (2)
				   }
       MAX-ACCESS  read-write
       STATUS      current
       DESCRIPTION
               "Data trigger."
       DEFVAL { triggerOff }
       ::= { basCmtsMapDecodeControlEntry 5 }

   basCmtsMapDecodeControlTriggerInitMaint OBJECT-TYPE
       SYNTAX      INTEGER {
					triggerOn (1),
			            triggerOff (2)
				   }
       MAX-ACCESS  read-write
       STATUS      current
       DESCRIPTION
               "Data trigger."
       DEFVAL { triggerOff }
       ::= { basCmtsMapDecodeControlEntry 6 }

   basCmtsMapDecodeControlTriggerStationMaint OBJECT-TYPE
       SYNTAX      INTEGER {
					triggerOn (1),
			            triggerOff(2)
				   }
       MAX-ACCESS  read-write
       STATUS      current
       DESCRIPTION
               "Data trigger."
       DEFVAL { triggerOff }
       ::= { basCmtsMapDecodeControlEntry 7 }

   basCmtsMapDecodeControlTriggerRequestIe OBJECT-TYPE
       SYNTAX      INTEGER {
					triggerOn (1),
			            triggerOff (2)
				   }
       MAX-ACCESS  read-write
       STATUS      current
       DESCRIPTION
               "Data trigger."
       DEFVAL { triggerOff }
       ::= { basCmtsMapDecodeControlEntry 8 }


 --
   -- ----------------------------------------------------------------------
   --
   -- Bas CMTS MAC To SID Objects
   --
   -- ----------------------------------------------------------------------
   --

   basCmtsMacToSidTable OBJECT-TYPE
       SYNTAX      SEQUENCE OF BasCmtsMacToSidEntry
       MAX-ACCESS  not-accessible
       STATUS      current
       DESCRIPTION
               "A list of BAS cmts mac to sid objects. "
       ::= { basCmtsMacToSidObjects 1 }

   basCmtsMacToSidEntry OBJECT-TYPE
       SYNTAX      BasCmtsMacToSidEntry
       MAX-ACCESS  not-accessible
       STATUS      current
       DESCRIPTION
               "An entry containing BAS CMTS MAC to SID settings."
       INDEX   { basCmtsMacToSidMacAddr }
       ::= {  basCmtsMacToSidTable 1 }

   BasCmtsMacToSidEntry ::=
       SEQUENCE {
           basCmtsMacToSidMacAddr  MacAddress,
           basCmtsMacToSidServiceId Integer32,
           basCmtsMacToSidType INTEGER
        }

   basCmtsMacToSidMacAddr OBJECT-TYPE
       SYNTAX      MacAddress
       MAX-ACCESS  read-only
       STATUS      current
       DESCRIPTION
               "The MAC address of the host or the cable modem"
       ::= { basCmtsMacToSidEntry 1 }

   basCmtsMacToSidServiceId OBJECT-TYPE
       SYNTAX      Integer32
       MAX-ACCESS  read-only
       STATUS      current
       DESCRIPTION
               "The SID of the host or the cable modem derived from
                the MAC"
       ::= { basCmtsMacToSidEntry 2 }


   basCmtsMacToSidType OBJECT-TYPE
       SYNTAX      INTEGER {
			      none (1),
			      cableModem(2),
			      host (3)
		      }
       MAX-ACCESS  read-only
       STATUS      current
       DESCRIPTION
               "Type of device attached to this SID"
       DEFVAL { none }
       ::= { basCmtsMacToSidEntry 3 }

   --
   -- ----------------------------------------------------------------------
   --
   -- End
   --
   -- ----------------------------------------------------------------------
   --

   END
