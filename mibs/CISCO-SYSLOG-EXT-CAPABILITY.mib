-- *****************************************************************
-- CISCO-SYSLOG-EXT-CAPABILITY.my:  Cisco Syslog Extension MIB 
--                             AGENT-CAPABILITIES
--
-- September 2005, Srini Kode
--
-- Copyright (c) 2005, 2006 by cisco Systems, Inc.
-- All rights reserved.
--
-- *****************************************************************

CISCO-SYSLOG-EXT-CAPABILITY DEFINITIONS ::= BEGIN


IMPORTS
        MODULE-IDENTITY
                FROM SNMPv2-SMI
        AGENT-CAPABILITIES
                FROM SNMPv2-CONF
        ciscoAgentCapability
                FROM CISCO-SMI;

ciscoSyslogExtCapability MODULE-IDENTITY
        LAST-UPDATED    "200604180000Z"
        ORGANIZATION    "Cisco Systems, Inc."
        CONTACT-INFO
                "       Cisco Systems
                        Customer Service

                Postal: 170 W Tasman Drive
                        San Jose, CA  95134
                        USA

                   Tel: +1 800 553-NETS

                E-mail: cs-san@cisco.com"
        DESCRIPTION
                "Agent capabilities for CISCO-SYSLOG-EXT-MIB."

        REVISION  "200604180000Z"
        DESCRIPTION
                "Added ciscoSyslogExtCapabilityACSWV03R0000 
                for Application Control Engine(ACE) module."
                
        REVISION  "200509010000Z"
        DESCRIPTION
                "Initial version of this MIB."
        ::= { ciscoAgentCapability 454 }

--
-- Agent capability for 3.0 (MDS Platform)
--
ciscoSyslogExtCapabilityMDS3R0 AGENT-CAPABILITIES

PRODUCT-RELEASE "Cisco MDS 3.0(1)"
        STATUS          current
        DESCRIPTION     "Cisco SYSLOG EXTENSION MIB capabilities"

        SUPPORTS        CISCO-SYSLOG-EXT-MIB
        INCLUDES        {
                           ciscoSyslogExtGroup 
                        }
                        
::= { ciscoSyslogExtCapability 1 }

ciscoSyslogExtCapabilityACSWV03R0000 AGENT-CAPABILITIES

PRODUCT-RELEASE "ACSW (Application Control Software) 3.0
                for Application Control Engine(ACE) module."
    STATUS          current
    DESCRIPTION     "CISCO-SYSLOG-EXT-MIB capabilities."
                
    SUPPORTS        CISCO-SYSLOG-EXT-MIB
    INCLUDES        { ciscoSyslogExtGroup,
                      ciscoSyslogProtocolGroup
                    }

    VARIATION    cseSyslogLogFileName
    ACCESS       not-implemented
    DESCRIPTION  "object not supported."
 
    VARIATION    cseSyslogLogFileMsgSeverity
    ACCESS       not-implemented
    DESCRIPTION  "object not supported."
 
    VARIATION    cseSyslogFileLoggingDisable
    ACCESS       not-implemented
    DESCRIPTION  "object not supported."
 
    VARIATION    cseSyslogLinecardEnable
    ACCESS       not-implemented
    DESCRIPTION  "object not supported."
 
    VARIATION    cseSyslogLinecardMsgSeverity
    ACCESS       not-implemented
    DESCRIPTION  "object not supported."
 
    VARIATION    cseSyslogMessageSeverity
    ACCESS       not-implemented
    DESCRIPTION  "object not supported."

    ::= { ciscoSyslogExtCapability 2 }

END
