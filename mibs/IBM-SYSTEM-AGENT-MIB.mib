IBM-SYSTEM-AGENT-MIB DEFINITIONS ::= BEGIN

IMPORTS
   OBJECT-TYPE
      FROM RFC-1212

   TRAP-TYPE
      FROM RFC-1215

   ibmSystemAgent,
   Boolean, Uint8, Sint8, Uint16, Sint16, Uint32,
   Sint32, Uint64, Sint64, Real32, Real64, String, Datetime
      FROM IBM-SYSTEM-MIB;

ibmSystemHTTPConfigurationTable OBJECT-TYPE
   SYNTAX         SEQUENCE OF IbmSystemHTTPConfigurationEntry
   ACCESS         not-accessible
   STATUS         mandatory
   DESCRIPTION    "The IBMPSG_HTTPConfiguration table contains configuration information for
                IBM Director Agent web based access"
   REFERENCE      "IBMPSG_HTTPConfiguration"
::= { ibmSystemAgent 2 }

ibmSystemHTTPConfigurationEntry OBJECT-TYPE
   SYNTAX         IbmSystemHTTPConfigurationEntry
   ACCESS         not-accessible
   STATUS         mandatory
   DESCRIPTION    "The index used by this table"
   INDEX          { ibmSystemHTTPConfigurationKeyIndex }
::= { ibmSystemHTTPConfigurationTable 1 }

IbmSystemHTTPConfigurationEntry ::= SEQUENCE
{
   ibmSystemHTTPConfigurationKeyIndex String,
   ibmSystemHTTPConfigurationSettingId String,
   ibmSystemHTTPConfigurationPort Uint16
}

ibmSystemHTTPConfigurationKeyIndex OBJECT-TYPE
   SYNTAX         String
   ACCESS         read-only
   STATUS         mandatory
   DESCRIPTION    "The index used by this table"
   REFERENCE      "IBMPSG_HTTPConfiguration.KeyIndex"
::= { ibmSystemHTTPConfigurationEntry 1 }

ibmSystemHTTPConfigurationSettingId OBJECT-TYPE
   SYNTAX         String
   ACCESS         read-only
   STATUS         mandatory
   DESCRIPTION    "Identifier by which this object is known."
   REFERENCE      "IBMPSG_HTTPConfiguration.SettingId"
::= { ibmSystemHTTPConfigurationEntry 2 }

ibmSystemHTTPConfigurationPort OBJECT-TYPE
   SYNTAX         Uint16
   ACCESS         read-only
   STATUS         mandatory
   DESCRIPTION    "Web based access port number"
   REFERENCE      "IBMPSG_HTTPConfiguration.Port"
::= { ibmSystemHTTPConfigurationEntry 3 }


-- IBMx_MgmtHwIPProtocolEndPoint 
-- Agent versions 5.20.3 and higher

ibmSystemMgmtHwIPEndPointTable OBJECT-TYPE
   SYNTAX         SEQUENCE OF IbmSystemMgmtHwIPEndPointEntry
   ACCESS         not-accessible
   STATUS         mandatory
   DESCRIPTION    "This table contains IP configuration information for the 
                   management hardware adapter"
   REFERENCE      "IBMx_MgmtHwIPProtocolEndPoint"
::= { ibmSystemAgent 3 }

ibmSystemMgmtHwIPEndPointEntry OBJECT-TYPE
   SYNTAX         IbmSystemMgmtHwIPEndPointEntry
   ACCESS         not-accessible
   STATUS         mandatory
   DESCRIPTION    "The index used by this table"
   INDEX          { ibmSystemHTTPConfigurationKeyIndex }
::= { ibmSystemMgmtHwIPEndPointTable 1 }

IbmSystemMgmtHwIPEndPointEntry ::= SEQUENCE
{
   ibmSystemMgmtHwIPEndPointKeyIndex String,
   ibmSystemMgmtHwIPEndPointAddressOrigin String,
   ibmSystemMgmtHwIPEndPointIPv4Address String,
   ibmSystemMgmtHwIPEndPointSubnetMask String,
   ibmSystemMgmtHwIPEndPointIPv6Address String
}

ibmSystemMgmtHwIPEndPointKeyIndex OBJECT-TYPE
   SYNTAX         String
   ACCESS         read-only
   STATUS         mandatory
   DESCRIPTION    "The index used by this table"
   REFERENCE      "IBMx_MgmtHwIPProtocolEndPoint.SystemName"
::= { ibmSystemMgmtHwIPEndPointEntry 1 }

ibmSystemMgmtHwIPEndPointAddressOrigin OBJECT-TYPE
   SYNTAX         String
   ACCESS         read-only
   STATUS         mandatory
   DESCRIPTION    "Indicates if the address is Static or DHCP"
   REFERENCE      "IBMx_MgmtHwIPProtocolEndPoint.AddressOrigin"
::= { ibmSystemMgmtHwIPEndPointEntry 2 }

ibmSystemMgmtHwIPEndPointIPv4Address OBJECT-TYPE
   SYNTAX         String
   ACCESS         read-only
   STATUS         mandatory
   DESCRIPTION    "The IPv4 address of the management endpoint"
   REFERENCE      "IBMx_MgmtHwIPProtocolEndPoint.IPv4Address"
::= { ibmSystemMgmtHwIPEndPointEntry 3 }

ibmSystemMgmtHwIPEndPointSubnetMask OBJECT-TYPE
   SYNTAX         String
   ACCESS         read-only
   STATUS         mandatory
   DESCRIPTION    "The subnet mask of the management endpoint"
   REFERENCE      "IBMx_MgmtHwIPProtocolEndPoint.SubnetMask"
::= { ibmSystemMgmtHwIPEndPointEntry 4 }

ibmSystemMgmtHwIPEndPointIPv6Address OBJECT-TYPE
   SYNTAX         String
   ACCESS         read-only
   STATUS         mandatory
   DESCRIPTION    "The IPv6 address of the management endpoint"
   REFERENCE      "IBMx_MgmtHwIPProtocolEndPoint.IPv6Address"
::= { ibmSystemMgmtHwIPEndPointEntry 5 }

END
