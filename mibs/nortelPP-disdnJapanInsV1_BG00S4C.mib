Nortel-Magellan-Passport-DisdnJapanInsMIB
DEFINITIONS ::= BEGIN



IMPORTS

      OBJECT-TYPE
   FROM RFC-1212

      passportMIBs
   FROM Nortel-Magellan-Passport-UsefulDefinitionsMIB

      DisplayString,
      StorageType,
      RowStatus,
      Unsigned32
   FROM Nortel-Magellan-Passport-StandardTextualConventionsMIB

      NonReplicated,
      Link
   FROM Nortel-Magellan-Passport-TextualConventionsMIB

      dataSigChanIndex,
      dataSigChan
   FROM Nortel-Magellan-Passport-DataIsdnMIB;




-- LAST-UPDATED   "9808030000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     DisdnJapanIns Enterprise MIB."

disdnJapanInsMIB OBJECT IDENTIFIER ::= { passportMIBs 118 }










-- DataSigChan/n JapanIns
-- The JapanIns component defines the operational characteristics of 
-- the signalling channel's connection to the external equipment.

dataSigChanIns OBJECT IDENTIFIER ::= { dataSigChan 11 }



dataSigChanInsRowStatusTable OBJECT-TYPE
   SYNTAX     SEQUENCE OF DataSigChanInsRowStatusEntry
   ACCESS     not-accessible
   STATUS     mandatory
   DESCRIPTION
     "This entry controls the addition and deletion of 
      dataSigChanIns components."
::= { dataSigChanIns 1 }

dataSigChanInsRowStatusEntry OBJECT-TYPE
   SYNTAX     DataSigChanInsRowStatusEntry
   ACCESS     not-accessible
   STATUS     mandatory
   DESCRIPTION
     "A single entry in the table represents a single 
      dataSigChanIns component."
   INDEX {
      dataSigChanIndex,
      dataSigChanInsIndex }
::= { dataSigChanInsRowStatusTable 1 }

DataSigChanInsRowStatusEntry ::= SEQUENCE {
   dataSigChanInsRowStatus
      RowStatus,
   dataSigChanInsComponentName
      DisplayString,
   dataSigChanInsStorageType
      StorageType,
   dataSigChanInsIndex
      NonReplicated }

dataSigChanInsRowStatus OBJECT-TYPE
   SYNTAX     RowStatus 
   ACCESS     read-write
   STATUS     mandatory
   DESCRIPTION
     "This variable is used as the basis for SNMP naming of
      dataSigChanIns components.
      These components can be added and deleted."
::= { dataSigChanInsRowStatusEntry 1 }

dataSigChanInsComponentName OBJECT-TYPE
   SYNTAX     DisplayString 
   ACCESS     read-only
   STATUS     mandatory
   DESCRIPTION
     "This variable provides the component's string name for
      use with the ASCII Console Interface"
::= { dataSigChanInsRowStatusEntry 2 }

dataSigChanInsStorageType OBJECT-TYPE
   SYNTAX     StorageType 
   ACCESS     read-only
   STATUS     mandatory
   DESCRIPTION
     "This variable represents the storage type value for the
      dataSigChanIns tables."
::= { dataSigChanInsRowStatusEntry 4 }

dataSigChanInsIndex OBJECT-TYPE
   SYNTAX     NonReplicated 
   ACCESS     not-accessible
   STATUS     mandatory
   DESCRIPTION
     "This variable represents the index for the dataSigChanIns tables."
::= { dataSigChanInsRowStatusEntry 10 }

dataSigChanInsL2Table OBJECT-TYPE
   SYNTAX     SEQUENCE OF DataSigChanInsL2Entry
   ACCESS     not-accessible
   STATUS     mandatory
   DESCRIPTION
     "This group represents the provisionable Layer 2 attributes of the 
      Q931 CCITT protocol."
::= { dataSigChanIns 11 }

dataSigChanInsL2Entry OBJECT-TYPE
   SYNTAX     DataSigChanInsL2Entry
   ACCESS     not-accessible
   STATUS     mandatory
   DESCRIPTION
     "An entry in the dataSigChanInsL2Table."
   INDEX {
      dataSigChanIndex,
      dataSigChanInsIndex }
::= { dataSigChanInsL2Table 1 }

DataSigChanInsL2Entry ::= SEQUENCE {
   dataSigChanInsT23
      Unsigned32,
   dataSigChanInsT200
      Unsigned32,
   dataSigChanInsN200
      Unsigned32,
   dataSigChanInsT203
      Unsigned32,
   dataSigChanInsN201
      Unsigned32,
   dataSigChanInsCircuitSwitchedK
      Unsigned32 }

dataSigChanInsT23 OBJECT-TYPE
   SYNTAX     Unsigned32 (1..15)
   ACCESS     read-write
   STATUS     mandatory
   DESCRIPTION
     "This attribute specifies the layer2 enable request timer."
   DEFVAL     { 10 }
::= { dataSigChanInsL2Entry 1 }

dataSigChanInsT200 OBJECT-TYPE
   SYNTAX     Unsigned32 (1..20)
   ACCESS     read-write
   STATUS     mandatory
   DESCRIPTION
     "This attribute specifies the maximum time between a layer 2 frame 
      and its acknowledgement"
   DEFVAL     { 2 }
::= { dataSigChanInsL2Entry 2 }

dataSigChanInsN200 OBJECT-TYPE
   SYNTAX     Unsigned32 (1..8)
   ACCESS     read-write
   STATUS     mandatory
   DESCRIPTION
     "This attribute specifies the maximum number of re-transmissions of 
      a layer2 frame."
   DEFVAL     { 3 }
::= { dataSigChanInsL2Entry 3 }

dataSigChanInsT203 OBJECT-TYPE
   SYNTAX     Unsigned32 (2..40)
   ACCESS     read-write
   STATUS     mandatory
   DESCRIPTION
     "This attribute specifies the maximum time that a no layer 2 traffic 
      situation can last. Expiry triggers a check on whether the far end is 
      a live."
   DEFVAL     { 10 }
::= { dataSigChanInsL2Entry 4 }

dataSigChanInsN201 OBJECT-TYPE
   SYNTAX     Unsigned32 (4..260)
   ACCESS     read-write
   STATUS     mandatory
   DESCRIPTION
     "This attribute specifies the maximum number of octets in an 
      information field."
   DEFVAL     { 260 }
::= { dataSigChanInsL2Entry 5 }

dataSigChanInsCircuitSwitchedK OBJECT-TYPE
   SYNTAX     Unsigned32 (1..632)
   ACCESS     read-write
   STATUS     mandatory
   DESCRIPTION
     "This attribute specifies the maximum number of frames for B 
      channel use."
   DEFVAL     { 7 }
::= { dataSigChanInsL2Entry 6 }

dataSigChanInsProvTable OBJECT-TYPE
   SYNTAX     SEQUENCE OF DataSigChanInsProvEntry
   ACCESS     not-accessible
   STATUS     mandatory
   DESCRIPTION
     "This group defines the general options of the d-channel signalling 
      link."
::= { dataSigChanIns 13 }

dataSigChanInsProvEntry OBJECT-TYPE
   SYNTAX     DataSigChanInsProvEntry
   ACCESS     not-accessible
   STATUS     mandatory
   DESCRIPTION
     "An entry in the dataSigChanInsProvTable."
   INDEX {
      dataSigChanIndex,
      dataSigChanInsIndex }
::= { dataSigChanInsProvTable 1 }

DataSigChanInsProvEntry ::= SEQUENCE {
   dataSigChanInsSide
      INTEGER }

dataSigChanInsSide OBJECT-TYPE
   SYNTAX     INTEGER  {
                 network(1),
                 user(2) }
   ACCESS     read-write
   STATUS     mandatory
   DESCRIPTION
     "This attribute specifies whether the layer 2 HDLC interface is the 
      network or user side of the connection."
   DEFVAL     { user }
::= { dataSigChanInsProvEntry 1 }

dataSigChanInsOperTable OBJECT-TYPE
   SYNTAX     SEQUENCE OF DataSigChanInsOperEntry
   ACCESS     not-accessible
   STATUS     mandatory
   DESCRIPTION
     "This group provides the operational attributes for the signalling 
      protocol."
::= { dataSigChanIns 15 }

dataSigChanInsOperEntry OBJECT-TYPE
   SYNTAX     DataSigChanInsOperEntry
   ACCESS     not-accessible
   STATUS     mandatory
   DESCRIPTION
     "An entry in the dataSigChanInsOperTable."
   INDEX {
      dataSigChanIndex,
      dataSigChanInsIndex }
::= { dataSigChanInsOperTable 1 }

DataSigChanInsOperEntry ::= SEQUENCE {
   dataSigChanInsActiveChannels
      Unsigned32,
   dataSigChanInsPeakActiveChannels
      Unsigned32,
   dataSigChanInsDChanStatus
      INTEGER }

dataSigChanInsActiveChannels OBJECT-TYPE
   SYNTAX     Unsigned32 (0..128)
   ACCESS     read-only
   STATUS     mandatory
   DESCRIPTION
     "This attribute indicates the number of currently active channels. 
      This includes data and voice channels."
   DEFVAL     { 0 }
::= { dataSigChanInsOperEntry 1 }

dataSigChanInsPeakActiveChannels OBJECT-TYPE
   SYNTAX     Unsigned32 (0..128)
   ACCESS     read-only
   STATUS     mandatory
   DESCRIPTION
     "This attribute indicates the maximum number of channels that have 
      been active on this signalling channel during the last polling period."
   DEFVAL     { 0 }
::= { dataSigChanInsOperEntry 4 }

dataSigChanInsDChanStatus OBJECT-TYPE
   SYNTAX     INTEGER  {
                 outOfService(0),
                 establishing(1),
                 established(2),
                 enabling(3),
                 inService(4),
                 restarting(5) }
   ACCESS     read-only
   STATUS     mandatory
   DESCRIPTION
     "This attribute indicates the state of the D-channel. 
      outOfService means that there is no layer 2 or layer 3 connectivity 
      to the PBX.
      establishing means that the signalling channel is attempting to stage 
      the layer 2.
      established means that the layer 2 is enabled. If the signalling 
      channel stays in the established state, then it is waiting for a restart 
      from the PBX.
      enabling means that the resources for processing calls are being 
      initialized. If the signalling channel stays in the enabling state then 
      it is waiting for a restart acknowledgement from the PBX. 
      inService means that the resources for processing calls are 
      available. 
      restarting means that the resources for call processing are being rei-
      initialized."
::= { dataSigChanInsOperEntry 7 }

dataSigChanInsToolsTable OBJECT-TYPE
   SYNTAX     SEQUENCE OF DataSigChanInsToolsEntry
   ACCESS     not-accessible
   STATUS     mandatory
   DESCRIPTION
     "This group contains a series of operational attributes which turn on 
      and off several kinds of tracing."
::= { dataSigChanIns 16 }

dataSigChanInsToolsEntry OBJECT-TYPE
   SYNTAX     DataSigChanInsToolsEntry
   ACCESS     not-accessible
   STATUS     mandatory
   DESCRIPTION
     "An entry in the dataSigChanInsToolsTable."
   INDEX {
      dataSigChanIndex,
      dataSigChanInsIndex }
::= { dataSigChanInsToolsTable 1 }

DataSigChanInsToolsEntry ::= SEQUENCE {
   dataSigChanInsTracing
      OCTET STRING }

dataSigChanInsTracing OBJECT-TYPE
   SYNTAX     OCTET STRING (SIZE (1))
   ACCESS     read-write
   STATUS     mandatory
   DESCRIPTION
     "This attribute defines which types of tracing are active for this 
      signalling channel.  The tracing messages are sent to the debug 
      stream. To see the messages the agentQueue attribute in Col/debug 
      must be greater than 0 and a Telnet NMIS session must list the 
      debug stream in in its data streams (ex. set nmis telnet session/1 
      dataStreams debug). Different types of tracing can be enabled 
      simultaneously. 
      Note that tracing consumes additional CPU resources and will slow 
      down call processing on a heavily loaded card.  If there is message 
      block exhaustion tracing will be suspended for a period and then 
      automatically reenabled.  An alarm is generated on tracing 
      suspension and resumption.  This mechanism protects the function 
      processor against excessive numbers of tracing messages.
      
      Types of tracing include: 
      protocolErrors - get details of any protocol errors which are 
      occuring. Protocol errors are also reported in summary form as 
      alarms. 
      q931Summary - Summary of the Q.931 messages on the signalling 
      link, including certain call details (calling number, called number, 
      release codes). 
      q931Hex - Q.931 messages displayed in hex format.  Useful to 
      determine protocol compliance in case of errors reported on local or 
      remote ends.
      q931Symbolic - Q.931 messages parsed to give maximum detail.  
      Useful for understanding content of messages flowing on the link.
      portHex - Messages in hex format being sent and received on the 
      link.

      Description of bits:
      protocolErrors(0)
      q931Summary(1)
      q931Hex(2)
      q931Symbolic(3)
      portHex(4)"
::= { dataSigChanInsToolsEntry 1 }


-- 
-- DataSigChan/n ts014 Framer
-- 
-- The Framer component controls link layer framing for application 
-- components sending and receiving data on a link interface. It is also 
-- through Framer, that an application component is associated with a 
-- specific hardware link interface.
-- 
-- The Framer component provides provisionable attributes related to 
-- datapath aspects of the hardware interface (such as crc and frame 
-- length). The Framer component also provides a provisionable 
-- attribute which binds the application component to a specific 
-- hardware component.
-- 
-- The Framer component contains operational attributes for link 
-- interface datapath statistics (such as frame counts and aborts).
-- 

dataSigChanInsFramer OBJECT IDENTIFIER ::= { dataSigChanIns 2 }



dataSigChanInsFramerRowStatusTable OBJECT-TYPE
   SYNTAX     SEQUENCE OF DataSigChanInsFramerRowStatusEntry
   ACCESS     not-accessible
   STATUS     mandatory
   DESCRIPTION
     "This entry controls the addition and deletion of 
      dataSigChanInsFramer components."
::= { dataSigChanInsFramer 1 }

dataSigChanInsFramerRowStatusEntry OBJECT-TYPE
   SYNTAX     DataSigChanInsFramerRowStatusEntry
   ACCESS     not-accessible
   STATUS     mandatory
   DESCRIPTION
     "A single entry in the table represents a single 
      dataSigChanInsFramer component."
   INDEX {
      dataSigChanIndex,
      dataSigChanInsIndex,
      dataSigChanInsFramerIndex }
::= { dataSigChanInsFramerRowStatusTable 1 }

DataSigChanInsFramerRowStatusEntry ::= SEQUENCE {
   dataSigChanInsFramerRowStatus
      RowStatus,
   dataSigChanInsFramerComponentName
      DisplayString,
   dataSigChanInsFramerStorageType
      StorageType,
   dataSigChanInsFramerIndex
      NonReplicated }

dataSigChanInsFramerRowStatus OBJECT-TYPE
   SYNTAX     RowStatus 
   ACCESS     read-only
   STATUS     mandatory
   DESCRIPTION
     "This variable is used as the basis for SNMP naming of
      dataSigChanInsFramer components.
      These components cannot be added nor deleted."
::= { dataSigChanInsFramerRowStatusEntry 1 }

dataSigChanInsFramerComponentName OBJECT-TYPE
   SYNTAX     DisplayString 
   ACCESS     read-only
   STATUS     mandatory
   DESCRIPTION
     "This variable provides the component's string name for
      use with the ASCII Console Interface"
::= { dataSigChanInsFramerRowStatusEntry 2 }

dataSigChanInsFramerStorageType OBJECT-TYPE
   SYNTAX     StorageType 
   ACCESS     read-only
   STATUS     mandatory
   DESCRIPTION
     "This variable represents the storage type value for the
      dataSigChanInsFramer tables."
::= { dataSigChanInsFramerRowStatusEntry 4 }

dataSigChanInsFramerIndex OBJECT-TYPE
   SYNTAX     NonReplicated 
   ACCESS     not-accessible
   STATUS     mandatory
   DESCRIPTION
     "This variable represents the index for the dataSigChanInsFramer tables."
::= { dataSigChanInsFramerRowStatusEntry 10 }

dataSigChanInsFramerProvTable OBJECT-TYPE
   SYNTAX     SEQUENCE OF DataSigChanInsFramerProvEntry
   ACCESS     not-accessible
   STATUS     mandatory
   DESCRIPTION
     "This group contains the base provisioning data for the Framer 
      component. Application or hardware interface specific provisioning 
      data is contained in other provisionable Framer groups."
::= { dataSigChanInsFramer 10 }

dataSigChanInsFramerProvEntry OBJECT-TYPE
   SYNTAX     DataSigChanInsFramerProvEntry
   ACCESS     not-accessible
   STATUS     mandatory
   DESCRIPTION
     "An entry in the dataSigChanInsFramerProvTable."
   INDEX {
      dataSigChanIndex,
      dataSigChanInsIndex,
      dataSigChanInsFramerIndex }
::= { dataSigChanInsFramerProvTable 1 }

DataSigChanInsFramerProvEntry ::= SEQUENCE {
   dataSigChanInsFramerInterfaceName
      Link }

dataSigChanInsFramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { dataSigChanInsFramerProvEntry 1 }

dataSigChanInsFramerStateTable OBJECT-TYPE
   SYNTAX     SEQUENCE OF DataSigChanInsFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { dataSigChanInsFramer 12 }

dataSigChanInsFramerStateEntry OBJECT-TYPE
   SYNTAX     DataSigChanInsFramerStateEntry
   ACCESS     not-accessible
   STATUS     mandatory
   DESCRIPTION
     "An entry in the dataSigChanInsFramerStateTable."
   INDEX {
      dataSigChanIndex,
      dataSigChanInsIndex,
      dataSigChanInsFramerIndex }
::= { dataSigChanInsFramerStateTable 1 }

DataSigChanInsFramerStateEntry ::= SEQUENCE {
   dataSigChanInsFramerAdminState
      INTEGER,
   dataSigChanInsFramerOperationalState
      INTEGER,
   dataSigChanInsFramerUsageState
      INTEGER }

dataSigChanInsFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { dataSigChanInsFramerStateEntry 1 }

dataSigChanInsFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { dataSigChanInsFramerStateEntry 2 }

dataSigChanInsFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { dataSigChanInsFramerStateEntry 3 }

dataSigChanInsFramerStatsTable OBJECT-TYPE
   SYNTAX     SEQUENCE OF DataSigChanInsFramerStatsEntry
   ACCESS     not-accessible
   STATUS     mandatory
   DESCRIPTION
     "This group contains the operational statistics data for a Framer 
      component."
::= { dataSigChanInsFramer 13 }

dataSigChanInsFramerStatsEntry OBJECT-TYPE
   SYNTAX     DataSigChanInsFramerStatsEntry
   ACCESS     not-accessible
   STATUS     mandatory
   DESCRIPTION
     "An entry in the dataSigChanInsFramerStatsTable."
   INDEX {
      dataSigChanIndex,
      dataSigChanInsIndex,
      dataSigChanInsFramerIndex }
::= { dataSigChanInsFramerStatsTable 1 }

DataSigChanInsFramerStatsEntry ::= SEQUENCE {
   dataSigChanInsFramerFrmToIf
      Unsigned32,
   dataSigChanInsFramerFrmFromIf
      Unsigned32,
   dataSigChanInsFramerOctetFromIf
      Unsigned32,
   dataSigChanInsFramerAborts
      Unsigned32,
   dataSigChanInsFramerCrcErrors
      Unsigned32,
   dataSigChanInsFramerLrcErrors
      Unsigned32,
   dataSigChanInsFramerNonOctetErrors
      Unsigned32,
   dataSigChanInsFramerOverruns
      Unsigned32,
   dataSigChanInsFramerUnderruns
      Unsigned32,
   dataSigChanInsFramerLargeFrmErrors
      Unsigned32 }

dataSigChanInsFramerFrmToIf OBJECT-TYPE
   SYNTAX     Unsigned32 (0..4294967295)
   ACCESS     read-only
   STATUS     mandatory
   DESCRIPTION
     "This attribute counts the number of frames transmitted to the link 
      interface by Framer.
      This count wraps to zero after reaching its maximum value."
   DEFVAL     { 0 }
::= { dataSigChanInsFramerStatsEntry 1 }

dataSigChanInsFramerFrmFromIf OBJECT-TYPE
   SYNTAX     Unsigned32 (0..4294967295)
   ACCESS     read-only
   STATUS     mandatory
   DESCRIPTION
     "This attribute counts the number of frames received from the link 
      interface by Framer.
      This count wraps to zero after reaching its maximum value."
   DEFVAL     { 0 }
::= { dataSigChanInsFramerStatsEntry 2 }

dataSigChanInsFramerOctetFromIf OBJECT-TYPE
   SYNTAX     Unsigned32 (0..4294967295)
   ACCESS     read-only
   STATUS     mandatory
   DESCRIPTION
     "The number of bytes received from the link interface by Framer."
   DEFVAL     { 0 }
::= { dataSigChanInsFramerStatsEntry 3 }

dataSigChanInsFramerAborts OBJECT-TYPE
   SYNTAX     Unsigned32 (0..4294967295)
   ACCESS     read-only
   STATUS     mandatory
   DESCRIPTION
     "This attribute counts the total number of aborts received.
      This count wraps to zero after reaching its maximum value."
   DEFVAL     { 0 }
::= { dataSigChanInsFramerStatsEntry 4 }

dataSigChanInsFramerCrcErrors OBJECT-TYPE
   SYNTAX     Unsigned32 (0..4294967295)
   ACCESS     read-only
   STATUS     mandatory
   DESCRIPTION
     "This attribute counts the total number of frames with CRC errors.
      This count wraps to zero after reaching its maximum value."
   DEFVAL     { 0 }
::= { dataSigChanInsFramerStatsEntry 5 }

dataSigChanInsFramerLrcErrors OBJECT-TYPE
   SYNTAX     Unsigned32 (0..4294967295)
   ACCESS     read-only
   STATUS     mandatory
   DESCRIPTION
     "This attribute counts the total number of frames with LRC errors.
      This count wraps to zero after reaching its maximum value."
   DEFVAL     { 0 }
::= { dataSigChanInsFramerStatsEntry 6 }

dataSigChanInsFramerNonOctetErrors OBJECT-TYPE
   SYNTAX     Unsigned32 (0..4294967295)
   ACCESS     read-only
   STATUS     mandatory
   DESCRIPTION
     "This attribute counts the total number of frames that were non octet 
      aligned.
      This count wraps to zero after reaching its maximum value."
   DEFVAL     { 0 }
::= { dataSigChanInsFramerStatsEntry 7 }

dataSigChanInsFramerOverruns OBJECT-TYPE
   SYNTAX     Unsigned32 (0..4294967295)
   ACCESS     read-only
   STATUS     mandatory
   DESCRIPTION
     "This attribute counts the total number of frames received from the 
      link for which overruns occurred.
      This count wraps to zero after reaching its maximum value."
   DEFVAL     { 0 }
::= { dataSigChanInsFramerStatsEntry 8 }

dataSigChanInsFramerUnderruns OBJECT-TYPE
   SYNTAX     Unsigned32 (0..4294967295)
   ACCESS     read-only
   STATUS     mandatory
   DESCRIPTION
     "This attribute counts the total number of frames transmitted to the 
      link for which underruns occurred.
      This count wraps to zero after reaching its maximum value."
   DEFVAL     { 0 }
::= { dataSigChanInsFramerStatsEntry 9 }

dataSigChanInsFramerLargeFrmErrors OBJECT-TYPE
   SYNTAX     Unsigned32 (0..4294967295)
   ACCESS     read-only
   STATUS     mandatory
   DESCRIPTION
     "This attribute counts the total number of frames received which 
      were too large. The frame was longer than 500 bytes.
      This count wraps to zero after reaching its maximum value."
   DEFVAL     { 0 }
::= { dataSigChanInsFramerStatsEntry 10 }




-- 
-- Version and Compliance statements
-- 



-- Object-Group Statement:
-- A list of all current accessible leaf objects.

-- OBJECTS { dataSigChanInsFramerOctetFromIf,
--           dataSigChanInsT203,
--           dataSigChanInsFramerFrmToIf,
--           dataSigChanInsDChanStatus,
--           dataSigChanInsFramerAdminState,
--           dataSigChanInsFramerLrcErrors,
--           dataSigChanInsFramerOverruns,
--           dataSigChanInsFramerAborts,
--           dataSigChanInsFramerRowStatus,
--           dataSigChanInsFramerLargeFrmErrors,
--           dataSigChanInsTracing,
--           dataSigChanInsFramerStorageType,
--           dataSigChanInsRowStatus,
--           dataSigChanInsN201,
--           dataSigChanInsT23,
--           dataSigChanInsFramerNonOctetErrors,
--           dataSigChanInsPeakActiveChannels,
--           dataSigChanInsFramerUsageState,
--           dataSigChanInsStorageType,
--           dataSigChanInsFramerComponentName,
--           dataSigChanInsN200,
--           dataSigChanInsFramerFrmFromIf,
--           dataSigChanInsFramerInterfaceName,
--           dataSigChanInsComponentName,
--           dataSigChanInsCircuitSwitchedK,
--           dataSigChanInsFramerUnderruns,
--           dataSigChanInsSide,
--           dataSigChanInsFramerCrcErrors,
--           dataSigChanInsActiveChannels,
--           dataSigChanInsFramerOperationalState,
--           dataSigChanInsT200 }
-- STATUS  mandatory
-- DESCRIPTION
--   "A list of all current accessible leaf objects."

disdnJapanInsGroup OBJECT IDENTIFIER ::= { disdnJapanInsMIB 1 }
disdnJapanInsGroupBE OBJECT IDENTIFIER ::= { disdnJapanInsGroup 5 }
disdnJapanInsGroupBE00 OBJECT IDENTIFIER ::= { disdnJapanInsGroupBE 1 }
disdnJapanInsGroupBE00A OBJECT IDENTIFIER ::= { disdnJapanInsGroupBE00 2 }



-- Agent-Capabilities Statement:

-- PRODUCT-RELEASE "Passport Release 7.0 DisdnJapanIns."
-- STATUS          mandatory
-- DESCRIPTION     "DisdnJapanIns MIB: MIB Version BE00A,
--                  Software Version BG00S4C."
-- SUPPORTS        Nortel-Magellan-Passport-DisdnJapanInsMIB
--    INCLUDES     { disdnJapanInsGroupBE00A }

disdnJapanInsCapabilities OBJECT IDENTIFIER ::= { disdnJapanInsMIB 3 }
disdnJapanInsCapabilitiesBE OBJECT IDENTIFIER ::= { disdnJapanInsCapabilities 5 }
disdnJapanInsCapabilitiesBE00 OBJECT IDENTIFIER ::= { disdnJapanInsCapabilitiesBE 1 }
disdnJapanInsCapabilitiesBE00A OBJECT IDENTIFIER ::= { disdnJapanInsCapabilitiesBE00 2 }





END
