-- Copyright 2000 by Marconi Communications

Fore-FAST-MIB	 DEFINITIONS ::= BEGIN

IMPORTS
        OBJECT-TYPE,
	Counter32	FROM SNMPv2-SMI
        ifIndex         FROM IF-MIB
	asx		FROM Fore-Common-MIB;

-- The the foreFASTIWFIfgroup definition

foreFastGroup	OBJECT IDENTIFIER ::= { asx 21 }

--
-- FastIwf Table Definition
--

foreFastIfTable OBJECT-TYPE
        SYNTAX  SEQUENCE OF ForeFastIfEntry
        MAX-ACCESS  not-accessible
        STATUS  current
        DESCRIPTION
                "A table containing FAST interface configuration and status."
        ::= { foreFastGroup 1 }

foreFastIfEntry OBJECT-TYPE
        SYNTAX  ForeFastIfEntry
        MAX-ACCESS  not-accessible
        STATUS  current
        DESCRIPTION
                "A table entry containing the FAST interface information."
        INDEX  { ifIndex }
        ::= { foreFastIfTable 1 }

ForeFastIfEntry ::= 
        SEQUENCE {
                foreFastIfFramingMode  INTEGER,
                foreFastIfAdminStatus  INTEGER
        }

foreFastIfFramingMode OBJECT-TYPE
        SYNTAX  INTEGER {
                         mode0(1)
                }
        MAX-ACCESS  read-only
        STATUS  current
        DESCRIPTION 
                "Indicates the operational Framing mode on this interface."
        ::= { foreFastIfEntry 1 }

foreFastIfAdminStatus OBJECT-TYPE
        SYNTAX  INTEGER {
                        up(1),
                        down(2)
                }
        MAX-ACCESS  read-write
        STATUS  current
        DESCRIPTION
	        "Indicates the admin status of this interface."
        ::= { foreFastIfEntry 2 }

-- 
-- Definition of FAST IWF statistics 
-- 
foreFastIwfStatsTable OBJECT-TYPE
        SYNTAX  SEQUENCE OF ForeFastIwfStatsEntry
        MAX-ACCESS  not-accessible
        STATUS  current
        DESCRIPTION
                "A table containing Fast IWF interface Statistics"
        ::= { foreFastGroup 2 }

foreFastIwfStatsEntry OBJECT-TYPE
        SYNTAX  ForeFastIwfStatsEntry
        MAX-ACCESS  not-accessible
        STATUS  current
        DESCRIPTION
                "A table entry containing the FastIwf statistics."
        INDEX  { ifIndex }
        ::= { foreFastIwfStatsTable 1 }

ForeFastIwfStatsEntry ::= 
        SEQUENCE {
                foreFastIwfTxCells   		Counter32,
		foreFastIwfTxOctets    		Counter32,
		foreFastIwfTxPackets    	Counter32,
		foreFastIwfTxHdrLookupErr  	Counter32,
		foreFastIwfTxResourceFail    	Counter32,
		foreFastIwfRxCells 		Counter32,
		foreFastIwfRxOctets		Counter32,
		foreFastIwfRxPackets    	Counter32,
		foreFastIwfRxHdrLookupErr	Counter32,
		foreFastIwfRxResourceFail	Counter32
        }

foreFastIwfTxCells OBJECT-TYPE
	SYNTAX Counter32
	MAX-ACCESS read-only
	STATUS current
	DESCRIPTION
		"The number of cells that have arrived at the ATM SAP from the upper layer."
	::= { foreFastIwfStatsEntry 1 }

foreFastIwfTxOctets OBJECT-TYPE
	SYNTAX Counter32
	MAX-ACCESS read-only
	STATUS current
	DESCRIPTION
		"The number of octets that the FAST Packet to ATM cells layer has passed to the lower layer."
	::= { foreFastIwfStatsEntry 2 }

foreFastIwfTxPackets OBJECT-TYPE
	SYNTAX Counter32
	MAX-ACCESS read-only
	STATUS current
	DESCRIPTION
		"The number of pkts that the FAST Packet to ATM cells layer has passed to the lower layer."
	::= { foreFastIwfStatsEntry 3 }

foreFastIwfTxHdrLookupErr OBJECT-TYPE
	SYNTAX Counter32
	MAX-ACCESS read-only
	STATUS current
	DESCRIPTION
		"The number of cells that the FAST Packet to ATM Cells layer has discarded due to addressing errors."
	::= { foreFastIwfStatsEntry 4 }

foreFastIwfTxResourceFail OBJECT-TYPE
	SYNTAX Counter32
	MAX-ACCESS read-only
	STATUS current
	DESCRIPTION
		"The number of cells that the FAST Packet To ATM Cells layer has discarded due to resource limitations."
	::= { foreFastIwfStatsEntry 5 }

foreFastIwfRxCells OBJECT-TYPE
	SYNTAX Counter32
	MAX-ACCESS read-only
	STATUS current
	DESCRIPTION
		"The number of cells that the ATM SAP has passed to the upper layer."
	::= { foreFastIwfStatsEntry 6 }
	
foreFastIwfRxOctets OBJECT-TYPE
	SYNTAX Counter32
	MAX-ACCESS read-only
	STATUS current
	DESCRIPTION
		"The number of octets that the FAST Packet to ATM Cells layer has received from the lower layer."	
	::= { foreFastIwfStatsEntry 7 }


foreFastIwfRxPackets OBJECT-TYPE
	SYNTAX Counter32
	MAX-ACCESS read-only
	STATUS current
	DESCRIPTION
		"The number of FAST Packet to ATM Cells layer has received from the lower layer."	
	::= { foreFastIwfStatsEntry 8 }	

foreFastIwfRxHdrLookupErr OBJECT-TYPE
	SYNTAX Counter32
	MAX-ACCESS read-only
	STATUS current
	DESCRIPTION
		"The number of packets that the FAST Packet to ATM Cells layer has discarded due to addressing errors."
	::= { foreFastIwfStatsEntry 9 }

foreFastIwfRxResourceFail OBJECT-TYPE
	SYNTAX Counter32
	MAX-ACCESS read-only
	STATUS current
	DESCRIPTION
		"The number of packets that the FAST Packet to ATM Cells layer has discarded due to resource limitations."
	::= { foreFastIwfStatsEntry 10 }

END
