-- *****************************************************************
-- Unisphere-Data-FRAME-RELAY-MIB
--
-- Unisphere Networks Inc. Enterprise MIB
-- Frame Relay MIB
--
-- Copyright (c) 1998, 1999 Redstone Communications, Incorporated.
-- Copyright (c) 1999, 2002 Unisphere Networks, Incorporated.
-- All Rights Reserved.
-- *****************************************************************

Unisphere-Data-FRAME-RELAY-MIB DEFINITIONS ::= BEGIN

IMPORTS
    MODULE-IDENTITY,
    OBJECT-TYPE,
    Integer32,
    Counter32,
    TimeTicks
        FROM SNMPv2-SMI

    RowStatus,
    TimeStamp
        FROM SNMPv2-TC

    MODULE-COMPLIANCE, 
    OBJECT-GROUP  
        FROM SNMPv2-CONF

    InterfaceIndex,
    InterfaceIndexOrZero
        FROM IF-MIB

    DLCI
        FROM FRAME-RELAY-DTE-MIB

    usDataMibs
        FROM Unisphere-Data-MIBs

    UsdNextIfIndex
        FROM Unisphere-Data-TC;


usdFrameRelayMIB  MODULE-IDENTITY
    LAST-UPDATED "200009261730Z" -- 26-Sep-00 1:30 PM EDT
    ORGANIZATION "Unisphere Networks, Inc."
    CONTACT-INFO
        "       Unisphere Networks, Inc.
        Postal: 10 Technology Park Drive
                Westford MA  01886
                USA
        Tel:    +1 978 589 5800
        Email:  mib@UnisphereNetworks.com"
    DESCRIPTION
        "The Frame Relay MIB for the Unisphere Networks Inc. enterprise."
    -- Revision History
    REVISION      "200009261730Z" -- 26-Sep-00 1:30 PM EDT  kwc
    DESCRIPTION
        "Make it SMIv2 conformant."
    REVISION      "9906010000Z" -- 1-Jun-99
    DESCRIPTION
        "Add support for NNI behavior."
    REVISION      "9811130000Z" -- 13-Nov-98
    DESCRIPTION
        "Initial version of this MIB module."
    ::= { usDataMibs 10 }

-- ++++++++++++++++++++++++++++++++++++++++++++++++++++++++++++++++++++++
-- Textual conventions
-- ++++++++++++++++++++++++++++++++++++++++++++++++++++++++++++++++++++++

-- No textual conventions are defined in this MIB.


-- ++++++++++++++++++++++++++++++++++++++++++++++++++++++++++++++++++++++
-- Managed objects
-- ++++++++++++++++++++++++++++++++++++++++++++++++++++++++++++++++++++++

usdFrObjects     OBJECT IDENTIFIER ::= { usdFrameRelayMIB 1 }

-- 
-- This MIB contains managed objects for each of two interface
-- layers: Frame Relay interfaces, and Frame Relay subinterfaces. 
-- For each of these layers, management objects are provided to 
-- query for an available interface index, and to create/delete 
-- interfaces of that type. Creating/deleting these interface 
-- types using this MIB has the side effect of creating/deleting 
-- corresponding entries in the Interface MIB ifTable/ifXTable, 
-- and in the Unisphere Enterprise Interface MIB usdIfTable.
--
-- 
--

usdFrIfLayer        OBJECT IDENTIFIER ::= { usdFrObjects 1 }
usdFrSubIfLayer     OBJECT IDENTIFIER ::= { usdFrObjects 2 }


-- //////////////////////////////////////////////////////////////////////
--
-- Frame Relay Interface Layer
--
-- This layer is managed with the following elements:
--
--  o NextIfIndex (generator for Frame Relay IfIndex selection)
--  o Dlcmi Table (creation/configuration/deletion of Frame Relay interfaces)
--  o Dlcmi Statistics Table (Frame Relay interface statistics)
--  o Circuit Table (status of Frame Relay circuits)
--
-- //////////////////////////////////////////////////////////////////////

--
-- IfIndex selection for creating new Frame Relay interfaces
--

usdFrNextIfIndex OBJECT-TYPE
    SYNTAX      UsdNextIfIndex
    MAX-ACCESS  read-only
    STATUS      current
    DESCRIPTION
        "Coordinate ifIndex value allocation for entries
        in usdFrDlcmiTable.

        A GET of this object returns the next available ifIndex 
        value to be used to create an entry in the associated
        interface table; or zero, if no valid ifIndex value is
        available. This object also returns a value of zero when 
        it is the lexicographic successor of a varbind presented 
        in an SNMP GETNEXT or GETBULK request, for which circumstance
        it is assumed that ifIndex allocation is unintended.

        Successive GETs will typically return different
        values, thus avoiding collisions among cooperating
        management clients seeking to create table entries
        simultaneously.
        "
    ::= { usdFrIfLayer 1 }

--
-- The Frame Relay Dlcmi Table
--

usdFrDlcmiTable OBJECT-TYPE
    SYNTAX      SEQUENCE OF UsdFrDlcmiEntry
    MAX-ACCESS  not-accessible
    STATUS      current
    DESCRIPTION
        "The Parameters for the Data Link Connection Management
        Interface for the frame relay service on this interface.
        
        This table represents a superset of functionality specified in
        RFC2115 FRAME-RELAY-DTE-MIB. In particular, it adds attributes
        that permit the interface to operate as a network-side (DCE)
        interface."
    REFERENCE
        "American National Standard T1.617-1991, Annex D"
    ::= { usdFrIfLayer 2 }

usdFrDlcmiEntry OBJECT-TYPE
    SYNTAX      UsdFrDlcmiEntry
    MAX-ACCESS  not-accessible
    STATUS      current
    DESCRIPTION
        "The Parameters for a particular Data Link Connection
        Management Interface.

        Creating/deleting entries in this table causes corresponding 
        entries for be created/deleted in ifTable/ifXTable/usdIfTable,
        and usdFrDlcmiStatsTable.

        Creating/deleting user-side (DTE) entries in this table also causes
        coresponding entries to be created/deleted in RFC2115 frDlcmiTable.

        The organization and definitions of objects in this table are 
        intentionally aligned closely to those in RFC2115."
    INDEX   { usdFrDlcmiIfIndex }
    ::= { usdFrDlcmiTable 1 }

UsdFrDlcmiEntry ::= SEQUENCE {
    usdFrDlcmiIfIndex                        InterfaceIndex,
    usdFrDlcmiState                          INTEGER,
    usdFrDlcmiAddress                        INTEGER,
    usdFrDlcmiAddressLen                     INTEGER,
    usdFrDlcmiPollingInterval                Integer32,
    usdFrDlcmiFullEnquiryInterval            Integer32,
    usdFrDlcmiErrorThreshold                 Integer32,
    usdFrDlcmiMonitoredEvents                Integer32,
    usdFrDlcmiMaxSupportedVCs                DLCI,
    usdFrDlcmiMulticast                      INTEGER,
    usdFrDlcmiStatus                         INTEGER,
    usdFrDlcmiRowStatus                      RowStatus,
    usdFrDlcmiLowerIfIndex                   InterfaceIndexOrZero,
    usdFrDlcmiRole                           INTEGER,
    usdFrDlcmiDcePollingInterval             Integer32,
    usdFrDlcmiDceErrorThreshold              Integer32,
    usdFrDlcmiDceMonitoredEvents             Integer32
}


usdFrDlcmiIfIndex OBJECT-TYPE
    SYNTAX      InterfaceIndex
    MAX-ACCESS  read-only
    STATUS      current
    DESCRIPTION
        "The ifIndex value of the corresponding ifEntry."
    ::= { usdFrDlcmiEntry 1 }


usdFrDlcmiState OBJECT-TYPE
    SYNTAX      INTEGER {
                    noLmiConfigured (1),
                    lmiRev1         (2),
                    ansiT1617D      (3),  -- ANSI T1.617 Annex D
                    ansiT1617B      (4),  -- ANSI T1.617 Annex B
                    itut933A        (5),  -- CCITT Q933 Annex A
                    ansiT1617D1994  (6)   -- ANSI T1.617a-1994 Annex D
                }
    MAX-ACCESS  read-create
    STATUS      current
    DESCRIPTION
        "This variable states which Data Link Connection
        Management scheme is active (and by implication, what
        DLCI it uses) on the Frame Relay interface."
    REFERENCE
        "American National Standard T1.617-1991, American
        National Standard T1.617a-1994, ITU-T Recommendation
        Q.933 (03/93)."
    ::= { usdFrDlcmiEntry 2 }

usdFrDlcmiAddress OBJECT-TYPE
    SYNTAX      INTEGER {
                    q921           (1),  -- 13 bit DLCI
                    q922March90    (2),  -- 11 bit DLCI
                    q922November90 (3),  -- 10 bit DLCI
                    q922           (4)   -- Final Standard
                }
    MAX-ACCESS  read-create
    STATUS      current
    DESCRIPTION
        "This variable states which address format is in use on
        the Frame Relay interface."
    DEFVAL { q922 }
    ::= { usdFrDlcmiEntry 3 }


usdFrDlcmiAddressLen OBJECT-TYPE
    SYNTAX      INTEGER     {
                    twoOctets (2),
                    threeOctets (3),
                    fourOctets (4)
                }
    MAX-ACCESS  read-create
    STATUS      current
    DESCRIPTION
        "This variable states the address length in octets.  In
        the case of Q922 format, the length indicates the
        entire length of the address including the control
        portion."
    DEFVAL { twoOctets }
    ::= { usdFrDlcmiEntry 4 }


usdFrDlcmiPollingInterval OBJECT-TYPE
    SYNTAX      Integer32 (5..30)
    UNITS       "seconds"
    MAX-ACCESS  read-create
    STATUS      current
    DESCRIPTION
        "This is the number of seconds between successive
        status enquiry messages sent by the DTE.

        Pertains to DTE/NNI operation only. This parameter can
        be reconfigured only when the Frame Relay interface 
        is acting as a DTE or NNI."
    REFERENCE
        "American National Standard T1.617-1991, Section D.7
        Timer T391."
    DEFVAL  { 10 }
    ::= { usdFrDlcmiEntry 5 }

usdFrDlcmiFullEnquiryInterval OBJECT-TYPE
    SYNTAX      Integer32 (1..255)
    MAX-ACCESS  read-create
    STATUS      current
    DESCRIPTION
        "Number of status enquiry intervals that pass before
        issuance of a full status enquiry message.

        Pertains to DTE/NNI operation only. This parameter can
        be reconfigured only when the Frame Relay interface 
        is acting as a DTE or NNI."
    REFERENCE
        "American National Standard T1.617-1991, Section D.7
        Counter N391."
    DEFVAL  { 6 }
    ::= { usdFrDlcmiEntry 6 }


usdFrDlcmiErrorThreshold OBJECT-TYPE
    SYNTAX      Integer32 (1..10)
    MAX-ACCESS  read-create
    STATUS      current
    DESCRIPTION
        "The minimum number of errors that must be observed 
        within the number of events specified by usdFrDlcmiMonitoredEvents,
        to declare the interface down.
        
        'error' is lack of receipt of a Status, in response to an 
        issued Status Enquiry, within the Polling Interval (T391).

        Pertains to DTE/NNI operation only. This parameter can
        be reconfigured only when the Frame Relay interface 
        is acting as a DTE or NNI."
    REFERENCE
        "American National Standard T1.617-1991, Section D.5.1
        Counter N392."
    DEFVAL  { 3 }
    ::= { usdFrDlcmiEntry 7 }


usdFrDlcmiMonitoredEvents OBJECT-TYPE
    SYNTAX      Integer32 (1..10)
    MAX-ACCESS  read-create
    STATUS      current
    DESCRIPTION
        "The number of status polling intervals over which the 
        error threshold is counted.  For example, if within 
        'MonitoredEvents' number of events the station receives 
        'ErrorThreshold' number of errors, the interface is 
        marked as down.

        'status polling interval' is specified by
        usdFrDlcmiPollingInterval.

        Pertains to DTE/NNI operation only. This parameter can
        be reconfigured only when the Frame Relay interface 
        is acting as a DTE or NNI."
    REFERENCE
        "American National Standard T1.617-1991, Section D.5.2
        Counter N393."
    DEFVAL  { 4 }
    ::= { usdFrDlcmiEntry 8 }

usdFrDlcmiMaxSupportedVCs OBJECT-TYPE
    SYNTAX      DLCI
    MAX-ACCESS  read-create
    STATUS      current
    DESCRIPTION
        "The maximum number of Virtual Circuits allowed for
        this interface.  Usually dictated by the Frame Relay
        network.

        In response to a SET, if a value less than zero or
        higher than the agent's maximal capability is
        configured, the agent should respond badValue."
    ::= { usdFrDlcmiEntry 9 }


usdFrDlcmiMulticast OBJECT-TYPE
    SYNTAX      INTEGER {
                    nonBroadcast (1),
                    broadcast (2)
                }
    MAX-ACCESS  read-create
    STATUS      current
    DESCRIPTION
        "This indicates whether the Frame Relay interface is
        using a multicast service."
    DEFVAL { nonBroadcast }
    ::= { usdFrDlcmiEntry 10 }


usdFrDlcmiStatus OBJECT-TYPE
    SYNTAX      INTEGER {
                    running      (1),    -- init complete, system running
                    fault        (2),    -- error threshold exceeded
                    initializing (3)     -- system start up
                }
    MAX-ACCESS  read-only
    STATUS      current
    DESCRIPTION
        "This indicates the status of the Frame Relay interface
        as determined by the performance of the dlcmi.  If no
        dlcmi is running, the Frame Relay interface will stay
        in the running state indefinitely."
    ::= { usdFrDlcmiEntry 11 }

usdFrDlcmiRowStatus OBJECT-TYPE
    SYNTAX      RowStatus
    MAX-ACCESS  read-create
    STATUS      current
    DESCRIPTION
        "Controls creation/deletion of entries in this table
        according to the RowStatus textual convention, 
        constrained to support the following values only:

            createAndGo
            destroy
            
        To create an entry in this table, the following 
        entry objects MUST be explicitly configured:

            usdFrDlcmiRowStatus
            usdFrDlcmiState
            usdFrDlcmiMaxSupportedVCs
            usdFrDlcmiLowerIfIndex
            usdFrDlcmiRole

        In addition, when creating an entry the following
        conditions must hold:

            A value for usdFrDlcmiIndex must have been determined
            previously, by reading usdFrNextIfIndex. 

            The interface identified by usdFrDlcmiLowerIfIndex
            must exist, and must be an interface type that
            permits layering of Frame Relay above it.

        A corresponding entry in ifTable/ifXTable/usdIfTable is 
        created/destroyed as a result of creating/destroying an entry 
        in this table. If usdFrDlcmiRole is dte(0), a corresponding
        entry is created/deleted in frDlcmiTable."
    ::= { usdFrDlcmiEntry 12 }


usdFrDlcmiLowerIfIndex OBJECT-TYPE
    SYNTAX      InterfaceIndexOrZero
    MAX-ACCESS  read-create
    STATUS      current
    DESCRIPTION
        "The ifIndex of an interface over which this Frame Relay interface 
        is to be layered. A value of zero indicates no layering.
        An implementation may choose to require that a nonzero value
        be configured at entry creation."
    ::= { usdFrDlcmiEntry 13 }


usdFrDlcmiRole OBJECT-TYPE
    SYNTAX      INTEGER {
                    dte(0),
                    dce(1),
                    nni(2)
                }
    MAX-ACCESS  read-create
    STATUS      current
    DESCRIPTION
        "Specifies the role this interface assumes with respect 
        to the remote end.
        
        When acting as a DTE, the following objects are not relevant:

            usdFrDlcmiDcePollingInterval
            usdFrDlcmiDceErrorThreshold
            usdFrDlcmiDceMonitoredEvents

        When acting as a DCE, the following objects are not relevant:

            usdFrDlcmiPollingInterval
            usdFrDlcmiFullEnquiryInterval
            usdFrDlcmiErrorThreshold
            usdFrDlcmiMonitoredEvents
        "
    ::= { usdFrDlcmiEntry 14 }

usdFrDlcmiDcePollingInterval OBJECT-TYPE
    SYNTAX      Integer32 (5..30)
    UNITS       "seconds"
    MAX-ACCESS  read-create
    STATUS      current
    DESCRIPTION
        "The number of seconds within which a DCE
        expects to receive a Status Enquiry from the DTE.

        This value corresponds to the T392 timer.

        Pertains to DCE/NNI operation only. This parameter can
        be reconfigured only when the Frame Relay interface
        is acting as a DCE or NNI."
    DEFVAL  { 15 }
    ::= { usdFrDlcmiEntry 15 }


usdFrDlcmiDceErrorThreshold OBJECT-TYPE
    SYNTAX      Integer32 (1..10)
    MAX-ACCESS  read-create
    STATUS      current
    DESCRIPTION
        "The minimum number of errors that must be observed 
        within the number of events specified by 
        usdFrDlcmiDceMonitoredEvents, to declare the interface down.
        
        'error' is lack of receipt of a Status Enquiry within the 
        interval specified by usdFrDlcmiDcePollingInterval (T392).

        Pertains to DCE/NNI operation only. This parameter can
        be reconfigured only when the Frame Relay interface
        is acting as a DCE or NNI."
    DEFVAL  { 2 }
    ::= { usdFrDlcmiEntry 16 }


usdFrDlcmiDceMonitoredEvents OBJECT-TYPE
    SYNTAX      Integer32 (1..10)
    MAX-ACCESS  read-create
    STATUS      current
    DESCRIPTION
        "The number of DCE polling intervals over which
        accumulated errors are counted against the threshold 
        specified in usdFrDlcmiDceErrorThreshold. 

        If, within this number of events, the number of errors
        equals or exceeds the threshold, the interface is
        declared down.

        The 'DCE polling interval' is specified by
        usdFrDlcmiDcePollingInterval.

        Pertains to DCE/NNI operation only. This parameter can
        be reconfigured only when the Frame Relay interface
        is acting as a DCE or NNI."
    DEFVAL  { 2 }
    ::= { usdFrDlcmiEntry 17 }

--
-- The Frame Relay Dlcmi Statistics Table
--

usdFrDlcmiStatsTable OBJECT-TYPE
    SYNTAX      SEQUENCE OF UsdFrDlcmiStatsEntry
    MAX-ACCESS  not-accessible
    STATUS      current
    DESCRIPTION
        "The statistics for the Data Link Connection Management
        Interface for the frame relay service on this interface."
    ::= { usdFrIfLayer 3 }

usdFrDlcmiStatsEntry OBJECT-TYPE
    SYNTAX      UsdFrDlcmiStatsEntry
    MAX-ACCESS  not-accessible
    STATUS      current
    DESCRIPTION
        "The statistics for a particular Data Link Connection
        Management Interface.

        Statistics are not relevant while the usdFrDlcmiState
        has the value 'noLmiConfigured'.

        The DTE statistics are relevant when the corresponding
        usdFrDlcmiRole is DTE.

        The DTE statistics are relevant when the corresponding
        usdFrDlcmiRole is DCE."
    INDEX   { usdFrDlcmiIfIndex }
    ::= { usdFrDlcmiStatsTable 1 }

UsdFrDlcmiStatsEntry ::= SEQUENCE {
        usdFrDlcmiStatsDteEnquiries                 Counter32,
        usdFrDlcmiStatsDteFullEnquiries             Counter32,
        usdFrDlcmiStatsDteEnquiryResponses          Counter32,
        usdFrDlcmiStatsDteFullEnquiryResponses      Counter32,
        usdFrDlcmiStatsDteAsyncUpdates              Counter32,
        usdFrDlcmiStatsDteUnknownRxMessages         Counter32,
        usdFrDlcmiStatsDteLossOfSequences           Counter32,
        usdFrDlcmiStatsDteNoResponseTimeouts        Counter32,

        usdFrDlcmiStatsDceEnquiries                 Counter32,
        usdFrDlcmiStatsDceFullEnquiries             Counter32,
        usdFrDlcmiStatsDceEnquiryResponses          Counter32,
        usdFrDlcmiStatsDceFullEnquiryResponses      Counter32,
        usdFrDlcmiStatsDceAsyncUpdates              Counter32,
        usdFrDlcmiStatsDceUnknownRxMessages         Counter32,
        usdFrDlcmiStatsDceLossOfSequences           Counter32,
        usdFrDlcmiStatsDceNoResponseTimeouts        Counter32,

        usdFrDlcmiStatsDiscontinuityTime            TimeTicks
}


usdFrDlcmiStatsDteEnquiries OBJECT-TYPE
    SYNTAX      Counter32
    MAX-ACCESS  read-only
    STATUS      current
    DESCRIPTION
        "Number of Status Enquiries sent (as DTE)."
    ::= { usdFrDlcmiStatsEntry 1 }

usdFrDlcmiStatsDteFullEnquiries OBJECT-TYPE
    SYNTAX      Counter32
    MAX-ACCESS  read-only
    STATUS      current
    DESCRIPTION
        "Number of Full Enquiries sent (as DTE)."
    ::= { usdFrDlcmiStatsEntry 2 }

usdFrDlcmiStatsDteEnquiryResponses OBJECT-TYPE
    SYNTAX      Counter32
    MAX-ACCESS  read-only
    STATUS      current
    DESCRIPTION
        "Number of Status Enquiry responses received (as DTE)."
    ::= { usdFrDlcmiStatsEntry 3 }

usdFrDlcmiStatsDteFullEnquiryResponses OBJECT-TYPE
    SYNTAX      Counter32
    MAX-ACCESS  read-only
    STATUS      current
    DESCRIPTION
        "Number of Full Enquiry responses received (as DTE)."
    ::= { usdFrDlcmiStatsEntry 4 }

usdFrDlcmiStatsDteAsyncUpdates OBJECT-TYPE
    SYNTAX      Counter32
    MAX-ACCESS  read-only
    STATUS      current
    DESCRIPTION
        "Number of Asynchronous Updates received (as DTE)."
    ::= { usdFrDlcmiStatsEntry 5 }

usdFrDlcmiStatsDteUnknownRxMessages OBJECT-TYPE
    SYNTAX      Counter32
    MAX-ACCESS  read-only
    STATUS      current
    DESCRIPTION
        "Number of unknown messages received (as DTE)."
    ::= { usdFrDlcmiStatsEntry 6 }

usdFrDlcmiStatsDteLossOfSequences OBJECT-TYPE
    SYNTAX      Counter32
    MAX-ACCESS  read-only
    STATUS      current
    DESCRIPTION
        "Number of times a discontinuity in sequence numbering of received
        messages was detected (as DTE)."
    ::= { usdFrDlcmiStatsEntry 7 }

usdFrDlcmiStatsDteNoResponseTimeouts OBJECT-TYPE
    SYNTAX      Counter32
    MAX-ACCESS  read-only
    STATUS      current
    DESCRIPTION
        "Number of timer expirations awaiting a Status message (as DTE)."
    ::= { usdFrDlcmiStatsEntry 8 }

usdFrDlcmiStatsDceEnquiries OBJECT-TYPE
    SYNTAX      Counter32
    MAX-ACCESS  read-only
    STATUS      current
    DESCRIPTION
        "Number of Status Enquiries received (as DCE.)"
    ::= { usdFrDlcmiStatsEntry 9 }

usdFrDlcmiStatsDceFullEnquiries OBJECT-TYPE
    SYNTAX      Counter32
    MAX-ACCESS  read-only
    STATUS      current
    DESCRIPTION
        "Number of Full Enquiries received (as DCE)."
    ::= { usdFrDlcmiStatsEntry 10 }

usdFrDlcmiStatsDceEnquiryResponses OBJECT-TYPE
    SYNTAX      Counter32
    MAX-ACCESS  read-only
    STATUS      current
    DESCRIPTION
        "Number of Status Enquiry responses sent (as DCE)."
    ::= { usdFrDlcmiStatsEntry 11 }

usdFrDlcmiStatsDceFullEnquiryResponses OBJECT-TYPE
    SYNTAX      Counter32
    MAX-ACCESS  read-only
    STATUS      current
    DESCRIPTION
        "Number of Full Enquiry responses sent (as DCE)."
    ::= { usdFrDlcmiStatsEntry 12 }

usdFrDlcmiStatsDceAsyncUpdates OBJECT-TYPE
    SYNTAX      Counter32
    MAX-ACCESS  read-only
    STATUS      current
    DESCRIPTION
        "Number of Asynchronous Updates sent (as DCE)."
    ::= { usdFrDlcmiStatsEntry 13 }

usdFrDlcmiStatsDceUnknownRxMessages OBJECT-TYPE
    SYNTAX      Counter32
    MAX-ACCESS  read-only
    STATUS      current
    DESCRIPTION
        "Number of unknown messages received (as DCE)."
    ::= { usdFrDlcmiStatsEntry 14 }

usdFrDlcmiStatsDceLossOfSequences OBJECT-TYPE
    SYNTAX      Counter32
    MAX-ACCESS  read-only
    STATUS      current
    DESCRIPTION
        "Number of times a discontinuity in sequence numbering of received
        messages was detected (as DCE)."
    ::= { usdFrDlcmiStatsEntry 15 }

usdFrDlcmiStatsDceNoResponseTimeouts OBJECT-TYPE
    SYNTAX      Counter32
    MAX-ACCESS  read-only
    STATUS      current
    DESCRIPTION
        "Number of timer expirations awaiting a Status Enquiry (as DCE)."
    ::= { usdFrDlcmiStatsEntry 16 }

usdFrDlcmiStatsDiscontinuityTime OBJECT-TYPE
    SYNTAX      TimeTicks
    MAX-ACCESS  read-only
    STATUS      current
    DESCRIPTION
        "Value of sysUpTime at the most recent event that caused a 
        discontinuity in the monotonic operation of any of the
        counters in this entry. Such disruption might be caused by:

            Hardware insertion/removal.
            Reconfiguration of usdFrDlcmiState.
            Reconfiguration of usdFrDlcmiRole.

        Conclusions can be drawn from successive polls of an entry's
        counters only if the value of this object, simultaneously
        retrieved in those polls, remains unchanged."
    ::= { usdFrDlcmiStatsEntry 17 }

--
-- Frame Relay Circuit Table
-- 
usdFrCircuitTable OBJECT-TYPE
    SYNTAX      SEQUENCE OF UsdFrCircuitEntry
    MAX-ACCESS  not-accessible
    STATUS      current
    DESCRIPTION
        "A table containing information about specific Data Link Connections
        (DLC) or virtual circuits.

        This table mirrors the structure of RFC2115 FRAME-RELAY-DTE-MIB
        frCircuitTable, for the purpose of enumerating circuits on both
        DTE and DCE Frame Relay interfaces."
    ::= { usdFrIfLayer 4 }

usdFrCircuitEntry OBJECT-TYPE
    SYNTAX      UsdFrCircuitEntry
    MAX-ACCESS  not-accessible
    STATUS      current
    DESCRIPTION
        "The information regarding a single Data Link Connection.
        Discontinuities in the counters contained in this table are
        indicated by the value in usdFrCircuitCreationTime."
    INDEX { usdFrCircuitIfIndex, usdFrCircuitDlci }
    ::= { usdFrCircuitTable 1 }


UsdFrCircuitEntry ::= SEQUENCE {
        usdFrCircuitIfIndex                InterfaceIndex,
        usdFrCircuitDlci                   DLCI,
        usdFrCircuitState                  INTEGER,
        usdFrCircuitReceivedFECNs          Counter32,
        usdFrCircuitReceivedBECNs          Counter32,
        usdFrCircuitSentFrames             Counter32,
        usdFrCircuitSentOctets             Counter32,
        usdFrCircuitReceivedFrames         Counter32,
        usdFrCircuitReceivedOctets         Counter32,
        usdFrCircuitCreationTime           TimeStamp,
        usdFrCircuitLastTimeChange         TimeStamp,
        usdFrCircuitCommittedBurst         Integer32,
        usdFrCircuitExcessBurst            Integer32,
        usdFrCircuitThroughput             Integer32,
        usdFrCircuitMulticast              INTEGER,
        usdFrCircuitType                   INTEGER,
        usdFrCircuitDiscards               Counter32,
        usdFrCircuitReceivedDEs            Counter32,
        usdFrCircuitSentDEs                Counter32,
        usdFrCircuitLogicalIfIndex         InterfaceIndex,
        usdFrCircuitRowStatus              RowStatus,
        usdFrCircuitSentFECNs              Counter32,
        usdFrCircuitSentBECNs              Counter32
}


usdFrCircuitIfIndex OBJECT-TYPE
    SYNTAX      InterfaceIndex
    MAX-ACCESS  not-accessible
    STATUS      current
    DESCRIPTION
        "The ifIndex Value of the ifEntry this virtual circuit
        is layered onto."
    ::= { usdFrCircuitEntry 1 }

usdFrCircuitDlci OBJECT-TYPE
    SYNTAX      DLCI
    MAX-ACCESS  not-accessible
    STATUS      current
    DESCRIPTION
        "The Data Link Connection Identifier for this virtual
        circuit."
    REFERENCE
        "American National Standard T1.618-1991, Section 3.3.6"
    ::= { usdFrCircuitEntry 2 }

usdFrCircuitState OBJECT-TYPE
    SYNTAX      INTEGER {
                    invalid (1),
                    active (2),
                    inactive (3)
                }
    MAX-ACCESS  read-create
    STATUS      current
    DESCRIPTION
        "Indicates whether the particular virtual circuit is
        operational.  In the absence of a Data Link Connection
        Management Interface, virtual circuit entries (rows)
        may be created by setting virtual circuit state to
        'active', or deleted by changing Circuit state to
        'invalid'.

        Whether or not the row actually disappears is left to
        the implementation, so this object may actually read as
        'invalid' for some arbitrary length of time.  It is
        also legal to set the state of a virtual circuit to
        'inactive' to temporarily disable a given circuit.

        The use of 'invalid' is deprecated in this SNMP Version
        2 MIB, in favor of usdFrCircuitRowStatus."
    DEFVAL { active }
    ::= { usdFrCircuitEntry 3 }

usdFrCircuitReceivedFECNs OBJECT-TYPE
    SYNTAX      Counter32
    MAX-ACCESS  read-only
    STATUS      current
    DESCRIPTION
        "Number of frames received from the network indicating
        forward congestion since the virtual circuit was
        created.  This occurs when the remote DTE sets the FECN
        flag, or when a switch in the network enqueues the
        frame to a trunk whose transmission queue is
        congested."
    REFERENCE
        "American National Standard T1.618-1991, Section 3.3.3"
    ::= { usdFrCircuitEntry 4 }


usdFrCircuitReceivedBECNs OBJECT-TYPE
    SYNTAX      Counter32
    MAX-ACCESS  read-only
    STATUS      current
    DESCRIPTION
        "Number of frames received from the network indicating
        backward congestion since the virtual circuit was
        created.  This occurs when the remote DTE sets the BECN
        flag, or when a switch in the network receives the
        frame from a trunk whose transmission queue is
        congested."
    REFERENCE
        "American National Standard T1.618-1991, Section 3.3.4"
    ::= { usdFrCircuitEntry 5 }


usdFrCircuitSentFrames OBJECT-TYPE
    SYNTAX      Counter32
    MAX-ACCESS  read-only
    STATUS      current
    DESCRIPTION
        "The number of frames sent from this virtual circuit
        since it was created."
    ::= { usdFrCircuitEntry 6 }


usdFrCircuitSentOctets OBJECT-TYPE
    SYNTAX      Counter32
    MAX-ACCESS  read-only
    STATUS      current
    DESCRIPTION
        "The number of octets sent from this virtual circuit
        since it was created.  Octets counted are the full
        frame relay header and the payload, but do not include
        the flag characters or CRC."
    ::= { usdFrCircuitEntry 7 }


usdFrCircuitReceivedFrames OBJECT-TYPE
    SYNTAX      Counter32
    MAX-ACCESS  read-only
    STATUS      current
    DESCRIPTION
        "Number of frames received over this virtual circuit
        since it was created."
    ::= { usdFrCircuitEntry 8 }


usdFrCircuitReceivedOctets OBJECT-TYPE
    SYNTAX      Counter32
    MAX-ACCESS  read-only
    STATUS      current
    DESCRIPTION
        "Number of octets received over this virtual circuit
        since it was created.  Octets counted include the full
        frame relay header, but do not include the flag
        characters or the CRC."
    ::= { usdFrCircuitEntry 9 }


usdFrCircuitCreationTime OBJECT-TYPE
    SYNTAX      TimeStamp
    MAX-ACCESS  read-only
    STATUS      current
    DESCRIPTION
        "The value of sysUpTime when the virtual circuit was
        created, whether by the Data Link Connection Management
        Interface or by a SetRequest."
    ::= { usdFrCircuitEntry 10 }

usdFrCircuitLastTimeChange OBJECT-TYPE
    SYNTAX      TimeStamp
    MAX-ACCESS  read-only
    STATUS      current
    DESCRIPTION
        "The value of sysUpTime when last there was a change in
        the virtual circuit state"
    ::= { usdFrCircuitEntry 11 }


usdFrCircuitCommittedBurst OBJECT-TYPE
    SYNTAX      Integer32(0..2147483647)
    MAX-ACCESS  read-create
    STATUS      current
    DESCRIPTION
        "This variable indicates the maximum amount of data, in
        bits, that the network agrees to transfer under normal
        conditions, during the measurement interval."
    REFERENCE
        "American National Standard T1.617-1991, Section
        6.5.19"
    DEFVAL  { 0 }  -- the default indicates no commitment
    ::= { usdFrCircuitEntry 12 }


usdFrCircuitExcessBurst OBJECT-TYPE
    SYNTAX      Integer32(0..2147483647)
    MAX-ACCESS  read-create
    STATUS      current
    DESCRIPTION
        "This variable indicates the maximum amount of
        uncommitted data bits that the network will attempt to
        deliver over the measurement interval.

        By default, if not configured when creating the entry,
        the Excess Information Burst Size is set to the value
        of ifSpeed."
    REFERENCE
        "American National Standard T1.617-1991, Section
        6.5.19"
    ::= { usdFrCircuitEntry 13 }


usdFrCircuitThroughput OBJECT-TYPE
    SYNTAX      Integer32(0..2147483647)
    MAX-ACCESS  read-create
    STATUS      current
    DESCRIPTION
        "Throughput is the average number of 'Frame Relay
        Information Field' bits transferred per second across a
        user network interface in one direction, measured over
        the measurement interval.

        If the configured committed burst rate and throughput
        are both non-zero, the measurement interval, T, is

            T=usdFrCircuitCommittedBurst/usdFrCircuitThroughput.

        If the configured committed burst rate and throughput
        are both zero, the measurement interval, T, is

            T=usdFrCircuitExcessBurst/ifSpeed."
    REFERENCE
        "American National Standard T1.617-1991, Section
        6.5.19"
    DEFVAL  {0}  -- the default value of Throughput is "no commitment".
    ::= { usdFrCircuitEntry 14 }


usdFrCircuitMulticast OBJECT-TYPE
    SYNTAX      INTEGER {
                    unicast   (1),
                    oneWay    (2),
                    twoWay    (3),
                    nWay      (4)
                }
    MAX-ACCESS  read-create
    STATUS      current
    DESCRIPTION
        "This indicates whether this VC is used as a unicast VC
        (i.e. not multicast) or the type of multicast service
        subscribed to"
    REFERENCE
        "Frame Relay PVC Multicast Service and Protocol
        Description Implementation: FRF.7 Frame Relay Forum
        Technical Committe October 21, 1994"
    DEFVAL  {unicast}
    ::= { usdFrCircuitEntry 15 }


usdFrCircuitType OBJECT-TYPE
    SYNTAX      INTEGER {
                    static  (1),
                    dynamic (2)
                }
    MAX-ACCESS  read-only
    STATUS      current
    DESCRIPTION
        "Indication of whether the VC was manually created
        (static), or dynamically created (dynamic) via the data
        link control management interface."
    ::= { usdFrCircuitEntry 16 }


usdFrCircuitDiscards OBJECT-TYPE
    SYNTAX      Counter32
    MAX-ACCESS  read-only
    STATUS      current
    DESCRIPTION
        "The number of inbound frames dropped because of format
        errors, or because the VC is inactive."
    ::= { usdFrCircuitEntry 17 }


usdFrCircuitReceivedDEs OBJECT-TYPE
    SYNTAX      Counter32
    MAX-ACCESS  read-only
    STATUS      current
    DESCRIPTION
        "Number of frames received from the network indicating
        that they were eligible for discard since the virtual
        circuit was created.  This occurs when the remote DTE
        sets the DE flag, or when in remote DTE's switch
        detects that the frame was received as Excess Burst
        data."
    REFERENCE
        "American National Standard T1.618-1991, Section 3.3.4"
    ::= { usdFrCircuitEntry 18 }


usdFrCircuitSentDEs OBJECT-TYPE
    SYNTAX      Counter32
    MAX-ACCESS  read-only
    STATUS      current
    DESCRIPTION
        "Number of frames sent to the network indicating that
        they were eligible for discard since the virtual
        circuit was created.   This occurs when the local DTE
        sets the DE flag, indicating that during Network
        congestion situations those frames should be discarded
        in preference of other frames sent without the DE bit
        set."
    REFERENCE
        "American National  Standard  T1.618-1991, Section
        3.3.4"
   ::= { usdFrCircuitEntry 19 }

usdFrCircuitLogicalIfIndex OBJECT-TYPE
    SYNTAX      InterfaceIndex
    MAX-ACCESS  read-create
    STATUS      current
    DESCRIPTION
        "Normally the same value as frDlcmiIfIndex, but
        different when an implementation associates a virtual
        ifEntry with a DLC or set of DLCs in order to associate
        higher layer objects such as the ipAddrEntry with a
        subset of the virtual circuits on a Frame Relay
        interface. The type of such ifEntries is defined by the
        higher layer object; for example, if PPP/Frame Relay is
        implemented, the ifType of this ifEntry would be PPP.
        If it is not so defined, as would be the case with an
        ipAddrEntry, it should be of type Other."
    ::= { usdFrCircuitEntry 20 }

usdFrCircuitRowStatus OBJECT-TYPE
    SYNTAX      RowStatus
    MAX-ACCESS  read-create
    STATUS      current
    DESCRIPTION
        "This object is used to create a new row or modify or
        destroy an existing row in the manner described in the
        definition of the RowStatus textual convention.
        Writable objects in the table may be written in any
        RowStatus state."
    ::= { usdFrCircuitEntry 21 }

usdFrCircuitSentFECNs OBJECT-TYPE
    SYNTAX      Counter32
    MAX-ACCESS  read-only
    STATUS      current
    DESCRIPTION
        "Number of frames sent to the network indicating
        forward congestion since the virtual circuit was
        created.  This occurs when the remote DTE sets the FECN
        flag, or when a switch in the network enqueues the
        frame to a trunk whose transmission queue is
        congested."
    REFERENCE
        "American National Standard T1.618-1991, Section 3.3.3"
    ::= { usdFrCircuitEntry 22 }


usdFrCircuitSentBECNs OBJECT-TYPE
    SYNTAX      Counter32
    MAX-ACCESS  read-only
    STATUS      current
    DESCRIPTION
        "Number of frames sent to the network indicating
        backward congestion since the virtual circuit was
        created.  This occurs when the remote DTE sets the BECN
        flag, or when a switch in the network receives the
        frame from a trunk whose transmission queue is
        congested."
    REFERENCE
        "American National Standard T1.618-1991, Section 3.3.4"
    ::= { usdFrCircuitEntry 23 }




-- //////////////////////////////////////////////////////////////////////
--
-- Frame Relay Subinterface Layer
--
-- This layer is managed with the following elements:
--
--  o NextIfIndex (generator for Frame Relay subinterface IfIndex selection)
--  o SubIf Table (creation/configuration/deletion of Frame Relay subinterfaces)
--  o SubIf Circuit Table (creation/deletion of circuits assoc. w/ subinterfaces)
--
-- //////////////////////////////////////////////////////////////////////

--
-- IfIndex selection for creating new Frame Relay Subinterfaces
--

usdFrSubIfNextIfIndex OBJECT-TYPE
    SYNTAX      UsdNextIfIndex
    MAX-ACCESS  read-only
    STATUS      current
    DESCRIPTION
        "Coordinate ifIndex value allocation for entries
        in usdFrSubIfTable.

        A GET of this object returns the next available ifIndex 
        value to be used to create an entry in the associated
        interface table; or zero, if no valid ifIndex value is
        available. This object also returns a value of zero when 
        it is the lexicographic successor of a varbind presented 
        in an SNMP GETNEXT or GETBULK request, for which circumstance
        it is assumed that ifIndex allocation is unintended.

        Successive GETs will typically return different
        values, thus avoiding collisions among cooperating
        management clients seeking to create table entries
        simultaneously.
        "
    ::= { usdFrSubIfLayer 1 }

--
-- The Frame Relay Subinterface Table
--

usdFrSubIfTable OBJECT-TYPE
    SYNTAX      SEQUENCE OF UsdFrSubIfEntry
    MAX-ACCESS  not-accessible
    STATUS      current
    DESCRIPTION
        "This table contains entries for Frame Relay Subinterfaces present 
        in the system."
    ::= { usdFrSubIfLayer 2 }

usdFrSubIfEntry OBJECT-TYPE
    SYNTAX      UsdFrSubIfEntry
    MAX-ACCESS  not-accessible
    STATUS      current
    DESCRIPTION
        "Each entry describes the characteristics of a Frame Relay Subinterface.
        Creating/deleting entries in this table causes corresponding 
        entries for be created /deleted in ifTable/ifXTable/usdIfTable."
    INDEX   { usdFrSubIfIndex }
    ::= { usdFrSubIfTable 1 }

UsdFrSubIfEntry ::= SEQUENCE {
    usdFrSubIfIndex
        InterfaceIndex,
    usdFrSubIfRowStatus
        RowStatus,
    usdFrSubIfLowerIfIndex
        InterfaceIndexOrZero,
    usdFrSubIfId
        Integer32
    }


usdFrSubIfIndex OBJECT-TYPE
    SYNTAX      InterfaceIndex
    MAX-ACCESS  not-accessible
    STATUS      current
    DESCRIPTION
        "The ifIndex of the Frame Relay Subinterface. When 
        creating entries in this table, suitable values
        for this object are determined by reading
        usdFrSubNextIfIndex."
    ::= { usdFrSubIfEntry 1 }

usdFrSubIfRowStatus OBJECT-TYPE
    SYNTAX      RowStatus
    MAX-ACCESS  read-create
    STATUS      current
    DESCRIPTION
        "Controls creation/deletion of entries in this table
        according to the RowStatus textual convention, 
        constrained to support the following values only:

            createAndGo
            destroy
            
        To create an entry in this table, the following 
        entry objects MUST be explicitly configured:

            usdFrSubIfRowStatus
            usdFrSubIfLowerIfIndex

        In addition, when creating an entry the following
        conditions must hold:

            A value for usdFrSubIfIndex must have been determined
            previously, by reading usdFrSubIfNextIfIndex. 

            The interface identified by usdFrSubIfLowerIfIndex
            must exist, and must be a Frame Relay interface.

            A positive value configured for usdFrSubIfId must not
            already be assigned to another subinterface layered
            onto the same underlying Frame Relay interface.

        A corresponding entry in ifTable/ifXTable/usdIfTable is 
        created/destroyed as a result of creating/destroying an entry 
        in this table.
        "
    ::= { usdFrSubIfEntry 2 }

usdFrSubIfLowerIfIndex OBJECT-TYPE
    SYNTAX      InterfaceIndexOrZero
    MAX-ACCESS  read-create
    STATUS      current
    DESCRIPTION
        "The ifIndex of a Frame Relay interface over which this 
        Frame Relay Subinterface is to be layered. A value of zero 
        indicates no layering. An implementation may choose to require 
        that a nonzero value be configured at entry creation."
    ::= { usdFrSubIfEntry 3 }


usdFrSubIfId OBJECT-TYPE
    SYNTAX      Integer32 (-1..2147483647)
    MAX-ACCESS  read-create
    STATUS      current
    DESCRIPTION
        "An integer identifier for the Frame Relay subinterface, 
        used in conjunction with the command-line interface. 
        It is provided here for cross-reference purposes only.

        The value must be unique among subinterfaces configured on the same 
        underlying Frame Relay interface.
        
        If this object is not configured, or is configured with a 
        value of -1, a nonzero value will be allocated internally
        and can be retrieved from this object after table entry creation 
        has succeeded.

        A value of zero for this object is reserved for future use."
    DEFVAL { -1 }
    ::= { usdFrSubIfEntry 4 }

--
-- The Frame Relay Subinterface Circuit Table
--

usdFrSubIfCktTable OBJECT-TYPE
    SYNTAX      SEQUENCE OF UsdFrSubIfCktEntry
    MAX-ACCESS  not-accessible
    STATUS      current
    DESCRIPTION
        "This table contains entries for Frame Relay circuits configured on 
        Frame Relay Subinterfaces present in the system.

        An implementation may constrain the number of circuits permitted
        to be configured per Frame Relay Subinterface; in particular,
        an implementation may restrict each Frame Relay Subinterface to
        have a single circuit.
        
        Attributes in this entry can only be configured at entry creation,
        and remain fixed for the lifetime of the entry.
        "
    ::= { usdFrSubIfLayer 3 }

usdFrSubIfCktEntry OBJECT-TYPE
    SYNTAX      UsdFrSubIfCktEntry
    MAX-ACCESS  not-accessible
    STATUS      current
    DESCRIPTION
        "Each entry describes the characteristics of a Frame Relay Subinterface
        circuit."
    INDEX   { usdFrSubIfIndex, usdFrSubIfCktDlci }
    ::= { usdFrSubIfCktTable 1 }

UsdFrSubIfCktEntry ::= SEQUENCE {
    usdFrSubIfCktDlci
        DLCI,
    usdFrSubIfCktRowStatus
        RowStatus
    }


usdFrSubIfCktDlci OBJECT-TYPE
    SYNTAX      DLCI
    MAX-ACCESS  not-accessible
    STATUS      current
    DESCRIPTION
        "The DLCI of the Frame Relay circuit used by this subinterface."
    ::= { usdFrSubIfCktEntry 1 }

usdFrSubIfCktRowStatus OBJECT-TYPE
    SYNTAX      RowStatus
    MAX-ACCESS  read-create
    STATUS      current
    DESCRIPTION
        "Controls creation/deletion of entries in this table
        according to the RowStatus textual convention, 
        constrained to support the following values only:

            createAndGo
            destroy
            
        To create an entry in this table, the following 
        entry objects MUST be explicitly configured:

            usdFrSubIfCktRowStatus
        "
    ::= { usdFrSubIfCktEntry 2 }


-- ++++++++++++++++++++++++++++++++++++++++++++++++++++++++++++++++++++++
-- Notification control objects
-- ++++++++++++++++++++++++++++++++++++++++++++++++++++++++++++++++++++++

-- No notifications are defined in this MIB. Placeholder follows.

-- usdFrTrapControl      OBJECT IDENTIFIER ::= { usdFrameRelayMIB 2 }


-- ++++++++++++++++++++++++++++++++++++++++++++++++++++++++++++++++++++++
-- Notifications
-- ++++++++++++++++++++++++++++++++++++++++++++++++++++++++++++++++++++++

-- No notifications are defined in this MIB. Placeholder follows.

-- The following two OBJECT IDENTIFIERS are used to define SNMPv2 
-- Notifications that are easily translated into SNMPv1 Traps.

-- usdFrTraps            OBJECT IDENTIFIER ::= { usdFrameRelayMIB 3 }
-- usdFrTrapPrefix       OBJECT IDENTIFIER ::= { usdFrTraps 0 }


-- ++++++++++++++++++++++++++++++++++++++++++++++++++++++++++++++++++++++
-- Conformance information
-- ++++++++++++++++++++++++++++++++++++++++++++++++++++++++++++++++++++++

usdFrConformance OBJECT IDENTIFIER ::= { usdFrameRelayMIB 4 }
usdFrCompliances OBJECT IDENTIFIER ::= { usdFrConformance 1 }
usdFrGroups      OBJECT IDENTIFIER ::= { usdFrConformance 2 }

-- compliance statements

usdFrCompliance MODULE-COMPLIANCE
    STATUS  current
    DESCRIPTION
        "The compliance statement for entities that implement the Unisphere
        Frame Relay MIB."
    MODULE  -- this module
        MANDATORY-GROUPS { usdFrGroup, usdFrSubIfGroup }
    ::= { usdFrCompliances 1 }

-- units of conformance

usdFrGroup OBJECT-GROUP
    OBJECTS {
        usdFrNextIfIndex,

        usdFrDlcmiIfIndex,
        usdFrDlcmiState,
        usdFrDlcmiAddress,
        usdFrDlcmiAddressLen,
        usdFrDlcmiPollingInterval,
        usdFrDlcmiFullEnquiryInterval,
        usdFrDlcmiErrorThreshold,
        usdFrDlcmiMonitoredEvents,
        usdFrDlcmiMaxSupportedVCs,
        usdFrDlcmiMulticast,
        usdFrDlcmiStatus,
        usdFrDlcmiRowStatus,
        usdFrDlcmiLowerIfIndex,
        usdFrDlcmiRole,
        usdFrDlcmiDcePollingInterval,
        usdFrDlcmiDceErrorThreshold,
        usdFrDlcmiDceMonitoredEvents,

        usdFrDlcmiStatsDteEnquiries,
        usdFrDlcmiStatsDteFullEnquiries,
        usdFrDlcmiStatsDteEnquiryResponses,
        usdFrDlcmiStatsDteFullEnquiryResponses,
        usdFrDlcmiStatsDteAsyncUpdates,
        usdFrDlcmiStatsDteUnknownRxMessages,
        usdFrDlcmiStatsDteLossOfSequences,
        usdFrDlcmiStatsDteNoResponseTimeouts,
        usdFrDlcmiStatsDceEnquiries,
        usdFrDlcmiStatsDceFullEnquiries,
        usdFrDlcmiStatsDceEnquiryResponses,
        usdFrDlcmiStatsDceFullEnquiryResponses,
        usdFrDlcmiStatsDceAsyncUpdates,
        usdFrDlcmiStatsDceUnknownRxMessages,
        usdFrDlcmiStatsDceLossOfSequences,
        usdFrDlcmiStatsDceNoResponseTimeouts,
        usdFrDlcmiStatsDiscontinuityTime,

        usdFrCircuitState,
        usdFrCircuitReceivedFECNs,
        usdFrCircuitReceivedBECNs,
        usdFrCircuitSentFrames,
        usdFrCircuitSentOctets,
        usdFrCircuitReceivedFrames,
        usdFrCircuitReceivedOctets,
        usdFrCircuitCreationTime,
        usdFrCircuitLastTimeChange,
        usdFrCircuitCommittedBurst,
        usdFrCircuitExcessBurst,
        usdFrCircuitThroughput,
        usdFrCircuitMulticast,
        usdFrCircuitType,
        usdFrCircuitDiscards,
        usdFrCircuitReceivedDEs,
        usdFrCircuitSentDEs,
        usdFrCircuitLogicalIfIndex,
        usdFrCircuitRowStatus,
        usdFrCircuitSentFECNs,
        usdFrCircuitSentBECNs
    }
    STATUS  current
    DESCRIPTION
        "A collection of objects providing management of Frame Relay interfaces
        in a Unisphere product."
    ::= { usdFrGroups 1 }

usdFrSubIfGroup OBJECT-GROUP
    OBJECTS {
        usdFrSubIfNextIfIndex,

        usdFrSubIfRowStatus,
        usdFrSubIfLowerIfIndex,
        usdFrSubIfId,

        usdFrSubIfCktRowStatus
    }
    STATUS  current
    DESCRIPTION
        "A collection of objects providing management of Frame Relay
        subinterfaces in a Unisphere product."
    ::= { usdFrGroups 2 }

END
