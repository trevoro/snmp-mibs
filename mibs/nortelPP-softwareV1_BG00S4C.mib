Nortel-Magellan-Passport-SoftwareMIB
DEFINITIONS ::= BEGIN



IMPORTS

      OBJECT-TYPE
   FROM RFC-1212

      components,
      passportMIBs
   FROM Nortel-Magellan-Passport-UsefulDefinitionsMIB

      DisplayString,
      StorageType,
      RowStatus,
      Unsigned32
   FROM Nortel-Magellan-Passport-StandardTextualConventionsMIB

      AsciiString,
      NonReplicated,
      Link,
      AsciiStringIndex
   FROM Nortel-Magellan-Passport-TextualConventionsMIB;




-- LAST-UPDATED   "9902010000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     Software Enterprise MIB."

softwareMIB OBJECT IDENTIFIER ::= { passportMIBs 17 }










-- SW
-- This component is the top-level component of all software 
-- configuration components.

sw OBJECT IDENTIFIER ::= { components 14 }



swRowStatusTable OBJECT-TYPE
   SYNTAX     SEQUENCE OF SwRowStatusEntry
   ACCESS     not-accessible
   STATUS     mandatory
   DESCRIPTION
     "This entry controls the addition and deletion of 
      sw components."
::= { sw 1 }

swRowStatusEntry OBJECT-TYPE
   SYNTAX     SwRowStatusEntry
   ACCESS     not-accessible
   STATUS     mandatory
   DESCRIPTION
     "A single entry in the table represents a single 
      sw component."
   INDEX {
      swIndex }
::= { swRowStatusTable 1 }

SwRowStatusEntry ::= SEQUENCE {
   swRowStatus
      RowStatus,
   swComponentName
      DisplayString,
   swStorageType
      StorageType,
   swIndex
      NonReplicated }

swRowStatus OBJECT-TYPE
   SYNTAX     RowStatus 
   ACCESS     read-only
   STATUS     mandatory
   DESCRIPTION
     "This variable is used as the basis for SNMP naming of
      sw components.
      These components cannot be added nor deleted."
::= { swRowStatusEntry 1 }

swComponentName OBJECT-TYPE
   SYNTAX     DisplayString 
   ACCESS     read-only
   STATUS     mandatory
   DESCRIPTION
     "This variable provides the component's string name for
      use with the ASCII Console Interface"
::= { swRowStatusEntry 2 }

swStorageType OBJECT-TYPE
   SYNTAX     StorageType 
   ACCESS     read-only
   STATUS     mandatory
   DESCRIPTION
     "This variable represents the storage type value for the
      sw tables."
::= { swRowStatusEntry 4 }

swIndex OBJECT-TYPE
   SYNTAX     NonReplicated 
   ACCESS     not-accessible
   STATUS     mandatory
   DESCRIPTION
     "This variable represents the index for the sw tables."
::= { swRowStatusEntry 10 }

swOperTable OBJECT-TYPE
   SYNTAX     SEQUENCE OF SwOperEntry
   ACCESS     not-accessible
   STATUS     mandatory
   DESCRIPTION
     "This group contain the operational attributes for the SW component."
::= { sw 11 }

swOperEntry OBJECT-TYPE
   SYNTAX     SwOperEntry
   ACCESS     not-accessible
   STATUS     mandatory
   DESCRIPTION
     "An entry in the swOperTable."
   INDEX {
      swIndex }
::= { swOperTable 1 }

SwOperEntry ::= SEQUENCE {
   swTidyStatus
      INTEGER,
   swAvBeingTidied
      AsciiString }

swTidyStatus OBJECT-TYPE
   SYNTAX     INTEGER  {
                 inactive(0),
                 inProgress(1),
                 querying(2) }
   ACCESS     read-only
   STATUS     mandatory
   DESCRIPTION
     "This attribute indicates the tidy or remove status. If the value is 
      inactive, no tidy or remove is in progress. If the value is inProgress 
      or querying, the tidy or remove process has begun and therefore no 
      further Tidy Sw or Remove sw/<avName> command is allowed 
      until status returns to inactive."
::= { swOperEntry 1 }

swAvBeingTidied OBJECT-TYPE
   SYNTAX     AsciiString (SIZE (1..30))
   ACCESS     read-only
   STATUS     mandatory
   DESCRIPTION
     "This attribute indicates the name of the AV currently being tidied or 
      removed. An empty string indicates there is no AV being tidied."
::= { swOperEntry 421 }

swAvlTable OBJECT-TYPE
   SYNTAX     SEQUENCE OF SwAvlEntry
   ACCESS     not-accessible
   STATUS     mandatory
   DESCRIPTION
     "This attribute specifies, for each application, which version of its 
      Features and the associated software will be loaded when any of its 
      Features are selected in an LPT.
      A version of the 'base' application must be specified.
      All names specified by the user must actually be AV names.
      All AVs specified must be compatible with each other.
      No more than one version of a single application can be specified."
::= { sw 256 }

swAvlEntry OBJECT-TYPE
   SYNTAX     SwAvlEntry
   ACCESS     not-accessible
   STATUS     mandatory
   DESCRIPTION
     "An entry in the swAvlTable."
   INDEX {
      swIndex,
      swAvlValue }
::= { swAvlTable 1 }

SwAvlEntry ::= SEQUENCE {
   swAvlValue
      AsciiString,
   swAvlRowStatus
      RowStatus }

swAvlValue OBJECT-TYPE
   SYNTAX     AsciiString (SIZE (1..30))
   ACCESS     read-write
   STATUS     mandatory
   DESCRIPTION
     "This variable represents both the value and the index for the
      swAvlTable."
::= { swAvlEntry 1 }

swAvlRowStatus OBJECT-TYPE
   SYNTAX     RowStatus 
   ACCESS     write-only
   STATUS     mandatory
   DESCRIPTION
     "This variable is used to control the addition and deletion 
      of individual values of the swAvlTable."
::= { swAvlEntry 2 }

swAvListToTidyTable OBJECT-TYPE
   SYNTAX     SEQUENCE OF SwAvListToTidyEntry
   ACCESS     not-accessible
   STATUS     mandatory
   DESCRIPTION
     "This attribute holds the list of names of AVs to be tidied or 
      removed. As AVs are successfully cleaned, they are removed from 
      this list and added to avListTidied."
::= { sw 422 }

swAvListToTidyEntry OBJECT-TYPE
   SYNTAX     SwAvListToTidyEntry
   ACCESS     not-accessible
   STATUS     mandatory
   DESCRIPTION
     "An entry in the swAvListToTidyTable."
   INDEX {
      swIndex,
      swAvListToTidyValue }
::= { swAvListToTidyTable 1 }

SwAvListToTidyEntry ::= SEQUENCE {
   swAvListToTidyValue
      AsciiString }

swAvListToTidyValue OBJECT-TYPE
   SYNTAX     AsciiString (SIZE (1..30))
   ACCESS     read-only
   STATUS     mandatory
   DESCRIPTION
     "This variable represents both the value and the index for the
      swAvListToTidyTable."
::= { swAvListToTidyEntry 1 }

swAvListTidiedTable OBJECT-TYPE
   SYNTAX     SEQUENCE OF SwAvListTidiedEntry
   ACCESS     not-accessible
   STATUS     mandatory
   DESCRIPTION
     "This attribute holds the list of names of AVs which have been 
      successfully tidied or removed as a result of the last Tidy Sw or 
      Remove Sw av/<avName> command. It is cleared each time a new 
      Tidy Sw or Remove Sw av/<avName> command is issued."
::= { sw 423 }

swAvListTidiedEntry OBJECT-TYPE
   SYNTAX     SwAvListTidiedEntry
   ACCESS     not-accessible
   STATUS     mandatory
   DESCRIPTION
     "An entry in the swAvListTidiedTable."
   INDEX {
      swIndex,
      swAvListTidiedValue }
::= { swAvListTidiedTable 1 }

SwAvListTidiedEntry ::= SEQUENCE {
   swAvListTidiedValue
      AsciiString }

swAvListTidiedValue OBJECT-TYPE
   SYNTAX     AsciiString (SIZE (1..30))
   ACCESS     read-only
   STATUS     mandatory
   DESCRIPTION
     "This variable represents both the value and the index for the
      swAvListTidiedTable."
::= { swAvListTidiedEntry 1 }

swPatlTable OBJECT-TYPE
   SYNTAX     SEQUENCE OF SwPatlEntry
   ACCESS     not-accessible
   STATUS     mandatory
   DESCRIPTION
     "This attribute specifies which patches are to be loaded and enabled.
      Only patches for Av's that appear in the AvList may be specified.
      Only patches appearing as instances of Sw Av Patch may be 
      specified.
      Patch names are case insensitive. Except for case, patch names must 
      be typed as they appear as instances of Sw Av Patch.
      All patches specified must be compatible with one another.
      Any prerequisite patches for specified patches, must themselves be 
      specified.
      A patch must be specified only once in the list."
::= { sw 436 }

swPatlEntry OBJECT-TYPE
   SYNTAX     SwPatlEntry
   ACCESS     not-accessible
   STATUS     mandatory
   DESCRIPTION
     "An entry in the swPatlTable."
   INDEX {
      swIndex,
      swPatlValue }
::= { swPatlTable 1 }

SwPatlEntry ::= SEQUENCE {
   swPatlValue
      AsciiString,
   swPatlRowStatus
      RowStatus }

swPatlValue OBJECT-TYPE
   SYNTAX     AsciiString (SIZE (1..30))
   ACCESS     read-write
   STATUS     mandatory
   DESCRIPTION
     "This variable represents both the value and the index for the
      swPatlTable."
::= { swPatlEntry 1 }

swPatlRowStatus OBJECT-TYPE
   SYNTAX     RowStatus 
   ACCESS     write-only
   STATUS     mandatory
   DESCRIPTION
     "This variable is used to control the addition and deletion 
      of individual values of the swPatlTable."
::= { swPatlEntry 2 }


-- Sw Dld
-- This component manages the retrieval of software from the 
-- Software Distribution Site (SDS). The module initiates the 
-- connection to the SDS and retrieves the files it wants according to 
-- the AVs specified by the user in avListToDownload.

swDld OBJECT IDENTIFIER ::= { sw 2 }



swDldRowStatusTable OBJECT-TYPE
   SYNTAX     SEQUENCE OF SwDldRowStatusEntry
   ACCESS     not-accessible
   STATUS     mandatory
   DESCRIPTION
     "This entry controls the addition and deletion of 
      swDld components."
::= { swDld 1 }

swDldRowStatusEntry OBJECT-TYPE
   SYNTAX     SwDldRowStatusEntry
   ACCESS     not-accessible
   STATUS     mandatory
   DESCRIPTION
     "A single entry in the table represents a single 
      swDld component."
   INDEX {
      swIndex,
      swDldIndex }
::= { swDldRowStatusTable 1 }

SwDldRowStatusEntry ::= SEQUENCE {
   swDldRowStatus
      RowStatus,
   swDldComponentName
      DisplayString,
   swDldStorageType
      StorageType,
   swDldIndex
      NonReplicated }

swDldRowStatus OBJECT-TYPE
   SYNTAX     RowStatus 
   ACCESS     read-only
   STATUS     mandatory
   DESCRIPTION
     "This variable is used as the basis for SNMP naming of
      swDld components.
      These components cannot be added nor deleted."
::= { swDldRowStatusEntry 1 }

swDldComponentName OBJECT-TYPE
   SYNTAX     DisplayString 
   ACCESS     read-only
   STATUS     mandatory
   DESCRIPTION
     "This variable provides the component's string name for
      use with the ASCII Console Interface"
::= { swDldRowStatusEntry 2 }

swDldStorageType OBJECT-TYPE
   SYNTAX     StorageType 
   ACCESS     read-only
   STATUS     mandatory
   DESCRIPTION
     "This variable represents the storage type value for the
      swDld tables."
::= { swDldRowStatusEntry 4 }

swDldIndex OBJECT-TYPE
   SYNTAX     NonReplicated 
   ACCESS     not-accessible
   STATUS     mandatory
   DESCRIPTION
     "This variable represents the index for the swDld tables."
::= { swDldRowStatusEntry 10 }

swDldOperTable OBJECT-TYPE
   SYNTAX     SEQUENCE OF SwDldOperEntry
   ACCESS     not-accessible
   STATUS     mandatory
   DESCRIPTION
     "This group contains the operational attributes for the Download 
      component."
::= { swDld 10 }

swDldOperEntry OBJECT-TYPE
   SYNTAX     SwDldOperEntry
   ACCESS     not-accessible
   STATUS     mandatory
   DESCRIPTION
     "An entry in the swDldOperTable."
   INDEX {
      swIndex,
      swDldIndex }
::= { swDldOperTable 1 }

SwDldOperEntry ::= SEQUENCE {
   swDldAvBeingDownloaded
      AsciiString,
   swDldStatus
      INTEGER,
   swDldFilesToTransfer
      Unsigned32,
   swDldProcessorTargets
      OCTET STRING }

swDldAvBeingDownloaded OBJECT-TYPE
   SYNTAX     AsciiString (SIZE (0..30))
   ACCESS     read-only
   STATUS     mandatory
   DESCRIPTION
     "This attribute indicates the name of the AV currently being 
      downloaded. If the download is inProgress, the value of this 
      attribute is the first AV in the list of AVs to be downloaded. If there 
      is no AV being downloaded, this attribute contains an empty string."
::= { swDldOperEntry 1 }

swDldStatus OBJECT-TYPE
   SYNTAX     INTEGER  {
                 inactive(0),
                 inProgress(1),
                 stopping(2) }
   ACCESS     read-only
   STATUS     mandatory
   DESCRIPTION
     "This attribute indicates the download status.
      If it is inactive, no download is in progress. This is the value 
      required in order to issue a Start command.
      If it is inProgress, the download procedure has begun. This process 
      starts from the time a Software Distribution Site (SDS) login is 
      attempted and continues through the time during which files are 
      actually being transferred.
      If it is stopping, a user has requested a stoppage but the connections 
      have not yet been completely torn down."
::= { swDldOperEntry 2 }

swDldFilesToTransfer OBJECT-TYPE
   SYNTAX     Unsigned32 (0..1000)
   ACCESS     read-only
   STATUS     mandatory
   DESCRIPTION
     "This attribute indicates the number of files which are still left to 
      transfer for the AV currently being downloaded. It is cleared each 
      time a new AV is processed from the avListToDownload. Note that 
      for each AV, the value of this attribute is 0 until the actual number of 
      files to transfer has been computed."
::= { swDldOperEntry 3 }

swDldProcessorTargets OBJECT-TYPE
   SYNTAX     OCTET STRING (SIZE (1))
   ACCESS     read-write
   STATUS     mandatory
   DESCRIPTION
     "This attribute indicated the processor based object file to download 
      on switch.

      Description of bits:
      i960(0)
      ppc(1)"
::= { swDldOperEntry 4 }

swDldDldListTable OBJECT-TYPE
   SYNTAX     SEQUENCE OF SwDldDldListEntry
   ACCESS     not-accessible
   STATUS     mandatory
   DESCRIPTION
     "This attribute holds the list of names of AVs to be downloaded. If a 
      download is in progress, the first one in the list is the one currently 
      being downloaded. As AVs are successfully downloaded, they are 
      removed from this list and added to the downloadedAvList.
      The user cannot specify an AV which already exists on disk. It must 
      first be removed before re-downloading it (see the Tidy and Remove 
      commands)."
::= { swDld 260 }

swDldDldListEntry OBJECT-TYPE
   SYNTAX     SwDldDldListEntry
   ACCESS     not-accessible
   STATUS     mandatory
   DESCRIPTION
     "An entry in the swDldDldListTable."
   INDEX {
      swIndex,
      swDldIndex,
      swDldDldListValue }
::= { swDldDldListTable 1 }

SwDldDldListEntry ::= SEQUENCE {
   swDldDldListValue
      AsciiString,
   swDldDldListRowStatus
      RowStatus }

swDldDldListValue OBJECT-TYPE
   SYNTAX     AsciiString (SIZE (1..30))
   ACCESS     read-write
   STATUS     mandatory
   DESCRIPTION
     "This variable represents both the value and the index for the
      swDldDldListTable."
::= { swDldDldListEntry 1 }

swDldDldListRowStatus OBJECT-TYPE
   SYNTAX     RowStatus 
   ACCESS     write-only
   STATUS     mandatory
   DESCRIPTION
     "This variable is used to control the addition and deletion 
      of individual values of the swDldDldListTable."
::= { swDldDldListEntry 2 }

swDldDownloadedAvListTable OBJECT-TYPE
   SYNTAX     SEQUENCE OF SwDldDownloadedAvListEntry
   ACCESS     not-accessible
   STATUS     mandatory
   DESCRIPTION
     "This attribute holds the list of names of AVs which have been 
      successfully downloaded as a result of the last Start command. It is 
      cleared each time the Start command is issued."
::= { swDld 261 }

swDldDownloadedAvListEntry OBJECT-TYPE
   SYNTAX     SwDldDownloadedAvListEntry
   ACCESS     not-accessible
   STATUS     mandatory
   DESCRIPTION
     "An entry in the swDldDownloadedAvListTable."
   INDEX {
      swIndex,
      swDldIndex,
      swDldDownloadedAvListValue }
::= { swDldDownloadedAvListTable 1 }

SwDldDownloadedAvListEntry ::= SEQUENCE {
   swDldDownloadedAvListValue
      AsciiString }

swDldDownloadedAvListValue OBJECT-TYPE
   SYNTAX     AsciiString (SIZE (1..30))
   ACCESS     read-only
   STATUS     mandatory
   DESCRIPTION
     "This variable represents both the value and the index for the
      swDldDownloadedAvListTable."
::= { swDldDownloadedAvListEntry 1 }

-- 
-- *** THIS SUBTREE CURRENTLY NOT IMPLEMENTED ***
-- 

-- Sw Av/<name>
-- This component represents a particular version of an application 
-- that is available to use in the AVL. They can only be created by 
-- downloading and can only be deleted by using the Tidy or Remove 
-- commands.
-- An AV has one or more Feature subcomponents which belong to it.

swAv OBJECT IDENTIFIER ::= { sw 3 }



swAvRowStatusTable OBJECT-TYPE
   SYNTAX     SEQUENCE OF SwAvRowStatusEntry
   ACCESS     not-accessible
   STATUS     mandatory
   DESCRIPTION
     "*** THIS TABLE CURRENTLY NOT IMPLEMENTED ***

      This entry controls the addition and deletion of 
      swAv components."
::= { swAv 1 }

swAvRowStatusEntry OBJECT-TYPE
   SYNTAX     SwAvRowStatusEntry
   ACCESS     not-accessible
   STATUS     mandatory
   DESCRIPTION
     "A single entry in the table represents a single 
      swAv component."
   INDEX {
      swIndex,
      swAvIndex }
::= { swAvRowStatusTable 1 }

SwAvRowStatusEntry ::= SEQUENCE {
   swAvRowStatus
      RowStatus,
   swAvComponentName
      DisplayString,
   swAvStorageType
      StorageType,
   swAvIndex
      AsciiStringIndex }

swAvRowStatus OBJECT-TYPE
   SYNTAX     RowStatus 
   ACCESS     read-only
   STATUS     mandatory
   DESCRIPTION
     "This variable is used as the basis for SNMP naming of
      swAv components.
      These components cannot be added nor deleted."
::= { swAvRowStatusEntry 1 }

swAvComponentName OBJECT-TYPE
   SYNTAX     DisplayString 
   ACCESS     read-only
   STATUS     mandatory
   DESCRIPTION
     "This variable provides the component's string name for
      use with the ASCII Console Interface"
::= { swAvRowStatusEntry 2 }

swAvStorageType OBJECT-TYPE
   SYNTAX     StorageType 
   ACCESS     read-only
   STATUS     mandatory
   DESCRIPTION
     "This variable represents the storage type value for the
      swAv tables."
::= { swAvRowStatusEntry 4 }

swAvIndex OBJECT-TYPE
   SYNTAX     AsciiStringIndex (SIZE (1..30))
   ACCESS     not-accessible
   STATUS     mandatory
   DESCRIPTION
     "This variable represents the index for the swAv tables."
::= { swAvRowStatusEntry 10 }

swAvOperTable OBJECT-TYPE
   SYNTAX     SEQUENCE OF SwAvOperEntry
   ACCESS     not-accessible
   STATUS     mandatory
   DESCRIPTION
     "*** THIS TABLE CURRENTLY NOT IMPLEMENTED ***

      This group contains the operational attributes for an AV component."
::= { swAv 10 }

swAvOperEntry OBJECT-TYPE
   SYNTAX     SwAvOperEntry
   ACCESS     not-accessible
   STATUS     mandatory
   DESCRIPTION
     "An entry in the swAvOperTable."
   INDEX {
      swIndex,
      swAvIndex }
::= { swAvOperTable 1 }

SwAvOperEntry ::= SEQUENCE {
   swAvProcessorTargets
      OCTET STRING }

swAvProcessorTargets OBJECT-TYPE
   SYNTAX     OCTET STRING (SIZE (1))
   ACCESS     read-only
   STATUS     mandatory
   DESCRIPTION
     "This is a list of the processor based object file types which exist on 
      disk for a given AV. Semantic check will validate that the object 
      files needed for a provisioned card type are present as part of an 
      application.

      Description of bits:
      i960(0)
      ppc(1)"
::= { swAvOperEntry 1 }

swAvCompatibleAvListTable OBJECT-TYPE
   SYNTAX     SEQUENCE OF SwAvCompatibleAvListEntry
   ACCESS     not-accessible
   STATUS     mandatory
   DESCRIPTION
     "*** THIS TABLE CURRENTLY NOT IMPLEMENTED ***

      This is a list of the AV names which specify the minimum version 
      of all other applications that can be used in conjunction with this AV 
      in an AVL. Semantic checks will validate that AVs within the AVL 
      are indeed compatible."
::= { swAv 259 }

swAvCompatibleAvListEntry OBJECT-TYPE
   SYNTAX     SwAvCompatibleAvListEntry
   ACCESS     not-accessible
   STATUS     mandatory
   DESCRIPTION
     "An entry in the swAvCompatibleAvListTable."
   INDEX {
      swIndex,
      swAvIndex,
      swAvCompatibleAvListValue }
::= { swAvCompatibleAvListTable 1 }

SwAvCompatibleAvListEntry ::= SEQUENCE {
   swAvCompatibleAvListValue
      AsciiString }

swAvCompatibleAvListValue OBJECT-TYPE
   SYNTAX     AsciiString (SIZE (1..30))
   ACCESS     read-only
   STATUS     mandatory
   DESCRIPTION
     "This variable represents both the value and the index for the
      swAvCompatibleAvListTable."
::= { swAvCompatibleAvListEntry 1 }

-- 
-- *** THIS SUBTREE CURRENTLY NOT IMPLEMENTED ***
-- 

-- Sw Av/<name> Feat/<name>
-- There is one of these components for each provisionable feature of 
-- the parent AV component. Each feature's name can be used in an 
-- LPT's featureList attribute. A Feature component does not have any 
-- attributes of its own.

swAvFeat OBJECT IDENTIFIER ::= { swAv 2 }



swAvFeatRowStatusTable OBJECT-TYPE
   SYNTAX     SEQUENCE OF SwAvFeatRowStatusEntry
   ACCESS     not-accessible
   STATUS     mandatory
   DESCRIPTION
     "*** THIS TABLE CURRENTLY NOT IMPLEMENTED ***

      This entry controls the addition and deletion of 
      swAvFeat components."
::= { swAvFeat 1 }

swAvFeatRowStatusEntry OBJECT-TYPE
   SYNTAX     SwAvFeatRowStatusEntry
   ACCESS     not-accessible
   STATUS     mandatory
   DESCRIPTION
     "A single entry in the table represents a single 
      swAvFeat component."
   INDEX {
      swIndex,
      swAvIndex,
      swAvFeatIndex }
::= { swAvFeatRowStatusTable 1 }

SwAvFeatRowStatusEntry ::= SEQUENCE {
   swAvFeatRowStatus
      RowStatus,
   swAvFeatComponentName
      DisplayString,
   swAvFeatStorageType
      StorageType,
   swAvFeatIndex
      AsciiStringIndex }

swAvFeatRowStatus OBJECT-TYPE
   SYNTAX     RowStatus 
   ACCESS     read-only
   STATUS     mandatory
   DESCRIPTION
     "This variable is used as the basis for SNMP naming of
      swAvFeat components.
      These components cannot be added nor deleted."
::= { swAvFeatRowStatusEntry 1 }

swAvFeatComponentName OBJECT-TYPE
   SYNTAX     DisplayString 
   ACCESS     read-only
   STATUS     mandatory
   DESCRIPTION
     "This variable provides the component's string name for
      use with the ASCII Console Interface"
::= { swAvFeatRowStatusEntry 2 }

swAvFeatStorageType OBJECT-TYPE
   SYNTAX     StorageType 
   ACCESS     read-only
   STATUS     mandatory
   DESCRIPTION
     "This variable represents the storage type value for the
      swAvFeat tables."
::= { swAvFeatRowStatusEntry 4 }

swAvFeatIndex OBJECT-TYPE
   SYNTAX     AsciiStringIndex (SIZE (1..25))
   ACCESS     not-accessible
   STATUS     mandatory
   DESCRIPTION
     "This variable represents the index for the swAvFeat tables."
::= { swAvFeatRowStatusEntry 10 }

-- 
-- *** THIS SUBTREE CURRENTLY NOT IMPLEMENTED ***
-- 

-- Sw Av/<name> Patch/<name>
-- There is one of these components for each patch of the parent AV 
-- component that has been downloaded to the switch.

swAvPatch OBJECT IDENTIFIER ::= { swAv 3 }



swAvPatchRowStatusTable OBJECT-TYPE
   SYNTAX     SEQUENCE OF SwAvPatchRowStatusEntry
   ACCESS     not-accessible
   STATUS     mandatory
   DESCRIPTION
     "*** THIS TABLE CURRENTLY NOT IMPLEMENTED ***

      This entry controls the addition and deletion of 
      swAvPatch components."
::= { swAvPatch 1 }

swAvPatchRowStatusEntry OBJECT-TYPE
   SYNTAX     SwAvPatchRowStatusEntry
   ACCESS     not-accessible
   STATUS     mandatory
   DESCRIPTION
     "A single entry in the table represents a single 
      swAvPatch component."
   INDEX {
      swIndex,
      swAvIndex,
      swAvPatchIndex }
::= { swAvPatchRowStatusTable 1 }

SwAvPatchRowStatusEntry ::= SEQUENCE {
   swAvPatchRowStatus
      RowStatus,
   swAvPatchComponentName
      DisplayString,
   swAvPatchStorageType
      StorageType,
   swAvPatchIndex
      AsciiStringIndex }

swAvPatchRowStatus OBJECT-TYPE
   SYNTAX     RowStatus 
   ACCESS     read-only
   STATUS     mandatory
   DESCRIPTION
     "This variable is used as the basis for SNMP naming of
      swAvPatch components.
      These components cannot be added nor deleted."
::= { swAvPatchRowStatusEntry 1 }

swAvPatchComponentName OBJECT-TYPE
   SYNTAX     DisplayString 
   ACCESS     read-only
   STATUS     mandatory
   DESCRIPTION
     "This variable provides the component's string name for
      use with the ASCII Console Interface"
::= { swAvPatchRowStatusEntry 2 }

swAvPatchStorageType OBJECT-TYPE
   SYNTAX     StorageType 
   ACCESS     read-only
   STATUS     mandatory
   DESCRIPTION
     "This variable represents the storage type value for the
      swAvPatch tables."
::= { swAvPatchRowStatusEntry 4 }

swAvPatchIndex OBJECT-TYPE
   SYNTAX     AsciiStringIndex (SIZE (1..30))
   ACCESS     not-accessible
   STATUS     mandatory
   DESCRIPTION
     "This variable represents the index for the swAvPatch tables."
::= { swAvPatchRowStatusEntry 10 }

swAvPatchOperTable OBJECT-TYPE
   SYNTAX     SEQUENCE OF SwAvPatchOperEntry
   ACCESS     not-accessible
   STATUS     mandatory
   DESCRIPTION
     "*** THIS TABLE CURRENTLY NOT IMPLEMENTED ***

      This group contains the operational attributes for the Patch 
      component."
::= { swAvPatch 10 }

swAvPatchOperEntry OBJECT-TYPE
   SYNTAX     SwAvPatchOperEntry
   ACCESS     not-accessible
   STATUS     mandatory
   DESCRIPTION
     "An entry in the swAvPatchOperTable."
   INDEX {
      swIndex,
      swAvIndex,
      swAvPatchIndex }
::= { swAvPatchOperTable 1 }

SwAvPatchOperEntry ::= SEQUENCE {
   swAvPatchDescription
      AsciiString }

swAvPatchDescription OBJECT-TYPE
   SYNTAX     AsciiString (SIZE (0..512))
   ACCESS     read-only
   STATUS     mandatory
   DESCRIPTION
     "This attribute indicates the new behavior that the patch provides. 
      The availability of this description is dependent on the disk being 
      available."
::= { swAvPatchOperEntry 1 }


-- Sw Lpt/<name>
-- This component specifies characteristics of the software to be 
-- loaded on a card. Minimally, LPT/CP is required to exist. If it is 
-- deleted, semantic checks will fail.

swLpt OBJECT IDENTIFIER ::= { sw 4 }



swLptRowStatusTable OBJECT-TYPE
   SYNTAX     SEQUENCE OF SwLptRowStatusEntry
   ACCESS     not-accessible
   STATUS     mandatory
   DESCRIPTION
     "This entry controls the addition and deletion of 
      swLpt components."
::= { swLpt 1 }

swLptRowStatusEntry OBJECT-TYPE
   SYNTAX     SwLptRowStatusEntry
   ACCESS     not-accessible
   STATUS     mandatory
   DESCRIPTION
     "A single entry in the table represents a single 
      swLpt component."
   INDEX {
      swIndex,
      swLptIndex }
::= { swLptRowStatusTable 1 }

SwLptRowStatusEntry ::= SEQUENCE {
   swLptRowStatus
      RowStatus,
   swLptComponentName
      DisplayString,
   swLptStorageType
      StorageType,
   swLptIndex
      AsciiStringIndex }

swLptRowStatus OBJECT-TYPE
   SYNTAX     RowStatus 
   ACCESS     read-write
   STATUS     mandatory
   DESCRIPTION
     "This variable is used as the basis for SNMP naming of
      swLpt components.
      These components can be added and deleted."
::= { swLptRowStatusEntry 1 }

swLptComponentName OBJECT-TYPE
   SYNTAX     DisplayString 
   ACCESS     read-only
   STATUS     mandatory
   DESCRIPTION
     "This variable provides the component's string name for
      use with the ASCII Console Interface"
::= { swLptRowStatusEntry 2 }

swLptStorageType OBJECT-TYPE
   SYNTAX     StorageType 
   ACCESS     read-only
   STATUS     mandatory
   DESCRIPTION
     "This variable represents the storage type value for the
      swLpt tables."
::= { swLptRowStatusEntry 4 }

swLptIndex OBJECT-TYPE
   SYNTAX     AsciiStringIndex (SIZE (1..25))
   ACCESS     not-accessible
   STATUS     mandatory
   DESCRIPTION
     "This variable represents the index for the swLpt tables."
::= { swLptRowStatusEntry 10 }

swLptProvTable OBJECT-TYPE
   SYNTAX     SEQUENCE OF SwLptProvEntry
   ACCESS     not-accessible
   STATUS     mandatory
   DESCRIPTION
     "This group contains the provisionable attributes for the LPT 
      component."
::= { swLpt 10 }

swLptProvEntry OBJECT-TYPE
   SYNTAX     SwLptProvEntry
   ACCESS     not-accessible
   STATUS     mandatory
   DESCRIPTION
     "An entry in the swLptProvTable."
   INDEX {
      swIndex,
      swLptIndex }
::= { swLptProvTable 1 }

SwLptProvEntry ::= SEQUENCE {
   swLptCommentText
      AsciiString,
   swLptSystemConfig
      INTEGER }

swLptCommentText OBJECT-TYPE
   SYNTAX     AsciiString (SIZE (0..80))
   ACCESS     read-write
   STATUS     mandatory
   DESCRIPTION
     "An arbitrary string used to enter a comment about an LPT."
::= { swLptProvEntry 1 }

swLptSystemConfig OBJECT-TYPE
   SYNTAX     INTEGER  {
                 default(0) }
   ACCESS     read-write
   STATUS     mandatory
   DESCRIPTION
     "This attribute specifies which set of preconfigured system 
      parameters to use for the set of Features selected in featureList."
   DEFVAL     { default }
::= { swLptProvEntry 2 }

swLptFlTable OBJECT-TYPE
   SYNTAX     SEQUENCE OF SwLptFlEntry
   ACCESS     not-accessible
   STATUS     mandatory
   DESCRIPTION
     "This attribute specifies a list of names of Features that define a 
      particular configuration of application functionality that the user 
      wants to load on a single processor. 
      The combination of Features selected must be compatible (for 
      example, none can be mutually exclusive with another in the list).
      All Features must belong to an AV specified in the AVL.
      All Features must be able to be loaded on any of the Cards which 
      are linked to LPs which are linked to this LPT.
      All prerequisite Features of the ones in this list will also be loaded."
::= { swLpt 257 }

swLptFlEntry OBJECT-TYPE
   SYNTAX     SwLptFlEntry
   ACCESS     not-accessible
   STATUS     mandatory
   DESCRIPTION
     "An entry in the swLptFlTable."
   INDEX {
      swIndex,
      swLptIndex,
      swLptFlValue }
::= { swLptFlTable 1 }

SwLptFlEntry ::= SEQUENCE {
   swLptFlValue
      AsciiString,
   swLptFlRowStatus
      RowStatus }

swLptFlValue OBJECT-TYPE
   SYNTAX     AsciiString (SIZE (1..25))
   ACCESS     read-write
   STATUS     mandatory
   DESCRIPTION
     "This variable represents both the value and the index for the
      swLptFlTable."
::= { swLptFlEntry 1 }

swLptFlRowStatus OBJECT-TYPE
   SYNTAX     RowStatus 
   ACCESS     write-only
   STATUS     mandatory
   DESCRIPTION
     "This variable is used to control the addition and deletion 
      of individual values of the swLptFlTable."
::= { swLptFlEntry 2 }

swLptLogicalProcessorsTable OBJECT-TYPE
   SYNTAX     SEQUENCE OF SwLptLogicalProcessorsEntry
   ACCESS     not-accessible
   STATUS     mandatory
   DESCRIPTION
     "This attribute shows which LPs are configured to load the Feature 
      files associated with this LPT. It is the opposite side of the LP 
      component's logicalProcessorType link attribute."
::= { swLpt 258 }

swLptLogicalProcessorsEntry OBJECT-TYPE
   SYNTAX     SwLptLogicalProcessorsEntry
   ACCESS     not-accessible
   STATUS     mandatory
   DESCRIPTION
     "An entry in the swLptLogicalProcessorsTable."
   INDEX {
      swIndex,
      swLptIndex,
      swLptLogicalProcessorsValue }
::= { swLptLogicalProcessorsTable 1 }

SwLptLogicalProcessorsEntry ::= SEQUENCE {
   swLptLogicalProcessorsValue
      Link }

swLptLogicalProcessorsValue OBJECT-TYPE
   SYNTAX     Link 
   ACCESS     read-only
   STATUS     mandatory
   DESCRIPTION
     "This variable represents both the value and the index for the
      swLptLogicalProcessorsTable."
::= { swLptLogicalProcessorsEntry 1 }




-- 
-- Version and Compliance statements
-- 



-- Object-Group Statement:
-- A list of all current accessible leaf objects.

-- OBJECTS { swLptLogicalProcessorsValue,
--           swAvlValue,
--           swDldDownloadedAvListValue,
--           swDldFilesToTransfer,
--           swAvPatchRowStatus,
--           swLptCommentText,
--           swAvListToTidyValue,
--           swLptFlValue,
--           swRowStatus,
--           swLptComponentName,
--           swAvFeatComponentName,
--           swDldRowStatus,
--           swLptStorageType,
--           swAvPatchDescription,
--           swAvFeatStorageType,
--           swAvRowStatus,
--           swDldProcessorTargets,
--           swLptSystemConfig,
--           swAvCompatibleAvListValue,
--           swAvPatchComponentName,
--           swDldDldListRowStatus,
--           swAvBeingTidied,
--           swComponentName,
--           swLptFlRowStatus,
--           swTidyStatus,
--           swAvListTidiedValue,
--           swDldComponentName,
--           swPatlRowStatus,
--           swStorageType,
--           swDldAvBeingDownloaded,
--           swDldDldListValue,
--           swDldStorageType,
--           swAvPatchStorageType,
--           swAvComponentName,
--           swAvlRowStatus,
--           swPatlValue,
--           swAvStorageType,
--           swAvFeatRowStatus,
--           swDldStatus,
--           swLptRowStatus,
--           swAvProcessorTargets }
-- STATUS  mandatory
-- DESCRIPTION
--   "A list of all current accessible leaf objects."

softwareGroup OBJECT IDENTIFIER ::= { softwareMIB 1 }
softwareGroupBE OBJECT IDENTIFIER ::= { softwareGroup 5 }
softwareGroupBE01 OBJECT IDENTIFIER ::= { softwareGroupBE 2 }
softwareGroupBE01A OBJECT IDENTIFIER ::= { softwareGroupBE01 2 }



-- Agent-Capabilities Statement:

-- PRODUCT-RELEASE "Passport Release 7.0 Software."
-- STATUS          mandatory
-- DESCRIPTION     "Software MIB: MIB Version BE01A,
--                  Software Version BG00S4C."
-- SUPPORTS        Nortel-Magellan-Passport-SoftwareMIB
--    INCLUDES     { softwareGroupBE01A }

softwareCapabilities OBJECT IDENTIFIER ::= { softwareMIB 3 }
softwareCapabilitiesBE OBJECT IDENTIFIER ::= { softwareCapabilities 5 }
softwareCapabilitiesBE01 OBJECT IDENTIFIER ::= { softwareCapabilitiesBE 2 }
softwareCapabilitiesBE01A OBJECT IDENTIFIER ::= { softwareCapabilitiesBE01 2 }





END
