-- **********************************************************************
--
-- Product:             3Com LinkBuilder Repeater Groups
-- MIB Version:         2.00A
-- Comments:            The MIB is used in conjunction with version 2.00 of
--                      the FMS agent software, which supports all FMS, FMS II
--                      and 10BT/BTi units. This release is hosted on a 3C16030
--                      FMS Management Module.
--
-- History:             Date                    Reason for Change
--                      4th October 1993        Created from 1.30 MIB.
--                                              PDDRM Monitor Port Table now
--                                              supports per-port control of
--                                              link-state and partition traps.
--			11th November 1993	Created from 1.40 MIB.
--						Added support Resilience.
--						Added support for FMS II Units.
--						Added support for Modular Bridge.
--						Added SMART MIB Objects.
--
-- **********************************************************************
--	Copyright 3Com Technologies Limited. (1991) (1992) (1993)
-- **********************************************************************



-- --------------------------------------------------------------------
-- ************ THE STARTING POINT FOR ALL MIB DEFINITIONS ************
-- --------------------------------------------------------------------

          LBHUB-REPEATER-MIB DEFINITIONS ::= BEGIN

          IMPORTS
                  mgmt, NetworkAddress, IpAddress, Counter, Gauge,
                          TimeTicks, enterprises
                      FROM RFC1155-SMI
                  OBJECT-TYPE
		      FROM RFC-1212
		  TRAP-TYPE
		      FROM RFC-1215
		  DisplayString, PhysAddress
		      FROM RFC1213-MIB;

          --  This MIB module uses the extended OBJECT-TYPE macro as
          --  defined in RFC 1212;

          --  MIB-II (same prefix as MIB-I)

          mib-2      OBJECT IDENTIFIER ::= { mgmt 1 }

          -- textual conventions

          DisplayString ::= OCTET STRING
          -- This data type is used to model textual information taken
          -- from the NVT ASCII character set.  By convention, objects
          -- with this syntax are declared as having
          --
          --      SIZE (0..255)

          PhysAddress ::= OCTET STRING
          -- This data type is used to model media addresses.  For many
          -- types of media, this will be in a binary representation.
          -- For example, an ethernet address would be represented as
          -- a string of 6 octets.

          -- groups in MIB-II

          system       OBJECT IDENTIFIER ::= { mib-2 1 }
          interfaces   OBJECT IDENTIFIER ::= { mib-2 2 }
          at           OBJECT IDENTIFIER ::= { mib-2 3 }
          ip           OBJECT IDENTIFIER ::= { mib-2 4 }
          icmp         OBJECT IDENTIFIER ::= { mib-2 5 }
          tcp          OBJECT IDENTIFIER ::= { mib-2 6 }
          udp          OBJECT IDENTIFIER ::= { mib-2 7 }
          egp          OBJECT IDENTIFIER ::= { mib-2 8 }

          -- historical (some say hysterical)
          -- cmot      OBJECT IDENTIFIER ::= { mib-2 9 }
          transmission OBJECT IDENTIFIER ::= { mib-2 10 }
          snmp         OBJECT IDENTIFIER ::= { mib-2 11 }

          dot1dBridge  OBJECT IDENTIFIER ::= { mib-2 17 }


-- --------------------------------------------------------------------
-- ******************* PRIVATE BRANCH FOR 3Com ************************
-- --------------------------------------------------------------------

-- private		OBJECT IDENTIFIER ::= { internet 4 }
-- enterprises	OBJECT IDENTIFIER ::= { private 1 }

a3Com		OBJECT IDENTIFIER ::= { enterprises 43 }

products	OBJECT IDENTIFIER ::= { a3Com 1 }

	terminalServer		OBJECT IDENTIFIER ::= { products 1 }
	dedicatedBridgeServer	OBJECT IDENTIFIER ::= { products 2 }
	dedicatedRouteServer	OBJECT IDENTIFIER ::= { products 3 }
	brouter			OBJECT IDENTIFIER ::= { products 4 }
	genericMSWorkstation	OBJECT IDENTIFIER ::= { products 5 }
	genericMSServer		OBJECT IDENTIFIER ::= { products 6 }
	genericUnixServer	OBJECT IDENTIFIER ::= { products 7 }
	hub			OBJECT IDENTIFIER ::= { products 8 }
	cards			OBJECT IDENTIFIER ::= { products 9 }
	chipsets		OBJECT IDENTIFIER ::= { products 10 }

		linkBuilder3GH		OBJECT IDENTIFIER ::= { hub 1 }
		linkBuilder10BTi	OBJECT IDENTIFIER ::= { hub 2 }
		linkBuilderECS		OBJECT IDENTIFIER ::= { hub 3 }
		linkBuilderMSH		OBJECT IDENTIFIER ::= { hub 4 }
		linkBuilderFMS		OBJECT IDENTIFIER ::= { hub 5 }
		linkBuilderFDDIwg	OBJECT IDENTIFIER ::= { hub 6 }
		linkBuilderFMSII	OBJECT IDENTIFIER ::= { hub 7 }
		linkSwitchFMS		OBJECT IDENTIFIER ::= { hub 8 }
		linkSwitchMSH		OBJECT IDENTIFIER ::= { hub 9 }
		linkBuilderFMSLBridge	OBJECT IDENTIFIER ::= { hub 10 }

		linkBuilder3GH-cards	OBJECT IDENTIFIER ::= { cards 1 }
		linkBuilder10BTi-cards	OBJECT IDENTIFIER ::= { cards 2 }
		linkBuilderECS-cards	OBJECT IDENTIFIER ::= { cards 3 }
		linkBuilderMSH-cards	OBJECT IDENTIFIER ::= { cards 4 }
		linkBuilderFMS-cards	OBJECT IDENTIFIER ::= { cards 5 }
		linkBuilderFMSII-cards	OBJECT IDENTIFIER ::= { cards 6 }

			linkBuilder10BTi-cards-utp	OBJECT IDENTIFIER ::= { linkBuilder10BTi-cards 1 }
			linkBuilder10BT-cards-utp	OBJECT IDENTIFIER ::= { linkBuilder10BTi-cards 2 }

			linkBuilderFMS-cards-utp	OBJECT IDENTIFIER ::= { linkBuilderFMS-cards 1 }
			linkBuilderFMS-cards-coax	OBJECT IDENTIFIER ::= { linkBuilderFMS-cards 2 }
			linkBuilderFMS-cards-fiber	OBJECT IDENTIFIER ::= { linkBuilderFMS-cards 3 }
			linkBuilderFMS-cards-12fiber	OBJECT IDENTIFIER ::= { linkBuilderFMS-cards 4 }
			linkBuilderFMS-cards-24utp	OBJECT IDENTIFIER ::= { linkBuilderFMS-cards 5 }

			linkBuilderFMSII-cards-12tp-rj45	OBJECT IDENTIFIER ::= { linkBuilderFMSII-cards 1 }
			linkBuilderFMSII-cards-10coax-bnc	OBJECT IDENTIFIER ::= { linkBuilderFMSII-cards 2 }
			linkBuilderFMSII-cards-6fiber-st	OBJECT IDENTIFIER ::= { linkBuilderFMSII-cards 3 }
			linkBuilderFMSII-cards-12fiber-st	OBJECT IDENTIFIER ::= { linkBuilderFMSII-cards 4 }
			linkBuilderFMSII-cards-24tp-rj45	OBJECT IDENTIFIER ::= { linkBuilderFMSII-cards 5 }
			linkBuilderFMSII-cards-24tp-telco	OBJECT IDENTIFIER ::= { linkBuilderFMSII-cards 6 }

--experimental		OBJECT IDENTIFIER ::= { a3Com 2 }
amp-mib			OBJECT IDENTIFIER ::= { a3Com 3 }
genericTrap		OBJECT IDENTIFIER ::= { a3Com 4 }
viewBuilderApps		OBJECT IDENTIFIER ::= { a3Com 5 }
specificTrap		OBJECT IDENTIFIER ::= { a3Com 6 }
linkBuilder3GH-mib	OBJECT IDENTIFIER ::= { a3Com 7 }
linkBuilder10BTi-mib 	OBJECT IDENTIFIER ::= { a3Com 8 }
linkBuilderECS-mib	OBJECT IDENTIFIER ::= { a3Com 9 }
generic			OBJECT IDENTIFIER ::= { a3Com 10 }

        genExperimental 	OBJECT IDENTIFIER ::= { generic 1 }
	setup			OBJECT IDENTIFIER ::= { generic 2 }
	sysLoader		OBJECT IDENTIFIER ::= { generic 3 }
	security		OBJECT IDENTIFIER ::= { generic 4 }
	gauges			OBJECT IDENTIFIER ::= { generic 5 }
	asciiAgent		OBJECT IDENTIFIER ::= { generic 6 }
	serialIf		OBJECT IDENTIFIER ::= { generic 7 }
	repeaterMgmt		OBJECT IDENTIFIER ::= { generic 8 }
	endStation		OBJECT IDENTIFIER ::= { generic 9 }
	localSnmp		OBJECT IDENTIFIER ::= { generic 10 }
	manager			OBJECT IDENTIFIER ::= { generic 11 }
	unusedGeneric12		OBJECT IDENTIFIER ::= { generic 12 }
	chassis			OBJECT IDENTIFIER ::= { generic 14 }
	mrmResilience		OBJECT IDENTIFIER ::= { generic 15 }
	tokenRing		OBJECT IDENTIFIER ::= { generic 16 }
	multiRepeater 		OBJECT IDENTIFIER ::= { generic 17 }
	bridgeMgmt		OBJECT IDENTIFIER ::= { generic 18 }
	fault			OBJECT IDENTIFIER ::= { generic 19 }
	poll			OBJECT IDENTIFIER ::= { generic 20 }
	powerSupply		OBJECT IDENTIFIER ::= { generic 21 }

		testData	OBJECT IDENTIFIER ::= { genExperimental 1 }
		ifExtensions	OBJECT IDENTIFIER ::= { genExperimental 2 }

netBuilder-mib			OBJECT IDENTIFIER ::= { a3Com 11 }
lBridgeECS-mib			OBJECT IDENTIFIER ::= { a3Com 12 }
deskMan-mib			OBJECT IDENTIFIER ::= { a3Com 13 }
linkBuilderMSH-mib		OBJECT IDENTIFIER ::= { a3Com 14 }
linkBuilderFMS-mib		OBJECT IDENTIFIER ::= { a3Com 15 }
linkBuilderFDDI-wghub-mib	OBJECT IDENTIFIER ::= { a3Com 16 }
linkSwitch-mib			OBJECT IDENTIFIER ::= { a3Com 17 }



snmpDot3RptrMgt		OBJECT IDENTIFIER ::= {mib-2 22}

MacAddress		::= OCTET STRING (SIZE(6))

rptrBasicPackage	OBJECT IDENTIFIER ::= {snmpDot3RptrMgt 1}
rptrMonitorPackage	OBJECT IDENTIFIER ::= {snmpDot3RptrMgt 2}
rptrAddrTrackPackage	OBJECT IDENTIFIER ::= {snmpDot3RptrMgt 3}

rptrRptrInfo		OBJECT IDENTIFIER ::= {rptrBasicPackage 1}
rptrGroupInfo		OBJECT IDENTIFIER ::= {rptrBasicPackage 2}
rptrPortInfo		OBJECT IDENTIFIER ::= {rptrBasicPackage 3}

rptrMonitorRptrInfo	OBJECT IDENTIFIER ::= {rptrMonitorPackage 1}
rptrMonitorGroupInfo	OBJECT IDENTIFIER ::= {rptrMonitorPackage 2}
rptrMonitorPortInfo	OBJECT IDENTIFIER ::= {rptrMonitorPackage 3}

rptrAddrTrackRptrInfo	OBJECT IDENTIFIER ::= {rptrAddrTrackPackage 1}  -- this subtree is currently unused
rptrAddrTrackGroupInfo	OBJECT IDENTIFIER ::= {rptrAddrTrackPackage 2}  -- this subtree is currently unused
rptrAddrTrackPortInfo	OBJECT IDENTIFIER ::= {rptrAddrTrackPackage 3}

--
--		    The BASIC GROUP
--
-- Implementation of the Basic Group is mandatory for all
-- managed repeaters.

--
-- Basic Repeater Information
--
-- Configuration, STATUS, and control objects for the overall
-- repeater
--

rptrGroupCapacity OBJECT-TYPE
			SYNTAX			INTEGER (1..1024)
			ACCESS			read-only
			STATUS			mandatory
			DESCRIPTION
			"The rptrGroupCapacity is the number of groups
			that can be contained within the repeater.  Within
			each managed repeater, the groups are uniquely
			numbered in the range from 1 to rptrGroupCapacity.

			Some groups may not be present in the repeater, in
			which case the actual number of groups present
			will be less than rptrGroupCapacity.  The number
			of groups present will never be greater than
			rptrGroupCapacity.

			Note:  In practice, this will generally be the
			number of field-replaceable units (i.e., modules,
			cards, or boards) that can fit in the physical
			repeater enclosure, and the group numbers will
			correspond to numbers marked on the physical
			enclosure."
			::= {rptrRptrInfo 1}

rptrOperSTATUS		OBJECT-TYPE
			SYNTAX		INTEGER {
						other(1),		-- undefined or unknown STATUS
						ok(2),			-- no known failures
						rptrFailure(3), 	-- repeater-related failure
						groupFailure(4), 	-- group-related failure
						portFailure(5), 	-- port-related failure
						generalFailure(6) 	-- failure, unspecified type
			}
			ACCESS			read-only
			STATUS			mandatory
			DESCRIPTION
			"The rptrOperSTATUS object indicates the
			operational state of the repeater.  The
			rptrHealthText object may be consulted for more
			specific information about the state of the
			repeater's health.

			In the case of multiple kinds of failures (e.g.,
			repeater failure and port failure), the value of
			this attribute shall reflect the highest priority
			failure in the following order, listed highest
			priority first:

			    rptrFailure(3)
			    groupFailure(4)
			    portFailure(5)
			    generalFailure(6)."
			::= {rptrRptrInfo 2}

rptrHealthText		OBJECT-TYPE
			SYNTAX			DisplayString (SIZE (0..255))
			ACCESS			read-only
			STATUS			mandatory
			DESCRIPTION
			"The health text object is a text string that
			provides information relevant to the operational
			state of the repeater.  Agents may use this string
			to provide detailed information on current
			failures, including how they were detected, and/or
			instructions for problem resolution.  The contents
			are agent-specific."
			::= {rptrRptrInfo 3}

rptrReset		OBJECT-TYPE
			SYNTAX			INTEGER {
			      				noReset(1),
			      				reset(2)
			 				}
			ACCESS			read-write
			STATUS			mandatory
			DESCRIPTION
			"Setting this object to reset(2) causes a
			transition to the START state of Fig 9-2 in
			section 9 [IEEE 802.3 Std].

			Setting this object to noReset(1) has no effect.
			The agent will always return the value noReset(1)
			when this object is read.

			After receiving a request to set this variable to
			reset(2), the agent is allowed to delay the reset
			for a short period.  For example, the implementor
			may choose to delay the reset long enough to allow
			the SNMP response to be transmitted.  In any
			event, the SNMP response must be transmitted.

			This action does not reset the management counters
			defined in this document nor does it affect the
			portAdminSTATUS parameters.  Included in this
			action is the execution of a disruptive Self-Test
			with the following characteristics:  a) The nature
			of the tests is not specified.  b) The test resets
			the repeater but without affecting management
			information about the repeater.  c) The test does
			not inject packets onto any segment.  d) Packets
			received during the test may or may not be
			transferred.  e) The test does not interfere with
			management functions.

			After performing this self-test, the agent will
			update the repeater health information (including
			rptrOperSTATUS and rptrHealthText), and send a
			rptrHealth trap."
			::= {rptrRptrInfo 4}

rptrNonDisruptTest OBJECT-TYPE
			SYNTAX			INTEGER {
			      				noSelfTest(1),
			      				selfTest(2)
			 				}
			ACCESS			read-write
			STATUS			mandatory
			DESCRIPTION
			"Setting this object to selfTest(2) causes the
			repeater to perform a agent-specific, non-
			disruptive self-test that has the following
			characteristics:  a) The nature of the tests is
			not specified.  b) The test does not change the
			state of the repeater or management information
			about the repeater.  c) The test does not inject
			packets onto any segment.  d) The test does not
			prevent the relay of any packets.  e) The test
			does not interfere with management functions.

			After performing this test, the agent will update
			the repeater health information (including
			rptrOperSTATUS and rptrHealthText) and send a
			rptrHealth trap.

			Note that this definition allows returning an
			'okay' result after doing a trivial test.

			Setting this object to noSelfTest(1) has no
			effect.  The agent will always return the value
			noSelfTest(1) when this object is read."
			::= {rptrRptrInfo 5}

rptrTotalPartitionedPorts OBJECT-TYPE
			SYNTAX			Gauge
			ACCESS			read-only
			STATUS			mandatory
			DESCRIPTION
			"This object returns the total number of ports in
			the repeater whose current state meets all three
			of the following criteria:  rptrPortOperSTATUS
			does not have the value notPresent(3),
			rptrPortAdminSTATUS is enabled(1), and
			rptrPortAutoPartitionState is autoPartitioned(2)."
			::= {rptrRptrInfo 6}

--
-- The Basic Port Group Table
--

rptrGroupTable		OBJECT-TYPE
			SYNTAX			SEQUENCE OF RptrGroupEntry
			ACCESS			not-accessible
			STATUS			mandatory
			DESCRIPTION
			"Table of descriptive and STATUS information about
			the groups of ports."
			::= {rptrGroupInfo 1}

rptrGroupEntry		OBJECT-TYPE
			SYNTAX			RptrGroupEntry
			ACCESS			not-accessible
			STATUS			mandatory
			DESCRIPTION
			"An entry in the table, containing information
			about a single group of ports."
			INDEX    {rptrGroupIndex}
			::= {rptrGroupTable 1}

			RptrGroupEntry ::= SEQUENCE {
		    				rptrGroupIndex				INTEGER,
		   				rptrGroupDescr				DisplayString,
		    				rptrGroupObjectID			OBJECT IDENTIFIER,
		    				rptrGroupOperSTATUS			INTEGER,
		    				rptrGroupLastOperSTATUSChange		TimeTicks,
		    				rptrGroupPortCapacity			INTEGER
			}

rptrGroupIndex		OBJECT-TYPE
			SYNTAX			INTEGER (1..1024)
			ACCESS			read-only
			STATUS			mandatory
			DESCRIPTION
			"This object identifies the group within the
			repeater for which this entry contains
			information.  This value is never greater than
			rptrGroupCapacity."
			::= {rptrGroupEntry 1}

rptrGroupDescr		OBJECT-TYPE
			SYNTAX			DisplayString (SIZE (0..255))
			ACCESS			read-only
			STATUS			mandatory
			DESCRIPTION
			"A textual description of the group.  This value
			should include the full name and version
			identification of the group's hardware type and
			indicate how the group is differentiated from
			other types of groups in the repeater.  Plug-in
			Module, Rev A' or 'Barney Rubble 10BASE-T 4-port
			SIMM socket Version 2.1' are examples of valid
			group descriptions.

			It is mandatory that this only contain printable
			ASCII characters."
			::= {rptrGroupEntry 2}

rptrGroupObjectID	OBJECT-TYPE
			SYNTAX			OBJECT IDENTIFIER
			ACCESS			read-only
			STATUS			mandatory
			DESCRIPTION
			"The vendor's authoritative identification of the
			group.  This value may be allocated within the SMI
			enterprises subtree (1.3.6.1.4.1) and provides a
			straight-forward and unambiguous means for
			determining what kind of group is being managed.

			For example, this object could take the value
			1.3.6.1.4.1.4242.1.2.14 if vendor 'Flintstones,
			Inc.' was assigned the subtree 1.3.6.1.4.1.4242,
			and had assigned the identifier
			1.3.6.1.4.1.4242.1.2.14 to its 'Wilma Flintstone
			6-Port FOIRL Plug-in Module.'"
			::= {rptrGroupEntry 3}

rptrGroupOperSTATUS	OBJECT-TYPE
			SYNTAX			INTEGER {
			     				other(1),
			      				operational(2),
			      				malfunctioning(3),
			      				notPresent(4),
			      				underTest(5),
			      				resetInProgress(6)
			 }
			ACCESS			read-only
			STATUS			mandatory
			DESCRIPTION
			"An object that indicates the operational STATUS
			of the group.

			A STATUS of notPresent(4) indicates that the group
			is temporarily or permanently physically and/or
			logically not a part of the repeater.  It is an
			implementation-specific matter as to whether the
			agent effectively removes notPresent entries from
			the table.

			A STATUS of operational(2) indicates that the
			group is functioning, and a STATUS of
			malfunctioning(3) indicates that the group is
			malfunctioning in some way."
			::= {rptrGroupEntry 4}

rptrGroupLastOperSTATUSChange		OBJECT-TYPE
			SYNTAX			TimeTicks
			ACCESS			read-only
			STATUS			mandatory
			DESCRIPTION
			"An object that contains the value of sysUpTime at
			the time that the value of the rptrGroupOperSTATUS
			object for this group last changed.

			A value of zero indicates that the group's
			operational STATUS has not changed since the agent
			last restarted."
			::= {rptrGroupEntry 5}

rptrGroupPortCapacity OBJECT-TYPE
			SYNTAX			INTEGER (1..1024)
			ACCESS			read-only
			STATUS			mandatory
			DESCRIPTION
			"The rptrGroupPortCapacity is the number of ports
			that can be contained within the group.  Valid
			range is 1-1024.  Within each group, the ports are
			uniquely numbered in the range from 1 to
			rptrGroupPortCapacity.

			Note:  In practice, this will generally be the
			number of ports on a module, card, or board, and
			the port numbers will correspond to numbers marked
			on the physical embodiment."
			::= {rptrGroupEntry 6}

--
-- The Basic Port Table
--

rptrPortTable		OBJECT-TYPE
			SYNTAX			SEQUENCE OF RptrPortEntry
			ACCESS			not-accessible
			STATUS			mandatory
			DESCRIPTION
			"Table of descriptive and STATUS information about
			the ports."
			::= {rptrPortInfo 1}

rptrPortEntry OBJECT-TYPE
			SYNTAX			RptrPortEntry
			ACCESS			not-accessible
			STATUS			mandatory
			DESCRIPTION
			"An entry in the table, containing information
			about a single port."
			INDEX    		{rptrPortGroupIndex,rptrPortIndex}
			::= {rptrPortTable 1}

			RptrPortEntry ::= SEQUENCE {
		   			 rptrPortGroupIndex				INTEGER,
		  			 rptrPortIndex					INTEGER,
		   			 rptrPortAdminSTATUS				INTEGER,
		   			 rptrPortAutoPartitionState			INTEGER,
		   			 rptrPortOperSTATUS				INTEGER
			}

rptrPortGroupIndex OBJECT-TYPE
			SYNTAX			INTEGER (1..1024)
			ACCESS			read-only
			STATUS			mandatory
			DESCRIPTION
			"This object identifies the group containing the
			port for which this entry contains information."
			::= {rptrPortEntry 1}

rptrPortIndex OBJECT-TYPE
			SYNTAX			INTEGER (1..1024)
			ACCESS			read-only
			STATUS			mandatory
			DESCRIPTION
			"This object identifies the port within the group
			for which this entry contains information.  This
			value can never be greater than
			rptrGroupPortCapacity for the associated group."
			::= {rptrPortEntry 2}

rptrPortAdminSTATUS OBJECT-TYPE
			SYNTAX			INTEGER {
			      enabled(1),
			      disabled(2)
			 }
			ACCESS			read-write
			STATUS			mandatory
			DESCRIPTION
			"Setting this object to disabled(2) disables the
			port.  A disabled port neither transmits nor
			receives.  Once disabled, a port must be
			explicitly enabled to restore operation.  A port
			which is disabled when power is lost or when a
			reset is exerted shall remain disabled when normal
			operation resumes.

			The admin STATUS takes precedence over auto-
			partition and functionally operates between the
			auto-partition mechanism and the AUI/PMA.

			Setting this object to enabled(1) enables the port
			and exerts a BEGIN on the port's auto-partition
			state machine.

			(In effect, when a port is disabled, the value of
			rptrPortAutoPartitionState for that port is frozen
			until the port is next enabled.  When the port
			becomes enabled, the rptrPortAutoPartitionState
			becomes notAutoPartitioned(1), regardless of its
			pre-disabling state.)"
			::= {rptrPortEntry 3}

rptrPortAutoPartitionState OBJECT-TYPE
			SYNTAX			INTEGER {
			      				notAutoPartitioned(1),
			     				autoPartitioned(2)
							 }
			ACCESS			read-only
			STATUS			mandatory
			DESCRIPTION
			"The autoPartitionState flag indicates whether the
			port is currently partitioned by the repeater's
			auto-partition protection.

			The conditions that cause port partitioning are
			specified in partition state machine in Section 9
			[IEEE 802.3 Std].  They are not differentiated
			here."
			::= {rptrPortEntry 4}

rptrPortOperSTATUS	OBJECT-TYPE
			SYNTAX			INTEGER {
			     	 			operational(1),
			      				notOperational(2),
			      				notPresent(3)
			 				}
			ACCESS			read-only
			STATUS			mandatory
			DESCRIPTION
			"This object indicates the port's operational
				STATUS.  The notPresent(3) status indicates the
			port is physically removed (note this may or may
			not be possible depending on the type of port.)
			The operational(1) STATUS indicates that the port
			is enabled (see rptrPortAdminSTATUS) and working,
			even though it might be auto-partitioned (see
			rptrPortAutoPartitionState).

			If this object has the value operational(1) and
			rptrPortAdminSTATUS is set to disabled(2), it is
			expected that this object's value will soon change
			to notOperational(2)."
			::= {rptrPortEntry 5}

--
--		    The MONITOR GROUP
--
-- Implementation of this group is optional, but within the
-- group all elements are mandatory.  If a managed repeater
-- implements any part of this group, the entire group shall
-- be implemented.

--
-- Repeater Monitor Information
--
-- Performance monitoring statistics for the repeater
--

rptrMonitorTransmitCollisions OBJECT-TYPE
			SYNTAX			Counter
			ACCESS			read-only
			STATUS			mandatory
			DESCRIPTION
			"This counter is incremented every time the
			repeater state machine enters the TRANSMIT
			COLLISION state from any state other than ONE PORT
			LEFT (Ref: Fig 9-2, IEEE 802.3 Std).

			The approximate minimum time for rollover of this
			counter is 16 hours."
			::= {rptrMonitorRptrInfo 1}

--
-- The Group Monitor Table
--

rptrMonitorGroupTable	OBJECT-TYPE
			SYNTAX			SEQUENCE OF RptrMonitorGroupEntry
			ACCESS			not-accessible
			STATUS			mandatory
			DESCRIPTION
			"Table of performance and error statistics for the
			groups."
			::= {rptrMonitorGroupInfo 1}

rptrMonitorGroupEntry	OBJECT-TYPE
			SYNTAX			RptrMonitorGroupEntry
			ACCESS			not-accessible
			STATUS			mandatory
			DESCRIPTION
			"An entry in the table, containing total
			performance and error statistics for a single
			group.  Regular retrieval of the information in
			this table provides a means of tracking the
			performance and health of the networked devices
			attached to this group's ports.

			The counters in this table are redundant in the
			sense that they are the summations of information
			already available through other objects.  However,
			these sums provide a considerable optimization of
			network management traffic over the otherwise
			necessary retrieval of the individual counters
			included in each sum."
			INDEX    {rptrMonitorGroupIndex}
			::= {rptrMonitorGroupTable 1}

			RptrMonitorGroupEntry ::= SEQUENCE {
		    				rptrMonitorGroupIndex			INTEGER,
		    				rptrMonitorGroupTotalFrames		Counter,
		    				rptrMonitorGroupTotalOctets		Counter,
		    				rptrMonitorGroupTotalErrors		Counter
			}

rptrMonitorGroupIndex	OBJECT-TYPE
			SYNTAX			INTEGER (1..1024)
			ACCESS			read-only
			STATUS			mandatory
			DESCRIPTION
			"This object identifies the group within the
			repeater for which this entry contains
			information."
			::= {rptrMonitorGroupEntry 1}

rptrMonitorGroupTotalFrames OBJECT-TYPE
			SYNTAX			Counter
			ACCESS			read-only
			STATUS			mandatory
			DESCRIPTION
			"The total number of frames of valid frame length
			that have been received on the ports in this group
			and for which the FCSError and CollisionEvent
			signals were not asserted.  This counter is the
			summation of the values of the
			rptrMonitorPortReadableFrames counters for all of
			the ports in the group.

			This statistic provides one of the parameters
			necessary for obtaining the packet error rate.
			The approximate minimum time for rollover of this
			counter is 80 hours."
			::= {rptrMonitorGroupEntry 2}

rptrMonitorGroupTotalOctets OBJECT-TYPE
			SYNTAX			Counter
			ACCESS			read-only
			STATUS			mandatory
			DESCRIPTION
			"The total number of octets contained in the valid
			frames that have been received on the ports in
			this group.  This counter is the summation of the
			values of the rptrMonitorPortReadableOctets
			counters for all of the ports in the group.

			This statistic provides an indicator of the total
			data transferred.  The approximate minimum time
			for rollover of this counter is 58 minutes."
			::= {rptrMonitorGroupEntry 3}

rptrMonitorGroupTotalErrors OBJECT-TYPE
			SYNTAX			Counter
			ACCESS			read-only
			STATUS			mandatory
			DESCRIPTION
			"The total number of errors which have occurred on
			all of the ports in this group.  This counter is
			the summation of the values of the
			rptrMonitorPortTotalErrors counters for all of the
			ports in the group."
			::= {rptrMonitorGroupEntry 4}

--
-- The Port Monitor Table
--

rptrMonitorPortTable OBJECT-TYPE
			SYNTAX			SEQUENCE OF RptrMonitorPortEntry
			ACCESS			not-accessible
			STATUS			mandatory
			DESCRIPTION
			"Table of performance and error statistics for the
			ports."
			::= {rptrMonitorPortInfo 1}

rptrMonitorPortEntry OBJECT-TYPE
			SYNTAX			RptrMonitorPortEntry
			ACCESS			not-accessible
			STATUS			mandatory
			DESCRIPTION
			"An entry in the table, containing performance and
			error statistics for a single port."
			INDEX    		{rptrMonitorPortGroupIndex,rptrMonitorPortIndex}
			::= {rptrMonitorPortTable 1}

			RptrMonitorPortEntry ::= SEQUENCE {
		    				rptrMonitorPortGroupIndex		INTEGER,
		    				rptrMonitorPortIndex			INTEGER,
		    				rptrMonitorPortReadableFrames		Counter,
		    				rptrMonitorPortReadableOctets		Counter,
		    				rptrMonitorPortFCSErrors		Counter,
		    				rptrMonitorPortAlignmentErrors		Counter,
		    				rptrMonitorPortFrameTooLongs		Counter,
		    				rptrMonitorPortShortEvents		Counter,
		    				rptrMonitorPortRunts			Counter,
		    				rptrMonitorPortCollisions		Counter,
		    				rptrMonitorPortLateEvents		Counter,
		    				rptrMonitorPortVeryLongEvents		Counter,
		    				rptrMonitorPortDataRateMismatches	Counter,
		    				rptrMonitorPortAutoPartitions		Counter,
		    				rptrMonitorPortTotalErrors		Counter
			}

rptrMonitorPortGroupIndex OBJECT-TYPE
			SYNTAX			INTEGER (1..1024)
			ACCESS			read-only
			STATUS			mandatory
			DESCRIPTION
			"This object identifies the group containing the
			port for which this entry contains information."
			::= {rptrMonitorPortEntry 1}

rptrMonitorPortIndex OBJECT-TYPE
			SYNTAX			INTEGER (1..1024)
			ACCESS			read-only
			STATUS			mandatory
			DESCRIPTION
			"This object identifies the port within the group
			for which this entry contains information."
			::= {rptrMonitorPortEntry 2}

rptrMonitorPortReadableFrames OBJECT-TYPE
			SYNTAX			Counter
			ACCESS			read-only
			STATUS			mandatory
			DESCRIPTION
			"This object is the number of frames of valid
			frame length that have been received on this port.
			This counter is incremented by one for each frame
			received on this port whose OctetCount is greater
			than or equal to minFrameSize and less than or
			equal to maxFrameSize (Ref: IEEE 802.3 Std,
			4.4.2.1) and for which the FCSError and
			CollisionEvent signals are not asserted.

			This statistic provides one of the parameters
			necessary for obtaining the packet error rate.
			The approximate minimum time for rollover of this
			counter is 80 hours."
			::= {rptrMonitorPortEntry 3}

rptrMonitorPortReadableOctets OBJECT-TYPE
			SYNTAX			Counter
			ACCESS			read-only
			STATUS			mandatory
			DESCRIPTION
			"This object is the number of octets contained in
			valid frames that have been received on this port.
			This counter is incremented by OctetCount for each
			frame received on this port which has been
			determined to be a readable frame (i.e., including
			FCS octets but excluding framing bits and dribble
			bits).

			This statistic provides an indicator of the total
			data transferred.  The approximate minimum time
			for rollover of this counter is 58 minutes."
			::= {rptrMonitorPortEntry 4}

rptrMonitorPortFCSErrors OBJECT-TYPE
			SYNTAX			Counter
			ACCESS			read-only
			STATUS			mandatory
			DESCRIPTION
			"This counter is incremented by one for each frame
			received on this port with the FCSError signal
			asserted and the FramingError and CollisionEvent
			signals deasserted and whose OctetCount is greater
			than or equal to minFrameSize and less than or
			equal to maxFrameSize (Ref: 4.4.2.1, IEEE 802.3
			Std).

			The approximate minimum time for rollover of this
			counter is 80 hours."
			::= {rptrMonitorPortEntry 5}

rptrMonitorPortAlignmentErrors OBJECT-TYPE
			SYNTAX			Counter
			ACCESS			read-only
			STATUS			mandatory
			DESCRIPTION
			"This counter is incremented by one for each frame
			received on this port with the FCSError and
			FramingError signals asserted and CollisionEvent
			signal deasserted and whose OctetCount is greater
			than or equal to minFrameSize and less than or
			equal to maxFrameSize (Ref: IEEE 802.3 Std,
			4.4.2.1).  If rptrMonitorPortAlignmentErrors is
			incremented then the rptrMonitorPortFCSErrors
			Counter shall not be incremented for the same
			frame.

			The approximate minimum time for rollover of this
			counter is 80 hours."
			::= {rptrMonitorPortEntry 6}

rptrMonitorPortFrameTooLongs OBJECT-TYPE
			SYNTAX			Counter
			ACCESS			read-only
			STATUS			mandatory
			DESCRIPTION
			"This counter is incremented by one for each frame
			received on this port whose OctetCount is greater
			than maxFrameSize (Ref: 4.4.2.1, IEEE 802.3 Std).
			If rptrMonitorPortFrameTooLongs is incremented
			then neither the rptrMonitorPortAlignmentErrors
			nor the rptrMonitorPortFCSErrors counter shall be
			incremented for the frame.

			The approximate minimum time for rollover of this
			counter is 61 days."
			::= {rptrMonitorPortEntry 7}

rptrMonitorPortShortEvents OBJECT-TYPE
			SYNTAX			Counter
			ACCESS			read-only
			STATUS			mandatory
			DESCRIPTION
			"This counter is incremented by one for each
			CarrierEvent on this port with ActivityDuration
			less than ShortEventMaxTime.  ShortEventMaxTime is
			greater than 74 bit times and less than 82 bit
			times.  ShortEventMaxTime has tolerances included
			to provide for circuit losses between a
			conformance test point at the AUI and the
			measurement point within the state machine.

			Note:  shortEvents may indicate externally
			generated noise hits which will cause the repeater
			to transmit Runts to its other ports, or propagate
			a collision (which may be late) back to the
			transmitting DTE and damaged frames to the rest of
			the network.

			Implementors may wish to consider selecting the
			ShortEventMaxTime towards the lower end of the
			allowed tolerance range to accommodate bit losses
			suffered through physical channel devices not
			budgeted for within this standard.

			The approximate minimum time for rollover of this
			counter is 16 hours."
			::= {rptrMonitorPortEntry 8}

rptrMonitorPortRunts	OBJECT-TYPE
			SYNTAX			Counter
			ACCESS			read-only
			STATUS			mandatory
			DESCRIPTION
			"This counter is incremented by one for each
			CarrierEvent on this port that meets one of the
			following two conditions.  Only one test need be
			made.  a) The ActivityDuration is greater than
			ShortEventMaxTime and less than ValidPacketMinTime
			and the CollisionEvent signal is deasserted.  b)
			The OctetCount is less than 64, the
			ActivityDuration is greater than ShortEventMaxTime
			and the CollisionEvent signal is deasserted.
			ValidPacketMinTime is greater than or equal to 552
			bit times and less than 565 bit times.

			An event whose length is greater than 74 bit times
			but less than 82 bit times shall increment either
			the shortEvents counter or the runts counter but
			not both.  A CarrierEvent greater than or equal to
			552 bit times but less than 565 bit times may or
			may not be counted as a runt.

			ValidPacketMinTime has tolerances included to
			provide for circuit losses between a conformance
			test point at the AUI and the measurement point
			within the state machine.

			Runts usually indicate collision fragments, a
			normal network event.  In certain situations
			associated with large diameter networks a
			percentage of collision fragments may exceed
			ValidPacketMinTime.

			The approximate minimum time for rollover of this
			counter is 16 hours."
			::= {rptrMonitorPortEntry 9}

rptrMonitorPortCollisions OBJECT-TYPE
			SYNTAX			Counter
			ACCESS			read-only
			STATUS			mandatory
			DESCRIPTION
			"This counter is incremented by one for any
			CarrierEvent signal on any port for which the
			CollisionEvent signal on this port is also
			asserted.

			The approximate minimum time for rollover of this
			counter is 16 hours."
			::= {rptrMonitorPortEntry 10}

rptrMonitorPortLateEvents OBJECT-TYPE
			SYNTAX			Counter
			ACCESS			read-only
			STATUS			mandatory
			DESCRIPTION
			"This counter is incremented by one for each
			CarrierEvent on this port in which the CollIn(X)
			variable transitions to the value SQE (Ref:
			9.6.6.2, IEEE 802.3 Std) while the
			ActivityDuration is greater than the
			LateEventThreshold.  Such a CarrierEvent is
			counted twice, as both a collision and as a
			lateEvent.

			The LateEventThreshold is greater than 480 bit
			times and less than 565 bit times.
			LateEventThreshold has tolerances included to
			permit an implementation to build a single
			threshold to serve as both the LateEventThreshold
			and ValidPacketMinTime threshold.

			The approximate minimum time for rollover of this
			counter is 81 hours."
			::= {rptrMonitorPortEntry 11}

rptrMonitorPortVeryLongEvents OBJECT-TYPE
			SYNTAX			Counter
			ACCESS			read-only
			STATUS			mandatory
			DESCRIPTION
			"This counter is incremented by one for each
			CarrierEvent on this port whose ActivityDuration
			is greater than the MAU Jabber Lockup Protection
			timer TW3 (Ref: 9.6.1 & 9.6.5, IEEE 802.3 Std).
			Other counters may be incremented as appropriate."
			::= {rptrMonitorPortEntry 12}

rptrMonitorPortDataRateMismatches OBJECT-TYPE
			SYNTAX			Counter
			ACCESS			read-only
			STATUS			mandatory
			DESCRIPTION
			"This counter is incremented by one for each frame
			received on this port that meets all of the
			following conditions:  a) The CollisionEvent
			signal is not asserted.  b) The ActivityDuration
			is greater than ValidPacketMinTime.  c) The
			frequency (data rate) is detectably mismatched
			from the local transmit frequency.  The exact
			degree of mismatch is vendor specific and is to be
			defined by the vendor for conformance testing.

			When this event occurs, other counters whose
			increment conditions were satisfied may or may not
			also be incremented, at the implementor's
			discretion.  Whether or not the repeater was able
			to maintain data integrity is beyond the scope of
			this standard."
			::= {rptrMonitorPortEntry 13}

rptrMonitorPortAutoPartitions OBJECT-TYPE
			SYNTAX			Counter
			ACCESS			read-only
			STATUS			mandatory
			DESCRIPTION
			"This counter is incremented by one for each time
			the repeater has automatically partitioned this
			port.  The conditions that cause port partitioning
			are specified in the partition state machine in
			Section 9 [IEEE 802.3 Std].  They are not
			differentiated here."
			::= {rptrMonitorPortEntry 14}

rptrMonitorPortTotalErrors OBJECT-TYPE
			SYNTAX			Counter
			ACCESS			read-only
			STATUS			mandatory
			DESCRIPTION
			"The total number of errors which have occurred on
			this port.  This counter is the summation of the
			values of other error counters (for the same
			port), namely:

			    rptrMonitorPortFCSErrors,
			    rptrMonitorPortAlignmentErrors,
			    rptrMonitorPortFrameTooLongs,
			    rptrMonitorPortShortEvents,
			    rptrMonitorPortLateEvents,
			    rptrMonitorPortVeryLongEvents, and
			    rptrMonitorPortDataRateMismatches.

			This counter is redundant in the sense that it is
			the summation of information already available
			through other objects.  However, it is included
			specifically because the regular retrieval of this
			object as a means of tracking the health of a port
			provides a considerable optimization of network
			management traffic over the otherwise necessary
			retrieval of the summed counters."
			::= {rptrMonitorPortEntry 15}

--
--		    The ADDRESS TRACKING GROUP
--
-- Implementation of this group is optional; it is appropriate
-- for all systems which have the necessary instrumentation.  If a
-- managed repeater implements any part of this group, the entire
-- group shall be implemented.

--
-- The Port Address Tracking Table
--

rptrAddrTrackTable	OBJECT-TYPE
			SYNTAX			SEQUENCE OF RptrAddrTrackEntry
			ACCESS			not-accessible
			STATUS			mandatory
			DESCRIPTION
			"Table of address mapping information about the
			ports."
			::= {rptrAddrTrackPortInfo 1}

rptrAddrTrackEntry OBJECT-TYPE
			SYNTAX			RptrAddrTrackEntry
			ACCESS			not-accessible
			STATUS			mandatory
			DESCRIPTION
			"An entry in the table, containing address mapping
			information about a single port."
			INDEX    {rptrAddrTrackGroupIndex,rptrAddrTrackPortIndex}
			::= {rptrAddrTrackTable 1}

			RptrAddrTrackEntry ::= SEQUENCE {
		    				rptrAddrTrackGroupIndex		INTEGER,
		    				rptrAddrTrackPortIndex		INTEGER,
		    				rptrAddrTrackLastSourceAddress  MacAddress,  -- DEPRECATED OBJECT
		    				rptrAddrTrackSourceAddrChanges	Counter,
		    				rptrAddrTrackNewLastSrcAddress	OCTET STRING
			}

rptrAddrTrackGroupIndex OBJECT-TYPE
			SYNTAX			INTEGER (1..1024)
			ACCESS			read-only
			STATUS			mandatory
			DESCRIPTION
			"This object identifies the group containing the
			port for which this entry contains information."
			::= {rptrAddrTrackEntry 1}

rptrAddrTrackPortIndex OBJECT-TYPE
			SYNTAX			INTEGER (1..1024)
			ACCESS			read-only
			STATUS			mandatory
			DESCRIPTION
			"This object identifies the port within the group
			for which this entry contains information."
			::= {rptrAddrTrackEntry 2}

rptrAddrTrackLastSourceAddress OBJECT-TYPE
			SYNTAX			MacAddress
			ACCESS			read-only
			STATUS			deprecated
			DESCRIPTION
			"This object is the SourceAddress of the last
			readable frame (i.e., counted by
			rptrMonitorPortReadableFrames) received by this
			port.

			This object has been deprecated because its value
			is undefined when no frames have been observed on
			this port.  The replacement object is
			rptrAddrTrackNewLastSrcAddress."
			::= {rptrAddrTrackEntry 3}

rptrAddrTrackSourceAddrChanges OBJECT-TYPE
			SYNTAX			Counter
			ACCESS			read-only
			STATUS			mandatory
			DESCRIPTION
			"This counter is incremented by one for each time
			that the rptrAddrTrackLastSourceAddress attribute
			for this port has changed.

			This may indicate whether a link is connected to a
			single DTE or another multi-user segment.

			The approximate minimum time for rollover of this
			counter is 81 hours."
			::= {rptrAddrTrackEntry 4}

rptrAddrTrackNewLastSrcAddress OBJECT-TYPE
			SYNTAX			OCTET STRING (SIZE(0..6))
			ACCESS			read-only
			STATUS			mandatory
			DESCRIPTION
			"This object is the SourceAddress of the last
			readable frame (i.e., counted by
			rptrMonitorPortReadableFrames) received by this
			port.  If no frames have been received by this
			port since the agent began monitoring the port
			activity, the agent shall return a string of
			length zero."
			::= {rptrAddrTrackEntry 5}

-- Traps for use by Repeaters

-- Traps are defined using the conventions in RFC 1215 [6].

--rptrHealth	TRAP-TYPE
--		ENTERPRISE  snmpDot3RptrMgt
--		VARIABLES   {rptrOperSTATUS}
--			DESCRIPTION
--			"The rptrHealth trap conveys information related
--			to the operational STATUS of the repeater.  This
--			trap is sent either when the value of
--			rptrOperSTATUS changes, or upon completion of a
--			non-disruptive test.
--
--			The rptrHealth trap must contain the
--			rptrOperSTATUS object.  The agent may optionally
--			include the rptrHealthText object in the varBind
--			list.  See the rptrOperSTATUS and rptrHealthText
--			objects for descriptions of the information that
--			is sent.
--
--			The agent must throttle the generation of
--			consecutive rptrHealth traps so that there is at
--			least a five-second gap between traps of this
--			type.  When traps are throttled, they are dropped,
--			not queued for sending at a future time.  (Note
--			that 'generating' a trap means sending to all
--			configured recipients.)"
--		::= 21
--
--rptrGroupChange TRAP-TYPE
--		ENTERPRISE  snmpDot3RptrMgt
--		VARIABLES   {rptrGroupIndex}
--			DESCRIPTION
--			"This trap is sent when a change occurs in the
--			group structure of a repeater.  This occurs only
--			when a group is logically or physically removed
--			from or added to a repeater.  The varBind list
--			contains the identifier of the group that was
--			removed or added.
--
--			The agent must throttle the generation of
--			consecutive rptrGroupChange traps for the same
--			group so that there is at least a five-second gap
--			between traps of this type.  When traps are
--			throttled, they are dropped, not queued for
--			sending at a future time.  (Note that 'generating'
--			a trap means sending to all configured
--			recipients.)"
--		::= 22
--
--rptrResetEvent TRAP-TYPE
--		ENTERPRISE  snmpDot3RptrMgt
--		VARIABLES   {rptrOperSTATUS}
--			DESCRIPTION
--			"The rptrResetEvent trap conveys information
--			related to the operational STATUS of the repeater.
--			This trap is sent on completion of a repeater
--			reset action.  A repeater reset action is defined
--			as an a transition to the START state of Fig 9-2
--			in section 9 [IEEE 802.3 Std], when triggered by a
--			management command (e.g., an SNMP Set on the
--			rptrReset object).
--
--			The agent must throttle the generation of
--			consecutive rptrResetEvent traps so that there is
--			at least a five-second gap between traps of this
--			type.  When traps are throttled, they are dropped,
--			not queued for sending at a future time.  (Note
--			that 'generating' a trap means sending to all
--			configured recipients.)
--
--			The rptrResetEvent trap is not sent when the agent
--			restarts and sends an SNMP coldStart or warmStart
--			trap.  However, it is recommended that a repeater
--			agent send the rptrOper STATUS object as an
--			optional object with its coldStart and warmStart
--			trap PDUs.
--
--			The rptrOper STATUS object must be included in the
--			varbind list sent with this trap.  The agent may
--			optionally include the rptrHealthText object as
--			well."
--		::=			23
snmpDot3MauMgt 		OBJECT IDENTIFIER ::= { mib-2 26 }

dot3RpMauBasicGroup 	OBJECT IDENTIFIER ::= { snmpDot3MauMgt 1 }
dot3IfMauBasicGroup 	OBJECT IDENTIFIER ::= { snmpDot3MauMgt 2 }
dot3BroadMauBasicGroup 	OBJECT IDENTIFIER ::= { snmpDot3MauMgt 3 }

-- object identifiers for MAU types
--  (see rpMauType and ifMauType for usage)

dot3MauType		OBJECT IDENTIFIER ::= { snmpDot3MauMgt 4 }
dot3MauTypeAUI		OBJECT IDENTIFIER ::= { dot3MauType 1 }		-- no internal MAU, view from AUI
dot3MauType10Base5	OBJECT IDENTIFIER ::= { dot3MauType 2 }		-- thick coax MAU (per 802.3 section 8)
dot3MauTypeFoirl	OBJECT IDENTIFIER ::= { dot3MauType 3 }		-- FOIRL MAU (per 802.3 section 9.9)
dot3MauType10Base2	OBJECT IDENTIFIER ::= { dot3MauType 4 }		-- thin coax MAU (per 802.3 section 10)
dot3MauType10BaseT	OBJECT IDENTIFIER ::= { dot3MauType 5 }		-- UTP MAU (per 802.3 section 14)
dot3MauType10BaseFP	OBJECT IDENTIFIER ::= { dot3MauType 6 }		-- passive fiber MAU (per 802.3 section 16)
dot3MauType10BaseFB	OBJECT IDENTIFIER ::= { dot3MauType 7 }		-- sync fiber MAU (per 802.3 section 17)
dot3MauType10BaseFL	OBJECT IDENTIFIER ::= { dot3MauType 8 }		-- async fiber MAU (per 802.3 section 18)
dot3MauType10Broad36	OBJECT IDENTIFIER ::= { dot3MauType 9 }		-- broadband DTE MAU (per 802.3 section 11)

--
--                    The Repeater MAU Basic Group
--
-- Implementation of the Repeater MAU Basic Group is mandatory
-- for MAUs attached to repeaters.

--
-- The Basic Repeater MAU Table
--

rpMauTable OBJECT-TYPE
		SYNTAX    SEQUENCE OF RpMauEntry
		ACCESS    not-accessible
		STATUS    mandatory
		DESCRIPTION
		"Table of descriptive and status information about
		the MAU(s) attached to the ports of a repeater."
		::= { dot3RpMauBasicGroup 1 }

rpMauEntry OBJECT-TYPE
		SYNTAX    RpMauEntry
		ACCESS    not-accessible
		STATUS    mandatory
		DESCRIPTION
		"An entry in the table, containing information
		about a single MAU."
		INDEX    { rpMauGroupIndex, rpMauPortIndex, rpMauIndex }
		::= { rpMauTable 1 }

		RpMauEntry ::= SEQUENCE {
				rpMauGroupIndex			INTEGER,
				rpMauPortIndex			INTEGER,
				rpMauIndex			INTEGER,
				rpMauType			OBJECT IDENTIFIER,
				rpMauStatus			INTEGER,
				rpMauMediaAvailable		INTEGER,
				rpMauMediaAvailableStateExits	Counter,
				rpMauJabberState		INTEGER,
				rpMauJabberingStateEnters	Counter
    				}

rpMauGroupIndex OBJECT-TYPE
		SYNTAX    INTEGER (1..1024)
		ACCESS    read-only
		STATUS    mandatory
		DESCRIPTION
		"This variable uniquely identifies the repeater
		group containing the port to which the MAU
		described by this entry is connected."
		REFERENCE
		"Reference RFC1368, rptrGroupIndex."
		::= { rpMauEntry 1 }

rpMauPortIndex OBJECT-TYPE
		SYNTAX    INTEGER (1..1024)
		ACCESS    read-only
		STATUS    mandatory
		DESCRIPTION
		"This variable uniquely identifies the repeater
		port within group rpMauGroupIndex to which the MAU
		described by this entry is connected."
		REFERENCE
		"Reference RFC 1368, rptrPortIndex."
		::= { rpMauEntry 2 }

rpMauIndex OBJECT-TYPE
		SYNTAX    INTEGER (1..1024)
		ACCESS    read-only
		STATUS    mandatory
		DESCRIPTION
		"This variable uniquely identifies the MAU
		connected to port rpMauPortIndex within group
		rpMauGroupIndex that is described by this entry."
		REFERENCE
		"Reference IEEE 802.3 MAU Mgt, 20.2.3.2, aMAUID."
		::= { rpMauEntry 3 }

rpMauType OBJECT-TYPE
		SYNTAX    OBJECT IDENTIFIER
		ACCESS    read-only
		STATUS    mandatory
		DESCRIPTION
		"This object identifies the 10 Mb/s baseband MAU
		type.  An initial set of MAU types are defined
		above.  The assignment of OBJECT IDENTIFIERs to
		new types of MAUs is managed by the IANA.  If the
		MAU type is unknown, the object identifier

		    unknownMauType OBJECT IDENTIFIER ::= { 0 0 }

		is returned.  Note that unknownMauType is a
		syntactically valid object identifier, and any
		conformant implementation of ASN.1 and the BER
		must be able to generate and recognize this
		value."
		REFERENCE
		"Reference IEEE 802.3 MAU Mgt, 20.2.3.2,
		aMAUType."
		::= { rpMauEntry 4 }

rpMauStatus OBJECT-TYPE
		SYNTAX    INTEGER {
		      other(1),
		      unknown(2),
		      operational(3),
		      standby(4),
		      shutdown(5),
		      reset(6)
		  }
		ACCESS    read-write
		STATUS    mandatory
		DESCRIPTION
		"The current state of the MAU.  This object may be
		implemented as a read-only object by those agents
		and MAUs that do not implement software control of
		the MAU state.  Some agents may not support
		setting the value of this object to some of the
		enumerated values.

		The value other(1) is returned if the MAU is in a
		state other than one of the states 2 through 6.

		The value unknown(2) is returned when the MAU's
		true state is unknown; for example, when it is
		being initialized.

		A MAU in the operational(3) state is fully
		functional, operates, and passes signals to its
		attached DTE or repeater port in accordance to its
		specification.

		A MAU in standby(4) state forces DI and CI and the
		media transmitter to idle.  Standby(4) mode only
		applies to link type MAUs.  The state of
		rpMauMediaAvailable is unaffected.

		A MAU in shutdown(5) state assumes the same
		condition on DI, CI, and the media transmitter as
		though it were powered down.  The MAU may return
		other(1) value for the mauJabber and
		rpMauMediaAvailable objects when it is in this
		state.  For an AUI, this state will remove power
		from the AUI.

		Setting this variable to the value reset(6) resets
		the MAU in the same manner as a power-off, power-
		on cycle of at least one-half second would.  The
		agent is not required to return the value reset
		(6).

		Setting this variable to the value operational(3),
		standby(4), or shutdown(5) causes the MAU to
		assume the respective state except that setting a
		mixing-type MAU or an AUI to standby(4) will cause
		the MAU to enter the shutdown state."
        REFERENCE
		"Reference IEEE 802.3 MAU Mgt, 20.2.3.2,
		aMAUAdminState, and 20.2.3.3, acMAUAdminControl
		and acResetMAUAction."
		::= { rpMauEntry 5 }

rpMauMediaAvailable OBJECT-TYPE
		SYNTAX    INTEGER {
		      other(1),
		      unknown(2),
		      available(3),
		      notAvailable(4),
		      remoteFault(5),
		      invalidSignal(6)
		  }
		ACCESS    read-only
		STATUS    mandatory
		DESCRIPTION
		"If the MAU is a link or fiber type (FOIRL,
		10BASE-T, 10BASE-F) then this is equivalent to the
		link test fail state/low light function.  For an
		AUI or a coax (including broadband) MAU this
		indicates whether or not loopback is detected on
		the DI circuit.  The value of this attribute
		persists between packets for MAU types AUI,
		10BASE5, 10BASE2, 10BROAD36, and 10BASE-FP.

		The value other(1) is returned if the
		mediaAvailable state is not one of 2 through 6.

		The value unknown(2) is returned when the MAU's
		true state is unknown; for example, when it is
		being initialized.  At power-up or following a
		reset, the value of this attribute will be unknown
		for AUI, coax, and 10BASE-FP MAUs.  For these MAUs
		loopback will be tested on each transmission
		during which no collision is detected.  If DI is
		receiving input when DO returns to IDL after a
		transmission and there has been no collision
		during the transmission then loopback will be
		detected.  The value of this attribute will only
		change during non-collided transmissions for AUI,
		coax, and 10BASE-FP MAUs.

		The value available(3) indicates that the link,
		light, or loopback is normal.  The value
		notAvailable(4) indicates link loss, low light, or
		no loopback.

		The value remoteFault(5) indicates that a fault
		has been detected at the remote end of the link.
		The value invalidSignal(6) indicates that an
		invalid signal has been received from the other
		end of the link.  Both remoteFault(5) and
		invalidSignal(6) apply only to MAUs of type
		10BASE-FB."
		REFERENCE
		"Reference IEEE 802.3 MAU Mgt, 20.2.3.2,
		aMediaAvailable."
		::= { rpMauEntry 6 }

rpMauMediaAvailableStateExits OBJECT-TYPE
		SYNTAX    Counter
		ACCESS    read-only
		STATUS    mandatory
		DESCRIPTION
		"A count of the number of times that
		rpMauMediaAvailable for this MAU instance leaves
		the state available(3)."
		REFERENCE
		"Reference IEEE 802.3 MAU Mgt, 20.2.3.2,
		lostMediaCount."
		::= { rpMauEntry 7 }

rpMauJabberState OBJECT-TYPE
		SYNTAX    INTEGER {
		      other(1),
		      unknown(2),
		      noJabber(3),
		      jabbering(4)
		  }
		ACCESS    read-only
		STATUS    mandatory
		DESCRIPTION
		"The value other(1) is returned if the jabber
		state is not 2, 3, or 4.  The agent must always
		return other(1) for MAU type dot3MauTypeAUI.

		The value unknown(2) is returned when the MAU's
		true state is unknown; for example, when it is
		being initialized.

		If the MAU is not jabbering the agent returns
		noJabber(3).  This is the 'normal' state.

		If the MAU is in jabber state the agent returns
		the jabbering(4) value."
		REFERENCE
		"Reference IEEE 802.3 MAU Mgt, 20.2.3.2,
		aJabber.jabberFlag."
		::= { rpMauEntry 8 }

rpMauJabberingStateEnters OBJECT-TYPE
		SYNTAX    Counter
		ACCESS    read-only
		STATUS    mandatory
		DESCRIPTION
		"A count of the number of times that
		rpMauJabberState for this MAU instance enters the
		state jabbering(4).  For a MAU of type
		dot3MauTypeAUI, this counter will always indicate
		zero."
		REFERENCE
		"Reference IEEE 802.3 MAU Mgt, 20.2.3.2,
		aJabber.jabberCounter."
		::= { rpMauEntry 9 }

-- Traps for use by 802.3 MAUs

-- Traps are defined using the conventions in RFC 1215 [8].

--rpMauJabberTrap TRAP-TYPE
--		ENTERPRISE  snmpDot3MauMgt
--		VARIABLES   { rpMauJabberState }
--		DESCRIPTION
--		"This trap is sent whenever a managed repeater MAU
--		enters the jabber state.
--
--		The agent must throttle the generation of
--		consecutive rpMauJabberTraps so that there is at
--		least a five-second gap between them."
		-- REFERENCE
		-- "Reference IEEE 802.3 MAU Mgt, 20.2.3.4,
		-- nJabberNotification."
--		::= 24

------------------------------------------------------------------------------------------
--											--
--	The whole of the a3Com(43).linkbuilder10BTi-mib(8).snmpDot3RpMauMgt(5)		--
--	group has been deprecated.							--
--	The group is currently still implemented for backwards compatability,		--
--	but all new applications should use mib-2(1).snmpDot3MauMgt(26) instead.	--
--											--
------------------------------------------------------------------------------------------


       END
