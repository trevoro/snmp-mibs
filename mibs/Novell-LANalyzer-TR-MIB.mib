Novell-LANalyzer-TR-MIB DEFINITIONS ::= BEGIN

IMPORTS
	enterprises, Counter, TimeTicks		FROM RFC1155-SMI
	DisplayString		       		FROM RFC1213-MIB
	OwnerString, EntryStatus       	        FROM RFC1271-MIB
	OBJECT-TYPE		       		FROM RFC-1212
	TRAP-TYPE		       		FROM RFC-1215;

        -- textual conventions

        -- All representations of MAC addresses in this MIB Module use,
        -- as a textual convention (i.e. this convention does not affect
        -- their encoding), the data type:

        MacAddress ::= OCTET STRING (SIZE (6))

-- Token Ring Remote Monitoring MIB

novell			OBJECT IDENTIFIER ::= { enterprises 23 }

productType		OBJECT IDENTIFIER ::= { novell 1 }
mibDoc			OBJECT IDENTIFIER ::= { novell 2 }

ringrmon-mib		OBJECT IDENTIFIER ::= { mibDoc 15 }


tokenRingStatistics	OBJECT IDENTIFIER ::= { ringrmon-mib 1 }
tokenRingHistory	OBJECT IDENTIFIER ::= { ringrmon-mib 2 }
tokenRing               OBJECT IDENTIFIER ::= { ringrmon-mib 3 }


-- The Statistics Group

-- The statistics group in token ring remote network monitoring MIB contains
-- counters for MAC layer frame and byte throughput in terms of promiscuous,
-- multicast and broadcast address.  Also, it contains counters for MAC layer
-- state transitions, MAC and physical layer errors and the size distribution
-- of data frames.  The data frame size distribution is subjected to the view
-- with which the tokenRingStatsDataSource object is associated.

tokenRingStatsTable	OBJECT-TYPE
	SYNTAX	SEQUENCE OF TokenRingStatsEntry
	ACCESS	not-accessible
	STATUS	mandatory
	DESCRIPTION
		"A list of token ring statistics entries."
	::= { tokenRingStatistics 1 }

tokenRingStatsEntry	OBJECT-TYPE
	SYNTAX	TokenRingStatsEntry
	ACCESS	not-accessible
	STATUS	mandatory
	DESCRIPTION
		"A collection of statistics kept for a particular token ring
                 interface."
	INDEX	{ tokenRingStatsIndex }
	::= { tokenRingStatsTable 1 }

TokenRingStatsEntry ::= SEQUENCE {
	tokenRingStatsIndex				INTEGER ( 1..65535 ),
	tokenRingStatsDataSource			OBJECT IDENTIFIER,
	tokenRingStatsDropEvents			Counter,
	tokenRingStatsDataOctets			Counter,
	tokenRingStatsDataPkts				Counter,
	tokenRingStatsBroadcastDataPkts			Counter,
	tokenRingStatsMulticastDataPkts			Counter,
	tokenRingStatsMACOctets				Counter,
	tokenRingStatsMACPkts				Counter,
	tokenRingStatsRingPurges			Counter,
	tokenRingStatsMonitorContentions		Counter,
	tokenRingStatsBeacons				Counter,
	tokenRingStatsLostMonitors			Counter,
	tokenRingStatsDuplicateMonitors			Counter,
	tokenRingStatsDuplicateAddresses		Counter,
	tokenRingStatsRingPollFailures			Counter,
	tokenRingStatsLineErrors			Counter,
	tokenRingStatsInternalErrors			Counter,
	tokenRingStatsBurstErrors			Counter,
	tokenRingStatsACErrors				Counter,
	tokenRingStatsAbortDelimiters			Counter,
	tokenRingStatsLostFrameErrors			Counter,
	tokenRingStatsReceiveCongestions		Counter,
	tokenRingStatsFrameCopiedErrors			Counter,
	tokenRingStatsFrequencyErrors			Counter,
	tokenRingStatsTokenErrors			Counter,
	tokenRingStatsDataPktsUndersizePkts		Counter,
	tokenRingStatsDataPkts18to63Octets		Counter,
	tokenRingStatsDataPkts64to127Octets		Counter,
	tokenRingStatsDataPkts128to255Octets		Counter,
	tokenRingStatsDataPkts256to511Octets		Counter,
	tokenRingStatsDataPkts512to1023Octets		Counter,
	tokenRingStatsDataPkts1024to2047Octets		Counter,
	tokenRingStatsDataPkts2048to4608Octets		Counter,
	tokenRingStatsDataPkts4609to18000Octets		Counter,
	tokenRingStatsDataPktsMoreThan18000Octets	Counter,
	tokenRingStatsOwner				OwnerString,
	tokenRingStatsStatus				EntryStatus
}


tokenRingStatsIndex	OBJECT-TYPE
	SYNTAX	INTEGER ( 1..65535 )
	ACCESS	read-only
	STATUS	mandatory
	DESCRIPTION
		"The value of this object uniquely identifies this
                 tokenRingStat entry."
	::= { tokenRingStatsEntry 1 }

tokenRingStatsDataSource	OBJECT-TYPE
	SYNTAX	OBJECT IDENTIFIER
	ACCESS	read-write
	STATUS	mandatory
	DESCRIPTION
                "This object contains the identifier for the source of the
                 data that this tokenRingStats entry is set up to analyze.
                 The identifier is defined to contain the name of the
                 instance that this entry receives data from.

                 This object may not be modified unless the associated
                 tokenRingStatsEntry object is equal to invalid(4)."
	::= { tokenRingStatsEntry 2 }

tokenRingStatsDropEvents	OBJECT-TYPE
	SYNTAX	Counter
	ACCESS	read-only
	STATUS	mandatory
	DESCRIPTION
                "The total number of events in which packets are dropped by
                 the probe due to lack of resources.  Note that this is not
                 necessarily the number of packets dropped, it is just the 
                 number of times this condition has been detected."
	::= { tokenRingStatsEntry 3 }

tokenRingStatsDataOctets	OBJECT-TYPE
	SYNTAX	Counter
	ACCESS	read-only
	STATUS	mandatory
	DESCRIPTION
                "The total number of good NON-MAC octets received on the
                 network, excluding framing bits but including FCS octets.
                 In contrast to etherStatsOctets, octets from bad packets
                 are not counted."
	::= { tokenRingStatsEntry 4 }

tokenRingStatsDataPkts	OBJECT-TYPE
	SYNTAX	Counter
	ACCESS	read-only
	STATUS	mandatory
	DESCRIPTION
                "The total number of good NON-MAC packets received on the
                 network.  In contrast to etherStatsPkts, bad packets are not
                 counted."
	::= { tokenRingStatsEntry 5 }

tokenRingStatsBroadcastDataPkts 	OBJECT-TYPE
	SYNTAX	Counter
	ACCESS	read-only
	STATUS	mandatory
	DESCRIPTION
                "The total number of good NON-MAC packets received that were
                 direct to the broadcast address.  Note that bad broadcast
                 packets are not counted."
	::= { tokenRingStatsEntry 6 }

tokenRingStatsMulticastDataPkts	OBJECT-TYPE
	SYNTAX	Counter
	ACCESS	read-only
	STATUS	mandatory
	DESCRIPTION
                "The total number of good NON-MAC packets received that were
                 directed to a local or global multicast or functional
                 address.  Note that bad mutlicast packets are not counted."
	::= { tokenRingStatsEntry 7 }

tokenRingStatsMACOctets	OBJECT-TYPE
	SYNTAX	Counter
	ACCESS	read-only
	STATUS	mandatory
	DESCRIPTION
                "The total number of good MAC octets received on the network,
                 excluding framing bits but including FCS octets.  Same as
                 tokenRingStatsDataOctets, octets from bad MAC packets are
                 not counted."
	::= { tokenRingStatsEntry 8 }

tokenRingStatsMACPkts	OBJECT-TYPE
	SYNTAX	Counter
	ACCESS	read-only
	STATUS	mandatory
	DESCRIPTION
                "The total number of good MAC packets received on the network,
                 including unicast, multicast and broadcast MAC packets. Same
                 as tokenRingStatsDataPkts, bad MAC packets are not counted."
	::= { tokenRingStatsEntry 9 }

tokenRingStatsRingPurges	OBJECT-TYPE
	SYNTAX	Counter
	ACCESS	read-only
	STATUS	mandatory
	DESCRIPTION
                "The total number of times that the ring enters the ring purge
                 state from normal ring state.  Ring purge occurs when the
                 active monitor station detects a type 2 soft errors.
                 The ring purge state that comes from the monitor contention
                 or beacon state is not counted."
	::= { tokenRingStatsEntry 10 }

tokenRingStatsMonitorContentions	OBJECT-TYPE
	SYNTAX	Counter
	ACCESS	read-only
	STATUS	mandatory
	DESCRIPTION
                "The total number of times that the ring enters the monitor
                 contention state from normal ring state or ring purge state.
                 Monitor contention occurs when a type 3 soft error occurs 
                 in the network.  The monitor contention state that comes
                 from the beacon state is not counted."
	::= { tokenRingStatsEntry 11 }

tokenRingStatsBeacons	OBJECT-TYPE
	SYNTAX	Counter
	ACCESS	read-only
	STATUS	mandatory
	DESCRIPTION
                "The total number of times that the ring enters the beaconing
                 state.  Beaconing occurs when a type 4 soft error or hard
                 error occurs in the network."
	::= { tokenRingStatsEntry 12 }

tokenRingStatsLostMonitors	OBJECT-TYPE
	SYNTAX	Counter
	ACCESS	read-only
	STATUS	mandatory
	DESCRIPTION
                "The total number of monitor errors reported by the Report
                 Monitor Error MAC frame.  It occurs when the standby monitor
                 fails to detect a good token in 2.6 seconds, or no ring poll
                 process is executed in 15 seconds.  The standby monitor
                 assumes that the active monitor is not present or not
                 functioning.  Lost monitor is a type 3 error and will cause
                 the detect station to initiate the monitor contention
                 process."
	::= { tokenRingStatsEntry 13 }

tokenRingStatsDuplicateMonitors	OBJECT-TYPE
	SYNTAX	Counter
	ACCESS	read-only
	STATUS	mandatory
	DESCRIPTION
                "The total number of duplicate monitor errors reported by the
                 Report Monitor Error MAC frame.  When an active monitor
                 detects a ring purge frame or an active monitor present
                 frame from other station, it realizes another active monitor
                 in the ring.  This station reports duplicate monitor to the 
                 Ring Error Monitor and becomes a standby monitor."
	::= { tokenRingStatsEntry 14 }

tokenRingStatsDuplicateAddresses		OBJECT-TYPE
	SYNTAX	Counter
	ACCESS	read-only
	STATUS	mandatory
	DESCRIPTION
                "The total number of duplicate address errors reported by the
                 Report Monitor Error MAC frame.  It is generated by the
                 station when it detects other stations using its own address."
	::= { tokenRingStatsEntry 15 }

tokenRingStatsRingPollFailures	OBJECT-TYPE
	SYNTAX	Counter
	ACCESS	read-only
	STATUS	mandatory
	DESCRIPTION
                "The total number of Report Ring Poll Failure MAC frames
                 received.  It is generated when the active monitor cannot
                 see a ring poll cycle completed within a time limit.  The
                 MAC address of the last station in the incomplete ring poll
                 cycle is saved in the tokenRingNetwork table for reference."
	::= { tokenRingStatsEntry 16 }

tokenRingStatsLineErrors	OBJECT-TYPE
	SYNTAX	Counter
	ACCESS	read-only
	STATUS	mandatory
	DESCRIPTION
                "The total number of line errors reported to the Ring Error
                 Monitor.  Line error means packet contains incorrect CRC or
                 code violation.  Line error is isolated error.  It is a 
                 type 1 error and no ring recovery is performed."
	::= { tokenRingStatsEntry 17 }

tokenRingStatsInternalErrors	OBJECT-TYPE
	SYNTAX	Counter
	ACCESS	read-only
	STATUS	mandatory
	DESCRIPTION
                "The total number of adapter internal errors reported to the
                 Ring Error Monitor.  Internal error indicates that a station
                 recognizes a recoverable internal error.  Internal error is
                 isolated error.  It is a type 1 error and no ring recovery
                 is performed."
	::= { tokenRingStatsEntry 18 }

tokenRingStatsBurstErrors	OBJECT-TYPE
	SYNTAX	Counter
	ACCESS	read-only
	STATUS	mandatory
	DESCRIPTION
                "The total number of burst errors reported to the Ring Error
                 Monitor.  Burst error indicates that a station detects the
                 absence of transitions for five half-bit times.  Burst error
                 is isolated error.  It is a type 2 error and the active 
                 monitor will purge the ring."
	::= { tokenRingStatsEntry 19 }

tokenRingStatsACErrors	OBJECT-TYPE
	SYNTAX	Counter
	ACCESS	read-only
	STATUS	mandatory
	DESCRIPTION
                "The total number of AC errors reported to the Ring Error 
                 Monitor.  AC error indicates that a station cannot interpret
                 the address recognition bit or the frame copied bit.  AC error
                 is isolated error.  It is a type 1 error and no ring recovery
                 is performed."
	::= { tokenRingStatsEntry 20 }

tokenRingStatsAbortDelimiters	OBJECT-TYPE
	SYNTAX	Counter
	ACCESS	read-only
	STATUS	mandatory
	DESCRIPTION
                "The total number of abort delimiters reported to the Ring
                 Error Monitor.  Abort delimiter indicates that a station 
                 aborts a transmission.  Abort delimiter is isolated error.  
                 It is a type 1 error and no ring recovery is performed."
	::= { tokenRingStatsEntry 21 }

tokenRingStatsLostFrameErrors	OBJECT-TYPE
	SYNTAX	Counter
	ACCESS	read-only
	STATUS	mandatory
	DESCRIPTION
                "The total number of lost frame errors reported to the Ring
                 Error Monitor.  Lost frame error indicates that the end
                 delimiter of a frame is lost in the network.  Lost frame
                 error is non-isolated error.  It is a type 2 error and the
                 active monitor will purge the ring."
	::= { tokenRingStatsEntry 22 }

tokenRingStatsReceiveCongestions	OBJECT-TYPE
	SYNTAX	Counter
	ACCESS	read-only
	STATUS	mandatory
	DESCRIPTION
                "The total number of receive congestion errors reported to the
                 Ring Error Monitor.  Receive congestion error indicates that
                 a station recognizes a frame addressed to its specific address,
                 but has no available buffer space.  Receive congestion error
                 is non-isolated error.  It is a type 1 error and no ring
                 recovery is performed."
	::= { tokenRingStatsEntry 23 }

tokenRingStatsFrameCopiedErrors	OBJECT-TYPE
	SYNTAX	Counter
	ACCESS	read-only
	STATUS	mandatory
	DESCRIPTION
                "The total number of frame copied errors reported to the
                 Ring Error Monitor.  Frame copied error indicates that a
                 station recognizes a frame addressed to its specific address
                 and detects that the FS field A bits are set to 1.  It
                 implies either a line hit or duplicate address.  Frame copied
                 error is non-isolated error.  It is a type 1 error and no
                 ring recovery is performed."
	::= { tokenRingStatsEntry 24 }

tokenRingStatsFrequencyErrors	OBJECT-TYPE
	SYNTAX	Counter
	ACCESS	read-only
	STATUS	mandatory
	DESCRIPTION
                "The total number of frequency errors reported to the Ring
                 Error Monitor.  Frequency error indicates that a station
                 detects that the frequency of the incoming signal differs by
                 more than the standard specified margin.  Frequency error is
                 non-isolated error.  It is a type 3 error and will cause the
                 detect station initiating monitor contention process."
	::= { tokenRingStatsEntry 25 }

tokenRingStatsTokenErrors	OBJECT-TYPE
	SYNTAX	Counter
	ACCESS	read-only
	STATUS	mandatory
	DESCRIPTION
                "The total number of token errors reported to the Ring Error
                 Monitor.  Token error indicates that the Active Monitor
                 station recognizes an error condition that needs a token
                 transmitted.  Token error is non-isolated error.  It is a
                 type 2 error and the active monitor will purge the ring."
	::= { tokenRingStatsEntry 26 }

tokenRingStatsDataPktsUndersizePkts	OBJECT-TYPE
	SYNTAX	Counter
	ACCESS	read-only
	STATUS	mandatory
	DESCRIPTION
                "The total number of packets received that were between 0 and
                 17 octets in length inclusive, excluding framing bits but
                 including FCS octets.  Packets in this category are too short.
                 It is the counterpart of runt packets in Ethernet RMON."
	::= { tokenRingStatsEntry 27 }

tokenRingStatsDataPkts18to63Octets	OBJECT-TYPE
	SYNTAX	Counter
	ACCESS	read-only
	STATUS	mandatory
	DESCRIPTION
                "The total number of data packets received that were between
                 18 and 63 octets in length inclusive, excluding framing bits
                 but including FCS octets.  It is the counterpart of 
                 etherStatsPkts64Octets in Ethernet RMON.  In contrast to
                 Ethernet, error packets are not counted."
	::= { tokenRingStatsEntry 28 }

tokenRingStatsDataPkts64to127Octets	OBJECT-TYPE
	SYNTAX	Counter
	ACCESS	read-only
	STATUS	mandatory
	DESCRIPTION
                "The total number of data packets received that were between
                 64 and 127 octets in length inclusive, excluding framing bits
                 but including FCS octets.  It is the counterpart  of
                 etherStatsPkts65to127Octets in Ethernet RMON.  In contrast
                 to Ethernet, error packets are not counted."
	::= { tokenRingStatsEntry 29 }

tokenRingStatsDataPkts128to255Octets	OBJECT-TYPE
	SYNTAX	Counter
	ACCESS	read-only
	STATUS	mandatory
	DESCRIPTION
                "The total number of data packets received that were between
                 128 and 255 octets in length inclusive, excluding framing bits
                 but including FCS octets.  It is the counterpart of
                 etherStatsPkts128to255Octets in Ethernet RMON.  In contrast
                 to Ethernet, error packets are not counted."
	::= { tokenRingStatsEntry 30 }

tokenRingStatsDataPkts256to511Octets	OBJECT-TYPE
	SYNTAX	Counter
	ACCESS	read-only
	STATUS	mandatory
	DESCRIPTION
                "The total number of data packets received that were between
                 256 and 511 octets in length inclusive, excluding framing
                 bits but including FCS octets.  It is the counterpart of
                 etherStatsPkts256to511Octets in Ethernet RMON.  In contrast
                 to Ethernet, error packets are not counted."
	::= { tokenRingStatsEntry 31 }

tokenRingStatsDataPkts512to1023Octets	OBJECT-TYPE
	SYNTAX	Counter
	ACCESS	read-only
	STATUS	mandatory
	DESCRIPTION
                "The total number of data packets received that were between
                 512 and 1023 octets in length inclusive, excluding framing
                 bits but including FCS octets.  It is the counterpart of
                 etherStatsPkts512to1023Octets in Ethernet RMON.  In contrast
                 to Ethernet, error packets are not counted."
	::= { tokenRingStatsEntry 32 }

tokenRingStatsDataPkts1024to2047Octets	OBJECT-TYPE
	SYNTAX	Counter
	ACCESS	read-only
	STATUS	mandatory
	DESCRIPTION
                "The total number of data packets received that were between
                 1024 and 2047 octets in length inclusive, excluding framing
                 bits but including FCS octets.  It is the superset of 
                 etherStatsPkts1024to1518Octets in Ethernet RMON.  In contrast
                 to Ethernet, error packets are not counted."
	::= { tokenRingStatsEntry 33 }

tokenRingStatsDataPkts2048to4608Octets	OBJECT-TYPE
	SYNTAX	Counter
	ACCESS	read-only
	STATUS	mandatory
	DESCRIPTION
                "The total number of data packets (excluding error packets)
                 received that were between 2048 and 4608 octets in length
                 inclusive, excluding framing bits but including FCS octets.
                 Note that error packets in this length range is not counted."
	::= { tokenRingStatsEntry 34 }

tokenRingStatsDataPkts4609to18000Octets	OBJECT-TYPE
	SYNTAX	Counter
	ACCESS	read-only
	STATUS	mandatory
	DESCRIPTION
                "The total number of data packets (excluding error packets)
                 received that were between 4609 and 18000 octets in length
                 inclusive, excluding framing bits but including FCS octets.
                 Note that error packets in this length range is not counted."
	::= { tokenRingStatsEntry 35 }

tokenRingStatsDataPktsMoreThan18000Octets	OBJECT-TYPE
	SYNTAX	Counter
	ACCESS	read-only
	STATUS	mandatory
	DESCRIPTION
                "The total number of data packets (excluding error packets)
                 received that were more than 18000 in length, excluding
                 framing bits but including FCS octets.  Note that error 
                 packets in this length range is not counted."
	::= { tokenRingStatsEntry 36 }

tokenRingStatsOwner	OBJECT-TYPE
	SYNTAX	OwnerString
	ACCESS	read-write
	STATUS	mandatory
	DESCRIPTION
                "An administratively assigned name for the management station
                 that configured this entry and is therefore using the
                 resources assigned to it.  This object contains a NVT 
                 octet string up to 127 characters.

                 In some cases the agent itself will configure an entry.
                 In this case, the agent is responsible for the resources and
                 this object shall be set to a string starting with 'monitor'."
	::= { tokenRingStatsEntry 37 }

tokenRingStatsStatus	OBJECT-TYPE
	SYNTAX	EntryStatus
	ACCESS	read-write
	STATUS	mandatory
	DESCRIPTION
                "The status of this tokenRingStats entry."
	::= { tokenRingStatsEntry 38 }



-- The History Group

-- The history group periodically takes statistical samples from a network
-- and stores them for later retrieval.  The counters in the history group
-- is a subset in the statistics group.  In the history group, the counters
-- contain the statistics accumulated during the last sample.

-- The objects and structure in the history group are the same between Ethernet
-- and token ring remote network monitoring MIBs, except that the prefix of
-- the objects' names are changed from "ether" to "tokenRing" and the counters
-- in EtherHistoryEntry are replaced by the counters in TokenRingHistoryEntry.
-- The token ring history shares the control table with the ethernet version;
-- it is in the rmon mib.

-- The MIB address of the objects are enumerated from 1 to infinity.  The
-- address of the first object, which is tokenRingHistoryIndex , is
-- { tokenRingHistoryEntry 1 }, and so on.


tokenRingHistoryTable	OBJECT-TYPE
	SYNTAX	SEQUENCE OF TokenRingHistoryEntry
	ACCESS	not-accessible
	STATUS	mandatory
	DESCRIPTION
        	"A list of token ring statistics entries."
	::= { tokenRingHistory 1 }

tokenRingHistoryEntry	OBJECT-TYPE
	SYNTAX	TokenRingHistoryEntry
	ACCESS	not-accessible
	STATUS	mandatory
	DESCRIPTION
		"A collection of history statistics
                 kept for a particular token ring
                 interface."
	INDEX	{ tokenRingHistoryIndex, tokenRingHistoryStartIndex }
	::= { tokenRingHistoryTable 1 }


TokenRingHistoryEntry ::= SEQUENCE {
	tokenRingHistoryIndex				INTEGER ( 1..65535 ),
	tokenRingHistoryStartIndex			INTEGER,
	tokenRingHistoryIntervalStart			TimeTicks,
	tokenRingHistoryDropEvents			Counter,
	tokenRingHistoryDataOctets			Counter,
	tokenRingHistoryDataPkts			Counter,
	tokenRingHistoryBroadcastDataPkts		Counter,
	tokenRingHistoryMulticastDataPkts		Counter,
	tokenRingHistoryMACOctets			Counter,
	tokenRingHistoryMACPkts			        Counter,
	tokenRingHistoryRingPurges			Counter,
	tokenRingHistoryMonitorContentions		Counter,
	tokenRingHistoryBeacons				Counter,
	tokenRingHistoryLostMonitors			Counter,
	tokenRingHistoryDuplicateMonitors		Counter,
	tokenRingHistoryDuplicateAddresses		Counter,
        tokenRingHistoryRingPollFailures		Counter,
	tokenRingHistoryLineErrors			Counter,
	tokenRingHistoryInternalErrors			Counter,
	tokenRingHistoryBurstErrors			Counter,
	tokenRingHistoryACErrors			Counter,
	tokenRingHistoryAbortDelimiters			Counter,
	tokenRingHistoryLostFrameErrors			Counter,
	tokenRingHistoryReceiveCongestions		Counter,
	tokenRingHistoryFrameCopiedErrors		Counter,
	tokenRingHistoryFrequencyErrors			Counter,
	tokenRingHistoryTokenErrors			Counter,
	tokenRingHistoryUtilization			INTEGER ( 0..10000 )
}


tokenRingHistoryIndex OBJECT-TYPE
    SYNTAX INTEGER (1..65535)
    ACCESS read-only
    STATUS mandatory
    DESCRIPTION
        "The history of which this entry is a part.  The
        history identified by a particular value of this
        index is the same history as identified
        by the same value of historyControlIndex."
    ::= { tokenRingHistoryEntry 1 }

tokenRingHistoryStartIndex OBJECT-TYPE
    SYNTAX INTEGER
    ACCESS read-only
    STATUS mandatory
    DESCRIPTION
        "An index that uniquely identifies the particular
        sample this entry represents among all samples
        associated with the same historyControlEntry.
        This index starts at 1 and increases by one
        as each new sample is taken."
    ::= { tokenRingHistoryEntry 2 }

tokenRingHistoryIntervalStart OBJECT-TYPE
    SYNTAX TimeTicks
    ACCESS read-only
    STATUS mandatory
    DESCRIPTION
        "The value of sysUpTime at the start of the interval
        over which this sample was measured.  If the probe
        keeps track of the time of day, it should start
        the first sample of the history at a time such that
        when the next hour of the day begins, a sample is
        started at that instant.  Note that following this
        rule may require the probe to delay collecting the
        first sample of the history, as each sample must be
        of the same interval.  Also note that the sample which
        is currently being collected is not accessible in this
        table until the end of its interval."
    ::= { tokenRingHistoryEntry 3 }


tokenRingHistoryDropEvents	OBJECT-TYPE
	SYNTAX	Counter
	ACCESS	read-only
	STATUS	mandatory
	DESCRIPTION
                ""
	::= { tokenRingHistoryEntry 4 }

tokenRingHistoryDataOctets	OBJECT-TYPE
	SYNTAX	Counter
	ACCESS	read-only
	STATUS	mandatory
	DESCRIPTION
                ""
	::= { tokenRingHistoryEntry 5 }

tokenRingHistoryDataPkts	OBJECT-TYPE
	SYNTAX	Counter
	ACCESS	read-only
	STATUS	mandatory
	DESCRIPTION
                ""
	::= { tokenRingHistoryEntry 6 }

tokenRingHistoryBroadcastDataPkts	OBJECT-TYPE
	SYNTAX	Counter
	ACCESS	read-only
	STATUS	mandatory
	DESCRIPTION
                ""
	::= { tokenRingHistoryEntry 7 }

tokenRingHistoryMulticastDataPkts	OBJECT-TYPE
	SYNTAX	Counter
	ACCESS	read-only
	STATUS	mandatory
	DESCRIPTION
                ""
	::= { tokenRingHistoryEntry 8 }

tokenRingHistoryMACOctets	OBJECT-TYPE
	SYNTAX	Counter
	ACCESS	read-only
	STATUS	mandatory
	DESCRIPTION
                ""
	::= { tokenRingHistoryEntry 9 }

tokenRingHistoryMACPkts	OBJECT-TYPE
	SYNTAX	Counter
	ACCESS	read-only
	STATUS	mandatory
	DESCRIPTION
                ""
	::= { tokenRingHistoryEntry 10 }

tokenRingHistoryRingPurges	OBJECT-TYPE
	SYNTAX	Counter
	ACCESS	read-only
	STATUS	mandatory
	DESCRIPTION
                ""
	::= { tokenRingHistoryEntry 11 }

tokenRingHistoryMonitorContentions	OBJECT-TYPE
	SYNTAX	Counter
	ACCESS	read-only
	STATUS	mandatory
	DESCRIPTION
                ""
	::= { tokenRingHistoryEntry 12 }

tokenRingHistoryBeacons	OBJECT-TYPE
	SYNTAX	Counter
	ACCESS	read-only
	STATUS	mandatory
	DESCRIPTION
                ""
	::= { tokenRingHistoryEntry 13 }

tokenRingHistoryLostMonitors	OBJECT-TYPE
	SYNTAX	Counter
	ACCESS	read-only
	STATUS	mandatory
	DESCRIPTION
                ""
	::= { tokenRingHistoryEntry 14 }

tokenRingHistoryDuplicateMonitors	OBJECT-TYPE
	SYNTAX	Counter
	ACCESS	read-only
	STATUS	mandatory
	DESCRIPTION
                ""
	::= { tokenRingHistoryEntry 15 }

tokenRingHistoryDuplicateAddresses	OBJECT-TYPE
	SYNTAX	Counter
	ACCESS	read-only
	STATUS	mandatory
	DESCRIPTION
                ""
	::= { tokenRingHistoryEntry 16 }

tokenRingHistoryRingPollFailures	OBJECT-TYPE
	SYNTAX	Counter
	ACCESS	read-only
	STATUS	mandatory
	DESCRIPTION
                ""
	::= { tokenRingHistoryEntry 17 }

tokenRingHistoryLineErrors	OBJECT-TYPE
	SYNTAX	Counter
	ACCESS	read-only
	STATUS	mandatory
	DESCRIPTION
                ""
	::= { tokenRingHistoryEntry 18 }

tokenRingHistoryInternalErrors	OBJECT-TYPE
	SYNTAX	Counter
	ACCESS	read-only
	STATUS	mandatory
	DESCRIPTION
                ""
	::= { tokenRingHistoryEntry 19 }

tokenRingHistoryBurstErrors	OBJECT-TYPE
	SYNTAX	Counter
	ACCESS	read-only
	STATUS	mandatory
	DESCRIPTION
                ""
	::= { tokenRingHistoryEntry 20 }

tokenRingHistoryACErrors	OBJECT-TYPE
	SYNTAX	Counter
	ACCESS	read-only
	STATUS	mandatory
	DESCRIPTION
                ""
	::= { tokenRingHistoryEntry 21 }

tokenRingHistoryAbortDelimiters	OBJECT-TYPE
	SYNTAX	Counter
	ACCESS	read-only
	STATUS	mandatory
	DESCRIPTION
                ""
	::= { tokenRingHistoryEntry 22 }

tokenRingHistoryLostFrameErrors	OBJECT-TYPE
	SYNTAX	Counter
	ACCESS	read-only
	STATUS	mandatory
	DESCRIPTION
                ""
	::= { tokenRingHistoryEntry 23 }

tokenRingHistoryReceiveCongestions	OBJECT-TYPE
	SYNTAX	Counter
	ACCESS	read-only
	STATUS	mandatory
	DESCRIPTION
                ""
	::= { tokenRingHistoryEntry 24 }

tokenRingHistoryFrameCopiedErrors	OBJECT-TYPE
	SYNTAX	Counter
	ACCESS	read-only
	STATUS	mandatory
	DESCRIPTION
                ""
	::= { tokenRingHistoryEntry 25 }

tokenRingHistoryFrequencyErrors	OBJECT-TYPE
	SYNTAX	Counter
	ACCESS	read-only
	STATUS	mandatory
	DESCRIPTION
                ""
	::= { tokenRingHistoryEntry 26 }

tokenRingHistoryTokenErrors	OBJECT-TYPE
	SYNTAX	Counter
	ACCESS	read-only
	STATUS	mandatory
	DESCRIPTION
                ""
	::= { tokenRingHistoryEntry 27 }

tokenRingHistoryUtilization	OBJECT-TYPE
        SYNTAX INTEGER (0..10000)
	ACCESS	read-only
	STATUS	mandatory
	DESCRIPTION
                ""
	::= { tokenRingHistoryEntry 28 }

-- The token ring Group

-- The token ring group contains four tables.  They are the control, network,
-- host and order table.

-- The control table in the token ring group.

tokenRingControlTable	OBJECT-TYPE
		SYNTAX	SEQUENCE OF TokenRingControlEntry
		ACCESS	not-accessible
		STATUS	mandatory
		DESCRIPTION
                        "A list of token ring configuration control entries."
		::= { tokenRing 1 }

tokenRingControlEntry	OBJECT-TYPE
		SYNTAX	TokenRingControlEntry
		ACCESS	not-accessible
		STATUS	mandatory
		DESCRIPTION
                        "A list of parameters that sets up a command buffer
                         and two event pointers for the manager who has
                         created this instance."
		INDEX	{ tokenRingControlIndex }
		::= { tokenRingControlTable 1 }

TokenRingControlEntry ::= SEQUENCE {
		tokenRingControlIndex			INTEGER ( 1..65535 ),
		tokenRingControlIfIndex			INTEGER,
		tokenRingControlCommandStatus		INTEGER,
		tokenRingControlCommandType		INTEGER,
		tokenRingControlCommandTargetAddress	MacAddress,
		tokenRingControlBeaconEventIndex	INTEGER ( 0..65535 ),
		tokenRingControlConfigEventIndex	INTEGER ( 0..65535 ),
		tokenRingControlOwner			OwnerString,
		tokenRingControlStatus			EntryStatus
}

tokenRingControlIndex	OBJECT-TYPE
		SYNTAX	INTEGER ( 1..65535 )
		ACCESS	read-only
		STATUS	mandatory
		DESCRIPTION
                        "An index that uniquely identifies an entry in the
                         tokenRingControl table.  Each entry contains a
                         command buffer for the management station to issue
                         a command and two event indexes for specifying the
                         actions to be done when the ring starts beaconing
                         and a host has entered or exited the ring."
		::= { tokenRingControlEntry 1 }

tokenRingControlIfIndex	OBJECT-TYPE
		SYNTAX	INTEGER
		ACCESS	read-write
		STATUS	mandatory
		DESCRIPTION
                        "This object contains the board interface number
                         which is identical to the ifIndex object in the
                         interface table of MIB-I or MIB-II."
		::= { tokenRingControlEntry 2 }

tokenRingControlCommandStatus	OBJECT-TYPE
		SYNTAX	INTEGER {
				none(1),	 -- no test yet requested.
				success(2),
				inProgress(3),
				notSupported(4),
				unAbleToRun(5),  -- due to state of system.
                                missingData(6),
				aborted(7),
				failed(8),
                                sendPending(9)
		}
		ACCESS	read-write
		STATUS	mandatory
		DESCRIPTION
                        "The object contains the result of the most recent
                         test, or the value none(1) if no tests have been
                         requested since last reset.

                         After the manager issues a new command, the agent
                         will turn the status to inProgress(3) and start
                         executing.  Meanwhile, the manager polls this object
                         until a completion status is returned.  Then it
                         proceeds to read the result."
		::= { tokenRingControlEntry 3 }

tokenRingControlCommandType	OBJECT-TYPE
		SYNTAX	INTEGER {
                                nop( 1 ),
				removeStation( 2 ),
				testStation( 3 ),
				requestStationAddress( 4 ),
				requestStationState( 5 ),
				requestStationAttachment( 6 )
		}
		ACCESS	read-write
		STATUS	mandatory
		DESCRIPTION
                        "The object specifies the operation to act upon the
                         target station requested by the manager.  The agent
                         only accepts unicast address from the management
                         station.  If non-unicast address is specified, the
                         notSupported(4) value will be written to the
                         tokenRingControlCommandStatus object.  Note that
                         the agent does not check the specified address with
                         the host table.  In other words, the management
                         station can specify a non-existing MAC address in
                         the command.

                         The removeStation(1) command requests the agent to
                         send the Remove Ring Station MAC frame to the target
                         station that deinserts the target station from the
                         ring.

                         The testStation(2) command requests the agent to send
                         the Transmit Forward MAC frame to the tagart station.
                         The agent then monitors the response frames from the
                         target station.  If the expected response frame is
                         not detected, the agent will write the failed(7)
                         value to the tokenRingControlCommandStatus object.
                         Otherwise, the success(2) value will be written to.

                         The requestStationAddress(3) command requests the
                         agent to send the Request Station Address MAC frame
                         to the target station.  This command is to update
                         the address assignments of the target station in the
                         host table.

                         The requestStationState(4) command requests the agent
                         to send the Request Station State MAC frame to the
                         target station.  This command is to update the state
                         information of the target station in the host table.

                         The requestStationAttachment(5) command requests the
                         agent to send the Request Station Attachment MAC
                         frame to the target station.  This command is to
                         update the configuration information about the host
                         attachment unit of the target station in the host 
                         table."
		::= { tokenRingControlEntry 4 }

tokenRingControlCommandTargetAddress	OBJECT-TYPE
		SYNTAX	MacAddress
		ACCESS	read-write
		STATUS	mandatory
		DESCRIPTION
                        "This object contains the MAC address of the target
                         station requested by the manager.  The value must be
                         an unicast address.  Multicast, functional or
                         broadcast address is not allowed.  Note that the
                         proxy agent does not check whether the address is in
                         the host table or not."
		::= { tokenRingControlEntry 5 }

tokenRingControlBeaconEventIndex	OBJECT-TYPE
		SYNTAX	INTEGER ( 0..65535 )
		ACCESS	read-write
		STATUS	mandatory
		DESCRIPTION
                        "The value of this object identifies the event that
                         is configured to be generated when the ring to which
                         this interface board is connected starts beaconing.
                         The beacon event is generated only when the ring
                         enters the beacon state.  The beacon event will not
                         be generated again unless the ring has exited the
                         beacon state.  The agent reports the failure domain
                         and the beacon level in the first detected beacon
                         frame to the management station.  The information may
                         not be the most accurate because the failure domain
                         takes time to converge and the beacon level can be
                         elevated.  The station can poll the tokenRingNetwork
                         table to read the current status of the ring."
		::= { tokenRingControlEntry 6 }

tokenRingControlConfigEventIndex	OBJECT-TYPE
		SYNTAX	INTEGER ( 0..65535 )
		ACCESS	read-write
		STATUS	mandatory
		DESCRIPTION
                        "The value of this object identifies the event that
                         is configured to be generated when a station has
                         entered or exited the ring that this interface board
                         is connected to.

                         This control table does not establish any flow
                         control mechanism with the management station.  If a
                         group of stations enter or exit the ring at the same
                         time and the link between the management station and
                         the agent is slow, some events may be lost."
		::= { tokenRingControlEntry 7 }

tokenRingControlOwner	OBJECT-TYPE
		SYNTAX	OwnerString
		ACCESS	read-write
		STATUS	mandatory
		DESCRIPTION
                        "An administratively assigned name for the management
                         station that configured this entry and is therefore
                         using the resources assigned to it.

                        In some cases the agent itself will configure an
                        entry.  In this case, the agent is responsible for
                        the resources and this object shall be set to a
                        string starting with 'monitor'."
		::= { tokenRingControlEntry 8 }

tokenRingControlStatus	OBJECT-TYPE
		SYNTAX	EntryStatus
		ACCESS	read-write
		STATUS	mandatory
		DESCRIPTION
                        "The status of this entry."
		::= { tokenRingControlEntry 9 }


-- The network table in the token ring group.

tokenRingNetworkTable	OBJECT-TYPE
		SYNTAX	SEQUENCE OF TokenRingNetworkEntry
		ACCESS	not-accessible
		STATUS	mandatory
		DESCRIPTION
                        "The ring level information about the token ring
                         networks in this machine."
		::= { tokenRing 2 }

tokenRingNetworkEntry	OBJECT-TYPE
		SYNTAX	TokenRingNetworkEntry
		ACCESS	not-accessible
		STATUS	mandatory
		DESCRIPTION
                        "The current state of this token ring network."
		INDEX	{ tokenRingNetworkIfIndex }
		::= { tokenRingNetworkTable 1 }

TokenRingNetworkEntry ::= SEQUENCE {
		tokenRingNetworkIfIndex			INTEGER,
		tokenRingNetworkLastResetTime		TimeTicks,
		tokenRingNetworkRingNumber		INTEGER ( 0..4095 ),
		tokenRingNetworkMediaSpeed		INTEGER, 
		tokenRingNetworkBridges			INTEGER,
		tokenRingNetworkActiveStations		INTEGER,
		tokenRingNetworkInactiveStations	INTEGER,
		tokenRingNetworkLastEnterMACAddress	MacAddress,
		tokenRingNetworkLastExitMACAddress	MacAddress,
		tokenRingNetworkState			INTEGER,
		tokenRingNetworkStateCause		INTEGER,
		tokenRingNetworkStateSenderMACAddress	MacAddress,
		tokenRingNetworkStateUpstreamNeighborMACAddress	MacAddress,
		tokenRingNetworkHostOrderChanges	Counter,
		tokenRingNetworkActiveMonitorChanges	Counter
}


tokenRingNetworkIfIndex		OBJECT-TYPE
		SYNTAX	INTEGER
		ACCESS	read-only
		STATUS	mandatory
		DESCRIPTION
                        "This object contains the board interface number
                         which is identical to the ifIndex object in the
                         interface table of MIB-I or MIB-II."
		::= { tokenRingNetworkEntry 1 }

tokenRingNetworkLastResetTime	OBJECT-TYPE
		SYNTAX	TimeTicks ( 1..65535 )
		ACCESS	read-only
		STATUS	mandatory
		DESCRIPTION
                        "This object contains the sysUpTime when the data
                         base of this group is created or last reset."
		::= { tokenRingNetworkEntry 2 }

tokenRingNetworkRingNumber	OBJECT-TYPE
		SYNTAX	INTEGER ( 0..4095 )
		ACCESS	read-only
		STATUS	mandatory
		DESCRIPTION
                        "The ring number of which this interface board
                         connects to.  If the ring number is not known, it
                         should be set to zero."
		DEFVAL	{ 0 }
		::= { tokenRingNetworkEntry 3 }

tokenRingNetworkMediaSpeed	OBJECT-TYPE
		SYNTAX	INTEGER {
				fourMbps( 4 ),
				sixteenMbps( 16 )
				}
		ACCESS	read-only
		STATUS	mandatory
		DESCRIPTION
                        "The media speed of the ring.  The value is either
                         4 or 16.  Other values are not allowed."
		::= { tokenRingNetworkEntry 4 }

tokenRingNetworkBridges	OBJECT-TYPE
		SYNTAX	INTEGER
		ACCESS	read-only
		STATUS	mandatory
		DESCRIPTION
                        "The number of bridges in the host table.  The bridge
                         is referred to the device which supports the bridge
                         functional address."
		::= { tokenRingNetworkEntry 5 }

tokenRingNetworkActiveStations	OBJECT-TYPE
		SYNTAX	INTEGER
		ACCESS	read-only
		STATUS	mandatory
		DESCRIPTION
                        "The number of active stations in the host table.
                         The active stations are participating in the ring
                         poll process."
		::= { tokenRingNetworkEntry 6 }

tokenRingNetworkInactiveStations	OBJECT-TYPE
		SYNTAX	INTEGER
		ACCESS	read-only
		STATUS	mandatory
		DESCRIPTION
                        "The number of inactive stations in the host table.
                         The inactive stations are not inserted in the ring
                         or are not participating in the ring poll process.
                         Note that the station became inactive before the
                         tokenRingNetworkLastResetTime cannot be detected by
                         the agent."
		::= { tokenRingNetworkEntry 7 }

tokenRingNetworkLastEnterMACAddress	OBJECT-TYPE
		SYNTAX	MacAddress
		ACCESS	read-only
		STATUS	mandatory
		DESCRIPTION
                        "The MAC address of the token ring station that
                         has entered this ring most recently."
		::= { tokenRingNetworkEntry 8 }

tokenRingNetworkLastExitMACAddress	OBJECT-TYPE
		SYNTAX	MacAddress
		ACCESS	read-only
		STATUS	mandatory
		DESCRIPTION
                        "The MAC address of the token ring station that
                         has left this ring most recently."
		::= { tokenRingNetworkEntry 9 }

tokenRingNetworkState		OBJECT-TYPE
		SYNTAX	INTEGER {
				normalOperation( 1 ),
				ringPurgeState( 2 ),
				claimTokenState( 3 ),
				beaconState( 4 )
		}
		ACCESS	read-only
		STATUS	mandatory
		DESCRIPTION
                        "The state of the ring of which this entry is a part."
		::= { tokenRingNetworkEntry 10 }

tokenRingNetworkStateCause	OBJECT-TYPE
		SYNTAX	INTEGER {
				notClear( 1 ),
				initialState( 2 ),
                                normalRing( 3 ),
				recovering( 4 ),
				hardError( 5 ),
				beaconSetRecoveryMode( 6 ),
				beaconRingSignalLoss( 7 ),
				beaconBitStreaming( 8 ),
				beaconFrameStreaming( 9 ),
				type1SoftError( 10 ),
				type2SoftError( 11 ),
				type3SoftError( 12 ),
				type4SoftError( 13 ),
				burst5Error( 14 ),
				lostFrameError( 15 ),
				corruptedToken( 16 ),
				lostToken( 17 ),
				circulatingFrame( 18 ),
				multipleMonitor( 19 ),
				lostMonitor( 20 ),
				frequencyError( 21 )
		}
		ACCESS	read-only
		STATUS	mandatory
		DESCRIPTION
                        "The cause of this state transition.  It is required
                         to give the best estimation of the cause.  When this
                         interface just enters the ring, this object is
                         initialized to initiatState(2).  If no hint is
                         available, then it sets the cause to notClear(1)."
		DEFVAL	{ initialState }
		::= { tokenRingNetworkEntry 11 }

tokenRingNetworkStateSenderMACAddress	OBJECT-TYPE
		SYNTAX	MacAddress
		ACCESS	read-only
		STATUS	mandatory
		DESCRIPTION
                        "The MAC address of the station which initiates
                         the state transition."
		::= { tokenRingNetworkEntry 12 }

tokenRingNetworkStateUpstreamNeighborMACAddress	OBJECT-TYPE
		SYNTAX	MacAddress
		ACCESS	read-only
		STATUS	mandatory
		DESCRIPTION
                        "The MAC address in the upstream neighbor address
                         subvector of the MAC protocol frame.  Some MAC
                         protocol frames, such as ring purge frame, do not
                         contain that subvector, then the MAC address
                         contained in this object is irrelevant."
		::= { tokenRingNetworkEntry 13 }

tokenRingNetworkHostOrderChanges	OBJECT-TYPE
		SYNTAX	Counter
		ACCESS	read-only
		STATUS	mandatory
		DESCRIPTION
                        "The count of the index in the host table that has
                         changed since this table is created.  The host table
                         contains active and inactive stations which are
                         arranged in sequential order.  This counter roughly
                         estimates the number of times that the hosts have
                         changed their port connections."
		DEFVAL	{ 0 }
		::= { tokenRingNetworkEntry 14 }

tokenRingNetworkActiveMonitorChanges	OBJECT-TYPE
		SYNTAX	Counter
		ACCESS	read-only
		STATUS	mandatory
		DESCRIPTION
                        "The number of times that the active monitor changes
                         station since this table is created."
		DEFVAL	{ 0 }
		::= { tokenRingNetworkEntry 15 }


-- The host table in token ring group.

tokenRingHostTable	OBJECT-TYPE
		SYNTAX	SEQUENCE OF TokenRingHostEntry
		ACCESS	not-accessible
		STATUS	mandatory
		DESCRIPTION
                        "A list of token ring host table entries."
		::= { tokenRing 3 }

tokenRingHostEntry	OBJECT-TYPE
		SYNTAX	TokenRingHostEntry
		ACCESS	not-accessible
		STATUS	mandatory
		DESCRIPTION
                        "The information of the host that has been discovered
                         on this interface."
		INDEX	{ tokenRingHostIfIndex, tokenRingHostMACAddress }
		::= { tokenRingHostTable 1 }

TokenRingHostEntry ::= SEQUENCE {
		tokenRingHostIfIndex			INTEGER,
		tokenRingHostIndex			INTEGER ( 1..65535 ),
		tokenRingHostStatus			INTEGER,
        	tokenRingHostLastEnterTime		TimeTicks,
	        tokenRingHostLastExitTime		TimeTicks,
		tokenRingHostMACAddress			MacAddress,
		tokenRingHostPhysicalDropNumber		OCTET STRING,
		tokenRingHostSoftErrorReportTimerValue	INTEGER ( 0..65535 ),
		tokenRingHostGroupAddresses		INTEGER,
		tokenRingHostFunctionalAddresses	INTEGER,
		tokenRingHostAuthorizedFunctionClass	INTEGER ( 0..65535 ),
		tokenRingHostAuthorizedAccessPriority	INTEGER ( 0..7 ),
		tokenRingHostAdapterSoftwareLevel	OCTET STRING,
		tokenRingHostAdapterStatusVector	OCTET STRING,
		tokenRingHostProductID			OCTET STRING,
        	tokenRingHostLostMonitors		Counter,
	        tokenRingHostDuplicateMonitors		Counter,
        	tokenRingHostDuplicateAddresses		Counter,
	        tokenRingHostRingPollFailures		Counter,
        	tokenRingHostInLineErrors		Counter,
	        tokenRingHostInternalErrors		Counter,
        	tokenRingHostInBurstErrors		Counter,
	        tokenRingHostACErrors			Counter,
        	tokenRingHostAbortDelimiters		Counter,
	        tokenRingHostLostFrameErrors		Counter,
        	tokenRingHostReceiveCongestions		Counter,
	        tokenRingHostFrameCopiedErrors		Counter,
        	tokenRingHostFrequencyErrors		Counter,
	        tokenRingHostTokenErrors		Counter,
        	tokenRingHostOutLineErrors 		Counter,
        	tokenRingHostOutBurstErrors		Counter,
	        tokenRingHostInBeacons  		Counter,
	        tokenRingHostOutBeacons  		Counter,
	        tokenRingHostInsertions  		Counter
}

tokenRingHostIfIndex	OBJECT-TYPE
		SYNTAX	INTEGER
		ACCESS	read-only
		STATUS	mandatory
		DESCRIPTION
                        "This object contains the board interface number
                         which is identical to the ifIndex object in the
                         interface table of MIB-I or MIB-II."
		::= { tokenRingHostEntry 1 }

tokenRingHostIndex	OBJECT-TYPE
		SYNTAX	INTEGER ( 1..65535 )
		ACCESS	read-only
		STATUS	mandatory
		DESCRIPTION
                        "An index that defines the relative order of the
                         hosts in this ring starting from the Active Monitor
                         station.  The active monitor station contains the
                         value of 1.  The rest of the stations are arranged
                         in sequential order relative to the active monitor
                         station.

                         When a station becomes inactive, its entry is not
                         meant to be deleted.  The value in the
                         tokenRingHostStatus is changed to inactive.
                         The delete algorithm is implementation specific.

                         If a station becomes active and its entry is already
                         in the host table, then the value of the
                         tokenRingHostStatus object is changed to active.
                         In addition, if the relative order of the host
                         entries has changed, it shall increment the
                         tokenRingNetworkHostOrderChange counter in the
                         tokenRingNetwork table by one.

                         On the other hand, if a station becomes active and
                         its entry is not in the host table, then a new entry
                         must be created.  The new entry is inserted right
                         after its upstream neighbor station.  The
                         tokenRingNetworkHostOrderChange counter in the
                         tokenRingNetwork table shall not be increment.

                         If the active monitor changes station and the
                         relative position of the host entries is unchanged,
                         then the tokenRingNetworkHostOrderChange object in
                         the tokenRingNetwork table shall not be increment."
		::= { tokenRingHostEntry 2 }

tokenRingHostStatus	OBJECT-TYPE
		SYNTAX	INTEGER {
				active( 1 ),
				inactive( 2 ),
				activeMonitor( 3 )
				}
		ACCESS	read-only
		STATUS	mandatory
		DESCRIPTION
                        "The host table contains active and inactive stations.
                         An active station is currently participating in the
                         ring poll process.  An inactive station is vice
                         versa.  The inactive station can be a previous
                         active station which has exited the ring, or a
                         station which is in the ring but does not
                         participate in the ring poll process."
		::= { tokenRingHostEntry 3 }

tokenRingHostLastEnterTime	OBJECT-TYPE
		SYNTAX	TimeTicks
		ACCESS	read-only
		STATUS	mandatory
		DESCRIPTION
                        "The sysUpTime that the station has entered the ring
                         most recently or when the host entry is created."
		::= { tokenRingHostEntry 4 }

tokenRingHostLastExitTime	OBJECT-TYPE
		SYNTAX	TimeTicks
		ACCESS	read-only
		STATUS	mandatory
		DESCRIPTION
                        "The sysUpTime that the station has exited the ring
                         most recently.  When this object is created, it
                         shall reset its value to 0.  It indicates that the
                         station has never exited since creation."
		DEFVAL	{ 0 }
		::= { tokenRingHostEntry 5 }

tokenRingHostMACAddress	OBJECT-TYPE
		SYNTAX	MacAddress
		ACCESS	read-only
		STATUS	mandatory
		DESCRIPTION
                        "The station's MAC address to which this entry is
                         belonged."
		::= { tokenRingHostEntry 6 }

tokenRingHostPhysicalDropNumber	OBJECT-TYPE
		SYNTAX	OCTET STRING
		ACCESS	read-only
		STATUS	mandatory
		DESCRIPTION
                        "The station's physical drop number of which this
                         entry is belonged.  If the value of this object is
                         not assigned, then it is defaulted to four zeros."
		::= { tokenRingHostEntry 7 }

tokenRingHostSoftErrorReportTimerValue	OBJECT-TYPE
		SYNTAX	INTEGER ( 0..65535 )
		ACCESS	read-only
		STATUS	mandatory
		DESCRIPTION
                        "The time interval of the host station that the
                         Report Soft Error MAC frame is generated.  The
                         default value is two seconds.  The value is in
                         units of millisecond."
		DEFVAL	{ 2000 }
		::= { tokenRingHostEntry 8 }

tokenRingHostGroupAddresses	OBJECT-TYPE
		SYNTAX	INTEGER
		ACCESS	read-only
		STATUS	mandatory
		DESCRIPTION
                        "The group address of this station."
		::= { tokenRingHostEntry 9 }

tokenRingHostFunctionalAddresses	OBJECT-TYPE
		SYNTAX	INTEGER
		ACCESS	read-only
		STATUS	mandatory
		DESCRIPTION
                        "The functional address of the station.  The
                         functional address is assigned in the bit map
                         fashion.  The first two bytes are always 'C0-00' in
                         hex. and the first bit of the third byte is always
                         zero.  The following 31 bits are defined as follows:

                         00-00-00-01 : Active Monitor.
                         00-00-00-02 : Ring Parameter Server.
                         00-00-00-04 : 
                         00-00-00-08 : Ring Error Monitor.
                         00-00-00-10 : Configuration Report Server.
                         00-00-00-20 :
                         00-00-00-40 :
                         00-00-00-80 : NetBIOS.
                         00-00-01-00 : Bridge.
                         00-00-02-00 :
                         00-00-04-00 :
                         00-00-08-00 :
                         00-00-10-00 :
                         00-00-20-00 : IBM LAN Network Manager.
                         00-00-40-00 :
                         00-00-80-00 :

                         The bit range between 00-01-00-00 and 40-00-00-00
                         are not administrated by IEEE.  They are defined by
                         users.  Below lists a couple of popular assignments:

                         00-80-00-00 : Novell NetWare.
                         40-00-00-00 : Apple TokenTalk Broadcast."
		::= { tokenRingHostEntry 10 }

tokenRingHostAuthorizedFunctionClass	OBJECT-TYPE
		SYNTAX	INTEGER ( 0..65535 )
		ACCESS	read-only
		STATUS	mandatory
		DESCRIPTION
                        "Source classes for which the host is enabled to
                         transmit.  Valid range is '0000 0000 0000 0000'b
                         to '1111 1111 1111 1111'b.  Each bit 0 to 15
                         corresponds to function class '0000'b to '1111'b.
                         Bit value '1'b means function class is enabled.
                         Defined function classes are the following:

                         '00'H : Ring Station.
                         '01'H : LLC Manager.
                         '04'H : Configuration Report Server.
                         '05'H : Ring Parameter Server.
                         '06'H : Ring Error Monitor."
		::= { tokenRingHostEntry 11 }

tokenRingHostAuthorizedAccessPriority	OBJECT-TYPE
		SYNTAX	INTEGER ( 0..7 )
		ACCESS	read-only
		STATUS	mandatory
		DESCRIPTION
                        "Maximum allowed token priority with which the
                         attached product is allowed to transmit."
		::= { tokenRingHostEntry 12 }

tokenRingHostAdapterSoftwareLevel	OBJECT-TYPE
		SYNTAX	OCTET STRING
		ACCESS	read-only
		STATUS	mandatory
		DESCRIPTION
                        "The adapter software level of this station.
                         The interpretation of the value in this object is
                         vendor specific."
		::= { tokenRingHostEntry 13 }

tokenRingHostAdapterStatusVector	OBJECT-TYPE
		SYNTAX	OCTET STRING
		ACCESS	read-only
		STATUS	mandatory
		DESCRIPTION
                        "The adapter status vector of this station.
                         The interpretation of the value in this object is
                         vendor specific."
		::= { tokenRingHostEntry 14 }

tokenRingHostProductID	OBJECT-TYPE
		SYNTAX	OCTET STRING
		ACCESS	read-only
		STATUS	mandatory
		DESCRIPTION
                        "The product identification of this station.
                         The content is defined by vendor."
		::= { tokenRingHostEntry 15 }

tokenRingHostLostMonitors	OBJECT-TYPE
	SYNTAX	Counter
	ACCESS	read-only
	STATUS	mandatory
	DESCRIPTION
                "The total number of monitor errors reported by the Report
                 Monitor Error MAC frame.  It occurs when the standby monitor
                 fails to detect a good token in 2.6 seconds, or no ring poll
                 process is executed in 15 seconds.  The standby monitor
                 assumes that the active monitor is not present or not
                 functioning.  Lost monitor is a type 3 error and will cause
                 the detect station to initiate the monitor contention
                 process."
	::= { tokenRingHostEntry 16 }

tokenRingHostDuplicateMonitors	OBJECT-TYPE
	SYNTAX	Counter
	ACCESS	read-only
	STATUS	mandatory
	DESCRIPTION
                "The total number of duplicate monitor errors reported by
                 the Report Monitor Error MAC frame.  When an active monitor
                 detects a ring purge frame or an active monitor present frame
                 from other station, it realizes another active monitor in
                 the ring.  This station reports duplicate monitor to the
                 Ring Error Monitor and becomes a standby monitor."
	::= { tokenRingHostEntry 17 }

tokenRingHostDuplicateAddresses		OBJECT-TYPE
	SYNTAX	Counter
	ACCESS	read-only
	STATUS	mandatory
	DESCRIPTION
                "The total number of duplicate address errors reported by
                 the Report Monitor Error MAC frame.  It is generated by the
                 station when it detects other stations using its MAC address."
	::= { tokenRingHostEntry 18 }

tokenRingHostRingPollFailures	OBJECT-TYPE
	SYNTAX	Counter
	ACCESS	read-only
	STATUS	mandatory
	DESCRIPTION
                "The total number of Report Ring Poll Failure MAC frames
                 received.  It is generated when the active monitor cannot
                 see a ring poll cycle completed within a time limit.  The
                 MAC address of the last station in the incomplete ring poll
                 cycle is saved in the tokenRingNetwork table for reference."
	::= { tokenRingHostEntry 19 }

tokenRingHostInLineErrors	OBJECT-TYPE
	SYNTAX	Counter
	ACCESS	read-only
	STATUS	mandatory
	DESCRIPTION
                "The total number of line errors reported to the Ring Error
                 Monitor.  Line error means packet contains incorrect CRC
                 or code violation.  Line error is isolated error.  It is a 
                 type 1 error and no ring recovery is performed."
	::= { tokenRingHostEntry 20 }

tokenRingHostInternalErrors	OBJECT-TYPE
	SYNTAX	Counter
	ACCESS	read-only
	STATUS	mandatory
	DESCRIPTION
                "The total number of adapter internal errors reported to the
                 Ring Error Monitor.  Internal error indicates that a station
                 recognizes a recoverable internal error.  Internal error is
                 isolated error.  It is a type 1 error and no ring recovery
                 is performed."
	::= { tokenRingHostEntry 21 }

tokenRingHostInBurstErrors	OBJECT-TYPE
	SYNTAX	Counter
	ACCESS	read-only
	STATUS	mandatory
	DESCRIPTION
                "The total number of burst errors reported to the Ring Error
                 Monitor.  Burst error indicates that a station detects the
                 absence of transitions for five half-bit times.  Burst error
                 is isolated error.  It is a type 2 error and will casue
                 the active monitor purging the ring."
	::= { tokenRingHostEntry 22 }

tokenRingHostACErrors	OBJECT-TYPE
	SYNTAX	Counter
	ACCESS	read-only
	STATUS	mandatory
	DESCRIPTION
                "The total number of AC errors reported to the Ring Error
                 Monitor.  AC error indicates that a station cannot interpret
                 the address recognition bit or the frame copied bit.  AC 
                 error is isolated error.  It is a type 1 error and no ring
                 recovery is performed."
	::= { tokenRingHostEntry 23 }

tokenRingHostAbortDelimiters	OBJECT-TYPE
	SYNTAX	Counter
	ACCESS	read-only
	STATUS	mandatory
	DESCRIPTION
                "The number of abort delimiters reported to the Ring Error
                 Monitor.  Abort delimiter indicates that a station aborts
                 a transmission.  Abort delimiter is isolated error.  It is a 
                 type 1 error and no ring recovery is performed."
	::= { tokenRingHostEntry 24 }

tokenRingHostLostFrameErrors	OBJECT-TYPE
	SYNTAX	Counter
	ACCESS	read-only
	STATUS	mandatory
	DESCRIPTION
                "The number of lost frame errors reported to the Ring Error
                 Monitor.  Lost frame error indicates that the end delimiter
                 of a frame is lost in the network.  Lost frame error is 
                 non-isolated error.  It is a type 2 error and the active
                 monitor will purge the ring."
	::= { tokenRingHostEntry 25 }

tokenRingHostReceiveCongestions	OBJECT-TYPE
	SYNTAX	Counter
	ACCESS	read-only
	STATUS	mandatory
	DESCRIPTION
                "The number of receive congestions reported to the Ring Error
                 Monitor.  Receive congestion error indicates that a station
                 recognizes a frame addressed to its specific address, but
                 has no available buffer space.  Receive congestion error is
                 non-isolated error.  It is a type 1 error and no ring
                 recovery is performed."
	::= { tokenRingHostEntry 26 }

tokenRingHostFrameCopiedErrors	OBJECT-TYPE
	SYNTAX	Counter
	ACCESS	read-only
	STATUS	mandatory
	DESCRIPTION
                "The number of frame copied errors reported to the Ring Error
                 Monitor.  Frame copied error indicates that a station
                 recognizes a frame addressed to its specific address and 
                 detects that the A bits in Frame Status byte are set to 1.
                 It implies either a line hit or duplicate address.  Frame
                 copied error is non-isolated error.  It is a type 1 error
                 and no ring recovery is performed."
	::= { tokenRingHostEntry 27 }

tokenRingHostFrequencyErrors	OBJECT-TYPE
	SYNTAX	Counter
	ACCESS	read-only
	STATUS	mandatory
	DESCRIPTION
                "The number of frequency errors reported to the Ring Error
                 Monitor.  Frequency error indicates that a station detects
                 that the frequency of the incoming signal differs by more 
                 than the standard specified margin.  Frequency error is
                 non-isolated error.  It is a type 3 error and will cause the
                 detect station initiating monitor contention process."
	::= { tokenRingHostEntry 28 }

tokenRingHostTokenErrors	OBJECT-TYPE
	SYNTAX	Counter
	ACCESS	read-only
	STATUS	mandatory
	DESCRIPTION
                "The total number of token errors reported to the Ring Error
                 Monitor.  Token error indicates that the Active Monitor
                 station recognizes an error condition that needs a token
                 transmitted.  Token error is non-isolated error.  It is a
                 type 2 error and the active monitor will purge the ring."
	::= { tokenRingHostEntry 29 }

tokenRingHostOutLineErrors	OBJECT-TYPE
	SYNTAX	Counter
	ACCESS	read-only
	STATUS	mandatory
	DESCRIPTION
                "The total number of line errors reported to the Ring Error
                 Monitor.  Line error means packet contains incorrect CRC
                 or code violation.  Line error is isolated error.  It is a 
                 type 1 error and no ring recovery is performed."
	::= { tokenRingHostEntry 30 }

tokenRingHostOutBurstErrors	OBJECT-TYPE
	SYNTAX	Counter
	ACCESS	read-only
	STATUS	mandatory
	DESCRIPTION
                "The total number of burst errors reported to the Ring Error
                 Monitor.  Burst error indicates that a station detects the
                 absence of transitions for five half-bit times.  Burst error
                 is isolated error.  It is a type 2 error and will casue
                 the active monitor purging the ring."
	::= { tokenRingHostEntry 31 }

tokenRingHostInBeacons	OBJECT-TYPE
	SYNTAX	Counter
	ACCESS	read-only
	STATUS	mandatory
	DESCRIPTION
                ""
	::= { tokenRingHostEntry 32 }

tokenRingHostOutBeacons	OBJECT-TYPE
	SYNTAX	Counter
	ACCESS	read-only
	STATUS	mandatory
	DESCRIPTION
                ""
	::= { tokenRingHostEntry 33 }

tokenRingHostInsertions	OBJECT-TYPE
	SYNTAX	Counter
	ACCESS	read-only
	STATUS	mandatory
	DESCRIPTION
                ""
	::= { tokenRingHostEntry 34 }


-- The order table in token ring group.

tokenRingOrderTable	OBJECT-TYPE
		SYNTAX	SEQUENCE OF TokenRingOrderEntry
		ACCESS	not-accessible
		STATUS	mandatory
		DESCRIPTION
                        "A list of token ring host table entries."
		::= { tokenRing 4 }

tokenRingOrderEntry	OBJECT-TYPE
		SYNTAX	TokenRingOrderEntry
		ACCESS	not-accessible
		STATUS	mandatory
		DESCRIPTION
                        "The information of the host that has been discovered
                         on this interface."
		INDEX	{ tokenRingOrderIfIndex, tokenRingOrderIndex }
		::= { tokenRingOrderTable 1 }

TokenRingOrderEntry ::= SEQUENCE {
		tokenRingOrderIfIndex			INTEGER,
		tokenRingOrderIndex			INTEGER ( 1..65535 ),
		tokenRingOrderStatus			INTEGER,
        	tokenRingOrderLastEnterTime		TimeTicks,
	        tokenRingOrderLastExitTime		TimeTicks,
		tokenRingOrderMACAddress		OCTET STRING,
		tokenRingOrderPhysicalDropNumber	OCTET STRING,
		tokenRingOrderSoftErrorReportTimerValue	INTEGER ( 0..65535 ),
		tokenRingOrderGroupAddresses		INTEGER,
		tokenRingOrderFunctionalAddresses	INTEGER,
		tokenRingOrderAuthorizedFunctionClass	INTEGER ( 0..65535 ),
		tokenRingOrderAuthorizedAccessPriority	INTEGER ( 0..7 ),
		tokenRingOrderAdapterSoftwareLevel	OCTET STRING,
		tokenRingOrderAdapterStatusVector	OCTET STRING,
		tokenRingOrderProductID			OCTET STRING,
        	tokenRingOrderLostMonitors		Counter,
	        tokenRingOrderDuplicateMonitors		Counter,
        	tokenRingOrderDuplicateAddresses	Counter,
	        tokenRingOrderRingPollFailures		Counter,
        	tokenRingOrderInLineErrors		Counter,
	        tokenRingOrderInternalErrors		Counter,
        	tokenRingOrderInBurstErrors		Counter,
	        tokenRingOrderACErrors			Counter,
        	tokenRingOrderAbortDelimiters		Counter,
	        tokenRingOrderLostFrameErrors		Counter,
        	tokenRingOrderReceiveCongestions	Counter,
	        tokenRingOrderFrameCopiedErrors		Counter,
        	tokenRingOrderFrequencyErrors		Counter,
	        tokenRingOrderTokenErrors		Counter,
        	tokenRingOrderOutLineErrors		Counter,
        	tokenRingOrderOutBurstErrors		Counter,
	        tokenRingOrderInBeacons  		Counter,
	        tokenRingOrderOutBeacons  		Counter,
	        tokenRingOrderInsertions  		Counter
}

tokenRingOrderIfIndex	OBJECT-TYPE
		SYNTAX	INTEGER
		ACCESS	read-only
		STATUS	mandatory
		DESCRIPTION
                        "This object contains the board interface number
                         which is identical to the ifIndex object in the
                         interface table of MIB-I or MIB-II."
		::= { tokenRingOrderEntry 1 }

tokenRingOrderIndex	OBJECT-TYPE
		SYNTAX	INTEGER ( 1..65535 )
		ACCESS	read-only
		STATUS	mandatory
		DESCRIPTION
                        "An index that defines the relative order of the
                         hosts in this ring starting from the Active Monitor
                         station.  The active monitor station contains the
                         value of 1.  The rest of the stations are arranged
                         in sequential order relative to the active monitor
                         station.

                         When a station becomes inactive, its entry is not
                         meant to be deleted.  The value in the
                         tokenRingOrderStatus is changed to inactive.
                         The delete algorithm is implementation specific.

                         If a station becomes active and its entry is already
                         in the host table, then the value of the
                         tokenRingOrderStatus object is changed to active.
                         In addition, if the relative order of the host
                         entries has changed, it shall increment the
                         tokenRingNetworkHostOrderChange counter in the
                         tokenRingNetwork table by one.

                         On the other hand, if a station becomes active and
                         its entry is not in the host table, then a new entry
                         must be created.  The new entry is inserted right
                         after its upstream neighbor station.  The
                         tokenRingNetworkHostOrderChange counter in the
                         tokenRingNetwork table shall not be increment.

                         If the active monitor changes station and the
                         relative position of the host entries is unchanged,
                         then the tokenRingNetworkHostOrderChange object in
                         the tokenRingNetwork table shall not be increment."
		::= { tokenRingOrderEntry 2 }

tokenRingOrderStatus	OBJECT-TYPE
		SYNTAX	INTEGER {
				active( 1 ),
				inactive( 2 ),
				activeMonitor( 3 )
				}
		ACCESS	read-only
		STATUS	mandatory
		DESCRIPTION
                        "The host table contains active and inactive stations.
                         An active station is currently participating in the
                         ring poll process.  An inactive station is vice
                         versa.  The inactive station can be a previous
                         active station which has exited the ring, or a
                         station which is in the ring but does not
                         participate in the ring poll process."
		::= { tokenRingOrderEntry 3 }

tokenRingOrderLastEnterTime	OBJECT-TYPE
		SYNTAX	TimeTicks
		ACCESS	read-only
		STATUS	mandatory
		DESCRIPTION
                        "The sysUpTime that the station has entered the ring
                         most recently or when the host entry is created."
		::= { tokenRingOrderEntry 4 }

tokenRingOrderLastExitTime	OBJECT-TYPE
		SYNTAX	TimeTicks
		ACCESS	read-only
		STATUS	mandatory
		DESCRIPTION
                        "The sysUpTime that the station has exited the ring
                         most recently.  When this object is created, it
                         shall reset its value to 0.  It indicates that the
                         station has never exited since creation."
		DEFVAL	{ 0 }
		::= { tokenRingOrderEntry 5 }

tokenRingOrderMACAddress	OBJECT-TYPE
		SYNTAX	MacAddress
		ACCESS	read-only
		STATUS	mandatory
		DESCRIPTION
                        "The station's MAC address to which this entry is
                         belonged."
		::= { tokenRingOrderEntry 6 }

tokenRingOrderPhysicalDropNumber	OBJECT-TYPE
		SYNTAX	OCTET STRING
		ACCESS	read-only
		STATUS	mandatory
		DESCRIPTION
                        "The station's physical drop number of which this
                         entry is belonged.  If the value of this object is
                         not assigned, then it is defaulted to four zeros."
		::= { tokenRingOrderEntry 7 }

tokenRingOrderSoftErrorReportTimerValue	OBJECT-TYPE
		SYNTAX	INTEGER ( 0..65535 )
		ACCESS	read-only
		STATUS	mandatory
		DESCRIPTION
                        "The time interval of the host station that the
                         Report Soft Error MAC frame is generated.  The
                         default value is two seconds.  The value is in
                         units of millisecond."
		DEFVAL	{ 2000 }
		::= { tokenRingOrderEntry 8 }

tokenRingOrderGroupAddresses	OBJECT-TYPE
		SYNTAX	INTEGER
		ACCESS	read-only
		STATUS	mandatory
		DESCRIPTION
                        "The group address of this station."
		::= { tokenRingOrderEntry 9 }

tokenRingOrderFunctionalAddresses	OBJECT-TYPE
		SYNTAX	INTEGER
		ACCESS	read-only
		STATUS	mandatory
		DESCRIPTION
                        "The functional address of the station.  The
                         functional address is assigned in the bit map
                         fashion.  The first two bytes are always 'C0-00' in
                         hex. and the first bit of the third byte is always
                         zero.  The following 31 bits are defined as follows:

                         00-00-00-01 : Active Monitor.
                         00-00-00-02 : Ring Parameter Server.
                         00-00-00-04 : 
                         00-00-00-08 : Ring Error Monitor.
                         00-00-00-10 : Configuration Report Server.
                         00-00-00-20 :
                         00-00-00-40 :
                         00-00-00-80 : NetBIOS.
                         00-00-01-00 : Bridge.
                         00-00-02-00 :
                         00-00-04-00 :
                         00-00-08-00 :
                         00-00-10-00 :
                         00-00-20-00 : IBM LAN Network Manager.
                         00-00-40-00 :
                         00-00-80-00 :

                         The bit range between 00-01-00-00 and 40-00-00-00
                         are not administrated by IEEE.  They are defined by
                         users.  Below lists a couple of popular assignments:

                         00-80-00-00 : Novell NetWare.
                         40-00-00-00 : Apple TokenTalk Broadcast."
		::= { tokenRingOrderEntry 10 }

tokenRingOrderAuthorizedFunctionClass	OBJECT-TYPE
		SYNTAX	INTEGER ( 0..65535 )
		ACCESS	read-only
		STATUS	mandatory
		DESCRIPTION
                        "Source classes for which the host is enabled to
                         transmit.  Valid range is '0000 0000 0000 0000'b
                         to '1111 1111 1111 1111'b.  Each bit 0 to 15
                         corresponds to function class '0000'b to '1111'b.
                         Bit value '1'b means function class is enabled.
                         Defined function classes are the following:

                         '00'H : Ring Station.
                         '01'H : LLC Manager.
                         '04'H : Configuration Report Server.
                         '05'H : Ring Parameter Server.
                         '06'H : Ring Error Monitor."
		::= { tokenRingOrderEntry 11 }

tokenRingOrderAuthorizedAccessPriority	OBJECT-TYPE
		SYNTAX	INTEGER ( 0..7 )
		ACCESS	read-only
		STATUS	mandatory
		DESCRIPTION
                        "Maximum allowed token priority with which the
                         attached product is allowed to transmit."
		::= { tokenRingOrderEntry 12 }

tokenRingOrderAdapterSoftwareLevel	OBJECT-TYPE
		SYNTAX	OCTET STRING
		ACCESS	read-only
		STATUS	mandatory
		DESCRIPTION
                        "The adapter software level of this station.
                         The interpretation of the value in this object is
                         vendor specific."
		::= { tokenRingOrderEntry 13 }

tokenRingOrderAdapterStatusVector	OBJECT-TYPE
		SYNTAX	OCTET STRING
		ACCESS	read-only
		STATUS	mandatory
		DESCRIPTION
                        "The adapter status vector of this station.
                         The interpretation of the value in this object is
                         vendor specific."
		::= { tokenRingOrderEntry 14 }

tokenRingOrderProductID	OBJECT-TYPE
		SYNTAX	OCTET STRING
		ACCESS	read-only
		STATUS	mandatory
		DESCRIPTION
                        "The product identification of this station.
                         The content is defined by vendor."
		::= { tokenRingOrderEntry 15 }

tokenRingOrderLostMonitors	OBJECT-TYPE
	SYNTAX	Counter
	ACCESS	read-only
	STATUS	mandatory
	DESCRIPTION
                "The total number of monitor errors reported by the Report
                 Monitor Error MAC frame.  It occurs when the standby monitor
                 fails to detect a good token in 2.6 seconds, or no ring poll
                 process is executed in 15 seconds.  The standby monitor
                 assumes that the active monitor is not present or not
                 functioning.  Lost monitor is a type 3 error and will cause
                 the detect station to initiate the monitor contention
                 process."
	::= { tokenRingOrderEntry 16 }

tokenRingOrderDuplicateMonitors	OBJECT-TYPE
	SYNTAX	Counter
	ACCESS	read-only
	STATUS	mandatory
	DESCRIPTION
                "The total number of duplicate monitor errors reported by
                 the Report Monitor Error MAC frame.  When an active monitor
                 detects a ring purge frame or an active monitor present frame
                 from other station, it realizes another active monitor in
                 the ring.  This station reports duplicate monitor to the
                 Ring Error Monitor and becomes a standby monitor."
	::= { tokenRingOrderEntry 17 }

tokenRingOrderDuplicateAddresses		OBJECT-TYPE
	SYNTAX	Counter
	ACCESS	read-only
	STATUS	mandatory
	DESCRIPTION
                "The total number of duplicate address errors reported by
                 the Report Monitor Error MAC frame.  It is generated by the
                 station when it detects other stations using its MAC address."
	::= { tokenRingOrderEntry 18 }

tokenRingOrderRingPollFailures	OBJECT-TYPE
	SYNTAX	Counter
	ACCESS	read-only
	STATUS	mandatory
	DESCRIPTION
                "The total number of Report Ring Poll Failure MAC frames
                 received.  It is generated when the active monitor cannot
                 see a ring poll cycle completed within a time limit.  The
                 MAC address of the last station in the incomplete ring poll
                 cycle is saved in the tokenRingNetwork table for reference."
	::= { tokenRingOrderEntry 19 }

tokenRingOrderInLineErrors	OBJECT-TYPE
	SYNTAX	Counter
	ACCESS	read-only
	STATUS	mandatory
	DESCRIPTION
                "The total number of line errors reported to the Ring Error
                 Monitor.  Line error means packet contains incorrect CRC
                 or code violation.  Line error is isolated error.  It is a 
                 type 1 error and no ring recovery is performed."
	::= { tokenRingOrderEntry 20 }

tokenRingOrderInternalErrors	OBJECT-TYPE
	SYNTAX	Counter
	ACCESS	read-only
	STATUS	mandatory
	DESCRIPTION
                "The total number of adapter internal errors reported to the
                 Ring Error Monitor.  Internal error indicates that a station
                 recognizes a recoverable internal error.  Internal error is
                 isolated error.  It is a type 1 error and no ring recovery
                 is performed."
	::= { tokenRingOrderEntry 21 }

tokenRingOrderInBurstErrors	OBJECT-TYPE
	SYNTAX	Counter
	ACCESS	read-only
	STATUS	mandatory
	DESCRIPTION
                "The total number of burst errors reported to the Ring Error
                 Monitor.  Burst error indicates that a station detects the
                 absence of transitions for five half-bit times.  Burst error
                 is isolated error.  It is a type 2 error and will casue
                 the active monitor purging the ring."
	::= { tokenRingOrderEntry 22 }

tokenRingOrderACErrors	OBJECT-TYPE
	SYNTAX	Counter
	ACCESS	read-only
	STATUS	mandatory
	DESCRIPTION
                "The total number of AC errors reported to the Ring Error
                 Monitor.  AC error indicates that a station cannot interpret
                 the address recognition bit or the frame copied bit.  AC 
                 error is isolated error.  It is a type 1 error and no ring
                 recovery is performed."
	::= { tokenRingOrderEntry 23 }

tokenRingOrderAbortDelimiters	OBJECT-TYPE
	SYNTAX	Counter
	ACCESS	read-only
	STATUS	mandatory
	DESCRIPTION
                "The number of abort delimiters reported to the Ring Error
                 Monitor.  Abort delimiter indicates that a station aborts
                 a transmission.  Abort delimiter is isolated error.  It is a 
                 type 1 error and no ring recovery is performed."
	::= { tokenRingOrderEntry 24 }

tokenRingOrderLostFrameErrors	OBJECT-TYPE
	SYNTAX	Counter
	ACCESS	read-only
	STATUS	mandatory
	DESCRIPTION
                "The number of lost frame errors reported to the Ring Error
                 Monitor.  Lost frame error indicates that the end delimiter
                 of a frame is lost in the network.  Lost frame error is 
                 non-isolated error.  It is a type 2 error and the active
                 monitor will purge the ring."
	::= { tokenRingOrderEntry 25 }

tokenRingOrderReceiveCongestions	OBJECT-TYPE
	SYNTAX	Counter
	ACCESS	read-only
	STATUS	mandatory
	DESCRIPTION
                "The number of receive congestions reported to the Ring Error
                 Monitor.  Receive congestion error indicates that a station
                 recognizes a frame addressed to its specific address, but
                 has no available buffer space.  Receive congestion error is
                 non-isolated error.  It is a type 1 error and no ring
                 recovery is performed."
	::= { tokenRingOrderEntry 26 }

tokenRingOrderFrameCopiedErrors	OBJECT-TYPE
	SYNTAX	Counter
	ACCESS	read-only
	STATUS	mandatory
	DESCRIPTION
                "The number of frame copied errors reported to the Ring Error
                 Monitor.  Frame copied error indicates that a station
                 recognizes a frame addressed to its specific address and 
                 detects that the A bits in Frame Status byte are set to 1.
                 It implies either a line hit or duplicate address.  Frame
                 copied error is non-isolated error.  It is a type 1 error
                 and no ring recovery is performed."
	::= { tokenRingOrderEntry 27 }

tokenRingOrderFrequencyErrors	OBJECT-TYPE
	SYNTAX	Counter
	ACCESS	read-only
	STATUS	mandatory
	DESCRIPTION
                "The number of frequency errors reported to the Ring Error
                 Monitor.  Frequency error indicates that a station detects
                 that the frequency of the incoming signal differs by more 
                 than the standard specified margin.  Frequency error is
                 non-isolated error.  It is a type 3 error and will cause the
                 detect station initiating monitor contention process."
	::= { tokenRingOrderEntry 28 }

tokenRingOrderTokenErrors	OBJECT-TYPE
	SYNTAX	Counter
	ACCESS	read-only
	STATUS	mandatory
	DESCRIPTION
                "The total number of token errors reported to the Ring Error
                 Monitor.  Token error indicates that the Active Monitor
                 station recognizes an error condition that needs a token
                 transmitted.  Token error is non-isolated error.  It is a
                 type 2 error and the active monitor will purge the ring."
	::= { tokenRingOrderEntry 29 }

tokenRingOrderOutLineErrors	OBJECT-TYPE
	SYNTAX	Counter
	ACCESS	read-only
	STATUS	mandatory
	DESCRIPTION
                "The total number of line errors reported to the Ring Error
                 Monitor.  Line error means packet contains incorrect CRC
                 or code violation.  Line error is isolated error.  It is a 
                 type 1 error and no ring recovery is performed."
	::= { tokenRingOrderEntry 30 }

tokenRingOrderOutBurstErrors	OBJECT-TYPE
	SYNTAX	Counter
	ACCESS	read-only
	STATUS	mandatory
	DESCRIPTION
                "The total number of burst errors reported to the Ring Error
                 Monitor.  Burst error indicates that a station detects the
                 absence of transitions for five half-bit times.  Burst error
                 is isolated error.  It is a type 2 error and will casue
                 the active monitor purging the ring."
	::= { tokenRingOrderEntry 31 }

tokenRingOrderInBeacons	OBJECT-TYPE
	SYNTAX	Counter
	ACCESS	read-only
	STATUS	mandatory
	DESCRIPTION
                ""
	::= { tokenRingOrderEntry 32 }

tokenRingOrderOutBeacons	OBJECT-TYPE
	SYNTAX	Counter
	ACCESS	read-only
	STATUS	mandatory
	DESCRIPTION
                ""
	::= { tokenRingOrderEntry 33 }

tokenRingOrderInsertions	OBJECT-TYPE
	SYNTAX	Counter
	ACCESS	read-only
	STATUS	mandatory
	DESCRIPTION
                ""
	::= { tokenRingOrderEntry 34 }


-- Additional SNMP traps in token ring remote network monitoring MIB.

tokenRingBeaconing	TRAP-TYPE
	ENTERPRISE	 ringrmon-mib 
	VARIABLES	{ tokenRingNetworkRingNumber, tokenRingNetworkState, 
        		  tokenRingNetworkStateCause,
                          tokenRingNetworkStateSenderMACAddress,
			  tokenRingNetworkStateUpstreamNeighborMACAddress }
	DESCRIPTION
                "The SNMP trap that is generated when the token ring network
                 starts beaconing."
              --Alarm integrator annotation
              --#TYPE "Ring Beaconing"
              --#SUMMARY "Ring Network Number %d, Sender = %m, Upstream Neighbour = %m"
              --#ARGUMENTS {0, 3, 4}
              --#SEVERITY CRITICAL
              --#TIMEINDEX 8
              --#HELP "LSM.HLP"
              --#HELPTAG 0
              --#STATE NONOPERATIONAL
 	::= 4

tokenRingConfigurationChange	TRAP-TYPE
	ENTERPRISE	 ringrmon-mib 
	VARIABLES	{ tokenRingNetworkRingNumber, tokenRingHostMACAddress,
                          tokenRingHostPhysicalDropNumber,
			  tokenRingHostStatus }
	DESCRIPTION
                "The SNMP trap that is generated when the a host has entered
                 or exited the token ring network."
              --Alarm integrator annotation
              --#TYPE "Ring Configuration Change"
              --#SUMMARY "Ring Network Number %d, Affected host = %m, Status (inserted(1),deinserted(2)) = %d"
              --#ARGUMENTS {0, 1, 3 }
              --#SEVERITY INFORMATIONAL
              --#TIMEINDEX 8
              --#HELP "LSM.HLP"
              --#HELPTAG 0
              --#STATE OPERATIONAL
 	::= 5


END
