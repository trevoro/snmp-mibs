Nortel-Magellan-Passport-AlarmMIB 
DEFINITIONS ::= BEGIN

IMPORTS

      OBJECT-TYPE 
   FROM RFC-1212

      TRAP-TYPE
   FROM RFC-1215

      DisplayString, DateAndTime, RowPointer, Unsigned32
   FROM Nortel-Magellan-Passport-StandardTextualConventionsMIB

      Hex, AsciiString, HexString, DigitString
   FROM Nortel-Magellan-Passport-TextualConventionsMIB

      passportMIBs, passportTraps
   FROM Nortel-Magellan-Passport-UsefulDefinitionsMIB;
		

-- LAST-UPDATED    "9603010000Z"
-- ORGANIZATION    "Nortel"
-- CONTACT-INFO    "
--         Nortel Magellan Network Management
--
--         Postal: P.O. Box 5080, Station F
--                 Ottawa, Ontario
--                 Canada  K2C 3T1
--
--         Email:  nm_plm@nt.com"
-- DESCRIPTION
--    "This MIB module specifies the variables and notifications
--    used to implement the Passport Alarms reporting facility. 
--    The Passport Alarms NTP 241-7501-130 describes the Alarm
--    generation philosophy."

alarmMIB     OBJECT IDENTIFIER ::= { passportMIBs 4 }

alarmTrap    OBJECT IDENTIFIER ::= { passportTraps 2 }

-- the mandatoryAlarmInfo group

-- STATUS     	current
-- DESCRIPTION
--    " This group contains the mandatory variables representing information 
--      pertinent to all alarms: componentRowPointer, componentName, 
--      eventTime, activeListStatus, severity, alarmType, probableCause,  
--      ntpIndex, and commentData"
mandatoryAlarmInfo   OBJECT IDENTIFIER ::= { alarmTrap 7 }

componentRowPointer OBJECT-TYPE
   SYNTAX	RowPointer
   ACCESS	not-accessible  
   STATUS	mandatory
   DESCRIPTION
   	" A pointer to the RowStatus variable of the component emitting 
          the alarm."
   ::= { mandatoryAlarmInfo 1 }

componentName OBJECT-TYPE
   SYNTAX	DisplayString
   ACCESS	not-accessible 
   STATUS	mandatory
   DESCRIPTION
      " The textual name of the component emitting the alarm in a format
        suitable for use in commands entered on the `console'.  It 
        includes the name of the node from which the alarm was 
        sent, as specified in `ModuleData nodeName'."
   ::= { mandatoryAlarmInfo 2 }

eventTime OBJECT-TYPE
   SYNTAX	DateAndTime
   ACCESS	not-accessible
   STATUS	mandatory
   DESCRIPTION
      " The date and time at which the alarmed event occurred."
   ::= { mandatoryAlarmInfo 3 }

activeListStatus OBJECT-TYPE
   SYNTAX	INTEGER { message(0), set(1), clear(2) }
   ACCESS	not-accessible
   STATUS	mandatory
   DESCRIPTION
      " The active alarm list status. This may be used by the
        Manager to add (on receiving a set) and delete (on 
        receiving a clear) alarms from the alarm displays."
   ::= { mandatoryAlarmInfo 4 }

severity OBJECT-TYPE
   SYNTAX	INTEGER { indeterminate(0), critical(1), major(2), minor(3), 
                          warning(4), cleared(5) }
   ACCESS	not-accessible
   STATUS	mandatory
   DESCRIPTION
      " The severity of the alarm which should indicate what
        priority that fixing this problem should be given.  All
        values are OSI-defined; refer to CCITT X.733/ISO 10164-4
        for a more complete description."
   ::= { mandatoryAlarmInfo 5 }

alarmType OBJECT-TYPE
   SYNTAX	INTEGER { communications(0), qualityOfService(1),
		          processing(2), equipment(3), environmental(4),
			  security(5), operator(6), debug(7), unknown(8) }
   ACCESS	not-accessible
   STATUS	mandatory
   DESCRIPTION
      " The alarm type field as defined by OSI which is
        used to indicate a broad category of what is wrong. The 
        first 6 values are OSI-defined; refer to CCITT X.733/ISO 10164-4
        (for the first 5)  and CCITT X.736/ISO 10164-4 (for the last) 
        for a more complete description.

   	The value 'operator' is used when an alarm is issued due to an 
        operator command. The values 'debug' and 'unknown' are for 
        compatibility with older switches and are used for debugging alarms and 
        for those which do not fit any of the above, respectively."
   ::= { mandatoryAlarmInfo 6}

probableCause OBJECT-TYPE
   SYNTAX	INTEGER {
		-- Start of OSI-defined values
                -- (see X.733/ ISO 10165-3)

		lossOfSignal(0),
		lossOfFrame(1),
		framingError(2),
		localTransmissionError(3),
		remoteTransmissionError(4),
		callEstablishmentError(5),
		degradedSignal(6),
		commSubsystemFailure(7),
		commProtocolError(8),
		lanError(9),
		dteDceInterfaceError(10),
		
		responseTimeExcessive(20),
		queueSizeExceeded(21),
		bandwidthReduced(22),
		retransmissionRateReduced(23),
		thresholdCrossed(24),
		performanceDegraded(25),
		congestion(26),
		atOrNearCapacity(27),
		
		storageCapacityProblem(40),
		versionMismatch(41),
		corruptData(42),
		cpuCyclesLimitExceeded(43),
		softwareError(44),
		softwareProgramError(45),
		softwareProgramTermination(46),
		fileError(47),
		outOfMemory(48),
		underlyingResourceUnavail(49),
		applicationSubsystemFailure(50),
		configurationError(51),
		
		powerProblem(60),
		timingProblem(61),
		processorProblem(62),
		datasetModemError(63),
		multiplexorProblem(64),
		receiverFailure(65),
		transmitterFailure(66),
		outputDeviceError(67),
		inputDeviceError(68),
		ioDeviceError(69),
		equipmentFailure(70),
		adapterError(71),
		
		-- OSI-defined values continued (see X.736)
		duplicateInfo(80),
		infoMissing(81),
		infoModification(82),
		infoOutOfSequence(83),
		unexpectedInfo(84),
		
		denialOfService(90),
		outOfService(91),
		proceduralError(92),
		otherOperational(93),
		
		cableTamper(100),
		intrusionDetection(101),
		otherPhysical(102),
		
		authenticationFailure(110),
		breachOfConfidence(111),
		nonRepudiationFailure(112),
		unauthorizedAccess(113),
		otherSecurityService(114),
		
		delayedInfo(120),
		keyExpired(121),
		outOfHoursActivity(122),
		
		-- Start of non-OSI defined values
		operationalCondition(200),
		debugging(201),
		unknown(202),
		inactiveVirtualCircuit(203),
		networkServerIntervention(204)
	}
   ACCESS	not-accessible
   STATUS	mandatory
   DESCRIPTION
      " The probable cause for the alarm which usually qualifies
        the Alarm Type field. Most values are OSI-defined; refer
        refer to CCITT X.733 and X.736 (ISO 10164-4 and 10164-7) for a more 
        complete description."
   ::= { mandatoryAlarmInfo 7}

ntpIndex OBJECT-TYPE
   SYNTAX	DigitString (SIZE(8))
   ACCESS	not-accessible
   STATUS	mandatory
   DESCRIPTION
      " An 8-digit code which is an index into an NTP to 
        provide more description of the alarm and possible actions to 
        take. The first 4 digits indicate a 'group' of alarms 
        (belonging to a particular subsystem or component, etc.). The last 
   	4 digits are a subindex arbitrarily assigned by the application 
        which is responsible for them."
   ::= { mandatoryAlarmInfo 8 }

commentData	OBJECT-TYPE
   SYNTAX	AsciiString (SIZE(0..750))
   ACCESS	not-accessible
   STATUS	mandatory
   DESCRIPTION
      " Additional textual information for the network operator to use. 
        It contains only ASCII characters. 
        Note: The total number of bytes in commentData, operatorData, 
        and internalData may not exceed 750 bytes."
   ::= { mandatoryAlarmInfo 9}

-- the optionalAlarmInfo group

-- STATUS	current
-- DESCRIPTION
--    " This group contains optional variables representing information 
--      pertinent to all alarms: notificationID, lpForHierClear,
-- 	operatorData, pid, fileName, fileLineNumber, fileVersion, and 
--      internalData."
optionalAlarmInfo   OBJECT IDENTIFIER ::= { alarmTrap 8}

notificationID	OBJECT-TYPE
   SYNTAX	Hex
   ACCESS	not-accessible
   STATUS	mandatory
   DESCRIPTION
      " The notification Id of the alarm. The high-order byte is
        the card number of the card from which this alarm originated. 
        The low-order 24 bits contain a sequence number which increases each 
        time an alarm is generated. Thus, this id provides a simple way of 
        uniquely identifying an alarm as well as the order in which alarms 
        are generated on a card. For cross-card ordering, one 
	would have to look at the time stamp (see dateAndTime)."
   ::= { optionalAlarmInfo 1 }

lpForHierClear	OBJECT-TYPE
   SYNTAX	RowPointer
   ACCESS	not-accessible
   STATUS	mandatory
   DESCRIPTION
      " A pointer to the RowStatus variable of the Logical Processor 
        the component generating the alarm is running on. A component
        generating an Alarm with `activeListStatus = set' can include
        this variable in the Alarm.  If the identified Logical Processor 
        generates a Hierarchical Clear Alarm, then it will clear the 
        Set Alarm."
   ::= { optionalAlarmInfo 2 }

operatorData	OBJECT-TYPE
   SYNTAX	HexString (SIZE(0..750))
   ACCESS	not-accessible
   STATUS	mandatory
   DESCRIPTION
      " Additional hexadecimal information for the network operator to 
        use. Note: The total number of bytes in commentData, operatorData, 
        and internalData may not exceed 750 bytes."
   ::= { optionalAlarmInfo 3 }

pid		OBJECT-TYPE
   SYNTAX	DisplayString (SIZE (0..25))
   ACCESS	not-accessible
   STATUS	mandatory
   DESCRIPTION
      " A string representation of the internal process id (Pid) 
        of the process which generated the alarm (for 
        internal use only). Note that it may or may not map to the 
        componentName field. "
   ::= { optionalAlarmInfo 4 }

fileName	OBJECT-TYPE
   SYNTAX 	DisplayString
   ACCESS	not-accessible
   STATUS	mandatory
   DESCRIPTION
      " An internal filename (for internal use only)."
   ::= { optionalAlarmInfo 5 }

fileLineNumber	OBJECT-TYPE
   SYNTAX	Unsigned32
   ACCESS	not-accessible
   STATUS	mandatory
   DESCRIPTION
      " An internal line number in the file (see filename) 
        referred to above (for internal use only)."
   ::= { optionalAlarmInfo 6 }

fileVersion	OBJECT-TYPE
   SYNTAX	DisplayString
   ACCESS	not-accessible
   STATUS	mandatory
   DESCRIPTION
      " A version indicator of the file (filename) referred
        to above (for internal use only)."
   ::= { optionalAlarmInfo 7}

internalData	OBJECT-TYPE
   SYNTAX	HexString (SIZE(0..750))
   ACCESS	not-accessible
   STATUS	mandatory
   DESCRIPTION
      " An additional internal hexadecimal information for
        internal use only. Note: The total number of bytes in comment, 
        operator, and internal data may not exceed 750 bytes."
   ::= { optionalAlarmInfo 8 }

-- the provisionalAlarmInfo group

--   STATUS       current
--   DESCRIPTION
--      " This group contains provisional variables representing information
--        pertinent to all alarms: cid"
provisionalAlarmInfo OBJECT IDENTIFIER ::= { alarmTrap 9 }
cid    OBJECT-TYPE
   SYNTAX       Unsigned32
   ACCESS       not-accessible
   STATUS       mandatory
   DESCRIPTION
      " This is a Custom Identifier(CID) of the component which generated
        the alarm"
   ::= { provisionalAlarmInfo 1 }

-- The following notifications are defined. Note that the structure and content
-- of each notification is identical.

-- The notification types are defined (one for each type of Alarm severity)
-- to accomodate simple Trap monitoring tools which assign severity
-- to a Trap based on the Specific Trap Number as opposed to the value
-- of a variable bind in the trap.

-- A Passport alarm with severity = critical will be mapped into the
-- criticalAlarm notification.  A Passport alarm with severity = cleared
-- will be mapped into the clearedAlarm notification, etc.
-- Note that the Trap number corresponds to the severity variable bind's
-- enumerated value, with the exception of an indeterminateAlarm, which
-- has a number of 6, and a severity variable bind value of 0 to correspond
-- to the OSI-defined value.

criticalAlarm TRAP-TYPE
   ENTERPRISE alarmTrap
   VARIABLES { componentRowPointer, componentName, eventTime, activeListStatus, 
             severity, alarmType, probableCause, ntpIndex, commentData } 
   DESCRIPTION		
      " This trap is used to provide a real time indication of a critical Alarm
        condition.  The variables listed in the VARIABLES clause,
        defined in the `mandatoryAlarmInfo' group are present 
        in all critical alarms. Additional variables as defined in
        the 'optionalAlarmInfo' group may be included if appropriate. "
::= 1

majorAlarm TRAP-TYPE
   ENTERPRISE alarmTrap
   VARIABLES { componentRowPointer, componentName, eventTime, activeListStatus, 
             severity, alarmType, probableCause, ntpIndex, commentData } 
   DESCRIPTION		
      " This trap is used to provide a real time indication of a major Alarm
        condition.  The variables listed in the VARIABLES clause,
        defined in the `mandatoryAlarmInfo' group are present 
        in all major alarms. Additional variables as defined in
        the 'optionalAlarmInfo' group may be included if appropriate. "
::= 2

minorAlarm TRAP-TYPE
   ENTERPRISE alarmTrap
   VARIABLES { componentRowPointer, componentName, eventTime, activeListStatus, 
             severity, alarmType, probableCause, ntpIndex, commentData } 
   DESCRIPTION		
      " This trap is used to provide a real time indication of a minor Alarm
        condition.  The variables listed in the VARIABLES clause,
        defined in the `mandatoryAlarmInfo' group are present 
        in all minor alarms. Additional variables as defined in
        the 'optionalAlarmInfo' group may be included if appropriate. "
::= 3

warningAlarm TRAP-TYPE
   ENTERPRISE alarmTrap
   VARIABLES { componentRowPointer, componentName, eventTime, activeListStatus, 
             severity, alarmType, probableCause, ntpIndex, commentData } 
   DESCRIPTION		
      " This trap is used to provide a real time indication of a warning Alarm
        condition.  The variables listed in the VARIABLES clause,
        defined in the `mandatoryAlarmInfo' group are present 
        in all warning alarms. Additional variables as defined in
        the 'optionalAlarmInfo' group may be included if appropriate. "
::= 4

clearedAlarm TRAP-TYPE
   ENTERPRISE alarmTrap
   VARIABLES { componentRowPointer, componentName, eventTime, activeListStatus, 
             severity, alarmType, probableCause, ntpIndex, commentData } 
   DESCRIPTION		
      " This trap is used to provide a real time indication of a cleared
        Alarm.  The variables listed in the VARIABLES clause,
        defined in the `mandatoryAlarmInfo' group are present 
        in all cleared alarms. Additional variables as defined in
        the 'optionalAlarmInfo' group may be included if appropriate. "
::= 5

indeterminateAlarm TRAP-TYPE
   ENTERPRISE alarmTrap
   VARIABLES { componentRowPointer, componentName, eventTime, activeListStatus, 
             severity, alarmType, probableCause, ntpIndex, commentData } 
   DESCRIPTION		
      " This trap is used to provide a real time indication of an indeterminate
        Alarm condition.  The variables listed in the VARIABLES clause,
        defined in the `mandatoryAlarmInfo' group are present 
        in all indeterminate alarms. Additional variables as defined in
        the 'optionalAlarmInfo' group may be included if appropriate. "
::= 6


--
-- Version and Compliance statements
--
 
 
-- Object-Group Statement:
 
-- OBJECTS   { componentRowPointer, componentName, eventTime, 
--             activeListStatus, severity, alarmType, probableCause,  
--             ntpIndex, commentData, notificationID, lpForHierClear, 
-- 	       operatorData, pid, fileName, fileLineNumber, fileVersion, 
--             internalData }
-- STATUS     current
-- DESCRIPTION
--       "A list of all current accessible leaf objects."

alarmGroup OBJECT IDENTIFIER ::= { alarmMIB 1 }
alarmGroupBC OBJECT IDENTIFIER ::= { alarmGroup 3 }
alarmGroupBC02 OBJECT IDENTIFIER ::= { alarmGroupBC 2 }
alarmGroupBC02A OBJECT IDENTIFIER ::= { alarmGroupBC02 2 }



-- Notification Group:

-- NOTIFICATIONS   { criticalAlarm, majorAlarm, minorAlarm, 
--                   warningAlarm, clearedAlarm, indeterminateAlarm }
-- STATUS          current
-- DESCRIPTION
--    "A list of all current notifications defined in this Module."

alarmNotifications OBJECT IDENTIFIER ::= { alarmMIB 2 }
alarmNotificationsGroupBC02A OBJECT IDENTIFIER ::= { alarmNotifications 1 }



-- Agent-Capabilities Statement:

-- PRODUCT-RELEASE "Passport Release 3.2 Alarms."
-- STATUS          current
-- DESCRIPTION
--    "Passport Alarms MIB: MIB Version BC02A."
-- SUPPORTS        Nortel-Magellan-Passport-AlarmMIB
-- INCLUDES        { alarmGroupBC02A, 
--                   alarmNotificationsGroupBC02A }

alarmCapabilities OBJECT IDENTIFIER ::= { alarmMIB 3 }
alarmCapabilitiesBC OBJECT IDENTIFIER ::= { alarmCapabilities 3 }
alarmCapabilitiesBC02 OBJECT IDENTIFIER ::= { alarmCapabilitiesBC 2 }
alarmCapabilitiesBC02A OBJECT IDENTIFIER ::= { alarmCapabilitiesBC02 2 }


END
