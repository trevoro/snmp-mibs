-- **************************************************************************
-- *            SNMP Private MIB  PROTOTYPE ONLY
-- *
-- *   Copyright(c) - Johnson Controls, Inc, 2001
-- *   Use or copying of all or any part of the document, except as
-- *   permitted by the License Agreement is prohibited.
-- * 
-- *   This MIB defines the SNMP Interface of Johnson Controls
-- *   Controls Group
-- *
-- *            
-- * HISTORY
-- * Date      Name     Rel    EC/PT#  Task# Reason for change
-- * ________ ______ _______ _____ _________________________________
-- * 01 APR 18 kehossm  1.00                 Develop Prototype                                        Use function prototypes from rtos_ex.h
-- * 01 JUL 13 perryt   1.00          23461  Update for SNMP v2.0 and
-- *                                         add condition related Bacnet traps 
-- * 01 JUL 16 kehossm  1.00          23463  update trap descriptions   
-- * 01 JUL 25 perryt	1.00          23708  Split mib
-- *                                         update JCIControlsGroup to ...-MIB
-- *                  
-- **************************************************************************

JCIControlsGroup-MIB  DEFINITIONS ::= BEGIN


IMPORTS
    jciControlsGroup                     FROM JohnsonControlsInc-MIB;  

-- private                 OBJECT IDENTIFIER ::= { iso(1) org(3) dod(6) internet(1) 4 }
-- enterprises             OBJECT IDENTIFIER ::= { private(1)}

-- This is our private MIB 
-- johnsonControlsInc      OBJECT IDENTIFIER ::= { enterprises(4399) }
    
--jciControlsGroup           OBJECT IDENTIFIER ::= { johnsonControlsInc 2 }
cgProducts                 OBJECT IDENTIFIER ::= { jciControlsGroup 1 }
mSeries                    OBJECT IDENTIFIER ::= { cgProducts 10 }


END
