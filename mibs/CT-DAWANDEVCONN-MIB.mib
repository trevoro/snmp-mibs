CT-DAWANDEVCONN-MIB DEFINITIONS ::= BEGIN

--  ct-dawandevconn-mib
--  Revision: 0.0.01
--  Date: June 29, 1999
--              
--  Cabletron Systems, Inc.
--  35 Industrial Way, P.O. Box 5005
--  Rochester, NH 03867-0505
--  (603) 332-9400
--  support@ctron.com

--  This module provides authoritative definitions for the
--  WAN
--
--  This module will be extended, as required.
--

--  Cabletron Systems reserves the right to make changes in
--  specification and other information contained in this document
--  without prior notice.  The reader should consult Cabletron Systems
--  to determine whether any such changes have been made.^
--
--  In no event shall Cabletron Systems be liable for any incidental,
--  indirect, special, or consequential damages whatsoever (including
--  but not limited to lost profits) arising out of or related to this
--  document or the information contained in it, even if Cabletron
--  Systems has been advised of, known, or should have known, the
--  possibility of such damages.
--
--  Cabletron grants vendors, end-users, and other interested parties
--  a non-exclusive license to use this Specification in connection
--  with the management of Cabletron products.
--  Copyright June 99 Cabletron Systems
--
IMPORTS
    
    OBJECT-TYPE
            FROM RFC-1212
    
    cabletron
            FROM CTRON-OIDS;
                    
   ctSSA OBJECT IDENTIFIER ::= { cabletron 4497 }
   
   daWanDevConn OBJECT IDENTIFIER ::= { ctSSA 23 }
      

   daWanDevConnTable OBJECT-TYPE
       SYNTAX      SEQUENCE OF DaWanDevConnEntry
       ACCESS      not-accessible
       STATUS      mandatory
       DESCRIPTION
               "A list of Demand Access remote WAN connections"
       ::= {daWanDevConn 1}

   daWanDevConnEntry OBJECT-TYPE
       SYNTAX      DaWanDevConnEntry
       ACCESS      not-accessible
       STATUS      mandatory
       DESCRIPTION
               "An entry containing wan connection information and statistics."
       INDEX   {daWanDeviceIndex, daWanConnectionIndex}
       ::= {daWanDevConnTable 1}
   
   DaWanDevConnEntry ::=
       SEQUENCE {
           daWanDeviceIndex              INTEGER,
           daWanConnectionIndex          INTEGER
           }
               
   daWanDeviceIndex OBJECT-TYPE
       SYNTAX      INTEGER(0..2147483647)
       ACCESS      read-only
       STATUS      mandatory
       DESCRIPTION
               "This is the index into this table.  This index uniquely identifies
                the connection associated with the device."
       ::= { daWanDevConnEntry 1 }
   
   daWanConnectionIndex OBJECT-TYPE
       SYNTAX      INTEGER(0..2147483647)
       ACCESS      read-only
       STATUS      mandatory
       DESCRIPTION
               "This is the index into this table.  This index uniquely identifies
                the connection associated with the device."
       ::= { daWanDevConnEntry 2 }
END
