BSUSUBASE-MIB DEFINITIONS ::= BEGIN

	IMPORTS
		OBJECT-TYPE, MODULE-IDENTITY, Integer32
			FROM SNMPv2-SMI
		DisplayString
			FROM SNMPv2-TC
		aniBsuWirelessPort
			FROM BSUWIRELESSIF-MIB
		aniBsuSuMacAddr
			FROM BSUSUINV-MIB
		aniBsuSuGroup
			FROM ANIROOT-MIB;

aniBsuSuBase  MODULE-IDENTITY
	LAST-UPDATED "0105091130Z"      -- Wed May 9 11:30:00 PDT 2001
	ORGANIZATION "Aperto Networks"
	CONTACT-INFO
	  "       
	  Postal:  Aperto Networks Inc
		   1637 S Main Street 
		   Milpitas, California 95035
	  Tel:	   +1 408 719 9977
	  "       
	DESCRIPTION
	   "This group allows the users of the BSU to access some basic
	    information about the SU through Proxy.
	   "
	::= { aniBsuSuGroup 2 }


aniBsuSuBaseTable OBJECT-TYPE
	SYNTAX      SEQUENCE OF AniBsuSuBaseEntry
	MAX-ACCESS  not-accessible
	STATUS      current
	DESCRIPTION
	   "This table accesses the attributes of each SU MAC interface
	    through proxy.
	   "
        ::= { aniBsuSuBase 1 }

aniBsuSuBaseEntry OBJECT-TYPE
	SYNTAX      AniBsuSuBaseEntry
	MAX-ACCESS  not-accessible
	STATUS      current
	DESCRIPTION
	   "Basic information for a single SU.
	    An entry in this table exists for each SU that is connected
	    to the BSU.
	   "
	INDEX { aniBsuWirelessPort,aniBsuSuMacAddr }
	::= { aniBsuSuBaseTable 1 }

AniBsuSuBaseEntry ::= SEQUENCE {
	aniBsuSuNetworkAccess	INTEGER,
	aniBsuSuMaxHostSupport	Integer32,
    aniBsuSuTargetFreq DisplayString,
	aniBsuSuFrequencyTable   DisplayString
	}


aniBsuSuNetworkAccess  OBJECT-TYPE
	SYNTAX	INTEGER {
		enable(1),
		disable(2)
	}
	MAX-ACCESS  read-only
	STATUS      current
	DESCRIPTION
	   "This object controls whether the SU has access to the 
	    network or not.
	   "
	DEFVAL { 1 }
	::= { aniBsuSuBaseEntry 2 }

aniBsuSuMaxHostSupport  OBJECT-TYPE
	SYNTAX      Integer32 (1..254)
	MAX-ACCESS  read-only
	STATUS      current
	DESCRIPTION
	   "This object identifies the total number of hosts that can 
	    be granted access through SU.

	    For PacketWave 110/210, this value is limited to 5.
	    PacketWave 120/220 can support upto 20 hosts.
	    PacketWave 130/230 can support upto 254 hosts.
	   "
	::= { aniBsuSuBaseEntry 3 }

aniBsuSuTargetFreq  OBJECT-TYPE
	SYNTAX      DisplayString 
	MAX-ACCESS  read-only
	STATUS      current
	DESCRIPTION
	   "The objects displays the target frequency for a particular SU.
	    It returns the SU target frequency in a string format.
	   "
	::= { aniBsuSuBaseEntry 4 }

aniBsuSuFrequencyTable  OBJECT-TYPE
	SYNTAX      DisplayString 
	MAX-ACCESS  read-only
	STATUS      current
	DESCRIPTION
	   "The objects displays the Frequency Table for a particular SU.
	    It returns the SU frequency table in a string format.
	   "
	::= { aniBsuSuBaseEntry 5 }


	END
