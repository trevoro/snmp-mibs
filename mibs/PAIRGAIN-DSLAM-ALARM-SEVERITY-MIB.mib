------------------------------------------------------------
-- $Workfile:   pgdsalsv.my  $
--   pg alarm severity setting and alarm status mib 
-- $Archive:   S:\DSLAM\swdev\snmp14.2.1.16\mibs\common\pgdsalsv.myv  $
-- $Revision:   1.6  $
-- $Date:   Mar 18 1999 16:22:04  $
-- $Author:   Goltzt  $
------------------------------------------------------------

-- Release 1.0
-- Revision 10/1/98
-- Printed 

-- Copyright 1998 PairGain Technologies, Inc.  All Rights
-- Reserved.  Reproduction of this document is authorized on
-- condition that the foregoing copyright notice is included.
-- This PairGain SNMP Management Information Base Specification
-- (Specification) embodies PairGain's confidential and
-- proprietary intellectual property.  PairGain retains all
-- title and ownership in the Specification, including any
-- revisions.  
--
-- It is PairGain's intent to encourage the widespread use of
-- this Specification in connection with the management of
-- PairGain products. PairGain grants vendors, end-users,
-- and other interested parties a non-exclusive license to
-- use this Specification in connection with the management
-- of PairGain products.
--
-- This Specification is supplied "AS IS," and PairGain makes
-- no warranty, either expressed or implied, as to the use,
-- operation, condition, or performance of the Specification.


PAIRGAIN-DSLAM-ALARM-SEVERITY-MIB DEFINITIONS ::= BEGIN

-- SECTION 1: Top Level Definitions

IMPORTS
        MODULE-IDENTITY, OBJECT-TYPE
            FROM SNMPv2-SMI
        ifIndex
            FROM RFC1213-MIB
        RowStatus
            FROM SNMPv2-TC
        pgDSLAMAlarmSeverity, pgDSLAMAlarm
            FROM PAIRGAIN-COMMON-HD-MIB;


pgdsalsvMIB MODULE-IDENTITY
        LAST-UPDATED "9901141600Z"
        ORGANIZATION "PairGain Technologies, INC."
        CONTACT-INFO
                "       Ken Huang 
                        Tel: +1 714-481-4543
                        Fax: +1 714-481-2114
                        E-mail: ken_huang@pairgain.com "
        DESCRIPTION
                "The MIB module defining objects for the alarm severity configuration
                and status management of a central DSLAM (Digital Subscriber Line 
				Access Multiplexer), including from chassis power supply, fan status, 
			    to each channel/port related alarms in each HDSL/ADSL card inside the chassis.
				For HDSL alarm management:
				Please refer to  Spec#157-1759-01 by Ken Huang for detail architecture model.
                For ADSL alarm management: 
                Please refer to AdslLineMib(TR006) from adslForum for details architecture model.

                Naming Conventions:
                        Atuc -- (ATU-C) ADSL modem at near (Central) end of line
                        Atur -- (ATU-R) ADSL modem at Remote end of line
                        ES  -- Errored Second.
                        Lof -- Loss of Frame
                        Los -- Loss of Signal
                        Lpr -- Loss of Power
                        LOSW -- Loss of Sync Word
                        UAS  -- Unavailable Second
		        "
  ::= { pgDSLAMAlarmSeverity 1 }

-- Alarm Severity Settings
PgDSLAMAlarmSeverity ::=
    INTEGER {
        disable(1),   -- disable the alarm 
        minor(2),     -- set alarm severity to minor 
        major(3),     -- set alarm severity to major 
        critical(4)   --  set alarm severity to critical 
        }

PgDSLAMAlarmStatus ::=
    INTEGER {
        noalarm(1),   -- no such alarm condition currently present
        minor(2),     -- current alarming condition is minor 
        major(3),     -- current alarming condition is major 
        critical(4),  -- current alarming condition is critical 
	alarm(5)      -- such alarm currently present 
        }


-- SECTION 2: PairGain DSLAM Chassis Alarm Severity Setting Table
pgDSLAMChassisAlarmSeverity OBJECT IDENTIFIER ::= { pgDSLAMAlarmSeverity 2}

pgDSLAMChassisPsAlarmSeverity OBJECT-TYPE
        SYNTAX  PgDSLAMAlarmSeverity
        MAX-ACCESS  read-create 
        STATUS  current
        DESCRIPTION
                "The Chassis Power failure Alarm Severity Setting."
        ::= { pgDSLAMChassisAlarmSeverity 1 }

pgDSLAMChassisFanAlarmSeverity OBJECT-TYPE
        SYNTAX  PgDSLAMAlarmSeverity
        MAX-ACCESS  read-create
        STATUS  current
        DESCRIPTION
                "The Chassis Fan failure Alarm Severity Setting."
        ::= { pgDSLAMChassisAlarmSeverity 2 }

pgDSLAMChassisConfigChangeAlarmSeverity OBJECT-TYPE
        SYNTAX  PgDSLAMAlarmSeverity
        MAX-ACCESS  read-create
        STATUS  current
        DESCRIPTION
                "The Chassis Config change Alarm Severity Setting."
        ::= { pgDSLAMChassisAlarmSeverity 3 }

pgDSLAMChassisTempAlarmSeverity OBJECT-TYPE
        SYNTAX  PgDSLAMAlarmSeverity
        MAX-ACCESS  read-create
        STATUS  current
        DESCRIPTION
                "The Chassis Temperature exceed threshold Alarm Severity Setting."
        ::= { pgDSLAMChassisAlarmSeverity 4 }

-- SECTION 3: PairGain DSLAM HDSL Span Alarm Threshold Configuration Profile Table

pgDSLAMHDSLSpanAlarmThresholdConfProfileIndexNext OBJECT-TYPE
                SYNTAX          INTEGER(0..255)
                MAX-ACCESS      read-only
                STATUS          current
                DESCRIPTION
                        "This object contains an appropriate value to
                        be used for pgDSLAMHDSLSpanAlarmThresholdConfProfileIndex
                        when creating entries in the alarmThresholdConfTable.
                        The value '0' indicates that no unassigned entries are
                        available.
                        To obtain the pgDSLAMHDSLSpanAlarmThresholdConfProfileIndexNext
                        value for a new entry, the manager issues a
                        management protocol retrieval operation to obtain
                        the current value of this object.  After each
                        retrieval, the agent should modify the value to
                        the next unassigned index."
        ::= { pgdsalsvMIB 7 }

pgDSLAMHDSLSpanAlarmThresholdConfProfileTable OBJECT-TYPE
        SYNTAX  SEQUENCE OF PgDSLAMHDSLSpanAlarmThresholdConfProfileEntry
        MAX-ACCESS  not-accessible
        STATUS  current
        DESCRIPTION
                "The DSLAM HDSL Span Alarm Threshold Configuration Profile table."
        ::= { pgdsalsvMIB 8 }

pgDSLAMHDSLSpanAlarmThresholdConfProfileEntry OBJECT-TYPE
        SYNTAX  PgDSLAMHDSLSpanAlarmThresholdConfProfileEntry
        MAX-ACCESS  not-accessible
        STATUS  current
        DESCRIPTION
                "Entry in the DSLAM HDSL Span Alarm Threshold Configuration Profile table."
        INDEX   { pgDSLAMHDSLSpanAlarmThresholdConfProfileIndex }
        ::= { pgDSLAMHDSLSpanAlarmThresholdConfProfileTable 1 }

PgDSLAMHDSLSpanAlarmThresholdConfProfileEntry ::= SEQUENCE {
        pgDSLAMHDSLSpanAlarmThresholdConfProfileIndex
            INTEGER(0..255),
        pgDSLAMHDSLSpanMarginThreshold
            INTEGER(0..255),
        pgDSLAMHDSLSpanESThreshold
            INTEGER(0..255),
        pgDSLAMHDSLSpanUASThreshold
            INTEGER(0..255),
        pgDSLAMHDSLSpanAlarmThresholdConfProfileRowStatus
            RowStatus
    }

    pgDSLAMHDSLSpanAlarmThresholdConfProfileIndex    OBJECT-TYPE
                        SYNTAX          INTEGER(0..255)
                        MAX-ACCESS      not-accessible
                        STATUS          current
                        DESCRIPTION
                        "This object is used by the line alarm Threshold configuration table in
                        order to identify a row of this table"
                ::= {pgDSLAMHDSLSpanAlarmThresholdConfProfileEntry 1}

    pgDSLAMHDSLSpanMarginThreshold  OBJECT-TYPE
        SYNTAX    INTEGER(0..255)
        MAX-ACCESS    read-create
        STATUS    current
        DESCRIPTION
            "Sets the HDSL Margin threshold value."
        ::= {pgDSLAMHDSLSpanAlarmThresholdConfProfileEntry 2}

   pgDSLAMHDSLSpanESThreshold OBJECT-TYPE
        SYNTAX    INTEGER(0..255)
        MAX-ACCESS    read-create
        STATUS    current
        DESCRIPTION
            "Sets the HDSL Errored Seconds threshold value."
        ::= {pgDSLAMHDSLSpanAlarmThresholdConfProfileEntry 3}

    pgDSLAMHDSLSpanUASThreshold OBJECT-TYPE
        SYNTAX    INTEGER(0..255)
        MAX-ACCESS    read-create
        STATUS    current
        DESCRIPTION
            "Sets the HDSL Unavailable Seconds threshold value."
        ::= {pgDSLAMHDSLSpanAlarmThresholdConfProfileEntry 4}

    pgDSLAMHDSLSpanAlarmThresholdConfProfileRowStatus OBJECT-TYPE
                SYNTAX          RowStatus
                MAX-ACCESS      read-create
                STATUS          current
                DESCRIPTION
                        "This object is used to create a new row or modify or
                        delete an existing row in this table."
                ::= {pgDSLAMHDSLSpanAlarmThresholdConfProfileEntry 5}

-- SECTION 4: PairGain DSLAM HDSL Span Alarm Severity Configuration Profile Table

pgDSLAMHDSLSpanAlarmSeverityConfProfileIndexNext OBJECT-TYPE
                SYNTAX          INTEGER(0..255)
                MAX-ACCESS      read-only
                STATUS          current
                DESCRIPTION
                        "This object contains an appropriate value to
                        be used for pgDSLAMHDSLSpanAlarmSeverityConfProfileIndex
                        when creating entries in the alarmSeverityConfTable.
                        The value '0' indicates that no unassigned entries are
                        available.
                        To obtain the pgDSLAMHDSLSpanAlarmSeverityConfProfileIndexNext
                        value for a new entry, the manager issues a
                        management protocol retrieval operation to obtain
                        the current value of this object.  After each
                        retrieval, the agent should modify the value to
                        the next unassigned index."
        ::= { pgdsalsvMIB 9 }

pgDSLAMHDSLSpanAlarmSeverityConfProfileTable OBJECT-TYPE
        SYNTAX  SEQUENCE OF PgDSLAMHDSLSpanAlarmSeverityConfProfileEntry
        MAX-ACCESS  not-accessible
        STATUS  current
        DESCRIPTION
                "The DSLAM HDSL Span Alarm Severity Configuration Profile table."
        ::= { pgdsalsvMIB 10 }

pgDSLAMHDSLSpanAlarmSeverityConfProfileEntry OBJECT-TYPE
        SYNTAX  PgDSLAMHDSLSpanAlarmSeverityConfProfileEntry
        MAX-ACCESS  not-accessible
        STATUS  current
        DESCRIPTION
                "Entry in the DSLAM HDSL Span Alarm Severity Configuration Profile table."
        INDEX   { pgDSLAMHDSLSpanAlarmSeverityConfProfileIndex }
        ::= { pgDSLAMHDSLSpanAlarmSeverityConfProfileTable 1 }

PgDSLAMHDSLSpanAlarmSeverityConfProfileEntry ::= SEQUENCE {
        pgDSLAMHDSLSpanAlarmSeverityConfProfileIndex
            INTEGER(0..255),
        pgDSLAMHDSLSpanLOSWAlarmSetting
            PgDSLAMAlarmSeverity,
        pgDSLAMHDSLSpanMarginAlarmSetting
            PgDSLAMAlarmSeverity,
        pgDSLAMHDSLSpanESAlarmSetting
            PgDSLAMAlarmSeverity,
        pgDSLAMHDSLSpanUASAlarmSetting
            PgDSLAMAlarmSeverity,
        pgDSLAMHDSLSpanAlarmSeverityConfProfileRowStatus
            RowStatus
    }

    pgDSLAMHDSLSpanAlarmSeverityConfProfileIndex    OBJECT-TYPE
                        SYNTAX          INTEGER(0..255)
                        MAX-ACCESS      not-accessible
                        STATUS          current
                        DESCRIPTION
                        "This object is used by the line alarm severity configuration table in
                        order to identify a row of this table"
                ::= {pgDSLAMHDSLSpanAlarmSeverityConfProfileEntry 1}

    pgDSLAMHDSLSpanLOSWAlarmSetting OBJECT-TYPE
        SYNTAX    PgDSLAMAlarmSeverity
        MAX-ACCESS    read-create
        STATUS    current
        DESCRIPTION
            "Sets the severity for Loss of Sync Word alarm."
        ::= {pgDSLAMHDSLSpanAlarmSeverityConfProfileEntry 2}

    pgDSLAMHDSLSpanMarginAlarmSetting OBJECT-TYPE
        SYNTAX    PgDSLAMAlarmSeverity
        MAX-ACCESS    read-create
        STATUS    current
        DESCRIPTION
            "Sets the severity for Margin threshold exceeded alarm."
        ::= {pgDSLAMHDSLSpanAlarmSeverityConfProfileEntry 3}

    pgDSLAMHDSLSpanESAlarmSetting OBJECT-TYPE
        SYNTAX    PgDSLAMAlarmSeverity
        MAX-ACCESS    read-create
        STATUS    current
        DESCRIPTION
            "Sets the severity for Errored Seconds threshold exceeded alarm."
        ::= {pgDSLAMHDSLSpanAlarmSeverityConfProfileEntry 4}

    pgDSLAMHDSLSpanUASAlarmSetting OBJECT-TYPE
        SYNTAX    PgDSLAMAlarmSeverity
        MAX-ACCESS    read-create
        STATUS    current
        DESCRIPTION
            "Sets the severity for UAS threshold exceeded alarm."
        ::= {pgDSLAMHDSLSpanAlarmSeverityConfProfileEntry 5}

    pgDSLAMHDSLSpanAlarmSeverityConfProfileRowStatus OBJECT-TYPE
                SYNTAX          RowStatus
                MAX-ACCESS      read-create
                STATUS          current
                DESCRIPTION
                        "This object is used to create a new row or modify or
                        delete an existing row in this table."
                ::= {pgDSLAMHDSLSpanAlarmSeverityConfProfileEntry 6}

-- SECTION 5: PairGain DSLAM ADSL ATU-C Alarm Indication Table 
 
pgDSLAMADSLAtucAlarmTable OBJECT-TYPE
        SYNTAX  SEQUENCE OF PgDSLAMADSLAtucAlarmEntry
        MAX-ACCESS  not-accessible
        STATUS  current
        DESCRIPTION
                "The DSLAM ADSL ATU-C Alarm indication table."
        ::= { pgDSLAMAlarm 1 }

pgDSLAMADSLAtucAlarmEntry OBJECT-TYPE
        SYNTAX  PgDSLAMADSLAtucAlarmEntry
        MAX-ACCESS  not-accessible
        STATUS  current
        DESCRIPTION
                "Entry in the DSLAM ADSL ATU-C Alarm indication table."
        INDEX   { ifIndex }
        ::= { pgDSLAMADSLAtucAlarmTable 1 }

PgDSLAMADSLAtucAlarmEntry ::= SEQUENCE {
    pgDSLAMADSLAtucLofAlarm
        PgDSLAMAlarmStatus,
    pgDSLAMADSLAtucLosAlarm
        PgDSLAMAlarmStatus,
    pgDSLAMADSLAtucLprAlarm
        PgDSLAMAlarmStatus,
    pgDSLAMADSLAtucESAlarm
        PgDSLAMAlarmStatus,
    pgDSLAMADSLAtucRateChangeAlarm
        PgDSLAMAlarmStatus,
    pgDSLAMADSLAtucInitFailureAlarm
        PgDSLAMAlarmStatus
}

pgDSLAMADSLAtucLofAlarm OBJECT-TYPE
        SYNTAX  PgDSLAMAlarmStatus
        MAX-ACCESS  read-only
        STATUS  current
        DESCRIPTION
                "ADSL loss of framing alarm on ATU-C 
                "
        ::= { pgDSLAMADSLAtucAlarmEntry 1}

pgDSLAMADSLAtucLosAlarm OBJECT-TYPE
        SYNTAX  PgDSLAMAlarmStatus
        MAX-ACCESS  read-only
        STATUS  current
        DESCRIPTION
                "ADSL loss of signal alarm on ATU-C 
                "
        ::= { pgDSLAMADSLAtucAlarmEntry 2}

pgDSLAMADSLAtucLprAlarm OBJECT-TYPE
        SYNTAX  PgDSLAMAlarmStatus
        MAX-ACCESS  read-only
        STATUS  current
        DESCRIPTION
                "ADSL loss of power alarm on ATU-C 
                "
        ::= { pgDSLAMADSLAtucAlarmEntry 3}

pgDSLAMADSLAtucESAlarm OBJECT-TYPE
        SYNTAX  PgDSLAMAlarmStatus
        MAX-ACCESS  read-only
        STATUS  current
        DESCRIPTION
                "ADSL Errored Second threshold exceeded alarm on ATU-C 
                "
        ::= { pgDSLAMADSLAtucAlarmEntry 4}

pgDSLAMADSLAtucRateChangeAlarm OBJECT-TYPE
        SYNTAX  PgDSLAMAlarmStatus
        MAX-ACCESS  read-only
        STATUS  current
        DESCRIPTION
                "ADSL Rate Changed alarm on ATU-C 
                "
        ::= { pgDSLAMADSLAtucAlarmEntry 5}

pgDSLAMADSLAtucInitFailureAlarm OBJECT-TYPE
        SYNTAX  PgDSLAMAlarmStatus
        MAX-ACCESS  read-only
        STATUS  current
        DESCRIPTION
                "ADSL initialization failed alarm on ATU-C 
                "
        ::= { pgDSLAMADSLAtucAlarmEntry 6}

-- SECTION 6: PairGain DSLAM ADSL ATU-R Alarm Indication Table 
 
pgDSLAMADSLAturAlarmTable OBJECT-TYPE
        SYNTAX  SEQUENCE OF PgDSLAMADSLAturAlarmEntry
        MAX-ACCESS  not-accessible
        STATUS  current
        DESCRIPTION
                "The DSLAM ADSL ATU-R Alarm indication table."
        ::= { pgDSLAMAlarm 2 }

pgDSLAMADSLAturAlarmEntry OBJECT-TYPE
        SYNTAX  PgDSLAMADSLAturAlarmEntry
        MAX-ACCESS  not-accessible
        STATUS  current
        DESCRIPTION
                "Entry in the DSLAM ADSL ATU-R Alarm indication table."
        INDEX   { ifIndex }
        ::= { pgDSLAMADSLAturAlarmTable 1 }

PgDSLAMADSLAturAlarmEntry ::= SEQUENCE {
    pgDSLAMADSLAturLofAlarm
        PgDSLAMAlarmStatus,
    pgDSLAMADSLAturLosAlarm
        PgDSLAMAlarmStatus,
    pgDSLAMADSLAturLprAlarm
        PgDSLAMAlarmStatus,
    pgDSLAMADSLAturESAlarm
        PgDSLAMAlarmStatus,
    pgDSLAMADSLAturRateChangeAlarm
        PgDSLAMAlarmStatus,
    pgDSLAMADSLAturInitFailureAlarm
        PgDSLAMAlarmStatus
}

pgDSLAMADSLAturLofAlarm OBJECT-TYPE
        SYNTAX  PgDSLAMAlarmStatus
        MAX-ACCESS  read-only
        STATUS  current
        DESCRIPTION
                "ADSL loss of framing alarm on ATU-R 
                "
        ::= { pgDSLAMADSLAturAlarmEntry 1}

pgDSLAMADSLAturLosAlarm OBJECT-TYPE
        SYNTAX  PgDSLAMAlarmStatus
        MAX-ACCESS  read-only
        STATUS  current
        DESCRIPTION
                "ADSL loss of signal alarm on ATU-R 
                "
        ::= { pgDSLAMADSLAturAlarmEntry 2}

pgDSLAMADSLAturLprAlarm OBJECT-TYPE
        SYNTAX  PgDSLAMAlarmStatus
        MAX-ACCESS  read-only
        STATUS  current
        DESCRIPTION
                "ADSL loss of power alarm on ATU-R 
                "
        ::= { pgDSLAMADSLAturAlarmEntry 3}

pgDSLAMADSLAturESAlarm OBJECT-TYPE
        SYNTAX  PgDSLAMAlarmStatus
        MAX-ACCESS  read-only
        STATUS  current
        DESCRIPTION
                "ADSL Errored Second threshold exceeded alarm on ATU-R 
                "
        ::= { pgDSLAMADSLAturAlarmEntry 4}

pgDSLAMADSLAturRateChangeAlarm OBJECT-TYPE
        SYNTAX  PgDSLAMAlarmStatus
        MAX-ACCESS  read-only
        STATUS  current
        DESCRIPTION
                "ADSL Rate Changed alarm on ATU-R 
                "
        ::= { pgDSLAMADSLAturAlarmEntry 5}

pgDSLAMADSLAturInitFailureAlarm OBJECT-TYPE
        SYNTAX  PgDSLAMAlarmStatus
        MAX-ACCESS  read-only
        STATUS  current
        DESCRIPTION
                "ADSL initialization failed alarm on ATU-R 
                "
        ::= { pgDSLAMADSLAturAlarmEntry 6}


-- SECTION 7: PairGain DSLAM Chassis Alarm Indication Table 
 
pgDSLAMChassisAlarmTable OBJECT-TYPE
        SYNTAX  SEQUENCE OF PgDSLAMChassisAlarmEntry
        MAX-ACCESS  not-accessible
        STATUS  current
        DESCRIPTION
                "The DSLAM Chassis Alarm indication table."
        ::= { pgDSLAMAlarm 3 }

pgDSLAMChassisAlarmEntry OBJECT-TYPE
        SYNTAX  PgDSLAMChassisAlarmEntry
        MAX-ACCESS  not-accessible
        STATUS  current
        DESCRIPTION
                "Entry in the DSLAM Chassis Alarm indication table."
        INDEX   { ifIndex }
        ::= { pgDSLAMChassisAlarmTable 1 }

PgDSLAMChassisAlarmEntry ::= SEQUENCE {
    pgDSLAMPSFailureAlarm
        PgDSLAMAlarmStatus,
    pgDSLAMFanFailureAlarm
        PgDSLAMAlarmStatus,
    pgDSLAMConfigChangeAlarm
        PgDSLAMAlarmStatus,
    pgDSLAMTempExceedThreshAlarm
        PgDSLAMAlarmStatus,
    pgDSLAMLineCardDownAlarm
        PgDSLAMAlarmStatus,
    pgDSLAMCellBusDownAlarm
        PgDSLAMAlarmStatus
}

pgDSLAMPSFailureAlarm OBJECT-TYPE
        SYNTAX  PgDSLAMAlarmStatus
        MAX-ACCESS  read-only
        STATUS  current
        DESCRIPTION
                "chassis power supply failure alarm 
                "
        ::= { pgDSLAMChassisAlarmEntry 1}

pgDSLAMFanFailureAlarm OBJECT-TYPE
        SYNTAX  PgDSLAMAlarmStatus
        MAX-ACCESS  read-only
        STATUS  current
        DESCRIPTION
                "chassis fan failure alarm 
                "
        ::= { pgDSLAMChassisAlarmEntry 2}

pgDSLAMConfigChangeAlarm OBJECT-TYPE
        SYNTAX  PgDSLAMAlarmStatus
        MAX-ACCESS  read-only
        STATUS  current
        DESCRIPTION
                "chassis config changed alarm
                "
        ::= { pgDSLAMChassisAlarmEntry 3}

pgDSLAMTempExceedThreshAlarm OBJECT-TYPE
        SYNTAX  PgDSLAMAlarmStatus
        MAX-ACCESS  read-only
        STATUS  current
        DESCRIPTION
                "chassis temperature exceeded threshold 
                "
        ::= { pgDSLAMChassisAlarmEntry 4}

pgDSLAMLineCardDownAlarm OBJECT-TYPE
        SYNTAX  PgDSLAMAlarmStatus
        MAX-ACCESS  read-only
        STATUS  current
        DESCRIPTION
                "the line card in the chassis is down 
                "
        ::= { pgDSLAMChassisAlarmEntry 5}

pgDSLAMCellBusDownAlarm OBJECT-TYPE
        SYNTAX  PgDSLAMAlarmStatus
        MAX-ACCESS  read-only
        STATUS  current
        DESCRIPTION
                "the cell bus in the chassis is down 
                "
        ::= { pgDSLAMChassisAlarmEntry 6}

END
