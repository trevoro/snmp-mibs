--



-- Copyright (c) 1994 Chipcom Corporation.  All Rights Reserved.

--

-- Reproduction of this document is authorized on condition that this

-- copyright notice is included.  This SNMP MIB Specification

-- embodies proprietary intellectual property.  The copyright

-- retains all title and ownership in the specification, including any

-- revisions.

--

-- It is the intent to encourage the widespread use of this

-- specification in connection with the management of our

-- products. The copyright grants vendor, end-users, and other interested

-- parties a non-exclusive license to use this specification in

-- connection with the management of our products.

--

-- This specification is supplied "AS IS," and no

-- warranty, either express or implied, as to the use, operation,

-- condition, or performance of the specification, is made.

--

-- Copyright text courtesy of Dave Perkins.

--

-- The right to change this MIB without notification is retained.

--





--

-- If you have any questions about this MIB, please call your

-- Technical Support Center, or call 1-800-228-6840.

--



--

-- MIB Version Information:

--

-- Version     Description

------------------------------------------------------------------

--   v1.0      Initial version of the chipmib02 branch.

--   v2.0      Version tracking initiated.

--   v2.1      Version release with TRMM v.2.10

--   v2.2      Version release with EMM v4.0

--   v2.3      Version release with TRMM v.3.0

--   v2.39     Version release with DMM v.1.0 and FMM b.2.00

--   v2.4      Version release with FMM v.2.0

--   v2.41     Version release for edits, posted to venera.isi.edu and ftp.chipcom.com

--



--

-- Agents supporting this MIB:

--	Ethernet Management Module, Software Rev: v4.01

--	Token Ring Management Module, Software Rev: v3.0

--	FDDI Management Module, Software Rev: v2.0

--	Distributed Management Module, Software Rev: 1.0

--	Ethernet to Ethernet Bridge Module, Software Rev: v2.13

--	Ethernet to Ethernet Bridge Box, Software Rev: v2.13

--	Ethernet Interconnect Module, Software Rev: v1.0

--





CHIPCOMMIB DEFINITIONS ::= BEGIN

IMPORTS

	enterprises, IpAddress, Counter, Gauge, TimeTicks FROM RFC1155-SMI

	OBJECT-TYPE		FROM RFC-1212

	DisplayString		FROM RFC1213-MIB

	TRAP-TYPE		FROM RFC-1215;



-- All representations of MAC addresses in this MIB Module use,

-- as a textual convention (i.e. this convention does not affect

-- their encoding), the data type:



MacAddress ::= OCTET STRING (SIZE (6))    -- a 6 octet address in

					  -- the "canonical" order

-- defined by IEEE 802.1a, i.e., as if it were transmitted least

-- significant bit first, even though 802.5 (in contrast to other

-- 802.x protocols) requires MAC addresses to be transmitted most

-- significant bit first.

--

-- 16-bit addresses, if needed, are represented by setting their

-- upper 4 octets to all 0's, i.e., AAFF would be represented

-- as 00000000AAFF.





chipcom		OBJECT IDENTIFIER ::= { enterprises 49 }



chipmib02	OBJECT IDENTIFIER ::= { chipcom 2 }



--

-- Top level groups

--



chipGen		OBJECT IDENTIFIER ::= { chipmib02 1 }

chipEcho	OBJECT IDENTIFIER ::= { chipmib02 2 }

chipProducts	OBJECT IDENTIFIER ::= { chipmib02 3 }

chipExperiment  OBJECT IDENTIFIER ::= { chipmib02 4 }

chipTTY		OBJECT IDENTIFIER ::= { chipmib02 5 }

chipTFTP	OBJECT IDENTIFIER ::= { chipmib02 6 }

chipDownload	OBJECT IDENTIFIER ::= { chipmib02 7 }

chipAlert	OBJECT IDENTIFIER ::= { chipmib02 8 }





chipBootP	OBJECT IDENTIFIER ::= { chipmib02 11 }



--

-- Product specific branches.  Also used for sysObjectID.

--



online		OBJECT IDENTIFIER ::= { chipProducts 1 }

oebm		OBJECT IDENTIFIER ::= { chipProducts 2 }



midnight	OBJECT IDENTIFIER ::= { chipProducts 3 }

workGroupHub	OBJECT IDENTIFIER ::= { chipProducts 4 }



emm		OBJECT IDENTIFIER ::= { chipProducts 5 }

chipBridge	OBJECT IDENTIFIER ::= { chipProducts 6 }

trmm		OBJECT IDENTIFIER ::= { chipProducts 7 }

fmm		OBJECT IDENTIFIER ::= { chipProducts 8 }

focus1		OBJECT IDENTIFIER ::= { chipProducts 9 }

oeim		OBJECT IDENTIFIER ::= { chipProducts 10 }

oncore		OBJECT IDENTIFIER ::= { chipProducts 11 }

dmm		OBJECT IDENTIFIER ::= { chipProducts 12 }



onsembleEthernet	OBJECT IDENTIFIER ::= { chipProducts 13 }







--

-- Experimental Branches

--

-- When RFCs are still in the experimental stage, the MIB

-- is incorporated under the enterprise experimental branch

-- so that changes in the experimental MIB do not affect

-- the released product.

--

-- As the RFC becomes standard and support is provided by the agents,

-- the support under this branch will be moved to the appropriate

-- standard branch.  That is, the support under this branch

-- for the MIB in question will be removed.

--



chipExpTokenRing OBJECT IDENTIFIER ::= { chipExperiment 1 }

dot1dBridge	OBJECT IDENTIFIER ::= { chipExperiment 14 }

expDot5		OBJECT IDENTIFIER ::= { chipExpTokenRing 1 }



--

-- ONline Groups

--



olAgents	OBJECT IDENTIFIER ::= { online   1 }

olConc		OBJECT IDENTIFIER ::= { online   2 }

olEnv		OBJECT IDENTIFIER ::= { online   3 }

olModules	OBJECT IDENTIFIER ::= { online   4 }

olNets		OBJECT IDENTIFIER ::= { online   5 }

olGroups	OBJECT IDENTIFIER ::= { online   6 }

olAlarm		OBJECT IDENTIFIER ::= { online   7 }

ocPower		OBJECT IDENTIFIER ::= { online   8 }

ocPowerControl  OBJECT IDENTIFIER ::= { ocPower  1 }

ocInventory	OBJECT IDENTIFIER ::= { online   9 }

ocInvHub	OBJECT IDENTIFIER ::= { ocInventory 1 }

ocInvMods	OBJECT IDENTIFIER ::= { ocInventory 2 }



olPS2		OBJECT IDENTIFIER ::= { online  11 }







--

-- Value added module attributes

--



olSpecMods	OBJECT IDENTIFIER ::= { olModules 4 }



--

-- A node for each module type  :

--



ol50nnMCTL	OBJECT IDENTIFIER ::= { olSpecMods 3 }

ol51nnMMGT	OBJECT IDENTIFIER ::= { olSpecMods 4 }

ol51nnMFIB	OBJECT IDENTIFIER ::= { olSpecMods 5 }

ol51nnMUTP	OBJECT IDENTIFIER ::= { olSpecMods 6 }

ol51nnMTP	OBJECT IDENTIFIER ::= { olSpecMods 7 }

ol51nnMBNC	OBJECT IDENTIFIER ::= { olSpecMods 8 }

ol51nnBEE	OBJECT IDENTIFIER ::= { olSpecMods 9 }

ol51nnRES	OBJECT IDENTIFIER ::= { olSpecMods 10 }

ol51nnREE	OBJECT IDENTIFIER ::= { olSpecMods 11 }

ol51nnMAUIF	OBJECT IDENTIFIER ::= { olSpecMods 12 }

ol51nnMAUIM	OBJECT IDENTIFIER ::= { olSpecMods 13 }

ol5208MTP	OBJECT IDENTIFIER ::= { olSpecMods 14 }

ol51nnMFP	OBJECT IDENTIFIER ::= { olSpecMods 15 }

ol51nnMFBP	OBJECT IDENTIFIER ::= { olSpecMods 16 }

ol51nnMTPL	OBJECT IDENTIFIER ::= { olSpecMods 17 }

ol51nnMTPPL	OBJECT IDENTIFIER ::= { olSpecMods 18 }

ol52nnMTP	OBJECT IDENTIFIER ::= { olSpecMods 19 }

ol52nnMFR	OBJECT IDENTIFIER ::= { olSpecMods 20 }

ol51nnMTS	OBJECT IDENTIFIER ::= { olSpecMods 21 }

ol51nnMFL	OBJECT IDENTIFIER ::= { olSpecMods 22 }

ol50nnMRCTL	OBJECT IDENTIFIER ::= { olSpecMods 23 }

ol51nnMFB	OBJECT IDENTIFIER ::= { olSpecMods 24 }

ol53nnMMGT	OBJECT IDENTIFIER ::= { olSpecMods 25 }

ol53nnMFBMIC	OBJECT IDENTIFIER ::= { olSpecMods 26 }

ol53nnMFIBST	OBJECT IDENTIFIER ::= { olSpecMods 27 }

ol53nnMSTP	OBJECT IDENTIFIER ::= { olSpecMods 28 }

ol51nnMTPCL	OBJECT IDENTIFIER ::= { olSpecMods 29 }

ol52nnBTT	OBJECT IDENTIFIER ::= { olSpecMods 30 }

ol51nnIx	OBJECT IDENTIFIER ::= { olSpecMods 31 }

ol52nnMMGT	OBJECT IDENTIFIER ::= { olSpecMods 32 }

ol50nnMHCTL	OBJECT IDENTIFIER ::= { olSpecMods 33 }



--

-- Ethernet Carrier Module

-- Packaged as part of the 6106M-MGT blade (carrier with management option).

--

oc61nnMCAR	OBJECT IDENTIFIER ::= { olSpecMods 35 }





--

-- Distributed Management Module (DMM)

-- Packaged as part of the 6106M-MGT blade (carrier with management option).

--

oc60nnMMGT	OBJECT IDENTIFIER ::= { olSpecMods 43 } -- Module may be

							-- 61nnM-MGT (ethernet



oc61nnDMGT	OBJECT IDENTIFIER ::= { olSpecMods 45 } -- Ethernet MAC Module

oc61nnMFBP	OBJECT IDENTIFIER ::= { olSpecMods 46 }

oc61nnMTPL	OBJECT IDENTIFIER ::= { olSpecMods 47 }

ol51nnMTPLS	OBJECT IDENTIFIER ::= { olSpecMods 48 }

oc60nnMRCTL	OBJECT IDENTIFIER ::= { olSpecMods 50 }



ol50nnMRCLS	OBJECT IDENTIFIER ::= { olSpecMods 51 }





ol41nnHMTP	OBJECT IDENTIFIER ::= { olSpecMods 52 }

ol41nnHETP	OBJECT IDENTIFIER ::= { olSpecMods 53 }





ol52nnMEC	OBJECT IDENTIFIER ::= { olSpecMods 62 }





ol53nnMTDDI	OBJECT IDENTIFIER ::= { olSpecMods 65 }











--

-- Networking groups

--



olNet		OBJECT IDENTIFIER ::= { olNets 1 }

olEnet		OBJECT IDENTIFIER ::= { olNets 2 }

olTRnet		OBJECT IDENTIFIER ::= { olNets 3 }

olFDDInet	OBJECT IDENTIFIER ::= { olNets 4 }





--

-- Workgroup Hub

--



hubSysGroup	   OBJECT IDENTIFIER ::= { workGroupHub 1 }

hardwareGroup	   OBJECT IDENTIFIER ::= { workGroupHub 2 }

softwareGroup	   OBJECT IDENTIFIER ::= { workGroupHub 3 }

hubGroup	   OBJECT IDENTIFIER ::= { workGroupHub 4 }

boardGroup	   OBJECT IDENTIFIER ::= { workGroupHub 5 }

portGroup	   OBJECT IDENTIFIER ::= { workGroupHub 6 }

alarmGroup	   OBJECT IDENTIFIER ::= { workGroupHub 7 }





--

-- Threshold group

--



olThresh	OBJECT IDENTIFIER ::= { olAlarm 1 }



olThreshControl OBJECT IDENTIFIER ::= { olThresh 1 }

















-- The chipGen Group

--

-- Implementation of the chipGen group is mandatory for all agent products.

--

-- The chipGen Group is used by all agent products.  It provides

-- objects that identify what the product is and who is managing it.

--





chipGenProduct OBJECT-TYPE

	SYNTAX INTEGER {

		product-5100M-MGT(1),	-- EMM

		product-5102B-EE(2),	-- OEBM



		product-8383B(3),	-- Midnight

		product-5112H-UTP(4),	-- 12 port Workgroup Hub



		product-5300M-MGT(5),	-- FMM

		product-5200M-MGT(7)	-- TRMM



		,

		product-4112H-MTP(8)	-- ONsemble Ethernet Workgroup Hub



		,

		product-6100M-MGT(12)	-- DMM





	}

	ACCESS read-only

	STATUS mandatory

	DESCRIPTION

		"The product type represented by this agent."

	::= { chipGen 1 }



chipGenServiceDate OBJECT-TYPE

	SYNTAX DisplayString (SIZE(6))

	ACCESS read-only

	STATUS mandatory

	DESCRIPTION

		"The date that the product was last serviced in the

		format yymmdd.  If this date is unknown, the value of this

		object is '000000'."

	::= { chipGen 2 }



chipGenNetman OBJECT-TYPE

	SYNTAX IpAddress

	ACCESS read-only

	STATUS mandatory

	DESCRIPTION

		"The IP (source) Address of the last authenticated SNMP PDU

		received by this entity before this request.  An IP Address

		of 00.00.00.00 represents the default value."

	::= { chipGen 3 }



chipGenDiagnostics OBJECT-TYPE

	SYNTAX INTEGER {

		passed(1),

		failed(2)

	}

	ACCESS read-only

	STATUS mandatory

	DESCRIPTION

		"The result of this product's diagnostic test(s).  If

		any test fails, this will have the failed(2) value.

		Note, many products do not operate after a diagnostic

		failure.  In this case, no SNMP communication would

		be available."

	::= { chipGen 4 }



chipGenSerial OBJECT-TYPE

	SYNTAX DisplayString (SIZE(1..128))

	ACCESS read-only

	STATUS mandatory

	DESCRIPTION

		"The serial number of this product."

	::= { chipGen 5 }



chipGenID OBJECT-TYPE

	SYNTAX INTEGER

	ACCESS read-write

	STATUS mandatory

	DESCRIPTION

		"A unique ID used for grouping disparate agents together.

		For example, a concentrator may contain multiple agents.

		This ID is could be assigned by the management station

		to identify all of these agents as being contained in the

		same concentrator."

	::= { chipGen 6 }



chipGenVers OBJECT-TYPE

	SYNTAX DisplayString (SIZE(0..80))

	ACCESS read-only

	STATUS mandatory

	DESCRIPTION

		"The version identifier(s) for this agent."

	::= { chipGen 7 }



chipGenAuthFailureAddr OBJECT-TYPE

	SYNTAX IpAddress

	ACCESS read-only

	STATUS mandatory

	DESCRIPTION

		"The source IP Address of the last SNMP request that caused

		an authentication failure trap to be generated. This

		object is also included in the SNMP authenticationFailure

		trap."

	::= { chipGen 8 }



chipGenTimeLastChanged OBJECT-TYPE

	SYNTAX TimeTicks

	ACCESS read-only

	STATUS mandatory

	DESCRIPTION

		"A snapshot of sysUpTime when the last trap was generated.

		This attribute can be used to save polling by a management

		station.  If there have been no traps generated since the last

		poll, there is no need for the station to poll again."

	::= { chipGen 9 }





-- The chipEcho Group

--

-- Implementation of the chipEcho group is mandatory for all agent

-- products.

--

-- The chipEcho Group is used by a station to initiate a Ping from

-- this agent to the address denoted by chipEchoAddr.  When all of

-- the pings are sent, the agent issues a ping trap (enterprise specific)

-- reporting the total number of responses received at that time.

--

-- To ping another host, you must minimally set the chipEchoAddr to the

-- host that you want to ping and chipEchoStart to startEcho(2).  The

-- other objects let you change the characteristic of the Ping packets.

-- Note that only one Ping can be processed at a time.

--



chipEchoStart OBJECT-TYPE

	SYNTAX INTEGER {

		noEcho(1),

		startEcho(2)

		}

	ACCESS read-write

	STATUS mandatory

	DESCRIPTION

		"Setting chipEchoStart to startEcho(2) causes the device

		to begin an ICMP echo sequence using the parameters

		indicated by the rest of the chipEcho group."

	::= { chipEcho 1 }



chipEchoAddr OBJECT-TYPE

	SYNTAX IpAddress

	ACCESS read-write

	STATUS mandatory

	DESCRIPTION

		"The IP Address to which the device will ping.  This object can

	only be set to valid unicast class A, class B, or class C addresses. The

	default IP Address is loopback (127.0.0.1)."

	::= { chipEcho 2 }



chipEchoPattern OBJECT-TYPE

	SYNTAX INTEGER {

		zeroes(1),

		ones(2),

		mixed(3)

		}

	ACCESS read-write

	STATUS mandatory

	DESCRIPTION

		"The actual pattern to be contained in the ICMP echo packet."

	::= { chipEcho 3 }





chipEchoNumber OBJECT-TYPE

	SYNTAX INTEGER (1..255)

	ACCESS read-write

	STATUS mandatory

	DESCRIPTION

		"The number of ICMP echo packets (pings) to send."

	::= { chipEcho 4 }





chipEchoSize OBJECT-TYPE

	SYNTAX INTEGER (64..1500)

	ACCESS read-write

	STATUS mandatory

	DESCRIPTION

		"The size of the ICMP echo packet (ping) to send when

		chipEchoStart is set. The valid range is between 64 and

		1500 octets."

	::= { chipEcho 5 }



chipEchoResponseCounts OBJECT-TYPE

	SYNTAX Counter

	ACCESS read-only

	STATUS mandatory

	DESCRIPTION

		"The count of ICMP echo response packets received since

		the last PING was initiated. "

	::= { chipEcho 6 }







-- The ONline Concentrator Groups:

--

-- The following groups are specific to the Concentrator product family.

--



-- The olAgents Group:



-- This group is mandatory for all agents that exist in the concentrator.

--

-- The master management module(s) indicate all of the other SNMP agents

-- present in the concentrator.  The olAgents group is also used

-- by each agent to indicate his own agent status, whether master or not.

--



olAgentsMySlot OBJECT-TYPE

	SYNTAX INTEGER

	ACCESS read-only

	STATUS mandatory

	DESCRIPTION

		"The slot id of this agent."

	::= { olAgents 1 }



olAgentsMasterReset OBJECT-TYPE

	SYNTAX  INTEGER {

		noReset(1),

		reset(2)

		}

	ACCESS read-write

	STATUS mandatory

	DESCRIPTION

		"Resetting mastership causes a new mastership election to

		occur. The agent with the highest mastership priority will

		become the new master.  If there is more than one agent

		with the highest priority, the selection between

		those agents will be arbritrary."

	::= { olAgents 2 }



olAgentsTable OBJECT-TYPE

	SYNTAX  SEQUENCE OF OlAgentsEntry

	ACCESS  not-accessible

	STATUS  mandatory

	DESCRIPTION

		"A table of agents in the concentrator as seen by

		this agent.  A master will see all the agents; a slave

		will only see itself."

	::= { olAgents 3 }



olAgentsEntry OBJECT-TYPE

	SYNTAX  OlAgentsEntry

	ACCESS  not-accessible

	STATUS  mandatory

	DESCRIPTION

		"A profile of an agent within the concentrator."

	INDEX	{ olAgentsSlotIndex }

	::= { olAgentsTable 1 }



OlAgentsEntry ::=

	SEQUENCE {

		olAgentsSlotIndex

			INTEGER,

		olAgentsStationAddr

			OCTET STRING,

		olAgentsIpAddress

			IpAddress,

		olAgentsMasterStatus

			INTEGER,

		olAgentsMasterPriority

			INTEGER,

		ocAgentsSubSlot

			INTEGER

		}



olAgentsSlotIndex OBJECT-TYPE

	SYNTAX  INTEGER

	ACCESS  read-only

	STATUS  mandatory

	DESCRIPTION

		"The slot number that identifies the referenced agent."

	::= { olAgentsEntry 1 }



olAgentsStationAddr OBJECT-TYPE

	SYNTAX  OCTET STRING (SIZE(6))

	ACCESS  read-only

	STATUS  mandatory

	DESCRIPTION

		"The unique identifier for this agent.  Often this

		is the value of ifPhysAddress for the first interface."

	::= { olAgentsEntry 2 }



olAgentsIpAddress OBJECT-TYPE

	SYNTAX  IpAddress

	ACCESS  read-only

	STATUS  mandatory

	DESCRIPTION

		"An IP Address that can be used to communicate to

		this agent.  Note, this object's value may change

		as the agent switches to different sub-networks."

	::= { olAgentsEntry 3 }



olAgentsMasterStatus OBJECT-TYPE

	SYNTAX INTEGER {

		master(1),

		non-master(2), -- slave

		electing(3)

		}

	ACCESS read-only

	STATUS mandatory

	DESCRIPTION

		"The mastership status of this agent."

	::= { olAgentsEntry 4 }



olAgentsMasterPriority OBJECT-TYPE

	SYNTAX INTEGER {

		one(1),		-- lowest

		two(2),

		three(3),

		four(4),

		five(5),

		six(6),

		seven(7),

		eight(8),

		nine(9),

		ten(10),	-- highest

		never(11)

		}

	ACCESS read-write

	STATUS mandatory

	DESCRIPTION

		"The mastership priority of this agent.  Ten is the

		highest and one is the lowest.  Never means will not

		be able become master.  Some agents do not have the

		capability to become master (the etherent to ethernet bridge,

		e.g.) and setting those agents to a value other than

		never(11) will generate an invalid value error.  Priority is

		only used when an election occurs.  Mastership is not

		pre-emptive; use the reset mastership command

		(olAgentsMasterReset)."

	::= { olAgentsEntry 5 }



ocAgentsSubSlot OBJECT-TYPE

	SYNTAX INTEGER

	ACCESS read-only

	STATUS mandatory

	DESCRIPTION

		"The subslot index for this agent.  For agents not located

		in the ONcore system, this object will always

		return 1 for this object value."

	::= { olAgentsEntry 6 }





-- The olConc Group:



-- This group is mandatory for all devices that are acting as a concentrator

-- master.

--

-- The olConc group contains information and control relative to

-- the concentrator.

--



olConcType OBJECT-TYPE

	SYNTAX INTEGER {

		hub-5017C(1),

		hub-5006C(2),

		hub-5006C-FT(3),	-- 6 slot with flag board

		hub-5006C-HC(4),	-- 6-slot with hidden controller

		hub-5006C-HC-FT(5),	-- 6-slot with both

		hub-6017C-A(6)		-- 17-slot with ring backplane



		,

		hub-4112-HMTP(7)	-- Ethernet Rack 'em / Stack 'em hub





		,

		hub-5017C-LS(9)		-- 17-slot load-sharing hub





	}

	ACCESS read-only

	STATUS mandatory

	DESCRIPTION

		"This object identifies the type of concentrator represented

		by this agent."

	::= { olConc 1 }



olConcReset OBJECT-TYPE

	SYNTAX INTEGER {

		noReset(1),

		reset(2)

		}

	ACCESS read-write

	STATUS mandatory

	DESCRIPTION

		"Setting this value to reset(2) causes this concentrator to

		reset. "

	::= { olConc 2 }



olConcNumSlots OBJECT-TYPE

	SYNTAX INTEGER

	ACCESS read-only

	STATUS mandatory

	DESCRIPTION

		"The number of slots in this concentrator.  This value is

		the sum total of all payload slots plus any slots reserved

		for controller modules.  For example, for an ONcore agent

		operating in a 17-slot ONcore hub, this object will have

		the value 19 (17 payload slots plus 2 controller slots).

		Similarly, if an ONline hub contains a hidden controller,

		then this object will have the value 7 (the hidden

		controller does not actually occupy a main slot in the

		6-slot concentrator, but it will report itself as slot 7).

		Also, for an ONline agent operating in an ONcore hub,

		this object's value will not exceed 17."

	::= { olConc 3 }



olConcProfile OBJECT-TYPE

	SYNTAX OCTET STRING (SIZE(1..3))

	ACCESS read-only

	STATUS mandatory

	DESCRIPTION

		"A bit string where the least significant bit corresponds to

		slot 1.  A '1' in the bit indicates that a module is present

		in that slot.  The number of octets provided is based on

		the olConcNumSlots value divided by 8.  Any extra bits

		(for example, bits 18-24 for 17 slots) are meaningless.



		For example, the string 0x01 0xFF 0xFF would represent

		a full 17 slot concentrator."

	::= { olConc 4 }





-- The olEnv Group



-- This group represents the concentrator's environment.  It is available

-- from agents that are acting as a concentrator master.



olEnvTempStatus OBJECT-TYPE

	SYNTAX INTEGER {

		okay(1),

		extremeTemp(2),

		warning(3)

		}

	ACCESS read-only

	STATUS mandatory

	DESCRIPTION

		"The overall temperature status for this concentrator.

		This object's value is an aggregate of all the temperature

		probes in the concentrator, such that, when at least one probe

		reports extreme temperature, this object will have the value

		extremeTemp(2).  This object will have the value warning(3)

		prior to reporting the value extremeTemp(2) as a means of

		warning of a possible hub overheat condition."

    ::= { olEnv 1 }



olEnvPSCapacity OBJECT-TYPE

	SYNTAX INTEGER

	ACCESS read-only

	STATUS mandatory

	DESCRIPTION

		"The total capacity of power supplies for this concentrator."

	::= { olEnv 2 }



olEnvPSTable OBJECT-TYPE

	SYNTAX SEQUENCE OF OlEnvPSEntry

	ACCESS not-accessible

	STATUS mandatory

	DESCRIPTION

		"A table that contains information about each potential

		power supply in the concentrator."

	::= { olEnv 3 }





olEnvPSEntry OBJECT-TYPE

	SYNTAX OlEnvPSEntry

	ACCESS not-accessible

	STATUS mandatory

	DESCRIPTION

		"A list of information for each power supply in the

		concentrator."

	INDEX { olEnvPSIndex }

	::= { olEnvPSTable 1 }



OlEnvPSEntry ::=

	SEQUENCE {

		olEnvPSIndex

			INTEGER,

		olEnvPSAdminState

			INTEGER,

		olEnvPSOperStatus

			INTEGER

		}



olEnvPSIndex OBJECT-TYPE

	SYNTAX INTEGER

	ACCESS read-only

	STATUS mandatory

	DESCRIPTION

		"Identifies the power supply for which this entry contains

		power supply information.  For systems with the

		primary and backup power supply (as opposed to

		the N+1 design), index 1 refers to the primary,

		and index 2 refers to the backup. "

	::= { olEnvPSEntry 1 }



olEnvPSAdminState OBJECT-TYPE

	SYNTAX INTEGER {

		activate(1),

		standby(2)

		}

	ACCESS read-write

	STATUS mandatory

	DESCRIPTION

		"The current desired state of the power supply.  A power

		supply in standby does not provide power to the concentrator.

		Note, in a Load Sharing Hub, this object is read only."

	::= { olEnvPSEntry 2 }



olEnvPSOperStatus OBJECT-TYPE

	SYNTAX INTEGER {

		active(1),

		standby(2),

		faulty(3),

		not-installed(4)

		}

	ACCESS read-only

	STATUS mandatory

	DESCRIPTION

		"The current operational state of the power supply.  A power

		supply in standby does not provide power to the concentrator."

	::= { olEnvPSEntry 3 }



olEnvFanStatus OBJECT-TYPE

	SYNTAX INTEGER {

		okay(1),

		faulty(2),

		not-installed(4),

		unknown(5)

		}

	ACCESS read-only

	STATUS mandatory

	DESCRIPTION

		"The overall status of the fan(s).  When fan operational

		status is known, this object's value is an aggregate of

		all fan status in the concentrator such that, when at

		least one fan unit is faulty, this object will have the

		value faulty(2)."

	::= { olEnv 4 }





olEnvTable OBJECT-TYPE

	SYNTAX SEQUENCE OF OlEnvEntry

	ACCESS not-accessible

	STATUS mandatory

	DESCRIPTION

		"A table that contains information about the concentrator

		environment."

	::= { olEnv 5 }



olEnvEntry OBJECT-TYPE

	SYNTAX OlEnvEntry

	ACCESS not-accessible

	STATUS mandatory

	DESCRIPTION

		"A list of information for each monitored component in this

		concentrator."

	INDEX { olEnvType }

	::= { olEnvTable 1 }



OlEnvEntry ::=

	SEQUENCE {

		olEnvType

			INTEGER,

		olEnvStatus

			INTEGER

		}



olEnvType OBJECT-TYPE

	SYNTAX INTEGER {

		ls-pdb(1)		  --- Online load-sharing hub PDB

		}

	ACCESS read-only

	STATUS mandatory

	DESCRIPTION

		"The type of hardware component monitored in this

		concentrator."

	::= { olEnvEntry 1 }



olEnvStatus OBJECT-TYPE

	SYNTAX INTEGER {

		okay(1),

		faulty(2)

		}

	ACCESS read-only

	STATUS mandatory

	DESCRIPTION

		"The status of the monitored hardware component."

	::= { olEnvEntry 2 }





-- The olModules group



-- This group represents the information as seen by what is currently known

-- as the concentrator master.  If the module is not a master, this group

-- is not represented.  These tables have dynamic instances, that is,

-- if the module does not exist in the concentrator, the tables are empty.

-- No excess information is presented.

--

-- If the agent is an ONcore management module, the modules that exist

-- in subslot 1 (that is, the motherboard) will have an instance in the

-- olModTable

--



olModTable OBJECT-TYPE

	SYNTAX SEQUENCE OF OlModEntry

	ACCESS not-accessible

	STATUS mandatory

	DESCRIPTION

		"A table that contains generic information about every

		module that is present within the concentrator.

		If the concentrator is the ONcore Hub, then only the

		motherboard is present in this table."

	::= { olModules 1 }



olModEntry OBJECT-TYPE

	SYNTAX OlModEntry

	ACCESS not-accessible

	STATUS mandatory

	DESCRIPTION

		"A list of information for each module in the concentrator.

		If the concentrator is the ONcore Hub, then only the

		motherboard is present in this table."

	INDEX { olModSlotIndex }

	::= { olModTable 1 }



OlModEntry ::=

	SEQUENCE {

		olModSlotIndex

			INTEGER,

		olModType

			INTEGER,

		olModClass

			INTEGER,

		olModDescr

			DisplayString,

		olModVersion

			DisplayString,

		olModVendor

			INTEGER,

		olModResetModule

			INTEGER,

		olModConfigToDips

			INTEGER,

		olModConfigured

			INTEGER,

		olModNetwork

			INTEGER,

		olModNetworkType

			INTEGER,

		olModStatus

			INTEGER,

		olModNumPorts

			INTEGER,

		olModNumTrunks

			INTEGER



		}



olModSlotIndex OBJECT-TYPE

	SYNTAX INTEGER

	ACCESS read-only

	STATUS mandatory

	DESCRIPTION

		"The unique slot number of this module.  Its value ranges

		between 1 and olConcNumSlots and remains constant at

		least from one re-initialization of the entity's network

		management system to the next re-initialization."

	::= { olModEntry 1 }



olModType OBJECT-TYPE

	SYNTAX INTEGER {

		module-unmanageable(1), -- not manageable

		module-unknown(2),	-- only generically manageable

		module-50nnM-CTL(3),	-- Controller

		module-51nnM-MGT(4),	-- Ethernet Management

		module-51nnM-FIB(5),	-- Ethernet Fiber

		module-51nnM-UTP(6),	-- Ethernet 10BASE-T

		module-51nnM-TP(7),	-- Ethernet 10BASE-T

		module-51nnM-BNC(8),	-- Ethernet BNC

		module-51nnB-EE(9),	-- OEBM

		module-51nnR-ES(10),	-- Cisco Serial

		module-51nnR-EE(11),	-- Cisco Ethernet

		module-51nnM-AUIF(12),  -- Ethernet AUI Female

		module-51nnM-AUIM(13),  -- Ethernet AUI Male

		module-5208M-TP(14),	-- Token Ring 8-port MAU module

		module-51nnM-FP(15),	-- Ethernet Fiber port switching

		module-51nnM-FBP(16),	-- Ethernet 10BASE-F port switching

		module-51nnM-TPL(17),	-- Ethernet 10BASE-T

		module-51nnM-TPPL(18),  -- Ethernet 10BASE-T port switching

		module-52nnM-TP(19),	-- Token Ring Media Module

		module-52nnM-FR(20),	-- Token Ring FiberOptic Repeater

		module-51nnM-TS(21),	-- Ethernet Terminal Server

		module-51nnM-FL(22),	-- Ethernet FOIRL

		module-50nnM-RCTL(23),  -- Redundant Controller

		module-51nnM-FB(24),	-- Ethernet 10BASE-F

		module-53nnM-MGT(25),	-- FDDI managment module (FMM)

		module-53nnM-FBMIC(26), -- FDDI media w/ fiber ANSI MIC conn.

		module-53nnM-FIBST(27), -- FDDI media w/ fiber ST conn.

		module-53nnM-STP(28),	-- FDDI w/ shielded copper DB9 conn.

		module-51nnM-TPCL(29),  -- Ethernet 10BASE-T per-connector

		module-52nnB-TT(30),	-- Token Ring Bridge

		module-51nnI-x(31),	-- Ethernet Interconnect Module

		module-52nnM-MGT(32),	-- Token Ring Management

		module-50nnM-HCTL(33),  -- Hidden Controller

		module-61nnM-CAR(35),	-- Ethernet Carrier Module



		module-60nnM-MGT(43),	-- Distributed Management Module



		module-61nnD-MGT(45),	-- Ethernet MAC monitor card

		module-61nnM-FBP(46),	-- Ethernet 10-port per-port switchable fiber

		module-61nnM-TPL(47),	-- Ethernet 24-port per-port switching

		module-51nnM-TPLS(48),  -- Ethernet 10BASE-T Security Module

		module-60nnM-RCTL(50),  -- ONcore Ctlr (managed by ONcore mgmt)



		module-50nnM-RCLS(51),  -- Load Sharing Redundant Controller





		module-41nnH-MTP(52),	-- ONsemble Ethernet Management Unit

		module-41nnH-ETP(53),	-- ONsemble Ethernet Base Unit







		module-52nnM-EC(62)	-- 3174 Establistment Controller



		,

		module-53nnM-TDDI(65)	-- FDDI w/ copper RJ45 conn.











		}

	ACCESS read-only

	STATUS mandatory

	DESCRIPTION

		"The unique type identifier for this module.  This type

		is used to identify the branch in olSpecMods (see below).



		module-unmanageable(1) means that only the following

		objects are valid for this module:



			olModSlotIndex

			olModClass

			olModVersion

			olModVendor

			olModReset

			olModConfigToDips

			olModConfigured



		module-unknown(2) means that all the generic attributes

		are manageable, but there is no olSpecMods branch

		for this module as viewed by this agent."

		::= { olModEntry 2 }



olModClass OBJECT-TYPE

	SYNTAX INTEGER {

		controller(1),

		mgmt(2),

		ethernet-media(3),

		ethernet-interconnect(4),

		ethernet-portswitching-media(5),

		token-ring-media(6),

		terminal-server(7),

		fddi-media(8),

		token-ring-mgmt(9),

		ethernet-connswitching-media(10),

		token-ring-interconnect(11),

		fddi-mgmt(12),

		oncore-token-ring-media(13),

		ethernet-carrier(14),

		oncore-oem-specials(15),



		oncore-download(17),



		ethernet-media-extended(19),

		online-token-ring-mod-interconnect(20)







		}

	ACCESS read-only

	STATUS mandatory

	DESCRIPTION

		"The class of this module.  Generally speaking, this

		object indicates the kind of module.  Specifically,

		the class identifier specifies the internal representation

		of the module's managed information base."

	::= { olModEntry 3 }



olModDescr OBJECT-TYPE

	SYNTAX DisplayString (SIZE(1..128))

	ACCESS read-only

	STATUS mandatory

	DESCRIPTION

		"A textual string containing information about the module."

	::= { olModEntry 4 }



olModVersion OBJECT-TYPE

	SYNTAX DisplayString (SIZE(1..32))

	ACCESS read-only

	STATUS mandatory

	DESCRIPTION

		"The software version number of this module.  "

	::= { olModEntry 5 }



olModVendor OBJECT-TYPE

	SYNTAX INTEGER {

		chipcom(1),

		cisco(2),

		pilkington(3),

		datability(5),

		ibm(6),

		raycom(7),

		retix(8),

		intellicom(9)

		}

	ACCESS read-only

	STATUS mandatory

	DESCRIPTION

		"The actual manufacturer of this board."

	::= { olModEntry 6 }



olModResetModule OBJECT-TYPE

	SYNTAX INTEGER {

		noReset(1),

		reset(2)

		}

	ACCESS read-write

	STATUS mandatory

	DESCRIPTION

		"Setting this object to reset(2) causes this module to reset."

	::= { olModEntry 7 }



olModConfigToDips OBJECT-TYPE

	SYNTAX INTEGER {

		noConfigure(1),

		configure(2)

		}

	ACCESS read-write

	STATUS mandatory

	DESCRIPTION

		"Setting this object to configure(2) causes this module to

		configure based on the dip switch settings."

	::= { olModEntry 8 }



olModConfigured OBJECT-TYPE

	SYNTAX INTEGER {

		notConfigured(1),

		configured(2)

		}

	ACCESS read-only

	STATUS mandatory

	DESCRIPTION

		"This object indicates whether this module has already been

		configured.  An unconfigured module is configured to a safe

		state where the network is isolated and the ports are

		disabled."

	::= { olModEntry 9 }





olModNetwork OBJECT-TYPE

	SYNTAX INTEGER {

		other(1),

		isolated(2),

		port-switching(3),

		front-panel(5),

		ethernet-1(6),

		ethernet-2(7),

		ethernet-3(8),

		token-ring-1(9),

		token-ring-2(10),

		token-ring-3(11),

		token-ring-4(12),

		token-ring-5(13),

		token-ring-6(14),

		token-ring-7(15),

		fddi-1(16),

		fddi-2(17),

		fddi-3(18),

		fddi-4(19),

		per-connector(20),

		isolated-1(21),		-- for modules with multiple

		isolated-2(22),		-- isolated networks within the module

		isolated-3(23),

		isolated-4(24),

		isolated-5(25),

		isolated-6(26),

		isolated-7(27),

		isolated-8(28),

		isolated-9(29),

		isolated-10(30),

		isolated-11(31),

		ethernet-4(32),		-- Available in ONcore.

		ethernet-5(33),

		ethernet-6(34),

		ethernet-7(35),

		ethernet-8(36)



		}

	ACCESS read-write

	STATUS mandatory

	DESCRIPTION

		"The network that this module is attached to.  If the

		value is other(1) or port-switching(3), setting this object

		to a different value will generate the invalidData error.



		If the value is port-switching(3), manage the networks via

		the olPortNetwork object.



		The value per-connector(20) is returned if the managed

		module is a per-connector switchable and the connectors are on

		different networks.  The connector networks are managed

		by the objects defined in the olSpecMods branch

		specified for this module.



		Modules and ports on the same network intercommunicate.

		Setting the module to isolated(2) (or other isolated values),

		removes this module from the backplane.



		Setting this module to a value that is not the same

		protocol type will return an invalidData error.



		Setting this module to a value that it does not support

		will return an invalidData error."

	::= { olModEntry 10 }



olModNetworkType OBJECT-TYPE

	SYNTAX INTEGER {

		other(1),	    -- other only

		port-switching(3),  -- use olPortNetwork

		ethernet(5),	    -- ethernet 1-3 or 1-8, isolated

		token-ring(6), -- token-ring 1-7, isolated,



		fddi(7),	    -- fddi 1-4, isolated

		serial(8)	    -- front or isolated only

		}

	ACCESS read-only

	STATUS mandatory

	DESCRIPTION

		"The network type of this module.  port-switching(3)

		means that the network type differs depending on the

		port (like the router module). The network type reflects

		the valid values for olModNetwork."

	::= { olModEntry 11 }



olModStatus OBJECT-TYPE

	SYNTAX INTEGER {

		okay(1),

		fatalError(10),

		booting(20),

		partial-failure(21)

		}

	ACCESS read-only

	STATUS mandatory

	DESCRIPTION

		"The module's status."

	::= { olModEntry 12 }



olModNumPorts OBJECT-TYPE

	SYNTAX INTEGER

	ACCESS read-only

	STATUS mandatory

	DESCRIPTION

		"The number of ports on this module.  Note, ports may be

		physical ports like 10BASE-T ports, or logical, like

		the bridge module ports."

	::= { olModEntry 13 }



olModNumTrunks OBJECT-TYPE

	SYNTAX INTEGER

	ACCESS read-only

	STATUS mandatory

	DESCRIPTION

		"The number of trunks on this module.  Note, trunks

		are links that are, by definition, backbone connections.

		Examples of trunks are ring in and ring out ports for

		token ring, and the connections for rings to the backplane."

	::= { olModEntry 14 }





--

-- Generic Port Table

--



olPortTable OBJECT-TYPE

	SYNTAX SEQUENCE OF OlPortEntry

	ACCESS not-accessible

	STATUS mandatory

	DESCRIPTION

		"A table that contains generic information about

		each port on each module present within the concentrator."

	::= { olModules 2 }



olPortEntry OBJECT-TYPE

	SYNTAX OlPortEntry

	ACCESS not-accessible

	STATUS mandatory

	DESCRIPTION

		"A list of information about each port in the

		concentrator."

	INDEX { olPortSlotIndex, olPortIndex }

	::= { olPortTable 1}



OlPortEntry ::=

	SEQUENCE {

		olPortSlotIndex

			INTEGER,

		olPortIndex

			INTEGER,

		olPortType

			INTEGER,

		olPortConnector

			INTEGER,

		olPortStatus

			INTEGER,

		olPortAdminState

			INTEGER,

		olPortNetwork

			INTEGER,

		olPortNetworkType

			INTEGER,

		olPortAlertFilter

			INTEGER

		}



olPortSlotIndex OBJECT-TYPE

	SYNTAX INTEGER

	ACCESS read-only

	STATUS mandatory

	DESCRIPTION

		"The slot number of this port's module."

	::= { olPortEntry 1 }



olPortIndex OBJECT-TYPE

	SYNTAX INTEGER

	ACCESS read-only

	STATUS mandatory

	DESCRIPTION

		"The port number of this port within this module."

	::= { olPortEntry 2 }



olPortType OBJECT-TYPE

	SYNTAX INTEGER {

		logical(1),	-- oebm's ports for example

		media(2),	-- normal ports

		virtual(5)	-- oets'  ports for example

		}

	ACCESS read-only

	STATUS mandatory

	DESCRIPTION

		"The type of port.  logical(1) is used to manage

		port resources that may not map directly to physical

		connections.  The OEBM, for example, has two logical

		ports, although those two ports can be assigned to

		different combinations of four physical connections.

		media(2) refers to ports such as those on the 10BASE-T

		module. "

	::= { olPortEntry 3 }





olPortConnector OBJECT-TYPE

	SYNTAX INTEGER {

		backPlane(1),		-- connects directly to backplane

		bnc(2),			-- thinnet

		faui(3),		-- female aui

		maui(4),		-- male aui

		fiber(5),		-- fiber connector

		db-50(6),		-- serial port

		telco(7),		-- 50 pin connector

		rj45(8),		-- unshielded

		rj45S(9),		-- shielded

		db-9(10),		-- 9 pin connector

		virtual(11),		-- e.g. terminal server port

		fddi-lc(12),		-- low cost connector

		fddi-st(13),		-- ST type connector

		fddi-mic(14),		-- MIC connector

		db-25(15),		-- 25 pin d-shell connector

		ethernet-sma(17),	-- SMA fiber connector

		ethernet-fc(23),	-- FC fiber connector

		ethernet-st(24)		-- ST fiber connector

		}

	ACCESS read-only

	STATUS mandatory

	DESCRIPTION

		"The connector type of this port."

	::= { olPortEntry 4 }



olPortStatus OBJECT-TYPE

	SYNTAX INTEGER {

		okay(1),

		linkFailure(2),

		jabber(3),

		remoteLinkFailure(4),

		remoteJabber(5),

		invalidData(6),

		lowLight(7),

		fifoOverrun(8),

		fifoUnderrun(9),

		fatalError(10),

		partition(11),

		mjlp(12),

		noCable(13),

		noSquelch(14),

		noPhantom(15),

		okay-standby(19),

		off(22),

		connecting(23),

		backup-link(24),

		security-breach(25),

		unknownStatus(26),

		beacon(27),

		wireFault(28),

		macRemoved(29),

		notInserted(30),

		speedMismatch(31),

		attach3174Unknown(32),

		attach3174To8-3299(33),

		attach3174To32-3299(34),

		attach3174ToDirect(35),

		attach3174Unavailable(36),

		transientError(37)





		}

	ACCESS read-only

	STATUS mandatory

	DESCRIPTION

		"The status of this port."

	::= { olPortEntry 5 }



olPortAdminState OBJECT-TYPE

	SYNTAX INTEGER {

		enabled(1),	      -- only valid value for class 2&4 modules

		disabled(2),

		redundant-primary(3), -- use olSpecMods to set

		redundant-backup(4),  -- redundancy buddys

		redundant-rfs(5),     -- used by FOIRL only

		local(6),	      -- terminal server only

		remote(7),	      -- terminal server only

		remote-diagnostics(8),

		unknown(9)

		}

	ACCESS read-write

	STATUS mandatory

	DESCRIPTION

		"The desired state of this port.  Setting a port to be

		redundant-primary(3) or redundant-backup requires that the

		buddy slot and buddy port also be set to valid values

		(see appropriate olSpecMods objects).  If the

		values associated with the redundant buddys

		are not valid, a genError will be returned.  If the port

		is already redundant, an invalid set may result in both

		ports being disabled."

	::= { olPortEntry 6 }



olPortNetwork OBJECT-TYPE

	SYNTAX INTEGER {

		other(1),

		isolated(2),

		per-module(4),

		front-panel(5),

		ethernet-1(6),

		ethernet-2(7),

		ethernet-3(8),

		token-ring-1(9),

		token-ring-2(10),

		token-ring-3(11),

		token-ring-4(12),

		token-ring-5(13),

		token-ring-6(14),

		token-ring-7(15),

		fddi-1(16),

		fddi-2(17),

		fddi-3(18),

		fddi-4(19),

		per-connector(20),

		isolated-1(21),		-- for modules with multiple

		isolated-2(22),		-- isolated networks within the module

		isolated-3(23),

		isolated-4(24),

		isolated-5(25),

		isolated-6(26),

		isolated-7(27),

		isolated-8(28),

		isolated-9(29),

		isolated-10(30),

		isolated-11(31),

		ethernet-4(32),

		ethernet-5(33),

		ethernet-6(34),

		ethernet-7(35),

		ethernet-8(36)



		}

	ACCESS read-write

	STATUS mandatory

	DESCRIPTION

		"The network that this port is attached to.



		If the value of olPortNetwork is per-module(4),

		then use the olModNetwork to manage this port.

		Setting olPortNetwork to a different value in this

		case will generate the invalidData error.



		Setting this port to a value that is not the same protocol

		type will return invalidData error.  front-panel(5) is used for

		modules that have a logical port and a physical front

		connection. An example of this is the Eth2Eth Bridge module.



		Setting this port to a value that it does not support will

		generate an invalidData error."

	::= { olPortEntry 7 }



olPortNetworkType OBJECT-TYPE

	SYNTAX INTEGER {

		other(1),	-- other only

		ethernet(5),	-- ethernet 1-3, isolated



		fddi(7),	-- fddi 1-4, isolated

		serial(8)	-- front or isolated only

		}

	ACCESS read-only

	STATUS mandatory

	DESCRIPTION

		"The network type of this port.  The type reflects the

		valid values for olPortNetwork. "

	::= { olPortEntry 8 }



olPortAlertFilter OBJECT-TYPE

	SYNTAX INTEGER {

		enable(1),

		disable(2),

		other(3)

		}

	ACCESS read-write

	STATUS mandatory

	DESCRIPTION

		"Enabling this object for a port will allow the

		generation of port up (or port down) traps for port status

		transitions caused by end stations powering up (or down).

		Disabling this object will suppress the generation of port up

		(or port down) traps for a port.



		Note that this object is used in the trap generation decision

		only if chipAlertMode, an object in chipAlertTable, is set

		to filter(3).



		Some ports, such as integrated bridge or router ports

		do not support this feature. A getRequest on one of these

		types of  ports will return a value of other(3), and a

		setRequest to enable(1) or disable(2) will return

		the invalidData object. "

	::= { olPortEntry 9 }



--

-- Trunk Table

--



olTrunkTable OBJECT-TYPE

	SYNTAX SEQUENCE OF OlTrunkEntry

	ACCESS not-accessible

	STATUS mandatory

	DESCRIPTION

		"A table that contains generic information about

		each trunk on each module present within the concentrator."

	::= { olModules 3 }



olTrunkEntry OBJECT-TYPE

	SYNTAX OlTrunkEntry

	ACCESS not-accessible

	STATUS mandatory

	DESCRIPTION

		"A list of information about each trunk in the

		concentrator."

	INDEX { olTrunkSlotIndex, olTrunkIndex }

	::= { olTrunkTable 1}



OlTrunkEntry ::=

	SEQUENCE {

		olTrunkSlotIndex

			INTEGER,

		olTrunkIndex

			INTEGER,

		olTrunkType

			INTEGER,

		olTrunkConnector

			INTEGER,

		olTrunkStatus

			INTEGER,

		olTrunkAdminState

			INTEGER,

		olTrunkWrapState

			INTEGER,

		olTrunkNeighbor

			INTEGER



		}



olTrunkSlotIndex OBJECT-TYPE

	SYNTAX INTEGER

	ACCESS read-only

	STATUS mandatory

	DESCRIPTION

		"The slot number of this trunk's module."

	::= { olTrunkEntry 1 }



olTrunkIndex OBJECT-TYPE

	SYNTAX INTEGER

	ACCESS read-only

	STATUS mandatory

	DESCRIPTION

		"The trunk number of this trunk."

	::= { olTrunkEntry 2 }



olTrunkType OBJECT-TYPE

	SYNTAX INTEGER {

		other(1),

		ringIn(3),	-- ring access trunks

		ringOut(4),

		backplaneIn(6), -- backplane access

		backplaneOut(7)

		}

	ACCESS read-only

	STATUS mandatory

	DESCRIPTION

		"The type of trunk. ringIn(3) and ringOut(4) refer to special

		trunks on the token ring protocol type modules."

	::= { olTrunkEntry 3 }





olTrunkConnector OBJECT-TYPE

	SYNTAX INTEGER {

		backplane(1),

		fiber(5),	--

		rj45S(9)	-- shielded



		}

	ACCESS read-only

	STATUS mandatory

	DESCRIPTION

		"The connector type of this trunk."

	::= { olTrunkEntry 4 }



olTrunkStatus OBJECT-TYPE

	SYNTAX INTEGER {

		okay(1),

		linkFailure(2),

		fatalError(10),

		noCable(13),

		noSquelch(14),

		lostLock(16),

		upstreamNeighborLost(17),

		invalidConfig(18),



		okay-standby(19),



		beacon(27),

		wireFault(28)



		}

	ACCESS read-only

	STATUS mandatory

	DESCRIPTION

		"The status of this trunk."

	::= { olTrunkEntry 5 }



olTrunkAdminState OBJECT-TYPE

	SYNTAX INTEGER {

		enabled(1),

		disabled(2)



		,

		redundant-primary(3),

		redundant-backup(4)



		}

	ACCESS read-write

	STATUS mandatory

	DESCRIPTION

		"The desired state of this trunk.  Enabling a trunk

		allows the trunk to pass network traffic.  This

		object may be used to configure fiber trunk

		redundancy.  Setting a trunk to be redundant-primary(3)

		or redundant-backup(4) requires that the buddy slot

		be previously set to a valid value (see appropriate

		olSpecMods objects).  If fiber trunk redundancy is

		already configured, setting this object to a

		redundant state will remove the previous configuration."

	::= { olTrunkEntry 6 }



olTrunkWrapState OBJECT-TYPE

	SYNTAX INTEGER {

		wrapped(1),

		unwrapped(2)

		}

	ACCESS read-only

	STATUS mandatory

	DESCRIPTION

		"The wrap state of this trunk.  A trunk can wrap in

		response to a network event such as a break in

		the cable."

	::= { olTrunkEntry 7 }



olTrunkNeighbor OBJECT-TYPE

	SYNTAX INTEGER {

		slot-1(1),

		slot-2(2),

		slot-3(3),

		slot-4(4),

		slot-5(5),

		slot-6(6),

		slot-7(7),

		slot-8(8),

		slot-9(9),

		slot-10(10),

		slot-11(11),

		slot-12(12),

		slot-13(13),

		slot-14(14),

		slot-15(15),

		slot-16(16),

		slot-17(17),

		external(256)

		}

	ACCESS read-only

	STATUS mandatory

	DESCRIPTION

		"The upstream or downstream neighbor of the trunk."

	::= { olTrunkEntry 8 }







-- olSpecMods Group

--

-- This group contains the module and port tables specific to the

-- particular module.  Each module is indexed by the olModType value.

-- For more information, please refer to the MIB information supplied

-- with each module.



-- olSpecMods Group takes the following object identifier format:

--

-- olSpecMods.<type>.<level>.1.<object>.<instance>

--

-- where :

--	<type> ::= the unique number identifying the type of this module

--			see olModType above.

--	<level> ::= module table (1) ||

--		    port table (2)   ||

--		    trunk  (3)       ||

--		    submodule table (6)

--	1	::= branch for entry, i.e. module entry or port entry

--	<object>::= the object ID as indicated in the MIB documentation for

--			this type module.

--	<instance> ::=

--			<slot> for module level ||

--			<slot>.<port> for port level ||

--			<slot>.<trunk> for trunk level ||

--			<slot>.<subslot> for submodule level

--

--

--	The lexicographical ordering for this group is:

--

--	1. To walk through all of the instances associated

--		particular module type.  That is, the group

--		walks through a module type - all slots, before

--		walking to the next module type.  For example, if

--		module type A is in slot 1 & 5, and module type B

--		is in slot 3 (where A < B), then a tree walk would

--		yield A.1, A.3, and then B.3.

--

--	2. To walk through all of the resources of a particular module

--		before walking to the next module.  All ports and trunks

--		of a module are instantiated in the tree before the

--		the next module is instiated.

--

--	3. ONcore modules do not return a module level table, only

--		a submodule level table.

--



--

-- ONline Controller Module

--



ol50nnMCTLModTable OBJECT-TYPE

	SYNTAX SEQUENCE OF Ol50nnMCTLModEntry

	ACCESS not-accessible

	STATUS mandatory

	DESCRIPTION

		"A table that contains information about each 50nnM-CTL

		in the concentrator.  Note, current architecture will

		limit the number of instances to one per concentrator."

	::= { ol50nnMCTL 1 }



ol50nnMCTLModEntry OBJECT-TYPE

	SYNTAX Ol50nnMCTLModEntry

	ACCESS not-accessible

	STATUS mandatory

	DESCRIPTION

		"A list of information for each 50nnM-CTL module

		in the concentrator."

	INDEX { ol50nnMCTLModSlotIndex }

	::= { ol50nnMCTLModTable 1 }



Ol50nnMCTLModEntry ::=

	SEQUENCE {

		ol50nnMCTLModSlotIndex

			INTEGER,

		ol50nnMCTLModTempStatus

			INTEGER

		}



ol50nnMCTLModSlotIndex OBJECT-TYPE

	SYNTAX INTEGER

	ACCESS read-only

	STATUS mandatory

	DESCRIPTION

		"The slot number for this module."

	::= { ol50nnMCTLModEntry 1 }



ol50nnMCTLModTempStatus OBJECT-TYPE

	SYNTAX INTEGER {

		okay(1),

		extremeTemp(2)

		}

	ACCESS read-only

	STATUS mandatory

	DESCRIPTION

		"The temperature as detected by the probes on this module."

	::= { ol50nnMCTLModEntry 2 }





--

-- Ethernet Management Module

--



ol51nnMMGTModTable OBJECT-TYPE

	SYNTAX SEQUENCE OF Ol51nnMMGTModEntry

	ACCESS not-accessible

	STATUS mandatory

	DESCRIPTION

		"A table that contains module information about each

		EMM module in the concentrator."

	::= { ol51nnMMGT 1 }



ol51nnMMGTModEntry OBJECT-TYPE

	SYNTAX Ol51nnMMGTModEntry

	ACCESS not-accessible

	STATUS mandatory

	DESCRIPTION

		"A list of module information for a particular EMM module

		in the concentrator."

	INDEX { ol51nnMMGTModSlotIndex }

	::= { ol51nnMMGTModTable 1 }



Ol51nnMMGTModEntry ::=

	SEQUENCE {

		ol51nnMMGTModSlotIndex

			INTEGER,

		ol51nnMMGTModMasterPriority

			INTEGER,

		ol51nnMMGTModMasterStatus

			INTEGER,

		ol51nnMMGTModStationAddr

			OCTET STRING

		}



ol51nnMMGTModSlotIndex OBJECT-TYPE

	SYNTAX INTEGER

	ACCESS read-only

	STATUS mandatory

	DESCRIPTION

		"The slot number of this module."

	::= { ol51nnMMGTModEntry 1 }



ol51nnMMGTModMasterPriority OBJECT-TYPE

	SYNTAX INTEGER {

		one(1),

		two(2),

		three(3),

		four(4),

		five(5),

		six(6),

		seven(7),

		eight(8),

		nine(9),

		ten(10)

		}

	ACCESS read-write

	STATUS mandatory

	DESCRIPTION

		"The mastership priority of this agent.  Ten is the

		highest and one is the lowest.  Priority is

		only used when an election occurs.  Mastership is not

		preemptive unless the reset mastership command is used."

	::= { ol51nnMMGTModEntry 2 }



ol51nnMMGTModMasterStatus OBJECT-TYPE

	SYNTAX INTEGER {

		master(1),

		non-master(2),

		electing(3)

		}

	ACCESS read-only

	STATUS mandatory

	DESCRIPTION

		"The mastership status of this agent."

	::= { ol51nnMMGTModEntry 3 }



ol51nnMMGTModStationAddr OBJECT-TYPE

	SYNTAX OCTET STRING (SIZE(6))

	ACCESS read-only

	STATUS mandatory

	DESCRIPTION

		"A 6 octet address that uniquely identifies this module.

		The station address is the mac address of port 1.  Note

		that EMMs before v3.0 will have 00-00-00-00-00-00 as their

		station address."

	::= { ol51nnMMGTModEntry 4 }



ol51nnMMGTPortTable OBJECT-TYPE

	SYNTAX SEQUENCE OF Ol51nnMMGTPortEntry

	ACCESS not-accessible

	STATUS mandatory

	DESCRIPTION

		"A table of information that contains port-specific

		information for each port on each 51nnM-MGT module."

	::= { ol51nnMMGT 2 }



ol51nnMMGTPortEntry OBJECT-TYPE

	SYNTAX Ol51nnMMGTPortEntry

	ACCESS not-accessible

	STATUS mandatory

	DESCRIPTION

		"A list of information about a specific port on a

		51nnM-MGT module."

	INDEX { ol51nnMMGTPortSlotIndex, ol51nnMMGTPortIndex }

	::= { ol51nnMMGTPortTable 1 }



Ol51nnMMGTPortEntry ::=

	SEQUENCE {

		ol51nnMMGTPortSlotIndex

			INTEGER,

		ol51nnMMGTPortIndex

			INTEGER,

		ol51nnMMGTIpAddress

			IpAddress

		}



ol51nnMMGTPortSlotIndex OBJECT-TYPE

	SYNTAX INTEGER

	ACCESS read-only

	STATUS mandatory

	DESCRIPTION

		"The slot number of this port's module."

	::= { ol51nnMMGTPortEntry 1 }





ol51nnMMGTPortIndex OBJECT-TYPE

	SYNTAX INTEGER

	ACCESS read-only

	STATUS mandatory

	DESCRIPTION

		"The port number of this port."

	::= { ol51nnMMGTPortEntry 2 }





ol51nnMMGTIpAddress OBJECT-TYPE

	SYNTAX IpAddress

	ACCESS read-only

	STATUS mandatory

	DESCRIPTION

		"The IP Address associated with this port."

	::= { ol51nnMMGTPortEntry 3 }



--

-- ONline Ethernet Synchronous Fiber Module

--





ol51nnMFIBModTable OBJECT-TYPE

	SYNTAX SEQUENCE OF Ol51nnMFIBModEntry

	ACCESS not-accessible

	STATUS mandatory

	DESCRIPTION

		"A table of module-specific information for each

		51nnM-FIB module in the concentrator."

	::= { ol51nnMFIB 1 }



ol51nnMFIBModEntry OBJECT-TYPE

	SYNTAX Ol51nnMFIBModEntry

	ACCESS not-accessible

	STATUS mandatory

	DESCRIPTION

		"A list of module-specific information associated

		with a particular 51nnM-FIB module in the concentrator."

	INDEX { ol51nnMFIBModSlotIndex }

	::= { ol51nnMFIBModTable 1 }



Ol51nnMFIBModEntry ::=

	SEQUENCE {

		ol51nnMFIBModSlotIndex

			INTEGER,

		ol51nnMFIBModDipNetwork

			INTEGER,

		ol51nnMFIBModLLW

			INTEGER,

		ol51nnMFIBModDipLLW

			INTEGER

		}



ol51nnMFIBModSlotIndex OBJECT-TYPE

	SYNTAX INTEGER

	ACCESS read-only

	STATUS mandatory

	DESCRIPTION

		"The slot number of this module."

	::= { ol51nnMFIBModEntry 1 }



ol51nnMFIBModDipNetwork OBJECT-TYPE

	SYNTAX INTEGER {

		isolated(2),

		ethernet-1(6),

		ethernet-2(7),

		ethernet-3(8)

		}

	ACCESS read-only

	STATUS mandatory

	DESCRIPTION

		"The network indicated by the module's dip switches."

	::= { ol51nnMFIBModEntry 2 }



ol51nnMFIBModLLW OBJECT-TYPE

	SYNTAX INTEGER {

		enabled(1),

		disabled(2)

		}

	ACCESS read-write

	STATUS mandatory

	DESCRIPTION

		"The current state of this module's low light warning

		configuration.  Enabling this feature causes the module to

		check for low light and to issue a warning if low light is

		present.  Disabling low light has the advantage of faster

		redundancy switchover in the event of a port error."

	::= { ol51nnMFIBModEntry 3 }



ol51nnMFIBModDipLLW OBJECT-TYPE

	SYNTAX INTEGER {

		enabled(1),

		disabled(2)

		}

	ACCESS read-only

	STATUS mandatory

	DESCRIPTION

		"The low light warning configuration indicated by this module's

		dip switches."

	::= { ol51nnMFIBModEntry 4 }



ol51nnMFIBPortTable OBJECT-TYPE

	SYNTAX SEQUENCE OF Ol51nnMFIBPortEntry

	ACCESS not-accessible

	STATUS mandatory

	DESCRIPTION

		"A table of port-specific information for each port

		of each 51nnM-FIB module."

	::= { ol51nnMFIB 2 }



ol51nnMFIBPortEntry OBJECT-TYPE

	SYNTAX Ol51nnMFIBPortEntry

	ACCESS not-accessible

	STATUS mandatory

	DESCRIPTION

		"A list of information about a specific port on a

		51nnM-FIB module."

	INDEX { ol51nnMFIBPortSlotIndex, ol51nnMFIBPortIndex }

	::= { ol51nnMFIBPortTable 1 }



Ol51nnMFIBPortEntry ::=

	SEQUENCE {

		ol51nnMFIBPortSlotIndex

			INTEGER,

		ol51nnMFIBPortIndex

			INTEGER,

		ol51nnMFIBPortAdminState

			INTEGER,

		ol51nnMFIBPortBuddySlot

			INTEGER,

		ol51nnMFIBPortBuddyPort

			INTEGER,

		ol51nnMFIBPortDipAdminState

			INTEGER

		}



	ol51nnMFIBPortSlotIndex OBJECT-TYPE

	SYNTAX INTEGER

	ACCESS read-only

	STATUS mandatory

	DESCRIPTION

		"The slot number of this port's module."

	::= { ol51nnMFIBPortEntry 1 }





ol51nnMFIBPortIndex OBJECT-TYPE

	SYNTAX INTEGER

	ACCESS read-only

	STATUS mandatory

	DESCRIPTION

		"The port number of this port."

	::= { ol51nnMFIBPortEntry 2 }





ol51nnMFIBPortAdminState OBJECT-TYPE

	SYNTAX INTEGER {

		enabled(1),

		disabled(2),

		redundant-primary(3),

		redundant-backup(4)

		}

	ACCESS read-write

	STATUS mandatory

	DESCRIPTION

		"The desired state of this port.  Setting this port to

		be redundant with invalid settings of buddy slot and

		buddy port will return the genError error."

	::= { ol51nnMFIBPortEntry 3 }



ol51nnMFIBPortBuddySlot OBJECT-TYPE

	SYNTAX INTEGER

	ACCESS read-write

	STATUS mandatory

	DESCRIPTION

		"The slot index of the redundant port's buddy.  To set

		a port to be redundant, the buddy's slot and port must

		be set to valid values.



		The buddy is automatically set to be redundant to this port."

	::= { ol51nnMFIBPortEntry 4 }



ol51nnMFIBPortBuddyPort  OBJECT-TYPE

	SYNTAX INTEGER

	ACCESS read-write

	STATUS mandatory

	DESCRIPTION

		"The port index of the redundant port's buddy.  To set

		a port to be redundant, the buddy's slot and port must

		be set to valid values.



		The buddy is automatically set to be redundant to this port."

	::= { ol51nnMFIBPortEntry 5 }





ol51nnMFIBPortDipAdminState OBJECT-TYPE

	SYNTAX INTEGER {

		enabled(1),

		disabled(2),

		redundant-primary(3),

		redundant-backup(4)

		}

	ACCESS read-only

	STATUS mandatory

	DESCRIPTION

		"The state of this port as indicated by the port's dip

		switches."

	::= { ol51nnMFIBPortEntry 6 }



--

-- ONline Ethernet 10BASE-T Module

--





ol51nnMUTPModTable OBJECT-TYPE

	SYNTAX SEQUENCE OF Ol51nnMUTPModEntry

	ACCESS not-accessible

	STATUS mandatory

	DESCRIPTION

		"A list of module-specific information associated

		with a particular 51nnM-UTP module in the concentrator."

	::= { ol51nnMUTP 1 }



ol51nnMUTPModEntry OBJECT-TYPE

	SYNTAX Ol51nnMUTPModEntry

	ACCESS not-accessible

	STATUS mandatory

	DESCRIPTION

		"A module entry containing objects that describe the

		module level for that particular module."

	INDEX { ol51nnMUTPModSlotIndex }

	::= { ol51nnMUTPModTable 1 }



Ol51nnMUTPModEntry ::=

	SEQUENCE {

		ol51nnMUTPModSlotIndex

			INTEGER,

		ol51nnMUTPModDipNetwork

			INTEGER,

		ol51nnMUTPModCrossover

			INTEGER,

		ol51nnMUTPModDipCrossover

			INTEGER,

		ol51nnMUTPModFFL

			INTEGER,

		ol51nnMUTPModDipFFL

			INTEGER

		}



ol51nnMUTPModSlotIndex OBJECT-TYPE

	SYNTAX INTEGER

	ACCESS read-only

	STATUS mandatory

	DESCRIPTION

		"The slot number of this module."

	::= { ol51nnMUTPModEntry 1 }



ol51nnMUTPModDipNetwork OBJECT-TYPE

	SYNTAX INTEGER {

		isolated(2),

		ethernet-1(6),

		ethernet-2(7),

		ethernet-3(8)

		}

	ACCESS read-only

	STATUS mandatory

	DESCRIPTION

		"The network indicated by the module's dip switches."

	::= { ol51nnMUTPModEntry 2 }



ol51nnMUTPModCrossover OBJECT-TYPE

	SYNTAX INTEGER {

		crossed(1),

		uncrossed(2)

		}

	ACCESS read-write

	STATUS mandatory

	DESCRIPTION

		"The current state of this module's crossover

		configuration.  Setting this object to uncrossed(2)

		allows the last port to be used to connect to another

		repeater.  Often this feature is used to connect one 10BASE-T

		module to another."

	::= { ol51nnMUTPModEntry 3 }



ol51nnMUTPModDipCrossover OBJECT-TYPE

	SYNTAX INTEGER {

		crossed(1),

		uncrossed(2)

		}

	ACCESS read-only

	STATUS mandatory

	DESCRIPTION

		"The crossover configuration indicated by this module's

		dip switches."

	::= { ol51nnMUTPModEntry 4 }



ol51nnMUTPModFFL OBJECT-TYPE

	SYNTAX INTEGER {

		eight-bits(1),

		seven-bits(2)

		}

	ACCESS read-write

	STATUS mandatory

	DESCRIPTION

		"The number of bits to store in the repeater's fifo

		buffer.  See the module user's guide for more information."

	::= { ol51nnMUTPModEntry 5 }



ol51nnMUTPModDipFFL OBJECT-TYPE

	SYNTAX INTEGER {

		eight-bits(1),

		seven-bits(2)

		}

	ACCESS read-write

	STATUS mandatory

	DESCRIPTION

		"The fifo fill level as indicated by this module's dip

		switches."

	::= { ol51nnMUTPModEntry 6 }



ol51nnMUTPPortTable			 OBJECT-TYPE

	SYNTAX SEQUENCE OF Ol51nnMUTPPortEntry

	ACCESS not-accessible

	STATUS mandatory

	DESCRIPTION

		"A table of port-specific information for each port of

		this module type."

	::= { ol51nnMUTP 2 }



ol51nnMUTPPortEntry OBJECT-TYPE

	SYNTAX Ol51nnMUTPPortEntry

	ACCESS not-accessible

	STATUS mandatory

	DESCRIPTION

		"A port entry containing objects that describe this port."

	INDEX { ol51nnMUTPPortSlotIndex, ol51nnMUTPPortIndex }

	::= { ol51nnMUTPPortTable 1 }



Ol51nnMUTPPortEntry ::=

	SEQUENCE {

		ol51nnMUTPPortSlotIndex

			INTEGER,

		ol51nnMUTPPortIndex

			INTEGER,

		ol51nnMUTPPortAdminState

			INTEGER,

		ol51nnMUTPPortBuddySlot

			INTEGER,

		ol51nnMUTPPortBuddyPort

			INTEGER,

		ol51nnMUTPPortDipAdminState

			INTEGER,

		ol51nnMUTPPortLinkInteg

			INTEGER,

		ol51nnMUTPPortDipLinkInteg

			INTEGER,

		ol51nnMUTPPortSquelch

			INTEGER,

		ol51nnMUTPPortDipSquelch

			INTEGER

		}



	ol51nnMUTPPortSlotIndex OBJECT-TYPE

	SYNTAX INTEGER

	ACCESS read-only

	STATUS mandatory

	DESCRIPTION

		"The slot number of this port's module."

	::= { ol51nnMUTPPortEntry 1 }





ol51nnMUTPPortIndex OBJECT-TYPE

	SYNTAX INTEGER

	ACCESS read-only

	STATUS mandatory

	DESCRIPTION

		"The port number of this port."

	::= { ol51nnMUTPPortEntry 2 }



ol51nnMUTPPortAdminState OBJECT-TYPE

	SYNTAX INTEGER {

		enabled(1),

		disabled(2),

		redundant-primary(3),

		redundant-backup(4)

		}

	ACCESS read-write

	STATUS mandatory

	DESCRIPTION

		"The desired state of this port.  Setting this port to

		be redundant with invalid settings of buddy slot and

		buddy port will return the genError error."

	::= { ol51nnMUTPPortEntry 3 }



ol51nnMUTPPortBuddySlot OBJECT-TYPE

	SYNTAX INTEGER

	ACCESS read-write

	STATUS mandatory

	DESCRIPTION

		"The slot index of the redundant port's buddy.  To set

		a port to be redundant, the buddy's slot and port must

		be set to valid values.



		The buddy is automatically set to be redundant to this port."

	::= { ol51nnMUTPPortEntry 4 }



ol51nnMUTPPortBuddyPort  OBJECT-TYPE

	SYNTAX INTEGER

	ACCESS read-write

	STATUS mandatory

	DESCRIPTION

		"The port index of the redundant port's buddy.  To set

		a port to be redundant, the buddy's slot and port must

		be set to valid values.



		The buddy is automatically set to be redundant to this port."

	::= { ol51nnMUTPPortEntry 5 }



ol51nnMUTPPortDipAdminState OBJECT-TYPE

	SYNTAX INTEGER {

		enabled(1),

		disabled(2)

		}

	ACCESS read-only

	STATUS mandatory

	DESCRIPTION

		"The state of this port as indicated by the port's dip

		switches."

	::= { ol51nnMUTPPortEntry 6 }



ol51nnMUTPPortLinkInteg OBJECT-TYPE

	SYNTAX INTEGER {

		enabled(1),

		disabled(2)

		}

	ACCESS read-write

	STATUS mandatory

	DESCRIPTION

		"The port's link integrity configuration.  Enabling

		link integrity configures the port to conform to

		the link integrity feature as specified by 10BASE-T."

	::= { ol51nnMUTPPortEntry 7 }



ol51nnMUTPPortDipLinkInteg OBJECT-TYPE

	SYNTAX INTEGER {

		enabled(1),

		disabled(2)

		}

	ACCESS read-only

	STATUS mandatory

	DESCRIPTION

		"The link integrity configuration as indicated by this

		port's dip switches."

	::= { ol51nnMUTPPortEntry 8 }



ol51nnMUTPPortSquelch	 OBJECT-TYPE

	SYNTAX INTEGER {

		normal(1),		-- high squelch

		low(2)

		}

	ACCESS read-write

	STATUS mandatory

	DESCRIPTION

		"The port's squelch configuration.  See the module's

		user's guide for more information."

	::= { ol51nnMUTPPortEntry 9 }



ol51nnMUTPPortDipSquelch	 OBJECT-TYPE

	SYNTAX INTEGER {

		normal(1),		-- high squelch

		low(2)

		}

	ACCESS read-only

	STATUS mandatory

	DESCRIPTION

		"The port's squelch configuration as indicated by this

		port's dip switches."

	::= { ol51nnMUTPPortEntry 10 }





--

-- ONline Ethernet 10BASE-T Module

--



ol51nnMTPModTable OBJECT-TYPE

	SYNTAX SEQUENCE OF Ol51nnMTPModEntry

	ACCESS not-accessible

	STATUS mandatory

	DESCRIPTION

		"A table of module-specific information for each

		51nnM-TP module in the concentrator."

	::= { ol51nnMTP 1 }



ol51nnMTPModEntry OBJECT-TYPE

	SYNTAX Ol51nnMTPModEntry

	ACCESS not-accessible

	STATUS mandatory

	DESCRIPTION

		"A list of module-specific information about a

		specific 51nnM-TP module in the concentrator."

	INDEX { ol51nnMTPModSlotIndex }

	::= { ol51nnMTPModTable 1 }



Ol51nnMTPModEntry ::=

	SEQUENCE {

		ol51nnMTPModSlotIndex

			INTEGER,

		ol51nnMTPModDipNetwork

			INTEGER,

		ol51nnMTPModCrossover

			INTEGER,

		ol51nnMTPModDipCrossover

			INTEGER

		}



ol51nnMTPModSlotIndex OBJECT-TYPE

	SYNTAX INTEGER

	ACCESS read-only

	STATUS mandatory

	DESCRIPTION

		"The slot number of this module."

	::= { ol51nnMTPModEntry 1 }



ol51nnMTPModDipNetwork OBJECT-TYPE

	SYNTAX INTEGER {

		isolated(2),

		ethernet-1(6),

		ethernet-2(7),

		ethernet-3(8)

		}

	ACCESS read-only

	STATUS mandatory

	DESCRIPTION

		"The network indicated by the module's dip switches."

	::= { ol51nnMTPModEntry 2 }



ol51nnMTPModCrossover OBJECT-TYPE

	SYNTAX INTEGER {

		crossed(1),

		uncrossed(2)

		}

	ACCESS read-write

	STATUS mandatory

	DESCRIPTION

		"The current state of this module's crossover

		configuration.  Setting this object to uncrossed(2)

		allows the last port to be used to connect to another

		repeater.  Often this feature is used to connect one 10BASE-T

		module to another."

	::= { ol51nnMTPModEntry 3 }



ol51nnMTPModDipCrossover OBJECT-TYPE

	SYNTAX INTEGER {

		crossed(1),

		uncrossed(2)

		}

	ACCESS read-only

	STATUS mandatory

	DESCRIPTION

		"The crossover configuration indicated by this module's

		dip switches."

	::= { ol51nnMTPModEntry 4 }





ol51nnMTPPortTable			 OBJECT-TYPE

	SYNTAX SEQUENCE OF Ol51nnMTPPortEntry

	ACCESS not-accessible

	STATUS mandatory

	DESCRIPTION

		"A table of port-specific information for each port of

		this module type."

	::= { ol51nnMTP 2 }



ol51nnMTPPortEntry OBJECT-TYPE

	SYNTAX Ol51nnMTPPortEntry

	ACCESS not-accessible

	STATUS mandatory

	DESCRIPTION

		"A port entry containing objects that describe this port."

	INDEX { ol51nnMTPPortSlotIndex, ol51nnMTPPortIndex }

	::= { ol51nnMTPPortTable 1 }



Ol51nnMTPPortEntry ::=

	SEQUENCE {

		ol51nnMTPPortSlotIndex

			INTEGER,

		ol51nnMTPPortIndex

			INTEGER,

		ol51nnMTPPortAdminState

			INTEGER,

		ol51nnMTPPortBuddySlot

			INTEGER,

		ol51nnMTPPortBuddyPort

			INTEGER,

		ol51nnMTPPortDipAdminState

			INTEGER,

		ol51nnMTPPortLinkInteg

			INTEGER,

		ol51nnMTPPortDipLinkInteg

			INTEGER,

		ol51nnMTPPortSquelch

			INTEGER,

		ol51nnMTPPortDipSquelch

			INTEGER

		}



	ol51nnMTPPortSlotIndex OBJECT-TYPE

	SYNTAX INTEGER

	ACCESS read-only

	STATUS mandatory

	DESCRIPTION

		"The slot number of this port's module."

	::= { ol51nnMTPPortEntry 1 }





ol51nnMTPPortIndex OBJECT-TYPE

	SYNTAX INTEGER

	ACCESS read-only

	STATUS mandatory

	DESCRIPTION

		"The port number of this port."

	::= { ol51nnMTPPortEntry 2 }



ol51nnMTPPortAdminState OBJECT-TYPE

	SYNTAX INTEGER {

		enabled(1),

		disabled(2),

		redundant-primary(3),

		redundant-backup(4)

		}

	ACCESS read-write

	STATUS mandatory

	DESCRIPTION

		"The desired state of this port.  Setting this port to

		be redundant with invalid settings of buddy slot and

		buddy port will return the genError error."

	::= { ol51nnMTPPortEntry 3 }



ol51nnMTPPortBuddySlot OBJECT-TYPE

	SYNTAX INTEGER

	ACCESS read-write

	STATUS mandatory

	DESCRIPTION

		"The slot index of the redundant port's buddy.  To set

		a port to be redundant, the buddy's slot and port must

		be set to valid values.



		The buddy is automatically set to be redundant to this port."

	::= { ol51nnMTPPortEntry 4 }



ol51nnMTPPortBuddyPort  OBJECT-TYPE

	SYNTAX INTEGER

	ACCESS read-write

	STATUS mandatory

	DESCRIPTION

		"The port index of the redundant port's buddy.  To set

		a port to be redundant, the buddy's slot and port must

		be set to valid values.



		The buddy is automatically set to be redundant to this port."

	::= { ol51nnMTPPortEntry 5 }



ol51nnMTPPortDipAdminState OBJECT-TYPE

	SYNTAX INTEGER {

		enabled(1),

		disabled(2)

		}

	ACCESS read-only

	STATUS mandatory

	DESCRIPTION

		"The state of this port as indicated by the port's dip

		switches."

	::= { ol51nnMTPPortEntry 6 }



ol51nnMTPPortLinkInteg OBJECT-TYPE

	SYNTAX INTEGER {

		enabled(1),

		disabled(2)

		}

	ACCESS read-write

	STATUS mandatory

	DESCRIPTION

		"The port's link integrity configuration.  Enabling

		link integrity configures the port to conform to

		the link integrity feature as specified by 10BASE-T."

	::= { ol51nnMTPPortEntry 7 }



ol51nnMTPPortDipLinkInteg OBJECT-TYPE

	SYNTAX INTEGER {

		enabled(1),

		disabled(2)

		}

	ACCESS read-only

	STATUS mandatory

	DESCRIPTION

		"The link integrity configuration as indicated by this

		port's dip switches."

	::= { ol51nnMTPPortEntry 8 }



ol51nnMTPPortSquelch	 OBJECT-TYPE

	SYNTAX INTEGER {

		normal(1),		-- high squelch

		low(2)

		}

	ACCESS read-write

	STATUS mandatory

	DESCRIPTION

		"The port's squelch configuration.  See the module's

		user's guide for more information."

	::= { ol51nnMTPPortEntry 9 }



ol51nnMTPPortDipSquelch  OBJECT-TYPE

	SYNTAX INTEGER {

		normal(1),		-- high squelch

		low(2)

		}

	ACCESS read-only

	STATUS mandatory

	DESCRIPTION

		"The port's squelch configuration as indicated by this

		port's dip switches."

	::= { ol51nnMTPPortEntry 10 }



--

-- ONline Ethernet BNC Module

--





ol51nnMBNCModTable OBJECT-TYPE

	SYNTAX SEQUENCE OF Ol51nnMBNCModEntry

	ACCESS not-accessible

	STATUS mandatory

	DESCRIPTION

		"A list of module-specific information associated

		with a particular 51nnM-BNC module in the concentrator."

	::= { ol51nnMBNC 1 }



ol51nnMBNCModEntry OBJECT-TYPE

	SYNTAX Ol51nnMBNCModEntry

	ACCESS not-accessible

	STATUS mandatory

	DESCRIPTION

		"A module entry containing objects that describe the

		module level for that particular module."

	INDEX { ol51nnMBNCModSlotIndex }

	::= { ol51nnMBNCModTable 1 }



Ol51nnMBNCModEntry ::=

	SEQUENCE {

		ol51nnMBNCModSlotIndex

			INTEGER,

		ol51nnMBNCModDipNetwork

			INTEGER

		}



ol51nnMBNCModSlotIndex OBJECT-TYPE

	SYNTAX INTEGER

	ACCESS read-only

	STATUS mandatory

	DESCRIPTION

		"The slot number of this module."

	::= { ol51nnMBNCModEntry 1 }



ol51nnMBNCModDipNetwork OBJECT-TYPE

	SYNTAX INTEGER {

		isolated(2),

		ethernet-1(6),

		ethernet-2(7),

		ethernet-3(8)

		}

	ACCESS read-only

	STATUS mandatory

	DESCRIPTION

		"The network indicated by the module's dip switches."

	::= { ol51nnMBNCModEntry 2 }



ol51nnMBNCPortTable OBJECT-TYPE

	SYNTAX SEQUENCE OF Ol51nnMBNCPortEntry

	ACCESS not-accessible

	STATUS mandatory

	DESCRIPTION

		"A table of port-specific information for each port of

		this module type."

	::= { ol51nnMBNC 2 }



ol51nnMBNCPortEntry OBJECT-TYPE

	SYNTAX Ol51nnMBNCPortEntry

	ACCESS not-accessible

	STATUS mandatory

	DESCRIPTION

		"A port entry containing objects that describe this port."

	INDEX { ol51nnMBNCPortSlotIndex, ol51nnMBNCPortIndex }

	::= { ol51nnMBNCPortTable 1 }



Ol51nnMBNCPortEntry ::=

	SEQUENCE {

		ol51nnMBNCPortSlotIndex

			INTEGER,

		ol51nnMBNCPortIndex

			INTEGER,

		ol51nnMBNCPortDipAdminState

			INTEGER,

		ol51nnMBNCPortDipTermination

			INTEGER,

		ol51nnMBNCPortDipGround

			INTEGER

		}



ol51nnMBNCPortSlotIndex OBJECT-TYPE

	SYNTAX INTEGER

	ACCESS read-only

	STATUS mandatory

	DESCRIPTION

		"The slot number of this port's module."

	::= { ol51nnMBNCPortEntry 1 }





ol51nnMBNCPortIndex OBJECT-TYPE

	SYNTAX INTEGER

	ACCESS read-only

	STATUS mandatory

	DESCRIPTION

		"The port number of this port."

	::= { ol51nnMBNCPortEntry 2 }



ol51nnMBNCPortDipAdminState OBJECT-TYPE

	SYNTAX INTEGER {

		enabled(1),

		disabled(2)

		}

	ACCESS read-only

	STATUS mandatory

	DESCRIPTION

		"The state of this port as indicated by the port's dip

		switches."

	::= { ol51nnMBNCPortEntry 3 }



ol51nnMBNCPortDipTermination OBJECT-TYPE

	SYNTAX INTEGER {

		terminated(1),

		not-terminated(2)

		}

	ACCESS read-only

	STATUS mandatory

	DESCRIPTION

		"The state of this port's termination as indicated by the

		port's dip switches."

	::= { ol51nnMBNCPortEntry 4 }



ol51nnMBNCPortDipGround OBJECT-TYPE

	SYNTAX INTEGER {

		grounded(1),

		not-grounded(2)

		}

	ACCESS read-only

	STATUS mandatory

	DESCRIPTION

		"The state of this port's ground as indicated by the port's

		dip switches."

	::= { ol51nnMBNCPortEntry 5 }



--

-- ONline Ethernet to Ethernet Bridge Module

--



ol51nnBEEModTable OBJECT-TYPE

	SYNTAX SEQUENCE OF Ol51nnBEEModEntry

	ACCESS not-accessible

	STATUS mandatory

	DESCRIPTION

		"A table of module-specific information for

		each 51nnB-EE module in the concentrator."

	::= { ol51nnBEE 1 }



ol51nnBEEModEntry OBJECT-TYPE

	SYNTAX Ol51nnBEEModEntry

	ACCESS not-accessible

	STATUS mandatory

	DESCRIPTION

		"A list of module-specific information about a specific

		51nnB-EE module in the concentrator."

	INDEX { ol51nnBEEModSlotIndex }

	::= { ol51nnBEEModTable 1 }



Ol51nnBEEModEntry ::=

	SEQUENCE {

		ol51nnBEEModSlotIndex

			INTEGER,

		ol51nnBEEModStationAddr

			OCTET STRING,

		ol51nnBEEModProtocols

			DisplayString

		}



ol51nnBEEModSlotIndex OBJECT-TYPE

	SYNTAX INTEGER

	ACCESS read-only

	STATUS mandatory

	DESCRIPTION

		"The slot number of this module."

	::= { ol51nnBEEModEntry 1 }



ol51nnBEEModStationAddr OBJECT-TYPE

	SYNTAX OCTET STRING (SIZE(6))

	ACCESS read-only

	STATUS mandatory

	DESCRIPTION

		"A 6 octet address that uniquely identifies this module.

		The station address is the mac address of port 1."

	::= { ol51nnBEEModEntry 2 }



ol51nnBEEModProtocols OBJECT-TYPE

	SYNTAX DisplayString

	ACCESS read-only

	STATUS mandatory

	DESCRIPTION

		"A textual description of the protocols supported by

		this module"

	::= { ol51nnBEEModEntry 3 }





ol51nnBEEPortTable	OBJECT-TYPE

	SYNTAX SEQUENCE OF Ol51nnBEEPortEntry

	ACCESS not-accessible

	STATUS mandatory

	DESCRIPTION

		"A table of port-specific for each port of each

		51nnB-EE module in the concentrator."

	::= { ol51nnBEE 2 }





ol51nnBEEPortEntry OBJECT-TYPE

	SYNTAX Ol51nnBEEPortEntry

	ACCESS not-accessible

	STATUS mandatory

	DESCRIPTION

		"A list of port-specific informatoin about a specific

		51nnB-EE port in the concentrator."

	INDEX { ol51nnBEEPortSlotIndex, ol51nnBEEPortIndex }

	::= { ol51nnBEEPortTable 1 }



Ol51nnBEEPortEntry ::=

	SEQUENCE {

		ol51nnBEEPortSlotIndex

			INTEGER,

		ol51nnBEEPortIndex

			INTEGER,

		ol51nnBEEPortIpAddress

			IpAddress,

		ol51nnBEEPortDipNetwork

			INTEGER,

		ol51nnBEEPortDefNetwork

			INTEGER

		}



ol51nnBEEPortSlotIndex OBJECT-TYPE

	SYNTAX INTEGER

	ACCESS read-only

	STATUS mandatory

	DESCRIPTION

		"The slot number for this port's module."

	::= { ol51nnBEEPortEntry 1 }



ol51nnBEEPortIndex OBJECT-TYPE

	SYNTAX INTEGER

	ACCESS read-only

	STATUS mandatory

	DESCRIPTION

		"The port number for this port within this slot."

	::= { ol51nnBEEPortEntry 2 }



ol51nnBEEPortIpAddress OBJECT-TYPE

	SYNTAX IpAddress

	ACCESS read-only

	STATUS mandatory

	DESCRIPTION

		"The IP Address associated with this port."

	::= { ol51nnBEEPortEntry 3 }



ol51nnBEEPortDipNetwork OBJECT-TYPE

	SYNTAX INTEGER {

		isolated(2),

		front-panel(5),

		ethernet-1(6),

		ethernet-2(7),

		ethernet-3(8)

		}

	ACCESS read-only

	STATUS mandatory

	DESCRIPTION

		"The network for this port as specified by this port's

		dip switches."

	::= { ol51nnBEEPortEntry 4 }



ol51nnBEEPortDefNetwork OBJECT-TYPE

	SYNTAX INTEGER {

		isolated(2),

		front-panel(5),

		ethernet-1(6),

		ethernet-2(7),

		ethernet-3(8)

		}

	ACCESS read-only

	STATUS mandatory

	DESCRIPTION

		"The network for this port as specified by the OEBM's

		non-volatile storage."

	::= { ol51nnBEEPortEntry 5 }



--

-- ONline Ethernet to Serial Router Module

--





ol51nnRESModTable OBJECT-TYPE

	SYNTAX SEQUENCE OF Ol51nnRESModEntry

	ACCESS not-accessible

	STATUS mandatory

	DESCRIPTION

		"A table of module-specific information for

		each 51nnR-ES module in the concentrator."

	::= { ol51nnRES 1 }



ol51nnRESModEntry OBJECT-TYPE

	SYNTAX Ol51nnRESModEntry

	ACCESS not-accessible

	STATUS mandatory

	DESCRIPTION

		"A list of module-specific information about a specific

		51nnR-ES module in the concentrator."

	INDEX { ol51nnRESModSlotIndex }

	::= { ol51nnRESModTable 1 }



Ol51nnRESModEntry ::=

	SEQUENCE {

		ol51nnRESModSlotIndex

			INTEGER,

		ol51nnRESModStationAddr

			OCTET STRING,

		ol51nnRESModProtocols

			DisplayString

		}



ol51nnRESModSlotIndex OBJECT-TYPE

	SYNTAX INTEGER

	ACCESS read-only

	STATUS mandatory

	DESCRIPTION

		"The slot number of this module."

	::= { ol51nnRESModEntry 1 }



ol51nnRESModStationAddr OBJECT-TYPE

	SYNTAX OCTET STRING (SIZE(6))

	ACCESS read-only

	STATUS mandatory

	DESCRIPTION

		"A 6 octet address that uniquely identifies this module.

		The station address is the mac address of port 1."

	::= { ol51nnRESModEntry 2 }





ol51nnRESModProtocols OBJECT-TYPE

	SYNTAX DisplayString

	ACCESS read-only

	STATUS mandatory

	DESCRIPTION

		"A textual description of the protocols supported by

		this module"

	::= { ol51nnRESModEntry 3 }



ol51nnRESPortTable	OBJECT-TYPE

	SYNTAX SEQUENCE OF Ol51nnRESPortEntry

	ACCESS not-accessible

	STATUS mandatory

	DESCRIPTION

		"A table of port-specific for each port of each

		51nnR-ES module in the concentrator."

	::= { ol51nnRES 2 }



ol51nnRESPortEntry OBJECT-TYPE

	SYNTAX Ol51nnRESPortEntry

	ACCESS not-accessible

	STATUS mandatory

	DESCRIPTION

		"A list of port-specific informatoin about a specific

		51nnR-ES port in the concentrator."

	INDEX { ol51nnRESPortSlotIndex, ol51nnRESPortIndex }

	::= { ol51nnRESPortTable 1 }



Ol51nnRESPortEntry ::=

	SEQUENCE {

		ol51nnRESPortSlotIndex

			INTEGER,

		ol51nnRESPortIndex

			INTEGER,

		ol51nnRESPortIpAddress

			IpAddress,

		ol51nnRESPortDipNetwork

			INTEGER,

		ol51nnRESPortDefNetwork

			INTEGER

		}



ol51nnRESPortSlotIndex OBJECT-TYPE

	SYNTAX INTEGER

	ACCESS read-only

	STATUS mandatory

	DESCRIPTION

		"The slot number for this port's module."

	::= { ol51nnRESPortEntry 1 }



ol51nnRESPortIndex OBJECT-TYPE

	SYNTAX INTEGER

	ACCESS read-only

	STATUS mandatory

	DESCRIPTION

		"The port number for this port."

	::= { ol51nnRESPortEntry 2 }



ol51nnRESPortIpAddress OBJECT-TYPE

	SYNTAX IpAddress

	ACCESS read-only

	STATUS mandatory

	DESCRIPTION

		"The IP Address associated with this port."

	::= { ol51nnRESPortEntry 3 }



ol51nnRESPortDipNetwork OBJECT-TYPE

	SYNTAX INTEGER {

		isolated(2),

		front-panel(5),

		ethernet-1(6),

		ethernet-2(7),

		ethernet-3(8)

		}

	ACCESS read-only

	STATUS mandatory

	DESCRIPTION

		"The network for this port as specified by this port's

		dip switches."

	::= { ol51nnRESPortEntry 4 }



ol51nnRESPortDefNetwork OBJECT-TYPE

	SYNTAX INTEGER {

		isolated(2),

		front-panel(5),

		ethernet-1(6),

		ethernet-2(7),

		ethernet-3(8)

		}

	ACCESS read-only

	STATUS mandatory

	DESCRIPTION

		"The network for this port as specified by the OERM's

		non-volatile storage."

	::= { ol51nnRESPortEntry 5 }



--

-- ONline Ethernet to Ethernet Router Module

--





ol51nnREEModTable OBJECT-TYPE

	SYNTAX SEQUENCE OF Ol51nnREEModEntry

	ACCESS not-accessible

	STATUS mandatory

	DESCRIPTION

		"A table of module-specific information for

		each 51nnR-EE module in the concentrator."

	::= { ol51nnREE 1 }



ol51nnREEModEntry OBJECT-TYPE

	SYNTAX Ol51nnREEModEntry

	ACCESS not-accessible

	STATUS mandatory

	DESCRIPTION

		"A list of module-specific information about a specific

		51nnR-EE module in the concentrator."

	INDEX { ol51nnREEModSlotIndex }

	::= { ol51nnREEModTable 1 }



Ol51nnREEModEntry ::=

	SEQUENCE {

		ol51nnREEModSlotIndex

			INTEGER,

		ol51nnREEModStationAddr

			OCTET STRING,

		ol51nnREEModProtocols

			DisplayString

		}



ol51nnREEModSlotIndex OBJECT-TYPE

	SYNTAX INTEGER

	ACCESS read-only

	STATUS mandatory

	DESCRIPTION

		"The slot number of this module."

	::= { ol51nnREEModEntry 1 }



ol51nnREEModStationAddr OBJECT-TYPE

	SYNTAX OCTET STRING (SIZE(6))

	ACCESS read-only

	STATUS mandatory

	DESCRIPTION

		"A 6 octet address that uniquely identifies this module.

		The station address is the mac address of port 1."

	::= { ol51nnREEModEntry 2 }





ol51nnREEModProtocols OBJECT-TYPE

	SYNTAX DisplayString

	ACCESS read-only

	STATUS mandatory

	DESCRIPTION

		"A textual description of the protocols supported by

		this module"

	::= { ol51nnREEModEntry 3 }



ol51nnREEPortTable	OBJECT-TYPE

	SYNTAX SEQUENCE OF Ol51nnREEPortEntry

	ACCESS not-accessible

	STATUS mandatory

	DESCRIPTION

		"A table of port-specific for each port of each

		51nnR-EE module in the concentrator."

	::= { ol51nnREE 2 }



ol51nnREEPortEntry OBJECT-TYPE

	SYNTAX Ol51nnREEPortEntry

	ACCESS not-accessible

	STATUS mandatory

	DESCRIPTION

		"A list of port-specific informatoin about a specific

		51nnR-EE port in the concentrator."

	INDEX { ol51nnREEPortSlotIndex, ol51nnREEPortIndex }

	::= { ol51nnREEPortTable 1 }



Ol51nnREEPortEntry ::=

	SEQUENCE {

		ol51nnREEPortSlotIndex

			INTEGER,

		ol51nnREEPortIndex

			INTEGER,

		ol51nnREEPortIpAddress

			IpAddress,

		ol51nnREEPortDipNetwork

			INTEGER,

		ol51nnREEPortDefNetwork

			INTEGER

		}



ol51nnREEPortSlotIndex OBJECT-TYPE

	SYNTAX INTEGER

	ACCESS read-only

	STATUS mandatory

	DESCRIPTION

		"The slot number for this port's module."

	::= { ol51nnREEPortEntry 1 }



ol51nnREEPortIndex OBJECT-TYPE

	SYNTAX INTEGER

	ACCESS read-only

	STATUS mandatory

	DESCRIPTION

		"The port number of this port."

	::= { ol51nnREEPortEntry 2 }



ol51nnREEPortIpAddress OBJECT-TYPE

	SYNTAX IpAddress

	ACCESS read-only

	STATUS mandatory

	DESCRIPTION

		"The IP Address associated with this port."

	::= { ol51nnREEPortEntry 3 }



ol51nnREEPortDipNetwork OBJECT-TYPE

	SYNTAX INTEGER {

		isolated(2),

		front-panel(5),

		ethernet-1(6),

		ethernet-2(7),

		ethernet-3(8)

		}

	ACCESS read-only

	STATUS mandatory

	DESCRIPTION

		"The network for this port as specified by this port's

		dip switches."

	::= { ol51nnREEPortEntry 4 }



ol51nnREEPortDefNetwork OBJECT-TYPE

	SYNTAX INTEGER {

		isolated(2),

		front-panel(5),

		ethernet-1(6),

		ethernet-2(7),

		ethernet-3(8)

		}

	ACCESS read-only

	STATUS mandatory

	DESCRIPTION

		"The network for this port as specified by the OERM's

		non-volatile storage."

	::= { ol51nnREEPortEntry 5 }



--

-- ONline Ethernet Female AUI Module

--



ol51nnMAUIFModTable OBJECT-TYPE

	SYNTAX SEQUENCE OF Ol51nnMAUIFModEntry

	ACCESS not-accessible

	STATUS mandatory

	DESCRIPTION

		"A list of module-specific information associated

		with a particular 51nnM-AUIF module in the concentrator."

	::= { ol51nnMAUIF 1 }



ol51nnMAUIFModEntry OBJECT-TYPE

	SYNTAX Ol51nnMAUIFModEntry

	ACCESS not-accessible

	STATUS mandatory

	DESCRIPTION

		"A list of module-specific information about a specific

		51nnM-AUIF module in the concentrator."

	INDEX { ol51nnMAUIFModSlotIndex }

	::= { ol51nnMAUIFModTable 1 }



Ol51nnMAUIFModEntry ::=

	SEQUENCE {

		ol51nnMAUIFModSlotIndex

			INTEGER

		}



ol51nnMAUIFModSlotIndex OBJECT-TYPE

	SYNTAX INTEGER

	ACCESS read-only

	STATUS mandatory

	DESCRIPTION

		"The slot number of this module."

	::= { ol51nnMAUIFModEntry 1 }



ol51nnMAUIFPortTable OBJECT-TYPE

	SYNTAX SEQUENCE OF Ol51nnMAUIFPortEntry

	ACCESS not-accessible

	STATUS mandatory

	DESCRIPTION

		"A table of port-specific information for each port of

		this module type."

	::= { ol51nnMAUIF 2 }



ol51nnMAUIFPortEntry OBJECT-TYPE

	SYNTAX Ol51nnMAUIFPortEntry

	ACCESS not-accessible

	STATUS mandatory

	DESCRIPTION

		"A list of module-specific information about a specific

		51nnM-AUIF port in the concentrator."

	INDEX { ol51nnMAUIFPortSlotIndex, ol51nnMAUIFPortIndex }

	::= { ol51nnMAUIFPortTable 1 }



Ol51nnMAUIFPortEntry ::=

	SEQUENCE {

		ol51nnMAUIFPortSlotIndex

			INTEGER,

		ol51nnMAUIFPortIndex

			INTEGER,

		ol51nnMAUIFPortAdminState

			INTEGER,

		ol51nnMAUIFPortBuddySlot

			INTEGER,

		ol51nnMAUIFPortBuddyPort

			INTEGER,

		ol51nnMAUIFPortDipAdminState

			INTEGER,

		ol51nnMAUIFPortDipNetwork

			INTEGER

		}



ol51nnMAUIFPortSlotIndex OBJECT-TYPE

	SYNTAX INTEGER

	ACCESS read-only

	STATUS mandatory

	DESCRIPTION

		"The slot number of this port's module."

	::= { ol51nnMAUIFPortEntry 1 }





ol51nnMAUIFPortIndex OBJECT-TYPE

	SYNTAX INTEGER

	ACCESS read-only

	STATUS mandatory

	DESCRIPTION

		"The port number of this port."

	::= { ol51nnMAUIFPortEntry 2 }



ol51nnMAUIFPortAdminState OBJECT-TYPE

	SYNTAX INTEGER {

		enabled(1),

		disabled(2),

		redundant-primary(3),

		redundant-backup(4)

		}

	ACCESS read-write

	STATUS mandatory

	DESCRIPTION

		"The desired state of this port.  Setting this port to

		be redundant with invalid settings of buddy slot and

		buddy port will return the genError error."

	::= { ol51nnMAUIFPortEntry 3 }



ol51nnMAUIFPortBuddySlot OBJECT-TYPE

	SYNTAX INTEGER

	ACCESS read-write

	STATUS mandatory

	DESCRIPTION

		"The slot index of the redundant port's buddy.  To set

		a port to be redundant, the buddy's slot and port must

		be set to valid values.



		The buddy is automatically set to be redundant to this port."

	::= { ol51nnMAUIFPortEntry 4 }



ol51nnMAUIFPortBuddyPort  OBJECT-TYPE

	SYNTAX INTEGER

	ACCESS read-write

	STATUS mandatory

	DESCRIPTION

		"The port index of the redundant port's buddy.  To set

		a port to be redundant, the buddy's slot and port must

		be set to valid values.



		The buddy is automatically set to be redundant to this port."

	::= { ol51nnMAUIFPortEntry 5 }



ol51nnMAUIFPortDipAdminState OBJECT-TYPE

	SYNTAX INTEGER {

		enabled(1),

		disabled(2),

		redundant-primary(3),

		redundant-backup(4)

		}

	ACCESS read-only

	STATUS mandatory

	DESCRIPTION

		"The state of this port as indicated by the port's dip

		switches."

	::= { ol51nnMAUIFPortEntry 6 }





ol51nnMAUIFPortDipNetwork OBJECT-TYPE

	SYNTAX INTEGER {

		isolated(2),

		ethernet-1(6),

		ethernet-2(7),

		ethernet-3(8)

		}

	ACCESS read-only

	STATUS mandatory

	DESCRIPTION

		"The network indicated by the port's dip switches."

	::= { ol51nnMAUIFPortEntry 7 }





--

-- ONline Ethernet Male AUI Module

--



ol51nnMAUIMModTable OBJECT-TYPE

	SYNTAX SEQUENCE OF Ol51nnMAUIMModEntry

	ACCESS not-accessible

	STATUS mandatory

	DESCRIPTION

		"A list of module-specific information associated

		with a particular 51nnM-AUIM module in the concentrator."

	::= { ol51nnMAUIM 1 }



ol51nnMAUIMModEntry OBJECT-TYPE

	SYNTAX Ol51nnMAUIMModEntry

	ACCESS not-accessible

	STATUS mandatory

	DESCRIPTION

		"A list of module-specific information about a specific

		51nnM-AUIM module in the concentrator."

	INDEX { ol51nnMAUIMModSlotIndex }

	::= { ol51nnMAUIMModTable 1 }



Ol51nnMAUIMModEntry ::=

	SEQUENCE {

		ol51nnMAUIMModSlotIndex

			INTEGER

		}



ol51nnMAUIMModSlotIndex OBJECT-TYPE

	SYNTAX INTEGER

	ACCESS read-only

	STATUS mandatory

	DESCRIPTION

		"The slot number of this module."

	::= { ol51nnMAUIMModEntry 1 }



ol51nnMAUIMPortTable			 OBJECT-TYPE

	SYNTAX SEQUENCE OF Ol51nnMAUIMPortEntry

	ACCESS not-accessible

	STATUS mandatory

	DESCRIPTION

		"A table of port-specific information for each port of

		this module type."

	::= { ol51nnMAUIM 2 }



ol51nnMAUIMPortEntry OBJECT-TYPE

	SYNTAX Ol51nnMAUIMPortEntry

	ACCESS not-accessible

	STATUS mandatory

	DESCRIPTION

		"A list of module-specific information about a specific

		51nnM-AUIM port in the concentrator."

	INDEX { ol51nnMAUIMPortSlotIndex, ol51nnMAUIMPortIndex }

	::= { ol51nnMAUIMPortTable 1 }



Ol51nnMAUIMPortEntry ::=

	SEQUENCE {

		ol51nnMAUIMPortSlotIndex

			INTEGER,

		ol51nnMAUIMPortIndex

			INTEGER,

		ol51nnMAUIMPortAdminState

			INTEGER,

		ol51nnMAUIMPortBuddySlot

			INTEGER,

		ol51nnMAUIMPortBuddyPort

			INTEGER,

		ol51nnMAUIMPortDipAdminState

			INTEGER,

		ol51nnMAUIMPortDipNetwork

			INTEGER,

		ol51nnMAUIMPortSQETest

			INTEGER,

		ol51nnMAUIMPortDipSQETest

			INTEGER,

		ol51nnMAUIMPortCollision

			INTEGER,

		ol51nnMAUIMPortDipCollision

			INTEGER,

		ol51nnMAUIMPortHalfStep

			INTEGER,

		ol51nnMAUIMPortDipHalfStep

			INTEGER

		}



ol51nnMAUIMPortSlotIndex OBJECT-TYPE

	SYNTAX INTEGER

	ACCESS read-only

	STATUS mandatory

	DESCRIPTION

		"The slot number of this port's module."

	::= { ol51nnMAUIMPortEntry 1 }





ol51nnMAUIMPortIndex OBJECT-TYPE

	SYNTAX INTEGER

	ACCESS read-only

	STATUS mandatory

	DESCRIPTION

		"The port number of this port."

	::= { ol51nnMAUIMPortEntry 2 }



ol51nnMAUIMPortAdminState OBJECT-TYPE

	SYNTAX INTEGER {

		enabled(1),

		disabled(2),

		redundant-primary(3),

		redundant-backup(4)

		}

	ACCESS read-write

	STATUS mandatory

	DESCRIPTION

		"The desired state of this port.  Setting this port to

		be redundant with invalid settings of buddy slot and

		buddy port will return the genError error."

	::= { ol51nnMAUIMPortEntry 3 }



ol51nnMAUIMPortBuddySlot OBJECT-TYPE

	SYNTAX INTEGER

	ACCESS read-write

	STATUS mandatory

	DESCRIPTION

		"The slot index of the redundant port's buddy.  To set

		a port to be redundant, the buddy's slot and port must

		be set to valid values.



		The buddy is automatically set to be redundant to this port."

	::= { ol51nnMAUIMPortEntry 4 }



ol51nnMAUIMPortBuddyPort  OBJECT-TYPE

	SYNTAX INTEGER

	ACCESS read-write

	STATUS mandatory

	DESCRIPTION

		"The port index of the redundant port's buddy.  To set

		a port to be redundant, the buddy's slot and port must

		be set to valid values.



		The buddy is automatically set to be redundant to this port."

	::= { ol51nnMAUIMPortEntry 5 }



ol51nnMAUIMPortDipAdminState OBJECT-TYPE

	SYNTAX INTEGER {

		enabled(1),

		disabled(2)

		}

	ACCESS read-only

	STATUS mandatory

	DESCRIPTION

		"The state of this port as indicated by the port's dip

		switches."

	::= { ol51nnMAUIMPortEntry 6 }



ol51nnMAUIMPortDipNetwork OBJECT-TYPE

	SYNTAX INTEGER {

		isolated(2),

		ethernet-1(6),

		ethernet-2(7),

		ethernet-3(8)

		}

	ACCESS read-only

	STATUS mandatory

	DESCRIPTION

		"The network indicated by the port's dip switches."

	::= { ol51nnMAUIMPortEntry 7 }



ol51nnMAUIMPortSQETest OBJECT-TYPE

	SYNTAX INTEGER {

		enabled(1),

		disabled(2)

		}

	ACCESS read-write

	STATUS mandatory

	DESCRIPTION

		"The current SQE test configuration for this port."

	::= { ol51nnMAUIMPortEntry 8 }



ol51nnMAUIMPortDipSQETest OBJECT-TYPE

	SYNTAX INTEGER {

		enabled(1),

		disabled(2)

		}

	ACCESS read-only

	STATUS mandatory

	DESCRIPTION

		"The SQE test configuration for this port as indicated

		by the port's dip switches."

	::= { ol51nnMAUIMPortEntry 9 }



ol51nnMAUIMPortCollision OBJECT-TYPE

	SYNTAX INTEGER {

		normal(1),

		alternate(2)

		}

	ACCESS read-write

	STATUS mandatory

	DESCRIPTION

		"The current collision configuration for this port."

	::= { ol51nnMAUIMPortEntry 10 }



ol51nnMAUIMPortDipCollision OBJECT-TYPE

	SYNTAX INTEGER {

		normal(1),

		alternate(2)

		}

	ACCESS read-only

	STATUS mandatory

	DESCRIPTION

		"The collision configuration for this port as indicated

		by the port's dip switches."

	::= { ol51nnMAUIMPortEntry 11 }



ol51nnMAUIMPortHalfStep OBJECT-TYPE

	SYNTAX INTEGER {

		enabled(1),

		disabled(2)

		}

	ACCESS read-write

	STATUS mandatory

	DESCRIPTION

		"The current step configuration for this port."

	::= { ol51nnMAUIMPortEntry 12 }



ol51nnMAUIMPortDipHalfStep OBJECT-TYPE

	SYNTAX INTEGER {

		enabled(1),

		disabled(2)

		}

	ACCESS read-only

	STATUS mandatory

	DESCRIPTION

		"The step configuration for this port as indicated

		by the port's dip switches."

	::= { ol51nnMAUIMPortEntry 13 }



--

-- ONline Token Ring 8-Port MAU Module

--

ol5208MTPModTable OBJECT-TYPE

	SYNTAX SEQUENCE OF Ol5208MTPModEntry

	ACCESS not-accessible

	STATUS mandatory

	DESCRIPTION

		"A list of module-specific information associated

		with a particular 5208M-TP module in the concentrator."

	::= { ol5208MTP 1 }



ol5208MTPModEntry OBJECT-TYPE

	SYNTAX Ol5208MTPModEntry

	ACCESS not-accessible

	STATUS mandatory

	DESCRIPTION

		"A description of the 5208M-TP module attributes."

	INDEX { ol5208MTPModSlotIndex }

	::= { ol5208MTPModTable 1 }



Ol5208MTPModEntry ::=

	SEQUENCE {

		ol5208MTPModSlotIndex

			INTEGER,

		ol5208MTPModBypsAdminState

			INTEGER,

		ol5208MTPModBypsOperState

			INTEGER,

		ol5208MTPModDipCableImp

			INTEGER

		}



ol5208MTPModSlotIndex OBJECT-TYPE

	SYNTAX INTEGER

	ACCESS read-only

	STATUS mandatory

	DESCRIPTION

		"The slot number of this module."

	::= { ol5208MTPModEntry 1 }





ol5208MTPModBypsAdminState OBJECT-TYPE

	SYNTAX INTEGER {

		insert(1),

		bypass(2)

		}

	ACCESS read-write

	STATUS mandatory

	DESCRIPTION

		"The desired state of this module with respect

		to the ring.  Setting this attribute to bypass(2)

		will cause this module to be removed from the ring

		that passes through the module's ring in and ring out

		ports."

	::= { ol5208MTPModEntry 2 }



ol5208MTPModBypsOperState OBJECT-TYPE

	SYNTAX INTEGER {

		insert(1),

		bypass(2)

		}

	ACCESS read-only

	STATUS mandatory

	DESCRIPTION

		"The operational state of this module with respect

		to the ring.  If this attribute is equal to bypass(2),

		then the module has been removed from the ring that

		passes through the module's ring in and ring out ports."

	::= { ol5208MTPModEntry 3 }



ol5208MTPModDipCableImp OBJECT-TYPE

	SYNTAX INTEGER {

		ohm100(1),

		ohm150(2)

		}

	ACCESS read-only

	STATUS mandatory

	DESCRIPTION

		"The setting of this module's port impedance matching, with

		100 ohm corresponding to unshielded twisted pair cabling and

		150 ohm corresponding to shielded twisted pair cabling.

		This setting is valid for all ports on this module."

	::= { ol5208MTPModEntry 4 }





ol5208MTPPortTable OBJECT-TYPE

	SYNTAX SEQUENCE OF Ol5208MTPPortEntry

	ACCESS not-accessible

	STATUS mandatory

	DESCRIPTION

		"A table of port-specific information for each port of

		this module type."

	::= { ol5208MTP 2 }



ol5208MTPPortEntry OBJECT-TYPE

	SYNTAX Ol5208MTPPortEntry

	ACCESS not-accessible

	STATUS mandatory

	DESCRIPTION

		"A description of 5208M-TP port attributes."

	INDEX { ol5208MTPPortSlotIndex, ol5208MTPPortIndex }

	::= { ol5208MTPPortTable 1 }



Ol5208MTPPortEntry ::=

	SEQUENCE {

		ol5208MTPPortSlotIndex

			INTEGER,

		ol5208MTPPortIndex

			INTEGER,

		ol5208MTPPortDipAdminState

			INTEGER,

		ol5208MTPPortStationType

			INTEGER

		}



ol5208MTPPortSlotIndex OBJECT-TYPE

	SYNTAX INTEGER

	ACCESS read-only

	STATUS mandatory

	DESCRIPTION

		"The slot number of this port's module."

	::= { ol5208MTPPortEntry 1 }





ol5208MTPPortIndex OBJECT-TYPE

	SYNTAX INTEGER

	ACCESS read-only

	STATUS mandatory

	DESCRIPTION

		"The port number of this port."

	::= { ol5208MTPPortEntry 2 }



ol5208MTPPortDipAdminState OBJECT-TYPE

	SYNTAX INTEGER {

		enabled(1),

		disabled(2)

		}

	ACCESS read-only

	STATUS mandatory

	DESCRIPTION

		"The state of this port as indicated by the port's dip

		switches."

	::= { ol5208MTPPortEntry 3 }



ol5208MTPPortStationType OBJECT-TYPE

	SYNTAX INTEGER {

		mac-present(1),

		mac-not-present(2)

		}

	ACCESS read-write

	STATUS mandatory

	DESCRIPTION

		"Determines whether the station connected to this port

		has a MAC address."

	::= { ol5208MTPPortEntry 4 }



ol5208MTPTrunkTable OBJECT-TYPE

	SYNTAX SEQUENCE OF Ol5208MTPTrunkEntry

	ACCESS not-accessible

	STATUS mandatory

	DESCRIPTION

		"A list of trunk-specific information about each trunk

		for this module type."

	::= { ol5208MTP 3 }



ol5208MTPTrunkEntry OBJECT-TYPE

	SYNTAX Ol5208MTPTrunkEntry

	ACCESS not-accessible

	STATUS mandatory

	DESCRIPTION

		"A description of 5208M-TP trunk attributes."

	INDEX { ol5208MTPTrunkSlotIndex, ol5208MTPTrunkIndex }

	::= { ol5208MTPTrunkTable 1 }



Ol5208MTPTrunkEntry ::=

	SEQUENCE {

		ol5208MTPTrunkSlotIndex

			INTEGER,

		ol5208MTPTrunkIndex

			INTEGER,

		ol5208MTPTrunkDipAdminState

			INTEGER,

		ol5208MTPTrunkCableMon

			INTEGER,

		ol5208MTPTrunkDipCableMon

			INTEGER,

		ol5208MTPTrunkNetMapState

			INTEGER,

		ol5208MTPTrunkExtBcnRecovery

			INTEGER

		}



ol5208MTPTrunkSlotIndex OBJECT-TYPE

	SYNTAX INTEGER

	ACCESS read-only

	STATUS mandatory

	DESCRIPTION

		"A unique value that identifies a particular module.  Its

		value ranges between 1 and olModSlotNumber.  The module

		identified by a particular value of this index is the same

		module as indentified by the same value of

		olTrunkSlotIndex."

	::= { ol5208MTPTrunkEntry 1 }





ol5208MTPTrunkIndex OBJECT-TYPE

	SYNTAX INTEGER

	ACCESS read-only

	STATUS mandatory

	DESCRIPTION

		"The trunk number for this trunk."

	::= { ol5208MTPTrunkEntry 2 }



ol5208MTPTrunkDipAdminState OBJECT-TYPE

	SYNTAX INTEGER {

		enabled(1),

		disabled(2)

		}

	ACCESS read-only

	STATUS mandatory

	DESCRIPTION

		"The state of this trunk as indicated by the trunk's dip

		switches."

	::= { ol5208MTPTrunkEntry 3 }





ol5208MTPTrunkCableMon OBJECT-TYPE

	SYNTAX INTEGER {

		enabled(1),

		disabled(2),

		notApplicable(3)

	}

	ACCESS read-write

	STATUS mandatory

	DESCRIPTION

		"The cable monitor configuration for this trunk."

	::= { ol5208MTPTrunkEntry 4 }



ol5208MTPTrunkDipCableMon OBJECT-TYPE

	SYNTAX INTEGER {

		enabled(1),

		disabled(2),

		notApplicable(3)

	}

	ACCESS read-only

	STATUS mandatory

	DESCRIPTION

		"The cable monitor configuration as indicated by this trunk's

		dip switches."

	::= { ol5208MTPTrunkEntry 5 }





ol5208MTPTrunkNetMapState OBJECT-TYPE

	SYNTAX INTEGER {

		notApplicable(1),

		internal(2),

		external(3)

	}

	ACCESS read-write

	STATUS mandatory

	DESCRIPTION

		"The map state of the copper ring-in trunk.  This

		should be set to external for ring-in trunks which

		connect to external hubs.  The mapping logic will not

		operate on trunks which are set to external.  This

		prevents incorrect mapping which can occur when a

		module in one hub detects the mapping signal from

		another hub. This attribute only applies to copper

		ring-in trunks."

	::= { ol5208MTPTrunkEntry 6 }





ol5208MTPTrunkExtBcnRecovery OBJECT-TYPE

	SYNTAX INTEGER {

		exists(1),

		nonExists(2),

		notApplicable(3)

	}

	ACCESS read-write

	STATUS mandatory

	DESCRIPTION

		"Indicates whether the trunk is connected to a

		segment that will perform beacon recovery.  This

		should be set to exists(1) for trunks which connect

		to hubs which perform beacon recovery.  This attribute

		is used to determine the fault domain when resolving a

		beaconing condition.



		The beacon recovery process will resolve beaconing on

		trunks with this attribute set to nonExists(2) before

		trunks with the attribute set to exists(1) are resolved.

		For backplane trunks, setting to a value other than

		notApplicable will return invalidData error.  The

		default value is nonExists(2)."

	::= { ol5208MTPTrunkEntry 7 }





--

-- ONline Ethernet Fiber Per-Port Module

--



ol51nnMFPModTable OBJECT-TYPE

	SYNTAX SEQUENCE OF Ol51nnMFPModEntry

	ACCESS not-accessible

	STATUS mandatory

	DESCRIPTION

		"A list of module-specific information associated

		with a particular 51nnM-FP module in the concentrator."

	::= { ol51nnMFP 1 }



ol51nnMFPModEntry OBJECT-TYPE

	SYNTAX Ol51nnMFPModEntry

	ACCESS not-accessible

	STATUS mandatory

	DESCRIPTION

		"A list of module-specific information about a specific

		51nnM-FP module in the concentrator."

	INDEX { ol51nnMFPModSlotIndex }

	::= { ol51nnMFPModTable 1 }



Ol51nnMFPModEntry ::=

	SEQUENCE {

		ol51nnMFPModSlotIndex

			INTEGER

		}



ol51nnMFPModSlotIndex OBJECT-TYPE

	SYNTAX INTEGER

	ACCESS read-only

	STATUS mandatory

	DESCRIPTION

		"The slot number of this module."

	::= { ol51nnMFPModEntry 1 }



ol51nnMFPPortTable			 OBJECT-TYPE

	SYNTAX SEQUENCE OF Ol51nnMFPPortEntry

	ACCESS not-accessible

	STATUS mandatory

	DESCRIPTION

		"A table of port-specific information for each port of

		this module type."

	::= { ol51nnMFP 2 }



ol51nnMFPPortEntry OBJECT-TYPE

	SYNTAX Ol51nnMFPPortEntry

	ACCESS not-accessible

	STATUS mandatory

	DESCRIPTION

		"A list of module-specific information about a specific

		51nnM-FP port in the concentrator."

	INDEX { ol51nnMFPPortSlotIndex, ol51nnMFPPortIndex }

	::= { ol51nnMFPPortTable 1 }



Ol51nnMFPPortEntry ::=

	SEQUENCE {

		ol51nnMFPPortSlotIndex

			INTEGER,

		ol51nnMFPPortIndex

			INTEGER,

		ol51nnMFPPortAdminState

			INTEGER,

		ol51nnMFPPortBuddySlot

			INTEGER,

		ol51nnMFPPortBuddyPort

			INTEGER,

		ol51nnMFPPortDipAdminState

			INTEGER,

		ol51nnMFPPortDipNetwork

			INTEGER,

		ol51nnMFPPortLLW

			INTEGER,

		ol51nnMFPPortDipLLW

			INTEGER,

		ol51nnMFPPortHipwr

			INTEGER,

		ol51nnMFPPortDipHipwr

			INTEGER

		}



ol51nnMFPPortSlotIndex OBJECT-TYPE

	SYNTAX INTEGER

	ACCESS read-only

	STATUS mandatory

	DESCRIPTION

		"The slot number of this port's module."

	::= { ol51nnMFPPortEntry 1 }





ol51nnMFPPortIndex OBJECT-TYPE

	SYNTAX INTEGER

	ACCESS read-only

	STATUS mandatory

	DESCRIPTION

		"The port number of this port."

	::= { ol51nnMFPPortEntry 2 }



ol51nnMFPPortAdminState OBJECT-TYPE

	SYNTAX INTEGER {

		enabled(1),

		disabled(2),

		redundant-primary(3),

		redundant-backup(4)

		}

	ACCESS read-write

	STATUS mandatory

	DESCRIPTION

		"The desired state of this port.  Setting this port to

		be redundant with invalid settings of buddy slot and

		buddy port will return the genError error."

	::= { ol51nnMFPPortEntry 3 }



ol51nnMFPPortBuddySlot OBJECT-TYPE

	SYNTAX INTEGER

	ACCESS read-write

	STATUS mandatory

	DESCRIPTION

		"The slot index of the redundant port's buddy.  To set

		a port to be redundant, the buddy's slot and port must

		be set to valid values.



		The buddy is automatically set to be redundant to this port."

	::= { ol51nnMFPPortEntry 4 }



ol51nnMFPPortBuddyPort  OBJECT-TYPE

	SYNTAX INTEGER

	ACCESS read-write

	STATUS mandatory

	DESCRIPTION

		"The port index of the redundant port's buddy.  To set

		a port to be redundant, the buddy's slot and port must

		be set to valid values.



		The buddy is automatically set to be redundant to this port."

	::= { ol51nnMFPPortEntry 5 }



ol51nnMFPPortDipAdminState OBJECT-TYPE

	SYNTAX INTEGER {

		enabled(1),

		disabled(2),

		redundant-primary(3),

		redundant-backup(4)

		}

	ACCESS read-only

	STATUS mandatory

	DESCRIPTION

		"The state of this port as indicated by the port's dip

		switches."

	::= { ol51nnMFPPortEntry 6 }



ol51nnMFPPortDipNetwork OBJECT-TYPE

	SYNTAX INTEGER {

		isolated(2),

		ethernet-1(6),

		ethernet-2(7),

		ethernet-3(8)

		}

	ACCESS read-only

	STATUS mandatory

	DESCRIPTION

		"The network indicated by the port's dip switches."

	::= { ol51nnMFPPortEntry 7 }



ol51nnMFPPortLLW OBJECT-TYPE

	SYNTAX INTEGER {

		enabled(1),

		disabled(2)

		}

	ACCESS read-write

	STATUS mandatory

	DESCRIPTION

		"The current low light warning configuration for this port."

	::= { ol51nnMFPPortEntry 8 }



ol51nnMFPPortDipLLW OBJECT-TYPE

	SYNTAX INTEGER {

		enabled(1),

		disabled(2)

		}

	ACCESS read-only

	STATUS mandatory

	DESCRIPTION

		"The low light warning configuration indicated by this module's

		dip switches."

	::= { ol51nnMFPPortEntry 9 }



ol51nnMFPPortHipwr OBJECT-TYPE

	SYNTAX INTEGER {

		enabled(1),

		disabled(2)

		}

	ACCESS read-write

	STATUS mandatory

	DESCRIPTION

		"The current high power optic configuration for this port."

	::= { ol51nnMFPPortEntry 10 }



ol51nnMFPPortDipHipwr OBJECT-TYPE

	SYNTAX INTEGER {

		enabled(1),

		disabled(2)

		}

	ACCESS read-only

	STATUS mandatory

	DESCRIPTION

		"The high power optic configuration for this port as indicated

		by the port's dip switches."

	::= { ol51nnMFPPortEntry 11 }



--

-- ONline Ethernet 10BASE-F Per-Port Module

--



ol51nnMFBPModTable OBJECT-TYPE

	SYNTAX SEQUENCE OF Ol51nnMFBPModEntry

	ACCESS not-accessible

	STATUS mandatory

	DESCRIPTION

		"A list of module-specific information associated

		with a particular 51nnM-FBP module in the concentrator."

	::= { ol51nnMFBP 1 }



ol51nnMFBPModEntry OBJECT-TYPE

	SYNTAX Ol51nnMFBPModEntry

	ACCESS not-accessible

	STATUS mandatory

	DESCRIPTION

		"A list of module-specific information about a specific

		51nnM-FBP module in the concentrator."

	INDEX { ol51nnMFBPModSlotIndex }

	::= { ol51nnMFBPModTable 1 }



Ol51nnMFBPModEntry ::=

	SEQUENCE {

		ol51nnMFBPModSlotIndex

			INTEGER

		}



ol51nnMFBPModSlotIndex OBJECT-TYPE

	SYNTAX INTEGER

	ACCESS read-only

	STATUS mandatory

	DESCRIPTION

		"The slot number of this module."

	::= { ol51nnMFBPModEntry 1 }



ol51nnMFBPPortTable			 OBJECT-TYPE

	SYNTAX SEQUENCE OF Ol51nnMFBPPortEntry

	ACCESS not-accessible

	STATUS mandatory

	DESCRIPTION

		"A table of port-specific information for each port of

		this module type."

	::= { ol51nnMFBP 2 }



ol51nnMFBPPortEntry OBJECT-TYPE

	SYNTAX Ol51nnMFBPPortEntry

	ACCESS not-accessible

	STATUS mandatory

	DESCRIPTION

		"A list of module-specific information about a specific

		51nnM-FBP port in the concentrator."

	INDEX { ol51nnMFBPPortSlotIndex, ol51nnMFBPPortIndex }

	::= { ol51nnMFBPPortTable 1 }



Ol51nnMFBPPortEntry ::=

	SEQUENCE {

		ol51nnMFBPPortSlotIndex

			INTEGER,

		ol51nnMFBPPortIndex

			INTEGER,

		ol51nnMFBPPortAdminState

			INTEGER,

		ol51nnMFBPPortBuddySlot

			INTEGER,

		ol51nnMFBPPortBuddyPort

			INTEGER,

		ol51nnMFBPPortDipAdminState

			INTEGER,

		ol51nnMFBPPortDipNetwork

			INTEGER,

		ol51nnMFBPPortLLW

			INTEGER,

		ol51nnMFBPPortDipLLW

			INTEGER,

		ol51nnMFBPPortHipwr

			INTEGER,

		ol51nnMFBPPortDipHipwr

			INTEGER

		}



ol51nnMFBPPortSlotIndex OBJECT-TYPE

	SYNTAX INTEGER

	ACCESS read-only

	STATUS mandatory

	DESCRIPTION

		"The slot number of this port's module."

	::= { ol51nnMFBPPortEntry 1 }





ol51nnMFBPPortIndex OBJECT-TYPE

	SYNTAX INTEGER

	ACCESS read-only

	STATUS mandatory

	DESCRIPTION

		"The port number of this port."

	::= { ol51nnMFBPPortEntry 2 }



ol51nnMFBPPortAdminState OBJECT-TYPE

	SYNTAX INTEGER {

		enabled(1),

		disabled(2),

		redundant-primary(3),

		redundant-backup(4)

		}

	ACCESS read-write

	STATUS mandatory

	DESCRIPTION

		"The desired state of this port.  Setting this port to

		be redundant with invalid settings of buddy slot and

		buddy port will return the genError error."

	::= { ol51nnMFBPPortEntry 3 }



ol51nnMFBPPortBuddySlot OBJECT-TYPE

	SYNTAX INTEGER

	ACCESS read-write

	STATUS mandatory

	DESCRIPTION

		"The slot index of the redundant port's buddy.  To set

		a port to be redundant, the buddy's slot and port must

		be set to valid values.



		The buddy is automatically set to be redundant to this port."

	::= { ol51nnMFBPPortEntry 4 }



ol51nnMFBPPortBuddyPort  OBJECT-TYPE

	SYNTAX INTEGER

	ACCESS read-write

	STATUS mandatory

	DESCRIPTION

		"The port index of the redundant port's buddy.  To set

		a port to be redundant, the buddy's slot and port must

		be set to valid values.



		The buddy is automatically set to be redundant to this port."

	::= { ol51nnMFBPPortEntry 5 }



ol51nnMFBPPortDipAdminState OBJECT-TYPE

	SYNTAX INTEGER {

		enabled(1),

		disabled(2),

		redundant-primary(3),

		redundant-backup(4)

		}

	ACCESS read-only

	STATUS mandatory

	DESCRIPTION

		"The state of this port as indicated by the port's dip

		switches."

	::= { ol51nnMFBPPortEntry 6 }



ol51nnMFBPPortDipNetwork OBJECT-TYPE

	SYNTAX INTEGER {

		isolated(2),

		ethernet-1(6),

		ethernet-2(7),

		ethernet-3(8)

		}

	ACCESS read-only

	STATUS mandatory

	DESCRIPTION

		"The network indicated by the port's dip switches."

	::= { ol51nnMFBPPortEntry 7 }



ol51nnMFBPPortLLW OBJECT-TYPE

	SYNTAX INTEGER {

		enabled(1),

		disabled(2)

		}

	ACCESS read-write

	STATUS mandatory

	DESCRIPTION

		"The current low light warning configuration for this port."

	::= { ol51nnMFBPPortEntry 8 }



ol51nnMFBPPortDipLLW OBJECT-TYPE

	SYNTAX INTEGER {

		enabled(1),

		disabled(2)

		}

	ACCESS read-only

	STATUS mandatory

	DESCRIPTION

		"The low light warning configuration indicated by this module's

		dip switches."

	::= { ol51nnMFBPPortEntry 9 }



ol51nnMFBPPortHipwr OBJECT-TYPE

	SYNTAX INTEGER {

		enabled(1),

		disabled(2)

		}

	ACCESS read-write

	STATUS mandatory

	DESCRIPTION

		"The current high power optic configuration for this port."

	::= { ol51nnMFBPPortEntry 10 }



ol51nnMFBPPortDipHipwr OBJECT-TYPE

	SYNTAX INTEGER {

		enabled(1),

		disabled(2)

		}

	ACCESS read-only

	STATUS mandatory

	DESCRIPTION

		"The high power optic configuration for this port as indicated

		by the port's dip switches."

	::= { ol51nnMFBPPortEntry 11 }



--

-- ONline Ethernet 10BASE-T Module

--



ol51nnMTPLModTable OBJECT-TYPE

	SYNTAX SEQUENCE OF Ol51nnMTPLModEntry

	ACCESS not-accessible

	STATUS mandatory

	DESCRIPTION

		"A list of module-specific information associated

		with a particular 51nnM-TPL module in the concentrator."

	::= { ol51nnMTPL 1 }



ol51nnMTPLModEntry OBJECT-TYPE

	SYNTAX Ol51nnMTPLModEntry

	ACCESS not-accessible

	STATUS mandatory

	DESCRIPTION

		"A list of module-specific information about a specific

		51nnM-TPL module in the concentrator."

	INDEX { ol51nnMTPLModSlotIndex }

	::= { ol51nnMTPLModTable 1 }



Ol51nnMTPLModEntry ::=

	SEQUENCE {

		ol51nnMTPLModSlotIndex

			INTEGER,

		ol51nnMTPLModDipNetwork

			INTEGER

		}



ol51nnMTPLModSlotIndex OBJECT-TYPE

	SYNTAX INTEGER

	ACCESS read-only

	STATUS mandatory

	DESCRIPTION

		"The slot number of this module."

	::= { ol51nnMTPLModEntry 1 }



ol51nnMTPLModDipNetwork OBJECT-TYPE

	SYNTAX INTEGER {

		isolated(2),

		ethernet-1(6),

		ethernet-2(7),

		ethernet-3(8)

		}

	ACCESS read-only

	STATUS mandatory

	DESCRIPTION

		"The network indicated by the module's dip switches."

	::= { ol51nnMTPLModEntry 2 }



ol51nnMTPLPortTable			 OBJECT-TYPE

	SYNTAX SEQUENCE OF Ol51nnMTPLPortEntry

	ACCESS not-accessible

	STATUS mandatory

	DESCRIPTION

		"A table of port-specific information for each port of

		this module type."

	::= { ol51nnMTPL 2 }



ol51nnMTPLPortEntry OBJECT-TYPE

	SYNTAX Ol51nnMTPLPortEntry

	ACCESS not-accessible

	STATUS mandatory

	DESCRIPTION

		"A list of module-specific information about a specific

		51nnM-TPL port in the concentrator."

	INDEX { ol51nnMTPLPortSlotIndex, ol51nnMTPLPortIndex }

	::= { ol51nnMTPLPortTable 1 }



Ol51nnMTPLPortEntry ::=

	SEQUENCE {

		ol51nnMTPLPortSlotIndex

			INTEGER,

		ol51nnMTPLPortIndex

			INTEGER,

		ol51nnMTPLPortAdminState

			INTEGER,

		ol51nnMTPLPortBuddySlot

			INTEGER,

		ol51nnMTPLPortBuddyPort

			INTEGER,

		ol51nnMTPLPortDipAdminState

			INTEGER,

		ol51nnMTPLPortLinkInteg

			INTEGER,

		ol51nnMTPLPortDipLinkInteg

			INTEGER,

		ol51nnMTPLPortSquelch

			INTEGER,

		ol51nnMTPLPortJabber

			INTEGER,

		ol51nnMTPLPortDipJabber

			INTEGER

		}



ol51nnMTPLPortSlotIndex OBJECT-TYPE

	SYNTAX INTEGER

	ACCESS read-only

	STATUS mandatory

	DESCRIPTION

		"The slot number of this port's module."

	::= { ol51nnMTPLPortEntry 1 }





ol51nnMTPLPortIndex OBJECT-TYPE

	SYNTAX INTEGER

	ACCESS read-only

	STATUS mandatory

	DESCRIPTION

		"The port number of this port."

	::= { ol51nnMTPLPortEntry 2 }



ol51nnMTPLPortAdminState OBJECT-TYPE

	SYNTAX INTEGER {

		enabled(1),

		disabled(2),

		redundant-primary(3),

		redundant-backup(4),

		remote-diagnostics(8)

		}

	ACCESS read-write

	STATUS mandatory

	DESCRIPTION

		"The desired state of this port.  Setting this port to

		be redundant or for remote diagnostics with invalid settings

		of buddy slot and buddy port will return the genError error."

	::= { ol51nnMTPLPortEntry 3 }



ol51nnMTPLPortBuddySlot OBJECT-TYPE

	SYNTAX INTEGER

	ACCESS read-write

	STATUS mandatory

	DESCRIPTION

		"The slot index of the redundant port's buddy.  To set

		a port to be redundant, the buddy's slot and port must

		be set to valid values.



		The buddy is automatically set to be redundant to this port.



		If the port is configured for remote diagnostics, then

		this contains the slot index of the backup buddy port.

		To configure a port for remote diagnostics, the buddy's

		slot and port must be set to valid values."

	::= { ol51nnMTPLPortEntry 4 }



ol51nnMTPLPortBuddyPort  OBJECT-TYPE

	SYNTAX INTEGER

	ACCESS read-write

	STATUS mandatory

	DESCRIPTION

		"The port index of the redundant port's buddy.  To set

		a port to be redundant, the buddy's slot and port must

		be set to valid values.



		The buddy is automatically set to be redundant to this port.



		If the port is configured for remote diagnostics, then

		this contains the port index of the backup buddy port.

		To configure a port for remote diagnostics, the buddy's

		slot and port must be set to valid values."

	::= { ol51nnMTPLPortEntry 5 }



ol51nnMTPLPortDipAdminState OBJECT-TYPE

	SYNTAX INTEGER {

		enabled(1),

		disabled(2)

		}

	ACCESS read-only

	STATUS mandatory

	DESCRIPTION

		"The state of this port as indicated by the port's dip

		switches."

	::= { ol51nnMTPLPortEntry 6 }



ol51nnMTPLPortLinkInteg OBJECT-TYPE

	SYNTAX INTEGER {

		enabled(1),

		disabled(2)

		}

	ACCESS read-write

	STATUS mandatory

	DESCRIPTION

		"The current link integrity configuration for this port."

	::= { ol51nnMTPLPortEntry 7 }



ol51nnMTPLPortDipLinkInteg OBJECT-TYPE

	SYNTAX INTEGER {

		enabled(1),

		disabled(2)

		}

	ACCESS read-only

	STATUS mandatory

	DESCRIPTION

		"The link integrity configuration as indicated by this

		module's dip switches."

	::= { ol51nnMTPLPortEntry 8 }



ol51nnMTPLPortSquelch OBJECT-TYPE

	SYNTAX INTEGER {

		normal(1), -- high squelch

		low(2)

		}

	ACCESS read-write

	STATUS mandatory

	DESCRIPTION

		"The current squelch configuration for this port.  See

		the module's user's guide for more information."

	::= { ol51nnMTPLPortEntry 9 }



ol51nnMTPLPortJabber OBJECT-TYPE

	SYNTAX INTEGER {

		enabled(1),

		disabled(2)

		}

	ACCESS read-write

	STATUS mandatory

	DESCRIPTION

		"The current receive jabber configuration for this port."

	::= { ol51nnMTPLPortEntry 10 }



ol51nnMTPLPortDipJabber OBJECT-TYPE

	SYNTAX INTEGER {

		enabled(1),

		disabled(2)

		}

	ACCESS read-only

	STATUS mandatory

	DESCRIPTION

		"The receive jabber configuration as indicated by this

		module's dip switches."

	::= { ol51nnMTPLPortEntry 11 }





--

-- ONline Ethernet 10BASE-T Per-Port Module

--



ol51nnMTPPLModTable OBJECT-TYPE

	SYNTAX SEQUENCE OF Ol51nnMTPPLModEntry

	ACCESS not-accessible

	STATUS mandatory

	DESCRIPTION

		"A list of module-specific information about a specific

		51nnM-TPPL module in the concentrator."

	::= { ol51nnMTPPL 1 }



ol51nnMTPPLModEntry OBJECT-TYPE

	SYNTAX Ol51nnMTPPLModEntry

	ACCESS not-accessible

	STATUS mandatory

	DESCRIPTION

		"A list of module-specific information about a specific

		51nnM-TPPL module in the concentrator."

	INDEX { ol51nnMTPPLModSlotIndex }

	::= { ol51nnMTPPLModTable 1 }



Ol51nnMTPPLModEntry ::=

	SEQUENCE {

		ol51nnMTPPLModSlotIndex

			INTEGER

		}



ol51nnMTPPLModSlotIndex OBJECT-TYPE

	SYNTAX INTEGER

	ACCESS read-only

	STATUS mandatory

	DESCRIPTION

		"The slot number of this module."

	::= { ol51nnMTPPLModEntry 1 }



ol51nnMTPPLPortTable			 OBJECT-TYPE

	SYNTAX SEQUENCE OF Ol51nnMTPPLPortEntry

	ACCESS not-accessible

	STATUS mandatory

	DESCRIPTION

		"A table of port-specific information for each port of

		this module type."

	::= { ol51nnMTPPL 2 }



ol51nnMTPPLPortEntry OBJECT-TYPE

	SYNTAX Ol51nnMTPPLPortEntry

	ACCESS not-accessible

	STATUS mandatory

	DESCRIPTION

		"A list of module-specific information about a specific

		51nnM-TPPL port in the concentrator."

	INDEX { ol51nnMTPPLPortSlotIndex, ol51nnMTPPLPortIndex }

	::= { ol51nnMTPPLPortTable 1 }



Ol51nnMTPPLPortEntry ::=

	SEQUENCE {

		ol51nnMTPPLPortSlotIndex

			INTEGER,

		ol51nnMTPPLPortIndex

			INTEGER,

		ol51nnMTPPLPortAdminState

			INTEGER,

		ol51nnMTPPLPortBuddySlot

			INTEGER,

		ol51nnMTPPLPortBuddyPort

			INTEGER,

		ol51nnMTPPLPortDipAdminState

			INTEGER,

		ol51nnMTPPLPortDipNetwork

			INTEGER,

		ol51nnMTPPLPortLinkInteg

			INTEGER,

		ol51nnMTPPLPortDipLinkInteg

			INTEGER,

		ol51nnMTPPLPortSquelch

			INTEGER,

		ol51nnMTPPLPortJabber

			INTEGER,

		ol51nnMTPPLPortDipJabber

			INTEGER

		}



ol51nnMTPPLPortSlotIndex OBJECT-TYPE

	SYNTAX INTEGER

	ACCESS read-only

	STATUS mandatory

	DESCRIPTION

		"The slot number of this port's module."

	::= { ol51nnMTPPLPortEntry 1 }





ol51nnMTPPLPortIndex OBJECT-TYPE

	SYNTAX INTEGER

	ACCESS read-only

	STATUS mandatory

	DESCRIPTION

		"The port number of this port."

	::= { ol51nnMTPPLPortEntry 2 }



ol51nnMTPPLPortAdminState OBJECT-TYPE

	SYNTAX INTEGER {

		enabled(1),

		disabled(2),

		redundant-primary(3),

		redundant-backup(4),

		remote-diagnostics(8)

		}

	ACCESS read-write

	STATUS mandatory

	DESCRIPTION

		"The desired state of this port.  Setting this port to

		be redundant or for remote diagnostics with invalid settings

		of buddy slot and buddy port will return the genError error."

	::= { ol51nnMTPPLPortEntry 3 }



ol51nnMTPPLPortBuddySlot OBJECT-TYPE

	SYNTAX INTEGER

	ACCESS read-write

	STATUS mandatory

	DESCRIPTION

		"The slot index of the redundant port's buddy.  To set

		a port to be redundant, the buddy's slot and port must

		be set to valid values.



		The buddy is automatically set to be redundant to this port.



		If the port is configured for remote diagnostics, then

		this contains the slot index of the backup buddy port.

		To configure a port for remote diagnostics, the buddy's

		slot and port must be set to valid values."



	::= { ol51nnMTPPLPortEntry 4 }



ol51nnMTPPLPortBuddyPort  OBJECT-TYPE

	SYNTAX INTEGER

	ACCESS read-write

	STATUS mandatory

	DESCRIPTION

		"The port index of the redundant port's buddy.  To set

		a port to be redundant, the buddy's slot and port must

		be set to valid values.



		The buddy is automatically set to be redundant to this port.



		If the port is configured for remote diagnostics, then

		this contains the port index of the backup buddy port.

		To configure a port for remote diagnostics, the buddy's

		slot and port must be set to valid values."

	::= { ol51nnMTPPLPortEntry 5 }



ol51nnMTPPLPortDipAdminState OBJECT-TYPE

	SYNTAX INTEGER {

		enabled(1),

		disabled(2)

		}

	ACCESS read-only

	STATUS mandatory

	DESCRIPTION

		"The state of this port as indicated by the port's dip

		switches."

	::= { ol51nnMTPPLPortEntry 6 }



ol51nnMTPPLPortDipNetwork OBJECT-TYPE

	SYNTAX INTEGER {

		isolated(2),

		ethernet-1(6),

		ethernet-2(7),

		ethernet-3(8)

		}

	ACCESS read-only

	STATUS mandatory

	DESCRIPTION

		"The network indicated by the port's dip switches."

	::= { ol51nnMTPPLPortEntry 7 }



ol51nnMTPPLPortLinkInteg OBJECT-TYPE

	SYNTAX INTEGER {

		enabled(1),

		disabled(2)

		}

	ACCESS read-write

	STATUS mandatory

	DESCRIPTION

		"The current link integrity configuration for this port."

	::= { ol51nnMTPPLPortEntry 8 }



ol51nnMTPPLPortDipLinkInteg OBJECT-TYPE

	SYNTAX INTEGER {

		enabled(1),

		disabled(2)

		}

	ACCESS read-only

	STATUS mandatory

	DESCRIPTION

		"The link integrity configuration as indicated by this

		module's dip switches."

	::= { ol51nnMTPPLPortEntry 9 }



ol51nnMTPPLPortSquelch OBJECT-TYPE

	SYNTAX INTEGER {

		normal(1), -- high squelch

		low(2)

		}

	ACCESS read-write

	STATUS mandatory

	DESCRIPTION

		"The current squelch configuration for this port.  See

		the module's user's guide for more information."

	::= { ol51nnMTPPLPortEntry 10 }



ol51nnMTPPLPortJabber OBJECT-TYPE

	SYNTAX INTEGER {

		enabled(1),

		disabled(2)

		}

	ACCESS read-write

	STATUS mandatory

	DESCRIPTION

		"The current receive jabber configuration for this port."

	::= { ol51nnMTPPLPortEntry 11 }



ol51nnMTPPLPortDipJabber OBJECT-TYPE

	SYNTAX INTEGER {

		enabled(1),

		disabled(2)

		}

	ACCESS read-only

	STATUS mandatory

	DESCRIPTION

		"The receive jabber configuration as indicated by this

		module's dip switches."

	::= { ol51nnMTPPLPortEntry 12 }



--

-- ONline Token Ring Media Module

--

ol52nnMTPModTable OBJECT-TYPE

	SYNTAX SEQUENCE OF Ol52nnMTPModEntry

	ACCESS not-accessible

	STATUS mandatory

	DESCRIPTION

		"A list of module-specific information about a specific

		52nnM-TP module in the concentrator."

	::= { ol52nnMTP 1 }



ol52nnMTPModEntry OBJECT-TYPE

	SYNTAX Ol52nnMTPModEntry

	ACCESS not-accessible

	STATUS mandatory

	DESCRIPTION

		"A description of the 52nnM-TP module attributes."

	INDEX { ol52nnMTPModSlotIndex }

	::= { ol52nnMTPModTable 1 }



Ol52nnMTPModEntry ::=

	SEQUENCE {

		ol52nnMTPModSlotIndex

			INTEGER,

		ol52nnMTPModRingSpeed

			INTEGER,

		ol52nnMTPModDipRingSpeed

			INTEGER,

		ol52nnMTPModCableImp

			INTEGER,

		ol52nnMTPModDipCableImp

			INTEGER

		}



ol52nnMTPModSlotIndex OBJECT-TYPE

	SYNTAX INTEGER

	ACCESS read-only

	STATUS mandatory

	DESCRIPTION

		"A unique value that identifies a particular module.  Its

		value ranges between 1 and olModSlotNumber.  The module

		identified by a particular value of this index is the same

		module as indentified by the same value of

		olModSlotIndex."

	::= { ol52nnMTPModEntry 1 }



ol52nnMTPModRingSpeed OBJECT-TYPE

	SYNTAX INTEGER {

		fourMegabit(1),

		sixteenMegabit(2)

		}

	ACCESS read-write

	STATUS mandatory

	DESCRIPTION

		"The ring's bandwidth."

	::= { ol52nnMTPModEntry 2 }



ol52nnMTPModDipRingSpeed OBJECT-TYPE

	SYNTAX INTEGER {

		fourMegabit(1),

		sixteenMegabit(2)

		}

	ACCESS read-only

	STATUS mandatory

	DESCRIPTION

		"The dip switch setting for the ring's bandwidth."

	::= { ol52nnMTPModEntry 3 }



ol52nnMTPModCableImp OBJECT-TYPE

	SYNTAX INTEGER {

		ohm100(1),

		ohm150(2)

		}

	ACCESS read-write

	STATUS mandatory

	DESCRIPTION

		"The setting of this module's port impedance matching, with

		100 ohm corresponding to unshielded twisted pair cabling and

		150 ohm corresponding to shielded twisted pair cabling.

		This setting is valid for all ports on this module."

	::= { ol52nnMTPModEntry 4 }



ol52nnMTPModDipCableImp OBJECT-TYPE

	SYNTAX INTEGER {

		ohm100(1),

		ohm150(2)

		}

	ACCESS read-only

	STATUS mandatory

	DESCRIPTION

		"The dip switch setting for the module's port impedance

		matching."

	::= { ol52nnMTPModEntry 5 }



ol52nnMTPPortTable OBJECT-TYPE

	SYNTAX SEQUENCE OF Ol52nnMTPPortEntry

	ACCESS not-accessible

	STATUS mandatory

	DESCRIPTION

		"A table of port-specific information for each port of

		this module type."

	::= { ol52nnMTP 2 }



ol52nnMTPPortEntry OBJECT-TYPE

	SYNTAX Ol52nnMTPPortEntry

	ACCESS not-accessible

	STATUS mandatory

	DESCRIPTION

		"A description of 52nnM-TP port attributes."

	INDEX { ol52nnMTPPortSlotIndex, ol52nnMTPPortIndex }

	::= { ol52nnMTPPortTable 1 }



Ol52nnMTPPortEntry ::=

	SEQUENCE {

		ol52nnMTPPortSlotIndex

			INTEGER,

		ol52nnMTPPortIndex

			INTEGER,

		ol52nnMTPPortDipAdminState

			INTEGER,

		ol52nnMTPPortStationType

			INTEGER

		}



ol52nnMTPPortSlotIndex OBJECT-TYPE

	SYNTAX INTEGER

	ACCESS read-only

	STATUS mandatory

	DESCRIPTION

		"The slot number of this port's module."

	::= { ol52nnMTPPortEntry 1 }





ol52nnMTPPortIndex OBJECT-TYPE

	SYNTAX INTEGER

	ACCESS read-only

	STATUS mandatory

	DESCRIPTION

		"The port number of this port."

	::= { ol52nnMTPPortEntry 2 }



ol52nnMTPPortDipAdminState OBJECT-TYPE

	SYNTAX INTEGER {

		enabled(1),

		disabled(2)

		}

	ACCESS read-only

	STATUS mandatory

	DESCRIPTION

		"The state of this port as indicated by the port's dip

		switches."

	::= { ol52nnMTPPortEntry 3 }



ol52nnMTPPortStationType OBJECT-TYPE

	SYNTAX INTEGER {

		mac-present(1),

		mac-not-present(2)

		}

	ACCESS read-write

	STATUS mandatory

	DESCRIPTION

		"Determines whether the station connected to this port

		has a MAC address."

	::= { ol52nnMTPPortEntry 4 }



ol52nnMTPTrunkTable OBJECT-TYPE

	SYNTAX SEQUENCE OF Ol52nnMTPTrunkEntry

	ACCESS not-accessible

	STATUS mandatory

	DESCRIPTION

		"A list of trunk-specific information about each trunk

		for this module type."

	::= { ol52nnMTP 3 }



ol52nnMTPTrunkEntry OBJECT-TYPE

	SYNTAX Ol52nnMTPTrunkEntry

	ACCESS not-accessible

	STATUS mandatory

	DESCRIPTION

		"A description of 52nnM-TP trunk attributes."

	INDEX { ol52nnMTPTrunkSlotIndex, ol52nnMTPTrunkIndex }

	::= { ol52nnMTPTrunkTable 1 }



Ol52nnMTPTrunkEntry ::=

	SEQUENCE {

		ol52nnMTPTrunkSlotIndex

			INTEGER,

		ol52nnMTPTrunkIndex

			INTEGER,

		ol52nnMTPTrunkDipAdminState

			INTEGER

		}



ol52nnMTPTrunkSlotIndex OBJECT-TYPE

	SYNTAX INTEGER

	ACCESS read-only

	STATUS mandatory

	DESCRIPTION

		"A unique value that identifies a particular module.  Its

		value ranges between 1 and olModSlotNumber.  The module

		identified by a particular value of this index is the same

		module as indentified by the same value of

		olTrunkSlotIndex."

	::= { ol52nnMTPTrunkEntry 1 }





ol52nnMTPTrunkIndex OBJECT-TYPE

	SYNTAX INTEGER

	ACCESS read-only

	STATUS mandatory

	DESCRIPTION

		"The trunk number for this trunk."

	::= { ol52nnMTPTrunkEntry 2 }



ol52nnMTPTrunkDipAdminState OBJECT-TYPE

	SYNTAX INTEGER {

		enabled(1),

		disabled(2)

		}

	ACCESS read-only

	STATUS mandatory

	DESCRIPTION

		"The state of this trunk as indicated by the trunk's dip

		switches."

	::= { ol52nnMTPTrunkEntry 3 }



--

-- ONline Token Fiberoptic Repeater Module

--

ol52nnMFRModTable OBJECT-TYPE

	SYNTAX SEQUENCE OF Ol52nnMFRModEntry

	ACCESS not-accessible

	STATUS mandatory

	DESCRIPTION

		"A list of module-specific information about a specific

		52nnM-FR module in the concentrator."

	::= { ol52nnMFR 1 }



ol52nnMFRModEntry OBJECT-TYPE

	SYNTAX Ol52nnMFRModEntry

	ACCESS not-accessible

	STATUS mandatory

	DESCRIPTION

		"A description of the 52nnM-FR module attributes."

	INDEX { ol52nnMFRModSlotIndex }

	::= { ol52nnMFRModTable 1 }



Ol52nnMFRModEntry ::=

	SEQUENCE {

		ol52nnMFRModSlotIndex

			INTEGER,

		ol52nnMFRModRingSpeed

			INTEGER,

		ol52nnMFRModDipRingSpeed

			INTEGER

		}



ol52nnMFRModSlotIndex OBJECT-TYPE

	SYNTAX INTEGER

	ACCESS read-only

	STATUS mandatory

	DESCRIPTION

		"The slot number of this module."

	::= { ol52nnMFRModEntry 1 }



ol52nnMFRModRingSpeed OBJECT-TYPE

	SYNTAX INTEGER {

		fourMegabit(1),

		sixteenMegabit(2)

		}

	ACCESS read-write

	STATUS mandatory

	DESCRIPTION

		"The ring's bandwidth."

	::= { ol52nnMFRModEntry 2 }



ol52nnMFRModDipRingSpeed OBJECT-TYPE

	SYNTAX INTEGER {

		fourMegabit(1),

		sixteenMegabit(2)

		}

	ACCESS read-only

	STATUS mandatory

	DESCRIPTION

		"The dip switch setting for the ring's bandwidth."

	::= { ol52nnMFRModEntry 3 }



ol52nnMFRPortTable OBJECT-TYPE

	SYNTAX SEQUENCE OF Ol52nnMFRPortEntry

	ACCESS not-accessible

	STATUS mandatory

	DESCRIPTION

		"A table of port-specific information for each port of

		this module type."

	::= { ol52nnMFR 2 }



ol52nnMFRPortEntry OBJECT-TYPE

	SYNTAX Ol52nnMFRPortEntry

	ACCESS not-accessible

	STATUS mandatory

	DESCRIPTION

		"A description of 52nnM-FR port attributes."

	INDEX { ol52nnMFRPortSlotIndex, ol52nnMFRPortIndex }

	::= { ol52nnMFRPortTable 1 }



Ol52nnMFRPortEntry ::=

	SEQUENCE {

		ol52nnMFRPortSlotIndex

			INTEGER,

		ol52nnMFRPortIndex

			INTEGER,

		ol52nnMFRPortDipAdminState

			INTEGER,

		ol52nnMFRPortCableImp

			INTEGER,

		ol52nnMFRPortStationType

			INTEGER

		}



ol52nnMFRPortSlotIndex OBJECT-TYPE

	SYNTAX INTEGER

	ACCESS read-only

	STATUS mandatory

	DESCRIPTION

		"The slot number of this port's module."

	::= { ol52nnMFRPortEntry 1 }





ol52nnMFRPortIndex OBJECT-TYPE

	SYNTAX INTEGER

	ACCESS read-only

	STATUS mandatory

	DESCRIPTION

		"The port number of this port."

	::= { ol52nnMFRPortEntry 2 }



ol52nnMFRPortDipAdminState OBJECT-TYPE

	SYNTAX INTEGER {

		enabled(1),

		disabled(2)

		}

	ACCESS read-only

	STATUS mandatory

	DESCRIPTION

		"The state of this port as indicated by the port's dip

		switches."

	::= { ol52nnMFRPortEntry 3 }



ol52nnMFRPortCableImp OBJECT-TYPE

	SYNTAX INTEGER {

		ohm100(1),

		ohm150(2)

		}

	ACCESS read-only

	STATUS mandatory

	DESCRIPTION

		"The setting of this port's impedance matching, with 100 ohm

		corresponding to unshielded twisted pair cabling and 150 ohm

		corresponding to shielded twisted pair cabling."

	::= { ol52nnMFRPortEntry 4 }



ol52nnMFRPortStationType OBJECT-TYPE

	SYNTAX INTEGER {

		mac-present(1),

		mac-not-present(2)

		}

	ACCESS read-write

	STATUS mandatory

	DESCRIPTION

		"Determines whether the station connected to this port

		has a MAC address."

	::= { ol52nnMFRPortEntry 5 }



ol52nnMFRTrunkTable OBJECT-TYPE

	SYNTAX SEQUENCE OF Ol52nnMFRTrunkEntry

	ACCESS not-accessible

	STATUS mandatory

	DESCRIPTION

		"A list of trunk-specific information about each trunk

		for this module type."

	::= { ol52nnMFR 3 }



ol52nnMFRTrunkEntry OBJECT-TYPE

	SYNTAX Ol52nnMFRTrunkEntry

	ACCESS not-accessible

	STATUS mandatory

	DESCRIPTION

		"A description of 52nnM-FR trunk attributes."

	INDEX { ol52nnMFRTrunkSlotIndex, ol52nnMFRTrunkIndex }

	::= { ol52nnMFRTrunkTable 1 }



Ol52nnMFRTrunkEntry ::=

	SEQUENCE {

		ol52nnMFRTrunkSlotIndex

			INTEGER,

		ol52nnMFRTrunkIndex

			INTEGER,

		ol52nnMFRTrunkDipAdminState

			INTEGER,

		ol52nnMFRTrunkCableMon

			INTEGER,

		ol52nnMFRTrunkDipCableMon

			INTEGER,

		ol52nnMFRTrunkCompMode

			INTEGER,

		ol52nnMFRTrunkDipCompMode

			INTEGER,

		ol52nnMFRTrunkNetMapState

			INTEGER,

		ol52nnMFRTrunkExtBcnRecovery

			INTEGER



			  ,

		ol52nnMFRTrunkBuddySlot

			INTEGER,

		ol52nnMFRTrunkAdminState

			INTEGER



		}



ol52nnMFRTrunkSlotIndex OBJECT-TYPE

	SYNTAX INTEGER

	ACCESS read-only

	STATUS mandatory

	DESCRIPTION

		"A unique value that identifies a particular module.  Its

		value ranges between 1 and olModSlotNumber.  The module

		identified by a particular value of this index is the same

		module as indentified by the same value of

		olTrunkSlotIndex."

	::= { ol52nnMFRTrunkEntry 1 }





ol52nnMFRTrunkIndex OBJECT-TYPE

	SYNTAX INTEGER

	ACCESS read-only

	STATUS mandatory

	DESCRIPTION

		"The trunk number of this trunk."

	::= { ol52nnMFRTrunkEntry 2 }



ol52nnMFRTrunkDipAdminState OBJECT-TYPE

	SYNTAX INTEGER {

		enabled(1),

		disabled(2)

		}

	ACCESS read-only

	STATUS mandatory

	DESCRIPTION

		"The state of this trunk as indicated by the trunk's dip

		switches."

	::= { ol52nnMFRTrunkEntry 3 }



ol52nnMFRTrunkCableMon OBJECT-TYPE

	SYNTAX INTEGER {

		enabled(1),

		disabled(2),

		notApplicable(3)

	}

	ACCESS read-write

	STATUS mandatory

	DESCRIPTION

		"The cable monitor configuration for this trunk. This

		does not apply to fiber trunks."

	::= { ol52nnMFRTrunkEntry 4 }



ol52nnMFRTrunkDipCableMon OBJECT-TYPE

	SYNTAX INTEGER {

		enabled(1),

		disabled(2),

		notApplicable(3)

	}

	ACCESS read-only

	STATUS mandatory

	DESCRIPTION

		"The cable monitor configuration as indicated by this trunk's

		dip switches. This does not apply to fiber trunks."

	::= { ol52nnMFRTrunkEntry 5 }





ol52nnMFRTrunkCompMode OBJECT-TYPE

	SYNTAX INTEGER {

		enabled(1),

		disabled(2),

		notApplicable(3)

	}

	ACCESS read-write

	STATUS mandatory

	DESCRIPTION

		"The compatibility mode for this trunk. This

		only applies to fiber trunks."

	::= { ol52nnMFRTrunkEntry 6 }



ol52nnMFRTrunkDipCompMode OBJECT-TYPE

	SYNTAX INTEGER {

		enabled(1),

		disabled(2),

		notApplicable(3)

	}

	ACCESS read-only

	STATUS mandatory

	DESCRIPTION

		"The compatibility mode as indicated by this trunk's

		dip switches. This only applies to fiber trunks."

	::= { ol52nnMFRTrunkEntry 7 }





ol52nnMFRTrunkNetMapState OBJECT-TYPE

	SYNTAX INTEGER {

		notApplicable(1),

		internal(2),

		external(3)

	}

	ACCESS read-write

	STATUS mandatory

	DESCRIPTION

		"The map state of the copper ring-in trunk.  This

		should be set to external for ring-in trunks which

		connect to external hubs.  The mapping logic will not

		operate on trunks which are set to external.  This

		prevents incorrect mapping which can occur when a

		module in one hub detects the mapping signal from

		another hub. This attribute only applies to copper

		ring-in trunks."

	::= { ol52nnMFRTrunkEntry 8 }





ol52nnMFRTrunkExtBcnRecovery OBJECT-TYPE

	SYNTAX INTEGER {

		exists(1),

		nonExists(2),

		notApplicable(3)

	}

	ACCESS read-write

	STATUS mandatory

	DESCRIPTION

		"Indicates whether the trunk is connected to a

		segment that will perform beacon recovery.  This

		should be set to exists(1) for trunks which connect

		to hubs which perform beacon recovery.  This attribute

		is used to determine the fault domain when resolving a

		beaconing condition.



		The beacon recovery process will resolve beaconing on

		trunks with this attribute set to nonExists(2) before

		trunks with the attribute set to exists(1) are resolved.

		For backplane trunks, setting to a value other than

		notApplicable will return invalidData error.  The

		default value is nonExists(2)."

	::= { ol52nnMFRTrunkEntry 9 }





ol52nnMFRTrunkBuddySlot OBJECT-TYPE

	SYNTAX INTEGER

	ACCESS read-write

	STATUS mandatory

	DESCRIPTION

		"The slot index of the redundant trunk's buddy.  To

		 set a trunk to be redundant, the buddy's slot must

		 be set to a valid value.  This object is applicable

		 to fiber trunks only.  This value is only considered

		 valid if the corresponding TrunkAdminState object

		 for this trunk is configured for redundancy.

		 Copper and backplane trunks will return invdata(6).



		 If both the ring-in and ring-out trunks of a module

		 are configured for redundancy, they must both be

		 redundant to the same module.



		 The buddy slot object for this slot is automatically

		 set to this trunk."

	::= { ol52nnMFRTrunkEntry 10 }



ol52nnMFRTrunkAdminState OBJECT-TYPE

	SYNTAX INTEGER {

		enabled(1),

		disabled(2),

		redundant-primary(3),

		redundant-standby(4)

	      }

	ACCESS read-write

	STATUS mandatory

	DESCRIPTION

		"The desired state of this trunk.  Enabling a trunk

		allows the trunk to pass network traffic.  This

		object may be used to configure fiber trunk

		redundancy.  Setting a trunk to be redundant-primary(3)

		or redundant-backup(4) requires that the

		ol52nnMFRTrunkBuddySlot object be set to a valid value.

		If fiber trunk redundancy is already configured,

		setting this object to a redundant state will remove

		the previous configuration."

	::= { ol52nnMFRTrunkEntry 11 }





--

-- ONline Ethernet Terminal Server Module

--





ol51nnMTSModTable OBJECT-TYPE

	SYNTAX SEQUENCE OF Ol51nnMTSModEntry

	ACCESS not-accessible

	STATUS mandatory

	DESCRIPTION

		"A table of module-specific information for each

		51nnM-TS module in the concentrator."

	::= { ol51nnMTS 1 }



ol51nnMTSModEntry OBJECT-TYPE

       SYNTAX Ol51nnMTSModEntry

       ACCESS not-accessible

       STATUS mandatory

       DESCRIPTION

	       "A list of module information for each 51nnM-TS module

	       in the concentrator."

       INDEX { ol51nnMTSModSlotIndex }

       ::= { ol51nnMTSModTable 1 }



Ol51nnMTSModEntry ::=

       SEQUENCE {

	       ol51nnMTSModSlotIndex

		       INTEGER,

	       ol51nnMTSModProtocols

		       DisplayString,

	       ol51nnMTSModIpAddress

		       IpAddress,

	       ol51nnMTSModTCPPort

		       INTEGER,

	       ol51nnMTSModStationAddr

		       OCTET STRING,

	       ol51nnMTSModDipNetwork

		       INTEGER,

	       ol51nnMTSModCPURev

		       DisplayString

	       }



ol51nnMTSModSlotIndex OBJECT-TYPE

       SYNTAX INTEGER

       ACCESS read-only

       STATUS mandatory

       DESCRIPTION

	       "The slot number of this module."

       ::= { ol51nnMTSModEntry 1 }



ol51nnMTSModProtocols OBJECT-TYPE

	SYNTAX DisplayString

	ACCESS read-only

	STATUS mandatory

	DESCRIPTION

		"A textual description of the protocols supported by

		this module"

	::= { ol51nnMTSModEntry 2 }



ol51nnMTSModIpAddress OBJECT-TYPE

       SYNTAX IpAddress

       ACCESS read-only

       STATUS mandatory

       DESCRIPTION

	       "The IP Address of the terminal server."

       ::= { ol51nnMTSModEntry 3 }



ol51nnMTSModTCPPort OBJECT-TYPE

       SYNTAX INTEGER

       ACCESS read-only

       STATUS mandatory

       DESCRIPTION

	       "The TCP port number of the the terminal server's remote

		console port."

       ::= { ol51nnMTSModEntry 4 }



ol51nnMTSModStationAddr OBJECT-TYPE

       SYNTAX OCTET STRING (SIZE(6))

       ACCESS read-only

       STATUS mandatory

       DESCRIPTION

	       "A 6 octet address that uniquely identifies this module.

	       The station address is the mac address of the terminal server."

       ::= { ol51nnMTSModEntry 5 }



ol51nnMTSModDipNetwork OBJECT-TYPE

       SYNTAX INTEGER {

	       isolated(2),

	       ethernet-1(6),

	       ethernet-2(7),

	       ethernet-3(8)

	       }

       ACCESS read-only

       STATUS mandatory

       DESCRIPTION

	       "The network indicated by the module's dip switches."

       ::= { ol51nnMTSModEntry 6 }



ol51nnMTSModCPURev OBJECT-TYPE

       SYNTAX DisplayString (SIZE(1..10))

       ACCESS read-only

       STATUS mandatory

       DESCRIPTION

	       "The terminal server's CPU revision."

       ::= { ol51nnMTSModEntry 7 }





ol51nnMTSPortTable OBJECT-TYPE

       SYNTAX SEQUENCE OF Ol51nnMTSPortEntry

       ACCESS not-accessible

       STATUS mandatory

       DESCRIPTION

	       "A table of information that contains port-specific

	       information for each port on each 51nnM-TS module."

       ::= { ol51nnMTS 2 }



ol51nnMTSPortEntry OBJECT-TYPE

       SYNTAX Ol51nnMTSPortEntry

       ACCESS not-accessible

       STATUS mandatory

       DESCRIPTION

	       "A list of information about a specific port on a

	       51nnM-TS module."

       INDEX { ol51nnMTSPortSlotIndex, ol51nnMTSPortIndex }

       ::= { ol51nnMTSPortTable 1 }



Ol51nnMTSPortEntry ::=

       SEQUENCE {

	       ol51nnMTSPortSlotIndex

		       INTEGER,

	       ol51nnMTSPortIndex

		       INTEGER,

	       ol51nnMTSPortAdminState

		       INTEGER,

	       ol51nnMTSPortOperState

		       INTEGER

	       }



ol51nnMTSPortSlotIndex OBJECT-TYPE

       SYNTAX INTEGER

       ACCESS read-only

       STATUS mandatory

       DESCRIPTION

		"The slot number for this port."

       ::= { ol51nnMTSPortEntry 1 }



ol51nnMTSPortIndex OBJECT-TYPE

       SYNTAX INTEGER

       ACCESS read-only

       STATUS mandatory

       DESCRIPTION

		"The port number of this port."

       ::= { ol51nnMTSPortEntry 2 }



ol51nnMTSPortAdminState OBJECT-TYPE

       SYNTAX INTEGER {

	       enabled(1),

	       disabled(2),

	       local(6),

	       remote(7)

	       }

       ACCESS read-write

       STATUS mandatory

       DESCRIPTION

	       "The administrative state of this port."

       ::= { ol51nnMTSPortEntry 3 }



ol51nnMTSPortOperState OBJECT-TYPE

       SYNTAX INTEGER {

	       idle(1),

	       local(2),

	       connected(3)

	       }

       ACCESS read-only

       STATUS mandatory

       DESCRIPTION

	       "The operational mode of this port."

       ::= { ol51nnMTSPortEntry 4 }





--

-- ONline Ethernet FOIRL MOdule

--





ol51nnMFLModTable OBJECT-TYPE

	SYNTAX SEQUENCE OF Ol51nnMFLModEntry

	ACCESS not-accessible

	STATUS mandatory

	DESCRIPTION

		"A table of module-specific information for each

		51nnM-FL module in the concentrator."

	::= { ol51nnMFL 1 }



ol51nnMFLModEntry OBJECT-TYPE

	SYNTAX Ol51nnMFLModEntry

	ACCESS not-accessible

	STATUS mandatory

	DESCRIPTION

		"A list of module-specific information associated

		with a particular 51nnM-FL module in the concentrator."

	INDEX { ol51nnMFLModSlotIndex }

	::= { ol51nnMFLModTable 1 }



Ol51nnMFLModEntry ::=

	SEQUENCE {

		ol51nnMFLModSlotIndex

			INTEGER,

		ol51nnMFLModDipNetwork

			INTEGER

		}



ol51nnMFLModSlotIndex OBJECT-TYPE

	SYNTAX INTEGER

	ACCESS read-only

	STATUS mandatory

	DESCRIPTION

		"The slot number of this module."

	::= { ol51nnMFLModEntry 1 }



ol51nnMFLModDipNetwork OBJECT-TYPE

	SYNTAX INTEGER {

		isolated(2),

		ethernet-1(6),

		ethernet-2(7),

		ethernet-3(8)

		}

	ACCESS read-only

	STATUS mandatory

	DESCRIPTION

		"The network indicated by the module's dip switches."

	::= { ol51nnMFLModEntry 2 }



ol51nnMFLPortTable OBJECT-TYPE

	SYNTAX SEQUENCE OF Ol51nnMFLPortEntry

	ACCESS not-accessible

	STATUS mandatory

	DESCRIPTION

		"A table of port-specific information for each port

		of each 51nnM-FL module."

	::= { ol51nnMFL 2 }



ol51nnMFLPortEntry OBJECT-TYPE

	SYNTAX Ol51nnMFLPortEntry

	ACCESS not-accessible

	STATUS mandatory

	DESCRIPTION

		"A list of information about a specific port on a

		51nnM-FL module."

	INDEX { ol51nnMFLPortSlotIndex, ol51nnMFLPortIndex }

	::= { ol51nnMFLPortTable 1 }



Ol51nnMFLPortEntry ::=

	SEQUENCE {

		ol51nnMFLPortSlotIndex

			INTEGER,

		ol51nnMFLPortIndex

			INTEGER,

		ol51nnMFLPortAdminState

			INTEGER,

		ol51nnMFLPortBuddySlot

			INTEGER,

		ol51nnMFLPortBuddyPort

			INTEGER,

		ol51nnMFLPortDipAdminState

			INTEGER

		}



	ol51nnMFLPortSlotIndex OBJECT-TYPE

	SYNTAX INTEGER

	ACCESS read-only

	STATUS mandatory

	DESCRIPTION

		"A unique value that identifies a particular module.  Its

		value ranges between 1 and olModSlotNumber.  The module

		identified by a particular value of this index is the same

		module as indentified by the same value of

		olPortSlotIndex."

	::= { ol51nnMFLPortEntry 1 }





ol51nnMFLPortIndex OBJECT-TYPE

	SYNTAX INTEGER

	ACCESS read-only

	STATUS mandatory

	DESCRIPTION

		"The port number of this port."

	::= { ol51nnMFLPortEntry 2 }





ol51nnMFLPortAdminState OBJECT-TYPE

	SYNTAX INTEGER {

		enabled(1),

		disabled(2),

		redundant-primary(3),

		redundant-backup(4),

		redundant-rfs(5)

		}

	ACCESS read-write

	STATUS mandatory

	DESCRIPTION

		"The desired state of this port.  Setting this port to

		be redundant with invalid settings of buddy slot and

		buddy port will return invalidData error. Remote

		Failure Signaling (RFS), is set on connected module

		port to permit transmit error detection on local port.

		Port must be set to be RFS when connected port is set to

		be redundant"

	::= { ol51nnMFLPortEntry 3 }



ol51nnMFLPortBuddySlot OBJECT-TYPE

	SYNTAX INTEGER

	ACCESS read-write

	STATUS mandatory

	DESCRIPTION

		"The slot index of the redundant port's buddy.   "

	::= { ol51nnMFLPortEntry 4 }





ol51nnMFLPortBuddyPort  OBJECT-TYPE

	SYNTAX INTEGER

	ACCESS read-write

	STATUS mandatory

	DESCRIPTION

		"The port index of the redundant port's buddy."

	::= { ol51nnMFLPortEntry 5 }





ol51nnMFLPortDipAdminState OBJECT-TYPE

	SYNTAX INTEGER {

		enabled(1),

		disabled(2),

		redundant-primary(3),

		redundant-backup(4),

		redundant-rfs(5)

		}

	ACCESS read-only

	STATUS mandatory

	DESCRIPTION

		"The state of this port as indicated by the port's dip

		switches."

	::= { ol51nnMFLPortEntry 6 }





--

-- ONline Redundant Controller Module

--



ol50nnMRCTLModTable OBJECT-TYPE

	SYNTAX SEQUENCE OF Ol50nnMRCTLModEntry

	ACCESS not-accessible

	STATUS mandatory

	DESCRIPTION

		"A table that contains information about each 50nnM-RCTL

		in the concentrator.  "

	::= { ol50nnMRCTL 1 }



ol50nnMRCTLModEntry OBJECT-TYPE

	SYNTAX Ol50nnMRCTLModEntry

	ACCESS not-accessible

	STATUS mandatory

	DESCRIPTION

		"A list of information for each 50nnM-RCTL module

		in the concentrator."

	INDEX { ol50nnMRCTLModSlotIndex }

	::= { ol50nnMRCTLModTable 1 }



Ol50nnMRCTLModEntry ::=

	SEQUENCE {

		ol50nnMRCTLModSlotIndex

			INTEGER,

		ol50nnMRCTLModOperState

			INTEGER,

		ol50nnMRCTLModClockStatus

			INTEGER,

		ol50nnMRCTLModTempStatus

			INTEGER

		}



ol50nnMRCTLModSlotIndex OBJECT-TYPE

	SYNTAX INTEGER

	ACCESS read-only

	STATUS mandatory

	DESCRIPTION

		"The slot number for this module."

	::= { ol50nnMRCTLModEntry 1 }



ol50nnMRCTLModOperState OBJECT-TYPE

	SYNTAX INTEGER {

		active(1),

		standby(2)

		}

	ACCESS read-only

	STATUS mandatory

	DESCRIPTION

		"The operational state of the 50nnM-RCTL module.  Specifically,

		this is an indicator of whether the 50nnM-RCTL module is

		providing clock signals to the backplane.  An active 50nnM-RCTL

		module provides clock signals to the backplane while a standby

		50nnM-RCTL module does not.  Note that only one 50nnM-RCTL

		module will be active at any given time; all other 50nnM-RCTL

		modules in the concentrator will be in standby mode."

	::= { ol50nnMRCTLModEntry 2 }



ol50nnMRCTLModClockStatus OBJECT-TYPE

	SYNTAX INTEGER {

		okay(1),

		faulty(2)

		}

	ACCESS read-only

	STATUS mandatory

	DESCRIPTION

		"The current status of the on-board clocks on this module."

	::= { ol50nnMRCTLModEntry 3 }



ol50nnMRCTLModTempStatus OBJECT-TYPE

	SYNTAX INTEGER {

		okay(1),

		extremeTemp(2)

		}

	ACCESS read-only

	STATUS mandatory

	DESCRIPTION

		"The temperature as detected by the probe on this module."

	::= { ol50nnMRCTLModEntry 4 }



--

-- ONline Ethernet 10BASE-F Module

--



ol51nnMFBModTable OBJECT-TYPE

	SYNTAX SEQUENCE OF Ol51nnMFBModEntry

	ACCESS not-accessible

	STATUS mandatory

	DESCRIPTION

		"A list of module-specific information associated

		with a particular 51nnM-FB module in the concentrator."

	::= { ol51nnMFB 1 }



ol51nnMFBModEntry OBJECT-TYPE

	SYNTAX Ol51nnMFBModEntry

	ACCESS not-accessible

	STATUS mandatory

	DESCRIPTION

		"A list of module-specific information about a specific

		51nnM-FB module in the concentrator."

	INDEX { ol51nnMFBModSlotIndex }

	::= { ol51nnMFBModTable 1 }



Ol51nnMFBModEntry ::=

	SEQUENCE {

		ol51nnMFBModSlotIndex

			INTEGER,

		ol51nnMFBModDipNetwork

			INTEGER,

		ol51nnMFBModLLW

			INTEGER,

		ol51nnMFBModDipLLW

			INTEGER

		}



ol51nnMFBModSlotIndex OBJECT-TYPE

	SYNTAX INTEGER

	ACCESS read-only

	STATUS mandatory

	DESCRIPTION

		"The slot number of this module."

	::= { ol51nnMFBModEntry 1 }



ol51nnMFBModDipNetwork OBJECT-TYPE

	SYNTAX INTEGER {

		isolated(2),

		ethernet-1(6),

		ethernet-2(7),

		ethernet-3(8)

		}

	ACCESS read-only

	STATUS mandatory

	DESCRIPTION

		"The network indicated by the module's dip switches."

	::= { ol51nnMFBModEntry 2 }



ol51nnMFBModLLW OBJECT-TYPE

	SYNTAX INTEGER {

		enabled(1),

		disabled(2)

		}

	ACCESS read-write

	STATUS mandatory

	DESCRIPTION

		"The current state of this module's low light warning

		configuration.  Enabling this feature causes the module to

		check for low light and to issue a warning if low light is

		present.  Disabling low light has the advantage of faster

		redundancy switchover in the event of a port error."

	::= { ol51nnMFBModEntry 3 }



ol51nnMFBModDipLLW OBJECT-TYPE

	SYNTAX INTEGER {

		enabled(1),

		disabled(2)

		}

	ACCESS read-only

	STATUS mandatory

	DESCRIPTION

		"The low light warning configuration indicated by this module's

		dip switches."

	::= { ol51nnMFBModEntry 4 }



ol51nnMFBPortTable OBJECT-TYPE

	SYNTAX SEQUENCE OF Ol51nnMFBPortEntry

	ACCESS not-accessible

	STATUS mandatory

	DESCRIPTION

		"A table of port-specific information for each port of

		this module type."

	::= { ol51nnMFB 2 }



ol51nnMFBPortEntry OBJECT-TYPE

	SYNTAX Ol51nnMFBPortEntry

	ACCESS not-accessible

	STATUS mandatory

	DESCRIPTION

		"A list of module-specific information about a specific

		51nnM-FB port in the concentrator."

	INDEX { ol51nnMFBPortSlotIndex, ol51nnMFBPortIndex }

	::= { ol51nnMFBPortTable 1 }



Ol51nnMFBPortEntry ::=

	SEQUENCE {

		ol51nnMFBPortSlotIndex

			INTEGER,

		ol51nnMFBPortIndex

			INTEGER,

		ol51nnMFBPortAdminState

			INTEGER,

		ol51nnMFBPortBuddySlot

			INTEGER,

		ol51nnMFBPortBuddyPort

			INTEGER,

		ol51nnMFBPortDipAdminState

			INTEGER

		}



ol51nnMFBPortSlotIndex OBJECT-TYPE

	SYNTAX INTEGER

	ACCESS read-only

	STATUS mandatory

	DESCRIPTION

		"The slot number of this port's module."

	::= { ol51nnMFBPortEntry 1 }





ol51nnMFBPortIndex OBJECT-TYPE

	SYNTAX INTEGER

	ACCESS read-only

	STATUS mandatory

	DESCRIPTION

		"The port number of this port."

	::= { ol51nnMFBPortEntry 2 }



ol51nnMFBPortAdminState OBJECT-TYPE

	SYNTAX INTEGER {

		enabled(1),

		disabled(2),

		redundant-primary(3),

		redundant-backup(4)

		}

	ACCESS read-write

	STATUS mandatory

	DESCRIPTION

		"The desired state of this port.  Setting this port to

		be redundant with invalid settings of buddy slot and

		buddy port will return the genError error."

	::= { ol51nnMFBPortEntry 3 }



ol51nnMFBPortBuddySlot OBJECT-TYPE

	SYNTAX INTEGER

	ACCESS read-write

	STATUS mandatory

	DESCRIPTION

		"The slot index of the redundant port's buddy.  To set

		a port to be redundant, the buddy's slot and port must

		be set to valid values.



		The buddy is automatically set to be redundant to this port."

	::= { ol51nnMFBPortEntry 4 }



ol51nnMFBPortBuddyPort  OBJECT-TYPE

	SYNTAX INTEGER

	ACCESS read-write

	STATUS mandatory

	DESCRIPTION

		"The port index of the redundant port's buddy.  To set

		a port to be redundant, the buddy's slot and port must

		be set to valid values.



		The buddy is automatically set to be redundant to this port."

	::= { ol51nnMFBPortEntry 5 }



ol51nnMFBPortDipAdminState OBJECT-TYPE

	SYNTAX INTEGER {

		enabled(1),

		disabled(2)

		}

	ACCESS read-only

	STATUS mandatory

	DESCRIPTION

		"The state of this port as indicated by the port's dip

		switches."

	::= { ol51nnMFBPortEntry 6 }



--

-- FDDI media module, for fiber with MIC connector

--



ol53nnMFBMICModTable OBJECT-TYPE

	SYNTAX SEQUENCE OF Ol53nnMFBMICModEntry

	ACCESS not-accessible

	STATUS mandatory

	DESCRIPTION

		"A list of module attributes that apply to this model.

		To access an ol53nnMFBMICModTable entry, the

		ol53nnMFBMICModSlotIndex attribute is used."

	::= { ol53nnMFBMIC 1 }



ol53nnMFBMICModEntry OBJECT-TYPE

	SYNTAX Ol53nnMFBMICModEntry

	ACCESS not-accessible

	STATUS mandatory

	DESCRIPTION

		"A list of module-specific information about a specific

		53nnM-FBMIC module in the concentrator."

	INDEX { ol53nnMFBMICModSlotIndex }

	::= { ol53nnMFBMICModTable 1 }



Ol53nnMFBMICModEntry ::=

	SEQUENCE {

		ol53nnMFBMICModSlotIndex

			INTEGER,

		ol53nnMFBMICModDownStreamModule

			INTEGER,

		ol53nnMFBMICModUpStreamModule

			INTEGER,

		ol53nnMFBMICModDownStreamOperPath

			INTEGER,

		ol53nnMFBMICModUpStreamOperPath

			INTEGER,

		ol53nnMFBMICModRingInfo

			OCTET STRING

		}



ol53nnMFBMICModSlotIndex OBJECT-TYPE

	SYNTAX INTEGER

	ACCESS read-only

	STATUS mandatory

	DESCRIPTION

		"A unique value that identifies a particular module.  Its

		value ranges between 1 and olModSlotNumber.  The module

		identified by a particular value of this index is the same

		module as indentified by the same value of olModSlotIndex."

	::= { ol53nnMFBMICModEntry 1 }



ol53nnMFBMICModDownStreamModule OBJECT-TYPE

	SYNTAX INTEGER (1..16)

	ACCESS read-only

	STATUS mandatory

	DESCRIPTION

		"Down stream slot (transmit to)"

	::= { ol53nnMFBMICModEntry 2 }



ol53nnMFBMICModUpStreamModule OBJECT-TYPE

	SYNTAX INTEGER (1..16)

	ACCESS read-only

	STATUS mandatory

	DESCRIPTION

		"Up stream slot (receive from)"

	::= { ol53nnMFBMICModEntry 3 }



ol53nnMFBMICModDownStreamOperPath OBJECT-TYPE

	SYNTAX INTEGER {

		isolated(2),

		fddi-path-1(24),

		fddi-path-2(25),

		fddi-path-3(26),

		fddi-path-4(27),

		fddi-path-5(28),

		fddi-path-6(29),

		fddi-path-7(30),

		fddi-path-8(31)

		}

	ACCESS read-only

	STATUS mandatory

	DESCRIPTION

		"Transmit DBA  (debug only)"

	::= { ol53nnMFBMICModEntry 4 }



ol53nnMFBMICModUpStreamOperPath OBJECT-TYPE

	SYNTAX INTEGER  {

		isolated(2),

		fddi-path-1(24),

		fddi-path-2(25),

		fddi-path-3(26),

		fddi-path-4(27),

		fddi-path-5(28),

		fddi-path-6(29),

		fddi-path-7(30),

		fddi-path-8(31)

		}

	ACCESS read-only

	STATUS mandatory

	DESCRIPTION

		"Receive DBA (debug only)"

	::= { ol53nnMFBMICModEntry 5 }



ol53nnMFBMICModRingInfo OBJECT-TYPE

	SYNTAX OCTET STRING (SIZE(1..8))

	ACCESS read-only

	STATUS mandatory

	DESCRIPTION

		"An array which is indexed by DBA number. Each element

		 contains the slot number (1..16) which is assigned to

		 transmit on this DBA. (debug only)"

	::= { ol53nnMFBMICModEntry 6 }





-- port table



ol53nnMFBMICPortTable OBJECT-TYPE

	SYNTAX SEQUENCE OF Ol53nnMFBMICPortEntry

	ACCESS not-accessible

	STATUS mandatory

	DESCRIPTION

		"A table of port-specific information for each port of

		this module type."

	::= { ol53nnMFBMIC 2 }



ol53nnMFBMICPortEntry OBJECT-TYPE

	SYNTAX Ol53nnMFBMICPortEntry

	ACCESS not-accessible

	STATUS mandatory

	DESCRIPTION

		"A list of module-specific information about a specific

		53nnM-FBMIC port in the concentrator."

	INDEX { ol53nnMFBMICPortSlotIndex, ol53nnMFBMICPortIndex }

	::= { ol53nnMFBMICPortTable 1 }



Ol53nnMFBMICPortEntry ::=

	SEQUENCE {

		ol53nnMFBMICPortSlotIndex

			INTEGER,

		ol53nnMFBMICPortIndex

			INTEGER,

		ol53nnMFBMICPortConfig

			INTEGER,

		ol53nnMFBMICPortPcmState

			INTEGER,

		ol53nnMFBMICPortConnectState

			INTEGER,

		ol53nnMFBMICPortNeighbor

			INTEGER,

		ol53nnMFBMICPortRemoteMACIndicated

			INTEGER,

		ol53nnMFBMICPortBSFlag

			INTEGER,

		ol53nnMFBMICPortPCWithhold

			INTEGER,

		ol53nnMFBMICPortLerCondition

			INTEGER

		}



ol53nnMFBMICPortSlotIndex OBJECT-TYPE

	SYNTAX INTEGER

	ACCESS read-only

	STATUS mandatory

	DESCRIPTION

		"A unique value that identifies a particular module.  Its

		value ranges between 1 and olModSlotNumber.  The module

		identified by a particular value of this index is the same

		module as indentified by the same value of

		olPortSlotIndex."

	::= { ol53nnMFBMICPortEntry 1 }





ol53nnMFBMICPortIndex OBJECT-TYPE

	SYNTAX INTEGER

	ACCESS read-only

	STATUS mandatory

	DESCRIPTION

		"A unique value that identifies a particular port within this

		module. Its value ranges between 1 and olModPortNumber.

		The module identified by a particular value of this index is

		the same module as indentified by the same value of

		olPortIndex."

	::= { ol53nnMFBMICPortEntry 2 }



ol53nnMFBMICPortConfig OBJECT-TYPE

	SYNTAX INTEGER {

		slave(3),

		master(4)

		}

	ACCESS read-write

	STATUS mandatory

	DESCRIPTION

		"Specifies the FDDI port type. If the port is on an

		 FFM, the only allowed values are slave(3), and master(4).

		 In addition, there can only be one active slave port on any

		 concentrator FDDI network."

	::= { ol53nnMFBMICPortEntry 3 }



ol53nnMFBMICPortPcmState OBJECT-TYPE

	SYNTAX INTEGER {

		  pc0(1), -- Off

		  pc1(2), -- Break

		  pc2(3), -- Trace

		  pc3(4), -- Connect

		  pc4(5), -- Next

		  pc5(6), -- Signal

		  pc6(7), -- Join

		  pc7(8), -- Verify

		  pc8(9), -- Active

		  pc9(10) -- Maint

	}

	ACCESS read-only

	STATUS mandatory

	DESCRIPTION

		      "(refer to ANSI SMT 9.6.2)."

	::= { ol53nnMFBMICPortEntry 4 }



ol53nnMFBMICPortConnectState OBJECT-TYPE

	SYNTAX INTEGER {

	  disabled(1),

	  connecting(2),

	  standby(3),

	  active(4)

		}

	ACCESS read-only

	STATUS mandatory

	DESCRIPTION

	     "An indication of the connect state of this PORT.

	      Basically, this gives a higher level view of the

	      state of the connection by grouping PCM states and

	      the PC-Withhold flag state.  The supported values

	      and their corresponding PCM states and PC-Withhold

	      condition, when relevant, are:

		  disabled: (PC0:Off, PC9:Maint)

		  connecting: (PC1(Break) || PC3 (Connect) || PC4(next) ||

			       PC5 (Signal) || PC6(Join) || PC7 (Verify)) &&

			      (PC-Withhold = None)

		  standby: (PC-Withhold != None)

		  active: (PC2:Trace || PC8:Active)"

	::= { ol53nnMFBMICPortEntry 5 }



ol53nnMFBMICPortNeighbor OBJECT-TYPE

	SYNTAX INTEGER {

		a(1),

		b(2),

		slave(3),

		master(4),

		unknown(5)

		}

	ACCESS read-only

	STATUS mandatory

	DESCRIPTION

	     "The type (PC-Neighbor) of the remote PORT that is

	      determined in PC-Signaling in R-Val (1,2) (refer

	      to ANSI SMT 9.6.3.2)."

	::= { ol53nnMFBMICPortEntry 6 }



ol53nnMFBMICPortRemoteMACIndicated OBJECT-TYPE

	SYNTAX INTEGER { true(1), false(2) }

	ACCESS read-only

	STATUS mandatory

	DESCRIPTION

	  "The indication, in PC-Signaling that the remote

	   partner intends to place a MAC in the output token

	   PATH of this PORT.  Signaled as R-Val (9) (refer

	   to ANSI SMT 9.6.3.2)."

	::= { ol53nnMFBMICPortEntry 7 }



ol53nnMFBMICPortBSFlag OBJECT-TYPE

	SYNTAX INTEGER { true(1), false(2) }

	ACCESS read-only

	STATUS mandatory

	DESCRIPTION

	  "The Break State, BS-Flag (refer to ANSI SMT

	   9.4.3.4)."

	::= { ol53nnMFBMICPortEntry 8 }



ol53nnMFBMICPortPCWithhold OBJECT-TYPE

	SYNTAX INTEGER  { none(1), m-m(2), other(3) }

	ACCESS read-only

	STATUS mandatory

	DESCRIPTION

	   "PC-Withhold, (refer to ANSI SMT 9.4.1)."

	::= { ol53nnMFBMICPortEntry 9 }



ol53nnMFBMICPortLerCondition OBJECT-TYPE

	SYNTAX INTEGER  { bad(1), okay(2) }

	ACCESS read-only

	STATUS mandatory

	DESCRIPTION

	   "This variable is set to true whenever LerEstimate

	    is less than or equal to LerAlarm (the larger the number

	    the smaller the value)."

	::= { ol53nnMFBMICPortEntry 10 }





-- Trunk Table

-- (only present for compatibility)



ol53nnMFBMICTrunkTable OBJECT-TYPE

	SYNTAX SEQUENCE OF Ol53nnMFBMICTrunkEntry

	ACCESS not-accessible

	STATUS mandatory

	DESCRIPTION

		"FDDI module specific trunk table variables.

		 At present there are none."

	::= { ol53nnMFBMIC 3 }



ol53nnMFBMICTrunkEntry OBJECT-TYPE

	SYNTAX Ol53nnMFBMICTrunkEntry

	ACCESS not-accessible

	STATUS mandatory

	DESCRIPTION

		"A description of 53nnM-FBMIC trunk attributes."

	INDEX { ol53nnMFBMICTrunkSlotIndex, ol53nnMFBMICTrunkIndex }

	::= { ol53nnMFBMICTrunkTable 1 }



Ol53nnMFBMICTrunkEntry ::=

	SEQUENCE {

		ol53nnMFBMICTrunkSlotIndex

			INTEGER,

		ol53nnMFBMICTrunkIndex

			INTEGER

		}



ol53nnMFBMICTrunkSlotIndex OBJECT-TYPE

	SYNTAX INTEGER

	ACCESS read-only

	STATUS mandatory

	DESCRIPTION

		"A unique value that identifies a particular module.  Its

		value ranges between 1 and olModSlotNumber.  The module

		identified by a particular value of this index is the same

		module as indentified by the same value of

		olTrunkSlotIndex."

	::= { ol53nnMFBMICTrunkEntry 1 }





ol53nnMFBMICTrunkIndex OBJECT-TYPE

	SYNTAX INTEGER

	ACCESS read-only

	STATUS mandatory

	DESCRIPTION

		"A unique value that identifies a particular trunk within this

		module. Its value ranges between 1 and olModTrunkNumber.

		The module identified by a particular value of this index is

		the same module as indentified by the same value of

		olTrunkIndex."

	::= { ol53nnMFBMICTrunkEntry 2 }





--

-- FDDI media module, for fiber with ST connector

--



ol53nnMFIBSTModTable OBJECT-TYPE

	SYNTAX SEQUENCE OF Ol53nnMFIBSTModEntry

	ACCESS not-accessible

	STATUS mandatory

	DESCRIPTION

		"A list of module attributes that apply to this model.

		To access an ol53nnMFIBSTModTable entry, the

		ol53nnMFIBSTModSlotIndex attribute is used."

	::= { ol53nnMFIBST 1 }



ol53nnMFIBSTModEntry OBJECT-TYPE

	SYNTAX Ol53nnMFIBSTModEntry

	ACCESS not-accessible

	STATUS mandatory

	DESCRIPTION

		"A list of module-specific information about a specific

		53nnM-FIBST module in the concentrator."

	INDEX { ol53nnMFIBSTModSlotIndex }

	::= { ol53nnMFIBSTModTable 1 }



Ol53nnMFIBSTModEntry ::=

	SEQUENCE {

		ol53nnMFIBSTModSlotIndex

			INTEGER,

		ol53nnMFIBSTModDownStreamModule

			INTEGER,

		ol53nnMFIBSTModUpStreamModule

			INTEGER,

		ol53nnMFIBSTModDownStreamOperPath

			INTEGER,

		ol53nnMFIBSTModUpStreamOperPath

			INTEGER,

		ol53nnMFIBSTModRingInfo

			OCTET STRING

		}



ol53nnMFIBSTModSlotIndex OBJECT-TYPE

	SYNTAX INTEGER

	ACCESS read-only

	STATUS mandatory

	DESCRIPTION

		"A unique value that identifies a particular module.  Its

		value ranges between 1 and olModSlotNumber.  The module

		identified by a particular value of this index is the same

		module as indentified by the same value of olModSlotIndex."

	::= { ol53nnMFIBSTModEntry 1 }



ol53nnMFIBSTModDownStreamModule OBJECT-TYPE

	SYNTAX INTEGER (1..16)

	ACCESS read-only

	STATUS mandatory

	DESCRIPTION

		"Down stream slot (transmit to)"

	::= { ol53nnMFIBSTModEntry 2 }



ol53nnMFIBSTModUpStreamModule OBJECT-TYPE

	SYNTAX INTEGER (1..16)

	ACCESS read-only

	STATUS mandatory

	DESCRIPTION

		"Up stream slot (receive from)"

	::= { ol53nnMFIBSTModEntry 3 }



ol53nnMFIBSTModDownStreamOperPath OBJECT-TYPE

	SYNTAX INTEGER  {

		isolated(2),

		fddi-path-1(24),

		fddi-path-2(25),

		fddi-path-3(26),

		fddi-path-4(27),

		fddi-path-5(28),

		fddi-path-6(29),

		fddi-path-7(30),

		fddi-path-8(31)

		}

	ACCESS read-only

	STATUS mandatory

	DESCRIPTION

		"Transmit DBA (debug only)"

	::= { ol53nnMFIBSTModEntry 4 }



ol53nnMFIBSTModUpStreamOperPath OBJECT-TYPE

	SYNTAX INTEGER  {

		isolated(2),

		fddi-path-1(24),

		fddi-path-2(25),

		fddi-path-3(26),

		fddi-path-4(27),

		fddi-path-5(28),

		fddi-path-6(29),

		fddi-path-7(30),

		fddi-path-8(31)

		}

	ACCESS read-only

	STATUS mandatory

	DESCRIPTION

		"Receive DBA (debug only)"

	::= { ol53nnMFIBSTModEntry 5 }



ol53nnMFIBSTModRingInfo OBJECT-TYPE

	SYNTAX OCTET STRING (SIZE(1..8))

	ACCESS read-only

	STATUS mandatory

	DESCRIPTION

		"An array which is indexed by DBA number. Each element

		 contains the slot number (1..16) which is assigned to

		 transmit on this DBA. (debug only)"

	::= { ol53nnMFIBSTModEntry 6 }





-- port table



ol53nnMFIBSTPortTable OBJECT-TYPE

	SYNTAX SEQUENCE OF Ol53nnMFIBSTPortEntry

	ACCESS not-accessible

	STATUS mandatory

	DESCRIPTION

		"A table of port-specific information for each port of

		this module type."

	::= { ol53nnMFIBST 2 }



ol53nnMFIBSTPortEntry OBJECT-TYPE

	SYNTAX Ol53nnMFIBSTPortEntry

	ACCESS not-accessible

	STATUS mandatory

	DESCRIPTION

		"A list of module-specific information about a specific

		53nnM-FIBST port in the concentrator."

	INDEX { ol53nnMFIBSTPortSlotIndex, ol53nnMFIBSTPortIndex }

	::= { ol53nnMFIBSTPortTable 1 }



Ol53nnMFIBSTPortEntry ::=

	SEQUENCE {

		ol53nnMFIBSTPortSlotIndex

			INTEGER,

		ol53nnMFIBSTPortIndex

			INTEGER,

		ol53nnMFIBSTPortConfig

			INTEGER,

		ol53nnMFIBSTPortPcmState

			INTEGER,

		ol53nnMFIBSTPortConnectState

			INTEGER,

		ol53nnMFIBSTPortNeighbor

			INTEGER,

		ol53nnMFIBSTPortRemoteMACIndicated

			INTEGER,

		ol53nnMFIBSTPortBSFlag

			INTEGER,

		ol53nnMFIBSTPortPCWithhold

			INTEGER,

		ol53nnMFIBSTPortLerCondition

			INTEGER

		}



ol53nnMFIBSTPortSlotIndex OBJECT-TYPE

	SYNTAX INTEGER

	ACCESS read-only

	STATUS mandatory

	DESCRIPTION

		"A unique value that identifies a particular module.  Its

		value ranges between 1 and olModSlotNumber.  The module

		identified by a particular value of this index is the same

		module as indentified by the same value of

		olPortSlotIndex."

	::= { ol53nnMFIBSTPortEntry 1 }





ol53nnMFIBSTPortIndex OBJECT-TYPE

	SYNTAX INTEGER

	ACCESS read-only

	STATUS mandatory

	DESCRIPTION

		"A unique value that identifies a particular port within this

		module. Its value ranges between 1 and olModPortNumber.

		The module identified by a particular value of this index is

		the same module as indentified by the same value of

		olPortIndex."

	::= { ol53nnMFIBSTPortEntry 2 }



ol53nnMFIBSTPortConfig OBJECT-TYPE

	SYNTAX INTEGER {

		slave(3),

		master(4)

		}

	ACCESS read-write

	STATUS mandatory

	DESCRIPTION

		"Specifies the FDDI port type. If the port is on an

		 FFM, the only allowed values are slave(3) and master(4).

		 In addition, there can only be one active slave port on any

		 concentrator FDDI network."

	::= { ol53nnMFIBSTPortEntry 3 }



ol53nnMFIBSTPortPcmState OBJECT-TYPE

	SYNTAX INTEGER {

		  pc0(1), -- Off

		  pc1(2), -- Break

		  pc2(3), -- Trace

		  pc3(4), -- Connect

		  pc4(5), -- Next

		  pc5(6), -- Signal

		  pc6(7), -- Join

		  pc7(8), -- Verify

		  pc8(9), -- Active

		  pc9(10) -- Maint

	}

	ACCESS read-only

	STATUS mandatory

	DESCRIPTION

		      "(refer to ANSI SMT 9.6.2)."

	::= { ol53nnMFIBSTPortEntry 4 }



ol53nnMFIBSTPortConnectState OBJECT-TYPE

	SYNTAX INTEGER {

	  disabled(1),

	  connecting(2),

	  standby(3),

	  active(4)

		}

	ACCESS read-only

	STATUS mandatory

	DESCRIPTION

	     "An indication of the connect state of this PORT.

	      Basically, this gives a higher level view of the

	      state of the connection by grouping PCM states and

	      the PC-Withhold flag state.  The supported values

	      and their corresponding PCM states and PC-Withhold

	      condition, when relevant, are:

		  disabled: (PC0:Off, PC9:Maint)

		  connecting: (PC1(Break) || PC3 (Connect) || PC4(next) ||

			       PC5 (Signal) || PC6(Join) || PC7 (Verify)) &&

			      (PC-Withhold = None)

		  standby: (PC-Withhold != None)

		  active: (PC2:Trace || PC8:Active)"

	::= { ol53nnMFIBSTPortEntry 5 }



ol53nnMFIBSTPortNeighbor OBJECT-TYPE

	SYNTAX INTEGER {

		a(1),

		b(2),

		slave(3),

		master(4),

		unknown(5)

		}

	ACCESS read-only

	STATUS mandatory

	DESCRIPTION

	     "The type (PC-Neighbor) of the remote PORT that is

	      determined in PC-Signaling in R-Val (1,2) (refer

	      to ANSI SMT 9.6.3.2)."

	::= { ol53nnMFIBSTPortEntry 6 }



ol53nnMFIBSTPortRemoteMACIndicated OBJECT-TYPE

	SYNTAX INTEGER { true(1), false(2) }

	ACCESS read-only

	STATUS mandatory

	DESCRIPTION

	  "The indication, in PC-Signaling that the remote

	   partner intends to place a MAC in the output token

	   PATH of this PORT.  Signaled as R-Val (9) (refer

	   to ANSI SMT 9.6.3.2)."

	::= { ol53nnMFIBSTPortEntry 7 }



ol53nnMFIBSTPortBSFlag OBJECT-TYPE

	SYNTAX INTEGER { true(1), false(2) }

	ACCESS read-only

	STATUS mandatory

	DESCRIPTION

	  "The Break State, BS-Flag (refer to ANSI SMT

	   9.4.3.4)."

	::= { ol53nnMFIBSTPortEntry 8 }



ol53nnMFIBSTPortPCWithhold OBJECT-TYPE

	SYNTAX INTEGER  { none(1), m-m(2), other(3) }

	ACCESS read-only

	STATUS mandatory

	DESCRIPTION

	   "PC-Withhold, (refer to ANSI SMT 9.4.1)."

	::= { ol53nnMFIBSTPortEntry 9 }



ol53nnMFIBSTPortLerCondition OBJECT-TYPE

	SYNTAX INTEGER  { bad(1), okay(2) }

	ACCESS read-only

	STATUS mandatory

	DESCRIPTION

	   "This variable is set to true whenever LerEstimate

	    is less than or equal to LerAlarm (the larger the number

	    the smaller the value)."

	::= { ol53nnMFIBSTPortEntry 10 }





-- Trunk Table

-- (only present for compatibility)



ol53nnMFIBSTTrunkTable OBJECT-TYPE

	SYNTAX SEQUENCE OF Ol53nnMFIBSTTrunkEntry

	ACCESS not-accessible

	STATUS mandatory

	DESCRIPTION

		"FDDI module specific trunk table variables.

		 At present there are none."

	::= { ol53nnMFIBST 3 }



ol53nnMFIBSTTrunkEntry OBJECT-TYPE

	SYNTAX Ol53nnMFIBSTTrunkEntry

	ACCESS not-accessible

	STATUS mandatory

	DESCRIPTION

		"A description of 53nnM-FIBST trunk attributes."

	INDEX { ol53nnMFIBSTTrunkSlotIndex, ol53nnMFIBSTTrunkIndex }

	::= { ol53nnMFIBSTTrunkTable 1 }



Ol53nnMFIBSTTrunkEntry ::=

	SEQUENCE {

		ol53nnMFIBSTTrunkSlotIndex

			INTEGER,

		ol53nnMFIBSTTrunkIndex

			INTEGER

		}



ol53nnMFIBSTTrunkSlotIndex OBJECT-TYPE

	SYNTAX INTEGER

	ACCESS read-only

	STATUS mandatory

	DESCRIPTION

		"A unique value that identifies a particular module.  Its

		value ranges between 1 and olModSlotNumber.  The module

		identified by a particular value of this index is the same

		module as indentified by the same value of

		olTrunkSlotIndex."

	::= { ol53nnMFIBSTTrunkEntry 1 }





ol53nnMFIBSTTrunkIndex OBJECT-TYPE

	SYNTAX INTEGER

	ACCESS read-only

	STATUS mandatory

	DESCRIPTION

		"A unique value that identifies a particular trunk within this

		module. Its value ranges between 1 and olModTrunkNumber.

		The module identified by a particular value of this index is

		the same module as indentified by the same value of

		olTrunkIndex."

	::= { ol53nnMFIBSTTrunkEntry 2 }





--

-- FDDI media module, for shielded copper with DB9 connector.

--



ol53nnMSTPModTable OBJECT-TYPE

	SYNTAX SEQUENCE OF Ol53nnMSTPModEntry

	ACCESS not-accessible

	STATUS mandatory

	DESCRIPTION

		"A list of module attributes that apply to this model.

		To access an ol53nnMSTPModTable entry, the

		ol53nnMSTPModSlotIndex attribute is used."

	::= { ol53nnMSTP 1 }



ol53nnMSTPModEntry OBJECT-TYPE

	SYNTAX Ol53nnMSTPModEntry

	ACCESS not-accessible

	STATUS mandatory

	DESCRIPTION

		"A list of module-specific information about a specific

		53nnM-STP module in the concentrator."

	INDEX { ol53nnMSTPModSlotIndex }

	::= { ol53nnMSTPModTable 1 }



Ol53nnMSTPModEntry ::=

	SEQUENCE {

		ol53nnMSTPModSlotIndex

			INTEGER,

		ol53nnMSTPModDownStreamModule

			INTEGER,

		ol53nnMSTPModUpStreamModule

			INTEGER,

		ol53nnMSTPModDownStreamOperPath

			INTEGER,

		ol53nnMSTPModUpStreamOperPath

			INTEGER,

		ol53nnMSTPModRingInfo

			OCTET STRING

		}



ol53nnMSTPModSlotIndex OBJECT-TYPE

	SYNTAX INTEGER

	ACCESS read-only

	STATUS mandatory

	DESCRIPTION

		"A unique value that identifies a particular module.  Its

		value ranges between 1 and olModSlotNumber.  The module

		identified by a particular value of this index is the same

		module as indentified by the same value of olModSlotIndex."

	::= { ol53nnMSTPModEntry 1 }



ol53nnMSTPModDownStreamModule OBJECT-TYPE

	SYNTAX INTEGER (1..16)

	ACCESS read-only

	STATUS mandatory

	DESCRIPTION

		"Down stream slot (transmit to)"

	::= { ol53nnMSTPModEntry 2 }



ol53nnMSTPModUpStreamModule OBJECT-TYPE

	SYNTAX INTEGER (1..16)

	ACCESS read-only

	STATUS mandatory

	DESCRIPTION

		"Down stream slot (receive from)"

	::= { ol53nnMSTPModEntry 3 }



ol53nnMSTPModDownStreamOperPath OBJECT-TYPE

	SYNTAX INTEGER  {

		isolated(2),

		fddi-path-1(24),

		fddi-path-2(25),

		fddi-path-3(26),

		fddi-path-4(27),

		fddi-path-5(28),

		fddi-path-6(29),

		fddi-path-7(30),

		fddi-path-8(31)

		}

	ACCESS read-only

	STATUS mandatory

	DESCRIPTION

		"transmit DBA  (debug only)"

	::= { ol53nnMSTPModEntry 4 }



ol53nnMSTPModUpStreamOperPath OBJECT-TYPE

	SYNTAX INTEGER  {

		isolated(2),

		fddi-path-1(24),

		fddi-path-2(25),

		fddi-path-3(26),

		fddi-path-4(27),

		fddi-path-5(28),

		fddi-path-6(29),

		fddi-path-7(30),

		fddi-path-8(31)

		}

	ACCESS read-only

	STATUS mandatory

	DESCRIPTION

		"receive DBA  (debug only)"

	::= { ol53nnMSTPModEntry 5 }



ol53nnMSTPModRingInfo OBJECT-TYPE

	SYNTAX OCTET STRING (SIZE(1..8))

	ACCESS read-only

	STATUS mandatory

	DESCRIPTION

		"An array which is indexed by DBA number. Each element

		 contains the slot number (1..16) which is assigned to

		 transmit on this DBA. (debug only)"

	::= { ol53nnMSTPModEntry 6 }





-- port table



ol53nnMSTPPortTable OBJECT-TYPE

	SYNTAX SEQUENCE OF Ol53nnMSTPPortEntry

	ACCESS not-accessible

	STATUS mandatory

	DESCRIPTION

		"A table of port-specific information for each port of

		this module type."

	::= { ol53nnMSTP 2 }



ol53nnMSTPPortEntry OBJECT-TYPE

	SYNTAX Ol53nnMSTPPortEntry

	ACCESS not-accessible

	STATUS mandatory

	DESCRIPTION

		"A list of module-specific information about a specific

		53nnM-STP port in the concentrator."

	INDEX { ol53nnMSTPPortSlotIndex, ol53nnMSTPPortIndex }

	::= { ol53nnMSTPPortTable 1 }



Ol53nnMSTPPortEntry ::=

	SEQUENCE {

		ol53nnMSTPPortSlotIndex

			INTEGER,

		ol53nnMSTPPortIndex

			INTEGER,

		ol53nnMSTPPortConfig

			INTEGER,

		ol53nnMSTPPortPcmState

			INTEGER,

		ol53nnMSTPPortConnectState

			INTEGER,

		ol53nnMSTPPortNeighbor

			INTEGER,

		ol53nnMSTPPortRemoteMACIndicated

			INTEGER,

		ol53nnMSTPPortBSFlag

			INTEGER,

		ol53nnMSTPPortPCWithhold

			INTEGER,

		ol53nnMSTPPortLerCondition

			INTEGER,

		ol53nnMSTPPortPersonality

			INTEGER

		}



ol53nnMSTPPortSlotIndex OBJECT-TYPE

	SYNTAX INTEGER

	ACCESS read-only

	STATUS mandatory

	DESCRIPTION

		"A unique value that identifies a particular module.  Its

		value ranges between 1 and olModSlotNumber.  The module

		identified by a particular value of this index is the same

		module as indentified by the same value of

		olPortSlotIndex."

	::= { ol53nnMSTPPortEntry 1 }





ol53nnMSTPPortIndex OBJECT-TYPE

	SYNTAX INTEGER

	ACCESS read-only

	STATUS mandatory

	DESCRIPTION

		"A unique value that identifies a particular port within this

		module. Its value ranges between 1 and olModPortNumber.

		The module identified by a particular value of this index is

		the same module as indentified by the same value of

		olPortIndex."

	::= { ol53nnMSTPPortEntry 2 }



ol53nnMSTPPortConfig OBJECT-TYPE

	SYNTAX INTEGER {

		slave(3),

		master(4)

		}

	ACCESS read-write

	STATUS mandatory

	DESCRIPTION

		"Specifies the FDDI port type. If the port is on an

		 FFM, the only allowed values are slave(3) and master(4).

		 In addition, there can only be one active slave port on any

		 concentrator FDDI network."

	::= { ol53nnMSTPPortEntry 3 }



ol53nnMSTPPortPcmState OBJECT-TYPE

	SYNTAX INTEGER {

		  pc0(1), -- Off

		  pc1(2), -- Break

		  pc2(3), -- Trace

		  pc3(4), -- Connect

		  pc4(5), -- Next

		  pc5(6), -- Signal

		  pc6(7), -- Join

		  pc7(8), -- Verify

		  pc8(9), -- Active

		  pc9(10) -- Maint

	}

	ACCESS read-only

	STATUS mandatory

	DESCRIPTION

		      "(refer to ANSI SMT 9.6.2)."

	::= { ol53nnMSTPPortEntry 4 }



ol53nnMSTPPortConnectState OBJECT-TYPE

	SYNTAX INTEGER {

	  disabled(1),

	  connecting(2),

	  standby(3),

	  active(4)

		}

	ACCESS read-only

	STATUS mandatory

	DESCRIPTION

	     "An indication of the connect state of this PORT.

	      Basically, this gives a higher level view of the

	      state of the connection by grouping PCM states and

	      the PC-Withhold flag state.  The supported values

	      and their corresponding PCM states and PC-Withhold

	      condition, when relevant, are:

		  disabled: (PC0:Off, PC9:Maint)

		  connecting: (PC1(Break) || PC3 (Connect) || PC4(next) ||

			       PC5 (Signal) || PC6(Join) || PC7 (Verify)) &&

			      (PC-Withhold = None)

		  standby: (PC-Withhold != None)

		  active: (PC2:Trace || PC8:Active)"

	::= { ol53nnMSTPPortEntry 5 }



ol53nnMSTPPortNeighbor OBJECT-TYPE

	SYNTAX INTEGER {

		a(1),

		b(2),

		slave(3),

		master(4),

		unknown(5)

		}

	ACCESS read-only

	STATUS mandatory

	DESCRIPTION

	     "The type (PC-Neighbor) of the remote PORT that is

	      determined in PC-Signaling in R-Val (1,2) (refer

	      to ANSI SMT 9.6.3.2)."

	::= { ol53nnMSTPPortEntry 6 }



ol53nnMSTPPortRemoteMACIndicated OBJECT-TYPE

	SYNTAX INTEGER { true(1), false(2) }

	ACCESS read-only

	STATUS mandatory

	DESCRIPTION

	  "The indication, in PC-Signaling that the remote

	   partner intends to place a MAC in the output token

	   PATH of this PORT.  Signaled as R-Val (9) (refer

	   to ANSI SMT 9.6.3.2)."

	::= { ol53nnMSTPPortEntry 7 }



ol53nnMSTPPortBSFlag OBJECT-TYPE

	SYNTAX INTEGER { true(1), false(2) }

	ACCESS read-only

	STATUS mandatory

	DESCRIPTION

	  "The Break State, BS-Flag (refer to ANSI SMT

	   9.4.3.4)."

	::= { ol53nnMSTPPortEntry 8 }



ol53nnMSTPPortPCWithhold OBJECT-TYPE

	SYNTAX INTEGER  { none(1), m-m(2), other(3) }

	ACCESS read-only

	STATUS mandatory

	DESCRIPTION

	   "PC-Withhold, (refer to ANSI SMT 9.4.1)."

	::= { ol53nnMSTPPortEntry 9 }



ol53nnMSTPPortLerCondition OBJECT-TYPE

	SYNTAX INTEGER  { bad(1), okay(2) }

	ACCESS read-only

	STATUS mandatory

	DESCRIPTION

	   "This variable is set to true whenever LerEstimate

	    is less than or equal to LerAlarm (the larger the number

	    the smaller the value)."

	::= { ol53nnMSTPPortEntry 10 }





ol53nnMSTPPortPersonality OBJECT-TYPE

	SYNTAX INTEGER {

		sddi(1),

		tpddi(2)

		}

	ACCESS read-write

	STATUS mandatory

	DESCRIPTION

		"Specifies the physical signaling used by the port, the only

		 valid values are sddi(3) and tpddi(4)."

	::= { ol53nnMSTPPortEntry 11 }





-- Trunk Table

-- (only present for compatibility)



ol53nnMSTPTrunkTable OBJECT-TYPE

	SYNTAX SEQUENCE OF Ol53nnMSTPTrunkEntry

	ACCESS not-accessible

	STATUS mandatory

	DESCRIPTION

		"FDDI module specific trunk table variables.

		 At present there are none."

	::= { ol53nnMSTP 3 }



ol53nnMSTPTrunkEntry OBJECT-TYPE

	SYNTAX Ol53nnMSTPTrunkEntry

	ACCESS not-accessible

	STATUS mandatory

	DESCRIPTION

		"A description of 53nnM-STP trunk attributes."

	INDEX { ol53nnMSTPTrunkSlotIndex, ol53nnMSTPTrunkIndex }

	::= { ol53nnMSTPTrunkTable 1 }



Ol53nnMSTPTrunkEntry ::=

	SEQUENCE {

		ol53nnMSTPTrunkSlotIndex

			INTEGER,

		ol53nnMSTPTrunkIndex

			INTEGER

		}



ol53nnMSTPTrunkSlotIndex OBJECT-TYPE

	SYNTAX INTEGER

	ACCESS read-only

	STATUS mandatory

	DESCRIPTION

		"A unique value that identifies a particular module.  Its

		value ranges between 1 and olModSlotNumber.  The module

		identified by a particular value of this index is the same

		module as indentified by the same value of

		olTrunkSlotIndex."

	::= { ol53nnMSTPTrunkEntry 1 }





ol53nnMSTPTrunkIndex OBJECT-TYPE

	SYNTAX INTEGER

	ACCESS read-only

	STATUS mandatory

	DESCRIPTION

		"A unique value that identifies a particular trunk within this

		module. Its value ranges between 1 and olModTrunkNumber.

		The module identified by a particular value of this index is

		the same module as indentified by the same value of

		olTrunkIndex."

	::= { ol53nnMSTPTrunkEntry 2 }





--

-- FDDI media module, for copper with RJ45 connector.

--



ol53nnMTDDIModTable OBJECT-TYPE

	SYNTAX SEQUENCE OF Ol53nnMTDDIModEntry

	ACCESS not-accessible

	STATUS mandatory

	DESCRIPTION

		"A list of module attributes that apply to this model.

		To access an ol53nnMTDDIModTable entry, the

		ol53nnMTDDIModSlotIndex attribute is used."

	::= { ol53nnMTDDI 1 }



ol53nnMTDDIModEntry OBJECT-TYPE

	SYNTAX Ol53nnMTDDIModEntry

	ACCESS not-accessible

	STATUS mandatory

	DESCRIPTION

		"A list of module-specific information about a specific

		53nnM-TDDI module in the concentrator."

	INDEX { ol53nnMTDDIModSlotIndex }

	::= { ol53nnMTDDIModTable 1 }



Ol53nnMTDDIModEntry ::=

	SEQUENCE {

		ol53nnMTDDIModSlotIndex

			INTEGER,

		ol53nnMTDDIModDownStreamModule

			INTEGER,

		ol53nnMTDDIModUpStreamModule

			INTEGER,

		ol53nnMTDDIModDownStreamOperPath

			INTEGER,

		ol53nnMTDDIModUpStreamOperPath

			INTEGER,

		ol53nnMTDDIModRingInfo

			OCTET STRING

		}



ol53nnMTDDIModSlotIndex OBJECT-TYPE

	SYNTAX INTEGER

	ACCESS read-only

	STATUS mandatory

	DESCRIPTION

		"A unique value that identifies a particular module.  Its

		value ranges between 1 and olModSlotNumber.  The module

		identified by a particular value of this index is the same

		module as indentified by the same value of olModSlotIndex."

	::= { ol53nnMTDDIModEntry 1 }



ol53nnMTDDIModDownStreamModule OBJECT-TYPE

	SYNTAX INTEGER (1..16)

	ACCESS read-only

	STATUS mandatory

	DESCRIPTION

		"Down stream slot (transmit to)"

	::= { ol53nnMTDDIModEntry 2 }



ol53nnMTDDIModUpStreamModule OBJECT-TYPE

	SYNTAX INTEGER (1..16)

	ACCESS read-only

	STATUS mandatory

	DESCRIPTION

		"Down stream slot (receive from)"

	::= { ol53nnMTDDIModEntry 3 }



ol53nnMTDDIModDownStreamOperPath OBJECT-TYPE

	SYNTAX INTEGER  {

		isolated(2),

		fddi-path-1(24),

		fddi-path-2(25),

		fddi-path-3(26),

		fddi-path-4(27),

		fddi-path-5(28),

		fddi-path-6(29),

		fddi-path-7(30),

		fddi-path-8(31)

		}

	ACCESS read-only

	STATUS mandatory

	DESCRIPTION

		"transmit DBA  (debug only)"

	::= { ol53nnMTDDIModEntry 4 }



ol53nnMTDDIModUpStreamOperPath OBJECT-TYPE

	SYNTAX INTEGER  {

		isolated(2),

		fddi-path-1(24),

		fddi-path-2(25),

		fddi-path-3(26),

		fddi-path-4(27),

		fddi-path-5(28),

		fddi-path-6(29),

		fddi-path-7(30),

		fddi-path-8(31)

		}

	ACCESS read-only

	STATUS mandatory

	DESCRIPTION

		"receive DBA  (debug only)"

	::= { ol53nnMTDDIModEntry 5 }



ol53nnMTDDIModRingInfo OBJECT-TYPE

	SYNTAX OCTET STRING (SIZE(1..8))

	ACCESS read-only

	STATUS mandatory

	DESCRIPTION

		"An array which is indexed by DBA number. Each element

		 contains the slot number (1..16) which is assigned to

		 transmit on this DBA. (debug only)"

	::= { ol53nnMTDDIModEntry 6 }





-- port table



ol53nnMTDDIPortTable OBJECT-TYPE

	SYNTAX SEQUENCE OF Ol53nnMTDDIPortEntry

	ACCESS not-accessible

	STATUS mandatory

	DESCRIPTION

		"A table of port-specific information for each port of

		this module type."

	::= { ol53nnMTDDI 2 }



ol53nnMTDDIPortEntry OBJECT-TYPE

	SYNTAX Ol53nnMTDDIPortEntry

	ACCESS not-accessible

	STATUS mandatory

	DESCRIPTION

		"A list of module-specific information about a specific

		53nnM-TDDI port in the concentrator."

	INDEX { ol53nnMTDDIPortSlotIndex, ol53nnMTDDIPortIndex }

	::= { ol53nnMTDDIPortTable 1 }



Ol53nnMTDDIPortEntry ::=

	SEQUENCE {

		ol53nnMTDDIPortSlotIndex

			INTEGER,

		ol53nnMTDDIPortIndex

			INTEGER,

		ol53nnMTDDIPortConfig

			INTEGER,

		ol53nnMTDDIPortPcmState

			INTEGER,

		ol53nnMTDDIPortConnectState

			INTEGER,

		ol53nnMTDDIPortNeighbor

			INTEGER,

		ol53nnMTDDIPortRemoteMACIndicated

			INTEGER,

		ol53nnMTDDIPortBSFlag

			INTEGER,

		ol53nnMTDDIPortPCWithhold

			INTEGER,

		ol53nnMTDDIPortLerCondition

			INTEGER

		}



ol53nnMTDDIPortSlotIndex OBJECT-TYPE

	SYNTAX INTEGER

	ACCESS read-only

	STATUS mandatory

	DESCRIPTION

		"A unique value that identifies a particular module.  Its

		value ranges between 1 and olModSlotNumber.  The module

		identified by a particular value of this index is the same

		module as indentified by the same value of

		olPortSlotIndex."

	::= { ol53nnMTDDIPortEntry 1 }





ol53nnMTDDIPortIndex OBJECT-TYPE

	SYNTAX INTEGER

	ACCESS read-only

	STATUS mandatory

	DESCRIPTION

		"A unique value that identifies a particular port within this

		module. Its value ranges between 1 and olModPortNumber.

		The module identified by a particular value of this index is

		the same module as indentified by the same value of

		olPortIndex."

	::= { ol53nnMTDDIPortEntry 2 }



ol53nnMTDDIPortConfig OBJECT-TYPE

	SYNTAX INTEGER {

		slave(3),

		master(4)

		}

	ACCESS read-write

	STATUS mandatory

	DESCRIPTION

		"Specifies the FDDI port type. If the port is on an

		 FFM, the only allowed values are slave(3) and master(4).

		 In addition, there can only be one active slave port on any

		 concentrator FDDI network."

	::= { ol53nnMTDDIPortEntry 3 }



ol53nnMTDDIPortPcmState OBJECT-TYPE

	SYNTAX INTEGER {

		  pc0(1), -- Off

		  pc1(2), -- Break

		  pc2(3), -- Trace

		  pc3(4), -- Connect

		  pc4(5), -- Next

		  pc5(6), -- Signal

		  pc6(7), -- Join

		  pc7(8), -- Verify

		  pc8(9), -- Active

		  pc9(10) -- Maint

	}

	ACCESS read-only

	STATUS mandatory

	DESCRIPTION

		      "(refer to ANSI SMT 9.6.2)."

	::= { ol53nnMTDDIPortEntry 4 }



ol53nnMTDDIPortConnectState OBJECT-TYPE

	SYNTAX INTEGER {

	  disabled(1),

	  connecting(2),

	  standby(3),

	  active(4)

		}

	ACCESS read-only

	STATUS mandatory

	DESCRIPTION

	     "An indication of the connect state of this PORT.

	      Basically, this gives a higher level view of the

	      state of the connection by grouping PCM states and

	      the PC-Withhold flag state.  The supported values

	      and their corresponding PCM states and PC-Withhold

	      condition, when relevant, are:

		  disabled: (PC0:Off, PC9:Maint)

		  connecting: (PC1(Break) || PC3 (Connect) || PC4(next) ||

			       PC5 (Signal) || PC6(Join) || PC7 (Verify)) &&

			      (PC-Withhold = None)

		  standby: (PC-Withhold != None)

		  active: (PC2:Trace || PC8:Active)"

	::= { ol53nnMTDDIPortEntry 5 }



ol53nnMTDDIPortNeighbor OBJECT-TYPE

	SYNTAX INTEGER {

		a(1),

		b(2),

		slave(3),

		master(4),

		unknown(5)

		}

	ACCESS read-only

	STATUS mandatory

	DESCRIPTION

	     "The type (PC-Neighbor) of the remote PORT that is

	      determined in PC-Signaling in R-Val (1,2) (refer

	      to ANSI SMT 9.6.3.2)."

	::= { ol53nnMTDDIPortEntry 6 }



ol53nnMTDDIPortRemoteMACIndicated OBJECT-TYPE

	SYNTAX INTEGER { true(1), false(2) }

	ACCESS read-only

	STATUS mandatory

	DESCRIPTION

	  "The indication, in PC-Signaling that the remote

	   partner intends to place a MAC in the output token

	   PATH of this PORT.  Signaled as R-Val (9) (refer

	   to ANSI SMT 9.6.3.2)."

	::= { ol53nnMTDDIPortEntry 7 }



ol53nnMTDDIPortBSFlag OBJECT-TYPE

	SYNTAX INTEGER { true(1), false(2) }

	ACCESS read-only

	STATUS mandatory

	DESCRIPTION

	  "The Break State, BS-Flag (refer to ANSI SMT

	   9.4.3.4)."

	::= { ol53nnMTDDIPortEntry 8 }



ol53nnMTDDIPortPCWithhold OBJECT-TYPE

	SYNTAX INTEGER  { none(1), m-m(2), other(3) }

	ACCESS read-only

	STATUS mandatory

	DESCRIPTION

	   "PC-Withhold, (refer to ANSI SMT 9.4.1)."

	::= { ol53nnMTDDIPortEntry 9 }



ol53nnMTDDIPortLerCondition OBJECT-TYPE

	SYNTAX INTEGER  { bad(1), okay(2) }

	ACCESS read-only

	STATUS mandatory

	DESCRIPTION

	   "This variable is set to true whenever LerEstimate

	    is less than or equal to LerAlarm (the larger the number

	    the smaller the value)."

	::= { ol53nnMTDDIPortEntry 10 }



-- Trunk Table

-- (only present for compatibility)



ol53nnMTDDITrunkTable OBJECT-TYPE

	SYNTAX SEQUENCE OF Ol53nnMTDDITrunkEntry

	ACCESS not-accessible

	STATUS mandatory

	DESCRIPTION

		"FDDI module specific trunk table variables.

		 At present there are none."

	::= { ol53nnMTDDI 3 }



ol53nnMTDDITrunkEntry OBJECT-TYPE

	SYNTAX Ol53nnMTDDITrunkEntry

	ACCESS not-accessible

	STATUS mandatory

	DESCRIPTION

		"A description of 53nnM-TDDI trunk attributes."

	INDEX { ol53nnMTDDITrunkSlotIndex, ol53nnMTDDITrunkIndex }

	::= { ol53nnMTDDITrunkTable 1 }



Ol53nnMTDDITrunkEntry ::=

	SEQUENCE {

		ol53nnMTDDITrunkSlotIndex

			INTEGER,

		ol53nnMTDDITrunkIndex

			INTEGER

		}



ol53nnMTDDITrunkSlotIndex OBJECT-TYPE

	SYNTAX INTEGER

	ACCESS read-only

	STATUS mandatory

	DESCRIPTION

		"A unique value that identifies a particular module.  Its

		value ranges between 1 and olModSlotNumber.  The module

		identified by a particular value of this index is the same

		module as indentified by the same value of

		olTrunkSlotIndex."

	::= { ol53nnMTDDITrunkEntry 1 }





ol53nnMTDDITrunkIndex OBJECT-TYPE

	SYNTAX INTEGER

	ACCESS read-only

	STATUS mandatory

	DESCRIPTION

		"A unique value that identifies a particular trunk within this

		module. Its value ranges between 1 and olModTrunkNumber.

		The module identified by a particular value of this index is

		the same module as indentified by the same value of

		olTrunkIndex."

	::= { ol53nnMTDDITrunkEntry 2 }





--

-- ONline Ethernet 10BASE-T Per-Connector Module

--



ol51nnMTPCLModTable OBJECT-TYPE

	SYNTAX SEQUENCE OF Ol51nnMTPCLModEntry

	ACCESS not-accessible

	STATUS mandatory

	DESCRIPTION

		"A list of module-specific information about a specific

		51nnM-TPCL module in the concentrator."

	::= { ol51nnMTPCL 1 }



ol51nnMTPCLModEntry OBJECT-TYPE

	SYNTAX Ol51nnMTPCLModEntry

	ACCESS not-accessible

	STATUS mandatory

	DESCRIPTION

		"A list of module-specific information about a specific

		51nnM-TPCL module in the concentrator."

	INDEX { ol51nnMTPCLModSlotIndex }

	::= { ol51nnMTPCLModTable 1 }



Ol51nnMTPCLModEntry ::=

	SEQUENCE {

		ol51nnMTPCLModSlotIndex

			INTEGER,

		ol51nnMTPCLModMonitorConn

			INTEGER,

		ol51nnMTPCLModConn1Network

			INTEGER,

		ol51nnMTPCLModConn2Network

			INTEGER,

		ol51nnMTPCLModConn1DipNetwork

			INTEGER,

		ol51nnMTPCLModConn2DipNetwork

			INTEGER,

		ol51nnMTPCLModAutoPartition

			INTEGER

		}



ol51nnMTPCLModSlotIndex OBJECT-TYPE

	SYNTAX INTEGER

	ACCESS read-only

	STATUS mandatory

	DESCRIPTION

		"The slot number of this module."

	::= { ol51nnMTPCLModEntry 1 }



ol51nnMTPCLModMonitorConn OBJECT-TYPE

	SYNTAX INTEGER {

		connector-1(1),

		connector-2(2)

		}

	ACCESS read-write

	STATUS mandatory

	DESCRIPTION

		"When both connectors are on the same network:



		   Setting this object to connector-1 allows the EMM to

		   monitor the port statistics of port 1-12 on a per-port

		   basis, and the port statistics of port 13-24 are summed

		   and are reported through port 13.



		   Setting this object to connector-2 allows the EMM to

		   monitor the port statistics of port 12-24 on a per-port

		   basis, and the port statistics of port 1-12 are summed

		   and are reported through port 13.



		 Note: when the 2 connectors are on different networks,

		 setting this object to the value connector-1 or

		 connector-2 will not have any effect.  The port counters

		 will be cleared whenever the value of this object is

		 changed."

	::= { ol51nnMTPCLModEntry 2 }



ol51nnMTPCLModConn1Network OBJECT-TYPE

	SYNTAX INTEGER {

		ethernet-1(6),

		ethernet-2(7),

		ethernet-3(8),

		isolated-1(21),

		isolated-2(22)

		}

	ACCESS read-write

	STATUS mandatory

	DESCRIPTION

		"The network that this connector is attached to."

	::= { ol51nnMTPCLModEntry 3 }



ol51nnMTPCLModConn2Network OBJECT-TYPE

	SYNTAX INTEGER {

		ethernet-1(6),

		ethernet-2(7),

		ethernet-3(8),

		isolated-1(21),

		isolated-2(22)

		}

	ACCESS read-write

	STATUS mandatory

	DESCRIPTION

		"The network that this connector is attached to."



	::= { ol51nnMTPCLModEntry 4 }



ol51nnMTPCLModConn1DipNetwork OBJECT-TYPE

	SYNTAX INTEGER {

		ethernet-1(6),

		ethernet-2(7),

		ethernet-3(8),

		isolated-1(21),

		isolated-2(22)

		}

	ACCESS read-only

	STATUS mandatory

	DESCRIPTION

		"The network indicated by the connector dip switch."

	::= { ol51nnMTPCLModEntry 5 }



ol51nnMTPCLModConn2DipNetwork OBJECT-TYPE

	SYNTAX INTEGER {

		ethernet-1(6),

		ethernet-2(7),

		ethernet-3(8),

		isolated-1(21),

		isolated-2(22)

		}

	ACCESS read-only

	STATUS mandatory

	DESCRIPTION

		"The network indicated by the connector dip switch."

	::= { ol51nnMTPCLModEntry 6 }



ol51nnMTPCLModAutoPartition OBJECT-TYPE

	SYNTAX INTEGER {

		collisions-31(1),

		collisions-63(2),

		collisions-127(3),

		collisions-255(4)

		}

	ACCESS read-write

	STATUS mandatory

	DESCRIPTION

		"This object holds the consecutive collision count

		 limit value.  The module goes into the auto-partition

		 mode whenever the consecutive collision count exceeds

		 the consecutive collision limit count."

	::= { ol51nnMTPCLModEntry 7 }



ol51nnMTPCLPortTable OBJECT-TYPE

	SYNTAX SEQUENCE OF Ol51nnMTPCLPortEntry

	ACCESS not-accessible

	STATUS mandatory

	DESCRIPTION

		"A table of port-specific information for each port of

		this module type."

	::= { ol51nnMTPCL 2 }



ol51nnMTPCLPortEntry OBJECT-TYPE

	SYNTAX Ol51nnMTPCLPortEntry

	ACCESS not-accessible

	STATUS mandatory

	DESCRIPTION

		"A list of module-specific information about a specific

		51nnM-TPCL port in the concentrator."

	INDEX { ol51nnMTPCLPortSlotIndex, ol51nnMTPCLPortIndex }

	::= { ol51nnMTPCLPortTable 1 }



Ol51nnMTPCLPortEntry ::=

	SEQUENCE {

		ol51nnMTPCLPortSlotIndex

			INTEGER,

		ol51nnMTPCLPortIndex

			INTEGER,

		ol51nnMTPCLPortAdminState

			INTEGER,

		ol51nnMTPCLPortBuddySlot

			INTEGER,

		ol51nnMTPCLPortBuddyPort

			INTEGER,

		ol51nnMTPCLPortDipAdminState

			INTEGER,

		ol51nnMTPCLPortLinkInteg

			INTEGER,

		ol51nnMTPCLPortDipLinkInteg

			INTEGER

		}



ol51nnMTPCLPortSlotIndex OBJECT-TYPE

	SYNTAX INTEGER

	ACCESS read-only

	STATUS mandatory

	DESCRIPTION

		"The slot number of this port's module."

	::= { ol51nnMTPCLPortEntry 1 }





ol51nnMTPCLPortIndex OBJECT-TYPE

	SYNTAX INTEGER

	ACCESS read-only

	STATUS mandatory

	DESCRIPTION

		"The port number of this port."

	::= { ol51nnMTPCLPortEntry 2 }



ol51nnMTPCLPortAdminState OBJECT-TYPE

	SYNTAX INTEGER {

		enabled(1),

		disabled(2),

		redundant-primary(3),

		redundant-backup(4),

		remote-diagnostics(8)

		}

	ACCESS read-write

	STATUS mandatory

	DESCRIPTION

		"The desired state of this port.  Setting this port to

		be redundant or for remote diagnostics with invalid settings

		of buddy slot and buddy port will return the genError error."

	::= { ol51nnMTPCLPortEntry 3 }



ol51nnMTPCLPortBuddySlot OBJECT-TYPE

	SYNTAX INTEGER

	ACCESS read-write

	STATUS mandatory

	DESCRIPTION

		"The slot index of the redundant port's buddy.  To set

		a port to be redundant, the buddy's slot and port must

		be set to valid values.



		The buddy is automatically set to be redundant to this port.



		If the port is configured for remote diagnostics, then

		this contains the slot index of the backup buddy port.

		To configure a port for remote diagnostics, the buddy's

		slot and port must be set to valid values."

	::= { ol51nnMTPCLPortEntry 4 }



ol51nnMTPCLPortBuddyPort  OBJECT-TYPE

	SYNTAX INTEGER

	ACCESS read-write

	STATUS mandatory

	DESCRIPTION

		"The port index of the redundant port's buddy.  To set

		a port to be redundant, the buddy's slot and port must

		be set to valid values.



		The buddy is automatically set to be redundant to this port.



		If the port is configured for remote diagnostics, then

		this contains the port index of the backup buddy port.

		To configure a port for remote diagnostics, the buddy's

		slot and port must be set to valid values."

	::= { ol51nnMTPCLPortEntry 5 }



ol51nnMTPCLPortDipAdminState OBJECT-TYPE

	SYNTAX INTEGER {

		enabled(1),

		disabled(2)

		}

	ACCESS read-only

	STATUS mandatory

	DESCRIPTION

		"The state of this port as indicated by the port's dip

		switches."

	::= { ol51nnMTPCLPortEntry 6 }



ol51nnMTPCLPortLinkInteg OBJECT-TYPE

	SYNTAX INTEGER {

		enabled(1),

		disabled(2)

		}

	ACCESS read-write

	STATUS mandatory

	DESCRIPTION

		"The current link integrity configuration for this port."

	::= { ol51nnMTPCLPortEntry 7 }



ol51nnMTPCLPortDipLinkInteg OBJECT-TYPE

	SYNTAX INTEGER {

		enabled(1),

		disabled(2)

		}

	ACCESS read-only

	STATUS mandatory

	DESCRIPTION

		"The link integrity configuration as indicated by this

		dip switch."

	::= { ol51nnMTPCLPortEntry 8 }





--

-- ONline Token Ring to Token Ring Bridge Module

--



ol52nnBTTModTable OBJECT-TYPE

	SYNTAX SEQUENCE OF Ol52nnBTTModEntry

	ACCESS not-accessible

	STATUS mandatory

	DESCRIPTION

		"A table of module-specific information for each

		52nnB-TT module in the concentrator."

	::= { ol52nnBTT 1 }



ol52nnBTTModEntry OBJECT-TYPE

	SYNTAX Ol52nnBTTModEntry

	ACCESS not-accessible

	STATUS mandatory

	DESCRIPTION

		"A list of module-specific information about a specific

		52nnB-TT module in the concentrator."

	INDEX { ol52nnBTTModSlotIndex }

	::= {ol52nnBTTModTable 1 }



Ol52nnBTTModEntry ::=

	SEQUENCE {

		ol52nnBTTModSlotIndex

			INTEGER,

		ol52nnBTTModBridgeType

			INTEGER,

		ol52nnBTTModSoftwareVersion

			DisplayString,

		ol52nnBTTModSRBridgeNo

			INTEGER,

		ol52nnBTTModNetworkStatus

			INTEGER

	}



ol52nnBTTModSlotIndex OBJECT-TYPE

	SYNTAX INTEGER

	ACCESS read-only

	STATUS mandatory

	DESCRIPTION

		"The slot number of this module."

	::= { ol52nnBTTModEntry 1 }



ol52nnBTTModBridgeType OBJECT-TYPE

	SYNTAX INTEGER {

		  bridge-type-sr(1),

		  bridge-type-srt(2)

		}

	ACCESS read-only

	STATUS mandatory

	DESCRIPTION

		"Whether the bridge is a source-routing bridge or a

		source-routing-transparent bridge."

	::= { ol52nnBTTModEntry 2 }



ol52nnBTTModSoftwareVersion OBJECT-TYPE

       SYNTAX DisplayString (SIZE(1..10))

       ACCESS read-only

       STATUS mandatory

       DESCRIPTION

	       "The version number of the software loaded into the

		module's flash chips."

       ::= { ol52nnBTTModEntry 3 }



ol52nnBTTModSRBridgeNo OBJECT-TYPE

	SYNTAX INTEGER

	ACCESS read-only

	STATUS mandatory

	DESCRIPTION

		"The module's source routing bridge number."

	::= { ol52nnBTTModEntry 4 }



ol52nnBTTModNetworkStatus OBJECT-TYPE

	SYNTAX INTEGER {

		okay(1),

		closed(2),

		beaconing(3)

		}

	ACCESS read-only

	STATUS mandatory

	DESCRIPTION

		"The status of the ring containing this module."

	::= {ol52nnBTTModEntry 5}



ol52nnBTTPortTable OBJECT-TYPE

	SYNTAX SEQUENCE OF Ol52nnBTTPortEntry

	ACCESS not-accessible

	STATUS mandatory

	DESCRIPTION

		"A table of port-specific for each port of each

		52nnB-TT module i the concentrator."

	::= { ol52nnBTT 2 }



ol52nnBTTPortEntry OBJECT-TYPE

	SYNTAX Ol52nnBTTPortEntry

	ACCESS not-accessible

	STATUS mandatory

	DESCRIPTION

		"A list of port-specific information about a specific

		52nnB-TT port in the concentrator."

	INDEX { ol52nnBTTPortSlotIndex, ol52nnBTTPortIndex }

	::= { ol52nnBTTPortTable 1 }



Ol52nnBTTPortEntry ::=

	SEQUENCE {

		ol52nnBTTPortSlotIndex

			INTEGER,

		ol52nnBTTPortIndex

			INTEGER,

		ol52nnBTTPortConnector

			INTEGER,

		ol52nnBTTPortSTAPState

			INTEGER,

		ol52nnBTTPortIpAddress

			IpAddress,

		ol52nnBTTPortMACAddress

			OCTET STRING,

		ol52nnBTTPortThroughput

			Gauge,

		ol52nnBTTPortForwarding

			Gauge,

		ol52nnBTTPortSRRingNo

			INTEGER,

		ol52nnBTTPortRingSpeed

			INTEGER

		}



ol52nnBTTPortSlotIndex OBJECT-TYPE

	SYNTAX INTEGER

	ACCESS read-only

	STATUS mandatory

	DESCRIPTION

		"The slot number for this port's module."

	::= { ol52nnBTTPortEntry 1 }



ol52nnBTTPortIndex OBJECT-TYPE

	SYNTAX INTEGER

	ACCESS read-only

	STATUS mandatory

	DESCRIPTION

		"The port number for this port within this slot."

	::= { ol52nnBTTPortEntry 2 }



ol52nnBTTPortConnector OBJECT-TYPE

	SYNTAX INTEGER {

		backPlane(1),	-- connects directly to backplane

		rj45(8),	-- unshielded

		db-9(10)	-- shielded

		}

	ACCESS read-write

	STATUS mandatory

	DESCRIPTION

		"The port connector. Notice that setting port connector

		 available only for the front pannel port."

	::= { ol52nnBTTPortEntry 3 }



ol52nnBTTPortSTAPState OBJECT-TYPE

	SYNTAX INTEGER {

		disabled (1),	-- receive and process frames

		blocking (2),	-- receive and process frames

		listening (3),  -- receive and process frames

		learning (4),	-- receive and process frames

		forwarding (5), -- receive, process and forward frames

		off (6)		-- receive and discard frames

		}

	ACCESS read-only

	STATUS mandatory

	DESCRIPTION

		"The port connector. Notice that setting port connector

		 available only for the front pannel port."

	::= { ol52nnBTTPortEntry 4 }





ol52nnBTTPortIpAddress OBJECT-TYPE

	SYNTAX IpAddress

	ACCESS read-only

	STATUS mandatory

	DESCRIPTION

		"The IP address associated with this port."

	::= { ol52nnBTTPortEntry 5 }



ol52nnBTTPortMACAddress OBJECT-TYPE

	SYNTAX OCTET STRING (SIZE(6))

	ACCESS read-only

	STATUS mandatory

	DESCRIPTION

		"A 6 octet address that uniquely identifies this port."

	::= { ol52nnBTTPortEntry 6 }



ol52nnBTTPortThroughput OBJECT-TYPE

	SYNTAX Gauge

	ACCESS read-only

	STATUS mandatory

	DESCRIPTION

		"Port throughput measured in Kbytes per second."

	::= { ol52nnBTTPortEntry 7 }



ol52nnBTTPortForwarding OBJECT-TYPE

	SYNTAX Gauge

	ACCESS read-only

	STATUS mandatory

	DESCRIPTION

		"Port forwarding rate measured in frames per second."

	::= { ol52nnBTTPortEntry 8 }



ol52nnBTTPortSRRingNo OBJECT-TYPE

	SYNTAX INTEGER

	ACCESS read-only

	STATUS mandatory

	DESCRIPTION

		"The port's source routing ring number."

	::= { ol52nnBTTPortEntry 9 }



ol52nnBTTPortRingSpeed OBJECT-TYPE

	SYNTAX INTEGER {

		fourMegabit(1),

		sixteenMegabit(2)

		}

	ACCESS read-write

	STATUS mandatory

	DESCRIPTION

		"The ring's bandwidth."

	::= { ol52nnBTTPortEntry 10 }





--

-- Trunk table is for compatibility purposes only

--



ol52nnBTTTrunkTable  OBJECT-TYPE

	SYNTAX SEQUENCE OF Ol52nnBTTTrunkEntry

	ACCESS not-accessible

	STATUS mandatory

	DESCRIPTION

		"A table that contains trunk-specific information for

		each trunk on each 52nnB-TT in the concentrator."

	::= {ol52nnBTT 3}



ol52nnBTTTrunkEntry  OBJECT-TYPE

	SYNTAX Ol52nnBTTTrunkEntry

	ACCESS not-accessible

	STATUS mandatory

	DESCRIPTION

		"A list of information about a specific Trunk on a

		52nnB-TT module in the concentrator."

	INDEX {ol52nnBTTTrunkSlotIndex, ol52nnBTTTrunkIndex}

	::= {ol52nnBTTTrunkTable 1}



Ol52nnBTTTrunkEntry ::=

	SEQUENCE {

		ol52nnBTTTrunkSlotIndex

			INTEGER,

		ol52nnBTTTrunkIndex

			INTEGER

		}



ol52nnBTTTrunkSlotIndex OBJECT-TYPE

	SYNTAX INTEGER

	ACCESS read-only

	STATUS mandatory

	DESCRIPTION

		"The slot number of this module. Its value ranges

		between 1 and olConcNumSlots."

	::= {ol52nnBTTTrunkEntry 1}



ol52nnBTTTrunkIndex OBJECT-TYPE

	SYNTAX INTEGER

	ACCESS read-only

	STATUS mandatory

	DESCRIPTION

		"The trunk number of this module. Its value ranges

		between 1 and olModNumTrunks."

	::= {ol52nnBTTTrunkEntry 2}





--

-- Token ring management module

--



ol52nnMMGTModTable  OBJECT-TYPE

	SYNTAX SEQUENCE OF Ol52nnMMGTModEntry

	ACCESS not-accessible

	STATUS mandatory

	DESCRIPTION

		"A table that contains module information about

		each 52nnM-MGT in the concentrator."

	::= {ol52nnMMGT 1}



ol52nnMMGTModEntry  OBJECT-TYPE

	SYNTAX Ol52nnMMGTModEntry

	ACCESS not-accessible

	STATUS mandatory

	DESCRIPTION

		"A list of module information for each 52nnM-MGT

		in the concentrator."

	INDEX {ol52nnMMGTModSlotIndex}

	::= {ol52nnMMGTModTable 1}



Ol52nnMMGTModEntry ::=

	SEQUENCE {

		ol52nnMMGTModSlotIndex

			INTEGER,

		ol52nnMMGTModMasterPriority

			INTEGER,

		ol52nnMMGTModMasterStatus

			INTEGER,

		ol52nnMMGTModStationAddr

			OCTET STRING,

		ol52nnMMGTModRingSpeed

			INTEGER,

		ol52nnMMGTModNetworkStatus

			INTEGER,

		ol52nnMMGTModMasterNetwork

			INTEGER,

		ol52nnMMGTModLocalMACAddress

			MacAddress,

		ol52nnMMGTModMACAddressType

			INTEGER,

		ol52nnMMGTModActiveMACAddress

			MacAddress

		}



ol52nnMMGTModSlotIndex OBJECT-TYPE

	SYNTAX INTEGER

	ACCESS read-only

	STATUS mandatory

	DESCRIPTION

		"The slot number of this module. Its value ranges

		between 1 and olConcNumSlots."

	::= {ol52nnMMGTModEntry 1}



ol52nnMMGTModMasterPriority OBJECT-TYPE

	SYNTAX INTEGER {

		one(1),

		two(2),

		three(3),

		four(4),

		five(5),

		six(6),

		seven(7),

		eight(8),

		nine(9),

		ten(10)

		}

	ACCESS read-write

	STATUS mandatory

	DESCRIPTION

		"The mastership priority of this agent. Ten is the

		highest and one is the lowest. Priority is only

		used when an election occurs. Mastership is not

		preemptive unless the reset mastership command is used."

	::= {ol52nnMMGTModEntry 2}



ol52nnMMGTModMasterStatus OBJECT-TYPE

	SYNTAX INTEGER {

		master(1),

		non-master(2),

		electing(3)

		}

	ACCESS read-only

	STATUS mandatory

	DESCRIPTION

		"The mastership status of this agent."

	::= {ol52nnMMGTModEntry 3}



ol52nnMMGTModStationAddr OBJECT-TYPE

	SYNTAX OCTET STRING

	ACCESS read-only

	STATUS mandatory

	DESCRIPTION

		"A 6 octet address that uniquely identifies this module.

		The station address is the MAC address of port 1."

	::= {ol52nnMMGTModEntry 4}



ol52nnMMGTModRingSpeed OBJECT-TYPE

	SYNTAX INTEGER {

		fourMegabit(1),

		sixteenMegabit(2)

		}

	ACCESS read-write

	STATUS mandatory

	DESCRIPTION

		"The ring's bandwidth."

	::= {ol52nnMMGTModEntry 5}



ol52nnMMGTModNetworkStatus OBJECT-TYPE

	SYNTAX INTEGER {

		okay(1),

		closed(2),

		beaconing(3)

		}

	ACCESS read-only

	STATUS mandatory

	DESCRIPTION

		"The status of the ring containing this module."

	::= {ol52nnMMGTModEntry 6}



ol52nnMMGTModMasterNetwork OBJECT-TYPE

	SYNTAX INTEGER {

		isolated(2),

		token-ring-1(9),

		token-ring-2(10),

		token-ring-3(11),

		token-ring-4(12),

		token-ring-5(13),

		token-ring-6(14),

		token-ring-7(15),

		no-change(25)

		}

	ACCESS read-write

	STATUS mandatory

	DESCRIPTION

		"The network that this module should assign itself to upon

		 becoming master if the module was previously a slave.

		 no-change(25) indicates that the module should not change

		 its current network assignment."

	::= {ol52nnMMGTModEntry 7}





ol52nnMMGTModLocalMACAddress OBJECT-TYPE

	SYNTAX MacAddress

	ACCESS read-write

	STATUS mandatory

	DESCRIPTION

		"A MAC address with the locally administered bit set to

		one. Setting this value to an invalid address will return

		invalidData error.  An invalid address is a value with the

		locally administered bit set to zero, or a value of all ones."

	::= {ol52nnMMGTModEntry 8}





ol52nnMMGTModMACAddressType OBJECT-TYPE

	SYNTAX INTEGER {

		burned-in(1),

		locally-administered(2)

		}

	ACCESS read-write

	STATUS mandatory

	DESCRIPTION

		"The desired MAC address for this agent.  burned-in(1)

		indicates that the factory setting as defined in

		ol52nnMMGTModStationAddr should be used.

		locally-administered(2) indicates that the MAC address

		set in ol52nnMMGTModLocalMACAddress should be used.  This

		change will take effect following a reset of the agent.

		The actual MAC address in use is defined in

		ol52nnMMGTModActiveMACAddress.  Setting this value to use

		an invalid MAC address (for example, all zeros) will return

		invalidData error."

	::= {ol52nnMMGTModEntry 9}



ol52nnMMGTModActiveMACAddress OBJECT-TYPE

	SYNTAX MacAddress

	ACCESS read-only

	STATUS mandatory

	DESCRIPTION

		"A actual MAC address that is being used by this agent. This

		is the MAC address of port 1."

	::= {ol52nnMMGTModEntry 10}



ol52nnMMGTPortTable  OBJECT-TYPE

	SYNTAX SEQUENCE OF Ol52nnMMGTPortEntry

	ACCESS not-accessible

	STATUS mandatory

	DESCRIPTION

		"A table that contains port-specific information for

		each port on each 52nnM-MGT in the concentrator."

	::= {ol52nnMMGT 2}



ol52nnMMGTPortEntry  OBJECT-TYPE

	SYNTAX Ol52nnMMGTPortEntry

	ACCESS not-accessible

	STATUS mandatory

	DESCRIPTION

		"A list of information about a specific port on a

		52nnM-MGT module in the concentrator."

	INDEX {ol52nnMMGTPortSlotIndex, ol52nnMMGTPortIndex}

	::= {ol52nnMMGTPortTable 1}



Ol52nnMMGTPortEntry ::=

	SEQUENCE {

		ol52nnMMGTPortSlotIndex

			INTEGER,

		ol52nnMMGTPortIndex

			INTEGER,

		ol52nnMMGTPortIpAddress

			IpAddress

		}



ol52nnMMGTPortSlotIndex OBJECT-TYPE

	SYNTAX INTEGER

	ACCESS read-only

	STATUS mandatory

	DESCRIPTION

		"The slot number of this port's module."

	::= {ol52nnMMGTPortEntry 1}



ol52nnMMGTPortIndex OBJECT-TYPE

	SYNTAX INTEGER

	ACCESS read-only

	STATUS mandatory

	DESCRIPTION

		"The port number of this port."

	::= {ol52nnMMGTPortEntry 2}



ol52nnMMGTPortIpAddress  OBJECT-TYPE

	SYNTAX IpAddress

	ACCESS read-only

	STATUS mandatory

	DESCRIPTION

		"The IP address associated with this port."

	::= {ol52nnMMGTPortEntry 3}



ol52nnMMGTTrunkTable  OBJECT-TYPE

	SYNTAX SEQUENCE OF Ol52nnMMGTTrunkEntry

	ACCESS not-accessible

	STATUS mandatory

	DESCRIPTION

		"A table that contains trunk-specific information for

		each trunk on each 52nnM-MGT in the concentrator."

	::= {ol52nnMMGT 3}



ol52nnMMGTTrunkEntry  OBJECT-TYPE

	SYNTAX Ol52nnMMGTTrunkEntry

	ACCESS not-accessible

	STATUS mandatory

	DESCRIPTION

		"A list of information about a specific Trunk on a

		52nnM-MGT module in the concentrator."

	INDEX {ol52nnMMGTTrunkSlotIndex, ol52nnMMGTTrunkIndex}

	::= {ol52nnMMGTTrunkTable 1}



Ol52nnMMGTTrunkEntry ::=

	SEQUENCE {

		ol52nnMMGTTrunkSlotIndex

			INTEGER,

		ol52nnMMGTTrunkIndex

			INTEGER,

		ol52nnMMGTTrunkCableMon

			INTEGER,

		ol52nnMMGTTrunkNetMapState

			INTEGER,

		ol52nnMMGTTrunkExtBcnRecovery

			INTEGER

		}



ol52nnMMGTTrunkSlotIndex OBJECT-TYPE

	SYNTAX INTEGER

	ACCESS read-only

	STATUS mandatory

	DESCRIPTION

		"The slot number of this module. Its value ranges

		between 1 and olConcNumSlots."

	::= {ol52nnMMGTTrunkEntry 1}



ol52nnMMGTTrunkIndex OBJECT-TYPE

	SYNTAX INTEGER

	ACCESS read-only

	STATUS mandatory

	DESCRIPTION

		"The slot number of this module. Its value ranges

		between 1 and olModNumTrunks."

	::= {ol52nnMMGTTrunkEntry 2}



ol52nnMMGTTrunkCableMon OBJECT-TYPE

	SYNTAX INTEGER {

		enable(1),

		disable(2),

		notApplicable(3)

		}

	ACCESS read-write

	STATUS mandatory

	DESCRIPTION

		"The cable monitor configuration for this trunk."

	::= {ol52nnMMGTTrunkEntry 3}



ol52nnMMGTTrunkNetMapState OBJECT-TYPE

	SYNTAX INTEGER {

		notApplicable(1),

		internal(2),

		external(3)

		}

	ACCESS read-write

	STATUS mandatory

	DESCRIPTION

		"The map state of the copper ring-in trunk. This

		should be set to external for ring-in trunks which

		connect to external hubs. The mapping logic will not

		operate on trunks which are set to external. This

		prevents incorrect mapping which can occur when a

		module in one hub detects the mapping signal from

		another hub. This attribute only applies to copper

		ring-in trunks."

	::= {ol52nnMMGTTrunkEntry 4}





ol52nnMMGTTrunkExtBcnRecovery OBJECT-TYPE

	SYNTAX INTEGER {

		exists(1),

		nonExists(2),

		notApplicable(3)

	}

	ACCESS read-write

	STATUS mandatory

	DESCRIPTION

		"Indicates whether the trunk is connected to a

		segment that will perform beacon recovery.  This

		should be set to exists(1) for trunks which connect

		to hubs which perform beacon recovery.  This attribute

		is used to determine the fault domain when resolving a

		beaconing condition.



		The beacon recovery process will resolve beaconing on

		trunks with this attribute set to nonExists(2) before

		trunks with the attribute set to exists(1) are resolved.

		For backplane trunks, setting to a value other than

		notApplicable will return invalidData error.  The

		default value is nonExists(2)."

	::= { ol52nnMMGTTrunkEntry 5 }





--

-- ONline Ethernet Interconnect Module

--



ol51nnIxModTable OBJECT-TYPE

	SYNTAX SEQUENCE OF Ol51nnIxModEntry

	ACCESS not-accessible

	STATUS mandatory

	DESCRIPTION

		"A table of module-specific information for

		each 51nnI-x module in the concentrator."

	::= { ol51nnIx 1 }



ol51nnIxModEntry OBJECT-TYPE

	SYNTAX Ol51nnIxModEntry

	ACCESS not-accessible

	STATUS mandatory

	DESCRIPTION

		"A list of module-specific information about a specific

		51nnI-x module in the concentrator."

	INDEX { ol51nnIxModSlotIndex }

	::= { ol51nnIxModTable 1 }



Ol51nnIxModEntry ::=

	SEQUENCE {

		ol51nnIxModSlotIndex

			INTEGER,

		ol51nnIxModSwType

			INTEGER,

		ol51nnIxModStationAddr

			OCTET STRING,

		ol51nnIxModDipPromDefaults

			INTEGER,

		ol51nnIxModProtocols

			DisplayString

		}



ol51nnIxModSlotIndex OBJECT-TYPE

	SYNTAX INTEGER

	ACCESS read-only

	STATUS mandatory

	DESCRIPTION

		"The slot number of this module."

	::= { ol51nnIxModEntry 1 }



ol51nnIxModSwType OBJECT-TYPE

	SYNTAX INTEGER {

		bridge(1),

		switch(2),

		router(3)

		}

	ACCESS read-only

	STATUS mandatory

	DESCRIPTION

		"The software currently loaded and executing has the

		module operating as a Bridge, Switch or Router."

	::= { ol51nnIxModEntry 2 }



ol51nnIxModStationAddr OBJECT-TYPE

	SYNTAX OCTET STRING (SIZE(6))

	ACCESS read-only

	STATUS mandatory

	DESCRIPTION

		"A 6 octet address that uniquely identifies this module.

		The station address is the mac address of port 1."

	::= { ol51nnIxModEntry 3 }



ol51nnIxModDipPromDefaults OBJECT-TYPE

	SYNTAX INTEGER {

		true(1),

		false(2)

		}

	ACCESS read-only

	STATUS mandatory

	DESCRIPTION

		"The current module configuration with respect to

		default PROM values as specified by dip switches."

	::= { ol51nnIxModEntry 4 }





ol51nnIxModProtocols OBJECT-TYPE

	SYNTAX DisplayString

	ACCESS read-only

	STATUS mandatory

	DESCRIPTION

		"A textual description of the protocols supported by

		this module"

	::= { ol51nnIxModEntry 5 }





ol51nnIxPortTable	OBJECT-TYPE

	SYNTAX SEQUENCE OF Ol51nnIxPortEntry

	ACCESS not-accessible

	STATUS mandatory

	DESCRIPTION

		"A table of port-specific information for each port of

		each 51nnI-x module in the concentrator."

	::= { ol51nnIx 2 }





ol51nnIxPortEntry OBJECT-TYPE

	SYNTAX Ol51nnIxPortEntry

	ACCESS not-accessible

	STATUS mandatory

	DESCRIPTION

		"A list of port-specific information about a specific

		51nnI-x port in the concentrator."

	INDEX { ol51nnIxPortSlotIndex, ol51nnIxPortIndex }

	::= { ol51nnIxPortTable 1 }



Ol51nnIxPortEntry ::=

	SEQUENCE {

		ol51nnIxPortSlotIndex

			INTEGER,

		ol51nnIxPortIndex

			INTEGER,

		ol51nnIxPortDipAdminState

			INTEGER,

		ol51nnIxPortSTAPState

			INTEGER,

		ol51nnIxPortIpAddress

			IpAddress,

		ol51nnIxPortDipNetwork

			INTEGER,

		ol51nnIxPortDefNetwork

			INTEGER

		}



ol51nnIxPortSlotIndex OBJECT-TYPE

	SYNTAX INTEGER

	ACCESS read-only

	STATUS mandatory

	DESCRIPTION

		"The slot number for this port's module."

	::= { ol51nnIxPortEntry 1 }



ol51nnIxPortIndex OBJECT-TYPE

	SYNTAX INTEGER

	ACCESS read-only

	STATUS mandatory

	DESCRIPTION

		"The port number for this port within this slot."

	::= { ol51nnIxPortEntry 2 }



ol51nnIxPortDipAdminState OBJECT-TYPE

	SYNTAX INTEGER {

		enabled(1),

		disabled(2)

		}

	ACCESS read-only

	STATUS mandatory

	DESCRIPTION

		"The state of this port as indicated by the port's dip

		switches."

	::= { ol51nnIxPortEntry 3 }



ol51nnIxPortSTAPState OBJECT-TYPE

	SYNTAX INTEGER {

		disabled (1),	-- receive and process frames

		blocking (2),	-- receive and process frames

		listening (3),  -- receive and process frames

		learning (4),	-- receive and process frames

		forwarding (5), -- receive, process and forward frames

		off (6),	-- receive SNMP frames, others discarded

		unknown(7)	-- not currently reporting STAP state

		}

	ACCESS read-only

	STATUS mandatory

	DESCRIPTION

		"The current IEEE 802.1d Spanning Tree Algorithm and Protocol

		 state (STAP) of this port."

	::= { ol51nnIxPortEntry 4 }



ol51nnIxPortIpAddress OBJECT-TYPE

	SYNTAX IpAddress

	ACCESS read-only

	STATUS mandatory

	DESCRIPTION

		"The IP Address associated with this port."

	::= { ol51nnIxPortEntry 5 }



ol51nnIxPortDipNetwork OBJECT-TYPE

	SYNTAX INTEGER {

		isolated(2),

		front-panel(5),

		ethernet-1(6),

		ethernet-2(7),

		ethernet-3(8)

		}

	ACCESS read-only

	STATUS mandatory

	DESCRIPTION

		"The network for this port as specified by this port's

		dip switches."

	::= { ol51nnIxPortEntry 6 }



ol51nnIxPortDefNetwork OBJECT-TYPE

	SYNTAX INTEGER {

		isolated(2),

		front-panel(5),

		ethernet-1(6),

		ethernet-2(7),

		ethernet-3(8)

		}

	ACCESS read-only

	STATUS mandatory

	DESCRIPTION

		"The network for this port as specified by the OEIM's

		non-volatile storage."

	::= { ol51nnIxPortEntry 7 }





--

-- FDDI Management Module

--



ol53nnMMGTModTable OBJECT-TYPE

	SYNTAX SEQUENCE OF Ol53nnMMGTModEntry

	ACCESS not-accessible

	STATUS mandatory

	DESCRIPTION

		"A list of module attributes that apply to this model.

		To access an ol53nnMMGTModTable entry, the

		ol53nnMMGTModSlotIndex attribute is used."

	::= { ol53nnMMGT 1 }



ol53nnMMGTModEntry OBJECT-TYPE

	SYNTAX Ol53nnMMGTModEntry

	ACCESS not-accessible

	STATUS mandatory

	DESCRIPTION

		"A list of module-specific information about a specific

		53nnM-MGT module in the concentrator."

	INDEX { ol53nnMMGTModSlotIndex }

	::= { ol53nnMMGTModTable 1 }



Ol53nnMMGTModEntry ::=

	SEQUENCE {

		ol53nnMMGTModSlotIndex

			INTEGER,

		ol53nnMMGTModMasterPriority

			INTEGER,

		ol53nnMMGTModMasterStatus

			INTEGER,

		ol53nnMMGTModStationAddr

			OCTET STRING,

		ol53nnMMGTModIpAddress

			IpAddress,

		ol53nnMMGTModDownStreamMAC

			OCTET STRING,

		ol53nnMMGTModUpStreamMAC

			OCTET STRING,

		ol53nnMMGTModfddiMACPath

			INTEGER,

		ol53nnMMGTModDownStreamModule

			INTEGER,

		ol53nnMMGTModUpStreamModule

			INTEGER,

		ol53nnMMGTModDownStreamOperPath

			INTEGER,

		ol53nnMMGTModUpStreamOperPath

			INTEGER,

		ol53nnMMGTModRingInfo

			OCTET STRING

		}



ol53nnMMGTModSlotIndex OBJECT-TYPE

	SYNTAX INTEGER

	ACCESS read-only

	STATUS mandatory

	DESCRIPTION

		"A unique value that identifies a particular module.  Its

		value ranges between 1 and olModSlotNumber.  The module

		identified by a particular value of this index is the same

		module as indentified by the same value of olModSlotIndex."

	::= { ol53nnMMGTModEntry 1 }



ol53nnMMGTModMasterPriority OBJECT-TYPE

	SYNTAX INTEGER {

		one(1),

		two(2),

		three(3),

		four(4),

		five(5),

		six(6),

		seven(7),

		eight(8),

		nine(9),

		ten(10)

		}

	ACCESS read-write

	STATUS mandatory

	DESCRIPTION

		"The mastership priority of this agent. Ten is the

		highest and one is the lowest. Priority is only

		used when an election occurs. Mastership is not

		preemptive unless the reset mastership command is used."

	::= {ol53nnMMGTModEntry 2 }



ol53nnMMGTModMasterStatus OBJECT-TYPE

	SYNTAX INTEGER {

		master(1),

		non-master(2),

		electing(3)

		}

	ACCESS read-only

	STATUS mandatory

	DESCRIPTION

		"The mastership status of this agent."

	::= {ol53nnMMGTModEntry 3 }



ol53nnMMGTModStationAddr OBJECT-TYPE

	SYNTAX OCTET STRING (SIZE (6))

	ACCESS read-only

	STATUS mandatory

	DESCRIPTION

		"A 6 octet address that uniquely identifies this module.

		The station address is the MAC address of port 1."

	::= {ol53nnMMGTModEntry 4 }



ol53nnMMGTModIpAddress  OBJECT-TYPE

	SYNTAX IpAddress

	ACCESS read-only

	STATUS mandatory

	DESCRIPTION

		"The IP address associated with this module."

	::= {ol53nnMMGTModEntry 5 }



ol53nnMMGTModDownStreamMAC OBJECT-TYPE

	SYNTAX OCTET STRING (SIZE (6))

	ACCESS read-only

	STATUS mandatory

	DESCRIPTION

		"Down stream MAC"

	::= { ol53nnMMGTModEntry 6 }



ol53nnMMGTModUpStreamMAC OBJECT-TYPE

	SYNTAX OCTET STRING (SIZE (6))

	ACCESS read-only

	STATUS mandatory

	DESCRIPTION

		"Up stream MAC"

	::= { ol53nnMMGTModEntry 7 }



ol53nnMMGTModfddiMACPath OBJECT-TYPE

	SYNTAX INTEGER {

		primary(1),

		secondary(2)

		}

	ACCESS read-write

	STATUS mandatory

	DESCRIPTION

		"The FDDI path which should be inserted into the MAC"

	::= { ol53nnMMGTModEntry 8 }



ol53nnMMGTModDownStreamModule OBJECT-TYPE

	SYNTAX INTEGER (1..16)

	ACCESS read-only

	STATUS mandatory

	DESCRIPTION

		"Down stream slot (transmit to)"

	::= { ol53nnMMGTModEntry 9 }



ol53nnMMGTModUpStreamModule OBJECT-TYPE

	SYNTAX INTEGER (1..16)

	ACCESS read-only

	STATUS mandatory

	DESCRIPTION

		"Up stream slot (receive from)"

	::= { ol53nnMMGTModEntry 10 }



ol53nnMMGTModDownStreamOperPath OBJECT-TYPE

	SYNTAX INTEGER {

		isolated(2),

		fddi-path-1(24),

		fddi-path-2(25),

		fddi-path-3(26),

		fddi-path-4(27),

		fddi-path-5(28),

		fddi-path-6(29),

		fddi-path-7(30),

		fddi-path-8(31)

		}

	ACCESS read-only

	STATUS mandatory

	DESCRIPTION

		"Transmit DBA  (debug only)"

	::= { ol53nnMMGTModEntry 11 }



ol53nnMMGTModUpStreamOperPath OBJECT-TYPE

	SYNTAX INTEGER  {

		isolated(2),

		fddi-path-1(24),

		fddi-path-2(25),

		fddi-path-3(26),

		fddi-path-4(27),

		fddi-path-5(28),

		fddi-path-6(29),

		fddi-path-7(30),

		fddi-path-8(31)

		}

	ACCESS read-only

	STATUS mandatory

	DESCRIPTION

		"Receive DBA (debug only)"

	::= { ol53nnMMGTModEntry 12 }



ol53nnMMGTModRingInfo OBJECT-TYPE

	SYNTAX OCTET STRING (SIZE(1..8))

	ACCESS read-only

	STATUS mandatory

	DESCRIPTION

		"An array which is indexed by DBA number. Each element

		 contains the slot number (1..16) which is assigned to

		 transmit on this DBA. (debug only)"

	::= { ol53nnMMGTModEntry 13 }





-- port table



ol53nnMMGTPortTable OBJECT-TYPE

	SYNTAX SEQUENCE OF Ol53nnMMGTPortEntry

	ACCESS not-accessible

	STATUS mandatory

	DESCRIPTION

		"A table of port-specific information for each port of

		this module type."

	::= { ol53nnMMGT 2 }



ol53nnMMGTPortEntry OBJECT-TYPE

	SYNTAX Ol53nnMMGTPortEntry

	ACCESS not-accessible

	STATUS mandatory

	DESCRIPTION

		"A list of module-specific information about a specific

		53nnM-MGT port in the concentrator."

	INDEX { ol53nnMMGTPortSlotIndex, ol53nnMMGTPortIndex }

	::= { ol53nnMMGTPortTable 1 }



Ol53nnMMGTPortEntry ::=

	SEQUENCE {

		ol53nnMMGTPortSlotIndex

			INTEGER,

		ol53nnMMGTPortIndex

			INTEGER,

		ol53nnMMGTPortConfig

			INTEGER,

		ol53nnMMGTPortPcmState

			INTEGER,

		ol53nnMMGTPortConnectState

			INTEGER,

		ol53nnMMGTPortNeighbor

			INTEGER,

		ol53nnMMGTPortRemoteMACIndicated

			INTEGER,

		ol53nnMMGTPortBSFlag

			INTEGER,

		ol53nnMMGTPortPCWithhold

			INTEGER,

		ol53nnMMGTPortLerCondition

			INTEGER

		}



ol53nnMMGTPortSlotIndex OBJECT-TYPE

	SYNTAX INTEGER

	ACCESS read-only

	STATUS mandatory

	DESCRIPTION

		"A unique value that identifies a particular module.  Its

		value ranges between 1 and olModSlotNumber.  The module

		identified by a particular value of this index is the same

		module as indentified by the same value of

		olPortSlotIndex."

	::= { ol53nnMMGTPortEntry 1 }





ol53nnMMGTPortIndex OBJECT-TYPE

	SYNTAX INTEGER

	ACCESS read-only

	STATUS mandatory

	DESCRIPTION

		"A unique value that identifies a particular port within this

		module. Its value ranges between 1 and olModPortNumber.

		The module identified by a particular value of this index is

		the same module as indentified by the same value of

		olPortIndex."

	::= { ol53nnMMGTPortEntry 2 }



ol53nnMMGTPortConfig OBJECT-TYPE

	SYNTAX INTEGER {

		a(1),

		b(2)

		}

	ACCESS read-only

	STATUS mandatory

	DESCRIPTION

		"Specifies the FDDI port type (a or b)."

	::= { ol53nnMMGTPortEntry 3 }



ol53nnMMGTPortPcmState OBJECT-TYPE

	SYNTAX INTEGER {

		  pc0(1), -- Off

		  pc1(2), -- Break

		  pc2(3), -- Trace

		  pc3(4), -- Connect

		  pc4(5), -- Next

		  pc5(6), -- Signal

		  pc6(7), -- Join

		  pc7(8), -- Verify

		  pc8(9), -- Active

		  pc9(10) -- Maint

	}

	ACCESS read-only

	STATUS mandatory

	DESCRIPTION

		      "(refer to ANSI SMT 9.6.2)."

	::= { ol53nnMMGTPortEntry 4 }



ol53nnMMGTPortConnectState OBJECT-TYPE

	SYNTAX INTEGER {

	  disabled(1),

	  connecting(2),

	  standby(3),

	  active(4)

		}

	ACCESS read-only

	STATUS mandatory

	DESCRIPTION

	     "An indication of the connect state of this PORT.

	      Basically, this gives a higher level view of the

	      state of the connection by grouping PCM states and

	      the PC-Withhold flag state.  The supported values

	      and their corresponding PCM states and PC-Withhold

	      condition, when relevant, are:

		  disabled: (PC0:Off, PC9:Maint)

		  connecting: (PC1(Break) || PC3 (Connect) || PC4(next) ||

			       PC5 (Signal) || PC6(Join) || PC7 (Verify)) &&

			      (PC-Withhold = None)

		  standby: (PC-Withhold != None)

		  active: (PC2:Trace || PC8:Active)"

	::= { ol53nnMMGTPortEntry 5 }



ol53nnMMGTPortNeighbor OBJECT-TYPE

	SYNTAX INTEGER {

		a(1),

		b(2),

		slave(3),

		master(4),

		unknown(5)

		}

	ACCESS read-only

	STATUS mandatory

	DESCRIPTION

	     "The type (PC-Neighbor) of the remote PORT that is

	      determined in PC-Signaling in R-Val (1,2) (refer

	      to ANSI SMT 9.6.3.2)."

	::= { ol53nnMMGTPortEntry 6 }



ol53nnMMGTPortRemoteMACIndicated OBJECT-TYPE

	SYNTAX INTEGER { true(1), false(2) }

	ACCESS read-only

	STATUS mandatory

	DESCRIPTION

	  "The indication, in PC-Signaling that the remote

	   partner intends to place a MAC in the output token

	   PATH of this PORT.  Signaled as R-Val (9) (refer

	   to ANSI SMT 9.6.3.2)."

	::= { ol53nnMMGTPortEntry 7 }



ol53nnMMGTPortBSFlag OBJECT-TYPE

	SYNTAX INTEGER { true(1), false(2) }

	ACCESS read-only

	STATUS mandatory

	DESCRIPTION

	  "The Break State, BS-Flag (refer to ANSI SMT

	   9.4.3.4)."

	::= { ol53nnMMGTPortEntry 8 }



ol53nnMMGTPortPCWithhold OBJECT-TYPE

	SYNTAX INTEGER  { none(1), m-m(2), other(3) }

	ACCESS read-only

	STATUS mandatory

	DESCRIPTION

	   "PC-Withhold, (refer to ANSI SMT 9.4.1)."

	::= { ol53nnMMGTPortEntry 9 }



ol53nnMMGTPortLerCondition OBJECT-TYPE

	SYNTAX INTEGER  { bad(1), okay(2) }

	ACCESS read-only

	STATUS mandatory

	DESCRIPTION

	   "This variable is set to true whenever LerEstimate

	    is less than or equal to LerAlarm (the larger the number

	    the smaller the value)."

	::= { ol53nnMMGTPortEntry 10 }





-- Trunk Table

-- (only present for compatibility)



ol53nnMMGTTrunkTable OBJECT-TYPE

	SYNTAX SEQUENCE OF Ol53nnMMGTTrunkEntry

	ACCESS not-accessible

	STATUS mandatory

	DESCRIPTION

		"FDDI module specific trunk table variables.

		 At present there are none."

	::= { ol53nnMMGT 3 }



ol53nnMMGTTrunkEntry OBJECT-TYPE

	SYNTAX Ol53nnMMGTTrunkEntry

	ACCESS not-accessible

	STATUS mandatory

	DESCRIPTION

		"A description of 53nnM-MGT trunk attributes."

	INDEX { ol53nnMMGTTrunkSlotIndex, ol53nnMMGTTrunkIndex }

	::= { ol53nnMMGTTrunkTable 1 }



Ol53nnMMGTTrunkEntry ::=

	SEQUENCE {

		ol53nnMMGTTrunkSlotIndex

			INTEGER,

		ol53nnMMGTTrunkIndex

			INTEGER

		}



ol53nnMMGTTrunkSlotIndex OBJECT-TYPE

	SYNTAX INTEGER

	ACCESS read-only

	STATUS mandatory

	DESCRIPTION

		"A unique value that identifies a particular module.  Its

		value ranges between 1 and olModSlotNumber.  The module

		identified by a particular value of this index is the same

		module as indentified by the same value of

		olTrunkSlotIndex."

	::= { ol53nnMMGTTrunkEntry 1 }





ol53nnMMGTTrunkIndex OBJECT-TYPE

	SYNTAX INTEGER

	ACCESS read-only

	STATUS mandatory

	DESCRIPTION

		"A unique value that identifies a particular trunk within this

		module. Its value ranges between 1 and olModTrunkNumber.

		The module identified by a particular value of this index is

		the same module as indentified by the same value of

		olTrunkIndex."

	::= { ol53nnMMGTTrunkEntry 2 }





--

-- ONline Hidden Controller Module

--



ol50nnMHCTLModTable OBJECT-TYPE

	SYNTAX SEQUENCE OF Ol50nnMHCTLModEntry

	ACCESS not-accessible

	STATUS mandatory

	DESCRIPTION

		"A table that contains information about each 50nnM-HCTL

		in the concentrator.  "

	::= { ol50nnMHCTL 1 }



ol50nnMHCTLModEntry OBJECT-TYPE

	SYNTAX Ol50nnMHCTLModEntry

	ACCESS not-accessible

	STATUS mandatory

	DESCRIPTION

		"A list of information for each 50nnM-HCTL module

		in the concentrator."

	INDEX { ol50nnMHCTLModSlotIndex }

	::= { ol50nnMHCTLModTable 1 }



Ol50nnMHCTLModEntry ::=

	SEQUENCE {

		ol50nnMHCTLModSlotIndex

			INTEGER,

		ol50nnMHCTLModOperState

			INTEGER,

		ol50nnMHCTLModClockStatus

			INTEGER,

		ol50nnMHCTLModTempStatus

			INTEGER,

		ol50nnMHCTLModPDBStatus

			INTEGER,

		ol50nnMHCTLModDipCh1ActCol

			INTEGER,

		ol50nnMHCTLModDipCh2ActCol

			INTEGER,

		ol50nnMHCTLModDipCh3ActCol

			INTEGER

		}



ol50nnMHCTLModSlotIndex OBJECT-TYPE

	SYNTAX INTEGER

	ACCESS read-only

	STATUS mandatory

	DESCRIPTION

		"The slot number for this module.  The value should be 7."

	::= { ol50nnMHCTLModEntry 1 }



ol50nnMHCTLModOperState OBJECT-TYPE

	SYNTAX INTEGER {

		active(1),

		standby(2)

		}

	ACCESS read-only

	STATUS mandatory

	DESCRIPTION

		"The operational state of the 50nnM-HCTL module.  Specifically,

		this is an indicator of whether the 50nnM-HCTL module is

		providing clock signals to the backplane.  An active 50nnM-HCTL

		module provides clock signals to the backplane while a standby

		50nnM-HCTL module does not.  Note that only one 50nnM-HCTL

		module will be active at any given time; all other 50nnM-HCTL/

		50nnM-RCTL modules in the concentrator will be in standby mode."

	::= { ol50nnMHCTLModEntry 2 }



ol50nnMHCTLModClockStatus OBJECT-TYPE

	SYNTAX INTEGER {

		okay(1),

		faulty(2)

		}

	ACCESS read-only

	STATUS mandatory

	DESCRIPTION

		"The current status of the on-board clocks on this module."

	::= { ol50nnMHCTLModEntry 3 }



ol50nnMHCTLModTempStatus OBJECT-TYPE

	SYNTAX INTEGER {

		okay(1),

		extremeTemp(2)

		}

	ACCESS read-only

	STATUS mandatory

	DESCRIPTION

		"The temperature as detected by the probe on this module."

	::= { ol50nnMHCTLModEntry 4 }



ol50nnMHCTLModPDBStatus OBJECT-TYPE

	SYNTAX INTEGER {

		present(1),

		notPresent(2)

		}

	ACCESS read-only

	STATUS mandatory

	DESCRIPTION

		"Indicates whether this 6-slot concentrator contains a power

		distribution board that supports powersupply redundancy."

	::= { ol50nnMHCTLModEntry 5 }



ol50nnMHCTLModDipCh1ActCol OBJECT-TYPE

	SYNTAX INTEGER {

		enabled(1),

		disabled(2)

		}

	ACCESS read-only

	STATUS mandatory

	DESCRIPTION

		"The Ethernet channel 1 activity/collision LED configuration

		as indicated by this module's dip switches."

	::= { ol50nnMHCTLModEntry 6 }



ol50nnMHCTLModDipCh2ActCol OBJECT-TYPE

	SYNTAX INTEGER {

		enabled(1),

		disabled(2)

		}

	ACCESS read-only

	STATUS mandatory

	DESCRIPTION

		"The Ethernet channel 2 activity/collision LED configuration

		as indicated by this module's dip switches."

	::= { ol50nnMHCTLModEntry 7 }



ol50nnMHCTLModDipCh3ActCol OBJECT-TYPE

	SYNTAX INTEGER {

		enabled(1),

		disabled(2)

		}

	ACCESS read-only

	STATUS mandatory

	DESCRIPTION

		"The Ethernet channel 3 activity/collision LED configuration

		as indicated by this module's dip switches."

	::= { ol50nnMHCTLModEntry 8 }





--

-- ONline Load Sharing Redundant Controller Module

--



ol50nnMRCLSModTable OBJECT-TYPE

	SYNTAX SEQUENCE OF Ol50nnMRCLSModEntry

	ACCESS not-accessible

	STATUS mandatory

	DESCRIPTION

		"A table that contains information about each Redundant

		Controller in the concentrator."

	::= { ol50nnMRCLS 1 }



ol50nnMRCLSModEntry OBJECT-TYPE

	SYNTAX Ol50nnMRCLSModEntry

	ACCESS not-accessible

	STATUS mandatory

	DESCRIPTION

		"A list of information for each Load Sharing Redundant

		 controller module in the concentrator."

	INDEX { ol50nnMRCLSModSlotIndex }

	::= { ol50nnMRCLSModTable 1 }



Ol50nnMRCLSModEntry ::=

	SEQUENCE {

		ol50nnMRCLSModSlotIndex

			INTEGER,

		ol50nnMRCLSModOperState

			INTEGER,

		ol50nnMRCLSModClockStatus

			INTEGER,

		ol50nnMRCLSModTempStatus

			INTEGER

		}



ol50nnMRCLSModSlotIndex OBJECT-TYPE

	SYNTAX INTEGER

	ACCESS read-only

	STATUS mandatory

	DESCRIPTION

		"The slot number for this module."

	::= { ol50nnMRCLSModEntry 1 }



ol50nnMRCLSModOperState OBJECT-TYPE

	SYNTAX INTEGER {

		active(1),

		standby(2)

		}

	ACCESS read-only

	STATUS mandatory

	DESCRIPTION

		"The operational state of the Load Sharing Redudant Controller

		module.  Specifically, this is an indicator of whether the

		Load Sharing Redudant Controller module is providing clock

		signals to the backplane.  An active Load Sharing Redudant

		Controller module provides clock signals to the backplane

		while a standby Load Sharing Redudant Controller module does

		not.  Note that only one Load Sharing Redudant Controller

		module will be active at any given time; all other

		Load Sharing Redudant Controller modules in the concentrator

		will be in standby mode."

	::= { ol50nnMRCLSModEntry 2 }



ol50nnMRCLSModClockStatus OBJECT-TYPE

	SYNTAX INTEGER {

		okay(1),

		faulty(2)

		}

	ACCESS read-only

	STATUS mandatory

	DESCRIPTION

		"The current status of the on-board clocks on this module."

	::= { ol50nnMRCLSModEntry 3 }



ol50nnMRCLSModTempStatus OBJECT-TYPE

	SYNTAX INTEGER {

		okay(1),

		extremeTemp(2)

		}

	ACCESS read-only

	STATUS mandatory

	DESCRIPTION

		"The temperature as detected by the probe on this module."

	::= { ol50nnMRCLSModEntry 4 }





--

-- ONline Ethernet 10BASE-T Security Module (OESM)

--



ol51nnMTPLSModTable OBJECT-TYPE

	SYNTAX SEQUENCE OF Ol51nnMTPLSModEntry

	ACCESS not-accessible

	STATUS mandatory

	DESCRIPTION

		"A list of module-specific information about a specific

		51nnM-TPLS module in the concentrator."

	::= { ol51nnMTPLS 1 }



ol51nnMTPLSModEntry OBJECT-TYPE

	SYNTAX Ol51nnMTPLSModEntry

	ACCESS not-accessible

	STATUS mandatory

	DESCRIPTION

		"A list of module-specific information about a specific

		51nnM-TPLS module in the concentrator."

	INDEX { ol51nnMTPLSModSlotIndex }

	::= { ol51nnMTPLSModTable 1 }



Ol51nnMTPLSModEntry ::=

	SEQUENCE {

		ol51nnMTPLSModSlotIndex

			INTEGER,

		ol51nnMTPLSModDipNetwork

			INTEGER,

		ol51nnMTPLSModAutoPartition

			INTEGER

		}



ol51nnMTPLSModSlotIndex OBJECT-TYPE

	SYNTAX INTEGER

	ACCESS read-only

	STATUS mandatory

	DESCRIPTION

		"The slot number of this module."

	::= { ol51nnMTPLSModEntry 1 }



ol51nnMTPLSModDipNetwork OBJECT-TYPE

	SYNTAX INTEGER {

		isolated(2),

		ethernet-1(6),

		ethernet-2(7),

		ethernet-3(8)

		}

	ACCESS read-only

	STATUS mandatory

	DESCRIPTION

		"The network indicated by the module's dip switches."

	::= { ol51nnMTPLSModEntry 2 }



ol51nnMTPLSModAutoPartition OBJECT-TYPE

	SYNTAX INTEGER {

		collisions-31(1),

		collisions-63(2),

		collisions-127(3),

		collisions-255(4)

		}

	ACCESS read-write

	STATUS mandatory

	DESCRIPTION

		"This object holds the consecutive collision count

		 limit value.  The module goes into the auto-partition

		 mode whenever the consecutive collision count exceeds

		 this limit."

	::= { ol51nnMTPLSModEntry 3 }



ol51nnMTPLSPortTable OBJECT-TYPE

	SYNTAX SEQUENCE OF Ol51nnMTPLSPortEntry

	ACCESS not-accessible

	STATUS mandatory

	DESCRIPTION

		"A table of port-specific information for each port of

		this module type."

	::= { ol51nnMTPLS 2 }



ol51nnMTPLSPortEntry OBJECT-TYPE

	SYNTAX Ol51nnMTPLSPortEntry

	ACCESS not-accessible

	STATUS mandatory

	DESCRIPTION

		"A list of module-specific information about a specific

		51nnM-TPLS port in the concentrator."

	INDEX { ol51nnMTPLSPortSlotIndex, ol51nnMTPLSPortIndex }

	::= { ol51nnMTPLSPortTable 1 }



Ol51nnMTPLSPortEntry ::=

	SEQUENCE {

		ol51nnMTPLSPortSlotIndex

			INTEGER,

		ol51nnMTPLSPortIndex

			INTEGER,

		ol51nnMTPLSPortAdminState

			INTEGER,

		ol51nnMTPLSPortDipAdminState

			INTEGER,

		ol51nnMTPLSPortDipSecurity

			INTEGER,

		ol51nnMTPLSPortBuddySlot

			INTEGER,

		ol51nnMTPLSPortBuddyPort

			INTEGER,

		ol51nnMTPLSPortLinkInteg

			INTEGER,

		ol51nnMTPLSPortDipLinkInteg

			INTEGER

		}



ol51nnMTPLSPortSlotIndex OBJECT-TYPE

	SYNTAX INTEGER

	ACCESS read-only

	STATUS mandatory

	DESCRIPTION

		"The slot number of this port's module."

	::= { ol51nnMTPLSPortEntry 1 }





ol51nnMTPLSPortIndex OBJECT-TYPE

	SYNTAX INTEGER

	ACCESS read-only

	STATUS mandatory

	DESCRIPTION

		"The port number of this port."

	::= { ol51nnMTPLSPortEntry 2 }



ol51nnMTPLSPortAdminState OBJECT-TYPE

	SYNTAX INTEGER {

		enabled(1),

		disabled(2),

		redundant-primary(3),

		redundant-backup(4),

		remote-diagnostics(8)

		}

	ACCESS read-write

	STATUS mandatory

	DESCRIPTION

		"The desired state of this port.  Setting this port to

		be redundant or for remote diagnostics with invalid settings

		of buddy slot and buddy port will return the genError error."

	::= { ol51nnMTPLSPortEntry 3 }



ol51nnMTPLSPortDipAdminState OBJECT-TYPE

	SYNTAX INTEGER {

		enabled(1),

		disabled(2)

		}

	ACCESS read-write

	STATUS mandatory

	DESCRIPTION

		"The admin state of this port as indicated by the dip

		switches.  i.e. This object indicates whether the port

		will initialize to enabled or disabled when the module

		configures itself from dips."

	::= { ol51nnMTPLSPortEntry 4 }



ol51nnMTPLSPortDipSecurity OBJECT-TYPE

	SYNTAX INTEGER {

		enabled(1),

		disabled(2)

		}

	ACCESS read-only

	STATUS mandatory

	DESCRIPTION

		"The security state of this port as indicated by the dip

		switches.  i.e. This object indicates whether the port's

		security state will initialize to enabled (full security)

		or disabled (no security) when the module configures itself

		from dips."

	::= { ol51nnMTPLSPortEntry 5 }



ol51nnMTPLSPortBuddySlot OBJECT-TYPE

	SYNTAX INTEGER

	ACCESS read-write

	STATUS mandatory

	DESCRIPTION

		"The slot index of the redundant port's buddy.  To set

		a port to be redundant, the buddy's slot and port must

		be set to valid values.



		The buddy is automatically set to be redundant to this port.



		If the port is configured for remote diagnostics, then

		this contains the slot index of the backup buddy port.

		To configure a port for remote diagnostics, the buddy's

		slot and port must be set to valid values."

	::= { ol51nnMTPLSPortEntry 6 }



ol51nnMTPLSPortBuddyPort  OBJECT-TYPE

	SYNTAX INTEGER

	ACCESS read-write

	STATUS mandatory

	DESCRIPTION

		"The port index of the redundant port's buddy.  To set

		a port to be redundant, the buddy's slot and port must

		be set to valid values.



		The buddy is automatically set to be redundant to this port.



		If the port is configured for remote diagnostics, then

		this contains the port index of the backup buddy port.

		To configure a port for remote diagnostics, the buddy's

		slot and port must be set to valid values."

	::= { ol51nnMTPLSPortEntry 7 }



ol51nnMTPLSPortLinkInteg OBJECT-TYPE

	SYNTAX INTEGER {

		enabled(1),

		disabled(2)

		}

	ACCESS read-write

	STATUS mandatory

	DESCRIPTION

		"The current link integrity configuration for this port."

	::= { ol51nnMTPLSPortEntry 8 }



ol51nnMTPLSPortDipLinkInteg OBJECT-TYPE

	SYNTAX INTEGER {

		enabled(1),

		disabled(2)

		}

	ACCESS read-only

	STATUS mandatory

	DESCRIPTION

		"The link integrity configuration as indicated by this

		module's dip switches."

	::= { ol51nnMTPLSPortEntry 9 }





--

-- ONcore Ethernet 10BASE-T Per-Port Module

--



oc61nnMTPLPortTable			 OBJECT-TYPE

	SYNTAX SEQUENCE OF Oc61nnMTPLPortEntry

	ACCESS not-accessible

	STATUS mandatory

	DESCRIPTION

		"A table of port-specific information for each port of

		this module type."

	::= { oc61nnMTPL 2 }



oc61nnMTPLPortEntry OBJECT-TYPE

	SYNTAX Oc61nnMTPLPortEntry

	ACCESS not-accessible

	STATUS mandatory

	DESCRIPTION

		"A list of module-specific information about a specific

		61nnM-TPL port in the concentrator."

	INDEX { oc61nnMTPLPortSlotIndex, oc61nnMTPLPortIndex }

	::= { oc61nnMTPLPortTable 1 }



Oc61nnMTPLPortEntry ::=

	SEQUENCE {

		oc61nnMTPLPortSlotIndex

			INTEGER,

		oc61nnMTPLPortIndex

			INTEGER,

		oc61nnMTPLPortAdminState

			INTEGER,

		oc61nnMTPLPortBuddySlot

			INTEGER,

		oc61nnMTPLPortBuddyPort

			INTEGER,

		oc61nnMTPLPortDipNetwork

			INTEGER,

		oc61nnMTPLPortLinkInteg

			INTEGER,

		oc61nnMTPLPortAutoPolarity

			INTEGER

		}



oc61nnMTPLPortSlotIndex OBJECT-TYPE

	 SYNTAX INTEGER

	 ACCESS read-only

	 STATUS mandatory

	 DESCRIPTION

		 "The slot number of this port's module."

	 ::= { oc61nnMTPLPortEntry 1 }





oc61nnMTPLPortIndex OBJECT-TYPE

	 SYNTAX INTEGER

	 ACCESS read-only

	 STATUS mandatory

	 DESCRIPTION

		 "The port number of this port."

	 ::= { oc61nnMTPLPortEntry 2 }



oc61nnMTPLPortAdminState OBJECT-TYPE

	 SYNTAX INTEGER {

		 enabled(1),

		 disabled(2),

		 redundant-primary(3),

		 redundant-backup(4),

		 remote-diagnostics(8)

		 }

	 ACCESS read-write

	 STATUS mandatory

	 DESCRIPTION

		 "The desired state of this port.  Setting this port to

		 be redundant or for remote diagnostics with invalid settings

		 of buddy slot and buddy port will return the genError error."

	 ::= { oc61nnMTPLPortEntry 3 }



oc61nnMTPLPortBuddySlot OBJECT-TYPE

	 SYNTAX INTEGER

	 ACCESS read-write

	 STATUS mandatory

	 DESCRIPTION

		 "The slot index of the redundant port's buddy.  To set

		 a port to be redundant, the buddy's slot and port must

		 be set to valid values.



		 The buddy is automatically set to be redundant to this port.



		 If the port is configured for remote diagnostics, then

		 this contains the slot index of the backup buddy port.

		 To configure a port for remote diagnostics, the buddy's

		 slot and port must be set to valid values."



	 ::= { oc61nnMTPLPortEntry 4 }



oc61nnMTPLPortBuddyPort  OBJECT-TYPE

	 SYNTAX INTEGER

	 ACCESS read-write

	 STATUS mandatory

	 DESCRIPTION

		 "The port index of the redundant port's buddy.  To set

		 a port to be redundant, the buddy's slot and port must

		 be set to valid values.



		 The buddy is automatically set to be redundant to this port.



		 If the port is configured for remote diagnostics, then

		 this contains the port index of the backup buddy port.

		 To configure a port for remote diagnostics, the buddy's

		 slot and port must be set to valid values."

	 ::= { oc61nnMTPLPortEntry 5 }



oc61nnMTPLPortDipNetwork OBJECT-TYPE

	 SYNTAX INTEGER {

		 ethernet-1(6),

		 ethernet-2(7),

		 ethernet-3(8),

		 isolated-1(21),

		 ethernet-4(32),	-- ONcore networks : --

		 ethernet-5(33),

		 ethernet-6(34),

		 ethernet-7(35),

		 ethernet-8(36)

		 }

	 ACCESS read-only

	 STATUS mandatory

	 DESCRIPTION

		 "The network indicated by the port's dip switches."

	 ::= { oc61nnMTPLPortEntry 6 }



oc61nnMTPLPortLinkInteg OBJECT-TYPE

	 SYNTAX INTEGER {

		 enabled(1),

		 disabled(2)

		 }

	 ACCESS read-write

	 STATUS mandatory

	 DESCRIPTION

		 "The current link integrity configuration for this

		  port.  Setting this object to enabled(1) makes it

		  conform to the 10BASE-T link integrity standard.

		  Setting this object to disabled(2) makes it compatible

		  with the older pre 10BASE-T module."

	 ::= { oc61nnMTPLPortEntry 7 }



oc61nnMTPLPortAutoPolarity OBJECT-TYPE

	 SYNTAX INTEGER {

		 enabled(1),

		 disabled(2)

		 }

	 ACCESS read-write

	 STATUS mandatory

	 DESCRIPTION

		 "The current auto polarity configuration for this port.

		  Setting this object to enabled(1) causes the module to

		  switch the port polarity automatically when the port

		  polarity is reverted."

	 ::= { oc61nnMTPLPortEntry 8 }





oc61nnMTPLModTable OBJECT-TYPE

	SYNTAX SEQUENCE OF Oc61nnMTPLModEntry

	ACCESS not-accessible

	STATUS mandatory

	DESCRIPTION

		"A list of module-specific information about a specific

		61nnM-TPL module in the concentrator."

	::= { oc61nnMTPL 6 }



oc61nnMTPLModEntry OBJECT-TYPE

	SYNTAX Oc61nnMTPLModEntry

	ACCESS not-accessible

	STATUS mandatory

	DESCRIPTION

		"A list of module-specific information about a specific

		61nnM-TPL module in the concentrator."

	INDEX { oc61nnMTPLModSlotIndex, oc61nnMTPLModSubSlotIndex }

	::= { oc61nnMTPLModTable 1 }



Oc61nnMTPLModEntry ::=

	SEQUENCE {

		oc61nnMTPLModSlotIndex

			INTEGER,

		oc61nnMTPLModSubSlotIndex

			INTEGER,

		oc61nnMTPLModBootVersion

			DisplayString,

		oc61nnMTPLModDipNVRam

			INTEGER

		}



oc61nnMTPLModSlotIndex OBJECT-TYPE

	SYNTAX INTEGER

	ACCESS read-only

	STATUS mandatory

	DESCRIPTION

		"The slot number of this module."

	::= { oc61nnMTPLModEntry 1 }



oc61nnMTPLModSubSlotIndex OBJECT-TYPE

	SYNTAX INTEGER

	ACCESS read-only

	STATUS mandatory

	DESCRIPTION

		"The subslot number of this module."

	::= { oc61nnMTPLModEntry 2 }



oc61nnMTPLModBootVersion OBJECT-TYPE

	SYNTAX DisplayString (SIZE(1..32))

	ACCESS read-only

	STATUS mandatory

	DESCRIPTION

		"The software boot eprom version of this module.  "

	::= { oc61nnMTPLModEntry 3 }



oc61nnMTPLModDipNVRam OBJECT-TYPE

	SYNTAX INTEGER {

	enabled(1),

	disabled(2)

	}

	ACCESS read-only

	STATUS mandatory

	DESCRIPTION

		"The Non-Volatile RAM dip switch setting for this

		 module.  Enabling this switch will cause the module

		 to be configured according to the configurations that

		 were saved in the non-volatile storage after the

		 module reset."

	::= { oc61nnMTPLModEntry 4 }





--

-- ONcore Ethernet Carrier Module

--

oc61nnMCARModTable OBJECT-TYPE

	SYNTAX SEQUENCE OF Oc61nnMCARModEntry

	ACCESS not-accessible

	STATUS mandatory

	DESCRIPTION

		"A list of module-specific information associated

		with a particular 61nnM-CAR module in the concentrator."

	::= { oc61nnMCAR 6 }



oc61nnMCARModEntry OBJECT-TYPE

	SYNTAX Oc61nnMCARModEntry

	ACCESS not-accessible

	STATUS mandatory

	DESCRIPTION

		"A list of module-specific information about a specific

		61nnM-CAR module in the concentrator."

	INDEX { oc61nnMCARModSlotIndex, oc61nnMCARModSubSlotIndex }

	::= { oc61nnMCARModTable 1 }



Oc61nnMCARModEntry ::=

	SEQUENCE {

		oc61nnMCARModSlotIndex

			INTEGER,

		oc61nnMCARModSubSlotIndex

			INTEGER,

		oc61nnMCARModBootVersion

			DisplayString

		}



oc61nnMCARModSlotIndex OBJECT-TYPE

	SYNTAX INTEGER

	ACCESS read-only

	STATUS mandatory

	DESCRIPTION

		"The slot number of this module."

	::= { oc61nnMCARModEntry 1 }



oc61nnMCARModSubSlotIndex OBJECT-TYPE

	SYNTAX INTEGER

	ACCESS read-only

	STATUS mandatory

	DESCRIPTION

		"The subslot number of this module."

	::= { oc61nnMCARModEntry 2 }



oc61nnMCARModBootVersion OBJECT-TYPE

	SYNTAX DisplayString (SIZE(1..32))

	ACCESS read-only

	STATUS mandatory

	DESCRIPTION

		"The software boot eprom version of this module.  "

	::= { oc61nnMCARModEntry 3 }





--

-- ONcore Ethernet 10BASE-FB 10-PORT Per-Port switchable Module

--

--

-- Port Table

--

oc61nnMFBPPortTable OBJECT-TYPE

	SYNTAX SEQUENCE OF Oc61nnMFBPPortEntry

	ACCESS not-accessible

	STATUS mandatory

	DESCRIPTION

		"A table of port-specific information for each port of

		 this module type."

	::= { oc61nnMFBP 2 }



oc61nnMFBPPortEntry OBJECT-TYPE

	SYNTAX Oc61nnMFBPPortEntry

	ACCESS not-accessible

	STATUS mandatory

	DESCRIPTION

		"A list of port specific information about this

		 module's ports."

	INDEX { oc61nnMFBPPortSlotIndex, oc61nnMFBPPortIndex }

	::= { oc61nnMFBPPortTable 1 }



Oc61nnMFBPPortEntry ::=

	SEQUENCE {

		oc61nnMFBPPortSlotIndex

			INTEGER,

		oc61nnMFBPPortIndex

			INTEGER,

		oc61nnMFBPPortAdminState

			INTEGER,

		oc61nnMFBPPortBuddySlot

			INTEGER,

		oc61nnMFBPPortBuddyPort

			INTEGER,

		oc61nnMFBPPortDipNetwork

			INTEGER,

		oc61nnMFBPPortHipwr

			INTEGER

		}



oc61nnMFBPPortSlotIndex OBJECT-TYPE

	SYNTAX INTEGER

	ACCESS read-only

	STATUS mandatory

	DESCRIPTION

		"The slot number of the module assocaited with this port."

	::= { oc61nnMFBPPortEntry 1 }



oc61nnMFBPPortIndex OBJECT-TYPE

	SYNTAX INTEGER

	ACCESS read-only

	STATUS mandatory

	DESCRIPTION

		"The port number with respect to the module it resides on."

	::= { oc61nnMFBPPortEntry 2 }



oc61nnMFBPPortAdminState OBJECT-TYPE

	SYNTAX INTEGER {

		enabled(1),

		disabled(2),

		redundant-primary(3),

		redundant-backup(4)

		}

	ACCESS read-write

	STATUS mandatory

	DESCRIPTION

		"The desired state of this port.  Setting this port to

		 redundant-primary or redundant-backup with invalid buddy

		 slot or buddy port will result in an error."

	::= { oc61nnMFBPPortEntry 3 }



oc61nnMFBPPortBuddySlot OBJECT-TYPE

	SYNTAX INTEGER

	ACCESS read-write

	STATUS mandatory

	DESCRIPTION

		"The slot index of the redundant port's buddy port."

	::= { oc61nnMFBPPortEntry 4 }



oc61nnMFBPPortBuddyPort  OBJECT-TYPE

	SYNTAX INTEGER

	ACCESS read-write

	STATUS mandatory

	DESCRIPTION

		"The port index of the redundant port's buddy. Valid ports

		 are those ports which are not redundant. The buddy port

		 admin state will be set to redundant."

	::= { oc61nnMFBPPortEntry 5 }



oc61nnMFBPPortDipNetwork OBJECT-TYPE

	SYNTAX INTEGER {

		ethernet-1(6),

		ethernet-2(7),

		ethernet-3(8),

		isolated-1(21),

		ethernet-4(32),

		ethernet-5(33),

		ethernet-6(34),

		ethernet-7(35),

		ethernet-8(36)

		}

	ACCESS read-only

	STATUS mandatory

	DESCRIPTION

		"The network indicated by the port's dip switches."

	::= { oc61nnMFBPPortEntry 6 }



oc61nnMFBPPortHipwr OBJECT-TYPE

	SYNTAX INTEGER {

		enable(1),

		disable(2)

		}

	ACCESS read-write

	STATUS mandatory

	DESCRIPTION

		"The current port high power optics mode. Setting

		 this variable to enable(1), will enable the port

		 to drive up to 4K meter fiber cable."

	::= { oc61nnMFBPPortEntry 7 }



--

-- module specific table

--

oc61nnMFBPModTable OBJECT-TYPE

	SYNTAX SEQUENCE OF Oc61nnMFBPModEntry

	ACCESS not-accessible

	STATUS mandatory

	DESCRIPTION

		"A list of module specific information about this module."

	::= { oc61nnMFBP 6 }



oc61nnMFBPModEntry OBJECT-TYPE

	SYNTAX Oc61nnMFBPModEntry

	ACCESS not-accessible

	STATUS mandatory

	DESCRIPTION

		"Values to describe module specific inormation."

	INDEX { oc61nnMFBPModSlotIndex, oc61nnMFBPModSubSlotIndex }

	::= { oc61nnMFBPModTable 1 }



Oc61nnMFBPModEntry ::=

	SEQUENCE {

		oc61nnMFBPModSlotIndex

			INTEGER,

		oc61nnMFBPModSubSlotIndex

			INTEGER,

		oc61nnMFBPModBootVersion

			DisplayString,

		oc61nnMFBPModDipNVRam

			INTEGER

		}



oc61nnMFBPModSlotIndex OBJECT-TYPE

	SYNTAX INTEGER

	ACCESS read-only

	STATUS mandatory

	DESCRIPTION

		"The slot index of this module."

	::= { oc61nnMFBPModEntry 1 }



oc61nnMFBPModSubSlotIndex OBJECT-TYPE

	SYNTAX INTEGER

	ACCESS read-only

	STATUS mandatory

	DESCRIPTION

		"The subslot index of this module. (e.g. mother boards

		 have subslot index equals to one."

	::= { oc61nnMFBPModEntry 2 }



oc61nnMFBPModBootVersion OBJECT-TYPE

	SYNTAX DisplayString (SIZE(1..32))

	ACCESS read-only

	STATUS mandatory

	DESCRIPTION

		"The software boot eprom version of this module.  "

	::= { oc61nnMFBPModEntry 3 }



oc61nnMFBPModDipNVRam OBJECT-TYPE

	SYNTAX INTEGER {

		enabled(1),

		disabled(2)

		}

	ACCESS read-only

	STATUS mandatory

	DESCRIPTION

		"The Non-Volatile RAM dip switch setting for this

		 module. Setting this object to enable(1) will cause

		 the module to be configured according to the

		 configuration which was saved in the non-volatile

		 storage."

	::= { oc61nnMFBPModEntry 4 }





--

-- ONcore Redundant Controller Module managed by ONline agent.

--



ol60nnMRCTLModTable OBJECT-TYPE

	SYNTAX SEQUENCE OF Ol60nnMRCTLModEntry

	ACCESS not-accessible

	STATUS mandatory

	DESCRIPTION

		"A table that contains information about the Controller

		in the concentrator."

	::= { oc60nnMRCTL 1 }



ol60nnMRCTLModEntry OBJECT-TYPE

	SYNTAX Ol60nnMRCTLModEntry

	ACCESS not-accessible

	STATUS mandatory

	DESCRIPTION

		"A list of information for the Controller module

		in the concentrator."

	INDEX { ol60nnMRCTLModSlotIndex }

	::= { ol60nnMRCTLModTable 1 }



Ol60nnMRCTLModEntry ::=

	SEQUENCE {

		ol60nnMRCTLModSlotIndex

			INTEGER,

		ol60nnMRCTLModOperState

			INTEGER,

		ol60nnMRCTLModClockStatus

			INTEGER,

		ol60nnMRCTLModTempStatus

			INTEGER

		}



ol60nnMRCTLModSlotIndex OBJECT-TYPE

	SYNTAX INTEGER

	ACCESS read-only

	STATUS mandatory

	DESCRIPTION

		"The slot number for this module.  Note that this module will

		 always be in slot 17."

	::= { ol60nnMRCTLModEntry 1 }



ol60nnMRCTLModOperState OBJECT-TYPE

	SYNTAX INTEGER {

		active(1),

		standby(2)

		}

	ACCESS read-only

	STATUS mandatory

	DESCRIPTION

		"The operational state of the Controller module.  Specifically,

		this is an indicator of whether the Controller module is

		providing clock signals to the backplane.  An active Controller

		module provides clock signals to the backplane while a standby

		Controller module does not.  Note that only the active

		Controller is visible to an ONline agent; hence, this object

		will have the value active(1)."

	::= { ol60nnMRCTLModEntry 2 }



ol60nnMRCTLModClockStatus OBJECT-TYPE

	SYNTAX INTEGER {

		okay(1),

		faulty(2)

		}

	ACCESS read-only

	STATUS mandatory

	DESCRIPTION

		"The current status of the on-board clocks on this module."

	::= { ol60nnMRCTLModEntry 3 }



ol60nnMRCTLModTempStatus OBJECT-TYPE

	SYNTAX INTEGER {

		okay(1),

		extremeTemp(2)

		}

	ACCESS read-only

	STATUS mandatory

	DESCRIPTION

		"The overall temperature status for this concentrator as

		detected by this module.  This object's value is an aggregate

		of all temperature probes located within this concentrator as

		sensed by this module.  Hence, when at least one probe in

		the concentrator reports an extreme temperature, then this

		object will have the value extremeTemp(2)."

	::= { ol60nnMRCTLModEntry 4 }



--

-- ONcore Redundant Controller Module managed by ONcore agent

--



oc60nnMRCTLModTable OBJECT-TYPE

	SYNTAX SEQUENCE OF Oc60nnMRCTLModEntry

	ACCESS not-accessible

	STATUS mandatory

	DESCRIPTION

		"A table that contains information about the Controller

		in the concentrator."

	::= { oc60nnMRCTL 6 }



oc60nnMRCTLModEntry OBJECT-TYPE

	SYNTAX Oc60nnMRCTLModEntry

	ACCESS not-accessible

	STATUS mandatory

	DESCRIPTION

		"A list of information for the Controller module

		in the concentrator."

	INDEX { oc60nnMRCTLModSlotIndex, oc60nnMRCTLModSubSlotIndex }

	::= { oc60nnMRCTLModTable 1 }



Oc60nnMRCTLModEntry ::=

	SEQUENCE {

		oc60nnMRCTLModSlotIndex

			INTEGER,

		oc60nnMRCTLModSubSlotIndex

			INTEGER,

		oc60nnMRCTLModBootVersion

			DisplayString,

		oc60nnMRCTLModOperState

			INTEGER,

		oc60nnMRCTLModClockStatus

			INTEGER,

		oc60nnMRCTLModTempStatus

			INTEGER,

		oc60nnMRCTLModAtoDConverterStatus

			INTEGER,

		oc60nnMRCTLModPS1Status

			INTEGER,

		oc60nnMRCTLModPS2Status

			INTEGER,

		oc60nnMRCTLModPS3Status

			INTEGER,

		oc60nnMRCTLModPS4Status

			INTEGER

		}



oc60nnMRCTLModSlotIndex OBJECT-TYPE

	SYNTAX INTEGER

	ACCESS read-only

	STATUS mandatory

	DESCRIPTION

		"The slot number for this module."

	::= { oc60nnMRCTLModEntry 1 }



oc60nnMRCTLModSubSlotIndex OBJECT-TYPE

	SYNTAX INTEGER

	ACCESS read-only

	STATUS mandatory

	DESCRIPTION

		"The subslot number for this module."

	::= { oc60nnMRCTLModEntry 2 }



oc60nnMRCTLModBootVersion OBJECT-TYPE

	SYNTAX DisplayString (SIZE(1..32))

	ACCESS read-only

	STATUS mandatory

	DESCRIPTION

		"The software boot eprom version of this module.  "

	::= { oc60nnMRCTLModEntry 3 }



oc60nnMRCTLModOperState OBJECT-TYPE

	SYNTAX INTEGER {

		active(1),

		standby(2)

		}

	ACCESS read-only

	STATUS mandatory

	DESCRIPTION

		"The operational state of the Controller module.

		Specifically, this is an indicator of whether the Controller

		module is providing clock signals to the backplane.  An

		active Controller module provides clock signals to the

		backplane while a standby Controller module does not."

	::= { oc60nnMRCTLModEntry 4 }



oc60nnMRCTLModClockStatus OBJECT-TYPE

	SYNTAX INTEGER {

		okay(1),

		faulty(2)

		}

	ACCESS read-only

	STATUS mandatory

	DESCRIPTION

		"The current status of the on-board clocks on this module."

	::= { oc60nnMRCTLModEntry 5 }



oc60nnMRCTLModTempStatus OBJECT-TYPE

	SYNTAX INTEGER {

		okay(1),

		extremeTemp(2)

		}

	ACCESS read-only

	STATUS mandatory

	DESCRIPTION

		"The overall temperature status for the concentrator as

		detected by this module.  This object's value is an aggregate

		of all the temperature probes located within this

		concentrator as sensed by this module.  Hence, when at least

		one probe in the concentrator reports an extreme temperature,

		then this object will have the value extremeTemp(2)."

	::= { oc60nnMRCTLModEntry 6 }



oc60nnMRCTLModAtoDConverterStatus OBJECT-TYPE

	SYNTAX INTEGER {

		okay(1),

		faulty(2)

		}

	ACCESS read-only

	STATUS mandatory

	DESCRIPTION

		"The current status of the on-board A/D converter.

		Typically, when this object has a value of faulty(2), it

		is because the value obtained from the A/D converter internal

		test channel is out of tolerance from what is specified by

		the manufacturer."

	::= { oc60nnMRCTLModEntry 7 }



oc60nnMRCTLModPS1Status OBJECT-TYPE

	SYNTAX INTEGER {

		active(1),

		faulty(3),

		not-installed(4)

		}

	ACCESS read-only

	STATUS mandatory

	DESCRIPTION

		"The current status of powersupply 1."

	::= { oc60nnMRCTLModEntry 8 }



oc60nnMRCTLModPS2Status OBJECT-TYPE

	SYNTAX INTEGER {

		active(1),

		faulty(3),

		not-installed(4)

		}

	ACCESS read-only

	STATUS mandatory

	DESCRIPTION

		"The current status of powersupply 2."

	::= { oc60nnMRCTLModEntry 9 }



oc60nnMRCTLModPS3Status OBJECT-TYPE

	SYNTAX INTEGER {

		active(1),

		faulty(3),

		not-installed(4)

		}

	ACCESS read-only

	STATUS mandatory

	DESCRIPTION

		"The current status of powersupply 3."

	::= { oc60nnMRCTLModEntry 10 }



oc60nnMRCTLModPS4Status OBJECT-TYPE

	SYNTAX INTEGER {

		active(1),

		faulty(3),

		not-installed(4)

		}

	ACCESS read-only

	STATUS mandatory

	DESCRIPTION

		"The current status of powersupply 4."

	::= { oc60nnMRCTLModEntry 11 }





--

-- ONcore Ethernet Network Monitor Card

--



oc61nnDMGTModTable OBJECT-TYPE

	SYNTAX SEQUENCE OF Oc61nnDMGTModEntry

	ACCESS not-accessible

	STATUS mandatory

	DESCRIPTION

		"A table that contains information about Ethernet

		Network Monitor Cards in the ONcore Hub.  "

	::= { oc61nnDMGT 6 }



oc61nnDMGTModEntry OBJECT-TYPE

	SYNTAX Oc61nnDMGTModEntry

	ACCESS not-accessible

	STATUS mandatory

	DESCRIPTION

		"A list of information for an Ethernet Network Monitor

		 Card in the ONcore Hub."

	INDEX { oc61nnDMGTModSlotIndex, oc61nnDMGTModSubSlotIndex}

	::= { oc61nnDMGTModTable 1 }



Oc61nnDMGTModEntry ::=

	SEQUENCE {

		oc61nnDMGTModSlotIndex

			INTEGER,

		oc61nnDMGTModSubSlotIndex

			INTEGER,

		oc61nnDMGTModBootVersion

			DisplayString,

		oc61nnDMGTModIpAddress

			IpAddress,

		oc61nnDMGTModSubnetMask

			IpAddress,

		oc61nnDMGTModDefaultGateway

			IpAddress,

		oc61nnDMGTModStationAddr

			MacAddress,

		oc61nnDMGTModInterfaceMode

			INTEGER,

		oc61nnDMGTModRMONHostStatsMode

			INTEGER



	}





oc61nnDMGTModSlotIndex OBJECT-TYPE

	SYNTAX INTEGER

	ACCESS read-only

	STATUS mandatory

	DESCRIPTION

		"The slot number of this card."

	::= { oc61nnDMGTModEntry 1 }



oc61nnDMGTModSubSlotIndex OBJECT-TYPE

	SYNTAX INTEGER

	ACCESS read-only

	STATUS mandatory

	DESCRIPTION

		"The subslot number of this card."

	::= { oc61nnDMGTModEntry 2 }



oc61nnDMGTModBootVersion OBJECT-TYPE

	SYNTAX DisplayString (SIZE(1..32))

	ACCESS read-only

	STATUS mandatory

	DESCRIPTION

		"The software boot eprom version of this module.  "

	::= { oc61nnDMGTModEntry 3 }



oc61nnDMGTModIpAddress OBJECT-TYPE

	SYNTAX IpAddress

	ACCESS read-only

	STATUS mandatory

	DESCRIPTION

		"The current IP address of this card and the associated interface."

	::= { oc61nnDMGTModEntry 4 }





oc61nnDMGTModSubnetMask OBJECT-TYPE

	SYNTAX IpAddress

	ACCESS read-only

	STATUS mandatory

	DESCRIPTION

		"The current subnet mask of this card and the associated interface."

	::= { oc61nnDMGTModEntry 5 }





oc61nnDMGTModDefaultGateway OBJECT-TYPE

	SYNTAX IpAddress

	ACCESS read-only

	STATUS mandatory

	DESCRIPTION

		"The current default gateway of this card and the associated interface.

		 Note that a value of 0.0.0.0 indicates that this interface is not con-

		 configured to be used with a default gateway."

	::= { oc61nnDMGTModEntry 6 }



oc61nnDMGTModStationAddr OBJECT-TYPE

	SYNTAX MacAddress

	ACCESS read-only

	STATUS mandatory

	DESCRIPTION

		"A 6 octet address that uniquely identifies this card.

		Note that an address of 00-00-00-00-00-00 is invalid

		and the module has failed."

	::= { oc61nnDMGTModEntry 7 }



oc61nnDMGTModInterfaceMode OBJECT-TYPE

	SYNTAX INTEGER {

		enabled(1),

		disabled(2),

		standby(3)

		}

	ACCESS read-write

	STATUS mandatory

	DESCRIPTION

		"The desired connectvity mode of this card.  When this

		 attribute is set to enabled(1) and the card is set to a

		 network, it will forward  messages to and from the master

		 Distributed Management Module.  If this attribute is set

		 to disabled(2), the card may still collect statistics but not

		 forward messages to and from the Distributed Management Module.

		 If this attribute is set to standby(3), the card will not collect

		 statistics or forward messages to/from the Distributed Management

		 Module."

	::= { oc61nnDMGTModEntry 8 }



oc61nnDMGTModRMONHostStatsMode  OBJECT-TYPE

       SYNTAX INTEGER {

	       enabled(1),

	       disabled(2)

	       }

	ACCESS read-write

	STATUS mandatory

	DESCRIPTION

		"The desired RMON host staticstics mode of this card.

		 When this attribute is set to enabled, the card will

		 gather RMON host table statistics.  Note that when this

		 attribute is enabled, the accuracy of all statistics

		 may be impaired during peak loads."

	::= { oc61nnDMGTModEntry 9 }





--

-- ONcore Distribute Management Module

--



oc60nnMMGTModTable OBJECT-TYPE

	SYNTAX SEQUENCE OF Oc60nnMMGTModEntry

	ACCESS not-accessible

	STATUS mandatory

	DESCRIPTION

		"A table that contains module information about each

		60nnM-MGT module in the concentrator."

	::= { oc60nnMMGT 6 }



oc60nnMMGTModEntry OBJECT-TYPE

	SYNTAX Oc60nnMMGTModEntry

	ACCESS not-accessible

	STATUS mandatory

	DESCRIPTION

		"A list of module information for each 60nnM-MGT module

		in the concentrator."

	INDEX { oc60nnMMGTModSlotIndex, oc60nnMMGTModSubSlotIndex }

	::= { oc60nnMMGTModTable 1 }



Oc60nnMMGTModEntry ::=

	SEQUENCE {

		oc60nnMMGTModSlotIndex

			INTEGER,

		oc60nnMMGTModSubSlotIndex

			INTEGER,

		oc60nnMMGTModBootVersion

			DisplayString,

		oc60nnMMGTModMasterPriority

			INTEGER,

		oc60nnMMGTModMasterStatus

			INTEGER,

		oc60nnMMGTModHubSerial

			DisplayString

	}



oc60nnMMGTModSlotIndex OBJECT-TYPE

	SYNTAX INTEGER

	ACCESS read-only

	STATUS mandatory

	DESCRIPTION

		"The slot number of this module."

	::= { oc60nnMMGTModEntry 1 }



oc60nnMMGTModSubSlotIndex OBJECT-TYPE

	SYNTAX INTEGER

	ACCESS read-only

	STATUS mandatory

	DESCRIPTION

		"The subslot number of this module."

	::= { oc60nnMMGTModEntry 2 }



oc60nnMMGTModBootVersion OBJECT-TYPE

	SYNTAX DisplayString (SIZE(1..32))

	ACCESS read-only

	STATUS mandatory

	DESCRIPTION

		"The software boot eprom version of this module.  "

	::= { oc60nnMMGTModEntry 3 }



oc60nnMMGTModMasterPriority OBJECT-TYPE

	SYNTAX INTEGER {

		one(1),

		two(2),

		three(3),

		four(4),

		five(5),

		six(6),

		seven(7),

		eight(8),

		nine(9),

		ten(10)

		}

	ACCESS read-write

	STATUS mandatory

	DESCRIPTION

		"The mastership priority of this agent.  Ten is the

		highest and one is the lowest.  Priority is

		only used when an election occurs.  Mastership is not

		preemptive unless the reset mastership command is used."

	::= { oc60nnMMGTModEntry 4 }



oc60nnMMGTModMasterStatus OBJECT-TYPE

	SYNTAX INTEGER {

		master(1),

		non-master(2),

		electing(3)

		}

	ACCESS read-only

	STATUS mandatory

	DESCRIPTION

		"The mastership status of this agent."

	::= { oc60nnMMGTModEntry 5 }



oc60nnMMGTModHubSerial OBJECT-TYPE

	SYNTAX DisplayString

	ACCESS read-only

	STATUS mandatory

	DESCRIPTION

		"The Hub serial number mastership is presiding over.

		 Zero length string for slaves."

	::= { oc60nnMMGTModEntry 6 }





--

-- ONline Token Ring Establishment Controller Module

--



ol52nnMECModTable OBJECT-TYPE

	SYNTAX SEQUENCE OF Ol52nnMECModEntry

	ACCESS not-accessible

	STATUS mandatory

	DESCRIPTION

		"A list of module-specific information associated

		with a particular 52nnM-EC module in the concentrator."

	::= { ol52nnMEC 1 }



ol52nnMECModEntry OBJECT-TYPE

	SYNTAX Ol52nnMECModEntry

	ACCESS not-accessible

	STATUS mandatory

	DESCRIPTION

		"A description of the 52nnM-EC module attributes."

	INDEX { ol52nnMECModSlotIndex }

	::= { ol52nnMECModTable 1 }



Ol52nnMECModEntry ::=

	SEQUENCE {

		ol52nnMECModSlotIndex

			INTEGER,

		ol52nnMECModSoftwareVersion

			DisplayString,

		ol52nnMECModSystemStatusCode

			DisplayString,

		ol52nnMECModRingSpeed

			INTEGER,

		ol52nnMECModNetworkStatus

			INTEGER,

		ol52nnMECModIpAddress

			IpAddress,

		ol52nnMECModMACStationAddr

			OCTET STRING

	}



ol52nnMECModSlotIndex OBJECT-TYPE

	SYNTAX INTEGER

	ACCESS read-only

	STATUS mandatory

	DESCRIPTION

		"The slot number of this module."

	::= { ol52nnMECModEntry 1 }





ol52nnMECModSoftwareVersion OBJECT-TYPE

       SYNTAX DisplayString (SIZE(1..10))

       ACCESS read-only

       STATUS mandatory

       DESCRIPTION

	       "The version number of the software."

       ::= { ol52nnMECModEntry 2 }



ol52nnMECModSystemStatusCode OBJECT-TYPE

	SYNTAX DisplayString (SIZE(43))

	ACCESS read-only

	STATUS mandatory

	DESCRIPTION

		"A 43 octet indication of the current applicable

		IBM 3174 System Status Code. For more information

		consult the 52nnM-EC reference manual."

	::= { ol52nnMECModEntry 3 }



ol52nnMECModRingSpeed OBJECT-TYPE

	SYNTAX INTEGER {

	     fourMegabit(1),

	     sixteenMegabit(2)

	     }

	ACCESS read-write

	STATUS mandatory

	DESCRIPTION

		"The ring's bandwidth in Mega-bits per second."

	::= { ol52nnMECModEntry 4 }



ol52nnMECModNetworkStatus OBJECT-TYPE

	SYNTAX INTEGER {

	     okay(1),

	     closed(2),

	     beaconing(3)

	     }

	ACCESS read-only

	STATUS mandatory

	DESCRIPTION

		"The status of the ring containing this module."

	::= {ol52nnMECModEntry 5}



ol52nnMECModIpAddress OBJECT-TYPE

       SYNTAX IpAddress

       ACCESS read-only

       STATUS mandatory

       DESCRIPTION

	       "The IP Address of this module."

       ::= { ol52nnMECModEntry 6 }



ol52nnMECModMACStationAddr OBJECT-TYPE

	SYNTAX OCTET STRING

	ACCESS read-only

	STATUS mandatory

	DESCRIPTION

		"A 6 octet address that uniquely identifies the MAC

		address of this module."

	::= { ol52nnMECModEntry 7 }



ol52nnMECPortTable OBJECT-TYPE

	SYNTAX SEQUENCE OF Ol52nnMECPortEntry

	ACCESS not-accessible

	STATUS mandatory

	DESCRIPTION

		"A table of port-specific information for each port of

		this module type."

	::= { ol52nnMEC 2 }



ol52nnMECPortEntry OBJECT-TYPE

	SYNTAX Ol52nnMECPortEntry

	ACCESS not-accessible

	STATUS mandatory

	DESCRIPTION

		"A description of this module's port attributes."

	INDEX { ol52nnMECPortSlotIndex, ol52nnMECPortIndex }

	::= { ol52nnMECPortTable 1 }



Ol52nnMECPortEntry ::=

	SEQUENCE {

		ol52nnMECPortSlotIndex

			INTEGER,

		ol52nnMECPortIndex

			INTEGER

	}



ol52nnMECPortSlotIndex OBJECT-TYPE

	SYNTAX INTEGER

	ACCESS read-only

	STATUS mandatory

	DESCRIPTION

		"The slot number of this port's module."

	::= { ol52nnMECPortEntry 1 }





ol52nnMECPortIndex OBJECT-TYPE

	SYNTAX INTEGER

	ACCESS read-only

	STATUS mandatory

	DESCRIPTION

		"The port number of this port."

	::= { ol52nnMECPortEntry 2 }



ol52nnMECTrunkTable OBJECT-TYPE

	SYNTAX SEQUENCE OF Ol52nnMECTrunkEntry

	ACCESS not-accessible

	STATUS mandatory

	DESCRIPTION

		"A list of trunk-specific information about each trunk

		for this module type."

	::= { ol52nnMEC 3 }



ol52nnMECTrunkEntry OBJECT-TYPE

	SYNTAX Ol52nnMECTrunkEntry

	ACCESS not-accessible

	STATUS mandatory

	DESCRIPTION

		"A description of 52nnM-EC trunk attributes."

	INDEX { ol52nnMECTrunkSlotIndex, ol52nnMECTrunkIndex }

	::= { ol52nnMECTrunkTable 1 }



Ol52nnMECTrunkEntry ::=

	SEQUENCE {

		ol52nnMECTrunkSlotIndex

			INTEGER,

		ol52nnMECTrunkIndex

			INTEGER

	}



ol52nnMECTrunkSlotIndex OBJECT-TYPE

	SYNTAX INTEGER

	ACCESS read-only

	STATUS mandatory

	DESCRIPTION

		"A unique value that identifies a particular module.  Its

		value ranges between 1 and olModSlotNumber.  The module

		identified by a particular value of this index is the same

		module as indentified by the same value of

		olTrunkSlotIndex."

	::= { ol52nnMECTrunkEntry 1 }





ol52nnMECTrunkIndex OBJECT-TYPE

	SYNTAX INTEGER

	ACCESS read-only

	STATUS mandatory

	DESCRIPTION

		"The trunk number for this trunk."

	::= { ol52nnMECTrunkEntry 2 }





--

-- Value Added Tables for the Ethernet Work Group Hub

--

-- Module Table (41nnH-MTP and 41nnH-MTP-FL)



ol41nnHMTPModTable OBJECT-TYPE

     SYNTAX SEQUENCE OF Ol41nnHMTPModEntry

     ACCESS not-accessible

     STATUS mandatory

     DESCRIPTION

	  "A list of module-specific information associated

	  with a particular ol41nnHMTP or ol41nnHMTP-FL module."

     ::= { ol41nnHMTP 1 }



ol41nnHMTPModEntry OBJECT-TYPE

     SYNTAX Ol41nnHMTPModEntry

     ACCESS not-accessible

     STATUS mandatory

     DESCRIPTION

	  "A module entry containing objects that describe the

	  module level for that particular module."

     INDEX { ol41nnHMTPModSlotIndex }

     ::= { ol41nnHMTPModTable 1 }



Ol41nnHMTPModEntry ::=

     SEQUENCE {

	  ol41nnHMTPModSlotIndex

		INTEGER,

	  ol41nnHMTPModSerialNo

		DisplayString,

	  ol41nnHMTPModProtocols

		DisplayString,

	  ol41nnHMTPModIpAddress

		IpAddress

	  }



ol41nnHMTPModSlotIndex OBJECT-TYPE

     SYNTAX INTEGER

     ACCESS read-only

     STATUS mandatory

     DESCRIPTION

	  "The slot number of this module."

     ::= { ol41nnHMTPModEntry 1 }



ol41nnHMTPModSerialNo  OBJECT-TYPE

	SYNTAX DisplayString

	ACCESS read-only

	STATUS mandatory

	DESCRIPTION

		"The serial number of this module, as entered by

		the user through the Management interface."

	::= { ol41nnHMTPModEntry 2 }



ol41nnHMTPModProtocols  OBJECT-TYPE

	SYNTAX DisplayString

	ACCESS read-only

	STATUS mandatory

	DESCRIPTION

		"A list of the various protocols supported by

		the module's agent."

	::= { ol41nnHMTPModEntry 3 }



ol41nnHMTPModIpAddress OBJECT-TYPE

       SYNTAX IpAddress

       ACCESS read-only

       STATUS mandatory

       DESCRIPTION

	       "The IP Address of this module."

       ::= { ol41nnHMTPModEntry 4 }



-- Port Table (41nnH-MTP)



ol41nnHMTPPortTable  OBJECT-TYPE

     SYNTAX SEQUENCE OF Ol41nnHMTPPortEntry

     ACCESS not-accessible

     STATUS mandatory

     DESCRIPTION

	  "A table of port-specific information for each port of

	  this module type."

     ::= { ol41nnHMTP 2 }



ol41nnHMTPPortEntry OBJECT-TYPE

     SYNTAX Ol41nnHMTPPortEntry

     ACCESS not-accessible

     STATUS mandatory

     DESCRIPTION

	  "A port entry containing objects that describe this port."

     INDEX { ol41nnHMTPPortSlotIndex, ol41nnHMTPPortIndex }

     ::= { ol41nnHMTPPortTable 1 }



Ol41nnHMTPPortEntry ::=

     SEQUENCE {

	  ol41nnHMTPPortSlotIndex

	       INTEGER,

	  ol41nnHMTPPortIndex

	       INTEGER,

	  ol41nnHMTPPortReset

	       INTEGER,

	  ol41nnHMTPPortLinkInteg

	       INTEGER

	  }

ol41nnHMTPPortSlotIndex OBJECT-TYPE

     SYNTAX INTEGER

     ACCESS read-only

     STATUS mandatory

     DESCRIPTION

	  "The slot (stack) number of this port's module."

     ::= { ol41nnHMTPPortEntry 1 }



ol41nnHMTPPortIndex OBJECT-TYPE

     SYNTAX INTEGER

     ACCESS read-only

     STATUS mandatory

     DESCRIPTION

	  "The port number of this port."

     ::= { ol41nnHMTPPortEntry 2 }





ol41nnHMTPPortReset OBJECT-TYPE

     SYNTAX INTEGER {

	noReset(1),

	reset(2)

	}

     ACCESS read-write

     STATUS mandatory

     DESCRIPTION

		"Used to reset the port's '802.3 state machine',

		which will re-enable a disabled port and/or reconnect

		a partitioned port."

     ::= { ol41nnHMTPPortEntry 3 }



ol41nnHMTPPortLinkInteg OBJECT-TYPE

     SYNTAX INTEGER {

	enabled(1),

	disabled(2),

	notApplicable(3)

	}

     ACCESS read-write

     STATUS mandatory

     DESCRIPTION

	  "The port's (good) link integrity configuration.  Enabling

	  link integrity configures the port to conform to

	  the link integrity feature as specified by 10BASE-T.

	  Applicable only to 10BASE-T ports."

     ::= { ol41nnHMTPPortEntry 4 }



-- Module Table (41nnH-ETP)



ol41nnHETPModTable OBJECT-TYPE

     SYNTAX SEQUENCE OF Ol41nnHETPModEntry

     ACCESS not-accessible

     STATUS mandatory

     DESCRIPTION

	  "A list of module-specific information associated

	  with a particular ol41nnHETP module."

     ::= { ol41nnHETP 1 }



ol41nnHETPModEntry OBJECT-TYPE

     SYNTAX Ol41nnHETPModEntry

     ACCESS not-accessible

     STATUS mandatory

     DESCRIPTION

	  "A module entry containing objects that describe the

	  module level for that particular module."

     INDEX { ol41nnHETPModSlotIndex }

     ::= { ol41nnHETPModTable 1 }



Ol41nnHETPModEntry ::=

     SEQUENCE {

	  ol41nnHETPModSlotIndex

		INTEGER,

	  ol41nnHETPModSerialNo

		DisplayString

	 }



ol41nnHETPModSlotIndex OBJECT-TYPE

     SYNTAX INTEGER

     ACCESS read-only

     STATUS mandatory

     DESCRIPTION

	  "The slot number of this module."

     ::= { ol41nnHETPModEntry 1 }



ol41nnHETPModSerialNo  OBJECT-TYPE

	SYNTAX DisplayString

	ACCESS read-only

	STATUS mandatory

	DESCRIPTION

		"The serial number of this module, as entered by

		the user through the Management interface."

	::= {ol41nnHETPModEntry 2 }



-- Port Table (41nnH-ETP)



ol41nnHETPPortTable  OBJECT-TYPE

     SYNTAX SEQUENCE OF Ol41nnHETPPortEntry

     ACCESS not-accessible

     STATUS mandatory

     DESCRIPTION

	  "A table of port-specific information for each port of

	  this module type."

     ::= { ol41nnHETP 2 }



ol41nnHETPPortEntry OBJECT-TYPE

     SYNTAX Ol41nnHETPPortEntry

     ACCESS not-accessible

     STATUS mandatory

     DESCRIPTION

	  "A port entry containing objects that describe this port."

     INDEX { ol41nnHETPPortSlotIndex, ol41nnHETPPortIndex }

     ::= { ol41nnHETPPortTable 1 }



Ol41nnHETPPortEntry ::=

     SEQUENCE {

	  ol41nnHETPPortSlotIndex

	       INTEGER,

	  ol41nnHETPPortIndex

	       INTEGER,

	  ol41nnHETPPortReset

	       INTEGER,

	  ol41nnHETPPortLinkInteg

	       INTEGER

	  }



ol41nnHETPPortSlotIndex OBJECT-TYPE

     SYNTAX INTEGER

     ACCESS read-only

     STATUS mandatory

     DESCRIPTION

	  "The slot (stack) number of this port's module."

     ::= { ol41nnHETPPortEntry 1 }



ol41nnHETPPortIndex OBJECT-TYPE

     SYNTAX INTEGER

     ACCESS read-only

     STATUS mandatory

     DESCRIPTION

	  "The port number of this port."

     ::= { ol41nnHETPPortEntry 2 }



ol41nnHETPPortReset OBJECT-TYPE

     SYNTAX INTEGER {

		ready(1),

		reset(2)

		}

     ACCESS read-write

     STATUS mandatory

     DESCRIPTION

		"Used to reset the port's '802.3 state machine',

		which will re-enable a disabled port and/or reconnect

		a partitioned port."

     ::= { ol41nnHETPPortEntry 3 }



ol41nnHETPPortLinkInteg OBJECT-TYPE

     SYNTAX INTEGER {

	  enabled(1),

	  disabled(2)

	  }

     ACCESS read-write

     STATUS mandatory

     DESCRIPTION

	  "The port's (good) link integrity configuration.  Enabling

	  link integrity configures the port to conform to

	  the link integrity feature as specified by 10BASE-T."

     ::= { ol41nnHETPPortEntry 4 }

















--

-- olModSummary

--

-- This group was designed to enhance the performance of retrievals of

-- module related information.  It is specifically targeted for use by

-- closely designed management applications.  It is NOT designed for use

-- by off the shelf applications and is documented here only for completeness.

--

-- The summary group encodes the module information into an octet string

-- that includes the values of each object in the module, port and trunk

-- tables.  This allows fast retrieval of a large amount of information

-- within no more that 17 Get operations, rather than utilizing 17 operations

-- (max) for the modules, and 17 x Number of Ports (max) for the port

-- information, and 17 x Number of Trunks (max) for the trunk information.

--

-- Users should be aware that this table requires the application to

-- parse out information and therefore, applications should be sensitive to

-- the positioning of information within the summary string.

--





olModSummaryTable OBJECT-TYPE

	SYNTAX SEQUENCE OF OlModSummaryEntry

	ACCESS not-accessible

	STATUS mandatory

	DESCRIPTION

		"A table of condensed module information."

	::= { olModules 5 }



olModSummaryEntry OBJECT-TYPE

	SYNTAX OlModSummaryEntry

	ACCESS not-accessible

	STATUS mandatory

	DESCRIPTION

		"A summary of all the generic and value added information

		associated with this module."

	INDEX { olModSummarySlotIndex }

	::= { olModSummaryTable 1 }



OlModSummaryEntry ::=

	SEQUENCE {

		olModSummarySlotIndex

			INTEGER,

		olModSummaryInfo

			OCTET STRING

		}



olModSummarySlotIndex OBJECT-TYPE

	SYNTAX INTEGER

	ACCESS read-only

	STATUS mandatory

	DESCRIPTION

		"The slot number of this module that this summary

		pertains to."

	::= { olModSummaryEntry 1 }



olModSummaryInfo OBJECT-TYPE

	SYNTAX OCTET STRING (SIZE(0..512))

	ACCESS read-only

	STATUS mandatory

	DESCRIPTION

		"A summary of all information relating to this module in

		condensed format.  The condensed format is only as large

		as needed to hence the largest value which usually is one

		octet.  The TCP port for the terminal server, however,

		uses 4 octets.



		The summary consists of a header, a module portion, a port

		portion, and a trunk portion.  Each portion consists of

		generic information and module specific information.

		For example, the module information consists of the

		olModTable entry for this slot and the olSpecMods module

		table information for this module type for this slot.





		---------------------------------------------------

		The header consists of the following octets:

			Version of structure : 1



			Number of octets in generic module

			Number of octets in specific module

			Number of octets in generic port

			Number of octets in specific port

			Number of octets in generic trunk

			Number of octets in specific trunk



		The format of the data portion is as follows:



			Some of the olModTable:

				olModType

				olModClass

				olModDescr

				olModVersion

				olModNetwork

				olModNetworkType

				olModStatus



				olModNumPorts

				olModNumTrunks





			olSpecMods module table (for this module)

				Not including slot number.



		For each port:

			Some of the olPortTable:

				olPortType

				olPortConnector

				olPortStatus

				olPortAdminState

				olPortNetwork

				olPortNetworkType

				olPortAlertFilter



			olSpecMods port table (for this port's module)

				Not including slot and port number.



		For each trunk:

			Some of the olTrunkTable:

				olTrunkType

				olTrunkConnector

				olTrunkStatus

				olTrunkAdminState

				olTrunkWrapState

				olTrunkNeighbor





			olSpecMods trunk table (for this trunk's module)

				Not including slot and trunk number.



		---------------------------------------------------

		Version 2 of the summary structure:



		Version 2 is returned only when there is a possibility

		of multiple modules per slot.  This is a function of

		the platform (concentrator).  The ONcore platform

		is an example of this.  ONline modules in the ONcore

		platform will still be represented by version 1 structure.



		Version 2 is an array of version 1 structures,



		Version: 2



		Maximum number of v1 structures = 8.

		Number of v1 structures to follow => max of 8.

		Reserved octet = 0.



		2 octets each describing the length of v1 summaries:

			Number of octets in summary #1.

			Number of octets in summary #2.

			Number of octets in summary #3.

			Number of octets in summary #4.

			Number of octets in summary #5.

			Number of octets in summary #6.

			Number of octets in summary #7.

			Number of octets in summary #8.



		Array of Version 1 structures.



		For example, there are 3 modules in slot 5, in subslot

		locations 1, 3 and 8.



			Byte		Description

			----		-----------

			 1		Version = 2

			 2		Max number of v1 structures (8)

			 3		Number of v1 structures (3)

			 4		Reserved (0)

			 5&6		Number of bytes N(1)

			 7&8		Number of bytes N(2) = 0

			 9&10		Number of bytes N(3)

			11&12		Number of bytes N(4) = 0

			13&14		Number of bytes N(4) = 0

			15&16		Number of bytes N(4) = 0

			17&18		Number of bytes N(4) = 0

			19&20		Number of bytes N(4)



			21

			to		Version 1 summary for module in sslot 1

			21 + N(1)



			21 + N(1)

			to		Version 1 summary for module in sslot 3

			(21 + N(1)) + N(3)



			(21 + N(1)) + N(3)

			to		Version 1 summary for module in sslot 8



			((21 + N(1)) + N(3)) + N(8)



			21 to 21 + N(1) Version 1 summary for module in sslot 1



		----------------------------------------------------



		In all of the above, the index for all of these tables

		is condensed out of the summary. "

	::= { olModSummaryEntry 2 }





--

--

-- The ONcore Modules Table

--

--

-- This table represents the information about modules

-- including mother boards and daughter boards.

--

-- Modules are instantiated by slot and subslot.  The slot

-- is the physical location of the module in the concentrator.

-- The subslot indicates the position of the module within a slot.

--

-- For example, the mother board is always subslot 1 of a slot, indicating

-- that it is the first module in that slot.  The first daughter board

-- would of course be the second module in that slot, and hence, subslot 2.

--





ocModTable OBJECT-TYPE

	SYNTAX SEQUENCE OF OcModEntry

	ACCESS not-accessible

	STATUS mandatory

	DESCRIPTION

		"A table that contains generic information about every

		module that is present within the concentrator."

	::= { olModules 6 }



ocModEntry OBJECT-TYPE

	SYNTAX OcModEntry

	ACCESS not-accessible

	STATUS mandatory

	DESCRIPTION

		"A list of information for each module in the concentrator."

	INDEX { ocModSlotIndex, ocModSubSlotIndex }

	::= { ocModTable 1 }



OcModEntry ::=

	SEQUENCE {

		ocModSlotIndex

			INTEGER,

		ocModSubSlotIndex

			INTEGER,

		ocModType

			INTEGER,

		ocModClass

			INTEGER,

		ocModDescr

			DisplayString,

		ocModVersion

			DisplayString,

		ocModVendor

			INTEGER,

		ocModResetModule

			INTEGER,

		ocModConfigToDips

			INTEGER,

		ocModConfigured

			INTEGER,

		ocModNetwork

			INTEGER,

		ocModNetworkType

			INTEGER,

		ocModStatus

			INTEGER,

		ocModNumPorts

			INTEGER,

		ocModNumTrunks

			INTEGER,

		ocModNumSubSlots

			INTEGER



		}





ocModSlotIndex OBJECT-TYPE

	SYNTAX INTEGER

	ACCESS read-only

	STATUS mandatory

	DESCRIPTION

		"The unique slot number of this module.  Its value ranges

		between 1 and olConcNumSlots and remains constant at

		least from one re-initialization of the entity's network

		management system to the next re-initialization."

	::= { ocModEntry 1 }



ocModSubSlotIndex OBJECT-TYPE

	SYNTAX INTEGER

	ACCESS read-only

	STATUS mandatory

	DESCRIPTION

		"The unique subslot number of this module.  Its value ranges

		between 1 and the value of ocModNumSubSlots for the

		mother board in this slot (ocModNumSubSlots.<slot>.1),

		and it remains constant between re-initializations of the

		mother board.



		The mother board is ALWAYS the first subslot index in any

		particular slot.  Not all subslots must be occupied, and an

		empty subslot will not return an instance."

	::= { ocModEntry 2 }



ocModType OBJECT-TYPE

	SYNTAX INTEGER {

		module-unmanageable(1), -- not manageable

		module-unknown(2),	-- only generically manageable

		module-50nnM-CTL(3),	-- Controller

		module-51nnM-MGT(4),	-- Ethernet Management

		module-51nnM-FIB(5),	-- Ethernet Fiber

		module-51nnM-UTP(6),	-- Ethernet 10BASE-T

		module-51nnM-TP(7),	-- Ethernet 10BASE-T

		module-51nnM-BNC(8),	-- Ethernet BNC

		module-51nnB-EE(9),	-- OEBM

		module-51nnR-ES(10),	-- Cisco Serial

		module-51nnR-EE(11),	-- Cisco Ethernet

		module-51nnM-AUIF(12),  -- Ethernet AUI Female

		module-51nnM-AUIM(13),  -- Ethernet AUI Male

		module-5208M-TP(14),	-- Token Ring 8-port MAU module

		module-51nnM-FP(15),	-- Ethernet Fiber port switching

		module-51nnM-FBP(16),	-- Ethernet 10BASE-F port switching

		module-51nnM-TPL(17),	-- Ethernet 10BASE-T

		module-51nnM-TPPL(18),  -- Ethernet 10BASE-T port switching

		module-52nnM-TP(19),	-- Token Ring Media Module

		module-52nnM-FR(20),	-- Token Ring FiberOptic Repeater

		module-51nnM-TS(21),	-- Ethernet Terminal Server

		module-51nnM-FL(22),	-- Ethernet FOIRL

		module-50nnM-RCTL(23),  -- Redundant Controller

		module-51nnM-FB(24),	-- Ethernet 10BASE-F

		module-53nnM-MGT(25),	-- FDDI managment module (FMM)

		module-53nnM-FBMIC(26), -- FDDI media w/ fiber ANSI MIC conn.

		module-53nnM-FIBST(27), -- FDDI media w/ fiber ST conn.

		module-53nnM-STP(28),	-- FDDI w/ shielded copper DB9 conn.

		module-51nnM-TPCL(29),  -- Ethernet 10BASE-T per-connector

		module-52nnB-TT(30),	-- Token Ring Bridge

		module-51nnI-x(31),	-- Ethernet Interconnect Module

		module-52nnM-MGT(32),	-- Token Ring Management

		module-50nnM-HCTL(33),  -- Hidden Controller

		module-61nnM-CAR(35),	-- Ethernet Carrier Module



		module-60nnM-MGT(43),	-- Distributed Management Module



		module-61nnD-MGT(45),	-- Ethernet MAC monitor card

		module-61nnM-FBP(46),	-- Ethernet 10-port per-port switchable fiber

		module-61nnM-TPL(47),	-- Ethernet 24-port per-port switching

		module-51nnM-TPLS(48),  -- Ethernet 10BASE-T Security Module

		module-60nnM-RCTL(50),  -- ONcore Ctlr (managed by ONcore mgmt)



		module-50nnM-RCLS(51),  -- Load Sharing Redundant Controller





		module-41nnH-MTP(52),	-- ONsemble Ethernet Management Unit

		module-41nnH-ETP(53),	-- ONsemble Ethernet Base Unit







		module-52nnM-EC(62)	-- 3174 Establistment Controller



		,

		module-53nnM-TDDI(65)	-- FDDI w/ copper RJ45 conn.











		}

	ACCESS read-only

	STATUS mandatory

	DESCRIPTION

		"The unique type identifier for this module.  This type

		is used to identify the branch in olSpecMods (see below).



		module-unmanageable(1) means that only the following

		objects are valid for this module:



			ocModSlotIndex

			ocModClass

			ocModVersion

			ocModVendor

			ocModReset

			ocModConfigToDips

			ocModConfigured



		module-unknown(2) means that all the generic attributes

		are manageable, but there is no olSpecMods branch

		for this module as viewed by this agent."

		::= { ocModEntry 3 }



ocModClass OBJECT-TYPE

	SYNTAX INTEGER {



		controller(1),

		mgmt(2),

		ethernet-media(3),

		ethernet-interconnect(4),

		ethernet-portswitching-media(5),

		token-ring-media(6),

		terminal-server(7),

		fddi-media(8),

		token-ring-mgmt(9),

		ethernet-connswitching-media(10),

		token-ring-interconnect(11),

		fddi-mgmt(12),

		oncore-token-ring-media(13),

		ethernet-carrier(14),

		oncore-oem-specials(15),



		network-monitor(16),



		oncore-download(17),



		ethernet-media-extended(19),

		online-token-ring-mod-interconnect(20)







		}

	ACCESS read-only

	STATUS mandatory

	DESCRIPTION

		"The class of this module.  The class defines the

	internal data structure used to manage this module."

	::= { ocModEntry 4 }



ocModDescr OBJECT-TYPE

	SYNTAX DisplayString (SIZE(1..128))

	ACCESS read-only

	STATUS mandatory

	DESCRIPTION

		"A textual string containing information about the module."

	::= { ocModEntry 5 }



ocModVersion OBJECT-TYPE

	SYNTAX DisplayString (SIZE(1..32))

	ACCESS read-only

	STATUS mandatory

	DESCRIPTION

		"The software version number of this module.  "

	::= { ocModEntry 6 }



ocModVendor OBJECT-TYPE

	SYNTAX INTEGER {

		chipcom(1),

		cisco(2),

		pilkington(3),

		datability(5),

		ibm(6),

		raycom(7),

		retix(8),

		intellicom(9)

		}

	ACCESS read-only

	STATUS mandatory

	DESCRIPTION

		"The vendor of this module."

	::= { ocModEntry 7 }



ocModResetModule OBJECT-TYPE

	SYNTAX INTEGER {

		noReset(1),

		reset(2)

		}

	ACCESS read-write

	STATUS mandatory

	DESCRIPTION

		"Setting this object to reset(2) causes this module to

		reset."

	::= { ocModEntry 8 }



ocModConfigToDips OBJECT-TYPE

	SYNTAX INTEGER {

		noConfigure(1),

		configure(2)

		}

	ACCESS read-write

	STATUS mandatory

	DESCRIPTION

		"Setting this object to configure(2) causes this module to

		configure based on the dip switch settings.  Note, if the

		NV dip switch (if applicable) is set to configure from NV,

		then the module will retrieve its configuration from the

		on-board non-volatile storage."

	::= { ocModEntry 9 }



ocModConfigured OBJECT-TYPE

	SYNTAX INTEGER {

		notConfigured(1),

		configured(2)

		}

	ACCESS read-only

	STATUS mandatory

	DESCRIPTION

		"This object indicates whether this module has already been

		configured.  An unconfigured module is configured to a safe

		state (ports are disabled and the module is isolated from

		the backplane networks)."

	::= { ocModEntry 10 }





ocModNetwork OBJECT-TYPE

	SYNTAX INTEGER {

		other(1),

		isolated(2),

		port-switching(3),

		front-panel(5),

		ethernet-1(6),

		ethernet-2(7),

		ethernet-3(8),

		token-ring-1(9),

		token-ring-2(10),

		token-ring-3(11),

		token-ring-4(12),

		token-ring-5(13),

		token-ring-6(14),

		token-ring-7(15),

		fddi-1(16),

		fddi-2(17),

		fddi-3(18),

		fddi-4(19),

		per-connector(20),

		isolated-1(21),		-- for modules with multiple

		isolated-2(22),		-- isolated networks within the

		isolated-3(23),		-- module - multiple isolated networks.

		isolated-4(24),

		isolated-5(25),

		isolated-6(26),

		isolated-7(27),

		isolated-8(28),

		isolated-9(29),

		isolated-10(30),

		isolated-11(31),

		ethernet-4(32),

		ethernet-5(33),

		ethernet-6(34),

		ethernet-7(35),

		ethernet-8(36)



		}

	ACCESS read-write

	STATUS mandatory

	DESCRIPTION

		"The network that this module is attached to.



		Setting this module to a value that it does not support

		will return an invalidData error."

	::= { ocModEntry 11 }



ocModNetworkType OBJECT-TYPE

	SYNTAX INTEGER {

		other(1),	    -- other only

		port-switching(3),  -- use olPortNetwork

		ethernet(5),	    -- ethernet 1-3 or 1-8, isolated

		token-ring(6), -- token-ring 1-7, isolated,



		fddi(7),	    -- fddi 1-4, isolated

		serial(8)	    -- front or isolated only

		}

	ACCESS read-only

	STATUS mandatory

	DESCRIPTION

		"The network type of this module. The network type

		reflects the valid values for ocModNetwork."

	::= { ocModEntry 12 }



ocModStatus OBJECT-TYPE

	SYNTAX INTEGER {

		okay(1),

		fatalError(10),

		booting(20),

		partial-failure(21),

		notInserted(30),

		speedMismatch(31)

		}

	ACCESS read-only

	STATUS mandatory

	DESCRIPTION

		"The module's status."

	::= { ocModEntry 13 }



ocModNumPorts OBJECT-TYPE

	SYNTAX INTEGER

	ACCESS read-only

	STATUS mandatory

	DESCRIPTION

		"The number of ports on this module.  Note, ports may be

		physical ports like 10BASE-T ports, or logical, like

		the bridge module ports."

	::= { ocModEntry 14 }



ocModNumTrunks OBJECT-TYPE

	SYNTAX INTEGER

	ACCESS read-only

	STATUS mandatory

	DESCRIPTION

		"The number of trunks on this module.  Note, trunks

		are links that are, by definition, backbone connections.

		Examples of trunks are ring in and ring out ports for

		token ring, and the connections for rings to the backplane."

	::= { ocModEntry 15 }



ocModNumSubSlots OBJECT-TYPE

	SYNTAX  INTEGER

	ACCESS  read-only

	STATUS  mandatory

	DESCRIPTION

		"The number of possible submodules that can exist in this

		slot."

	::= { ocModEntry 16 }







-- The olNet Group



-- This group represents information about ONline networks in general.



olNetDPTable OBJECT-TYPE

	SYNTAX SEQUENCE OF OlNetDPEntry

	ACCESS not-accessible

	STATUS mandatory

	DESCRIPTION

		"A table that contains information linking

		physical backplane allocation to logical

		networks. This information is useful:



			(1) to determine the physical allocation

			of networks on the backplane, and



			(2) to determine the remaining capacity of

			the backplane for future network growth.



		Since unknown modules are managed via dip

		switches, this is useful in order to set the

		dips to the appropriate settings.



		Ethernet is a bus architecture.  Once a path is

		allocated, all modules and ports can access that

		path.



		Token Ring and FDDI are ring architectures.

		Each module on a ring requires a path.  Therefore,

		4 paths could be used to link 4 modules together

		on one ring, or 2 modules on 2 separate rings.

		It is possible to have a module allocated to

		a ring (and thus a data path) without linking

		to another module.



		These rules can be used to determine the remaining

		capacity for network growth."

	::= { olNet 1 }



olNetDPEntry OBJECT-TYPE

	SYNTAX OlNetDPEntry

	ACCESS not-accessible

	STATUS mandatory

	DESCRIPTION

		"A list of information about each data path in the

		concentrator."

	INDEX { olNetDPDataPath }

	::= { olNetDPTable 1 }



OlNetDPEntry ::=

	SEQUENCE {

		olNetDPDataPath

			INTEGER,

		olNetDPNetID

			INTEGER

		}



olNetDPDataPath OBJECT-TYPE

	SYNTAX INTEGER {

		ethernet-path-1(6), -- channel 1

		ethernet-path-2(7), -- channel 2

		ethernet-path-3(8), -- channel 3

		token-ring-path-1(9),

		token-ring-path-2(10),

		token-ring-path-3(11),

		token-ring-path-4(12),

		token-ring-path-5(13),

		token-ring-path-6(14),

		token-ring-path-7(15),

		token-ring-path-8(16),

		token-ring-path-9(17),

		token-ring-path-10(18),

		token-ring-path-11(19),

		token-ring-path-12(20),

		token-ring-path-13(21),

		token-ring-path-14(22),

		token-ring-path-15(23),

		fddi-path-1(24),

		fddi-path-2(25),

		fddi-path-3(26),

		fddi-path-4(27),

		fddi-path-5(28),

		fddi-path-6(29),

		fddi-path-7(30),

		fddi-path-8(31),

		ethernet-path-4(32),

		ethernet-path-5(33),

		ethernet-path-6(34),

		ethernet-path-7(35),

		ethernet-path-8(36)

		}

	ACCESS read-only

	STATUS mandatory

	DESCRIPTION

		"The data path on the backplane.  Data paths between

		different protocols overlap.  That is, an ethernet data

		path will overlap with multiple token ring and fddi data

		paths. "

	::= { olNetDPEntry 1 }



olNetDPNetID OBJECT-TYPE

	SYNTAX INTEGER {

		notUsed(1),		-- available for use

		otherProto(2),		-- another protocol is using

					-- these resources

		ethernet-1(6),

		ethernet-2(7),

		ethernet-3(8),

		token-ring-1(9),

		token-ring-2(10),

		token-ring-3(11),

		token-ring-4(12),

		token-ring-5(13),

		token-ring-6(14),

		token-ring-7(15),

		fddi-1(16),

		fddi-2(17),

		fddi-3(18),

		fddi-4(19)

		}

	ACCESS  read-only

	STATUS mandatory

	DESCRIPTION

		"The network that this data path corresponds to.

		If the data path is not being used at all, notUsed(1)

		is the return value.  If the data path is being used

		by another protocol, then otherProto(2) is the

		return value."

	::= { olNetDPEntry 2 }





--

-- The following objects comprise the oldest style of security.

-- They are left here for backward compatibility with existing

-- applications; however, this group will not be enhanced.

--

olNetSecurityMACTable OBJECT-TYPE

	SYNTAX SEQUENCE OF OlNetSecurityMACEntry

	ACCESS not-accessible

	STATUS mandatory

	DESCRIPTION

		"A table of security configuration parameters and MAC

		addresses associated with every port with security

		configured in the concentrator."

	::= { olNet 2 }



olNetSecurityMACEntry OBJECT-TYPE

	SYNTAX OlNetSecurityMACEntry

	ACCESS not-accessible

	STATUS mandatory

	DESCRIPTION

		"A list of security configuration parameters and MAC

		addresses associated with each port with security

		configured in the concentrator."

	INDEX { olNetSecurityMACSlotIndex, olNetSecurityMACPortIndex,

		olNetSecurityMACAddress }

	::= { olNetSecurityMACTable 1 }



OlNetSecurityMACEntry ::=

	SEQUENCE {

		olNetSecurityMACSlotIndex

			INTEGER,

		olNetSecurityMACPortIndex

			INTEGER,

		olNetSecurityMACAddress

			MacAddress,

		olNetSecurityMACMode

			INTEGER,

		olNetSecurityMACStatus

			INTEGER

		 }

olNetSecurityMACSlotIndex OBJECT-TYPE

	 SYNTAX INTEGER

	 ACCESS read-only

	 STATUS mandatory

	 DESCRIPTION

		 "The slot number that contains this port."

	 ::= { olNetSecurityMACEntry 1 }



olNetSecurityMACPortIndex OBJECT-TYPE

	 SYNTAX INTEGER

	 ACCESS read-only

	 STATUS mandatory

	 DESCRIPTION

		 "The port number within this slot."

	 ::= { olNetSecurityMACEntry 2 }



olNetSecurityMACAddress OBJECT-TYPE

	 SYNTAX MacAddress

	 ACCESS read-write

	 STATUS mandatory

	 DESCRIPTION

		 "The security MAC address assigned to this port."

	 ::= { olNetSecurityMACEntry 3 }



olNetSecurityMACMode OBJECT-TYPE

	SYNTAX INTEGER {

		enabled(1),

		disabled(2)

		}

	ACCESS read-write

	STATUS mandatory

	DESCRIPTION

		"The desired security mode for this port/address."

--	DEFVAL {disabled(2)}

	::= { olNetSecurityMACEntry 4 }



olNetSecurityMACStatus OBJECT-TYPE

	SYNTAX INTEGER {

		valid(1),

		invalid(2)

		}

	ACCESS read-write

	STATUS mandatory

	DESCRIPTION

		"Each instance of the olNetSecurityMACTable associated

		with this olNetSecurityMACEntry (slot, port, and address)

		will be deleted by the agent if this olNetSecurityMACEntry

		is not equal to valid(1).  Initial creation of instances

		occurs via a set operation on a specific slot/port/address."

--	DEFVAL {valid(1)}

	::= { olNetSecurityMACEntry 5 }





--

-- The following groups of objects comprise the new style of security

-- (to be compared with the old style defined above).  This includes a

-- specific table for control parameters per port, objects for autolearning,

-- and a cache of previous intrusion attempts.

--



olNetOlSec	OBJECT IDENTIFIER ::= { olNet 3 }





olNetOlSecAddrTable OBJECT-TYPE

	SYNTAX SEQUENCE OF OlNetOlSecAddrEntry

	ACCESS not-accessible

	STATUS mandatory

	DESCRIPTION

		"A table of security MAC addresses."

	::= { olNetOlSec 1 }



olNetOlSecAddrEntry OBJECT-TYPE

	SYNTAX OlNetOlSecAddrEntry

	ACCESS not-accessible

	STATUS mandatory

	DESCRIPTION

		"Security MAC addresses indexed by slot, port, and MAC

		address."

	INDEX {olNetOlSecAddrSlotIndex, olNetOlSecAddrPortIndex,

		olNetOlSecAddrAddress }

	::= { olNetOlSecAddrTable 1 }



OlNetOlSecAddrEntry ::=

	SEQUENCE {

		olNetOlSecAddrSlotIndex

			INTEGER,

		olNetOlSecAddrPortIndex

			INTEGER,

		olNetOlSecAddrAddress

			MacAddress,

		olNetOlSecAddrStatus

			INTEGER

		}



olNetOlSecAddrSlotIndex OBJECT-TYPE

	SYNTAX INTEGER

	ACCESS read-only

	STATUS mandatory

	DESCRIPTION

		"The slot number index (used along with the port and address

		indices)."

	::= { olNetOlSecAddrEntry 1 }



olNetOlSecAddrPortIndex OBJECT-TYPE

	SYNTAX INTEGER

	ACCESS read-only

	STATUS mandatory

	DESCRIPTION

		"The port number index (used along with the slot and address

		indices)."

	::= { olNetOlSecAddrEntry 2 }



olNetOlSecAddrAddress OBJECT-TYPE

	SYNTAX MacAddress

	ACCESS read-write

	STATUS mandatory

	DESCRIPTION

		"The security MAC address index (used along with the slot and

		port indices).  Note that there may be multiple addresses

		associated with a single port."

	::= { olNetOlSecAddrEntry 3 }



olNetOlSecAddrStatus OBJECT-TYPE

	SYNTAX INTEGER {

		valid(1),

		invalid(2)

		}

	ACCESS read-write

	STATUS mandatory

	DESCRIPTION

		"Setting this object to valid(1) will cause the

		corresponding security MAC address to be associated

		with the given port.  Setting this object to

		invalid(2) will clear the corresponding MAC address

		for the given port."

	::= { olNetOlSecAddrEntry 4 }





olNetOlSecControlTable OBJECT-TYPE

	SYNTAX SEQUENCE OF OlNetOlSecControlEntry

	ACCESS not-accessible

	STATUS mandatory

	DESCRIPTION

		"A table of security configuration parameters pertaining

		to a specific port."

	::= { olNetOlSec 2 }



olNetOlSecControlEntry OBJECT-TYPE

	SYNTAX OlNetOlSecControlEntry

	ACCESS not-accessible

	STATUS mandatory

	DESCRIPTION

		"Security configuration parameters pertaining to a specific

		port (indexed by slot and port)."

	INDEX { olNetOlSecControlSlotIndex, olNetOlSecControlPortIndex }

	::= { olNetOlSecControlTable 1 }



OlNetOlSecControlEntry ::=

	SEQUENCE {

		olNetOlSecControlSlotIndex

			INTEGER,

		olNetOlSecControlPortIndex

			INTEGER,

		olNetOlSecControlMode

			INTEGER,

		olNetOlSecControlSecType

			INTEGER,

		olNetOlSecControlActOnIntr

			INTEGER,

		olNetOlSecControlClearAddrs

			INTEGER,

		olNetOlSecControlAutolearnMask

			INTEGER

		}



olNetOlSecControlSlotIndex OBJECT-TYPE

	SYNTAX INTEGER

	ACCESS read-only

	STATUS mandatory

	DESCRIPTION

		"The slot number index (used along with the port index)."

	::= { olNetOlSecControlEntry 1 }



olNetOlSecControlPortIndex OBJECT-TYPE

	SYNTAX INTEGER

	ACCESS read-only

	STATUS mandatory

	DESCRIPTION

		"The port number index (used along with the slot index)."

	::= { olNetOlSecControlEntry 2 }



olNetOlSecControlMode OBJECT-TYPE

	SYNTAX INTEGER {

		enable(1),

		disable(2)

		}

	ACCESS read-write

	STATUS mandatory

	DESCRIPTION

		"The desired security mode for this port.  Setting

		this object to enable(1) is equivalent to setting the

		'SecType' object (see below) to full(1), since both actions

		enable Eavesdropping and Intrusion Security."

	::= { olNetOlSecControlEntry 3 }



olNetOlSecControlSecType OBJECT-TYPE

	SYNTAX INTEGER {

		full(1),

		intrusion-only(2),

		eavesdropping-only(3),

		no-security(4)

		}

	ACCESS read-write

	STATUS mandatory

	DESCRIPTION

		"Setting this object enables a certain type of security

		for this port: Eavesdropping Security-only, Intrusion

		Security-only, or Full.  Note that setting this object to

		full(1) is equivalent to setting the 'Mode' object (see above)

		to enable(1)."

	::= { olNetOlSecControlEntry 4 }



olNetOlSecControlActOnIntr OBJECT-TYPE

	SYNTAX INTEGER {

		disable-and-trap(1),

		disable-only(2),

		trap-only(3),

		no-action(4)

		}

	ACCESS read-write

	STATUS mandatory

	DESCRIPTION

		"This object can be used to get or set the port-action-on-

		intrusion flag on a per-port basis.  When an Intrusion

		Security breach is attempted on a port, the Security Module

		can automatically disable the port and/or generate a trap to

		management, as dictated by this flag."

	::= { olNetOlSecControlEntry 5 }



olNetOlSecControlClearAddrs OBJECT-TYPE

	SYNTAX INTEGER {

		clear-all-addrs(1),

		not-clear(2)

		}

	ACCESS read-write

	STATUS mandatory

	DESCRIPTION

		"When this object is set to clear-all-addrs(1) then all of

		the security MAC addresses associated with this port

		will be cleared.  Note that this will not change the state

		of the 'Mode' (or any other) object in this table."

	::= { olNetOlSecControlEntry 6 }



olNetOlSecControlAutolearnMask OBJECT-TYPE

	SYNTAX INTEGER {

		enable(1),

		disable(2)

		}

	ACCESS read-write

	STATUS mandatory

	DESCRIPTION

		"This mask is used when autolearning is performed to determine

		whether the nMM should learn any security MAC addresses for

		this port.  If this object is set to enable(1) then the nMM

		will ignore this port during autolearning.  Note that

		autolearning is not supported by the TRMM."

	::= { olNetOlSecControlEntry 7 }





olNetOlSecAutolearn	OBJECT IDENTIFIER ::= { olNetOlSec 3 }



olNetOlSecAutolearnTrigger OBJECT-TYPE

	SYNTAX INTEGER {

		autolearn(1),

		no-autolearn(2)

		}

	ACCESS read-write

	STATUS mandatory

	DESCRIPTION

		"When this object is set to autolearn(1) then the nMM

		will capture a snapshot of its MAC address cache for those

		ports whose 'AutolearnMask' object is disabled(2).

		This snapshot may be investigated and modified via the

		'LearnTable' (see below).  The snapshot of addresses may

		be downloaded to the Security Module via the 'Download'

		object (see below)."

	::= { olNetOlSecAutolearn 1 }



olNetOlSecAutolearnDownload OBJECT-TYPE

	SYNTAX INTEGER {

		download-addresses(1),

		no-download(2)

		}

	ACCESS read-write

	STATUS mandatory

	DESCRIPTION

		"When this object is set to download-addresses(1) then the

		nMM will download its snapshot of addresses to the Security

		Module."

	::= { olNetOlSecAutolearn 2 }





olNetOlSecLearnTable OBJECT-TYPE

	SYNTAX SEQUENCE OF OlNetOlSecLearnEntry

	ACCESS not-accessible

	STATUS mandatory

	DESCRIPTION

		"A table of security MAC addresses which have been autolearned

		on the nMM by taking a snapshot of its MAC address cache."

	::= { olNetOlSec 4 }



olNetOlSecLearnEntry OBJECT-TYPE

	SYNTAX OlNetOlSecLearnEntry

	ACCESS not-accessible

	STATUS mandatory

	DESCRIPTION

		"Security MAC addresses which have been autolearned (indexed

		by slot, port, and address)."

	INDEX { olNetOlSecLearnSlotIndex, olNetOlSecLearnPortIndex,

		olNetOlSecLearnAddress }

	::= { olNetOlSecLearnTable 1 }



OlNetOlSecLearnEntry ::=

	SEQUENCE {

		olNetOlSecLearnSlotIndex

			INTEGER,

		olNetOlSecLearnPortIndex

			INTEGER,

		olNetOlSecLearnAddress

			MacAddress,

		olNetOlSecLearnStatus

			INTEGER

		}



olNetOlSecLearnSlotIndex OBJECT-TYPE

	SYNTAX INTEGER

	ACCESS read-only

	STATUS mandatory

	DESCRIPTION

		"The slot number index (used along with the port and address

		indices)."

	::= { olNetOlSecLearnEntry 1 }



olNetOlSecLearnPortIndex OBJECT-TYPE

	SYNTAX INTEGER

	ACCESS read-only

	STATUS mandatory

	DESCRIPTION

		"The port number index (used along with the slot and address

		indices)."

	::= { olNetOlSecLearnEntry 2 }



olNetOlSecLearnAddress OBJECT-TYPE

	SYNTAX MacAddress

	ACCESS read-write

	STATUS mandatory

	DESCRIPTION

		"The security MAC address index (used along with the slot and

		port indices).  Note that there may be multiple addresses per

		port."

	::= { olNetOlSecLearnEntry 3 }



olNetOlSecLearnStatus OBJECT-TYPE

	SYNTAX INTEGER {

		valid(1),

		invalid(2)

		}

	ACCESS read-write

	STATUS mandatory

	DESCRIPTION

		"Setting this object to valid(1) will cause the

		corresponding security MAC address to be included in

		the snapshot of autolearned addresses.  Setting this

		object to invalid(2) will clear the corresponding MAC

		address from the snapshot of autolearned addresses."

	::= { olNetOlSecLearnEntry 4 }





olNetOlSecIntruderTable OBJECT-TYPE

	SYNTAX SEQUENCE OF OlNetOlSecIntruderEntry

	ACCESS not-accessible

	STATUS mandatory

	DESCRIPTION

		"A table of entries which describe Intrusion Security

		breach attempts.  This table contains the same info as

		the following table, the difference being that this table

		is indexed by time only and the other is indexed by slot.

		port.time."

	::= { olNetOlSec 5 }



olNetOlSecIntruderEntry OBJECT-TYPE

	SYNTAX OlNetOlSecIntruderEntry

	ACCESS not-accessible

	STATUS mandatory

	DESCRIPTION

		"A table of entries which describe Intrusion Security

		breach attempts.  The index is simply the chronological

		order in which the attempt occurred; e.g. index 1

		corresponds to the first intrusion attempt, index 2

		to the next one, and so on.  Note that the the oldest

		entry will be deleted automatically when a new entry is

		added to a full table."

	INDEX { olNetOlSecIntruderChronIndex }

	::= { olNetOlSecIntruderTable 1 }



OlNetOlSecIntruderEntry ::=

	SEQUENCE {

		olNetOlSecIntruderChronIndex

			INTEGER,

		olNetOlSecIntruderSlot

			INTEGER,

		olNetOlSecIntruderPort

			INTEGER,

		olNetOlSecIntruderAddress

			MacAddress,

		olNetOlSecIntruderTimeSince

			TimeTicks,

		olNetOlSecIntruderDisabled

			INTEGER

		}



olNetOlSecIntruderChronIndex OBJECT-TYPE

	SYNTAX INTEGER

	ACCESS read-only

	STATUS mandatory

	DESCRIPTION

		"The chronological index into the Intruder Table.  An index of

		1 corresponds to the first Intrusion Security breach attempt,

		an index of 2 corresponds to the next attempt, etc.  Note

		that the oldest entry will be deleted automatically when a

		new entry is added to a full table."

	::= { olNetOlSecIntruderEntry 1 }



olNetOlSecIntruderSlot OBJECT-TYPE

	SYNTAX INTEGER

	ACCESS read-only

	STATUS mandatory

	DESCRIPTION

		"The slot number on which the intrusion attempt occurred."

	::= { olNetOlSecIntruderEntry 2 }



olNetOlSecIntruderPort OBJECT-TYPE

	SYNTAX INTEGER

	ACCESS read-only

	STATUS mandatory

	DESCRIPTION

		"The port number on which the intrusion attempt occurred."

	::= { olNetOlSecIntruderEntry 3 }



olNetOlSecIntruderAddress OBJECT-TYPE

	SYNTAX MacAddress

	ACCESS read-only

	STATUS mandatory

	DESCRIPTION

		"The address of the intruder, if known.  If it is not known then

		this object will equal all zeroes."

	::= { olNetOlSecIntruderEntry 4 }



olNetOlSecIntruderTimeSince OBJECT-TYPE

	SYNTAX TimeTicks

	ACCESS read-only

	STATUS mandatory

	DESCRIPTION

		"The time in hundredths of a second since the Intrusion Security

		breach attempt took place.  For example, if it is equal to 500

		ticks then the intrusion attempt occurred 5 seconds ago."

	::= { olNetOlSecIntruderEntry 5 }



olNetOlSecIntruderDisabled OBJECT-TYPE

	SYNTAX INTEGER {

		auto-disabled(1),

		not-auto-disabled(2)

		}

	ACCESS read-only

	STATUS mandatory

	DESCRIPTION

		"This object indicates whether the port on which the intrusion

		attempt took place was automatically disabled."

	::= { olNetOlSecIntruderEntry 6 }





olNetOlSecPortIntrTable OBJECT-TYPE

	SYNTAX SEQUENCE OF OlNetOlSecPortIntrEntry

	ACCESS not-accessible

	STATUS mandatory

	DESCRIPTION

		"A table of entries which describe Intrusion Security

		breach attempts.  This table contains the same info as

		the previous table, the difference being the indices used

		to access the data."

	::= { olNetOlSec 6 }



olNetOlSecPortIntrEntry OBJECT-TYPE

	SYNTAX OlNetOlSecPortIntrEntry

	ACCESS not-accessible

	STATUS mandatory

	DESCRIPTION

		"A table of entries which describe Intrusion Security

		breach attempts.  The indices are the slot, port, and

		chronological order in time of the intrusion attempt."

	INDEX { olNetOlSecPortIntrSlotIndex, olNetOlSecPortIntrPortIndex,

		  olNetOlSecPortIntrChronIndex }

	::= { olNetOlSecPortIntrTable 1 }



OlNetOlSecPortIntrEntry ::=

	SEQUENCE {

		olNetOlSecPortIntrSlotIndex

			INTEGER,

		olNetOlSecPortIntrPortIndex

			INTEGER,

		olNetOlSecPortIntrChronIndex

			INTEGER,

		olNetOlSecPortIntrAddress

			MacAddress,

		olNetOlSecPortIntrTimeSince

			TimeTicks,

		olNetOlSecPortIntrDisabled

			INTEGER

		}



olNetOlSecPortIntrSlotIndex OBJECT-TYPE

	SYNTAX INTEGER

	ACCESS read-only

	STATUS mandatory

	DESCRIPTION

		"The slot number on which the intrusion attempt occurred."

	::= { olNetOlSecPortIntrEntry 1 }



olNetOlSecPortIntrPortIndex OBJECT-TYPE

	SYNTAX INTEGER

	ACCESS read-only

	STATUS mandatory

	DESCRIPTION

		"The port number on which the intrusion attempt occurred."

	::= { olNetOlSecPortIntrEntry 2 }



olNetOlSecPortIntrChronIndex OBJECT-TYPE

	SYNTAX INTEGER

	ACCESS read-only

	STATUS mandatory

	DESCRIPTION

		"The chronological index into the Intruder Table.  An index of

		1 corresponds to the first Intrusion Security breach attempt

		for that port, an index of 2 corresponds to the next attempt,

		etc.  Note that the oldest overall entry (regardless of slot

		and port) will be deleted automatically when a new entry is

		added to a full table."

	::= { olNetOlSecPortIntrEntry 3 }



olNetOlSecPortIntrAddress OBJECT-TYPE

	SYNTAX MacAddress

	ACCESS read-only

	STATUS mandatory

	DESCRIPTION

		"The address of the intruder, if known.  If it is not known then

		this object will equal all zeroes."

	::= { olNetOlSecPortIntrEntry 4 }



olNetOlSecPortIntrTimeSince OBJECT-TYPE

	SYNTAX TimeTicks

	ACCESS read-only

	STATUS mandatory

	DESCRIPTION

		"The time in hundredths of a second since the Intrusion Security

		breach attempt took place.  For example, if it is equal to 500

		ticks then the intrusion attempt occurred 5 seconds ago."

	::= { olNetOlSecPortIntrEntry 5 }



olNetOlSecPortIntrDisabled OBJECT-TYPE

	SYNTAX INTEGER {

		auto-disabled(1),

		not-auto-disabled(2)

		}

	ACCESS read-only

	STATUS mandatory

	DESCRIPTION

		"This object indicates whether the port on which the intrusion

		attempt took place was automatically disabled."

	::= { olNetOlSecPortIntrEntry 6 }





olNetOlSecTrap  OBJECT IDENTIFIER ::= { olNetOlSec 7 }



olNetOlSecTrapReason OBJECT-TYPE

	SYNTAX INTEGER {

		not-applicable(1),

		intrusion-attempt(2)

		}

	ACCESS read-only

	STATUS mandatory

	DESCRIPTION

		"This object is included in security traps to specify the

		reason for the trap.  When this object is read it will represent

		the reason for the most recently generated security trap.  If

		this object is read before any security traps have been generated

		then the value not-applicable(1) will be returned."

	::= { olNetOlSecTrap 1 }









-- The olEnet Group



-- This group represents information about Ethernet networks.



olEnetStatsTable OBJECT-TYPE

	SYNTAX SEQUENCE OF OlEnetStatsEntry

	ACCESS not-accessible

	STATUS mandatory

	DESCRIPTION

		"A table that contains statistical information about

		Ethernet (IEEE 802.3) networks."

	::= { olEnet 1 }



olEnetStatsEntry OBJECT-TYPE

	SYNTAX OlEnetStatsEntry

	ACCESS not-accessible

	STATUS mandatory

	DESCRIPTION

		"A list of statistical information about each Ethernet

		(IEEE 802.3) network in the concentrator."

	INDEX { olEnetStatsNetID }

	::= { olEnetStatsTable 1 }



OlEnetStatsEntry ::=

	SEQUENCE {

		olEnetStatsNetID

			INTEGER,

		olEnetStatsFramesRcvdOks

			Counter,

		olEnetStatsOctetsRcvdOks

			Counter,

		olEnetStatsMcastRcvdOks

			Counter,

		olEnetStatsBcastRcvdOks

			Counter,

		olEnetStatsFrameTooLongs

			Counter,

		olEnetStatsAlignmentErrors

			Counter,

		olEnetStatsFCSErrors

			Counter,

		olEnetStatsRunts

			Counter,

		olEnetStatsLocalColls

			Counter,

		olEnetStatsDropEvents

			Counter

		}



olEnetStatsNetID OBJECT-TYPE

	SYNTAX INTEGER {

		ethernet-1(6), -- corresponds to ifIndex

		ethernet-2(7),

		ethernet-3(8),

		ethernet-4(32),

		ethernet-5(33),

		ethernet-6(34),

		ethernet-7(35),

		ethernet-8(36)

		}

	ACCESS read-only

	STATUS mandatory

	DESCRIPTION

		"The network index that uniquely identifies this network."

	::= { olEnetStatsEntry 1 }



olEnetStatsFramesRcvdOks OBJECT-TYPE

	SYNTAX Counter

	ACCESS read-only

	STATUS mandatory

	DESCRIPTION

		"The count of frames that were successfully received by this

		network.  This counter does not include frames received

		in error."

	::= { olEnetStatsEntry 2 }



olEnetStatsOctetsRcvdOks OBJECT-TYPE

	SYNTAX Counter

	ACCESS read-only

	STATUS mandatory

	DESCRIPTION

		"The count of the number of octets that were successfully

		received by this network.  This counter does not include

		octets that were part of frames that were received in error."

	::= { olEnetStatsEntry 3 }



olEnetStatsMcastRcvdOks OBJECT-TYPE

	SYNTAX Counter

	ACCESS read-only

	STATUS mandatory

	DESCRIPTION

		"The count of the number of multicast frames successfully

		received by this network."

	::= { olEnetStatsEntry 4 }



olEnetStatsBcastRcvdOks OBJECT-TYPE

	SYNTAX Counter

	ACCESS read-only

	STATUS mandatory

	DESCRIPTION

		"The count of the number of broadcast frames successfully

		received by this network."

	::= { olEnetStatsEntry 5 }



olEnetStatsFrameTooLongs OBJECT-TYPE

	SYNTAX Counter

	ACCESS read-only

	STATUS mandatory

	DESCRIPTION

		"The count of the number of frames received by this network

		that exceeds the maximum permitted Ethernet (802.3) frame

		size."

	::= { olEnetStatsEntry 6 }



olEnetStatsAlignmentErrors OBJECT-TYPE

	SYNTAX Counter

	ACCESS read-only

	STATUS mandatory

	DESCRIPTION

		"The count of the number of frames received by this network

		that did not pass the frame check sequence (FCS) check

		and that are not an integral number of octets.  These

		frames are not counted in olEnetStatsFCSErrors."

	::= { olEnetStatsEntry 7 }



olEnetStatsFCSErrors OBJECT-TYPE

	SYNTAX Counter

	ACCESS read-only

	STATUS mandatory

	DESCRIPTION

		"The count of the number of frames received by this network

		that did not pass the frame check sequence (FCS) check

		and are an integral number of octets."

	::= { olEnetStatsEntry 8 }



olEnetStatsRunts OBJECT-TYPE

	SYNTAX Counter

	ACCESS read-only

	STATUS mandatory

	DESCRIPTION

		"The count of the number of frames received by this network

		 that are less than 512 bits long.  "

	::= { olEnetStatsEntry 9 }



olEnetStatsLocalColls OBJECT-TYPE

	SYNTAX Counter

	ACCESS read-only

	STATUS mandatory

	DESCRIPTION

		"The count of the number of times that two or more ports

		within this concentrator have received traffic simultaneously."

	::= { olEnetStatsEntry 10 }



olEnetStatsDropEvents OBJECT-TYPE

	SYNTAX Counter

	ACCESS read-only

	STATUS mandatory

	DESCRIPTION

		"The total number of events in which frames were dropped

		due to lack of resources.  Note that this number is not

		necessarily the number of frames dropped; it is just

		the number of times this condition has been detected."

	::= { olEnetStatsEntry 11 }





olEnetStatsModTable OBJECT-TYPE

	SYNTAX SEQUENCE OF OlEnetStatsModEntry

	ACCESS not-accessible

	STATUS mandatory

	DESCRIPTION

		"A table of statistical information counted for each module

		in each Ethernet (IEEE 802.3) network."

	::= { olEnet 2 }



olEnetStatsModEntry OBJECT-TYPE

	SYNTAX OlEnetStatsModEntry

	ACCESS not-accessible

	STATUS mandatory

	DESCRIPTION

		"A list of statistical information for each port

		on each Ethernet (IEEE 802.3) network in the concentrator."

	INDEX { olEnetStatsModNetID, olEnetStatsModSlotIndex }

	::= { olEnetStatsModTable 1 }



OlEnetStatsModEntry ::=

	SEQUENCE {

		olEnetStatsModNetID

			INTEGER,

		olEnetStatsModSlotIndex

			INTEGER,

		olEnetStatsModFramesRcvdOks

			Counter,

		olEnetStatsModOctetsRcvdOks

			Counter,

		olEnetStatsModMcastRcvdOks

			Counter,

		olEnetStatsModBcastRcvdOks

			Counter,

		olEnetStatsModFrameTooLongs

			Counter,

		olEnetStatsModAlignmentErrors

			Counter,

		olEnetStatsModFCSErrors

			Counter,

		olEnetStatsModRunts

			Counter

		}



olEnetStatsModNetID OBJECT-TYPE

	SYNTAX INTEGER {

		ethernet-1(6), -- corresponds to ifIndex

		ethernet-2(7),

		ethernet-3(8)

		}

	ACCESS read-only

	STATUS mandatory

	DESCRIPTION

		"The unique identifier for this network."

	::= { olEnetStatsModEntry 1 }



olEnetStatsModSlotIndex OBJECT-TYPE

	SYNTAX INTEGER

	ACCESS read-only

	STATUS mandatory

	DESCRIPTION

		"The slot number that contains this module."

	::= { olEnetStatsModEntry 2 }



olEnetStatsModFramesRcvdOks OBJECT-TYPE

	SYNTAX Counter

	ACCESS read-only

	STATUS mandatory

	DESCRIPTION

		"The count of frames that were successfully received by this

		module.  This counter does not include frames received in

		error."

	::= { olEnetStatsModEntry 3 }



olEnetStatsModOctetsRcvdOks OBJECT-TYPE

	SYNTAX Counter

	ACCESS read-only

	STATUS mandatory

	DESCRIPTION

		"The count of the number of octets that were successfully

		received by this module.  This counter does not include

		octets that were part of frames that were received in error."

	::= { olEnetStatsModEntry 4 }



olEnetStatsModMcastRcvdOks OBJECT-TYPE

	SYNTAX Counter

	ACCESS read-only

	STATUS mandatory

	DESCRIPTION

		"The count of the number of multicast frames successfully

		received by this module."

	::= { olEnetStatsModEntry 5 }



olEnetStatsModBcastRcvdOks OBJECT-TYPE

	SYNTAX Counter

	ACCESS read-only

	STATUS mandatory

	DESCRIPTION

		"The count of the number of broadcast frames successfully

		received by this module."

	::= { olEnetStatsModEntry 6 }



olEnetStatsModFrameTooLongs OBJECT-TYPE

	SYNTAX Counter

	ACCESS read-only

	STATUS mandatory

	DESCRIPTION

		"The count of the number of frames received by this module

		that exceeds the maximum permitted Ethernet (802.3) frame

		size."

	::= { olEnetStatsModEntry 7 }



olEnetStatsModAlignmentErrors OBJECT-TYPE

	SYNTAX Counter

	ACCESS read-only

	STATUS mandatory

	DESCRIPTION

		"The count of the number of frames received by this module

		that did not pass the frame check sequence (FCS) check

		and that are not an integral number of octets.  These

		frames are not counted in olEnetStatsModFCSErrors."

	::= { olEnetStatsModEntry 8 }



olEnetStatsModFCSErrors OBJECT-TYPE

	SYNTAX Counter

	ACCESS read-only

	STATUS mandatory

	DESCRIPTION

		"The count of the number of frames received by this module

		that did not pass the frame check sequence (FCS) check

		and are an integral number of octets."

	::= { olEnetStatsModEntry 9 }



olEnetStatsModRunts OBJECT-TYPE

	SYNTAX Counter

	ACCESS read-only

	STATUS mandatory

	DESCRIPTION

		"The count of the number of frames received by

		this module that are less than 512 bits long.  "

	::= { olEnetStatsModEntry 10 }





olEnetStatsPortTable OBJECT-TYPE

	SYNTAX SEQUENCE OF OlEnetStatsPortEntry

	ACCESS not-accessible

	STATUS mandatory

	DESCRIPTION

		"A table of statistical information counted for each port

		in each Ethernet (IEEE 802.3) network."

	::= { olEnet 3 }



olEnetStatsPortEntry OBJECT-TYPE

	SYNTAX OlEnetStatsPortEntry

	ACCESS not-accessible

	STATUS mandatory

	DESCRIPTION

		"A list of statistical information for each port

		on each Ethernet (IEEE 802.3) network in the concentrator."

	INDEX { olEnetStatsPortSlotIndex, olEnetStatsPortIndex }

	::= { olEnetStatsPortTable 1 }



OlEnetStatsPortEntry ::=

	SEQUENCE {

		olEnetStatsPortNetID

			INTEGER,

		olEnetStatsPortSlotIndex

			INTEGER,

		olEnetStatsPortIndex

			INTEGER,

		olEnetStatsPortFramesRcvdOks

			Counter,

		olEnetStatsPortOctetsRcvdOks

			Counter,

		olEnetStatsPortMcastRcvdOks

			 Counter,

		 olEnetStatsPortBcastRcvdOks

			 Counter,

		 olEnetStatsPortFrameTooLongs

			 Counter,

		 olEnetStatsPortAlignmentErrors

			 Counter,

		 olEnetStatsPortFCSErrors

			 Counter,

		 olEnetStatsPortRunts

			 Counter,

		 olEnetStatsPortSrcAddrChanges

			 Counter,

		 olEnetStatsPortLastSrcAddr

			 OCTET STRING (SIZE(6)),

		 olEnetStatsPortLastErrAddr

			 OCTET STRING (SIZE(6))

		 }



olEnetStatsPortNetID OBJECT-TYPE

	 SYNTAX INTEGER {

		 ethernet-1(6), -- corresponds to ifIndex

		 ethernet-2(7),

		 ethernet-3(8),

		 ethernet-4(32),

		 ethernet-5(33),

		 ethernet-6(34),

		 ethernet-7(35),

		 ethernet-8(36)

		 }

	 ACCESS read-only

	 STATUS mandatory

	 DESCRIPTION

		 "The unique identifier for this network."

	 ::= { olEnetStatsPortEntry 1 }



olEnetStatsPortSlotIndex OBJECT-TYPE

	 SYNTAX INTEGER

	 ACCESS read-only

	 STATUS mandatory

	 DESCRIPTION

		 "The slot number that contains this port."

	 ::= { olEnetStatsPortEntry 2 }



olEnetStatsPortIndex OBJECT-TYPE

	 SYNTAX INTEGER

	 ACCESS read-only

	 STATUS mandatory

	 DESCRIPTION

		 "The port number within this slot."

	 ::= { olEnetStatsPortEntry 3 }



olEnetStatsPortFramesRcvdOks OBJECT-TYPE

	 SYNTAX Counter

	 ACCESS read-only

	 STATUS mandatory

	 DESCRIPTION

		 "The count of frames that were successfully received by this

		 port.  This counter does not include frames received in error."

	 ::= { olEnetStatsPortEntry 4 }



olEnetStatsPortOctetsRcvdOks OBJECT-TYPE

	 SYNTAX Counter

	 ACCESS read-only

	 STATUS mandatory

	 DESCRIPTION

		 "The count of the number of octets that were successfully

		 received by this port.  This counter does not include

		 octets that were part of frames that were received in error."

	 ::= { olEnetStatsPortEntry 5 }



olEnetStatsPortMcastRcvdOks OBJECT-TYPE

	 SYNTAX Counter

	 ACCESS read-only

	 STATUS mandatory

	 DESCRIPTION

		 "The count of the number of multicast frames successfully

		 received by this port."

	 ::= { olEnetStatsPortEntry 6 }



olEnetStatsPortBcastRcvdOks OBJECT-TYPE

	 SYNTAX Counter

	 ACCESS read-only

	 STATUS mandatory

	 DESCRIPTION

		 "The count of the number of broadcast frames successfully

		 received by this port."

	 ::= { olEnetStatsPortEntry 7 }



olEnetStatsPortFrameTooLongs OBJECT-TYPE

	 SYNTAX Counter

	 ACCESS read-only

	 STATUS mandatory

	 DESCRIPTION

		 "The count of the number of frames received by this port

		 that exceeds the maximum permitted Ethernet (802.3) frame

		 size."

	 ::= { olEnetStatsPortEntry 8 }



olEnetStatsPortAlignmentErrors OBJECT-TYPE

	 SYNTAX Counter

	 ACCESS read-only

	 STATUS mandatory

	 DESCRIPTION

		 "The count of the number of frames received by this port

		 that did not pass the frame check sequence (FCS) check

		 and that are not an integral number of octets.  These

		 frames are not counted in olEnetStatsPortFCSErrors."

	 ::= { olEnetStatsPortEntry 9 }



olEnetStatsPortFCSErrors OBJECT-TYPE

	 SYNTAX Counter

	 ACCESS read-only

	 STATUS mandatory

	 DESCRIPTION

		 "The count of the number of frames received by this port

		 that did not pass the frame check sequence (FCS) check

		 and are an integral number of octets."

	 ::= { olEnetStatsPortEntry 10 }



olEnetStatsPortRunts OBJECT-TYPE

	 SYNTAX Counter

	 ACCESS read-only

	 STATUS mandatory

	 DESCRIPTION

		 "The count of the number of frames received by this port that

		 are less than 512 bits long.  "

	 ::= { olEnetStatsPortEntry 11 }





olEnetStatsPortSrcAddrChanges OBJECT-TYPE

	 SYNTAX Counter

	 ACCESS read-only

	 STATUS mandatory

	 DESCRIPTION

		 "The count of the number of times that

		 olEnetStatsPortLastSourceAddr

		{ olEnetStatsPortEntry 11 } has changed."

	 ::= { olEnetStatsPortEntry 12 }



olEnetStatsPortLastSrcAddr OBJECT-TYPE

	 SYNTAX OCTET STRING (SIZE(6))

	 ACCESS read-only

	 STATUS mandatory

	 DESCRIPTION

		 "The last source address seen on this port for this

		 network for the last successfully received frame."

	 ::= { olEnetStatsPortEntry 13 }



olEnetStatsPortLastErrAddr OBJECT-TYPE

	 SYNTAX OCTET STRING (SIZE(6))

	 ACCESS read-only

	 STATUS mandatory

	 DESCRIPTION

		 "The value stored in the source address portion of

		 a frame received in error (alignment, FCS, or too long).

		 Since the frame was received in error, there is no

		 guarantee that this is an actual valid address."

	 ::= { olEnetStatsPortEntry 14 }



olEnetMapTable OBJECT-TYPE

	 SYNTAX SEQUENCE OF OlEnetMapEntry

	 ACCESS not-accessible

	 STATUS mandatory

	 DESCRIPTION

		 "A table that contains a cache of information relating

		 an Ethernet source address with a specific port for

		 a given network.  An indication of this source's utilization

		 of the network is also provided."

	 ::= { olEnet 4 }



olEnetMapEntry OBJECT-TYPE

	 SYNTAX OlEnetMapEntry

	 ACCESS not-accessible

	 STATUS mandatory

	 DESCRIPTION

		 "A list of information that tracks a source address to

		 a specific port for each network."

	 INDEX { olEnetMapNetID, olEnetMapAddress }

	 ::= { olEnetMapTable 1 }



OlEnetMapEntry ::=

	 SEQUENCE {

		 olEnetMapNetID

			 INTEGER,

		 olEnetMapAddress

			 OCTET STRING,

		 olEnetMapSlotIndex

			 INTEGER,

		 olEnetMapPortIndex

			 INTEGER,

		 olEnetMapFrames

			 Counter,

		 olEnetMapOctets

			 Counter,

		 olEnetMapTime

			 TimeTicks

		 }



olEnetMapNetID OBJECT-TYPE

	 SYNTAX INTEGER {

		 ethernet-1(6),  -- corresponds to ifIndex

		 ethernet-2(7),

		 ethernet-3(8),

		 ethernet-4(32),

		 ethernet-5(33),

		 ethernet-6(34),

		 ethernet-7(35),

		 ethernet-8(36)

		 }

	 ACCESS read-only

	 STATUS mandatory

	 DESCRIPTION

		 "The network index that uniquely identifies this network."

	 ::= { olEnetMapEntry 1 }



olEnetMapAddress OBJECT-TYPE

	 SYNTAX OCTET STRING (SIZE(6))

	 ACCESS read-only

	 STATUS mandatory

	 DESCRIPTION

		 "An Ethernet source address received by this port on this

		 network."

	 ::= { olEnetMapEntry 2 }



olEnetMapSlotIndex OBJECT-TYPE

	 SYNTAX INTEGER

	 ACCESS read-only

	 STATUS mandatory

	 DESCRIPTION

		 "The slot number of the port that received this address."

	 ::= { olEnetMapEntry 3 }





olEnetMapPortIndex OBJECT-TYPE

	 SYNTAX INTEGER

	 ACCESS read-only

	 STATUS mandatory

	 DESCRIPTION

		 "The port number within olEnetMapSlotIndex's slot that

		 received this address."

	 ::= { olEnetMapEntry 4 }



olEnetMapFrames OBJECT-TYPE

	 SYNTAX Counter

	 ACCESS read-only

	 STATUS mandatory

	 DESCRIPTION

		 "An estimated count of the number of frames generated by this

		 address.  This count should be interpreted as an

		 indicator, not a true frame count."

	 ::= { olEnetMapEntry 5 }



olEnetMapOctets OBJECT-TYPE

	 SYNTAX Counter

	 ACCESS read-only

	 STATUS mandatory

	 DESCRIPTION

		 "An estimated count of the number of octets generated by this

		 address.  This count should be interpreted as an

		 indicator, not a true octet count."

	 ::= { olEnetMapEntry 6 }



olEnetMapTime OBJECT-TYPE

	 SYNTAX TimeTicks

	 ACCESS read-only

	 STATUS mandatory

	 DESCRIPTION

		 "The time in in hundredths of a second since this address

		 was last seen.  For example, if olEnetMapTime is 500

		 ticks, then this adddress was seen 5 seconds ago."

	 ::= { olEnetMapEntry 7 }





chipSnmpDot3RptrMgt OBJECT IDENTIFIER ::= { olEnet 5 }









--			References

--

-- The following references are used throughout this MIB:

--

-- [IEEE 802.3 Std]

--    refers to IEEE 802.3/ISO 8802-3 Information processing

--    systems - Local area networks - Part 3: Carrier sense

--    multiple access with collision detection (CSMA/CD)

--    access method and physical layer specifications

--    (2nd edition, September 21, 1990).

--

-- [IEEE 802.3 Rptr Mgt]

--    refers to IEEE P802.3K, 'Layer Management for 10 Mb/s

--    Baseband Repeaters, Section 19,' Draft Supplement to

--    ANSI/IEEE 802.3, (Draft 8, April 9, 1992)





--			MIB Groups

--

-- The rptrBasicPackage group is mandatory.

-- The rptrMonitorPackage and rptrAddrTrackPackage

-- groups are optional.





chipRptrBasicPackage  OBJECT IDENTIFIER ::= { chipSnmpDot3RptrMgt 1 }



chipRptrMonitorPackage OBJECT IDENTIFIER ::= { chipSnmpDot3RptrMgt 2 }



chipRptrAddrTrackPackage OBJECT IDENTIFIER ::= { chipSnmpDot3RptrMgt 3 }





-- object identifiers for organizing the information

-- in the groups by repeater, port-group, and port



chipRptrRptrInfo OBJECT IDENTIFIER ::= { chipRptrBasicPackage 1 }

chipRptrGroupInfo OBJECT IDENTIFIER ::= { chipRptrBasicPackage 2 }

chipRptrPortInfo OBJECT IDENTIFIER ::= { chipRptrBasicPackage 3 }



chipRptrMonitorRptrInfo OBJECT IDENTIFIER ::= { chipRptrMonitorPackage 1 }

chipRptrMonitorGroupInfo OBJECT IDENTIFIER ::= { chipRptrMonitorPackage 2 }



chipRptrMonitorPortInfo OBJECT IDENTIFIER ::= { chipRptrMonitorPackage 3 }



-- this subtree is currently unused

chipRptrAddrTrackRptrInfo  OBJECT IDENTIFIER ::= { chipRptrAddrTrackPackage 1 }



-- this subtree is currently unused

chipRptrAddrTrackGroupInfo OBJECT IDENTIFIER ::= { chipRptrAddrTrackPackage 2 }

chipRptrAddrTrackPortInfo OBJECT IDENTIFIER ::= { chipRptrAddrTrackPackage 3 }



--

--		      The BASIC GROUP

--

-- Implementation of the Basic Group is mandatory for all

-- managed repeaters.





--

-- Basic Repeater Information

--

-- Configuration, status, and control objects for the overall

-- repeater

--

chipRptrRptrInfoTable OBJECT-TYPE

       SYNTAX	 SEQUENCE OF ChipRptrRptrInfoEntry

       ACCESS	 not-accessible

       STATUS	 mandatory

       DESCRIPTION

	       "Table of descriptive and status information about

	       the repeater."

       ::= { chipRptrRptrInfo 1 }



chipRptrRptrInfoEntry OBJECT-TYPE

       SYNTAX	 ChipRptrRptrInfoEntry

       ACCESS	 not-accessible

       STATUS	 mandatory

       DESCRIPTION

	       "An entry in the table, containing information

	       about a repeater."

       INDEX	{ chipRptrRptrInfoSlotIndex, chipRptrRptrInfoNetID }

       ::= { chipRptrRptrInfoTable 1 }



ChipRptrRptrInfoEntry ::=

       SEQUENCE {

	  chipRptrRptrInfoSlotIndex

	       INTEGER,

	   chipRptrRptrInfoNetID

	       INTEGER,

	   chipRptrGroupCapacity

	       INTEGER,

	   chipRptrOperStatus

	       INTEGER,

	   chipRptrHealthText

	       DisplayString,

	   chipRptrReset

	       INTEGER,

	   chipRptrNonDisruptTest

	       INTEGER,

	   chipRptrTotalPartitionedPorts

	       Gauge

       }





chipRptrRptrInfoSlotIndex OBJECT-TYPE

	SYNTAX INTEGER {

		slot-1(1),

		slot-2(2),

		slot-3(3),

		slot-4(4),

		slot-5(5),

		slot-6(6),

		slot-7(7),

		slot-8(8),

		slot-9(9),

		slot-10(10),

		slot-11(11),

		slot-12(12),

		slot-13(13),

		slot-14(14),

		slot-15(15),

		slot-16(16),

		slot-17(17),

		backplane(255)

		}

	ACCESS read-only

	STATUS mandatory

	DESCRIPTION

		"The slot number of the repeater module on which

		the isolated network identified by chipRptrRptrInfoNetID

		resides. If chipRptrRptrInfoNetID does not identify

		an isolated network, then the value of this object is

		backplane(255)."

	::= {chipRptrRptrInfoEntry  1 }



chipRptrRptrInfoNetID OBJECT-TYPE

	 SYNTAX INTEGER {



		 ethernet-1(6),

		 ethernet-2(7),

		 ethernet-3(8),



		 ethernet-4(32),

		 ethernet-5(33),

		 ethernet-6(34),

		 ethernet-7(35),

		 ethernet-8(36)

		 }

	 ACCESS read-only

	 STATUS mandatory

	 DESCRIPTION

		 "The network index that uniquely identifies this repeater."

       ::= { chipRptrRptrInfoEntry 2 }



chipRptrGroupCapacity OBJECT-TYPE

       SYNTAX	 INTEGER (1..1024)

       ACCESS	 read-only

       STATUS	 mandatory

       DESCRIPTION

		      "The chipRptrGroupCapacity is the number of groups

		      that can be contained within the repeater.  Within

		      each managed repeater, the groups are uniquely

		      numbered in the range from 1 to chipRptrGroupCapacity.



		      Some groups may not be present in the repeater, in

		      which case the actual number of groups present

		      will be less than chipRptrGroupCapacity.  The number

		      of groups present will never be greater than

		      chipRptrGroupCapacity.



		      Note:  In practice, this will generally be the

		      number of field-replaceable units (i.e., modules,

		      cards, or boards) that can fit in the physical

		      repeater enclosure, and the group numbers will

		      correspond to numbers marked on the physical

		      enclosure."

   REFERENCE

	       "Reference IEEE 802.3 Rptr Mgt, 19.2.3.2,

	       aRepeaterGroupCapacity."



   ::= { chipRptrRptrInfoEntry 3 }



chipRptrOperStatus OBJECT-TYPE

       SYNTAX  INTEGER {

		   other(1),		-- undefined or unknown status

		   ok(2),		-- no known failures

		   rptrFailure(3),	-- repeater-related failure

		   groupFailure(4),	-- group-related failure

		   portFailure(5),	-- port-related failure

		   generalFailure(6)	-- failure, unspecified type

	       }

       ACCESS	 read-only

       STATUS	 mandatory

       DESCRIPTION

	      "The chipRptrOperStatus object indicates the

	      operational state of the repeater.  The

	      chipRptrHealthText object may be consulted for more

	      specific information about the state of the

	      repeater's health.



	      In the case of multiple kinds of failures (e.g.,

	      repeater failure and port failure), the value of

	      this attribute shall reflect the highest priority

	      failure in the following order:



		   chipRptrFailure(3)

		   groupFailure(4)

		   portFailure(5)

		   generalFailure(6)."

       REFERENCE

	       "Reference IEEE 802.3 Rptr Mgt, 19.2.3.2,

	       aRepeaterHealthState."

       ::= { chipRptrRptrInfoEntry 4 }



chipRptrHealthText OBJECT-TYPE

       SYNTAX	 DisplayString (SIZE (0..255))

       ACCESS	 read-only

       STATUS	 mandatory

       DESCRIPTION

	       "The health text object is a text string that

	       provides information relevant to the operational

	       state of the repeater. Agents may use this string

	       to provide detailed information on current

	       failures, including how they were detected, and/or

	       instructions for problem resolution. The contents

	       are agent-specific."

       REFERENCE

	       "Reference IEEE 802.3 Rptr Mgt, 19.2.3.2,

	       aRepeaterHealthText."

       ::= { chipRptrRptrInfoEntry 5 }



chipRptrReset OBJECT-TYPE

       SYNTAX	 INTEGER {

		     noReset(1),

		     reset(2)

		 }

       ACCESS	 read-write

       STATUS	 mandatory

       DESCRIPTION

	       "Setting this object to reset(2) causes a

	       transition to the START state of Fig 9-2 in

	       section 9 [IEEE 802.3 Std].



	       Setting this object to noReset(1) has no effect.

	       The agent will always return the value noReset(1)

	       when this object is read.



	       This action does not reset the management counters

	       defined in this document nor does it affect the

	       portAdminStatus parameters.  Included in this

	       action is the execution of a disruptive Self-Test

	       with the following characteristics:  a) The nature

	       of the tests is not specified.  b) The test resets

	       the repeater but without affecting management

	       information about the repeater.  c) The test does

	       not inject packets onto any segment.  d) Packets

	       received during the test may or may not be

	       transferred.  e) The test does not interfere with

	       management functions.



	       As a result of this action a chipRptrResetEvent trap

	       should be sent."

       REFERENCE

	       "Reference IEEE 802.3 Rptr Mgt, 19.2.3.3,

	       acResetRepeater."

       ::= { chipRptrRptrInfoEntry 6 }



chipRptrNonDisruptTest OBJECT-TYPE

       SYNTAX	 INTEGER {

		     noSelfTest(1),

		     selfTest(2)

		 }

       ACCESS	 read-write

       STATUS	 mandatory

       DESCRIPTION

	       "Setting this object to selfTest(2) causes the



	       repeater to perform a agent-specific, non-

	       disruptive self-test that has the following

	       characteristics:  a) The nature of the tests is

	       not specified.  b) The test does not change the

	       state of the repeater or management information

	       about the repeater.  c) The test does not inject

	       packets onto any segment.  d) The test does not

	       prevent the relay of any packets.  e) The test

	       does not interfere with management functions.



	       After performing this test the agent will update

	       the repeater health information and send a

	       chipRptrHealth trap.



	       Setting this object to noSelfTest(1) has no

	       effect.  The agent will always return the value

	       noSelfTest(1) when this object is read."

       REFERENCE

	       "Reference IEEE 802.3 Rptr Mgt, 19.2.3.3,

	       acExecuteNonDisruptiveSelfTest."

       ::= { chipRptrRptrInfoEntry 7 }



chipRptrTotalPartitionedPorts OBJECT-TYPE

       SYNTAX	 Gauge

       ACCESS	 read-only

       STATUS	 mandatory

       DESCRIPTION

	       "This object returns the total number of ports in

	       the repeater whose current state meets all three

	       of the following criteria:  chipRptrPortOperStatus

	       does not have the value notPresent(3),

	       chipRptrPortAdminStatus is enabled(1), and

	       chipRptrPortAutoPartitionState is autoPartitioned(2)."

       ::= { chipRptrRptrInfoEntry 8 }



--

-- The Basic Port Group Table

--



chipRptrGroupTable OBJECT-TYPE

       SYNTAX	 SEQUENCE OF ChipRptrGroupEntry

       ACCESS	 not-accessible

       STATUS	 mandatory

       DESCRIPTION

	       "Table of descriptive and status information about

	       the groups of ports."

       ::= { chipRptrGroupInfo 1 }



chipRptrGroupEntry OBJECT-TYPE

       SYNTAX	 ChipRptrGroupEntry

       ACCESS	 not-accessible

       STATUS	 mandatory

       DESCRIPTION

	       "An entry in the table, containing information

	       about a single group of ports."

       INDEX	{ chipRptrGroupSlotIndex, chipRptrGroupNetID, chipRptrGroupIndex }

       ::= { chipRptrGroupTable 1 }



ChipRptrGroupEntry ::=

       SEQUENCE {

	   chipRptrGroupSlotIndex

	       INTEGER,

	   chipRptrGroupNetID

	       INTEGER,

	   chipRptrGroupIndex

	       INTEGER,

	   chipRptrGroupDescr

	       DisplayString,

	   chipRptrGroupObjectID

	       OBJECT IDENTIFIER,

	   chipRptrGroupOperStatus

	       INTEGER,

	   chipRptrGroupLastOperStatusChange

	       TimeTicks,

	   chipRptrGroupPortCapacity

	       INTEGER

       }





chipRptrGroupSlotIndex OBJECT-TYPE

	SYNTAX INTEGER {

		slot-1(1),

		slot-2(2),

		slot-3(3),

		slot-4(4),

		slot-5(5),

		slot-6(6),

		slot-7(7),

		slot-8(8),

		slot-9(9),

		slot-10(10),

		slot-11(11),

		slot-12(12),

		slot-13(13),

		slot-14(14),

		slot-15(15),

		slot-16(16),

		slot-17(17),

		backplane(255)

		}

	ACCESS read-only

	STATUS mandatory

	DESCRIPTION

		"The slot number of the repeater module on which

		the isolated network identified by chipRptrGroupNetID

		resides. If chipRptrGroupNetID does not identify

		an isolated network, then the value of this object is

		backplane(255)."

	::= {chipRptrGroupEntry 1 }



chipRptrGroupNetID OBJECT-TYPE

	 SYNTAX INTEGER {



		 ethernet-1(6),

		 ethernet-2(7),

		 ethernet-3(8),



		 ethernet-4(32),

		 ethernet-5(33),

		 ethernet-6(34),

		 ethernet-7(35),

		 ethernet-8(36)

		 }

	 ACCESS read-only

	 STATUS mandatory

	 DESCRIPTION

		 "The network index that uniquely identifies this group's repeater."

       ::= { chipRptrGroupEntry 2 }



chipRptrGroupIndex OBJECT-TYPE

       SYNTAX	 INTEGER (1..1024)

       ACCESS	 read-only

       STATUS	 mandatory

       DESCRIPTION

	       "This object identifies the group within the

	       repeater for which this entry contains

	       information.  This value is never greater than

	       chipRptrGroupCapacity."

       REFERENCE

	       "Reference IEEE 802.3 Rptr Mgt, 19.2.5.2,

	       aGroupID."

       ::= { chipRptrGroupEntry 3 }



chipRptrGroupDescr OBJECT-TYPE

       SYNTAX	 DisplayString (SIZE (0..255))

       ACCESS	 read-only

       STATUS	 mandatory

       DESCRIPTION

	       "A textual description of the group.  This value

	       should include the full name and version

	       identification of the group's hardware type and



	       indicate how the group is differentiated from

	       other groups in the repeater.  Plug-in Module, Rev

	       A' or 'Barney Rubble 10BASE-T 4-port SIMM socket

	       Version 2.1' are examples of valid group

	       descriptions.



	       It is mandatory that this only contain printable

	       ASCII characters."

       ::= { chipRptrGroupEntry 4 }



chipRptrGroupObjectID OBJECT-TYPE

       SYNTAX	 OBJECT IDENTIFIER

       ACCESS	 read-only

       STATUS	 mandatory

       DESCRIPTION

	       "The vendor's authoritative identification of the

	       group.  This value is allocated within the SMI

	       enterprises subtree (1.3.6.1.4.1) and provides a

	       straight-forward and unambiguous means for

	       determining what kind of group is being managed.



	       For example, this object could take the value

	       1.3.6.1.4.1.4242.1.2.14 if vendor 'Flintstones,

	       Inc.' was assigned the subtree 1.3.6.1.4.1.4242,

	       and had assigned the identifier

	       1.3.6.1.4.1.4242.1.2.14 to its 'Wilma Flintstone

	       6-Port FOIRL Plug-in Module.'"

       ::= { chipRptrGroupEntry 5 }



chipRptrGroupOperStatus OBJECT-TYPE

       SYNTAX	 INTEGER {

		     other(1),

		     operational(2),

		     malfunctioning(3),

		     notPresent(4),

		     underTest(5),

		     resetInProgress(6)

		 }

       ACCESS	 read-only

       STATUS	 mandatory

       DESCRIPTION

	       "An object that indicates the operational status

	       of the group.



	       A status of notPresent(4) indicates that the group

	       is temporarily or permanently physically and/or

	       logically not a part of the repeater.  It is an

	       implementation-specific matter as to whether the



	       agent effectively removes notPresent entries from

	       the table.



	       A status of operational(2) indicates that the

	       group is functioning, and a status of

	       malfunctioning(3) indicates that the group is

	       malfunctioning in some way."

       ::= { chipRptrGroupEntry 6 }



chipRptrGroupLastOperStatusChange OBJECT-TYPE

       SYNTAX	 TimeTicks

       ACCESS	 read-only

       STATUS	 mandatory

       DESCRIPTION

	       "An object that contains the value of sysUpTime at

	       the time that the value of the chipRptrGroupOperStatus

	       object for this group last changed.



	       A value of zero indicates that the group's oper

	       status has not changed since the agent last

	       restarted."

       ::= { chipRptrGroupEntry 7 }



chipRptrGroupPortCapacity OBJECT-TYPE

       SYNTAX	 INTEGER (1..1024)

       ACCESS	 read-only

       STATUS	 mandatory

       DESCRIPTION

	       "The chipRptrGroupPortCapacity is the number of ports

	       that can be contained within the group.  Valid

	       range is 1-1024.  Within each group, the ports are

	       uniquely numbered in the range from 1 to

	       chipRptrGroupPortCapacity.



	       Note:  In practice, this will generally be the

	       number of ports on a module, card, or board, and

	       the port numbers will correspond to numbers marked

	       on the physical embodiment."

       REFERENCE

	       "Reference IEEE 802.3 Rptr Mgt, 19.2.5.2,

	       aGroupPortCapacity."

       ::= { chipRptrGroupEntry 8 }







--

-- The Basic Port Table

--



chipRptrPortTable OBJECT-TYPE

       SYNTAX	 SEQUENCE OF ChipRptrPortEntry

       ACCESS	 not-accessible

       STATUS	 mandatory

       DESCRIPTION

	       "Table of descriptive and status information about

	       the ports."

       ::= { chipRptrPortInfo 1 }



chipRptrPortEntry OBJECT-TYPE

       SYNTAX	 ChipRptrPortEntry

       ACCESS	 not-accessible

       STATUS	 mandatory

       DESCRIPTION

	       "An entry in the table, containing information

	       about a single port."

       INDEX	{ chipRptrPortSlotIndex, chipRptrPortNetID, chipRptrPortGroupIndex, chipRptrPortIndex }

       ::= { chipRptrPortTable 1 }



ChipRptrPortEntry ::=

       SEQUENCE {

	   chipRptrPortSlotIndex

	       INTEGER,

	   chipRptrPortNetID

	       INTEGER,

	   chipRptrPortGroupIndex

	       INTEGER,

	   chipRptrPortIndex

	       INTEGER,

	   chipRptrPortAdminStatus

	       INTEGER,

	   chipRptrPortAutoPartitionState

	       INTEGER,

	   chipRptrPortOperStatus

	       INTEGER

       }





chipRptrPortSlotIndex OBJECT-TYPE

	SYNTAX INTEGER {

		slot-1(1),

		slot-2(2),

		slot-3(3),

		slot-4(4),

		slot-5(5),

		slot-6(6),

		slot-7(7),

		slot-8(8),

		slot-9(9),

		slot-10(10),

		slot-11(11),

		slot-12(12),

		slot-13(13),

		slot-14(14),

		slot-15(15),

		slot-16(16),

		slot-17(17),

		backplane(255)

		}

	ACCESS read-only

	STATUS mandatory

	DESCRIPTION

		"The slot number of the repeater module on which

		the isolated network identified by chipRptrPortNetID

		resides. If chipRptrPortNetID does not identify

		an isolated network, then the value of this object is

		backplane(255)."

	::= {chipRptrPortEntry 1 }



chipRptrPortNetID OBJECT-TYPE

	 SYNTAX INTEGER {



		 ethernet-1(6),

		 ethernet-2(7),

		 ethernet-3(8),



		 ethernet-4(32),

		 ethernet-5(33),

		 ethernet-6(34),

		 ethernet-7(35),

		 ethernet-8(36)

		 }

	 ACCESS read-only

	 STATUS mandatory

	 DESCRIPTION

		 "The network index that uniquely identifies this port's repeater."

       ::= { chipRptrPortEntry 2 }



chipRptrPortGroupIndex OBJECT-TYPE

       SYNTAX	 INTEGER (1..1024)

       ACCESS	 read-only

       STATUS	 mandatory

       DESCRIPTION

	       "This object identifies the group containing the

	       port for which this entry contains information."

       ::= { chipRptrPortEntry 3 }



chipRptrPortIndex OBJECT-TYPE

       SYNTAX	 INTEGER (1..1024)



       ACCESS	 read-only

       STATUS	 mandatory

       DESCRIPTION

	       "This object identifies the port within the group

	       for which this entry contains information.  This

	       value can never be greater than

	       chipRptrGroupPortCapacity for the associated group."

       REFERENCE

	       "Reference IEEE 802.3 Rptr Mgt, 19.2.6.2,

	       aPortID."

       ::= { chipRptrPortEntry 4 }



chipRptrPortAdminStatus OBJECT-TYPE

       SYNTAX	 INTEGER {

		     enabled(1),

		     disabled(2)

		 }

       ACCESS	 read-write

       STATUS	 mandatory

       DESCRIPTION

	       "Setting this object to disabled(2) disables the

	       port.  A disabled port neither transmits nor

	       receives.  Once disabled, a port must be

	       explicitly enabled to restore operation.  A port

	       which is disabled when power is lost or when a

	       reset is exerted shall remain disabled when normal

	       operation resumes.



	       When the logical port is actually a daughterboard

	       on the module, the AdminStatus directly relates to

	       the interface mode of the daughterboard.  Setting

	       it enabled(1) enables the interface and likewise

	       disabled(2) disables the interface mode.



	       The admin status takes precedence over auto-

	       partition and functionally operates between the

	       auto-partition mechanism and the AUI/PMA.



	       Setting this object to enabled(1) enables the port

	       and exerts a BEGIN on the port's auto-partition

	       state machine.

	       (In effect, when a port is disabled, the value of

	       chipRptrPortAutoPartitionState for that port is frozen

	       until the port is next enabled.  When the port

	       becomes enabled, the chipRptrPortAutoPartitionState

	       becomes notAutoPartitioned(1), regardless of its

	       pre-disabling state.)"

       REFERENCE

	       "Reference IEEE 802.3 Rptr Mgt, 19.2.6.2,

	       aPortAdminState and 19.2.6.3, acPortAdminControl."

       ::= { chipRptrPortEntry 5 }



chipRptrPortAutoPartitionState OBJECT-TYPE

       SYNTAX	 INTEGER {



		     notAutoPartitioned(1),

		     autoPartitioned(2)

		 }

       ACCESS	 read-only

       STATUS	 mandatory

       DESCRIPTION

	       "The autoPartitionState flag indicates whether the

	       port is currently partitioned by the repeater's

	       auto-partition protection.



	       The conditions that cause port partitioning are

	       specified in partition state machine in Section 9

	       [IEEE 802.3 Std].  They are not differentiated

	       here."

       REFERENCE

	       "Reference IEEE 802.3 Rptr Mgt, 19.2.6.2,

	       aAutoPartitionState."

       ::= { chipRptrPortEntry 6 }



chipRptrPortOperStatus  OBJECT-TYPE

       SYNTAX	 INTEGER {

		     operational(1),

		     notOperational(2),

		     notPresent(3)

		 }

       ACCESS	 read-only

       STATUS	 mandatory

       DESCRIPTION

	       "This object indicates the port's operational

	       status.  The notPresent(3) status indicates the

	       port is physically removed (note this may or may

	       not be possible depending on the type of port.)



	       The operational(1) status indicates that the port

	       is enabled (see chipRptrPortAdminStatus) and working,

	       even though it might be auto-partitioned (see

	       chipRptrPortAutoPartitionState).



	       If this object has the value operational(1) and

	       chipRptrPortAdminStatus is set to disabled(2), it is

	       expected that this object's value will change to

	       notOperational(2) soon after."

       ::= { chipRptrPortEntry 7 }







--

--		      The MONITOR GROUP

--

-- Implementation of this group is optional, but within the

-- group all elements are mandatory.  If a managed repeater

-- implements any part of this group, the entire group shall

-- be implemented.



--

-- Repeater Monitor Information

--

-- Performance monitoring statistics for the repeater

--





chipRptrMonitorRptrTable OBJECT-TYPE

       SYNTAX	 SEQUENCE OF ChipRptrMonitorRptrEntry

       ACCESS	 not-accessible

       STATUS	 mandatory

       DESCRIPTION

	       "Table of performance and error statistics for the

		Repeater."

       ::= { chipRptrMonitorRptrInfo 1 }





chipRptrMonitorRptrEntry OBJECT-TYPE

       SYNTAX	 ChipRptrMonitorRptrEntry



       ACCESS	 not-accessible

       STATUS	 mandatory

       DESCRIPTION

	       "An entry in the table, containing total

	       performance and error statistics for a

	       repeater."

       INDEX	{ chipRptrMonitorSlotIndex, chipRptrMonitorNetID }

       ::= { chipRptrMonitorRptrTable 1 }



   ChipRptrMonitorRptrEntry ::=

       SEQUENCE {

	   chipRptrMonitorSlotIndex

	       INTEGER,

	   chipRptrMonitorNetID

	       INTEGER,

	   chipRptrMonitorTransmitCollisions

	       Counter

       }





chipRptrMonitorSlotIndex OBJECT-TYPE

	SYNTAX INTEGER {

		slot-1(1),

		slot-2(2),

		slot-3(3),

		slot-4(4),

		slot-5(5),

		slot-6(6),

		slot-7(7),

		slot-8(8),

		slot-9(9),

		slot-10(10),

		slot-11(11),

		slot-12(12),

		slot-13(13),

		slot-14(14),

		slot-15(15),

		slot-16(16),

		slot-17(17),

		backplane(255)

		}

	ACCESS read-only

	STATUS mandatory

	DESCRIPTION

		"The slot number of the repeater module on which

		the isolated network identified by chipRptrMonitorNetID

		resides. If chipRptrMonitorNetID does not identify

		an isolated network, then the value of this object is

		backplane(255)."

	::= {chipRptrMonitorRptrEntry  1 }



chipRptrMonitorNetID OBJECT-TYPE

	 SYNTAX INTEGER {



		 ethernet-1(6),

		 ethernet-2(7),

		 ethernet-3(8),



		 ethernet-4(32),

		 ethernet-5(33),

		 ethernet-6(34),

		 ethernet-7(35),

		 ethernet-8(36)

		 }

	 ACCESS read-only

	 STATUS mandatory

	 DESCRIPTION

		 "The network index that uniquely identifies this repeater."

       ::= {chipRptrMonitorRptrEntry 2 }



chipRptrMonitorTransmitCollisions OBJECT-TYPE

       SYNTAX	 Counter

       ACCESS	 read-only

       STATUS	 mandatory

       DESCRIPTION

	       "This counter is incremented every time the

	       repeater state machine enters the TRANSMIT

	       COLLISION state from any state other than ONE PORT

	       LEFT (Ref: Fig 9-2, IEEE 802.3 Std).



	       The approximate minimum time for rollover of this

	       counter is 16 hours."

       REFERENCE

	       "Reference IEEE 802.3 Rptr Mgt, 19.2.3.2,

	       aTransmitCollisions."

       ::= { chipRptrMonitorRptrEntry 3 }





   --

   -- The Group Monitor Table

   --





   --

   -- Basic Repeater Information

   --

   -- Configuration, status, and control objects for the overall

   -- repeater

   --



chipRptrMonitorGroupTable OBJECT-TYPE

       SYNTAX	 SEQUENCE OF ChipRptrMonitorGroupEntry

       ACCESS	 not-accessible

       STATUS	 mandatory

       DESCRIPTION

	       "Table of performance and error statistics for the

	       groups."

       ::= { chipRptrMonitorGroupInfo 1 }





chipRptrMonitorGroupEntry OBJECT-TYPE

       SYNTAX	 ChipRptrMonitorGroupEntry



       ACCESS	 not-accessible

       STATUS	 mandatory

       DESCRIPTION

	       "An entry in the table, containing total

	       performance and error statistics for a single

	       group.  Regular retrieval of the information in

	       this table provides a means of tracking the

	       performance and health of the networked devices

	       attached to this group's ports.



	       The counters in this table are redundant in the

	       sense that they are the summations of information

	       already available through other objects.  However,

	       these sums provide a considerable optimization of

	       network management traffic over the otherwise

	       necessary retrieval of the individual counters

	       included in each sum."

       INDEX	{ chipRptrMonitorGroupSlotIndex, chipRptrMonitorGroupNetID, chipRptrMonitorGroupIndex }

       ::= { chipRptrMonitorGroupTable 1 }



   ChipRptrMonitorGroupEntry ::=

       SEQUENCE {

	   chipRptrMonitorGroupSlotIndex

	       INTEGER,

	   chipRptrMonitorGroupNetID

	       INTEGER,

	   chipRptrMonitorGroupIndex

	       INTEGER,

	   chipRptrMonitorGroupTotalFrames

	       Counter,

	   chipRptrMonitorGroupTotalOctets

	       Counter,

	   chipRptrMonitorGroupTotalErrors

	       Counter

       }





chipRptrMonitorGroupSlotIndex OBJECT-TYPE

	SYNTAX INTEGER {

		slot-1(1),

		slot-2(2),

		slot-3(3),

		slot-4(4),

		slot-5(5),

		slot-6(6),

		slot-7(7),

		slot-8(8),

		slot-9(9),

		slot-10(10),

		slot-11(11),

		slot-12(12),

		slot-13(13),

		slot-14(14),

		slot-15(15),

		slot-16(16),

		slot-17(17),

		backplane(255)

		}

	ACCESS read-only

	STATUS mandatory

	DESCRIPTION

		"The slot number of the repeater module on which

		the isolated network identified by chipRptrMonitorGroupNetID

		resides. If chipRptrMonitorGroupNetID does not identify

		an isolated network, then the value of this object is

		backplane(255)."

	::= {chipRptrMonitorGroupEntry  1 }



chipRptrMonitorGroupNetID OBJECT-TYPE

	 SYNTAX INTEGER {



		 ethernet-1(6),

		 ethernet-2(7),

		 ethernet-3(8),



		 ethernet-4(32),

		 ethernet-5(33),

		 ethernet-6(34),

		 ethernet-7(35),

		 ethernet-8(36)

		 }

	 ACCESS read-only

	 STATUS mandatory

	 DESCRIPTION

		 "The network index that uniquely identifies this group's repeater."

       ::= {chipRptrMonitorGroupEntry 2 }



chipRptrMonitorGroupIndex OBJECT-TYPE

       SYNTAX	 INTEGER (1..1024)

       ACCESS	 read-only

       STATUS	 mandatory

       DESCRIPTION

	       "This object identifies the group within the

	       repeater for which this entry contains

	       information."

       ::= { chipRptrMonitorGroupEntry 3 }



chipRptrMonitorGroupTotalFrames OBJECT-TYPE

       SYNTAX	 Counter

       ACCESS	 read-only

       STATUS	 mandatory

       DESCRIPTION

	       "The total number of frames of valid frame length



	       that have been received on the ports in this

	       group.  This counter is the summation of the

	       values of the chipRptrMonitorPortReadableFrames

	       counters for all of the ports in the group.



	       This statistic provides one of the parameters

	       necessary for obtaining the packet error rate.

	       The approximate minimum time for rollover of this

	       counter is 80 hours."

       ::= { chipRptrMonitorGroupEntry 4 }



chipRptrMonitorGroupTotalOctets OBJECT-TYPE

       SYNTAX	 Counter

       ACCESS	 read-only

       STATUS	 mandatory

       DESCRIPTION

	       "The total number of octets contained in the valid

	       frames that have been received on the ports in

	       this group.  This counter is the summation of the

	       values of the chipRptrMonitorPortReadableOctets

	       counters for all of the ports in the group.



	       This statistic provides an indicator of the total

	       data transferred.  The approximate minimum time

	       for rollover of this counter is 58 minutes."

       ::= { chipRptrMonitorGroupEntry 5 }



chipRptrMonitorGroupTotalErrors OBJECT-TYPE

       SYNTAX	 Counter

       ACCESS	 read-only

       STATUS	 mandatory

       DESCRIPTION

	       "The total number of errors which have occurred on

	       all of the ports in this group.  This counter is

	       the summation of the values of the

	       chipRptrMonitorPortTotalErrors counters for all of the

	       ports in the group."

       ::= { chipRptrMonitorGroupEntry 6 }





   --

   -- The Port Monitor Table

   --



chipRptrMonitorPortTable OBJECT-TYPE

       SYNTAX	 SEQUENCE OF ChipRptrMonitorPortEntry

       ACCESS	 not-accessible

       STATUS	 mandatory



       DESCRIPTION

	       "Table of performance and error statistics for the

	       ports."

       ::= { chipRptrMonitorPortInfo 1 }



chipRptrMonitorPortEntry OBJECT-TYPE

       SYNTAX	 ChipRptrMonitorPortEntry

       ACCESS	 not-accessible

       STATUS	 mandatory

       DESCRIPTION

	       "An entry in the table, containing performance and

	       error statistics for a single port."

       INDEX	{ chipRptrMonitorPortSlotIndex, chipRptrMonitorPortNetID, chipRptrMonitorPortGroupIndex, chipRptrMonitorPortIndex }

       ::= { chipRptrMonitorPortTable 1 }



   ChipRptrMonitorPortEntry ::=

       SEQUENCE {

	   chipRptrMonitorPortSlotIndex

	       INTEGER,

	   chipRptrMonitorPortNetID

	       INTEGER,

	   chipRptrMonitorPortGroupIndex

	       INTEGER,

	   chipRptrMonitorPortIndex

	       INTEGER,

	   chipRptrMonitorPortReadableFrames

	       Counter,

	   chipRptrMonitorPortReadableOctets

	       Counter,

	   chipRptrMonitorPortFCSErrors

	       Counter,

	   chipRptrMonitorPortAlignmentErrors

	       Counter,

	   chipRptrMonitorPortFrameTooLongs

	       Counter,

	   chipRptrMonitorPortShortEvents

	       Counter,

	   chipRptrMonitorPortRunts

	       Counter,

	   chipRptrMonitorPortCollisions

	       Counter,

	   chipRptrMonitorPortLateEvents

	       Counter,

	   chipRptrMonitorPortVeryLongEvents

	       Counter,

	   chipRptrMonitorPortDataRateMismatches

	       Counter,

	   chipRptrMonitorPortAutoPartitions

	       Counter,

	   chipRptrMonitorPortTotalErrors

	       Counter

       }





chipRptrMonitorPortSlotIndex OBJECT-TYPE

	SYNTAX INTEGER {

		slot-1(1),

		slot-2(2),

		slot-3(3),

		slot-4(4),

		slot-5(5),

		slot-6(6),

		slot-7(7),

		slot-8(8),

		slot-9(9),

		slot-10(10),

		slot-11(11),

		slot-12(12),

		slot-13(13),

		slot-14(14),

		slot-15(15),

		slot-16(16),

		slot-17(17),

		backplane(255)

		}

	ACCESS read-only

	STATUS mandatory

	DESCRIPTION

		"The slot number of the repeater module on which

		the isolated network identified by chipRptrMonitorPortNetID

		resides. If chipRptrMonitorPortNetID does not identify

		an isolated network, then the value of this object is

		backplane(255)."

	::= {chipRptrMonitorPortEntry 1 }



chipRptrMonitorPortNetID OBJECT-TYPE

	 SYNTAX INTEGER {



		 ethernet-1(6),

		 ethernet-2(7),

		 ethernet-3(8),



		 ethernet-4(32),

		 ethernet-5(33),

		 ethernet-6(34),

		 ethernet-7(35),

		 ethernet-8(36)

		 }

	 ACCESS read-only

	 STATUS mandatory

	 DESCRIPTION

		 "The network index that uniquely identifies this port's repeater."

       ::= {chipRptrMonitorPortEntry 2 }



chipRptrMonitorPortGroupIndex OBJECT-TYPE

       SYNTAX	 INTEGER (1..1024)

       ACCESS	 read-only

       STATUS	 mandatory

       DESCRIPTION

	       "This object identifies the group containing the

	       port for which this entry contains information."

       ::= { chipRptrMonitorPortEntry 3 }



chipRptrMonitorPortIndex OBJECT-TYPE

       SYNTAX	 INTEGER (1..1024)

       ACCESS	 read-only

       STATUS	 mandatory

       DESCRIPTION

	       "This object identifies the port within the group

	       for which this entry contains information."

       REFERENCE

	       "Reference IEEE 802.3 Rptr Mgt, 19.2.6.2,

	       aPortID."

       ::= { chipRptrMonitorPortEntry 4 }



chipRptrMonitorPortReadableFrames OBJECT-TYPE

       SYNTAX	 Counter

       ACCESS	 read-only

       STATUS	 mandatory

       DESCRIPTION

	       "This object is the number of frames of valid

	       frame length that have been received on this port.

	       This counter is incremented by one for each frame

	       received on this port whose OctetCount is greater

	       than or equal to minFrameSize and less than or

	       equal to maxFrameSize (Ref: IEEE 802.3 Std,

	       4.4.2.1) and for which the FCSError and

	       CollisionEvent signals are not asserted.



	       This statistic provides one of the parameters

	       necessary for obtaining the packet error rate.

	       The approximate minimum time for rollover of this

	       counter is 80 hours."

       REFERENCE

	       "Reference IEEE 802.3 Rptr Mgt, 19.2.6.2,

	       aReadableFrames."

       ::= { chipRptrMonitorPortEntry 5 }



chipRptrMonitorPortReadableOctets OBJECT-TYPE

       SYNTAX	 Counter

       ACCESS	 read-only

       STATUS	 mandatory



       DESCRIPTION

	       "This object is the number of octets contained in

	       valid frames that have been received on this port.

	       This counter is incremented by OctetCount for each

	       frame received on this port which has been

	       determined to be a readable frame.



	       This statistic provides an indicator of the total

	       data transferred.  The approximate minimum time

	       for rollover of this counter is 58 minutes."

       REFERENCE

	       "Reference IEEE 802.3 Rptr Mgt, 19.2.6.2,

	       aReadableOctets."

       ::= { chipRptrMonitorPortEntry 6 }



chipRptrMonitorPortFCSErrors OBJECT-TYPE

       SYNTAX	 Counter

       ACCESS	 read-only

       STATUS	 mandatory

       DESCRIPTION

	       "This counter is incremented by one for each frame

	       received on this port with the FCSError signal

	       asserted and the FramingError and CollisionEvent

	       signals deasserted and whose OctetCount is greater

	       than or equal to minFrameSize and less than or

	       equal to maxFrameSize (Ref: 4.4.2.1, IEEE 802.3

	       Std).



	       The approximate minimum time for rollover of this

	       counter is 80 hours."

       REFERENCE

	       "Reference IEEE 802.3 Rptr Mgt, 19.2.6.2,

	       aFrameCheckSequenceErrors."

       ::= { chipRptrMonitorPortEntry 7 }



chipRptrMonitorPortAlignmentErrors OBJECT-TYPE

       SYNTAX	 Counter

       ACCESS	 read-only

       STATUS	 mandatory

       DESCRIPTION

	       "This counter is incremented by one for each frame

	       received on this port with the FCSError and

	       FramingError signals asserted and CollisionEvent

	       signal deasserted and whose OctetCount is greater

	       than or equal to minFrameSize and less than or

	       equal to maxFrameSize (Ref: IEEE 802.3 Std,

	       4.4.2.1).  If chipRptrMonitorPortAlignmentErrors is

	       incremented then the chipRptrMonitorPortFCSErrors



	       Counter shall not be incremented for the same

	       frame.



	       The approximate minimum time for rollover of this

	       counter is 80 hours."

       REFERENCE

	       "Reference IEEE 802.3 Rptr Mgt, 19.2.6.2,

	       aAlignmentErrors."

       ::= { chipRptrMonitorPortEntry 8 }



chipRptrMonitorPortFrameTooLongs OBJECT-TYPE

       SYNTAX	 Counter

       ACCESS	 read-only

       STATUS	 mandatory

       DESCRIPTION

	       "This counter is incremented by one for each frame

	       received on this port whose OctetCount is greater

	       than maxFrameSize (Ref: 4.4.2.1, IEEE 802.3 Std).

	       If chipRptrMonitorPortFrameTooLongs is incremented

	       then neither the chipRptrMonitorPortAlignmentErrors

	       nor the chipRptrMonitorPortFCSErrors counter shall be

	       incremented for the frame.



	       The approximate minimum time for rollover of this

	       counter is 61 days."

       REFERENCE

	       "Reference IEEE 802.3 Rptr Mgt, 19.2.6.2,

	       aFramesTooLong."

       ::= { chipRptrMonitorPortEntry 9 }



chipRptrMonitorPortShortEvents OBJECT-TYPE

       SYNTAX	 Counter

       ACCESS	 read-only

       STATUS	 mandatory

       DESCRIPTION

	       "This counter is incremented by one for each

	       CarrierEvent on this port with ActivityDuration

	       less than ShortEventMaxTime.  ShortEventMaxTime is

	       greater than 74 bit times and less than 82 bit

	       times.  ShortEventMaxTime has tolerances included

	       to provide for circuit losses between a

	       conformance test point at the AUI and the

	       measurement point within the state machine.



	       Note:  shortEvents may indicate externally

	       generated noise hits which will cause the repeater

	       to transmit Runts to its other ports, or propagate

	       a collision (which may be late) back to the



	       transmitting DTE and damaged frames to the rest of

	       the network.



	       Implementors may wish to consider selecting the

	       ShortEventMaxTime towards the lower end of the

	       allowed tolerance range to accommodate bit losses

	       suffered through physical channel devices not

	       budgeted for within this standard.



	       The approximate minimum time for rollover of this

	       counter is 16 hours."

       REFERENCE

	       "Reference IEEE 802.3 Rptr Mgt, 19.2.6.2,

	       aShortEvents."

       ::= { chipRptrMonitorPortEntry 10 }



chipRptrMonitorPortRunts OBJECT-TYPE

       SYNTAX	 Counter

       ACCESS	 read-only

       STATUS	 mandatory

       DESCRIPTION

	       "This counter is incremented by one for each

	       CarrierEvent on this port that meets one of the

	       following two conditions.  Only one test need be

	       made.  a) The ActivityDuration is greater than

	       ShortEventMaxTime and less than ValidPacketMinTime

	       and the CollisionEvent signal is deasserted.  b)

	       The OctetCount is less than 64, the

	       ActivityDuration is greater than ShortEventMaxTime

	       and the CollisionEvent signal is deasserted.

	       ValidPacketMinTime is greater than or equal to 552

	       bit times and less than 565 bit times.



	       An event whose length is greater than 74 bit times

	       but less than 82 bit times shall increment either

	       the shortEvents counter or the runts counter but

	       not both.  A CarrierEvent greater than or equal to

	       552 bit times but less than 565 bit times may or

	       may not be counted as a runt.



	       ValidPacketMinTime has tolerances included to

	       provide for circuit losses between a conformance

	       test point at the AUI and the measurement point

	       within the state machine.



	       Runts usually indicate collision fragments, a

	       normal network event.  In certain situations

	       associated with large diameter networks a



	       percentage of runts may exceed ValidPacketMinTime.



	       The approximate minimum time for rollover of this

	       counter is 16 hours."

       REFERENCE

	       "Reference IEEE 802.3 Rptr Mgt, 19.2.6.2, aRunts."

       ::= { chipRptrMonitorPortEntry 11 }



chipRptrMonitorPortCollisions OBJECT-TYPE

       SYNTAX	 Counter

       ACCESS	 read-only

       STATUS	 mandatory

       DESCRIPTION

	       "This counter is incremented by one for any

	       CarrierEvent signal on any port for which the

	       CollisionEvent signal on this port is asserted.



	       The approximate minimum time for rollover of this

	       counter is 16 hours."

       REFERENCE

	       "Reference IEEE 802.3 Rptr Mgt, 19.2.6.2,

	       aCollisions."

       ::= { chipRptrMonitorPortEntry 12 }



chipRptrMonitorPortLateEvents OBJECT-TYPE

       SYNTAX	 Counter

       ACCESS	 read-only

       STATUS	 mandatory

       DESCRIPTION

	       "This counter is incremented by one for each

	       CarrierEvent on this port in which the CollIn(X)

	       variable transitions to the value SQE (Ref:

	       9.6.6.2, IEEE 802.3 Std) while the

	       ActivityDuration is greater than the

	       LateEventThreshold.  Such a CarrierEvent is

	       counted twice, as both a collision and as a

	       lateEvent.



	       The LateEventThreshold is greater than 480 bit

	       times and less than 565 bit times.

	       LateEventThreshold has tolerances included to

	       permit an implementation to build a single

	       threshold to serve as both the LateEventThreshold

	       and ValidPacketMinTime threshold.



	       The approximate minimum time for rollover of this

	       counter is 81 hours."

       REFERENCE



	       "Reference IEEE 802.3 Rptr Mgt, 19.2.6.2,

	       aLateEvents."

       ::= { chipRptrMonitorPortEntry 13 }



chipRptrMonitorPortVeryLongEvents OBJECT-TYPE

       SYNTAX	 Counter

       ACCESS	 read-only

       STATUS	 mandatory

       DESCRIPTION

	       "This counter is incremented by one for each

	       CarrierEvent on this port whose ActivityDuration

	       is greater than the MAU Jabber Lockup Protection

	       timer TW3 (Ref: 9.6.1 & 9.6.5, IEEE 802.3 Std).

	       Other counters may be incremented as appropriate."

       REFERENCE

	       "Reference IEEE 802.3 Rptr Mgt, 19.2.6.2,

	       aVeryLongEvents."

       ::= { chipRptrMonitorPortEntry 14 }



chipRptrMonitorPortDataRateMismatches OBJECT-TYPE

       SYNTAX	 Counter

       ACCESS	 read-only

       STATUS	 mandatory

       DESCRIPTION

	       "This counter is incremented by one for each frame

	       received on this port that meets all of the

	       following conditions:  a) The CollisionEvent

	       signal is not asserted.  b) The ActivityDuration

	       is greater than ValidPacketMinTime.  c) The

	       frequency (data rate) is detectably mismatched

	       from the local transmit frequency.  The exact

	       degree of mismatch is vendor specific and is to be

	       defined by the vendor for conformance testing.



	       When this event occurs, other counters whose

	       increment conditions were satisfied may or may not

	       also be incremented, at the implementor's

	       discretion.  Whether or not the repeater was able

	       to maintain data integrity is beyond the scope of

	       this standard."

       REFERENCE

	       "Reference IEEE 802.3 Rptr Mgt, 19.2.6.2,

	       aDataRateMismatches."

       ::= { chipRptrMonitorPortEntry 15 }



chipRptrMonitorPortAutoPartitions OBJECT-TYPE

       SYNTAX	 Counter

       ACCESS	 read-only



       STATUS	 mandatory

       DESCRIPTION

	       "This counter is incremented by one for each time

	       the repeater has automatically partitioned this

	       port.  The conditions that cause port partitioning

	       are specified in the partition state machine in

	       Section 9 [IEEE 802.3 Std].  They are not

	       differentiated here."

       REFERENCE

	       "Reference IEEE 802.3 Rptr Mgt, 19.2.6.2,

	       aAutoPartitions."

       ::= { chipRptrMonitorPortEntry 16 }



chipRptrMonitorPortTotalErrors OBJECT-TYPE

       SYNTAX	 Counter

       ACCESS	 read-only

       STATUS	 mandatory

       DESCRIPTION

	       "The total number of errors which have occurred on

	       this port.  This counter is the summation of the

	       values of other error counters (for the same

	       port), namely:



		   chipRptrMonitorPortFCSErrors,

		   chipRptrMonitorPortAlignmentErrors,

		   chipRptrMonitorPortFrameTooLongs,

		   chipRptrMonitorPortShortEvents,

		   chipRptrMonitorPortLateEvents,

		   chipRptrMonitorPortVeryLongEvents, and

		   chipRptrMonitorPortDataRateMismatches.



	       This counter is redundant in the sense that it is

	       the summation of information already available

	       through other objects.  However, it is included

	       specifically because the regular retrieval of this

	       object as a means of tracking the health of a port

	       provides a considerable optimization of network

	       management traffic over the otherwise necessary

	       retrieval of the summed counters."

       ::= { chipRptrMonitorPortEntry 17 }





   --

   --			 The ADDRESS TRACKING GROUP

   --

   -- Implementation of this group is optional; it is appropriate

   -- for all systems which have the necessary metering.  If a

   -- managed repeater implements any part of this group, the entire



   -- group shall be implemented.



   --

   -- The Port Address Tracking Table

   --



chipRptrAddrTrackTable OBJECT-TYPE

       SYNTAX	 SEQUENCE OF ChipRptrAddrTrackEntry

       ACCESS	 not-accessible

       STATUS	 mandatory

       DESCRIPTION

	       "Table of address mapping information about the

	       ports."

       ::= { chipRptrAddrTrackPortInfo 1 }



chipRptrAddrTrackEntry OBJECT-TYPE

       SYNTAX	 ChipRptrAddrTrackEntry

       ACCESS	 not-accessible

       STATUS	 mandatory

       DESCRIPTION

	       "An entry in the table, containing address mapping

	       information about a single port."

       INDEX	{ chipRptrAddrTrackSlotIndex, chipRptrAddrTrackGroupNetID, chipRptrAddrTrackGroupIndex, chipRptrAddrTrackPortIndex }

       ::= { chipRptrAddrTrackTable 1 }



   ChipRptrAddrTrackEntry ::=

       SEQUENCE {

	   chipRptrAddrTrackSlotIndex

	       INTEGER,

	   chipRptrAddrTrackGroupNetID

	       INTEGER,

	   chipRptrAddrTrackGroupIndex

	       INTEGER,

	   chipRptrAddrTrackPortIndex

	       INTEGER,

	   chipRptrAddrTrackLastSourceAddress

	       MacAddress,

	   chipRptrAddrTrackSourceAddrChanges

	       Counter,

	   chipRptrAddrTrackNewLastSrcAddress

	       OCTET STRING

       }





chipRptrAddrTrackSlotIndex OBJECT-TYPE

	SYNTAX INTEGER {

		slot-1(1),

		slot-2(2),

		slot-3(3),

		slot-4(4),

		slot-5(5),

		slot-6(6),

		slot-7(7),

		slot-8(8),

		slot-9(9),

		slot-10(10),

		slot-11(11),

		slot-12(12),

		slot-13(13),

		slot-14(14),

		slot-15(15),

		slot-16(16),

		slot-17(17),

		backplane(255)

		}

	ACCESS read-only

	STATUS mandatory

	DESCRIPTION

		"The slot number of the repeater module on which

		the isolated network identified by chipRptrMonitorGroupNetID

		resides. If chipRptrMonitorGroupNetID does not identify

		an isolated network, then the value of this object is

		backplane(255)."

	::= {chipRptrAddrTrackEntry 1 }



chipRptrAddrTrackGroupNetID OBJECT-TYPE

	 SYNTAX INTEGER {



		 ethernet-1(6),

		 ethernet-2(7),

		 ethernet-3(8),



		 ethernet-4(32),

		 ethernet-5(33),

		 ethernet-6(34),

		 ethernet-7(35),

		 ethernet-8(36)

		 }

	 ACCESS read-only

	 STATUS mandatory

	 DESCRIPTION

		 "The network index that uniquely identifies this port's repeater."

       ::= { chipRptrAddrTrackEntry 2 }



chipRptrAddrTrackGroupIndex OBJECT-TYPE

       SYNTAX	 INTEGER (1..1024)

       ACCESS	 read-only

       STATUS	 mandatory

       DESCRIPTION

	       "This object identifies the group containing the

	       port for which this entry contains information."

       ::= { chipRptrAddrTrackEntry 3 }



chipRptrAddrTrackPortIndex OBJECT-TYPE

       SYNTAX	 INTEGER (1..1024)



       ACCESS	 read-only

       STATUS	 mandatory

       DESCRIPTION

	       "This object identifies the port within the group

	       for which this entry contains information."

       REFERENCE

	       "Reference IEEE 802.3 Rptr Mgt, 19.2.6.2,

	       aPortID."

       ::= { chipRptrAddrTrackEntry 4 }



chipRptrAddrTrackLastSourceAddress OBJECT-TYPE

       SYNTAX	 MacAddress

       ACCESS	 read-only

       STATUS	 mandatory

       DESCRIPTION

	       "This object is the SourceAddress of the last

	       readable frame (i.e., counted by

	       chipRptrMonitorPortReadableFrames) received by this

	       port."

       REFERENCE

	       "Reference IEEE 802.3 Rptr Mgt, 19.2.6.2,

	       aLastSourceAddress."

       ::= { chipRptrAddrTrackEntry 5 }



chipRptrAddrTrackSourceAddrChanges OBJECT-TYPE

       SYNTAX	 Counter

       ACCESS	 read-only

       STATUS	 mandatory

       DESCRIPTION

	       "This counter is incremented by one for each time

	       that the chipRptrAddrTrackLastSourceAddress attribute

	       for this port has changed.



	       This may indicate whether a link is connected to a

	       single DTE or another multi-user segment.

	       The approximate minimum time for rollover of this

	       counter is 81 hours."

       REFERENCE

	       "Reference IEEE 802.3 Rptr Mgt, 19.2.6.2,

	       aSourceAddressChanges."

       ::= { chipRptrAddrTrackEntry 6 }



chipRptrAddrTrackNewLastSrcAddress OBJECT-TYPE

       SYNTAX	 OCTET STRING (SIZE(0..6))

       ACCESS	 read-only

       STATUS	 mandatory

       DESCRIPTION

	       "This object is the SourceAddress of the last

	       readable frame (i.e., counted by

	       chipRptrMonitorPortReadableFrames) received by this

	       port.  If no frames have been received by this

	       port since the agent began monitoring the port

	       activity, the agent shall return a string of

	       length zero."

       REFERENCE

	       "Reference IEEE 802.3 Rptr Mgt, 19.2.6.2,

	       aLastSourceAddress."

       ::= { chipRptrAddrTrackEntry 7 }









 -- The olTRnet Group



 -- This group represents information about Token Ring networks.



olTRnetMapState OBJECT-TYPE

	 SYNTAX INTEGER {

		 changing(1),

		 notChanging(2)

		 }

	 ACCESS read-only

	 STATUS mandatory

	 DESCRIPTION

		"The state of the inter-module token ring map. If the map

		is being updated, then the state of the map is changing."

	 ::= { olTRnet 1 }





olTRnetStatsTable OBJECT-TYPE

	SYNTAX SEQUENCE OF OlTRnetStatsEntry

	ACCESS not-accessible

	STATUS mandatory

	DESCRIPTION

		"A list of Token Ring statistics entries counted

		for each network."

	::= { olTRnet 2 }



olTRnetStatsEntry OBJECT-TYPE

	SYNTAX OlTRnetStatsEntry

	ACCESS not-accessible

	STATUS mandatory

	DESCRIPTION

		"A collection of statistics kept for a particular

		Token Ring interface."

	INDEX { olTRnetStatsNetID }

	::= { olTRnetStatsTable 1 }



OlTRnetStatsEntry ::=

	SEQUENCE {

		olTRnetStatsNetID

			INTEGER,

		olTRnetStatsLineErrors

			Counter,

		olTRnetStatsBurstErrors

			Counter,

		olTRnetStatsACErrors

			Counter,

		olTRnetStatsLostFrameErrors

			Counter,

		olTRnetStatsCongestionErrors

			Counter,

		olTRnetStatsFrameCopiedErrors

			Counter,

		olTRnetStatsTokenErrors

			Counter,

		olTRnetStatsDuplicateAddresses

			Counter,

		olTRnetStatsBeaconEvents

			Counter,

		olTRnetStatsLastBeaconSender

			OCTET STRING,

		olTRnetStatsLastBeaconNAUN

			OCTET STRING,

		olTRnetStatsLastBeaconTime

			TimeTicks,

		olTRnetStatsLastBeaconAction

			INTEGER,

		olTRnetStatsTotalStations

			INTEGER,

		olTRnetStatsConcStations

			INTEGER,

		olTRnetStatsTotalPorts

			INTEGER,

		olTRnetStatsEnabledPorts

			INTEGER,

		olTRnetStatsActivePorts

			INTEGER

		}



olTRnetStatsNetID OBJECT-TYPE

	SYNTAX INTEGER {

		isolated(2),

		token-ring-1(9),

		token-ring-2(10),

		token-ring-3(11),

		token-ring-4(12),

		token-ring-5(13),

		token-ring-6(14),

		token-ring-7(15)

		}

	ACCESS read-only

	STATUS mandatory

	DESCRIPTION

		"The network index that uniquely identifies this network.

		One of token-ring-1 through token-ring-7 or isolated."

	::= { olTRnetStatsEntry 1 }



olTRnetStatsLineErrors OBJECT-TYPE

	SYNTAX Counter

	ACCESS read-only

	STATUS mandatory

	DESCRIPTION

		"The total number of line errors reported in

		error reporting packets detected by the TRMM."

	::= { olTRnetStatsEntry 2 }



olTRnetStatsBurstErrors OBJECT-TYPE

	SYNTAX Counter

	ACCESS read-only

	STATUS mandatory

	DESCRIPTION

		"The total number of burst errors reported in

		error reporting packets detected by the TRMM."

	::= { olTRnetStatsEntry 3 }



olTRnetStatsACErrors OBJECT-TYPE

	SYNTAX Counter

	ACCESS read-only

	STATUS mandatory

	DESCRIPTION

		"The total number of AC (Address Copied) errors

		reported in error reporting packets detected by

		the TRMM."

	::= { olTRnetStatsEntry 4 }



olTRnetStatsLostFrameErrors OBJECT-TYPE

	SYNTAX Counter

	ACCESS read-only

	STATUS mandatory

	DESCRIPTION

		"The total number of lost frame errors reported

		in error reporting packets detected by the TRMM."

	::= { olTRnetStatsEntry 5 }



olTRnetStatsCongestionErrors OBJECT-TYPE

	SYNTAX Counter

	ACCESS read-only

	STATUS mandatory

	DESCRIPTION

		"The total number of receive congestion errors

		reported in error reporting packets detected by

		the TRMM."

	::= { olTRnetStatsEntry 6 }



olTRnetStatsFrameCopiedErrors OBJECT-TYPE

	SYNTAX Counter

	ACCESS read-only

	STATUS mandatory

	DESCRIPTION

		"The total number of frame copied errors

		reported in error reporting packets detected by

		the TRMM."

	::= { olTRnetStatsEntry 7 }



olTRnetStatsTokenErrors OBJECT-TYPE

	SYNTAX Counter

	ACCESS read-only

	STATUS mandatory

	DESCRIPTION

		"The total number of token errors reported in

		error reporting packets detected by the TRMM."

	::= { olTRnetStatsEntry 8 }



olTRnetStatsDuplicateAddresses OBJECT-TYPE

	SYNTAX Counter

	ACCESS read-only

	STATUS mandatory

	DESCRIPTION

		"The total number of token errors reported in

		error reporting packets detected by the TRMM."

	::= { olTRnetStatsEntry 9 }



olTRnetStatsBeaconEvents OBJECT-TYPE

	SYNTAX Counter

	ACCESS read-only

	STATUS mandatory

	DESCRIPTION

		"The total number of times that the ring enters

		the beaconing state."

	::= { olTRnetStatsEntry 10 }



olTRnetStatsLastBeaconSender OBJECT-TYPE

	SYNTAX OCTET STRING (SIZE(6))

	ACCESS read-only

	STATUS mandatory

	DESCRIPTION

		"The address of the sender of the last beacon frame

		received on this ring. If no beacon frames have been

		received, this object will be six zero octets."

	::= { olTRnetStatsEntry 11 }



olTRnetStatsLastBeaconNAUN OBJECT-TYPE

	SYNTAX OCTET STRING (SIZE(6))

	ACCESS read-only

	STATUS mandatory

	DESCRIPTION

		"The address of the NAUN in the last beacon frame

		received on this ring. If no beacon frames have been

		received, this object will be six zero octets."

	::= { olTRnetStatsEntry 12 }



olTRnetStatsLastBeaconTime OBJECT-TYPE

	SYNTAX TimeTicks

	ACCESS read-only

	STATUS mandatory

	DESCRIPTION

		"The time in in hundredths of a second since the last

		beacon event occurred.  For example, if the time  is 500

		ticks, then this event was seen 5 seconds ago. If no

		beacon events have occurred, then this will be equal

		to the sysUpTime."

	::= { olTRnetStatsEntry 13 }



olTRnetStatsLastBeaconAction OBJECT-TYPE

	SYNTAX INTEGER {

		noAction (1),

		portDisable (2),

		trunkDisable (3),

		moduleIsolate (4)

		}

	ACCESS read-only

	STATUS mandatory

	DESCRIPTION

		"The action (if any) taken to correct the last beacon

		event on the ring."

	::= { olTRnetStatsEntry 14 }



olTRnetStatsTotalStations OBJECT-TYPE

	SYNTAX INTEGER (1..255)

	ACCESS read-only

	STATUS mandatory

	DESCRIPTION

		"The number of stations currently participating in the 802.5

		MAC protocol on the ring."

	::= { olTRnetStatsEntry 15 }



olTRnetStatsConcStations OBJECT-TYPE

	SYNTAX INTEGER (1..255)

	ACCESS read-only

	STATUS mandatory

	DESCRIPTION

		"The number of stations currently participating in the 802.5

		MAC protocol on the ring which are connected to ports in

		this concentrator."

	::= { olTRnetStatsEntry 16}



olTRnetStatsTotalPorts OBJECT-TYPE

	SYNTAX INTEGER

	ACCESS read-only

	STATUS mandatory

	DESCRIPTION

		"The total number of ports within this concentrator and

		on this ring regardless of their admin state or status."

	::= { olTRnetStatsEntry 17 }



olTRnetStatsEnabledPorts OBJECT-TYPE

	SYNTAX INTEGER

	ACCESS read-only

	STATUS mandatory

	DESCRIPTION

		"The number of ports within this concentrator and on this ring

		which have olPortAdminState set to enabled."

	::= { olTRnetStatsEntry 18 }



olTRnetStatsActivePorts OBJECT-TYPE

	SYNTAX INTEGER

	ACCESS read-only

	STATUS mandatory

	DESCRIPTION

		"The number of ports within this concentrator and on this ring

		which have olPortAdminState set to enabled and whose

		olPortStatus has a status of okay."

	::= { olTRnetStatsEntry 19 }



olTRnetStatsStationTable OBJECT-TYPE

	SYNTAX SEQUENCE OF OlTRnetStatsStationEntry

	ACCESS not-accessible

	STATUS mandatory

	DESCRIPTION

		"A list of ring statistics entries."

	::= { olTRnet 3 }



olTRnetStatsStationEntry OBJECT-TYPE

	SYNTAX OlTRnetStatsStationEntry

	ACCESS not-accessible

	STATUS mandatory

	DESCRIPTION

		"A collection of statistics for a particular station

		that has been discovered on a a ring monitored by

		this device."

	INDEX { olTRnetStatsStationNetID, olTRnetStatsStationAddr }

	::= { olTRnetStatsStationTable 1 }



OlTRnetStatsStationEntry ::=

	SEQUENCE {

		olTRnetStatsStationNetID

			INTEGER,

		olTRnetStatsStationAddr

			OCTET STRING,

		olTRnetStatsStationSlotIndex

			INTEGER,

		olTRnetStatsStationPortIndex

			INTEGER,

		olTRnetStatsStationNAUNAddress

			OCTET STRING,

		olTRnetStatsStationLineErrors

			Counter,

		olTRnetStatsStationBurstErrors

			Counter,

		olTRnetStatsStationACErrors

			Counter,

		olTRnetStatsStationLostFrameErrors

			Counter,

		olTRnetStatsStationCongestionErrors

			Counter,

		olTRnetStatsStationFrameCopiedErrors

			Counter,

		olTRnetStatsStationTokenErrors

			Counter,

		olTRnetStatsStationDuplicateAddresses

			Counter

		}



olTRnetStatsStationNetID OBJECT-TYPE

	SYNTAX INTEGER {

		isolated(2),

		token-ring-1(9),

		token-ring-2(10),

		token-ring-3(11),

		token-ring-4(12),

		token-ring-5(13),

		token-ring-6(14),

		token-ring-7(15)

		}

	ACCESS read-only

	STATUS mandatory

	DESCRIPTION

		"The network index that uniquely identifies this network.

		One of token-ring-1 through token-ring-7 or isolated."

	::= { olTRnetStatsStationEntry 1 }



olTRnetStatsStationAddr OBJECT-TYPE

	SYNTAX OCTET STRING (SIZE(6))

	ACCESS read-only

	STATUS mandatory

	DESCRIPTION

		"The physical address of this station."

	::= { olTRnetStatsStationEntry 2 }



olTRnetStatsStationSlotIndex OBJECT-TYPE

	SYNTAX INTEGER {

		slot-1(1),

		slot-2(2),

		slot-3(3),

		slot-4(4),

		slot-5(5),

		slot-6(6),

		slot-7(7),

		slot-8(8),

		slot-9(9),

		slot-10(10),

		slot-11(11),

		slot-12(12),

		slot-13(13),

		slot-14(14),

		slot-15(15),

		slot-16(16),

		slot-17(17),

		external(255)

		}

	ACCESS read-only

	STATUS mandatory

	DESCRIPTION

		"The slot number of the station with this address.

		Addresses with a slot value of external(255) are

		not in this concentrator."

	::= { olTRnetStatsStationEntry 3 }



olTRnetStatsStationPortIndex OBJECT-TYPE

	SYNTAX INTEGER

	ACCESS read-only

	STATUS mandatory

	DESCRIPTION

		"The port number within olTRnetStatsStationSlotIndex's

		slot that received this address. If

		olTRnetStatsStationSlotIndex has a value of

		external(255), then the port address will be 255."

	::= { olTRnetStatsStationEntry 4 }



olTRnetStatsStationNAUNAddress OBJECT-TYPE

	SYNTAX OCTET STRING (SIZE(6))

	ACCESS read-only

	STATUS mandatory

	DESCRIPTION

		"The physical address of the nearest active upstream

		neighbor of this station."

	::= { olTRnetStatsStationEntry 5 }



olTRnetStatsStationLineErrors OBJECT-TYPE

	SYNTAX Counter

	ACCESS read-only

	STATUS mandatory

	DESCRIPTION

		"The total number of Line Errors pertaining to this station

		reported in error reporting packets detected by the TRMM."

	::= { olTRnetStatsStationEntry 6 }



olTRnetStatsStationBurstErrors OBJECT-TYPE

	SYNTAX Counter

	ACCESS read-only

	STATUS mandatory

	DESCRIPTION

		"The total number of burst errors pertaining to this station

		reported in error reporting packets detected by the TRMM."

	::= { olTRnetStatsStationEntry 7 }



olTRnetStatsStationACErrors OBJECT-TYPE

	SYNTAX Counter

	ACCESS read-only

	STATUS mandatory

	DESCRIPTION

		"The total number of AC (Address Copied)

		errors pertaining to this station reported in

		error reporting packets detected by the TRMM."

	::= { olTRnetStatsStationEntry 8 }



olTRnetStatsStationLostFrameErrors OBJECT-TYPE

	SYNTAX Counter

	ACCESS read-only

	STATUS mandatory

	DESCRIPTION

		"The total number of lost frame errors pertaining to

		this station reported in error reporting packets

		detected by the TRMM."

	::= { olTRnetStatsStationEntry 9 }



olTRnetStatsStationCongestionErrors OBJECT-TYPE

	SYNTAX Counter

	ACCESS read-only

	STATUS mandatory

	DESCRIPTION

		"The total number of congestion errors pertaining

		to this station reported in error reporting

		packets detected by the TRMM."

	::= { olTRnetStatsStationEntry 10 }



olTRnetStatsStationFrameCopiedErrors OBJECT-TYPE

	SYNTAX Counter

	ACCESS read-only

	STATUS mandatory

	DESCRIPTION

		"The total number of frame copied errors pertaining

		to this station reported in error reporting packets

		detected by the TRMM."

	::= { olTRnetStatsStationEntry 11 }



olTRnetStatsStationTokenErrors OBJECT-TYPE

	SYNTAX Counter

	ACCESS read-only

	STATUS mandatory

	DESCRIPTION

		"The total number of token errors pertaining to this

		station reported in error reporting packets detected

		by the TRMM."

	::= { olTRnetStatsStationEntry 12 }



olTRnetStatsStationDuplicateAddresses OBJECT-TYPE

	SYNTAX Counter

	ACCESS read-only

	STATUS mandatory

	DESCRIPTION

		"The number of times this station experienced

		a duplicate address error."

	::= { olTRnetStatsStationEntry 13 }





olTRnetStatsPortTable OBJECT-TYPE

	SYNTAX SEQUENCE OF OlTRnetStatsPortEntry

	ACCESS not-accessible

	STATUS mandatory

	DESCRIPTION

		"A list of statistic entries, for ports within the

		concentrator."

	::= { olTRnet 4 }



olTRnetStatsPortEntry OBJECT-TYPE

	SYNTAX OlTRnetStatsPortEntry

	ACCESS not-accessible

	STATUS mandatory

	DESCRIPTION

		"A collection of statistics for a particular station

		that has been discovered on a a ring monitored by

		this device."

	INDEX {olTRnetStatsPortSlotIndex, olTRnetStatsPortIndex }

	::= { olTRnetStatsPortTable 1 }



OlTRnetStatsPortEntry ::=

	SEQUENCE {

		olTRnetStatsPortSlotIndex

			INTEGER,

		olTRnetStatsPortIndex

			INTEGER,

		olTRnetStatsPortNetID

			INTEGER,

		olTRnetStatsPortTotalStations

			INTEGER,

		olTRnetStatsPortAddress

			OCTET STRING,

		olTRnetStatsPortLineErrors

			Counter,

		olTRnetStatsPortBurstErrors

			Counter,

		olTRnetStatsPortACErrors

			Counter,

		olTRnetStatsPortLostFrameErrors

			Counter,

		olTRnetStatsPortCongestionErrors

			Counter,

		olTRnetStatsPortFrameCopiedErrors

			Counter,

		olTRnetStatsPortTokenErrors

			Counter,

		olTRnetStatsPortDuplicateAddresses

			Counter

		}



olTRnetStatsPortSlotIndex OBJECT-TYPE

	SYNTAX INTEGER

	ACCESS read-only

	STATUS mandatory

	DESCRIPTION

		"The port slot number."

	::= { olTRnetStatsPortEntry 1 }



olTRnetStatsPortIndex OBJECT-TYPE

	SYNTAX INTEGER

	ACCESS read-only

	STATUS mandatory

	DESCRIPTION

		"The port number within olTRnetStatsPortSlotIndex's slot."

	::= { olTRnetStatsPortEntry 2 }



olTRnetStatsPortNetID OBJECT-TYPE

	SYNTAX INTEGER {

		isolated(2),

		token-ring-1(9),

		token-ring-2(10),

		token-ring-3(11),

		token-ring-4(12),

		token-ring-5(13),

		token-ring-6(14),

		token-ring-7(15)

		}

	ACCESS read-only

	STATUS mandatory

	DESCRIPTION

		"The network index that uniquely identifies this network.

		One of token-ring-1 through token-ring-7 or isolated."

	::= { olTRnetStatsPortEntry 3 }



olTRnetStatsPortTotalStations OBJECT-TYPE

	SYNTAX INTEGER

	ACCESS read-only

	STATUS mandatory

	DESCRIPTION

		"The total number of stations attached to this port."

	::= { olTRnetStatsPortEntry 4 }



olTRnetStatsPortAddress OBJECT-TYPE

	SYNTAX OCTET STRING (SIZE(6))

	ACCESS read-only

	STATUS mandatory

	DESCRIPTION

		"The mac address of the station connected to this

		If there are multiple mac addresses for this port,

		then this object will contain the last mac address."

	::= { olTRnetStatsPortEntry 5 }



olTRnetStatsPortLineErrors OBJECT-TYPE

	SYNTAX Counter

	ACCESS read-only

	STATUS mandatory

	DESCRIPTION

		"The total number of Line Errors pertaining to

		this port reported in error reporting

		packets detected by the TRMM."

	::= { olTRnetStatsPortEntry 6 }



olTRnetStatsPortBurstErrors OBJECT-TYPE

	SYNTAX Counter

	ACCESS read-only

	STATUS mandatory

	DESCRIPTION

		"The total number of burst errors pertaining

		to this port reported in error reporting

		packets detected by the TRMM."

	::= { olTRnetStatsPortEntry 7 }



olTRnetStatsPortACErrors OBJECT-TYPE

	SYNTAX Counter

	ACCESS read-only

	STATUS mandatory

	DESCRIPTION

		"The total number of AC (Address Copied)

		errors pertaining to this port reported in

		error reporting packets detected by the TRMM."

	::= { olTRnetStatsPortEntry 8 }



olTRnetStatsPortLostFrameErrors OBJECT-TYPE

	SYNTAX Counter

	ACCESS read-only

	STATUS mandatory

	DESCRIPTION

		"The total number of lost frame errors pertaining to

		this port reported in error reporting packets

		detected by the TRMM."

	::= { olTRnetStatsPortEntry 9 }



olTRnetStatsPortCongestionErrors OBJECT-TYPE

	SYNTAX Counter

	ACCESS read-only

	STATUS mandatory

	DESCRIPTION

		"The total number of congestion errors pertaining

		to this port reported in error reporting

		packets detected by the TRMM."

	::= { olTRnetStatsPortEntry 10 }



olTRnetStatsPortFrameCopiedErrors OBJECT-TYPE

	SYNTAX Counter

	ACCESS read-only

	STATUS mandatory

	DESCRIPTION

		"The total number of frame copied errors pertaining

		to this port reported in error reporting packets

		detected by the TRMM."

	::= { olTRnetStatsPortEntry 11 }



olTRnetStatsPortTokenErrors OBJECT-TYPE

	SYNTAX Counter

	ACCESS read-only

	STATUS mandatory

	DESCRIPTION

		"The total number of token errors pertaining to this

		station reported in error reporting packets detected

		by the TRMM."

	::= { olTRnetStatsPortEntry 12 }



olTRnetStatsPortDuplicateAddresses OBJECT-TYPE

	SYNTAX Counter

	ACCESS read-only

	STATUS mandatory

	DESCRIPTION

		"The number of times this port experienced

		a duplicate address error."

	::= { olTRnetStatsPortEntry 13 }



olTRnetMapSummary	OBJECT IDENTIFIER ::= { olTRnet 5 }



olTRnetMapSummaryLogicalState OBJECT-TYPE

	SYNTAX INTEGER {

		changing(1),

		notChanging(2)

		}

	ACCESS read-only

	STATUS mandatory

	DESCRIPTION

		"The state of the token ring summary table. If the summary

		is being updated, then the state of the summary is changing."

	::= { olTRnetMapSummary 1 }



olTRnetMapSummaryLogicalLock OBJECT-TYPE

	SYNTAX INTEGER {

		lock(1),

		unlock(2)

		}

	ACCESS read-write

	STATUS mandatory

	DESCRIPTION

		"A semaphore for locking the token ring summary table.

		When locked, updates to the summary will pend until the

		semaphore is unlocked, so that a valid summary can be read.

		This cannot be set to unlock if olTRnetSummaryLogicalState is

		changing.

		For complete accuracy, this should be read after being set to

		ensure that the map was not changing when the lock was

		attempted. After the summary information has been recorded,

		the semaphore should be set to unlock to allow changes to

		occur."

	::= { olTRnetMapSummary 2 }



olTRnetMapSummaryTable OBJECT-TYPE

	SYNTAX SEQUENCE OF OlTRnetMapSummaryEntry

	ACCESS not-accessible

	STATUS mandatory

	DESCRIPTION

		"A logical map of the token ring network, starting from the

		agent's specified token ring interface. Each station on the

		map is represented by it's MAC address, slot number and port

		number (8 octets per station). If the port is external

		to the concentrator, the slot number and the port number will

		be 255. The map is ordered in the same

		direction as the token flow. The MAC addresses

		are concatonated into groups of up to 32 addresses per entry.

		This table supports up to 256 stations."

	::= { olTRnetMapSummary 3 }



olTRnetMapSummaryEntry OBJECT-TYPE

	SYNTAX OlTRnetMapSummaryEntry

	ACCESS not-accessible

	STATUS mandatory

	DESCRIPTION

		"A group of MAC addresses associated with a Token Ring map."

	INDEX { olTRnetMapSummaryNetID, olTRnetMapSummaryIndex }

	::= { olTRnetMapSummaryTable 1 }



OlTRnetMapSummaryEntry ::=

	SEQUENCE {

		olTRnetMapSummaryNetID

			INTEGER,

		olTRnetMapSummaryIndex

			INTEGER,

		olTRnetMapSummary32Stations

			OCTET STRING

		}



olTRnetMapSummaryNetID OBJECT-TYPE

	SYNTAX INTEGER {

		isolated(2),		-- corresponds to ifIndex

		token-ring-1(9),

		token-ring-2(10),

		token-ring-3(11),

		token-ring-4(12),

		token-ring-5(13),

		token-ring-6(14),

		token-ring-7(15)

		}

	ACCESS read-only

	STATUS mandatory

	DESCRIPTION

		"The network index that uniquely identifies this network.

		It can be isolated from the backplane, or on one of seven

		possible backplane token ring networks."

	::= { olTRnetMapSummaryEntry 1 }



olTRnetMapSummaryIndex OBJECT-TYPE

	SYNTAX INTEGER

	ACCESS read-only

	STATUS mandatory

	DESCRIPTION

		"The index into the map array. Possible values are 1 through 8.

		The MAC address of this agent is the first MAC address in

		olTRnetMapSummary32Stations indexed by a 1 in this entry."

	::= { olTRnetMapSummaryEntry 2 }



olTRnetMapSummary32Stations OBJECT-TYPE

	SYNTAX OCTET STRING (SIZE(8..256))

	ACCESS read-only

	STATUS mandatory

	DESCRIPTION

		"A concatonated group of MAC addresses and their associated

		slot and port of stations on the ring. Each entry has the

		eight octets. The first six octets are the MAC address.

		The seventh octet is the slot ID (or 255 if it is external

		to the concentrator). The eighth is the port ID (or 255

		if it is external to the concentrator).

		The MAC addresses are in the same order as the token flow."

	::= { olTRnetMapSummaryEntry 3 }





--

--  Network Traffic

--



olTRTrafTable OBJECT-TYPE

    SYNTAX SEQUENCE OF OlTRTrafEntry

    ACCESS not-accessible

    STATUS mandatory

    DESCRIPTION

	"A list of Token Ring network traffic (non-error) statistics entries.

	Note that all of the frame and octet counters in this table

	include error frames that have valid length;

	all octet counters exclude framing bits but include FCS octets."

    ::= { olTRnet 6 }



olTRTrafEntry OBJECT-TYPE

    SYNTAX OlTRTrafEntry

    ACCESS not-accessible

    STATUS mandatory

    DESCRIPTION

	"A collection of statistics kept for a particular

	Token Ring interface.

	Note that all of the frame and octet counters in this table

	include error frames that have valid length;

	all octet counters exclude framing bits but include FCS octets."

    INDEX { olTRTrafNetID }

    ::= { olTRTrafTable 1 }



OlTRTrafEntry ::= SEQUENCE {

  olTRTrafNetID			INTEGER,

  olTRTrafTokenRotationTime	INTEGER,

  olTRTrafDropEvents		Counter,

  olTRTrafOctets		Counter,

  olTRTrafFrames		Counter,

  olTRTrafMacOctets		Counter,

  olTRTrafMacFrames		Counter,

  olTRTrafBroadcastFrames	Counter,

  olTRTrafMulticastFrames	Counter,

  olTRTrafFrames18to63Octets	Counter,

  olTRTrafFrames64to127Octets	Counter,

  olTRTrafFrames128to255Octets  Counter,

  olTRTrafFrames256to511Octets  Counter,

  olTRTrafFrames512to1023Octets Counter,

  olTRTrafFrames1024to2047Octets Counter,

  olTRTrafFrames2048to4095Octets Counter,

  olTRTrafFrames4096to8191Octets Counter,

  olTRTrafFrames8192to18000Octets Counter,

  olTRTrafFramesGreaterThan18000Octets  Counter

}



olTRTrafNetID OBJECT-TYPE

	SYNTAX INTEGER {

		isolated(2),

		token-ring-1(9),

		token-ring-2(10),

		token-ring-3(11),

		token-ring-4(12),

		token-ring-5(13),

		token-ring-6(14),

		token-ring-7(15)

		}

	ACCESS read-only

	STATUS mandatory

	DESCRIPTION

		"The network index that uniquely identifies this network.

		One of token-ring-1 through token-ring-7 or isolated."

	::= { olTRTrafEntry 1 }



olTRTrafTokenRotationTime OBJECT-TYPE

    SYNTAX INTEGER

    ACCESS read-only

    STATUS mandatory

    DESCRIPTION

	"An estimate of the time (in microseconds) that it takes for the

	token to complete a single rotation around the ring."

    ::= { olTRTrafEntry 2 }



olTRTrafDropEvents OBJECT-TYPE

    SYNTAX Counter

    ACCESS read-only

    STATUS mandatory

    DESCRIPTION

	"The total number of events in which frames

	were dropped by the TRMM due to lack of resources.

	Note that this number is not necessarily the number of

	frames dropped; it is just the number of times this

	condition has been detected."

    ::= { olTRTrafEntry 3 }



olTRTrafOctets OBJECT-TYPE

    SYNTAX Counter

    ACCESS read-only

    STATUS mandatory

    DESCRIPTION

	"The total number of octets of data received on the network."

    ::= { olTRTrafEntry 4 }



olTRTrafFrames OBJECT-TYPE

    SYNTAX Counter

    ACCESS read-only

    STATUS mandatory

    DESCRIPTION

	"The total number of frames received."

    ::= { olTRTrafEntry 5 }



olTRTrafMacOctets OBJECT-TYPE

    SYNTAX Counter

    ACCESS read-only

    STATUS mandatory

    DESCRIPTION

	"The total number of octets of data in MAC frames

	received on the network."

    ::= { olTRTrafEntry 6 }



olTRTrafMacFrames OBJECT-TYPE

    SYNTAX Counter

    ACCESS read-only

    STATUS mandatory

    DESCRIPTION

	"The total number of MAC frames received."

    ::= { olTRTrafEntry 7 }



olTRTrafBroadcastFrames OBJECT-TYPE

    SYNTAX Counter

    ACCESS read-only

    STATUS mandatory

    DESCRIPTION

	"The total number of non-MAC frames received that were

	directed to a broadcast address (0xFFFFFFFFFFFF or 0xC000FFFFFFFF)."

    ::= { olTRTrafEntry 8 }



olTRTrafMulticastFrames OBJECT-TYPE

    SYNTAX Counter

    ACCESS read-only

    STATUS mandatory

    DESCRIPTION

	"The total number of non-MAC frames received that were

	directed to a local or global multicast or functional address.

	Note that this number does not include frames directed to

	a broadcast address."

    ::= { olTRTrafEntry 9 }



olTRTrafFrames18to63Octets OBJECT-TYPE

    SYNTAX Counter

    ACCESS read-only

    STATUS mandatory

    DESCRIPTION

	"The total number of non-MAC frames received that were between

	18 and 63 octets in length inclusive."

    ::= { olTRTrafEntry 10 }



olTRTrafFrames64to127Octets OBJECT-TYPE

    SYNTAX Counter

    ACCESS read-only

    STATUS mandatory

    DESCRIPTION

	"The total number of non-MAC frames received that were between

	64 and 127 octets in length inclusive."

    ::= { olTRTrafEntry 11 }



olTRTrafFrames128to255Octets OBJECT-TYPE

    SYNTAX Counter

    ACCESS read-only

    STATUS mandatory

    DESCRIPTION

	"The total number of non-MAC frames received that were between

	128 and 255 octets in length inclusive."

    ::= { olTRTrafEntry 12 }



olTRTrafFrames256to511Octets OBJECT-TYPE

    SYNTAX Counter

    ACCESS read-only

    STATUS mandatory

    DESCRIPTION

	"The total number of non-MAC frames received that were between

	256 and 511 octets in length inclusive."

    ::= { olTRTrafEntry 13 }



olTRTrafFrames512to1023Octets OBJECT-TYPE

    SYNTAX Counter

    ACCESS read-only

    STATUS mandatory

    DESCRIPTION

	"The total number of non-MAC frames received that were between

	512 and 1023 octets in length inclusive."

    ::= { olTRTrafEntry 14 }



olTRTrafFrames1024to2047Octets OBJECT-TYPE

    SYNTAX Counter

    ACCESS read-only

    STATUS mandatory

    DESCRIPTION

	"The total number of non-MAC frames received that were between

	1024 and 2047 octets in length inclusive."

    ::= { olTRTrafEntry 15 }



olTRTrafFrames2048to4095Octets OBJECT-TYPE

    SYNTAX Counter

    ACCESS read-only

    STATUS mandatory

    DESCRIPTION

	"The total number of non-MAC frames received that were between

	2048 and 4095 octets in length inclusive."

    ::= { olTRTrafEntry 16 }



olTRTrafFrames4096to8191Octets OBJECT-TYPE

    SYNTAX Counter

    ACCESS read-only

    STATUS mandatory

    DESCRIPTION

	"The total number of non-MAC frames received that were between

	4096 and 8191 octets in length inclusive."

    ::= { olTRTrafEntry 17 }



olTRTrafFrames8192to18000Octets OBJECT-TYPE

    SYNTAX Counter

    ACCESS read-only

    STATUS mandatory

    DESCRIPTION

	"The total number of non-MAC frames received that were between

	8192 and 18000 octets in length inclusive."

    ::= { olTRTrafEntry 18 }



olTRTrafFramesGreaterThan18000Octets OBJECT-TYPE

    SYNTAX Counter

    ACCESS read-only

    STATUS mandatory

    DESCRIPTION

	"The total number of non-MAC frames received that were

	greater than or equal to 18000 octets in length."

    ::= { olTRTrafEntry 19 }





-- Station and Port Traffic





-- The OlTRTrafControl, OlTRTrafStation, OlTRTrafPort, OlTRTrafTopN, and

-- OlTRTrafTopNSummary Groups



--

-- New stations on the token ring network are discovered by

-- keeping a list of source and destination MAC Addresses seen

-- in good frames.  For each of these addresses, a set of statistics

-- is maintained.  The OlTRTrafStation, OlTRTrafPort, OlTRTrafTopN,

-- and OlTRTrafTopNSummary Groups provide four different ways

-- to retrieve this information.

--

-- Note that the list of stations will include

--	- stations internal to the concentrator on the local ring

--	- stations external to the concentrator on the local ring

--	- stations on remote rings

--

-- If the list is full, the least recently used entries not on the local ring

-- will be deleted first, as needed.



-- The olTRTrafStationTable contains entries for each address

-- discovered on a particular interface.  Each entry

-- contains statistical data about that station.  This table

-- is indexed by Network ID and the MAC address of the station.



-- The olTRTrafPortTable contains data in the same format as the

-- olTRTrafStationTable, and contains the same set of stations

-- except that stations external to the concentrator or not on the local ring

-- are omitted.  The olTRTrafPortTable is

-- indexed by Network ID, SlotIndex and PortIndex.



-- The olTRTrafTopNTable is composed of 7 sublists, one for each statistic.

-- Each sublist contains the same set of stations as

-- olTRTrafStationTable.  The stations in each sublist are sorted by

-- the statistic specified in olTRTrafTopNStatistic.

-- The olTRTrafTopNTable is indexed by olTRTrafTopNNetID,

-- by olTRTrafTopNStatistic to identify the sublist,

-- and by olTRTrafTopNIndex (1..N) with index 1 referring to

-- the entry with the highest value of the specifed counter.

-- (See description of olTRTrafTopNTable)



-- The olTRTrafTopNSummaryTable contains the same information as

-- olTRTrafTopNTable, but in a condensed format.



-- Note that table entries may be added, deleted, or resorted at any time.

-- There are three methods available for a management station to address this.



-- METHOD 1

-- Each of the 4 tables has an associated "-LastChangeTime" entry in

-- olTRTrafControlTable.  A management station should read the

-- associated "-LastChangeTime" entry before and after reading a group of

-- table entries.  If the before and after "-LastChangeTimes differ then the

-- management station should repeat the reading of table entries.



-- METHOD 2

-- Use olTRTrafControlLogicalLock and olTRTrafControlLogicalState to ensure

-- that changes don't occur while retrieving table entries.

-- (see description below)



-- METHOD 3

-- Don't worry about table entry changes.  Probably they won't happen while

-- you are reading the table.  The worst that would happen is you might miss

-- a few stations or see the same station twice in the list.





olTRTrafControlTable OBJECT-TYPE

    SYNTAX SEQUENCE OF OlTRTrafControlEntry

    ACCESS not-accessible

    STATUS mandatory

    DESCRIPTION

	"A list entries containing information about

	olTRTrafStationTable, olTRTrafPortTable, olTRTrafTopNTable, and

	olTRTrafTopNSummaryTable"

    ::= { olTRnet 7 }



olTRTrafControlEntry OBJECT-TYPE

    SYNTAX OlTRTrafControlEntry

    ACCESS not-accessible

    STATUS mandatory

    DESCRIPTION

	"A collection of information about

	olTRTrafStationTable, olTRTrafPortTable, olTRTrafTopNTable, and

	olTRTrafTopNSummaryTable"

    INDEX { olTRTrafControlNetID }

    ::= { olTRTrafControlTable 1 }



OlTRTrafControlEntry ::= SEQUENCE {

  olTRTrafControlNetID			INTEGER,

  olTRTrafControlLogicalState		INTEGER,

  olTRTrafControlLogicalLock		INTEGER,

  olTRTrafControlClear			INTEGER,

  olTRTrafControlLastClearTime		TimeTicks,

  olTRTrafControlTotalStations		INTEGER,

  olTRTrafControlStationLastChangeTime  TimeTicks,

  olTRTrafControlPortTotalStations	INTEGER,

  olTRTrafControlPortLastChangeTime	TimeTicks,

  olTRTrafControlTopNMaxStations	INTEGER,

  olTRTrafControlTopNTotalStations	INTEGER,

  olTRTrafControlTopNLastChangeTime	TimeTicks,

  olTRTrafControlTopNInterval		INTEGER

}



olTRTrafControlNetID OBJECT-TYPE

	SYNTAX INTEGER {

		isolated(2),

		token-ring-1(9),

		token-ring-2(10),

		token-ring-3(11),

		token-ring-4(12),

		token-ring-5(13),

		token-ring-6(14),

		token-ring-7(15)

		}

	ACCESS read-only

	STATUS mandatory

	DESCRIPTION

		"The network index that uniquely identifies this network.

		One of token-ring-1 through token-ring-7 or isolated."

	::= { olTRTrafControlEntry 1 }



olTRTrafControlLogicalState OBJECT-TYPE

	SYNTAX INTEGER {

		changing(1),

		notChanging(2)

		}

	ACCESS read-only

	STATUS mandatory

	DESCRIPTION

		"The state of the token ring station traffic tables:

		olTRTrafStationTable, olTRTrafPortTable, olTRTrafTopNTable

		and olTRTrafTopNSummaryTable. If any of the tables associated

		with this olTRTrafControlEntry are being updated,

		then the state is changing(1)."

	::= { olTRTrafControlEntry 2 }



olTRTrafControlLogicalLock OBJECT-TYPE

	SYNTAX INTEGER {

		lock(1),

		unlock(2)

		}

	ACCESS read-write

	STATUS mandatory

	DESCRIPTION

		"A semaphore for locking the token ring station traffic

		tables: olTRTrafStationTable, olTRTrafPortTable,

		olTRTrafTopNTable, and olTRTrafTopNSummaryTable.

		When the semaphore is locked, adds, deletes, and re-sorting

		the traffic tables associated with this

		olTRTrafControlEntry will pend until the

		semaphore is unlocked, so that a valid set of entries

		can be read.  Note that the normal incrementing of the traffic

		counters are not affected by the setting of this semaphore.

		This cannot be set to unlock if olTRTrafControlLogicalState is

		changing.

		For complete accuracy, this semaphore

		should be read after being set to

		ensure that the tables were not changing when the lock was

		attempted. After the table information has been recorded,

		the semaphore should be set to unlock to allow changes to

		occur."

	::= { olTRTrafControlEntry 3 }





olTRTrafControlClear OBJECT-TYPE

  SYNTAX INTEGER {

	  normal(1),

	  clear(2)

  }

  ACCESS read-write

  STATUS mandatory

  DESCRIPTION

	"When the value of this object is set to clear,

	all entries in the token ring station traffic

	tables (olTRTrafStationTable, olTRTrafPortTable,

	olTRTrafTopNTable, and olTRTrafTopNSummaryTable) are cleared."

    ::= { olTRTrafControlEntry 4 }



olTRTrafControlLastClearTime OBJECT-TYPE

  SYNTAX TimeTicks

  ACCESS read-only

  STATUS mandatory

  DESCRIPTION

	"The value of sysUpTime when the token ring station traffic

	tables (olTRTrafStationTable, olTRTrafPortTable,

	olTRTrafTopNTable and olTRTrafTopNSummaryTable) were cleared.

	If never cleared, this value shall be zero (and the token ring

	station traffic tables will contain information collected since

	startup)."

    ::= { olTRTrafControlEntry 5 }



olTRTrafControlTotalStations OBJECT-TYPE

  SYNTAX INTEGER

  ACCESS read-only

  STATUS mandatory

  DESCRIPTION

	"The number of stations in the portion of the olTRTrafStationTable

	associated with this olTRTrafControlEntry."

    ::= { olTRTrafControlEntry 6 }



olTRTrafControlStationLastChangeTime OBJECT-TYPE

  SYNTAX TimeTicks

  ACCESS read-only

  STATUS mandatory

  DESCRIPTION

      "The value of sysUpTime when the last entry

      was added to or deleted (or re-sorted)

      from the portion of the olTRTrafStationTable

      associated with this olTRTrafControlEntry.  If no

      additions or deletions have occurred, this value shall be zero."

    ::= { olTRTrafControlEntry 7 }



olTRTrafControlPortTotalStations OBJECT-TYPE

  SYNTAX INTEGER

  ACCESS read-only

  STATUS mandatory

  DESCRIPTION

	"The number of stations in the portion of the olTRTrafPortTable

	associated with this olTRTrafControlEntry."

    ::= { olTRTrafControlEntry 8 }



olTRTrafControlPortLastChangeTime OBJECT-TYPE

  SYNTAX TimeTicks

  ACCESS read-only

  STATUS mandatory

  DESCRIPTION

      "The value of sysUpTime when the last entry

      was added to or deleted (or re-sorted)

      from the portion of the olTRTrafPortTable

      associated with this olTRTrafControlEntry.  If no

      additions or deletions have occurred, this value shall be zero."

    ::= { olTRTrafControlEntry 9 }



olTRTrafControlTopNMaxStations OBJECT-TYPE

  SYNTAX INTEGER

  ACCESS read-write

  STATUS mandatory

  DESCRIPTION

	"Specifies a maximum value for olTRTrafControlTopNTotalStations

	in this olTRTrafControlEntry.  If this value is zero then no

	maximum value for olTRTrafControlTopNTotalStations is specified."

--	DEFVAL { 0 }

    ::= { olTRTrafControlEntry 10 }



olTRTrafControlTopNTotalStations OBJECT-TYPE

  SYNTAX INTEGER

  ACCESS read-only

  STATUS mandatory

  DESCRIPTION

	"The number of stations (for each statistic) in the portion of

	the olTRTrafTopNTable and olTRTrafTopNSummaryTable associated

	with this olTRTrafControlEntry.  If olTRTrafControlTopNMaxStations

	is zero or is not less than olTRTrafControlTotalStations then

	olTRTrafControlTopNTotalStations will have the same value as

	olTRTrafControlTotalStations.  Otherwise

	olTRTrafControlTopNTotalStations will

	have the same value as olTRTrafControlTopNMaxStations."

    ::= { olTRTrafControlEntry 11 }



olTRTrafControlTopNLastChangeTime OBJECT-TYPE

  SYNTAX TimeTicks

  ACCESS read-only

  STATUS mandatory

  DESCRIPTION

      "The value of sysUpTime when the last entry

      was added to or deleted (or re-sorted)

      from the portion of the olTRTrafTopNTable and olTRTrafTopNSummaryTable

      associated with this olTRTrafControlEntry.

      This is equivalent to the time when

      the last TopN data collection period ended.

      If no additions or deletions have occurred, this value shall be zero."

    ::= { olTRTrafControlEntry 12 }



olTRTrafControlTopNInterval OBJECT-TYPE

  SYNTAX INTEGER

  ACCESS read-write

  STATUS mandatory

  DESCRIPTION

      "Specifies the length of the TopN data collection period in seconds.

      Minimum length is 5 seconds; maximum is 86400 seconds (24 hours).

      When this value is modified, all associated entries in

      olTRTrafTopNTable and olTRTrafTopNSummaryTable are deleted and a new

      TopN data collection period is started."

--	DEFVAL {30}

    ::= { olTRTrafControlEntry 13 }





olTRTrafStationTable OBJECT-TYPE

  SYNTAX SEQUENCE OF OlTRTrafStationEntry

  ACCESS not-accessible

  STATUS mandatory

  DESCRIPTION

      "A list of Token Ring station traffic statistics entries

      indexed by Network ID and MAC address.  The table has

      olTRTrafTotalStations entries.

	Note that all of the frame and octet counters in this table

	include error frames that have valid length;

	all octet counters exclude framing bits but include FCS octets."

  ::= { olTRnet 8 }



olTRTrafStationEntry OBJECT-TYPE

  SYNTAX OlTRTrafStationEntry

  ACCESS not-accessible

  STATUS mandatory

  DESCRIPTION

      "A collection of station statistics for a particular station

      that has been discovered on an interface of this

      device.

	Note that all of the frame and octet counters in this table

	include error frames that have valid length;

	all octet counters exclude framing bits but include FCS octets."

  INDEX { olTRTrafStationNetID,

		olTRTrafStationAddress }

  ::= { olTRTrafStationTable 1 }



OlTRTrafStationEntry ::= SEQUENCE {

  olTRTrafStationNetID			INTEGER,

  olTRTrafStationAddress		MacAddress,

  olTRTrafStationSlotIndex		INTEGER,

  olTRTrafStationPortIndex		INTEGER,

  olTRTrafStationInFrames		Counter,

  olTRTrafStationOutFrames		Counter,

  olTRTrafStationInOctets		Counter,

  olTRTrafStationOutOctets		Counter,

  olTRTrafStationOutErrors		Counter,

  olTRTrafStationOutBroadcastFrames	Counter,

  olTRTrafStationOutMulticastFrames	Counter

}



olTRTrafStationNetID OBJECT-TYPE

	SYNTAX INTEGER {

		isolated(2),

		token-ring-1(9),

		token-ring-2(10),

		token-ring-3(11),

		token-ring-4(12),

		token-ring-5(13),

		token-ring-6(14),

		token-ring-7(15)

		}

	ACCESS read-only

	STATUS mandatory

	DESCRIPTION

		"The network index that uniquely identifies this network.

		One of token-ring-1 through token-ring-7 or isolated."

	::= { olTRTrafStationEntry 1 }



olTRTrafStationAddress OBJECT-TYPE

  SYNTAX MacAddress

  ACCESS read-only

  STATUS mandatory

  DESCRIPTION

      "The physical address of this station."

  ::= { olTRTrafStationEntry 2 }



olTRTrafStationSlotIndex OBJECT-TYPE

	SYNTAX INTEGER {

		slot-1(1),

		slot-2(2),

		slot-3(3),

		slot-4(4),

		slot-5(5),

		slot-6(6),

		slot-7(7),

		slot-8(8),

		slot-9(9),

		slot-10(10),

		slot-11(11),

		slot-12(12),

		slot-13(13),

		slot-14(14),

		slot-15(15),

		slot-16(16),

		slot-17(17),

		remote-ring(254),

		external(255)

		}

	ACCESS read-only

	STATUS mandatory

	DESCRIPTION

		"The slot number of the station with this address.

		Addresses with a slot value of remote-ring(254) are

		not in this ring.

		Addresses with a slot value of external(255) are

		not in this concentrator."

  ::= { olTRTrafStationEntry 3 }



olTRTrafStationPortIndex OBJECT-TYPE

	SYNTAX INTEGER

	ACCESS read-only

	STATUS mandatory

	DESCRIPTION

		"The port number within olTRTrafSlotIndex's

		slot that received this address.

		If olTRTrafSlotIndex has a value of

		remote-ring(254), then the port address will be 254.

		If olTRTrafSlotIndex has a value of

		external(255), then the port address will be 255."

  ::= { olTRTrafStationEntry 4 }



olTRTrafStationInFrames OBJECT-TYPE

  SYNTAX Counter

  ACCESS read-only

  STATUS mandatory

  DESCRIPTION

      "The number of frames transmitted to this address since it was

      added to this table."

  ::= { olTRTrafStationEntry 5 }



olTRTrafStationOutFrames OBJECT-TYPE

  SYNTAX Counter

  ACCESS read-only

  STATUS mandatory

  DESCRIPTION

      "The number of frames transmitted by this address since it was

      added to this table."

  ::= { olTRTrafStationEntry 6 }



olTRTrafStationInOctets OBJECT-TYPE

  SYNTAX Counter

  ACCESS read-only

  STATUS mandatory

  DESCRIPTION

      "The number of octets transmitted to this address since it was

      added to this table."

  ::= { olTRTrafStationEntry 7 }



olTRTrafStationOutOctets OBJECT-TYPE

  SYNTAX Counter

  ACCESS read-only

  STATUS mandatory

  DESCRIPTION

      "The number of octets transmitted by this address since it was

      added to this table."

  ::= { olTRTrafStationEntry 8 }



olTRTrafStationOutErrors OBJECT-TYPE

  SYNTAX Counter

  ACCESS read-only

  STATUS mandatory

  DESCRIPTION

      "The number of error frames transmitted by this

      address since it was added to this table.  Only isolating errors

      (LineErrors, BurstErrors, ACErrors, InternalErrors, and AbortErrors)

      and CongestionErrors are counted."

  ::= { olTRTrafStationEntry 9 }



olTRTrafStationOutBroadcastFrames OBJECT-TYPE

  SYNTAX Counter

  ACCESS read-only

  STATUS mandatory

  DESCRIPTION

      "The number of frames transmitted by this address

      that were directed to the broadcast address since it was

      added to this table."

  ::= { olTRTrafStationEntry 10 }



olTRTrafStationOutMulticastFrames OBJECT-TYPE

  SYNTAX Counter

  ACCESS read-only

  STATUS mandatory

  DESCRIPTION

      "The number of frames transmitted by this address

      that were directed to a multicast address since it was

      added to this table.

      Note that this number does not include frames

      directed to the broadcast address."

  ::= { olTRTrafStationEntry 11 }





olTRTrafPortTable OBJECT-TYPE

  SYNTAX SEQUENCE OF OlTRTrafPortEntry

  ACCESS not-accessible

  STATUS mandatory

  DESCRIPTION

      "A list of Token Ring station traffic statistics entries

      indexed by slot number, and port number.  Note that stations external

      to this concentrator or on another ring are excluded from this table.

	Note that all of the frame and octet counters in this table

	include error frames that have valid length;

	all octet counters exclude framing bits but include FCS octets."

  ::= { olTRnet 9 }



olTRTrafPortEntry OBJECT-TYPE

  SYNTAX OlTRTrafPortEntry

  ACCESS not-accessible

  STATUS mandatory

  DESCRIPTION

      "A collection of station statistics for a particular station

      that has been discovered on an interface of this

      device.

	Note that all of the frame and octet counters in this table

	include error frames that have valid length;

	all octet counters exclude framing bits but include FCS octets.

	include error frames; all octet counters exclude framing bits

	but include FCS octets."

  INDEX { olTRTrafPortSlotIndex, olTRTrafPortPortIndex }

  ::= { olTRTrafPortTable 1 }



OlTRTrafPortEntry ::= SEQUENCE {

  olTRTrafPortSlotIndex		  INTEGER,

  olTRTrafPortPortIndex		  INTEGER,

  olTRTrafPortNetID		  INTEGER,

  olTRTrafPortAddress		  MacAddress,

  olTRTrafPortInFrames		    Counter,

  olTRTrafPortOutFrames		    Counter,

  olTRTrafPortInOctets		  Counter,

  olTRTrafPortOutOctets		  Counter,

  olTRTrafPortOutErrors		  Counter,

  olTRTrafPortOutBroadcastFrames    Counter,

  olTRTrafPortOutMulticastFrames    Counter

}



olTRTrafPortSlotIndex OBJECT-TYPE

	SYNTAX INTEGER

	ACCESS read-only

	STATUS mandatory

	DESCRIPTION

		"The slot number of the station with this address."

  ::= { olTRTrafPortEntry 1 }



olTRTrafPortPortIndex OBJECT-TYPE

	SYNTAX INTEGER

	ACCESS read-only

	STATUS mandatory

	DESCRIPTION

		"The port number within olTRTrafPortSlotIndex's

		slot that received this address."

  ::= { olTRTrafPortEntry 2 }



olTRTrafPortNetID OBJECT-TYPE

	SYNTAX INTEGER {

		isolated(2),

		token-ring-1(9),

		token-ring-2(10),

		token-ring-3(11),

		token-ring-4(12),

		token-ring-5(13),

		token-ring-6(14),

		token-ring-7(15)

		}

	ACCESS read-only

	STATUS mandatory

	DESCRIPTION

		"The network index that uniquely identifies this network.

		One of token-ring-1 through token-ring-7 or isolated."

	::= { olTRTrafPortEntry 3 }



olTRTrafPortAddress OBJECT-TYPE

  SYNTAX MacAddress

  ACCESS read-only

  STATUS mandatory

  DESCRIPTION

      "The physical address of this station."

  ::= { olTRTrafPortEntry 4 }



olTRTrafPortInFrames OBJECT-TYPE

  SYNTAX Counter

  ACCESS read-only

  STATUS mandatory

  DESCRIPTION

      "The number of frames transmitted to this address since it was

      added to this table."

  ::= { olTRTrafPortEntry 5 }



olTRTrafPortOutFrames OBJECT-TYPE

  SYNTAX Counter

  ACCESS read-only

  STATUS mandatory

  DESCRIPTION

      "The number of frames transmitted by this address since it was

      added to this table."

  ::= { olTRTrafPortEntry 6 }



olTRTrafPortInOctets OBJECT-TYPE

  SYNTAX Counter

  ACCESS read-only

  STATUS mandatory

  DESCRIPTION

      "The number of octets transmitted to this address since it was

      added to this table."

  ::= { olTRTrafPortEntry 7 }



olTRTrafPortOutOctets OBJECT-TYPE

  SYNTAX Counter

  ACCESS read-only

  STATUS mandatory

  DESCRIPTION

      "The number of octets transmitted by this address since it was

      added to this table."

  ::= { olTRTrafPortEntry 8 }



olTRTrafPortOutErrors OBJECT-TYPE

  SYNTAX Counter

  ACCESS read-only

  STATUS mandatory

  DESCRIPTION

      "The number of error frames transmitted by this

      address since it was added to this table.  Only isolating errors

      (LineErrors, BurstErrors, ACErrors, InternalErrors, and AbortErrors)

      and CongestionErrors are counted."

  ::= { olTRTrafPortEntry 9 }



olTRTrafPortOutBroadcastFrames OBJECT-TYPE

  SYNTAX Counter

  ACCESS read-only

  STATUS mandatory

  DESCRIPTION

      "The number of frames transmitted by this address

      that were directed to the broadcast address since it was

      added to this table."

  ::= { olTRTrafPortEntry 10 }



olTRTrafPortOutMulticastFrames OBJECT-TYPE

  SYNTAX Counter

  ACCESS read-only

  STATUS mandatory

  DESCRIPTION

      "The number of frames transmitted by this address

      that were directed to a multicast address since it was

      added to this table.

      Note that this number does not include frames

      directed to the broadcast address."

  ::= { olTRTrafPortEntry 11 }





olTRTrafTopNTable OBJECT-TYPE

  SYNTAX SEQUENCE OF OlTRTrafTopNEntry

  ACCESS not-accessible

  STATUS mandatory

  DESCRIPTION

      "A list of Token Ring station traffic statistics entries indexed by

	olTRTrafTopNNetID, olTRTrafTopNStatistic, and olTRTrafTopNIndex.

	For each Network, the list contains 7 logical sublists - one for

	each statistic.

	Each of the sublists has olTRTrafControlTopNTotalStations entries.

	For eack Network, the table has 7 times

	olTRTrafTopNControlTotalStations entries.

	All of the counters in this table reflect activity during the last

	completed TopN data collection period

	(olTRTrafControlTopNInterval seconds).

	Note that this table will contain no entries

	if a TopN data collection period has not yet completed since

	olTRTrafControlTopNInterval was modified or since startup.

	Note that all of the frame and octet counters in this table

	include error frames that have valid length;

	all octet counters exclude framing bits but include FCS octets."

  ::= { olTRnet 10 }



olTRTrafTopNEntry OBJECT-TYPE

  SYNTAX OlTRTrafTopNEntry

  ACCESS not-accessible

  STATUS mandatory

  DESCRIPTION

      "A collection of station statistics for a particular station

      that has been discovered on an interface of this

      device.

	Note that all of the frame and octet counters in this table

	include error frames that have valid length;

	all octet counters exclude framing bits but include FCS octets."

  INDEX { olTRTrafTopNNetID,

		olTRTrafTopNStatistic,

		olTRTrafTopNIndex }

  ::= { olTRTrafTopNTable 1 }



OlTRTrafTopNEntry ::= SEQUENCE {

  olTRTrafTopNNetID		  INTEGER,

  olTRTrafTopNStatistic		  INTEGER,

  olTRTrafTopNIndex		  INTEGER,

  olTRTrafTopNAddress		  MacAddress,

  olTRTrafTopNSlotIndex		  INTEGER,

  olTRTrafTopNPortIndex		  INTEGER,

  olTRTrafTopNInFrames		    Counter,

  olTRTrafTopNOutFrames		    Counter,

  olTRTrafTopNInOctets		  Counter,

  olTRTrafTopNOutOctets		  Counter,

  olTRTrafTopNOutErrors		  Counter,

  olTRTrafTopNOutBroadcastFrames    Counter,

  olTRTrafTopNOutMulticastFrames    Counter

}



olTRTrafTopNNetID OBJECT-TYPE

	SYNTAX INTEGER {

		isolated(2),

		token-ring-1(9),

		token-ring-2(10),

		token-ring-3(11),

		token-ring-4(12),

		token-ring-5(13),

		token-ring-6(14),

		token-ring-7(15)

		}

	ACCESS read-only

	STATUS mandatory

	DESCRIPTION

		"The network index that uniquely identifies this network.

		One of token-ring-1 through token-ring-7 or isolated."

	::= { olTRTrafTopNEntry 1 }



olTRTrafTopNStatistic OBJECT-TYPE

  SYNTAX INTEGER {

	  olTRTrafTopNInFrames(1),

	  olTRTrafTopNOutFrames(2),

	  olTRTrafTopNInOctets(3),

	  olTRTrafTopNOutOctets(4),

	  olTRTrafTopNOutErrors(5),

	  olTRTrafTopNOutBroadcastFrames(6),

	  olTRTrafTopNOutMulticastFrames(7)

  }

  ACCESS read-only

  STATUS mandatory

  DESCRIPTION

      "The object representing the statistic for each station that this

      portion of the olTRTrafTopNTable is sorted on."

    ::= { olTRTrafTopNEntry 2 }



olTRTrafTopNIndex OBJECT-TYPE

  SYNTAX INTEGER

  ACCESS read-only

  STATUS mandatory

  DESCRIPTION

      "An index that uniquely identifies an entry in

      the olTRTrafTopN table among those in the same network

      and for the same olTRTrafTopNStatistic.

      This index is between 1 and N, where N is the value of

      olTRTrafControlTopNTotalStations.  Increasing values

      of olTRTrafTopNIndex shall be assigned to entries with

      decreasing values of the object referenced by olTRTrafTopNStatistic."

  ::= { olTRTrafTopNEntry 3 }



olTRTrafTopNAddress OBJECT-TYPE

  SYNTAX MacAddress

  ACCESS read-only

  STATUS mandatory

  DESCRIPTION

      "The physical address of this station."

  ::= { olTRTrafTopNEntry 4 }



olTRTrafTopNSlotIndex OBJECT-TYPE

	SYNTAX INTEGER {

		slot-1(1),

		slot-2(2),

		slot-3(3),

		slot-4(4),

		slot-5(5),

		slot-6(6),

		slot-7(7),

		slot-8(8),

		slot-9(9),

		slot-10(10),

		slot-11(11),

		slot-12(12),

		slot-13(13),

		slot-14(14),

		slot-15(15),

		slot-16(16),

		slot-17(17),

		remote-ring(254),

		external(255)

		}

	ACCESS read-only

	STATUS mandatory

	DESCRIPTION

		"The slot number of the station with this address.

		Addresses with a slot value of remote-ring(254) are

		not in this ring.

		Addresses with a slot value of external(255) are

		not in this concentrator."

  ::= { olTRTrafTopNEntry 5 }



olTRTrafTopNPortIndex OBJECT-TYPE

	SYNTAX INTEGER

	ACCESS read-only

	STATUS mandatory

	DESCRIPTION

		"The port number within olTRTrafTopNSlotIndex's

		slot that received this address.

		If olTRTrafTopNSlotIndex has a value of

		remote-ring(254), then the port address will be 254.

		If olTRTrafTopNSlotIndex has a value of

		external(255), then the port address will be 255."

  ::= { olTRTrafTopNEntry 6 }



olTRTrafTopNInFrames OBJECT-TYPE

  SYNTAX Counter

  ACCESS read-only

  STATUS mandatory

  DESCRIPTION

      "The number of frames transmitted to this address

      during the last TopN data collection period."

  ::= { olTRTrafTopNEntry 7 }



olTRTrafTopNOutFrames OBJECT-TYPE

  SYNTAX Counter

  ACCESS read-only

  STATUS mandatory

  DESCRIPTION

      "The number of frames transmitted by this address

      during the last TopN data collection period."

  ::= { olTRTrafTopNEntry 8 }



olTRTrafTopNInOctets OBJECT-TYPE

  SYNTAX Counter

  ACCESS read-only

  STATUS mandatory

  DESCRIPTION

      "The number of octets transmitted to this address

      during the last TopN data collection period."

  ::= { olTRTrafTopNEntry 9 }



olTRTrafTopNOutOctets OBJECT-TYPE

  SYNTAX Counter

  ACCESS read-only

  STATUS mandatory

  DESCRIPTION

      "The number of octets transmitted by this address

      during the last TopN data collection period."

  ::= { olTRTrafTopNEntry 10 }



olTRTrafTopNOutErrors OBJECT-TYPE

  SYNTAX Counter

  ACCESS read-only

  STATUS mandatory

  DESCRIPTION

      "The number of error frames transmitted by this address

      during the last TopN data collection period.  Only isolating errors

      (LineErrors, BurstErrors, ACErrors, InternalErrors, and AbortErrors)

      and CongestionErrors are counted."

  ::= { olTRTrafTopNEntry 11 }



olTRTrafTopNOutBroadcastFrames OBJECT-TYPE

  SYNTAX Counter

  ACCESS read-only

  STATUS mandatory

  DESCRIPTION

      "The number of frames transmitted by this address

      that were directed to the broadcast address

      during the last TopN data collection period."

  ::= { olTRTrafTopNEntry 12 }



olTRTrafTopNOutMulticastFrames OBJECT-TYPE

  SYNTAX Counter

  ACCESS read-only

  STATUS mandatory

  DESCRIPTION

      "The number of frames transmitted by this address

      that were directed to a multicast address

      during the last TopN data collection period.

      Note that this number does not include frames

      directed to the broadcast address."

  ::= { olTRTrafTopNEntry 13 }





olTRTrafTopNSummaryTable OBJECT-TYPE

  SYNTAX SEQUENCE OF OlTRTrafTopNSummaryEntry

  ACCESS not-accessible

  STATUS mandatory

  DESCRIPTION

      "A list containing information from olTRTrafTopNTable

	provided for the convenience of network management stations

	that wish to obtain this information in condensed form."

  ::= { olTRnet 11 }



olTRTrafTopNSummaryEntry OBJECT-TYPE

  SYNTAX OlTRTrafTopNSummaryEntry

  ACCESS not-accessible

  STATUS mandatory

  DESCRIPTION

      "A segment of the Top N list for a particular statistic."

  INDEX { olTRTrafTopNSummaryNetID,

		olTRTrafTopNSummaryStatistic,

		olTRTrafTopNSummaryIndex }

  ::= { olTRTrafTopNSummaryTable 1 }



OlTRTrafTopNSummaryEntry ::= SEQUENCE {

  olTRTrafTopNSummaryNetID		 INTEGER,

  olTRTrafTopNSummaryStatistic		  INTEGER,

  olTRTrafTopNSummaryIndex		 INTEGER,

  olTRTrafTopNSummaryStations		OCTET STRING

}



olTRTrafTopNSummaryNetID OBJECT-TYPE

	SYNTAX INTEGER {

		isolated(2),

		token-ring-1(9),

		token-ring-2(10),

		token-ring-3(11),

		token-ring-4(12),

		token-ring-5(13),

		token-ring-6(14),

		token-ring-7(15)

		}

	ACCESS read-only

	STATUS mandatory

	DESCRIPTION

		"The network index that uniquely identifies this network.

		One of token-ring-1 through token-ring-7 or isolated."

	::= { olTRTrafTopNSummaryEntry 1 }



olTRTrafTopNSummaryStatistic OBJECT-TYPE

  SYNTAX INTEGER {

	  olTRTrafTopNSummaryInFrames(1),

	  olTRTrafTopNSummaryOutFrames(2),

	  olTRTrafTopNSummaryInOctets(3),

	  olTRTrafTopNSummaryOutOctets(4),

	  olTRTrafTopNSummaryOutErrors(5),

	  olTRTrafTopNSummaryOutBroadcastFrames(6),

	  olTRTrafTopNSummaryOutMulticastFrames(7)

  }

  ACCESS read-only

  STATUS mandatory

  DESCRIPTION

      "The object representing the statistic for each station that this

      portion of the olTRTrafTopNSummaryTable is sorted on."

    ::= { olTRTrafTopNSummaryEntry 2 }



olTRTrafTopNSummaryIndex OBJECT-TYPE

  SYNTAX INTEGER

  ACCESS read-only

  STATUS mandatory

  DESCRIPTION

	"An index that uniquely identifies an entry in

	the olTRTrafTopNSummary table among those in the same network

	and for the same olTRTrafTopNSummaryStatistic.

	The number of entries for this portion of olTRTrafTopNSummaryTable

	is number of entries for the corresponding portion of

	olTRTrafTopNTable divided by 12 (rounded up to the next integer)."

  ::= { olTRTrafTopNSummaryEntry 3 }



olTRTrafTopNSummaryStations OBJECT-TYPE

	SYNTAX OCTET STRING

	ACCESS read-only

	STATUS mandatory

	DESCRIPTION

		"A concatonated list of (up to 12) MAC addresses,

		their associated slot and port, and a statistic value

		for traffic associated with stations on the ring.  Each entry

		has 36 octets. The first 6 octets are the MAC address.

		The 7th octet is the slot ID (or 255 if it is external

		to the concentrator or 254 if it is on a remote ring).

		The 8th is the port ID (or 255 if it is external to the

		concentrator or 254 if it is on a remote ring).

		The 9th through 36th octets contain the values of the

		statistics olTRTrafTopNInFrames, olTRTrafTopNOutFrames,

		olTRTrafTopNInOctets, olTRTrafTopNOutOctets,

		olTRTrafTopNOutErrors, olTRTrafTopNOutBroadcastFrames,

		and olTRTrafTopNOutMulticastFrames.  Each statistic is

		represented in 4 octets, most significant octet first.

		The stations are in order of decreasing values of the

		statistic referenced by olTRTrafTopNStatistic."

	::= { olTRTrafTopNSummaryEntry 4 }





-- The olFDDInet Group



olFDDIStatsModTable OBJECT-TYPE

	SYNTAX SEQUENCE OF OlFDDIStatsModEntry

	ACCESS not-accessible

	STATUS mandatory

	DESCRIPTION

		"A table of statistical information counted for each module

		in each FDDI network."

	::= { olFDDInet 2 }



olFDDIStatsModEntry OBJECT-TYPE

	SYNTAX OlFDDIStatsModEntry

	ACCESS not-accessible

	STATUS mandatory

	DESCRIPTION

		"A list of statistical information for each module

		on each FDDI network in the concentrator."

	INDEX { olFDDIStatsModSlotIndex }

	::= { olFDDIStatsModTable 1 }



OlFDDIStatsModEntry ::=

	SEQUENCE {

		olFDDIStatsModSlotIndex

			INTEGER,

		olFDDIStatsModMgtRcvErrs

			Counter,

		olFDDIStatsModMgtXmitErrs

			Counter,

		olFDDIStatsModBackplaneErrs

			Counter,

		olFDDIStatsModPllUnlockErrs

			Counter

		}



olFDDIStatsModSlotIndex OBJECT-TYPE

	SYNTAX INTEGER

	ACCESS read-only

	STATUS mandatory

	DESCRIPTION

		"The slot number that contains this module."

	::= { olFDDIStatsModEntry 1 }



olFDDIStatsModMgtRcvErrs OBJECT-TYPE

	SYNTAX Counter

	ACCESS read-only

	STATUS mandatory

	DESCRIPTION

		"The number of errors encountered while receiving data

		 on the Management Channel."

	::= { olFDDIStatsModEntry 2 }



olFDDIStatsModMgtXmitErrs OBJECT-TYPE

	SYNTAX Counter

	ACCESS read-only

	STATUS mandatory

	DESCRIPTION

		"The number of errors encountered while transmitting data

		 on the Management Channel."

	::= { olFDDIStatsModEntry 3 }



olFDDIStatsModBackplaneErrs OBJECT-TYPE

	SYNTAX Counter

	ACCESS read-only

	STATUS mandatory

	DESCRIPTION

		"The number of errors while receiving and transmitting

		 network data on the backplane."

	::= { olFDDIStatsModEntry 4 }



olFDDIStatsModPllUnlockErrs OBJECT-TYPE

	SYNTAX Counter

	ACCESS read-only

	STATUS mandatory

	DESCRIPTION

		"The number of times the phased lock loop on the

		 backplane network data channel was lost."

	::= { olFDDIStatsModEntry 5 }





-- Port table



olFDDIStatsPortTable OBJECT-TYPE

	SYNTAX SEQUENCE OF OlFDDIStatsPortEntry

	ACCESS not-accessible

	STATUS mandatory

	DESCRIPTION

		"A table of statistical information counted for each Port

		in each FDDI network."

	::= { olFDDInet 3 }



olFDDIStatsPortEntry OBJECT-TYPE

	SYNTAX OlFDDIStatsPortEntry

	ACCESS not-accessible

	STATUS mandatory

	DESCRIPTION

		"A list of statistical information for each Port

		on each FDDI network in the concentrator."

	INDEX { olFDDIStatsPortSlotIndex, olFDDIStatsPortIndex }

	::= { olFDDIStatsPortTable 1 }



OlFDDIStatsPortEntry ::=

	SEQUENCE {

		olFDDIStatsPortSlotIndex

			INTEGER,

		olFDDIStatsPortIndex

			INTEGER,

		olFDDIStatsPortLCTFailCts

			Counter,

		olFDDIStatsPortLerEstimate

			INTEGER,

		olFDDIStatsPortLemRejectCts

			Counter,

		olFDDIStatsPortLemCts

			Counter

		}



olFDDIStatsPortSlotIndex OBJECT-TYPE

	SYNTAX INTEGER

	ACCESS read-only

	STATUS mandatory

	DESCRIPTION

		"The slot number that contains this Port."

	::= { olFDDIStatsPortEntry 1 }



olFDDIStatsPortIndex OBJECT-TYPE

	SYNTAX INTEGER

	ACCESS read-only

	STATUS mandatory

	DESCRIPTION

		"The Port number of this port"

	::= { olFDDIStatsPortEntry 2 }



olFDDIStatsPortLCTFailCts OBJECT-TYPE

	SYNTAX Counter

	ACCESS read-only

	STATUS mandatory

	DESCRIPTION

	   "The count of the consecutive times the link

	    confidence test (LCT) has failed during connection

	    management. Once the connection has been established,

	    the count is zeroed. (refer to ANSI 9.4.1)."

	::= { olFDDIStatsPortEntry 3 }



olFDDIStatsPortLerEstimate OBJECT-TYPE

	SYNTAX INTEGER

	ACCESS read-only

	STATUS mandatory

	DESCRIPTION

	    "A long term average link error rate.  It ranges

	     from 10**-4 to 10**-15 and is reported as the

	     absolute value of the exponent of the estimate

	     (the larger the number, the smaller the value)."

	::= { olFDDIStatsPortEntry 4 }



olFDDIStatsPortLemRejectCts OBJECT-TYPE

	SYNTAX Counter

	ACCESS read-only

	STATUS mandatory

	DESCRIPTION

	    "A link error monitoring count of the times that a

	     link has been removed from the ring due to the

	     LerCutOff threshold being exceeded."

	::= { olFDDIStatsPortEntry 5 }



olFDDIStatsPortLemCts OBJECT-TYPE

	SYNTAX Counter

	ACCESS read-only

	STATUS mandatory

	DESCRIPTION

	    "The aggregate link error monitor error count, set

	     to zero only on station power up. This variable's

	     long term rate average is lerEstimate."

	::= { olFDDIStatsPortEntry 6 }





olFDDInetStatsTable OBJECT-TYPE

	SYNTAX SEQUENCE OF OlFDDInetStatsEntry

	ACCESS not-accessible

	STATUS mandatory

	DESCRIPTION

		"A table of statistical information counted for each FDDI

		network in the concentrator"

	::= { olFDDInet 4 }



olFDDInetStatsEntry OBJECT-TYPE

	SYNTAX OlFDDInetStatsEntry

	ACCESS not-accessible

	STATUS mandatory

	DESCRIPTION

		"A list of statistical information for each FDDI

		network in the concentrator."

	INDEX { olFDDInetStatsNetID }

	::= { olFDDInetStatsTable 1 }



OlFDDInetStatsEntry ::=

	SEQUENCE {

		olFDDInetStatsNetID

			INTEGER,

		olFDDInetStatsRingOpCounts

			Counter,

		olFDDInetStatsFrameCounts

			Counter,

		olFDDInetStatsErrorCounts

			Counter,

		olFDDInetStatsLostCounts

			Counter,

		olFDDInetStatsFrameErrorRatio

			INTEGER

	}



olFDDInetStatsNetID OBJECT-TYPE

	SYNTAX INTEGER {

		isolated(2),

		fddi-1(16),

		fddi-2(17),

		fddi-3(18),

		fddi-4(19)

		}

	ACCESS read-only

	STATUS mandatory

	DESCRIPTION

		"The network index that uniquely identifies this network.

		One of isolated, fddi-1, fddi-2, fddi-3, or fddi-4."

	::= { olFDDInetStatsEntry 1 }



olFDDInetStatsRingOpCounts OBJECT-TYPE

	SYNTAX Counter

	ACCESS read-only

	STATUS mandatory

	DESCRIPTION

		"The number times the ring transitioned to operational."

	::= { olFDDInetStatsEntry 2 }



olFDDInetStatsFrameCounts OBJECT-TYPE

	SYNTAX Counter

	ACCESS read-only

	STATUS mandatory

	DESCRIPTION

		"Frame-Ct (refer to ANSI MAC 2.2.1)."

	::= { olFDDInetStatsEntry 3 }



olFDDInetStatsErrorCounts OBJECT-TYPE

	SYNTAX Counter

	ACCESS read-only

	STATUS mandatory

	DESCRIPTION

		"Error-Ct (refer to ANSI MAC 2.2.1)."

	::= { olFDDInetStatsEntry 4 }



olFDDInetStatsLostCounts OBJECT-TYPE

	SYNTAX Counter

	ACCESS read-only

	STATUS mandatory

	DESCRIPTION

		"Lost-Ct (refer to ANSI MAC 2.2.1)."

	::= { olFDDInetStatsEntry 5 }



olFDDInetStatsFrameErrorRatio OBJECT-TYPE

	SYNTAX INTEGER (1..65535)

	ACCESS read-only

	STATUS mandatory

	DESCRIPTION

		"This attribute is the actual ratio, ((delta

		 snmpFddiMACLostCt + delta snmpFddiMACErrorCt) /

		 (delta snmpFddiMACFrameCt + delta

		 snmpFddiMACLostCt)) x 2**16."

	::= { olFDDInetStatsEntry 6 }











-- The olGroups group



-- These objects define ports which have been assigned to groups and actions

-- which can be performed on the groups.  To add ports to a group,

-- olGroupSetAction should be set to add-ports(1) and the port(s) defined

-- by olGroupSetSlotIndex and olGroupSetPortIndex will be added to the group

-- olGroupSetGroupID, if the port exists and is not a logical port.  To remove

-- ports from a group, olGroupSetAction should be set to delete-ports(2) and

-- the port(s) defined by olGroupSetSlotIndex and olGroupSetPortIndex will be

-- removed from the group olGroupSetGroupID.   To change the admin state of

-- all ports in the group, olGroupSetAction should be set to

-- set-admin-state(3) and the ports in group olGroupSetGroupID will be set

-- to the state defined in olGroupSetAdminState.



olGroupPortTable OBJECT-TYPE

	SYNTAX SEQUENCE OF OlGroupPortEntry

	ACCESS not-accessible

	STATUS mandatory

	DESCRIPTION

		"A list of groups that each port is in. Each port can

		can be in 0, 1, or many groups."

	::= { olGroups 1 }



olGroupPortEntry OBJECT-TYPE

	SYNTAX OlGroupPortEntry

	ACCESS not-accessible

	STATUS mandatory

	DESCRIPTION

		"The groups corresponding to a particular port."

	INDEX { olGroupPortSlotIndex, olGroupPortIndex }

	::= { olGroupPortTable 1 }



OlGroupPortEntry ::=

	SEQUENCE {

		olGroupPortSlotIndex

			INTEGER,

		olGroupPortIndex

			INTEGER,

		olGroupPortGroupID

			OCTET STRING

		}



olGroupPortSlotIndex OBJECT-TYPE

	SYNTAX INTEGER

	ACCESS read-only

	STATUS mandatory

	DESCRIPTION

		"The slot number that contains this port."

	::= { olGroupPortEntry 1 }



olGroupPortIndex OBJECT-TYPE

	SYNTAX INTEGER

	ACCESS read-only

	STATUS mandatory

	DESCRIPTION

		"The port number within this slot. Logical ports

		can not be put into groups."

	::= { olGroupPortEntry 2 }



olGroupPortGroupID OBJECT-TYPE

	SYNTAX OCTET STRING (SIZE(0..8))

	ACCESS read-only

	STATUS mandatory

	DESCRIPTION

		"The group(s) to which the port has been assigned."

	::= { olGroupPortEntry 3 }





olGroupSummaryTable OBJECT-TYPE

	SYNTAX SEQUENCE OF OlGroupSummaryEntry

	ACCESS not-accessible

	STATUS mandatory

	DESCRIPTION

		"A table of condensed group information listing all the ports

		in each group."

	::= { olGroups 2 }



olGroupSummaryEntry OBJECT-TYPE

	SYNTAX OlGroupSummaryEntry

	ACCESS not-accessible

	STATUS mandatory

	DESCRIPTION

		"The summary of all the ports in a particular group."

	INDEX { olGroupSummaryGroupID, olGroupSummaryIndex }

	::= { olGroupSummaryTable 1 }



OlGroupSummaryEntry ::=

	SEQUENCE {

		olGroupSummaryGroupID

			INTEGER,

		olGroupSummaryIndex

			INTEGER,

		olGroupSummaryPorts

			OCTET STRING

		}



olGroupSummaryGroupID OBJECT-TYPE

	SYNTAX INTEGER {

		group-1(1),

		group-2(2),

		group-3(3),

		group-4(4),

		group-5(5),

		group-6(6),

		group-7(7),

		group-8(8)

		}

	ACCESS read-only

	STATUS mandatory

	DESCRIPTION

		"The group to which the ports have been assigned. A port

		can be in one or more groups."

	::= { olGroupSummaryEntry 1 }



olGroupSummaryIndex OBJECT-TYPE

	SYNTAX INTEGER

	ACCESS read-only

	STATUS mandatory

	DESCRIPTION

		"The index into the summary array. Up to 256 ports will be shown

		in olGroupSummaryPorts for each value in this entry."

	::= { olGroupSummaryEntry 2 }



olGroupSummaryPorts OBJECT-TYPE

	SYNTAX OCTET STRING (SIZE(0..1400))

	ACCESS read-only

	STATUS mandatory

	DESCRIPTION

		"A condensed list of all the ports in this group. The summary

		is in the format: Slotx PortX SlotY PortY ..."

	::= { olGroupSummaryEntry 3 }





olGroupSet	OBJECT IDENTIFIER ::= { olGroups 3 }





olGroupSetAction OBJECT-TYPE

	SYNTAX INTEGER {

		add-ports(1),

		clear-ports(2),

		set-admin-state(3)

	}

	ACCESS read-write

	STATUS mandatory

	DESCRIPTION

		"This object specifies the action that we apply on

		 a group. add-ports(1) adds port(s) to a group,

		 clear-ports(2) clears (delete) port(s) from a group,

		 and set-admin-state sets the Admin State of

		 the group."

	::= { olGroupSet 1 }





olGroupSetGroupID OBJECT-TYPE

	SYNTAX INTEGER {

		group-1(1),

		group-2(2),

		group-3(3),

		group-4(4),

		group-5(5),

		group-6(6),

		group-7(7),

		group-8(8),

		all-groups(255) -- only valid for olGroupSetAction of

				-- clear-ports(2)

		}

	ACCESS read-write

	STATUS mandatory

	DESCRIPTION

		"A group index that uniquely identifies this group. A port

		can be in zero, one, or more groups."

	::= { olGroupSet 2 }





olGroupSetSlotIndex OBJECT-TYPE

	SYNTAX INTEGER

	ACCESS read-write

	STATUS mandatory

	DESCRIPTION

		"This object specifies the slot number of the port(s) that

		are to be added/cleared to/from the group. This object should

		be set whenever add-ports(1) or clear-ports(2) are selected

		for olGroupSetAction.  Value 254 refers to all non-existing

		ports, and value 255 refers to all slots which are only valid

		when olGroupSetAction is clear-ports(2)."

	::= { olGroupSet 3 }



olGroupSetPortIndex OBJECT-TYPE

	SYNTAX INTEGER

	ACCESS read-write

	STATUS mandatory

	DESCRIPTION

		"This object specifies the port number of the port(s) that

		are to be added/cleared to/from the group. This object should

		be set whenever add-ports(1) or clear-ports(2) are selected

		for olGroupSetAction. Value 255 refers to all ports."

	::= { olGroupSet 4 }





olGroupSetAdminState OBJECT-TYPE

	SYNTAX INTEGER {

		enabled(1),

		disabled(2)

	}

	ACCESS read-write

	STATUS mandatory

	DESCRIPTION

		"This object specifies the Admin State that all the ports in

		the group defined by olGroupSetGroupID should be set to.

		This object should be set whenever set-admin-state(3) is

		selected for olGroupSetAction."

	::= { olGroupSet 5 }





--  Threshold Group



--	This group provides access to agent thresholding.

--	If the agent does not support thresholding, then

--	olThreshTable will have no entries.





olThreshTotalEntries OBJECT-TYPE

  SYNTAX INTEGER

  ACCESS read-only

  STATUS mandatory

  DESCRIPTION

	"The number of entries currently in olThreshTable."

    ::= { olThreshControl 1 }



olThreshMaxEntries OBJECT-TYPE

  SYNTAX INTEGER

  ACCESS read-only

  STATUS mandatory

  DESCRIPTION

	"The maximum number of entries in olThreshTable supported by

	this agent."

    ::= { olThreshControl 2 }



olThreshLastCreatedIndex OBJECT-TYPE

  SYNTAX INTEGER

  ACCESS read-only

  STATUS mandatory

  DESCRIPTION

	"The index of the last entry in olThreshTable created via index 255

	(see olThreshMode).  If none, this value will be zero."

    ::= { olThreshControl 3 }



olThreshAllMode OBJECT-TYPE

	SYNTAX INTEGER {

		enable(1),

		disable(2),

		clear(3)

		}

	ACCESS read-write

	STATUS mandatory

	DESCRIPTION

		"Provides the management station with a convenient way to set

		olThreshMode for all of the entries in ThreshTable.

		Setting olThreshAllMode to enable(1) or disable(2)

		will not cause new entries to be created; this

		will only affect entries that have presiously been created.

		Getting olThreshAllMode will always yield clear(3)."

	::= { olThreshControl 4 }



olThreshTable OBJECT-TYPE

    SYNTAX SEQUENCE OF OlThreshEntry

    ACCESS not-accessible

    STATUS mandatory

    DESCRIPTION

	"A list of thresholding entries."

    ::= { olThresh 2 }



olThreshEntry OBJECT-TYPE

    SYNTAX OlThreshEntry

    ACCESS not-accessible

    STATUS mandatory

    DESCRIPTION

	"A collection of variables for controlling and monitoring a

	specific threshold."

    INDEX { olThreshIndex }

    ::= { olThreshTable 1 }



OlThreshEntry ::= SEQUENCE {

    olThreshIndex		INTEGER,

    olThreshMode		INTEGER,

    olThreshDescription		DisplayString,

    olThreshObjectIdentifier	OBJECT IDENTIFIER,

    olThreshStatCategory	INTEGER,

    olThreshStatType		INTEGER,

    olThreshStatNetID		INTEGER,

    olThreshStatSlotIndex	INTEGER,

    olThreshStatPortIndex	INTEGER,

    olThreshStatStationAddr	MacAddress,

    olThreshInterval		INTEGER,

    olThreshCondition		INTEGER,

    olThreshValue		INTEGER,

    olThreshCurrentValue	INTEGER,

    olThreshStatus		INTEGER,

    olThreshTimeSinceLastTriggered	TimeTicks,

    olThreshActionType		INTEGER,

    olThreshActionData		INTEGER,

    olThreshActionPriority	INTEGER

}



olThreshIndex OBJECT-TYPE

  SYNTAX INTEGER

  ACCESS read-only

  STATUS mandatory

  DESCRIPTION

	"An index that uniquely identifies an entry in

	the olThresh table.  The number of entries in olTRThreshTable

	is olThreshTotalEntries.  A new entry is created when a value is

	written to any object within the entry.  An entry is removed when

	olThreshMode is set to clear(3).

	Index 255 references a 'pseudo entry' that allows

	the management station to create a new entry without having to

	search for a clear entry.

	When olThreshMode for entry 255 is set to disable or enable,

	if there is no available (clear) entry, then the SNMP set-response will

	indicate a bad value error, otherwise the agent does the following:

	    - set the value of olThreshLastCreatedIndex to the index

		of the available entry

	    - copy the values currently in entry 255 to the available entry

	    - clear out entry 255."

  ::= { olThreshEntry 1 }



olThreshMode OBJECT-TYPE

	SYNTAX INTEGER {

		enable(1),

		disable(2),

		clear(3)

		}

	ACCESS read-write

	STATUS mandatory

	DESCRIPTION

		"The mode for this threshold.

		enable(1) indicates that this entry

		is in use and thresholding will be done.

		disable(2) indicates that this entry

		is in use but will no thresholding will be done.

		Setting olThreshMode to clear(3)  will cause this entry to be

		removed from the table."

--	DEFVAL {disable(2)}

	::= { olThreshEntry 2 }



olThreshDescription OBJECT-TYPE

	SYNTAX DisplayString (SIZE(0..40))

	ACCESS read-write

	STATUS mandatory

	DESCRIPTION

		"Description of the threshold to be sent with the

		chipAboveThreshd trap."

	::= { olThreshEntry 3 }



olThreshObjectIdentifier OBJECT-TYPE

	SYNTAX OBJECT IDENTIFIER

	ACCESS read-write

	STATUS mandatory

	DESCRIPTION

		"The object identifier that specifies the statistic to be

		thresholded.  The statistic to be thresholded can be

		specified either by setting olThreshObjectIdentifier

		or by setting values of the olThreshStat group of variables.

		When olThreshObjectIdentifier is set, the agent changes

		the values of the olThreshStat group of variables

		to refer to the new statistic to be thresholded.

		Similarly, when a olThreshStat variable is set, the agent

		changes olThreshObjectIdentifier to refer to the new statistic

		to be thresholded.  A null object identifier (0.0) is used

		when no statistic is specified."

	::= { olThreshEntry 4 }



olThreshStatCategory OBJECT-TYPE

	SYNTAX INTEGER {

		other(1),

		network(2),

		port(3),

		station(4)

	}

	ACCESS read-write

	STATUS mandatory

	DESCRIPTION

		"Specifies the category of statistic to be thresholded.

		When olThreshStatCategory is network(2) or station(4),

		olThreshStatNetID must also be specified and

		olThreshStatSlotIndex will be overwritten as well.

		When olThreshStatCategory is station(4),

		olThreshStatStation must be specified.

		When olThreshStatCategory is port(3), olThreshStatSlotIndex

		and olThreshStatPortIndex must be specified.  Modifying

		olThreshStatSlotIndex in this case will cause

		olThreshStatNetID to be overwritten as well."



--	DEFVAL {network(2)}

	::= { olThreshEntry 5 }



olThreshStatType OBJECT-TYPE

	SYNTAX INTEGER {

		other(1),

		frames(2),

		octets(3),

		broadcast-frames(4),

		multicast-frames(5),

		error-frames(6),

		tr-net-soft-errors(7),

		tr-net-hard-errors(8)

	}

	ACCESS read-write

	STATUS mandatory

	DESCRIPTION

		"Specifies the type of statistic to be thresholded.

		error-frames(6) is valid only when olThreshStatCategory is

		port(3) or station(4).  tr-net-soft-errors(7) or

		tr-net-hard-errors(8) is valid only when olThreshStatCategory

		is network(2).  Note that tr-net-soft-errors(7) and

		tr-net-hard-errors(8) refer to dot5StatsSoftErrors

		and dot5StatsHardErrors, respectively.  The other choices

		refer for items in the olTRTraf tables."

--	DEFVAL {frames(2)}

	::= { olThreshEntry 6 }



olThreshStatNetID OBJECT-TYPE

	SYNTAX INTEGER {

		other(1),

		isolated(2),

		token-ring-1(9),

		token-ring-2(10),

		token-ring-3(11),

		token-ring-4(12),

		token-ring-5(13),

		token-ring-6(14),

		token-ring-7(15),

		agent-network(255)

	}

	ACCESS read-write

	STATUS mandatory

	DESCRIPTION

		"When olThreshStatCategory is network(2) or station(4),

		specifies the network of statistic to be thresholded.

		If the agent is capable of collecting statistics only for

		the network that it is attached to, olThreshStatNetID can

		be set to agent-network(255); the agent will change

		olThreshStatNetID to reflect the network that the agent

		is currently attached to.  If olThreshStatType is

		tr-net-soft-errors(7) or tr-net-hard-errors(8) the

		agent will change olThreshStatNetID to other(1).

		Note that when this variable is set, olThreshStatSlotIndex

		is overwritten as well."

--	DEFVAL {agent-network(255)}

	::= { olThreshEntry 7 }



olThreshStatSlotIndex OBJECT-TYPE

	SYNTAX INTEGER

	ACCESS read-write

	STATUS mandatory

	DESCRIPTION

		"When olThreshStatCategory is port(3), specifies the

		slot index of the port of statistic to be thresholded.

		Note that when this variable is set, olThreshStatNetID

		is overwritten as well."

	::= { olThreshEntry 8 }



olThreshStatPortIndex OBJECT-TYPE

	SYNTAX INTEGER

	ACCESS read-write

	STATUS mandatory

	DESCRIPTION

		"When olThreshStatCategory is port(3), specifies the

		port index of the port of statistic to be thresholded."

	::= { olThreshEntry 9 }



olThreshStatStationAddr OBJECT-TYPE

	SYNTAX MacAddress

	ACCESS read-write

	STATUS mandatory

	DESCRIPTION

		"When olThreshStatCategory is station(4), specifies the

		MAC address of the station of statistic to be thresholded."

	::= { olThreshEntry 10 }



olThreshInterval OBJECT-TYPE

	SYNTAX INTEGER

	ACCESS read-write

	STATUS mandatory

	DESCRIPTION

		"Specifies the length of the thresholding period in seconds.

		Minimum length is 5 seconds; maximum is 86400 seconds

		(24 hours)."

--	DEFVAL {60}

	::= { olThreshEntry 11 }



olThreshCondition OBJECT-TYPE

	SYNTAX INTEGER {

		delta-above(1)

	}

	ACCESS read-write

	STATUS mandatory

	DESCRIPTION

		"Specifies the type of conditional comparison for the

		threshold."

--	  Possible future values for olThreshCondition: delta-below,

--	  absolute-above, absolute-below

--	DEFVAL {delta-above(1)}

	::= { olThreshEntry 12 }



olThreshValue OBJECT-TYPE

	SYNTAX INTEGER

	ACCESS read-write

	STATUS mandatory

	DESCRIPTION

	    "At the end of each thresholding interval (olThreshInterval

	    seconds), olThreshCurrentValue is compared against

	    olThreshValue (unsigned).

	    When olThreshType is delta-above(1):

		If olThreshStatus is valid(4), and olThreshCurrentValue is

		above olThreshValue, and olThreshMode is enabled,

		then a chipAboveThreshd trap will be sent.

		Another chipAboveThreshd trap will not be sent until

		olThreshCurrentValue drops to less than or equal to

		olThreshValue and then again exceeds it."

--	DEFVAL { 0 }

	::= { olThreshEntry 13 }



olThreshCurrentValue OBJECT-TYPE

	SYNTAX INTEGER

	ACCESS read-only

	STATUS mandatory

	DESCRIPTION

	    "When olThreshType is delta-exceed(1):

		The most recent delta value of olThreshStatObjectIdentifier

		(i.e. value of olThreshStatObjectIdentifier at the end of

		the interval minus the value of olThreshStatObjectIdentifier

		at the beginning of the interval).

	    If olThreshStatus is not valid(4), olThreshCurrentValue will be 0."

	::= { olThreshEntry 14 }



olThreshStatus OBJECT-TYPE

	SYNTAX INTEGER {

		no-statistic-specified(1),

		statistic-not-accessible(2),

		not-yet-available(3),

		valid(4)

	}

	ACCESS read-only

	STATUS mandatory

	DESCRIPTION

	    "When olThreshType is delta-exceed(1):

		If olThreshStatObjectIdentifier has not yet been specified,

		olThreshStatus will be no-statistic-specified(1).

		If the first interval has not yet completed,

		olThreshStatus will be not-yet-available(2).

		If object referenced by olThreshStatObjectIdentifier is not

		accessible, olThreshStatus will be not-accessible(3).

		Otherwise olThreshStatus will be valid(4)."

	::= { olThreshEntry 15 }



olThreshTimeSinceLastTriggered OBJECT-TYPE

  SYNTAX TimeTicks

  ACCESS read-only

  STATUS mandatory

  DESCRIPTION

	"Time in TimeTicks that has elapsed since a chipAboveThreshd trap

	associated with this ThreshEntry was last sent.

	If never sent, this value shall be zero."

    ::= { olThreshEntry 16 }



olThreshActionType OBJECT-TYPE

	SYNTAX INTEGER {

		trap-only(1),

		run-script-only(2),

		trap-run-script(3)

	}

	ACCESS read-write

	STATUS mandatory

	DESCRIPTION

		"The action to be performed when the threshold is triggered."

    ::= { olThreshEntry 17 }



olThreshActionData OBJECT-TYPE

	SYNTAX INTEGER

	ACCESS read-write

	STATUS mandatory

	DESCRIPTION

		"Additional information to be sent with the

		chipAboveThreshd trap.  In the case of

		scripts, this object will contain the script

		number to be executed."

    ::= { olThreshEntry 18 }



olThreshActionPriority OBJECT-TYPE

	SYNTAX INTEGER {

		low(1),

		medium(2),

		high(3)

	}

	ACCESS read-write

	STATUS mandatory

	DESCRIPTION

		"The priority for this entry.  Provided for use by the

		network management station (NMS) - not interpreted by

		the agent."

--	DEFVAL {low(1)}

    ::= { olThreshEntry 19 }





--

-- ONcore Power Group

--

-- This group is used for managing the

-- power in the ONcore hub.



--

-- Hub power mode

--

ocPowerModeAdminStatus OBJECT-TYPE

	SYNTAX INTEGER {

		fault-tolerant(1),

		not-fault-tolerant(2)

		}

	ACCESS read-write

	STATUS mandatory

	DESCRIPTION

		"The current desired state of hub power fault-tolerant

		mode.  Setting this object to fault-tolerant(1) will

		reserve one power supply's worth of power from the power

		budget for fault-tolerant operation, provided sufficient

		power is available.  Setting this object to

		not-fault-tolerant(2) returns the reserved power to the

		power budget."

	::= { ocPowerControl 1 }



ocPowerModeOperStatus OBJECT-TYPE

	SYNTAX INTEGER {

		fault-tolerant(1),

		not-fault-tolerant(2)

		}

	ACCESS read-only

	STATUS mandatory

	DESCRIPTION

		"The current operational status of hub power fault-tolerant

		mode."

	::= { ocPowerControl 2 }



ocPowerOverheatPowerDownMode OBJECT-TYPE

	SYNTAX INTEGER {

		enable(1),

		disable(2)

		}

	ACCESS read-write

	STATUS mandatory

	DESCRIPTION

		"The current desired state of hub overheat automatic power-

		down mode.  Setting this object to enable(1) will cause

		slots containing ONcore modules to be automatically

		power-disabled during a hub overheat condition.  Setting

		this object to disable(2) will cause no action to be taken

		when a hub overheat condition occurs."

	::= { ocPowerControl 3 }



--

--  Hub backplane power

--

ocPowerOutputTable OBJECT-TYPE

	SYNTAX SEQUENCE OF OcPowerOutputEntry

	ACCESS not-accessible

	STATUS mandatory

	DESCRIPTION

		"A table that contains information about the hub power

		budget.  This table is indexed by voltage line type, each

		of which is supplied by the operational power supplies."

	::= { ocPower 2 }



ocPowerOutputEntry OBJECT-TYPE

	SYNTAX OcPowerOutputEntry

	ACCESS not-accessible

	STATUS mandatory

	DESCRIPTION

		"A list of information about the hub power budget."

	INDEX { ocPowerOutputType }

	::= { ocPowerOutputTable 1 }



OcPowerOutputEntry ::=

	SEQUENCE {

		ocPowerOutputType

			INTEGER,

		ocPowerOutputVoltageLevel

			Gauge,

		ocPowerOutputWattageCapacity

			Gauge,

		ocPowerOutputWattageConsumed

			Gauge,

		ocPowerOutputWattageAvailable

			Gauge,

		ocPowerOutputUnmanagedWattageAlloc

			Gauge

		}



ocPowerOutputType OBJECT-TYPE

	SYNTAX INTEGER {

		plusFiveVolt(1),	-- + 5 Volt

		minusFiveVolt(2),	-- - 5 Volt

		plusTwelveVolt(3),	-- +12 Volt

		minusTwelveVolt(4),	-- -12 Volt

		plusTwoVolt(5)		-- + 2 Volt

		}

	ACCESS  read-only

	STATUS  mandatory

	DESCRIPTION

		"Identifies the power (voltage) line type for which this

		entry contains power budget information."

	::= { ocPowerOutputEntry 1 }



ocPowerOutputVoltageLevel OBJECT-TYPE

	SYNTAX Gauge

	ACCESS read-only

	STATUS mandatory

	DESCRIPTION

		"In millivolts (1/1000 Volt), the actual voltage level

		for this voltage type as sensed on the backplane.  This

		voltage is supplied by all operational power supplies."

	::= { ocPowerOutputEntry 2 }



ocPowerOutputWattageCapacity OBJECT-TYPE

	SYNTAX Gauge

	ACCESS read-only

	STATUS mandatory

	DESCRIPTION

		"In hundredths of a Watt (1/100 Watt), the maximum

		wattage for the voltage line that is output by all

		operational power supplies combined."

	::= { ocPowerOutputEntry 3 }



ocPowerOutputWattageConsumed OBJECT-TYPE

	SYNTAX Gauge

	ACCESS read-only

	STATUS mandatory

	DESCRIPTION

		"In hundredths of a Watt (1/100 Watt), the wattage

		consumed by all hub modules.  For a given voltage line,

		this object's value is the sum total of the power consumed

		by the hub itself, 2 Controller Modules, all installed

		ONline modules, and all power-enabled slots containing

		ONcore modules.  If power fault-tolerant mode is enabled

		(when it was previously disabled), this object's value is

		increased by the amount of power reserved for the voltage

		line.  If power fault-tolerant mode is disabled (when it

		was previously enabled), this object's value is decreased

		by the amount of power that is returned to the available

		power budget for the voltage line."

	::= { ocPowerOutputEntry 4 }



ocPowerOutputWattageAvailable OBJECT-TYPE

	SYNTAX Gauge

	ACCESS read-only

	STATUS mandatory

	DESCRIPTION

		"In hundredths of a Watt (1/100 Watt), the wattage

		available to power-up modules.  If power fault-tolerant

		mode is enabled (when it was previously disabled), this

		object's value is decreased by the amount of power reserved

		for the voltage line.  If power fault-tolerant mode is

		disabled (when it was previously enabled), this object's

		value is increased by the amount of power that is returned

		to the available power budget for the voltage line."

	::= { ocPowerOutputEntry 5 }



ocPowerOutputUnmanagedWattageAlloc OBJECT-TYPE

	SYNTAX Gauge

	ACCESS read-only

	STATUS mandatory

	DESCRIPTION

		"In hundredths of a Watt (1/100 Watt), the wattage

		allocated for modules that are not power-manageable

		(i.e., ONline modules)."

	::= { ocPowerOutputEntry 6 }



--

-- Module power configuration

--

ocPowerSlotTable OBJECT-TYPE

	SYNTAX SEQUENCE OF OcPowerSlotEntry

	ACCESS not-accessible

	STATUS mandatory

	DESCRIPTION

		"A table that contains power management information

		for each non-empty, payload slot in the hub."

	::= { ocPower 3  }



ocPowerSlotEntry OBJECT-TYPE

	SYNTAX OcPowerSlotEntry

	ACCESS not-accessible

	STATUS mandatory

	DESCRIPTION

		"A list of power management information for each

		non-empty, payload slot in the hub."

	INDEX { ocPowerSlotIndex }

	::= { ocPowerSlotTable 1 }



OcPowerSlotEntry ::=

	SEQUENCE {

		 ocPowerSlotIndex

			INTEGER,

		 ocPowerSlotClass

			INTEGER,

		 ocPowerSlotAdminStatus

			INTEGER,

		 ocPowerSlotOperStatus

			INTEGER

		 }



ocPowerSlotIndex OBJECT-TYPE

	SYNTAX INTEGER

	ACCESS read-only

	STATUS mandatory

	DESCRIPTION

		"The unique slot number that identifies the module

		associated with this power entry."

	::= { ocPowerSlotEntry 1 }



ocPowerSlotClass OBJECT-TYPE

	SYNTAX INTEGER {

		one(1),

		two(2),

		three(3),

		four(4),

		five(5),

		six(6),

		seven(7),

		eight(8),

		nine(9),

		ten(10),

		not-applicable(11)

		}

	ACCESS read-write

	STATUS mandatory

	DESCRIPTION

		"The current slot power class.  For a slot containing

		an ONcore module, this object's value ranges from 1 to

		10, where 1 is the lowest power class and 10 is the

		highest power class.  Slots assigned higher power classes

		will be power-enabled before slots assigned lower power

		classes.  Similarly, slots assigned lower power classes

		will be power-disabled before slots assigned higher power

		classes.  For a slot containing an ONline module, this

		object's value is reported as not-applicable(11) because

		ONline modules are not power-manageable (once an ONline

		module is inserted into the hub, it will consume power

		for as long as it remains in the hub).  The value

		not-applicable(11) is invalid for a slot containing an

		ONcore module.  Power class can be used to establish an

		ONcore module power-up and power-down priority scheme.

		Combined with slot location, slot power class defines the

		order in which slots containing ONcore modules will be

		power-enabled and power-disabled.  For a given power class,

		slots are power-enabled from lowest payload slot to highest

		payload slot and power-disabled from highest payload slot

		to lowest payload slot.  Slot power class is not pre-emptive;

		changing a slot's power class will not affect the power

		state of other slots.  It will take effect during a slot

		power-up or power-down event (e.g., the failure or recovery

		of a power supply)."

	::= { ocPowerSlotEntry 2 }



ocPowerSlotAdminStatus OBJECT-TYPE

	SYNTAX  INTEGER {

		enable(1),  -- enable slot power

		disable(2)  -- disable slot power

		}

	ACCESS read-write

	STATUS mandatory

	DESCRIPTION

		"The current desired slot power state.  For a slot

		containing an ONcore module, setting this object to

		enable(1) will cause the module to be power-enabled,

		provided sufficient power is available.  Setting this

		object to disable(2) will cause the module to be

		power-disabled.  The slot will not receive power until

		this object is set to the value enable(1).  For a slot

		containing an ONline module, setting this object to

		disable(2) is invalid because an ONline module is not

		power-manageable; once installed, an ONline module

		comsumes power for as long as it remains in the hub.

		Also, for a slot containing the ONcore agent, setting

		this object to disable(2) is not allowed to prevent the

		user from losing hub manageability."

	::= { ocPowerSlotEntry 3 }



ocPowerSlotOperStatus OBJECT-TYPE

	SYNTAX INTEGER {

		enabled(1),		-- Slot power is enabled

		disabled(2),		-- Slot power is disabled

		insufficient-power(3),  -- Slot power up not possible

		enabled-always(4)	-- Slot power is enabled always

		}

	ACCESS read-only

	STATUS mandatory

	DESCRIPTION

		"The current operational slot power status.  This object

		will have the value enabled(1), if the slot contains an

		ONcore module and is actually power-enabled.  This object

		will have the value disabled(2), if the slot contains an

		ONcore module and is actually power-disabled.  In this case,

		the slot is ineligible for power until ocPowerSlotAdminStatus

		for the slot is set to enable(1).  This object will have

		the value insufficient-power(3), if the slot is eligible to

		receive power but, due to power constraints, is not

		power-enabled.  When sufficient power becomes available,

		the slot will become power-enabled, and this object will

		then have the value enabled(1).  This object will have the

		value enabled-always(4) for a slot containing an ONline

		module or the ONcore agent."

	::= { ocPowerSlotEntry 4 }



--

-- ONcore Inventory Group

--

-- This group reflects inventory information about

-- components in the ONcore hub.

--



--

-- Hub chassis information

--

ocInvHubType OBJECT-TYPE

	SYNTAX DisplayString (SIZE(1..32))

	ACCESS read-only

	STATUS mandatory

	DESCRIPTION

		"The hub type (i.e. model number) of the hub.  An instance

		for which information is not valid will return 'invalid

		EEPROM!'."

	::= { ocInvHub 1 }



ocInvHubSerialNo OBJECT-TYPE

	SYNTAX DisplayString (SIZE(1..32))

	ACCESS read-only

	STATUS mandatory

	DESCRIPTION

		"The serial number of the hub.  An instance for which

		information is not valid will return 'invalid EEPROM!'."

	::= { ocInvHub 2 }



ocInvHubHWVer OBJECT-TYPE

	SYNTAX DisplayString (SIZE(1..32))

	ACCESS read-only

	STATUS mandatory

	DESCRIPTION

		"The revision number of the hardware of the hub.  An instance

		for which information is not valid will return 'invalid

		EEPROM!'."

	::= { ocInvHub 3 }



ocInvHubMfr OBJECT-TYPE

	SYNTAX DisplayString (SIZE(1..32))

	ACCESS read-only

	STATUS mandatory

	DESCRIPTION

		"The company name that manufactured this hub.  An instance

		for which information is not valid will return 'invalid

		EEPROM!."

	::= { ocInvHub 4 }



ocInvHubMfrDate OBJECT-TYPE

	SYNTAX DisplayString (SIZE(6))

	ACCESS read-only

	STATUS mandatory

	DESCRIPTION

		"The date in yymmdd format that this unit was manufactured.

		 An instance for which information is not valid will return

		 'invalid EEPROM!'."

	::= { ocInvHub 5 }





--

-- ONcore Modules inventory information

--

-- Contains information about the hub modules. The modules

-- information are organized as a base-one matrix. That is, a module,

-- motherboard or daughter card, can be located by a pair of primitives:

-- slot index and subslot index (i.e. <slot>.<subslot>)

--

-- ocInvModTable

--

ocInvModTable OBJECT-TYPE

	SYNTAX SEQUENCE OF OcInvModEntry

	ACCESS not-accessible

	STATUS mandatory

	DESCRIPTION

		"A list of inventory information related to a module,

		 indexed with respect to slot and subslot location numbers."

	::= { ocInvMods 1 }



ocInvModEntry OBJECT-TYPE

	SYNTAX OcInvModEntry

	ACCESS not-accessible

	STATUS mandatory

	DESCRIPTION

		"Values to describe a module inventory items."

	INDEX { ocInvModSlotIndex, ocInvModSubSlotIndex }

	::= { ocInvModTable 1 }



OcInvModEntry ::=

	SEQUENCE {

		ocInvModSlotIndex

			INTEGER,

		ocInvModSubSlotIndex

			INTEGER,

		ocInvModModel

			DisplayString,

		ocInvModSerialNo

			DisplayString,

		ocInvModHWVer

			DisplayString,

		ocInvModSWVer

			DisplayString,

		ocInvModSWBootVer

			DisplayString,

		ocInvModMfr

			DisplayString,

		ocInvModMfrDate

			DisplayString



		}



ocInvModSlotIndex OBJECT-TYPE

	SYNTAX INTEGER

	ACCESS read-only

	STATUS mandatory

	DESCRIPTION

		"The slot number where this Module is located."

	::= { ocInvModEntry 1 }



ocInvModSubSlotIndex OBJECT-TYPE

	SYNTAX INTEGER

	ACCESS read-only

	STATUS mandatory

	DESCRIPTION

		"The subslot number where this Module is located. It is

		 associated with a slot number. Motherboards are always

		 located in subslot one, (e.g. <slot>.1). However,

		 daughter cards can reside on any subslot within the range

		 (2 ... 8), (e.g. <slot>.<2 .. 8>)."

	::= { ocInvModEntry 2 }



ocInvModModel OBJECT-TYPE

	SYNTAX DisplayString (SIZE(1..32))

	ACCESS read-only

	STATUS mandatory

	DESCRIPTION

		"This Module model number. If the instance value is

		 unknown, ONline will be returned."

	::= { ocInvModEntry 3 }



ocInvModSerialNo OBJECT-TYPE

	SYNTAX DisplayString (SIZE(1..32))

	ACCESS read-only

	STATUS mandatory

	DESCRIPTION

		"This Module serial number. If the instance value

		 is unknown, N/A will be returned."

	::= { ocInvModEntry 4 }



ocInvModHWVer OBJECT-TYPE

	SYNTAX DisplayString (SIZE(1..32))

	ACCESS read-only

	STATUS mandatory

	DESCRIPTION

		"The revision number of the hardware on this module.

		 If the instant value is unknown, N/A will be returned."

	::= { ocInvModEntry 5 }



ocInvModSWVer OBJECT-TYPE

	SYNTAX DisplayString (SIZE(1..32))

	ACCESS read-only

	STATUS mandatory

	DESCRIPTION

		"The revision number of the software on this module.

		 If the instant value is unknown, N/A will be

		 returned."

	::= { ocInvModEntry 6 }



ocInvModSWBootVer OBJECT-TYPE

	SYNTAX DisplayString (SIZE(1..32))

	ACCESS read-only

	STATUS mandatory

	DESCRIPTION

		"The revision number of the boot software on this module.

		 If the instant value is unknown, N/A will be returned."

	::= { ocInvModEntry 7 }



ocInvModMfr OBJECT-TYPE

	SYNTAX DisplayString (SIZE(1..32))

	ACCESS read-only

	STATUS mandatory

	DESCRIPTION

		"The company name that manufactured this module. If the

		 instant value is unkonwn, N/A will be returned."

	::= { ocInvModEntry 8 }



ocInvModMfrDate OBJECT-TYPE

	SYNTAX DisplayString (SIZE(6))

	ACCESS read-only

	STATUS mandatory

	DESCRIPTION

		"The date in yymmdd format that this module was manufactured.

		 If the instant value is unknown, N/A will be returned."

	::= { ocInvModEntry 9 }







--

-- The olPS2 MIB:

--

-- The following group is used to manage PS/2 attributes in

-- the Hub. It provides detailed information about the hardware

-- configuration and adapter cards installed on the PS/2. In

-- addition it provides an indication of the software installed

-- on the PS/2.

--

-- This information must be set manually from the console interface

-- on the network management module, or remotely via its Telnet

-- interface.

--

--

--			PS2 Groups

--

-- Under the olPS2 branch exists:

--

--     olPS2Info      - system information about the PS/2

--     olPS2McaTable  - a table of information concerning

--			Micro channel adapter cards in the PS/2

--     olPS2ApplTable - a table of information decsribing the

--			software applications availabl on the PS/2

--





olPS2Info OBJECT IDENTIFIER ::= { olPS2 1 }



--

--			olPS2Info

--

--

-- System Information concerning the PS/2

--

--



olPS2OperatingSystem OBJECT-TYPE

	SYNTAX DisplayString (SIZE(0..32))

	ACCESS read-only

	STATUS mandatory

	DESCRIPTION

		"The type of operating system current

		including its version and release numbers,

		currently executing on the PS/2."

	::= { olPS2Info 1 }



olPS2FixedDiskSize OBJECT-TYPE

	SYNTAX DisplayString (SIZE(0..32))

	ACCESS read-only

	STATUS mandatory

	DESCRIPTION

		"The size in of Fixed Disk Memory currently

		installed on the PS/2."

	::= { olPS2Info 2 }



olPS2RamSize OBJECT-TYPE

	SYNTAX DisplayString (SIZE(0..32))

	ACCESS read-only

	STATUS mandatory

	DESCRIPTION

		"The size in of Random Access Memory

		currently installed on the PS/2."

	::= { olPS2Info 3 }



--

--			olPS2McaTable

--

--

-- Information about adapter cards that may be installed

-- in the Micro channel adapter card payload portion of

-- the hub.

--



olPS2McaTable OBJECT-TYPE

	SYNTAX  SEQUENCE OF OlPS2McaEntry

	ACCESS  not-accessible

	STATUS  mandatory

	DESCRIPTION

		"A table of software application information

		associated with the PS/2."

	::= { olPS2 2 }



olPS2McaEntry OBJECT-TYPE

	SYNTAX  OlPS2McaEntry

	ACCESS  not-accessible

	STATUS  mandatory

	DESCRIPTION

		"A profile of a specific software application

		associated with this PS/2."

	INDEX	{ olPS2McaIndex }

	::= { olPS2McaTable 1 }



OlPS2McaEntry ::=

	SEQUENCE {

		olPS2McaIndex

			INTEGER,

		olPS2McaDescription

			DisplayString,

		olPS2McaSlotConnectPoint

			INTEGER,

		olPS2McaPortConnectPoint

			INTEGER,

		olPS2McaMacAddress

			OCTET STRING

		}



olPS2McaIndex OBJECT-TYPE

	SYNTAX INTEGER

	ACCESS read-only

	STATUS mandatory

	DESCRIPTION

		"The index for this software application."

	::= { olPS2McaEntry 1 }



olPS2McaDescription   OBJECT-TYPE

	SYNTAX  DisplayString (SIZE(0..32))

	ACCESS  read-only

	STATUS  mandatory

	DESCRIPTION

		"A description of the software application."

	::= { olPS2McaEntry 2 }



olPS2McaSlotConnectPoint OBJECT-TYPE

	SYNTAX INTEGER

	ACCESS read-only

	STATUS mandatory

	DESCRIPTION

		"The slot number of a module within this

		ONline chassis to which this

		Micro channel Adapter Card is connected.

		If not connected to any ONline module

		module, the object value is zero."

	::= { olPS2McaEntry 3 }



olPS2McaPortConnectPoint OBJECT-TYPE

	SYNTAX INTEGER

	ACCESS read-only

	STATUS mandatory

	DESCRIPTION

		"The port number of a module within this

		ONline chassis to which this

		Micro channel Adapter Card is connected.

		If not connected to any ONline module

		module, the object value is zero."

	::= { olPS2McaEntry 4 }



olPS2McaMacAddress   OBJECT-TYPE

	SYNTAX OCTET STRING (SIZE(6))

	ACCESS  read-only

	STATUS  mandatory

	DESCRIPTION

		"The MAC Address of the Micro channel

		adapter card installed this PS/2 Micro

		channel Adapter Card slot. If no MAC

		address is defined this string is

		encoded as a zero length string."

	::= { olPS2McaEntry 5 }



--

--			olPS2ApplTable

--

--

-- Information about software applications that may be

-- installed on the PS/2.

--

--



olPS2ApplTable OBJECT-TYPE

	SYNTAX  SEQUENCE OF OlPS2ApplEntry

	ACCESS  not-accessible

	STATUS  mandatory

	DESCRIPTION

		"A table of software application information

		associated with the PS/2."

	::= { olPS2 3 }



olPS2ApplEntry OBJECT-TYPE

	SYNTAX  OlPS2ApplEntry

	ACCESS  not-accessible

	STATUS  mandatory

	DESCRIPTION

		"A profile of a specific software application

		associated with this PS/2."

	INDEX	{ olPS2ApplIndex }

	::= { olPS2ApplTable 1 }



OlPS2ApplEntry ::=

	SEQUENCE {

		olPS2ApplIndex

			INTEGER,

		olPS2ApplDescription

			DisplayString

		}



olPS2ApplIndex OBJECT-TYPE

	SYNTAX INTEGER

	ACCESS read-only

	STATUS mandatory

	DESCRIPTION

		"The index for this software application."

	::= { olPS2ApplEntry 1 }



olPS2ApplDescription   OBJECT-TYPE

	SYNTAX  DisplayString (SIZE(0..32))

	ACCESS  read-only

	STATUS  mandatory

	DESCRIPTION

		"A description of the software application."

	::= { olPS2ApplEntry 2 }









-- The Interface Table



-- This table contains state and parameter information which is

-- specific to 802.5 interfaces.  It is mandatory that systems

-- having 802.5 interfaces implement this table in addition to the

-- generic interfaces table [4,6] and its generic extensions [11].



expDot5Table  OBJECT-TYPE

	SYNTAX  SEQUENCE OF ExpDot5Entry

	ACCESS  not-accessible

	STATUS  obsolete

	DESCRIPTION

		"This table contains Token Ring interface

		parameters and state variables, one entry

		per 802.5 interface."

	::= { expDot5 1 }



expDot5Entry  OBJECT-TYPE

	SYNTAX  ExpDot5Entry

	ACCESS  not-accessible

	STATUS  obsolete

	DESCRIPTION

		"A list of Token Ring status and parameter

		values for an 802.5 interface."

	INDEX	{ expDot5IfIndex }

	::= { expDot5Table 1 }



ExpDot5Entry ::=

	SEQUENCE {

	      expDot5IfIndex

		  INTEGER,

	      expDot5Commands

		  INTEGER,

	      expDot5RingStatus

		  INTEGER,

	      expDot5RingState

		  INTEGER,

	      expDot5RingOpenStatus

		  INTEGER,

	      expDot5RingSpeed

		  INTEGER,

	      expDot5UpStream

		  MacAddress,

	      expDot5ActMonParticipate

		  INTEGER,

	      expDot5Functional

		  MacAddress

	  }



expDot5IfIndex  OBJECT-TYPE

	SYNTAX  INTEGER

	ACCESS  read-only

	STATUS  obsolete

	DESCRIPTION

	     "The value of this object identifies the

	      802.5 interface for which this entry contains

	      management information.  The value of this

	      object for a particular interface has the same

	      value as the ifIndex object, defined in [4,6],

	      for the same interface."

	::= { expDot5Entry 1 }



expDot5Commands  OBJECT-TYPE

	SYNTAX  INTEGER {

		no-op(1),

		open(2),

		reset(3),

		close(4)

	}

	ACCESS  read-write

	STATUS  obsolete

	DESCRIPTION

		"   When this object is set to the value of open(2),

		the station should go into the open state.  The

		progress and success of the open is given by the

		values of the objects expDot5RingState and

		expDot5RingOpenStatus.

		    When this object is set to the value of

		reset(3), then the station should do a reset.

		On a reset, all MIB counters should retain their

		values, if possible.  Other side affects are

		dependent on the hardware chip set.

		    When this object is set to the value of

		close(4), the station should go into the stopped

		state by removing itself from the ring.

		Setting this object to a value of no-op(1)

		has no effect.

		    When read, this object always has a value

		of no-op(1)."

	::= { expDot5Entry 2 }



expDot5RingStatus OBJECT-TYPE

	SYNTAX  INTEGER

	ACCESS  read-only

	STATUS  obsolete

	DESCRIPTION

	     "   The current interface status which can be used

	     to diagnose fluctuating problems that can occur

	     on token rings, after a station has successfully

	     been added to the ring.

		 Before an open is completed, this object has

	     the value for the 'no status' condition.  The

	     expDot5RingState and expDot5RingOpenStatus objects

	     provide for debugging problems when the station

	     can not even enter the ring.

		 The object's value is a sum of values, one

	     for each currently applicable condition.  The

	     following values are defined for various

	     conditions:

		0 = No Problems detected

		32 = Ring Recovery

		64 = Single Station

		256 = Remove Received

		512 = reserved

		1024 = Auto-Removal Error

		2048 = Lobe Wire Fault

		4096 = Transmit Beacon

		8192 = Soft Error

		16384 = Hard Error

		32768 = Signal Loss

		131072 = no status, open not completed."

	::= { expDot5Entry 3 }



expDot5RingState  OBJECT-TYPE

	SYNTAX  INTEGER {

		opened(1),

		closed(2),

		opening(3),

		closing(4),

		openFailure(5),

		ringFailure(6)

	}

	ACCESS  read-only

	STATUS  obsolete

	DESCRIPTION

	     "The current interface state with respect to

	     entering or leaving the ring."

	::= { expDot5Entry 4 }



expDot5RingOpenStatus  OBJECT-TYPE

	SYNTAX  INTEGER {

		noOpen(1),     -- no open attempted

		badParam(2),

		lobeFailed(3),

		signalLoss(4),

		insertionTimeout(5),

		ringFailed(6),

		beaconing(7),

		duplicateMAC(8),

		requestFailed(9),

		removeReceived(10),

		open(11)      -- last open successful

	}

	ACCESS  read-only

	STATUS  obsolete

	DESCRIPTION

	     "This object indicates the success, or the

	     reason for failure, of the station's most

	     recent attempt to enter the ring."

	::= { expDot5Entry 5 }



expDot5RingSpeed  OBJECT-TYPE

	SYNTAX  INTEGER {

		unknown(1),

		oneMegabit(2),

		fourMegabit(3),

		sixteenMegabit(4)

	}

	ACCESS  read-write

	STATUS  obsolete

	DESCRIPTION

		"The ring's bandwidth."

	::= { expDot5Entry 6 }



expDot5UpStream  OBJECT-TYPE

	SYNTAX  MacAddress

	ACCESS  read-only

	STATUS  obsolete

	DESCRIPTION

	     "The MAC-address of the up stream neighbor

	      station in the ring."

	::= { expDot5Entry 7 }



expDot5ActMonParticipate OBJECT-TYPE

	SYNTAX  INTEGER {

		true(1),

		false(2)

	}

	ACCESS  read-write

	STATUS  obsolete

	DESCRIPTION

	     "If this object has a value of true(1) then

	     this interface will participate in the active

	     monitor selection process.  If the value is

	     false(2) then it will not.  Setting this

	     object might not have an effect until the

	     next time the interface is opened."

	::= { expDot5Entry 8 }



expDot5Functional OBJECT-TYPE

	SYNTAX  MacAddress

	ACCESS  read-write

	STATUS  obsolete

	DESCRIPTION

	     "The bit mask of all Token Ring functional

	     addresses for which this interface will

	     accept frames."

	::= { expDot5Entry 9 }



--   The Statistics Table



-- This table contains statistics and error counter which are

-- specific to 802.5 interfaces.  It is mandatory that systems

-- having 802.5 interfaces implement this table.



expDot5StatsTable  OBJECT-TYPE

	SYNTAX  SEQUENCE OF ExpDot5StatsEntry

	ACCESS  not-accessible

	STATUS  obsolete

	DESCRIPTION

	     "A table containing Token Ring statistics,

	     one entry per 802.5 interface.

		 All the statistics are defined using the

	     syntax Counter as 32-bit wrap around counters.

	     Thus, if an interface's hardware maintains these

	     statistics in 16-bit counters, then the agent

	     must read the hardware's counters frequently

	     enough to prevent loss of significance, in

	     order to maintain 32-bit counters in software."

	::= { expDot5 2 }



expDot5StatsEntry  OBJECT-TYPE

	SYNTAX  ExpDot5StatsEntry

	ACCESS  not-accessible

	STATUS  obsolete

	DESCRIPTION

	     "An entry contains the 802.5 statistics for a

	      particular interface."

	INDEX	{ expDot5StatsIfIndex }

	::= { expDot5StatsTable 1 }



ExpDot5StatsEntry ::=

	SEQUENCE {

	      expDot5StatsIfIndex

		  INTEGER,

	      expDot5StatsLineErrors

		  Counter,

	      expDot5StatsBurstErrors

		  Counter,

	      expDot5StatsACErrors

		  Counter,

	      expDot5StatsAbortTransErrors

		  Counter,

	      expDot5StatsInternalErrors

		  Counter,

	      expDot5StatsLostFrameErrors

		  Counter,

	      expDot5StatsReceiveCongestions

		  Counter,

	      expDot5StatsFrameCopiedErrors

		  Counter,

	      expDot5StatsTokenErrors

		  Counter,

	      expDot5StatsSoftErrors

		  Counter,

	      expDot5StatsHardErrors

		  Counter,

	      expDot5StatsSignalLoss

		  Counter,

	      expDot5StatsTransmitBeacons

		  Counter,

	      expDot5StatsRecoverys

		  Counter,

	      expDot5StatsLobeWires

		  Counter,

	      expDot5StatsRemoves

		  Counter,

	      expDot5StatsSingles

		  Counter,

	      expDot5StatsFreqErrors

		  Counter

	  }



expDot5StatsIfIndex  OBJECT-TYPE

	SYNTAX  INTEGER

	ACCESS  read-only

	STATUS  obsolete

	DESCRIPTION

	     "The value of this object identifies the

	     802.5 interface for which this entry contains

	     management information.  The value of this

	     object for a particular interface has the

	     same value as the ifIndex object, defined

	     in [4,6], for the same interface."

	::= { expDot5StatsEntry 1 }



expDot5StatsLineErrors OBJECT-TYPE

	SYNTAX  Counter

	ACCESS  read-only

	STATUS  obsolete

	DESCRIPTION

	     "This counter is incremented when a frame or

	     token is copied or repeated by a station, the

	     E bit is zero in the frame or token and one of

	     the following conditions exists: 1) there is a

	     non-data bit (J or K bit) between the SD and

	     the ED of the frame or token, or 2) there is an

	     FCS error in the frame."

	::= { expDot5StatsEntry 2 }



expDot5StatsBurstErrors OBJECT-TYPE

	SYNTAX  Counter

	ACCESS  read-only

	STATUS  obsolete

	DESCRIPTION

	     "This counter is incremented when a station

	     detects the absence of transitions for five

	     half-bit timers (burst-five error)."

	::= { expDot5StatsEntry 3 }



expDot5StatsACErrors OBJECT-TYPE

	SYNTAX  Counter

	ACCESS  read-only

	STATUS  obsolete

	DESCRIPTION

		"This counter is incremented when a station

		receives an AMP or SMP frame in which A is

		equal to C is equal to 0, and then receives

		another SMP frame with A is equal to C is

		equal to 0 without first receiving an AMP

		frame. It denotes a station that cannot set

		the AC bits properly."

		::= { expDot5StatsEntry 4 }



expDot5StatsAbortTransErrors OBJECT-TYPE

	SYNTAX  Counter

	ACCESS  read-only

	STATUS  obsolete

	DESCRIPTION

		"This counter is incremented when a station

		transmits an abort delimiter while transmitting."

		::= { expDot5StatsEntry 5 }



expDot5StatsInternalErrors OBJECT-TYPE

	SYNTAX  Counter

	ACCESS  read-only

	STATUS  obsolete

	DESCRIPTION

		"This counter is incremented when a station

		recognizes an internal error."

	::= { expDot5StatsEntry 6 }



expDot5StatsLostFrameErrors OBJECT-TYPE

	SYNTAX  Counter

	ACCESS  read-only

	STATUS  obsolete

	DESCRIPTION

		"This counter is incremented when a station

		is transmitting and its TRR timer expires.

		This condition denotes a condition where a

		transmitting station in strip mode does not

		receive the trailer of the frame before the

		TRR timer goes off."

	::= { expDot5StatsEntry 7 }



expDot5StatsReceiveCongestions OBJECT-TYPE

	SYNTAX  Counter

	ACCESS  read-only

	STATUS  obsolete

	DESCRIPTION

		"This counter is incremented when a station

		recognizes a frame addressed to its specific

		address, but has no available buffer space

		indicating that the station is congested."

	::= { expDot5StatsEntry 8 }



expDot5StatsFrameCopiedErrors OBJECT-TYPE

	SYNTAX  Counter

	ACCESS  read-only

	STATUS  obsolete

	DESCRIPTION

		"This counter is incremented when a station

		recognizes a frame addressed to its specific

		address and detects that the FS field A bits

		are set to 1 indicating a possible line hit

		or duplicate address."

	::= { expDot5StatsEntry 9 }



expDot5StatsTokenErrors OBJECT-TYPE

	SYNTAX  Counter

	ACCESS  read-only

	STATUS  obsolete

	DESCRIPTION

		"This counter is incremented when a station

		acting as the active monitor recognizes an

		error condition that needs a token transmitted."

	::= { expDot5StatsEntry 10 }



expDot5StatsSoftErrors OBJECT-TYPE

	SYNTAX  Counter

	ACCESS  read-only

	STATUS  obsolete

	DESCRIPTION

		"The number of Soft Errors the interface has

		detected. It directly corresponds to the number

		of Report Error MAC frames that this interface

		has transmitted. Soft Errors are those which are

		recoverable by the MAC layer protocols."

	::= { expDot5StatsEntry 11 }



expDot5StatsHardErrors OBJECT-TYPE

	SYNTAX  Counter

	ACCESS  read-only

	STATUS  obsolete

	DESCRIPTION

		"The number of times this interface has

		detected an immediately recoverable fatal error.

		It denotes the number of times this interface

		is either transmitting or receiving beacon

		MAC frames."

	::= { expDot5StatsEntry 12 }



expDot5StatsSignalLoss OBJECT-TYPE

	SYNTAX  Counter

	ACCESS  read-only

	STATUS  obsolete

	DESCRIPTION

		"The number of times this interface has

		detected the loss of signal condition from

		the ring."

	::= { expDot5StatsEntry 13 }



expDot5StatsTransmitBeacons OBJECT-TYPE

	SYNTAX  Counter

	ACCESS  read-only

	STATUS  obsolete

	DESCRIPTION

		"The number of times this interface has

		transmitted a beacon frame."

	::= { expDot5StatsEntry 14 }



expDot5StatsRecoverys OBJECT-TYPE

	SYNTAX  Counter

	ACCESS  read-only

	STATUS  obsolete

	DESCRIPTION

		"The number of Claim Token MAC frames

		received or transmitted after the interface

		has received a Ring Purge MAC frame. This

		counter signifies the number of times the

		ring has been purged and is being recovered

		back into a normal operating state."

	::= { expDot5StatsEntry 15 }



expDot5StatsLobeWires OBJECT-TYPE

	SYNTAX  Counter

	ACCESS  read-only

	STATUS  obsolete

	DESCRIPTION

		"The number of times the interface has

		detected an open or short circuit in the

		lobe data path. The adapter will be closed

		and expDot5RingState will signify this condition."

	::= { expDot5StatsEntry 16 }



expDot5StatsRemoves OBJECT-TYPE

	SYNTAX  Counter

	ACCESS  read-only

	STATUS  obsolete

	DESCRIPTION

		"The number of times the interface has received

		a Remove Ring Station MAC frame request. When

		this frame is received the interface will enter

		the close state and expDot5RingState will signify

		this condition."

	::= { expDot5StatsEntry 17 }



expDot5StatsSingles OBJECT-TYPE

	SYNTAX  Counter

	ACCESS  read-only

	STATUS  obsolete

	DESCRIPTION

		"The number of times the interface has sensed

		that it is the only station on the ring. This

		will happen if the interface is the first one

		up on a ring, or if there is a hardware problem."

	::= { expDot5StatsEntry 18 }



expDot5StatsFreqErrors OBJECT-TYPE

	SYNTAX  Counter

	ACCESS  read-only

	STATUS  obsolete

	DESCRIPTION

		"The number of times the interface has detected

		that the frequency of the incoming signal differs

		from the expected frequency by more than that

		ispecified by the IEEE 802.5 standard, see

		chapter 7 in [10]."

	::= { expDot5StatsEntry 19 }





-- The Timer Table



-- This group contains the values of the timers defined in [10]

-- for 802.5 interfaces.  It is optional that systems having 802.5

-- interfaces implement this group.



expDot5TimerTable  OBJECT-TYPE

	SYNTAX  SEQUENCE OF ExpDot5TimerEntry

	ACCESS  not-accessible

	STATUS  obsolete

	DESCRIPTION

		"This table contains Token Ring interface

		timer values, one entry per 802.5 interface."

	::= { expDot5 5 }



expDot5TimerEntry  OBJECT-TYPE

	SYNTAX  ExpDot5TimerEntry

	ACCESS  not-accessible

	STATUS  obsolete

	DESCRIPTION

		"A list of Token Ring timer values for an 802.5

		interface."

	INDEX	{ expDot5TimerIfIndex }

	::= { expDot5TimerTable 1 }



ExpDot5TimerEntry ::=

	SEQUENCE {

		expDot5TimerIfIndex

			INTEGER,

		expDot5TimerReturnRepeat

			INTEGER,

		expDot5TimerHolding

			INTEGER,

		expDot5TimerQueuePDU

			INTEGER,

		expDot5TimerValidTransmit

			INTEGER,

		expDot5TimerNoToken

			INTEGER,

		expDot5TimerActiveMon

			INTEGER,

		expDot5TimerStandbyMon

			INTEGER,

		expDot5TimerErrorReport

			INTEGER,

		expDot5TimerBeaconTransmit

			 INTEGER,

		expDot5TimerBeaconReceive

			INTEGER

	}



expDot5TimerIfIndex  OBJECT-TYPE

	SYNTAX  INTEGER

	ACCESS  read-only

	STATUS  obsolete

	DESCRIPTION

		"The value of this object identifies the

		 802.5 interface for which this entry contains

		 timer values.  The value of this object for a

		 particular interface has the same value as the

		 ifIndex object, defined in [4,6], for the same

		 interface."

	::= { expDot5TimerEntry 1 }



expDot5TimerReturnRepeat  OBJECT-TYPE

	SYNTAX  INTEGER

	ACCESS  read-only

	STATUS  obsolete

	DESCRIPTION

		"The time-out value used to ensure the

		interface will return to Repeat State, in

		units of 100 micro-seconds.  The value should

		be greater than the maximum ring latency.

		 Implementors are encouraged to provide

		read-write access to this object if that is

		possible/useful in their system, but giving

		due consideration to the dangers of write-able

		timers."

	::= { expDot5TimerEntry 2 }



expDot5TimerHolding  OBJECT-TYPE

	SYNTAX  INTEGER

	ACCESS  read-only

	STATUS  obsolete

	DESCRIPTION

		"Maximum period of time a station is

		permitted to transmit frames after capturing

		a token, in units of 100 micro-seconds.

		 Implementors are encouraged to provide

		read-write access to this object if that is

		possible/useful in their system, but giving

		due consideration to the dangers of write-able

		timers."

	::= { expDot5TimerEntry 3 }



expDot5TimerQueuePDU  OBJECT-TYPE

	SYNTAX  INTEGER

	ACCESS  read-only

	STATUS  obsolete

	DESCRIPTION

		"The time-out value for enqueuing of an SMP

		PDU after reception of an AMP or SMP frame in

		which the A and C bits were equal to 0, in

		units of 100 micro-seconds.

		 Implementors are encouraged to provide

		read-write access to this object if that is

		possible/useful in their system, but giving

		due consideration to the dangers of write-able

		timers."

	::= { expDot5TimerEntry 4 }



expDot5TimerValidTransmit OBJECT-TYPE

	SYNTAX  INTEGER

	ACCESS  read-only

	STATUS  obsolete

	DESCRIPTION

		"The time-out value used by the active monitor

		to detect the absence of valid transmissions,

		in units of 100 micro-seconds.

		 Implementors are encouraged to provide

		read-write access to this object if that is

		possible/useful in their system, but giving

		due consideration to the dangers of write-able

		timers."

	::= { expDot5TimerEntry 5 }



expDot5TimerNoToken  OBJECT-TYPE

	SYNTAX  INTEGER

	ACCESS  read-only

	STATUS  obsolete

	DESCRIPTION

		"The time-out value used to recover from

		various-related error situations [9]. If N is

		the maximum number of stations on the ring,

		the value of this timer is normally:

		  expDot5TimerReturnRepeat + N*expDot5TimerHolding.

		 Implementors are encouraged to provide

		read-write access to this object if that is

		possible/useful in their system, but giving

		due consideration to the dangers of write-able

		timers."

	::= { expDot5TimerEntry 6 }



expDot5TimerActiveMon  OBJECT-TYPE

	SYNTAX  INTEGER

	ACCESS  read-only

	STATUS  obsolete

	DESCRIPTION

		"The time-out value used by the active monitor

		to stimulate the enqueuing of an AMP PDU for

		transmission, in units of 100 micro-seconds.

		 Implementors are encouraged to provide

		read-write access to this object if that is

		possible/useful in their system, but giving

		due consideration to the dangers of write-able

		timers."

	::= { expDot5TimerEntry 7 }



expDot5TimerStandbyMon  OBJECT-TYPE

	SYNTAX  INTEGER

	ACCESS  read-only

	STATUS  obsolete

	DESCRIPTION

		"The time-out value used by the stand-by

		monitors to ensure that there is an active

		monitor on the ring and to detect a continuous

		stream of tokens, in units of 100 micro-seconds.

		 Implementors are encouraged to provide

		read-write access to this object if that is

		possible/useful in their system, but giving

		due consideration to the dangers of write-able

		timers."

	::= { expDot5TimerEntry 8 }



expDot5TimerErrorReport  OBJECT-TYPE

	SYNTAX  INTEGER

	ACCESS  read-only

	STATUS  obsolete

	DESCRIPTION

		"The time-out value which determines how often a

		station shall send a Report Error MAC frame to

		report its error counters, in units of 100

		micro-seconds.

		 Implementors are encouraged to provide

		read-write access to this object if that is

		possible/useful in their system, but giving

		due consideration to the dangers of write-able

		timers."

	::= { expDot5TimerEntry 9 }



expDot5TimerBeaconTransmit  OBJECT-TYPE

	SYNTAX  INTEGER

	ACCESS  read-only

	STATUS  obsolete

	DESCRIPTION

		"The time-out value which determines how long a

		station shall remain in the state of transmitting

		Beacon frames before entering the Bypass state,

		in units of 100 micro-seconds.

		 Implementors are encouraged to provide

		read-write access to this object if that is

		possible/useful in their system, but giving

		due consideration to the dangers of write-able

		timers."

	::= { expDot5TimerEntry 10 }



expDot5TimerBeaconReceive  OBJECT-TYPE

	SYNTAX  INTEGER

	ACCESS  read-only

	STATUS  obsolete

	DESCRIPTION

		"The time-out value which determines how long a

		station shall receive Beacon frames from its

		downstream neighbor before entering the Bypass

		state, in units of 100 micro-seconds.

		 Implementors are encouraged to provide

		read-write access to this object if that is

		possible/useful in their system, but giving

		due consideration to the dangers of write-able

		timers."

	::= { expDot5TimerEntry 11 }



-- 802.5 Interface Tests



expDot5Tests OBJECT IDENTIFIER ::= { expDot5 3 }



-- The extensions to the interfaces table proposed in [11]

-- define a table object, ifExtnsTestTable, through which a

-- network manager can instruct an agent to test an interface

-- for various faults.  A test to be performed is identified

-- (as the value of ifExtnsTestType) via an OBJECT IDENTIFIER.

--

-- The Full-Duplex Loop Back Test is a common test, defined

-- in [11] as:

--

--    testFullDuplexLoopBack

--

-- Invoking this test on a 802.5 interface causes the interface

-- to check the path from memory through the chip set's internal

-- logic and back to memory, thus checking the proper functioning

-- of the systems's interface to the chip set.





-- The Insert Function test is defined by:



testInsertFunc    OBJECT IDENTIFIER ::= { expDot5Tests 1 }



-- Invoking this test causes the station to test the insert ring

-- logic of the hardware if the station's lobe media cable is

-- connected to a wiring concentrator.  Note that this command

-- inserts the station into the network, and thus, could cause

-- problems if the station is connected to a operational network.



-- 802.5 Hardware Chip Sets



expDot5ChipSets   OBJECT IDENTIFIER ::= { expDot5 4 }



-- The extensions to the interfaces table proposed in [11] define

-- an object, ifExtnsChipSet, with the syntax of OBJECT IDENTIFIER,

-- to identify the hardware chip set in use by an interface.  That

-- definition specifies just one applicable object identifier:

--

--    unknownChipSet

--

-- for use as the value of ifExtnsChipSet when the specific chip

-- set is unknown.

--

-- This MIB defines the following for use as values of ifExtnsChipSet:



-- IBM 16/4 Mb/s

chipSetIBM16  OBJECT IDENTIFIER ::= { expDot5ChipSets 1 }



-- TI 4Mb/s

chipSetTItms380    OBJECT IDENTIFIER ::= { expDot5ChipSets 2 }



-- TI 16/4 Mb/s

chipSetTItms380c16 OBJECT IDENTIFIER ::= { expDot5ChipSets 3 }









-- The chipTTY Group:

--

-- The following group is used to manage agent terminal ports.

--

--





chipTTYNumber OBJECT-TYPE

	SYNTAX INTEGER

	ACCESS read-only

	STATUS mandatory

	DESCRIPTION

		"The number of terminal ports on this agent product."

	::= { chipTTY 1 }



chipTTYTable OBJECT-TYPE

	SYNTAX  SEQUENCE OF ChipTTYEntry

	ACCESS  not-accessible

	STATUS  mandatory

	DESCRIPTION

		"A table of TTY specific information associated with

		this agent."

	::= { chipTTY 2 }



chipTTYEntry OBJECT-TYPE

	SYNTAX  ChipTTYEntry

	ACCESS  not-accessible

	STATUS  mandatory

	DESCRIPTION

		"A profile of a specific TTY interface associated with

		this agent."

	INDEX	{ chipTTYIndex }

	::= { chipTTYTable 1 }



ChipTTYEntry ::=

	SEQUENCE {

		chipTTYIndex

			INTEGER,

		chipTTYBaud

			INTEGER,

		chipTTYParity

			INTEGER,

		chipTTYStop

			INTEGER,

		chipTTYData

			INTEGER,

		chipTTYTimeout

			INTEGER,

		chipTTYPrompt

			DisplayString,

		chipTTYDTR

			INTEGER,

		chipTTYTerminalType



			DisplayString



		}



chipTTYIndex	OBJECT-TYPE

	SYNTAX  INTEGER

	ACCESS  read-only

	STATUS  mandatory

	DESCRIPTION

		"The TTY to which this entry refers."

	::= { chipTTYEntry 1 }



chipTTYBaud	OBJECT-TYPE

	SYNTAX  INTEGER {

		one-hundred-ten(110),

		three-hundred(300),

		twelve-hundred(1200),

		twenty-four-hundred(2400),

		forty-eight-hundred(4800),

		ninety-six-hundred(9600),

		nineteen-two-hundred(19200),

		thirty-eight-thousand-four-hundred(38400)

		}

	ACCESS  read-write

	STATUS  mandatory

	DESCRIPTION

		"The baud rate for this TTY. It should be noted that all

		 serial ports do not support all of the above baud rates."

	::= { chipTTYEntry 2 }



chipTTYParity	OBJECT-TYPE

	SYNTAX  INTEGER {

		odd(1),

		even(2),

		none(3)

		}

	ACCESS  read-write

	STATUS  mandatory

	DESCRIPTION

		"The parity setting for this TTY."

	::= { chipTTYEntry 3 }



chipTTYStop	OBJECT-TYPE

	SYNTAX  INTEGER {

		one(1),

		two(2)

		}

	ACCESS  read-write

	STATUS  mandatory

	DESCRIPTION

		"The number of stop bits for this TTY."

	::= { chipTTYEntry 4 }



chipTTYData	OBJECT-TYPE

	SYNTAX  INTEGER {

		seven(7),

		eight(8)

		}

	ACCESS  read-write

	STATUS  mandatory

	DESCRIPTION

		"The number of data bits for this TTY."

	::= { chipTTYEntry 5 }



chipTTYTimeout  OBJECT-TYPE

	SYNTAX  INTEGER

	ACCESS  read-write

	STATUS  mandatory

	DESCRIPTION

		"The number of minutes to wait before this agent logs out

		an inactive login session on this TTY.

		NOTE: In some implementations, this is a single variable

		      that is used by all of the terminal and telnet

		      sessions."

	::= { chipTTYEntry 6 }



chipTTYPrompt	OBJECT-TYPE

	SYNTAX  DisplayString (SIZE(0..15))

	ACCESS  read-write

	STATUS  mandatory

	DESCRIPTION

		"The terminal prompt to display on this TTY.

		NOTE: In some implementations, this is a single variable

		      that is used by all of the terminal and telnet

		      sessions."

	::= { chipTTYEntry 7 }



chipTTYDTR	OBJECT-TYPE

	SYNTAX  INTEGER {

			asserted(1),

			deasserted(2),

			notApplicable(3)

		}

	ACCESS  read-write

	STATUS  mandatory

	DESCRIPTION

		"This value dictates the behavior of the RS-232 Data

		Terminal Ready (DTR) signal at the time a session ends

		due to a logout, timeout, or shutdown.  This is used by

		some modems as an indication that they should hangup.

		This variable returns notApplicable(3) if the RS-232

		port does not have a DTR signal."

	::= { chipTTYEntry 8 }



chipTTYTerminalType   OBJECT-TYPE

      SYNTAX  DisplayString (SIZE(1..40))

      ACCESS  read-write

      STATUS  mandatory

      DESCRIPTION

	      "A string which indicates the type of terminal that

	      is attached to the serial port. It should be noted that

	      the string is passed to a telnet server whenever the server

	      issues the IAC DO TERMINAL-TYPE command (see rfc884)."

      ::= { chipTTYEntry 9 }





-- The chipTFTP Group

--

-- Implementation of the chipTFTP group is mandatory for all agent

-- products that support TFTP file transfers.

--

-- The chipTFTP Group is used by a station to initiate a TFTP transfer

-- from a TFTP server to this agent (the TFTP client).

--

-- In order to initiate a TFTP file transfer, the client must know

-- the following information:

--

-- 1. The operation to perform, either a get or a put (chipTFTPStart).

-- 2. What station is acting as the TFTP server (chipTFTPIpAddress).

-- 3. The file name (chipTFTPFileName) and the file type (chipTFTPFileType).

--	  The file name can be a pathname.  The file type indicates to

--	  the agent what kind of information is being transferred.

-- 4. What module should receive the file (chipTFTPSlot).

--

--

-- For example, if one wished to inband download flash code to this agent,

-- one would set:

--

-- File type	= Flash code

-- Slot number  = This agent (255).

-- File name	= Pathname on the server where the file is located.

-- IP Address	= The IP of the TFTP file server.

-- TFTP Start	= get - retrieve the file from the server.

--

-- After setting the start object, the transfer takes place.  The

-- chipTFTPResult object contains the result of the last TFTP transfer

-- attempted.

--



chipTFTPStart OBJECT-TYPE

	SYNTAX INTEGER {

		tftpNoTransfer(1),

		tftpGet(2),	-- download to agent

		tftpPut(3)	-- upload to server

		}

	ACCESS read-write

	STATUS mandatory

	DESCRIPTION

		"Setting chipTFTPStart to tftpGet(2) initiates a file

		transfer to the agent (download); tftpPut(3) initiates

		a file transfer to the server (upload)."

	::= { chipTFTP 1 }



chipTFTPSlot OBJECT-TYPE

	SYNTAX INTEGER {

		slot-1(1),

		slot-2(2),

		slot-3(3),

		slot-4(4),

		slot-5(5),

		slot-6(6),

		slot-7(7),

		slot-8(8),

		slot-9(9),

		slot-10(10),

		slot-11(11),

		slot-12(12),

		slot-13(13),

		slot-14(14),

		slot-15(15),

		slot-16(16),

		slot-17(17),



		all-fddi-port-slots(254),



		agent-slot(255)

	}

	ACCESS  read-write

	STATUS  mandatory

	DESCRIPTION

		"The slot number of the module that is to be involved

		in the TFTP transfer with the TFTP server (chipTFTPIpAddress)."

	::= { chipTFTP 2 }



chipTFTPIpAddress OBJECT-TYPE

	SYNTAX IpAddress

	ACCESS read-write

	STATUS mandatory

	DESCRIPTION

		"The IP Address of the TFTP server."

	::= { chipTFTP 3 }



chipTFTPFileName OBJECT-TYPE

	SYNTAX DisplayString (SIZE(0..128))

	ACCESS read-write

	STATUS mandatory

	DESCRIPTION

		"The file name of the file to retrieve (tftpGet), or the

		name of the file to create (tftpPut). "

	::= { chipTFTP 4 }



chipTFTPFileType OBJECT-TYPE

	SYNTAX INTEGER {

		flashCode(1),

		bootCode(2),

		ascii(3)

		}

	ACCESS read-write

	STATUS mandatory

	DESCRIPTION

		"The type of file image to upload/download.  The file

		type indicates to the agent what kind of file it is

		receiving.  flashCode(1) indicates a code upgrade of

		the operational proms.  bootCode(2) indicates a code

		upgrade of the boot proms.  ascii(3) indicates an

		ASCII file."

	::= { chipTFTP 5 }



chipTFTPResult OBJECT-TYPE

	SYNTAX INTEGER {

		clear(1),		-- not initialized

		xferInProgress(2),	-- transfer in progress

		okay(3),		-- no errors

		otherTFTPError(4),	-- undefined error

		fileNotFound(5),	-- check for valid file name

		accessError(6),		-- TFTP access error

		diskFull(7),		-- server disk is full

		illegalTFTPOperation(8),-- illegal TFTP operation

		invalidTFTPTransactionID(9),

		noResponse(10),		-- check valid server IP address

		invalidDownloadKey(11), -- key didn't verify

		invalidSlot(12),

		invalidNetwork(13),

		fepromErase(14),	-- problem erasing

		fepromProg(15),		-- problem programming

		xferError(16),		-- error in transfer

		decodeError(17),

		dlInProgress(18),

		notYetSupported(19),	-- action not yet supported

		noModsOfType(20),	-- no modules of this type in hub

		downloadFailed(21),	-- failure

		crcError(22),		-- file CRC failed

		invalidDLType(23),	-- file not correct

		unknownFEPROMType(24),  -- feprom type unknown

		fileTooLarge(25),	-- file too large for RAM buffering

		fileGetProblem(26),	-- error getting file

		notMaster(27),		-- not master/lost mastership

		onlyOperational(28),	-- if bad cksum, can only dload oper

		rejectedByTarget(29),	-- target rejected the file

		gatewayUnreachable(30), -- gateway is unreachable

		moduleTypeError(31),	-- file module type wrong

		fileTypeError(32),	-- file type (oper/boot) wrong

		fileForwardProblem(33), -- error forwarding file to target

		notifyTargetError(34),  -- error notifying target to dload

		serverTimeout(35),	-- t/o waiting for pkt from server

		noModuleInSlot(36),	-- no module in this slot/sslot

		targetTimeout(37)	-- t/o waiting for target to respond

		}

	ACCESS read-only

	STATUS mandatory

	DESCRIPTION

		"The result of the last TFTP operation."

	::= { chipTFTP 6 }



chipTFTPSubSlot OBJECT-TYPE

	SYNTAX INTEGER

	ACCESS read-write

	STATUS mandatory

	DESCRIPTION

	       "The subslot identifier for the module to be involved

	       in the TFTP transfer with the TFTP server.  If

	       this transfer involves a module not contained in the

	       ONcore system, the value of this object can only be 1.

	       If the value of chipTFTPSlot is agent-slot(255), this



	       object is ignored."



	::= { chipTFTP 7 }



chipTFTPTargetLocation OBJECT-TYPE

	SYNTAX INTEGER {

		target-Device(1),



		target-SlotSubSlot(2)



		}

	ACCESS read-write

	STATUS mandatory

	DESCRIPTION

		"Specifies the ultimate destination of the file

		being transfered.  This object will determine



		if the target is Device or Module."



	::= { chipTFTP 8 }





-- chipDownload Group

--

-- To begin an in-band download through SNMP the following mib objects

-- along with the chipTFTP objects must be completed with the correct

-- information.

--

-- Before download is allowed to begin, the agent will verify the

-- Software Key.  If the Software Key is found to be valid, download

-- will follow.  Otherwise, chipTFTPResult is set to (9)invalidDown-

-- loadKey.





chipDownloadUDKSerial OBJECT-TYPE

	SYNTAX DisplayString (SIZE(0..8))

	ACCESS read-write

	STATUS mandatory

	DESCRIPTION

		"A string representing the serial number of the

		 Upgrade Distribution Kit."

	::= { chipDownload 1 }



chipDownloadKey OBJECT-TYPE

	SYNTAX DisplayString (SIZE(0..8))

	ACCESS read-write

	STATUS mandatory

	DESCRIPTION



		"The key code provided by your VAR.  Available by

		 calling technical support at +1 508 460 6195."



	::= { chipDownload 2 }



chipDownloadDateTime OBJECT-TYPE

	SYNTAX DisplayString (SIZE(0..20))

	ACCESS read-only

	STATUS mandatory

	DESCRIPTION

		"The date of the last successful download in the

		 format hh:mm day DD Mon YY"

	::= { chipDownload 3 }





chipAlertTable OBJECT-TYPE

	SYNTAX SEQUENCE OF ChipAlertEntry

	ACCESS not-accessible

	STATUS mandatory

	DESCRIPTION

		"A table of entries associated with the management of

		alerts on this agent."

	::= { chipAlert 1 }



chipAlertEntry OBJECT-TYPE

	SYNTAX ChipAlertEntry

	ACCESS not-accessible

	STATUS mandatory

	DESCRIPTION

		"An entry associated with the management of an alert

		on this agent."

	INDEX { chipAlertIndex }

	::= { chipAlertTable 1 }



ChipAlertEntry ::=

	SEQUENCE {

		chipAlertIndex

			INTEGER,

		chipAlertMode

			INTEGER

		}



chipAlertIndex OBJECT-TYPE

	SYNTAX INTEGER {

		snmp-authentication(1),

		hello(2),

		change(3),

		console-display(4),

		port-up-down(5)

		}

	ACCESS  read-only

	STATUS  mandatory

	DESCRIPTION

		"The specific alert to manage.



		snmp-authentication(1) manages the standard authentication

		failure trap.



		hello(2) manages the hello trap.



		change(3), the change traps.



		console-display(4) controls the display of alerts at

		the console terminal.



		port-up-down(5) controls the generation of port up and

		port down traps."

	::= { chipAlertEntry 1 }



chipAlertMode OBJECT-TYPE

	SYNTAX INTEGER {

		enable(1),

		disable(2),

		filter(3)

		}

	ACCESS  read-write

	STATUS  mandatory

	DESCRIPTION

		"Enabling a specific alert allows that alert to be

		generated, or displayed at the console.



		If chipAlertIndex is set to port-up-down(5) then this object

		either overrides the port filter database by enabling or

		disabling all port alerts, or if this object is set to filter(3),

		then olPortAlertFilter in the olPortTable is consulted for

		when generating alerts for each individual port.



		Note that only port-up-down(5) alerts may be filtered. Setting

		this object to filter(3) for entries other than port-up-down(5)

		will return the invalidData object."

	::= { chipAlertEntry 2 }







-- The chipBootP Group

--

-- Implementation of the chipBootP group is mandatory for all agent

-- products that support the BootP protocol.

--

-- The chipBootP Group is used by an agent to initiate a BootP request

-- to a BootP server.





chipBootPStart OBJECT-TYPE

	SYNTAX INTEGER {

		bootpNoTransfer(1),

		bootpRequest(2)

		}

	ACCESS read-write

	STATUS mandatory

	DESCRIPTION

		"Setting chipBootPStart to bootpRequest(2) initiates an

		BootP request to obtain configuration information from a

		BootP server."

	::= { chipBootP 1 }



chipBootPPowerUpMode OBJECT-TYPE

	SYNTAX INTEGER {

		enable(1),

		disable(2)

		}

	ACCESS read-write

	STATUS mandatory

	DESCRIPTION

		"When set to enable(1) indicates that a BootP request to

		obtain configuration information should be initiated

		following a power-up sequence."

	::= { chipBootP 2 }



chipBootPIpAddress OBJECT-TYPE

	SYNTAX IpAddress

	ACCESS read-write

	STATUS mandatory

	DESCRIPTION

		"The IP Address of the BootP server. If no IP address is

		defined, the broadcast address will be used in a BootP request."

	::= { chipBootP 3 }



chipBootPResult OBJECT-TYPE

	SYNTAX INTEGER {

		clear(1),--not initialized

		xferInProgress(2),

		okay(3),

		noBootPResponse(4),

		otherBootPError(5)

		}

	ACCESS read-only

	STATUS mandatory

	DESCRIPTION

		"The result of the last BootP operation."

	::= { chipBootP 4 }









-- Chipcom Traps for use by agents.



-- Traps are defined using the conventions in RFC 1215.



chipHello TRAP-TYPE

	ENTERPRISE	chipcom

--	VARIABLES	{ sysObjectID }

	DESCRIPTION

		"A chipHello trap is sent every minute by an agent with

		the hello trap enabled.  The hello trap will discontinue

		being sent when either the agent receives an authenticate

		SNMP request, or after 255 minutes."

	::= 1



chipSlotDown TRAP-TYPE

	ENTERPRISE	chipcom

	VARIABLES	{ olModSlotIndex }

	DESCRIPTION

		"This trap indicates that the module in the indicated

		slot is down.  Usually, this trap is sent when the module

		has been removed.



		Sometimes, this trap is sent when management communications

		with this module have been broken.  In this case, it may not

		be possible to distinguish between a removed and a failed

		module.  The module type (olModType) and the module

		description (olModDescr) are also provided in this case."

	::= 2



chipSlotUp TRAP-TYPE

	ENTERPRISE	chipcom

	VARIABLES	{ olModSlotIndex }

	DESCRIPTION

		"This trap indicates that a blade in the indicated slot

		is up.  Usually, this trap is sent when the module is

		inserted into the hub.



		Sometimes, this trap is sent when management communications

		have been restored to a module where they had previously

		been broken.  In this case, it may not be possible to

		distinguish between a module that has just be inserted

		and a module that has just the.  The module type (olModType)

		and the module description (olModDescr) are also provided

		in this case."

	::= 3



chipEnvironment TRAP-TYPE

	ENTERPRISE	chipcom

	DESCRIPTION

		"A chipEnvironment trap indicates a change in the

		concentrator's environment has occurred.  The variables

		supplied indicate what exactly changed."

	::= 4



chipHardware TRAP-TYPE

	ENTERPRISE	chipcom

	DESCRIPTION

		"A chipHardware trap indicates that a soft hardware

		failure has been detected.  An example of a soft

		hardware failure is too many writes to non-vatile

		storage.  This is an indication to get the unit serviced."

	::= 5



chipSoftware TRAP-TYPE

	ENTERPRISE	chipcom

	DESCRIPTION

		"A chipSoftware trap indicates that a soft software

		failure has been detected.  This is an indication

		to get the unit serviced."

	::= 6



chipChange TRAP-TYPE

	ENTERPRISE	chipcom

	DESCRIPTION

		"A chipChange trap is used to indicate that a configuration

		change has occurred.  The actual variables that changed

		are included in the variables section of the PDU."

	::= 7



chipFatal TRAP-TYPE

	ENTERPRISE	chipcom

	DESCRIPTION

		"A chipFatal trap is used to indicate that a fatal

		error has occurred.  This is an indication to get

		the unit serviced."

	::= 8



chipTrunkDown TRAP-TYPE

	ENTERPRISE	chipcom

	VARIABLES	{ olTrunkSlotIndex,

			  olTrunkIndex,

			  olTrunkAdminState,

			  olTrunkStatus }

	DESCRIPTION

		"A chipTrunkDown trap indicates that trunk's status

		has changed to an error condition.  Multiple chipTrunkDown

		traps may be sent if the trunk's status changes from

		one error to another."

	::= 9



chipTrunkUp TRAP-TYPE

	ENTERPRISE	chipcom

	VARIABLES	{ olTrunkSlotIndex,

			  olTrunkIndex,

			  olTrunkAdminState,

			  olTrunkStatus }

	DESCRIPTION

		"A chipTrunkUp trap indicates that a trunk's status

		has changed to a non-error (okay or warning) condition."



	::= 10



chipPortDown TRAP-TYPE

	ENTERPRISE	chipcom

	VARIABLES	{ olPortSlotIndex,

			  olPortIndex,

			  olPortAdminState,

			  olPortStatus }

	DESCRIPTION

		"A chipPortDown trap indicates that a port's status

		has changed to an error condition.  Multiple chipPortDown

		traps may be sent if the port's status changes from

		one error to another."

	::= 11



chipPortUp TRAP-TYPE

	ENTERPRISE	chipcom

	VARIABLES	{ olPortSlotIndex,

			  olPortIndex,

			  olPortAdminState,

			  olPortStatus }

	DESCRIPTION

		"A chipPortUp trap indicates that a port's status

		has changed to a non-error (okay or warning) condition."

	::= 12



chipPing TRAP-TYPE

	ENTERPRISE	chipcom

	VARIABLES	{ chipEchoAddr, chipEchoNumber, chipEchoResponseCounts }

	DESCRIPTION

		"A chipPing trap is sent after the SNMP initiated PING

		command is completed.  After the last echo request packet

		is sent, this trap is sent indicating the ping address,

		the number of requests sent, and the number of responses

		received at the time the trap was generated."

	::= 13



chipAboveThreshd TRAP-TYPE

	ENTERPRISE	chipcom

	DESCRIPTION

		"A chipAboveThreshd trap indicates that a Counter or

		 Gauge variable has exceeded its threshd. The variable

		 which is above its threshd is the only variable in

		 the varBind list. Its value is taken at the time the

		 threshd calculation is performed and therefore may be

		 greater than the actual threshd value. Another above

		 threshd trap will not be sent until a below

		 threshd trap is sent."

	::= 14



chipBelowThreshd TRAP-TYPE

	ENTERPRISE	chipcom

	DESCRIPTION

		"A chipBelowThreshd trap indicates that a Counter or

		 Gauge variable had exceeded its threshd but is now

		 below its threshd. The variable which is below its

		 threshd is the only variable in the varBind list.

		 Its value is taken at the time the threshd calculation

		 is performed and therefore may be less than the

		 actual threshd value. Another below threshd trap

		 will not be sent until an above threshd trap is sent."

	::= 15



chipModuleDown TRAP-TYPE

	ENTERPRISE	chipcom

	VARIABLES	{ ocModSlotIndex, ocModSubSlotIndex,

			ocModType, ocModDescr }

	DESCRIPTION

		"A chipSlotDown trap indicates that management communications

		with the slot indicated by chipModSlotIndex has been

		broken.  This event usually occurs when a module has been

		physically removed from the concentrator.  However, it

		is possible for this event to occur when the particular

		module fails."

	::= 16



chipModuleUp TRAP-TYPE

	ENTERPRISE	chipcom

	VARIABLES	{ ocModSlotIndex, ocModSubSlotIndex,

			ocModType, ocModDescr }

	DESCRIPTION

		"A chipSlotUp trap indicates that management communications

		with the slot indicated by chipModSlotIndex has been

		established.  This event usually occurs when a module has

		physically been inserted into the concentrator.  The

		variable chipModType indicates the module type inserted.

		For "

	::= 17



chipSecurity TRAP-TYPE

	ENTERPRISE	chipcom

	VARIABLES	{ olNetOlSecTrapReason }

	DESCRIPTION

		"This trap indicates a change in the security environment.

		The olNetOlSecTrapReason specifies the reason for the

		trap.



		If the trap reason is intrusion-attempt(2), then the

		following objects will also be included in the trap:

		olPortSlotIndex and olPortPortIndex (to specify on which port

		the intrusion attempt occurred), and olPortAdminState (to

		indicate whether the port was automatically disabled).  The

		olEnetStatsPortLastSrcAddr object will be included if the

		MAC address of the intruder is available."

	::= 18





END
