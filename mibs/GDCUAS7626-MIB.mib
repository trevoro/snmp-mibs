-- Copyright 1998 General DataComm Inc., Inc. All Rights Reserved.
--
-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive license to use
-- this Specification in connection with the management of GDC's products.
--
-- This Specification is supplied "AS IS," and GDC makes no warranty,
-- either expressed or implied, as to the use operation, condition, or
-- performance of the Specification.
--
-- GDC UAS7626 MIB
-- **************************************************************************
--                        Revision History
-- **************************************************************************
-- Version	Date		Name		Description
-- 1.00A	26-Jan-98	C. Amorossi	Initial Revision. 
-- 1.00B        09-Feb-98	C. Amorossi	Added uas7626CircuitID
-- 1.00C        21-Apr-98       C. Amorossi     Changed description of
--						uas7626AlarmStatus
-- 1.00D        31-Aug-98       C. Amorossi     Added 
-- 						uas7626UnavailableTimeRegTable
-- ***************************************************************************

-- ***************************************************************************
--  MIB definitions begin
-- ***************************************************************************
GDCUAS7626-MIB DEFINITIONS ::= BEGIN

IMPORTS
    enterprises,TimeTicks   FROM RFC1155-SMI
    OBJECT-TYPE		    FROM RFC-1212
    DisplayString	    FROM RFC1213-MIB
    SCinstance		    FROM GDCMACRO-MIB;

gdc			    OBJECT IDENTIFIER ::= { enterprises 498 }
bql2			    OBJECT IDENTIFIER ::= { gdc 12 }
uas7626			    OBJECT IDENTIFIER ::= { bql2 12 }

uas7626Version		    OBJECT IDENTIFIER ::= { uas7626 1 }
uas7626Maintenance	    OBJECT IDENTIFIER ::= { uas7626 2 }
uas7626Configuration	    OBJECT IDENTIFIER ::= { uas7626 3 }
uas7626Diagnostics	    OBJECT IDENTIFIER ::= { uas7626 4 }
uas7626Performance	    OBJECT IDENTIFIER ::= { uas7626 5 }
uas7626AlarmConfig	    OBJECT IDENTIFIER ::= { uas7626 6 }
uas7626Alarms		    OBJECT IDENTIFIER ::= { uas7626 7 }

-- This MIB module uses the extended OBJECT-TYPE macro as
-- defined in RFC 1212.

-- Note:  All rows in all tables defined within this MIB module are
-- virtual.  They can neither be created or deleted by management
-- operations.
--
--****************************************************************************
-- 	SCinstance is defined as the addressing/indexing method of accessing
--	table objects in this MIB. The SCinstance represents the SpectraComm
--	shelf Slot, Line, Drop and interface address.
--	Represented as SLDi, (Slot, Line, Drop, interface).
--
--
-- 	For the uas7626: 
--
--		Byte		Range (dec.)		Identifies	
--		----		------------		----------
--		[S]lot		1 - 32			Physical Slot
--							1-16:  1st Shelf
--							17-32: 2nd Shelf
--
--		[L]ine		1
--		
--		[D]rop		0		
--
--		[i]nterface     0 - 6			0: Unit
--							1: Loop 1	
--							2: Loop 2
--							3: Loop 3
--							4: Loop 4	
--							5: Loop 5
--							6: Loop 6
--
-- ****************************************************************************
--
uas7626MIBversion OBJECT-TYPE
    SYNTAX  DisplayString (SIZE (5))
    ACCESS  read-only
    STATUS  mandatory
    DESCRIPTION
	    "Identifies the version of the MIB. The format of the version
	    is x.yzT, where 'x' identifies the major revision number, 'y'
	    identifies the minor revision number, 'z' identifies the
	    typographical revision, and T identifies the test revision.
	    Acceptable values for the individual revision components are
	    as follows:
		 x: 1 - 9
		 y: 0 - 9
		 z: 0 - 9
		 T: A - Z
	    Upon formal release, no designation for the test revision will
	    be present."
    ::= { uas7626Version 1 }



-- ****************************************************************************
--                                Version Table
-- ****************************************************************************
	
uas7626VersionTable OBJECT-TYPE
    SYNTAX  SEQUENCE OF Uas7626VersionEntry
    ACCESS  not-accessible
    STATUS  mandatory
    DESCRIPTION 
	    "The 7626 version table "
    ::= { uas7626Version 2  }

uas7626VersionEntry OBJECT-TYPE
    SYNTAX  Uas7626VersionEntry
    ACCESS  not-accessible
    STATUS  mandatory
    DESCRIPTION
	    "An entry in the GDC uas7626System Version Table."
    INDEX  { uas7626VersionIndex }
    ::= { uas7626VersionTable 1 }
									
Uas7626VersionEntry ::=
    SEQUENCE {
	uas7626VersionIndex          SCinstance,
	uas7626ActiveFirmwareRev     DisplayString,
	uas7626StoredFirmwareRev     DisplayString,
	uas7626StoredFirmwareStatus  INTEGER,
	uas7626SwitchActiveFirmware  INTEGER,
	uas7626DownloadingMode       INTEGER
	}

uas7626VersionIndex OBJECT-TYPE
    SYNTAX  SCinstance
    ACCESS  read-only
    STATUS  mandatory
    DESCRIPTION
        "Integer value which uniquely identifies the UAS7626 to which this
         entry is applicable. SCinstance is defined to be SLDi where:
         S (byte value) - physical shelf slot location (01-32)
         L (byte value) - line number (01)
         D (byte value) - drop number (00)
         i (byte value) - loop or interface number (00-06)"
    ::= { uas7626VersionEntry 1 }

uas7626ActiveFirmwareRev OBJECT-TYPE
    SYNTAX  DisplayString (SIZE(8))
    ACCESS  read-only
    STATUS  mandatory
    DESCRIPTION
        "The version number of the firmware currently executing.
	 The format is MM.NN.BB where:
		MM: Major Revision (0-99)
		NN: Minor Revision (0-99)
		BB: Bug Fix Revision (0-99)
	 Valid [i]nterface = 0"
    ::= { uas7626VersionEntry 2 }

uas7626StoredFirmwareRev OBJECT-TYPE
    SYNTAX DisplayString (SIZE(8))
    ACCESS read-only
    STATUS mandatory
    DESCRIPTION
        "The version number of the firmware stored (in a compressed format) 
         but not currently executing.
		MM: Major Revision (0-99)
		NN: Minor Revision (0-99)
		BB: Bug Fix Revision (0-99)
	 Valid [i]nterface = 0"
    ::= { uas7626VersionEntry 3 }

uas7626StoredFirmwareStatus OBJECT-TYPE
    SYNTAX INTEGER {
        statBlank(1),                       
        statDownLoading(2),
	statOK(3),
	statCheckSumBad(4),    
	statUnZipping(5),
	statBadUnZip(6),
	statDownloadAborted(7)
                    
    }
    ACCESS read-only
    STATUS mandatory
    DESCRIPTION
        "This object represents the state of the Non-Active or Stored firmware:

         statBlank(1)    	Factory Default                  
         statDownLoading(2)	In process of downloading firmware
	 statOK(3)		Zipped version checksum succesful (OK to switch)
				(can set uas7626SwitchActiveFirmware to	
				switchActive(2))
	 statCheckSumBad(4)    	Failed checksum after download
	 statUnZipping(5)	In process of uncompressing into active area
	 statBadUnZip(6)      	Failed last uncompress 
	 statDownloadAborted(7) Download aborted by user             

	 Valid [i]nterface = 0"
    ::= { uas7626VersionEntry 4 }


uas7626SwitchActiveFirmware OBJECT-TYPE
    SYNTAX INTEGER {
        switchNorm(1),                  -- Read only
        switchActive(2)			-- Write only
    }
    ACCESS read-write
    STATUS mandatory
    DESCRIPTION
        "This object is used to switch the active executing firmware from 
	 the version in uas7626ActiveFirmwareRev to the version in 
	 uas7626StoredFirmwareRev.

	 When a  switchActive(2) is set (write only) the element will:
		1) reboot
		2) uncompress stored code into active area
		3) perform checksum on active area
		4) Set uas7626StoredStatus object to indicate results
		5) If succesfull:
		    update uas7626ActiveFirmwareRev and uas7626StoredFirmwareRev
		    and begin executing
		   If failed: 
		    replace active area with previous revision

	 The switchNorm(1) enumeration will always be read. 

	 Setting switchActive(2) when the uas7626StoredFirmwareStatus is 
	 not statOK(3) will result in an error.
	 Valid [i]nterface = 0"
    ::= { uas7626VersionEntry 5 }


uas7626DownloadingMode OBJECT-TYPE
    SYNTAX INTEGER {
        disableAll(1),
        enableAndWait(2),
	enableAndSwitch(3)
    }
    ACCESS read-write
    STATUS mandatory
    DESCRIPTION
        "This object is used to configure the download mode:

         disableAll(1)	       Prevents any firmware downloading to UAS7626

         enableAndWait(2)      Allows downloading zipped code to be stored only!
								
	 enableAndSwitch(3)    Allows downloading and then unzips and begins executing
			       the new code
	 Valid [i]nterface = 0"
    ::= { uas7626VersionEntry 6 }


--
-- *********************************************************
--  GDC uas7626 Maintenance Table
-- **********************************************************

uas7626MaintenanceTable OBJECT-TYPE
    SYNTAX  SEQUENCE OF Uas7626MaintenanceEntry
    ACCESS  not-accessible
    STATUS  mandatory
    DESCRIPTION
	    "The table describes the maintenance objects for uas7626." 
    ::= { uas7626Maintenance 1  }

uas7626MaintenanceEntry OBJECT-TYPE
    SYNTAX  Uas7626MaintenanceEntry
    ACCESS  not-accessible
    STATUS  mandatory
    DESCRIPTION
	    "An entry in the GDC 7626 Maintenance Table."
    INDEX  { uas7626MaintenanceLineIndex }
    ::= { uas7626MaintenanceTable 1 }

Uas7626MaintenanceEntry ::=
    SEQUENCE {
	uas7626MaintenanceLineIndex SCinstance,
	uas7626SoftReset	    INTEGER,
	uas7626DefaultInit	    INTEGER,
	uas7626ResetMajorAlarm	    INTEGER,
	uas7626ResetMinorAlarm	    INTEGER,
	uas7626ResetStatistics	    INTEGER,
	uas7626ValidIntervals	    INTEGER,
	uas7626SysUpTime	    INTEGER,
	uas7626LedStatus	    OCTET STRING,
	uas7626AlarmStatus	    OCTET STRING,
	uas7626StatLastInitialized  TimeTicks,
	uas7626CircuitID	    DisplayString	
    }

uas7626MaintenanceLineIndex OBJECT-TYPE
    SYNTAX  SCinstance
    ACCESS  read-only
    STATUS  mandatory
    DESCRIPTION
        "Integer value which uniquely identifies the UAS7626 to which this
         entry is applicable. SCinstance is defined to be SLDi where:
         S (byte value) - physical shelf slot location (01-32)
         L (byte value) - line number (01)
         D (byte value) - drop number (00)
         i (byte value) - loop or interface number (00-06)"
    ::= { uas7626MaintenanceEntry 1 }

uas7626SoftReset OBJECT-TYPE
    SYNTAX  INTEGER {
		norm(1), -- read-only
		reset(2) -- write-only
	    }
    ACCESS  read-write
    STATUS  mandatory
    DESCRIPTION
	"Supports the action of soft resetting the unit.  
	 When this object is set to reset(2), then the unit 
	 performs a soft reset, whose meaning is specific to
	 the type of unit being managed. The value of norm(1) 
	 will be returned when the reset is complete.
	 The value of norm(1) can not be set by management.
	 Valid [i]nterface = 0"
	::= { uas7626MaintenanceEntry 2 }

uas7626DefaultInit OBJECT-TYPE
    SYNTAX  INTEGER {
		normal(1),         -- read-only
		factoryDefault(2)  -- write-only
	    }
    ACCESS  read-write
    STATUS  mandatory
    DESCRIPTION
	"This is used to allow the NonVolatile Configuration to 
	 be set to a factory default state.  When this value is set
	 to factoryDefault(2) the unit will perform  a reset to make 
	 the default configuration take affect. 
	 The value of normal(1) will be returned when the 
	 initialization is complete.
	 The value of normal(1) can not be set by management.
	 Valid [i]nterface = 0"
	::= { uas7626MaintenanceEntry 3 }

uas7626ResetMajorAlarm	OBJECT-TYPE
    SYNTAX  INTEGER {
		norm(1), -- read-only
		reset(2) -- write-only
	    }
    ACCESS  read-write 
    STATUS  mandatory
    DESCRIPTION 
	"This variable is used to reset the Major BER alarm.
	 A value of norm(1) cannot be set by management and
	 will always be returned on a read.
	 Valid [i]nterface = 01-06"
    ::= { uas7626MaintenanceEntry 4 }
 
uas7626ResetMinorAlarm OBJECT-TYPE
    SYNTAX  INTEGER {
		norm(1), -- read-only
		reset(2) -- write-only
	    }
    ACCESS  read-write 
    STATUS  mandatory
    DESCRIPTION 
	"This variable is used to reset the Minor BER alarm.
	 A value of norm(1) cannot be set by management and
	 will always be returned on a read.
	 Valid [i]nterface = 01-06"
    ::= { uas7626MaintenanceEntry 5 }

uas7626ResetStatistics OBJECT-TYPE
    SYNTAX  INTEGER {
		norm(1), -- read-only
		reset(2) -- write-only
	    }
    ACCESS  read-write
    STATUS  mandatory
    DESCRIPTION
	"This variable is used to reset the performance intervals.
	 When it is set to reset, the performance tables and uas7626Valid
	 intervals are reset to zero. The value of norm(1) can not be set 
	 by management.
	 Valid [i]nterface = 01-06"
    ::= { uas7626MaintenanceEntry 6 }

uas7626ValidIntervals OBJECT-TYPE
    SYNTAX  INTEGER (1..16)
    ACCESS  read-only
    STATUS  mandatory
    DESCRIPTION
	"The number of  previous  intervals  for  which
	 valid data was collected.  The value will be 16
	 unless the interface was brought on-line within
	 the last 4 hours, in which case the value will
	 be the number of complete 15  minute  intervals
	 the since interface has been online.	
	 Valid [i]nterface = 01-06"
    ::= {uas7626MaintenanceEntry 7 }

uas7626SysUpTime OBJECT-TYPE
    SYNTAX  INTEGER (1..2147483647)
    ACCESS  read-only
    STATUS  mandatory
    DESCRIPTION
	"This variable is used to report the elapsed system tick
	 time for conversion to real time at the controller and is
	 not related to the sysUpTime referenced in MIB-II.
	 Upon power-up of the unit, the elapsed time is cleared.
	 The elapsed time counter rolls over upon reaching the
	 maximum count.
	 Valid [i]nterface = 0"
    ::= { uas7626MaintenanceEntry 8 }

uas7626LedStatus OBJECT-TYPE
    SYNTAX  OCTET STRING (SIZE(4))
    ACCESS  read-only
    STATUS  mandatory
    DESCRIPTION
	"Returns a bitwise snapshot of the front panel LED state:

		key 
		---
		001 = SOLID GREEN 
		010 = SOLID RED	
		011 = FLASHING RED
		100 = FLASHING GREEN

		1.7 - n/a
		1.6 - \
		1.5 -  --  Loop 1	(001, 010, 011, 100)   
		1.4 - /  
		1.3 - \		
		1.2 -  --  Loop 2	(001, 010, 011, 100)Y
		1.1 - / 
		1.0 - f/u 	

		2.7 - f/u
		2.6 - \
		2.5 -  --  Loop 3	(001, 010, 011, 100)
		2.4 - /	
		2.3 - \ 
		2.2 -  --  Loop 4	(001, 010, 011, 100)		
		2.1 - /
		2.0 - f/u	

		3.7 - f/u
		3.6 - \
		3.5 -  --  Loop 5	(001, 010, 011, 100)
		3.4 - /	
		3.3 - \ 
		3.2 -  --  Loop 6	(001, 010, 011, 100)		
		3.1 - /
		3.0 - f/u	

		4.7 - f/u
		4.6 - f/u
		4.5 - f/u
		4.4 - Alarm                      (0 = Off; 1 = Alarm Active )
		4.3 - Test Mode                  (0 = Off; 1 = Alarm Active )
		4.2 - In Service                 (0 = Off; 1 = Alarm Active )
		4.1 - Transmitter Timing Failure (0 = Off; 1 = Alarm Active )
		4.0 - Management Response        (0 = Off; 1 = Alarm Active )

	 Valid [i]nterface = 0"
    ::= { uas7626MaintenanceEntry 9 }
	
uas7626AlarmStatus OBJECT-TYPE
    SYNTAX  OCTET STRING (SIZE(7))
    ACCESS  read-only
    STATUS  mandatory
    DESCRIPTION
	"Returns actual bit-wise Status of alarms 
	 regardless of whether the alarm is masked
	 or not.

		key 
		---
		0 = Inactive 
		1 = Active

		1.7 - f/u
		1.6 - Power-up
		1.5 - f/u
		1.4 - f/u
		1.3 - f/u
		1.2 - f/u
		1.1 - f/u
		1.0 - f/u

		Note: n=2-6 for octets 2-7

		n.7 - f/u
		n.6 - Loop n Major
		n.5 - Loop n Minor
		n.4 - Loop n Loss of Transmit Clock
		n.3 - Loop n 2B1Q Out of Sync
		n.2 - Loop n Sealing Current Non-Continuity Alarm
		n.1 - Loop n Errored Seconds
		n.0 - Loop n Unavailable Seconds

	 Valid [i]nterface = 0"
    ::= {uas7626MaintenanceEntry 10}

uas7626StatLastInitialized OBJECT-TYPE
    SYNTAX  TimeTicks
    ACCESS  read-only
    STATUS  mandatory
    DESCRIPTION
	"The elapsed time since the statistics were last initialized. 
	 This will be zero'd when uas7626ResetStatistics is reset(2).
	 Valid [i]nterface = 01-06"
    ::= {uas7626MaintenanceEntry 11 }


uas7626CircuitID       OBJECT-TYPE
    SYNTAX  DisplayString (SIZE(16))
    ACCESS  read-write
    STATUS  mandatory
    DESCRIPTION
	"Name to identify the circuit.
	 Valid [i]nterface = 01-06"
    ::= {uas7626MaintenanceEntry 12 }


--
-- ********************************************************************
-- The GDC 7626 Configuration Table
-- ********************************************************************
--

uas7626ConfigTable OBJECT-TYPE
    SYNTAX  SEQUENCE OF Uas7626ConfigEntry
    ACCESS  not-accessible
    STATUS  mandatory
    DESCRIPTION
	    "The GDC Configuration table."
    ::= { uas7626Configuration 1 }

uas7626ConfigEntry OBJECT-TYPE
    SYNTAX  Uas7626ConfigEntry
    ACCESS  not-accessible
    STATUS  mandatory
    DESCRIPTION
	    "The GDC Configuration table entry."
    INDEX { uas7626ConfigIndex }
    ::= { uas7626ConfigTable 1 }

Uas7626ConfigEntry ::= 
    SEQUENCE {
	uas7626ConfigIndex	SCinstance,
 	uas7626DataRate		INTEGER,
	uas7626Highway		INTEGER,
	uas7626TimeSlot		INTEGER
   }
	
uas7626ConfigIndex OBJECT-TYPE
    SYNTAX  SCinstance
    ACCESS  read-only
    STATUS  mandatory
    DESCRIPTION
        "Integer value which uniquely identifies the UAS7626 to which this
         entry is applicable. SCinstance is defined to be SLDi where:
         S (byte value) - physical shelf slot location (01-32)
         L (byte value) - line number (01)
         D (byte value) - drop number (00)
         i (byte value) - loop or interface number (00-06)"
    ::= { uas7626ConfigEntry 1 }

uas7626DataRate OBJECT-TYPE
    SYNTAX  INTEGER {
		kbps64(1),
		kbps128(2),
		inhibit(3)
    }
    ACCESS read-write
    STATUS mandatory
    DESCRIPTION
	"Object to select the Data Rate on Loop n.
	 Valid [i]nterface = 01-06"
    ::= { uas7626ConfigEntry 2 }

uas7626Highway	OBJECT-TYPE
    SYNTAX INTEGER {
	       notAssigned(1),
	       highway1(2),
	       highway2(3),
	       highway3(4),
	       highway4(5),
	       highway5(6),
	       highway6(7),
	       highway7(8),
	       highway8(9)
    }
    ACCESS read-write
    STATUS mandatory
    DESCRIPTION
	"Object to select the data highway for Loop n.
	 Valid [i]nterface = 01-06"
    ::= {uas7626ConfigEntry 3}

uas7626TimeSlot	OBJECT-TYPE
    SYNTAX INTEGER(1..64)
    ACCESS read-write
    STATUS mandatory
    DESCRIPTION
	"Object to select the timeslots for the data highway given by
	 uas7624Highway for loop n. Valid selections are 1-31 and 64.
	 A value of 64 indicates the loop is not assigned to a highway.
	 Valid [i]nterface = 01-06"
    ::= {uas7626ConfigEntry 4}

--
-- ********************************************************************
-- GDC 7626 Diagnostics
-- ********************************************************************
-- This table contains the diagnostic test information.
	
uas7626DiagTable OBJECT-TYPE
    SYNTAX  SEQUENCE OF Uas7626DiagEntry
    ACCESS  not-accessible
    STATUS  mandatory
    DESCRIPTION
	    "The GDC 7626 Diagnostics table.  Information in the entries of
	    this table support diagnostics testing, both active testing
	    via patterns, and passive testing via loopbacks."
    ::= { uas7626Diagnostics 1 }

uas7626DiagEntry OBJECT-TYPE
    SYNTAX  Uas7626DiagEntry
    ACCESS  not-accessible
    STATUS  mandatory
    DESCRIPTION
	    "The GDC 7626 Diagnostics table entry."
    INDEX { uas7626DiagIndex }
    ::= { uas7626DiagTable 1 }

Uas7626DiagEntry ::= 
    SEQUENCE {
	uas7626DiagIndex 		 SCinstance,
	uas7626TestSelection		 INTEGER,
	uas7626TestResults		 INTEGER,
	uas7626ResetTestResults 	 INTEGER
    }

uas7626DiagIndex OBJECT-TYPE
    SYNTAX  SCinstance
    ACCESS  read-only
    STATUS  mandatory
    DESCRIPTION
        "Integer value which uniquely identifies the UAS7626 to which this
         entry is applicable. SCinstance is defined to be SLDi where:
         S (byte value) - physical shelf slot location (01-32)
         L (byte value) - line number (01)
         D (byte value) - drop number (00)
         i (byte value) - loop or interface number (00-06)"
    ::= { uas7626DiagEntry 1 }

uas7626TestSelection OBJECT-TYPE
    SYNTAX INTEGER {
	      stopTest(1),
	      digitalLoopback(2),
	      selfTest(3),			 
	      remoteDigitalLoopback(4),
	      rdlSelfTest(5)
    }
    ACCESS read-write
    STATUS mandatory
    DESCRIPTION
	"Selects the test to run. A selection of 
	 stopTest(1) stops the current test.
	 Valid [i]nterface = 01-06"
    ::= { uas7626DiagEntry 2 }

uas7626TestResults OBJECT-TYPE
    SYNTAX  INTEGER(0..1048576)
    ACCESS  read-only
    STATUS  mandatory
    DESCRIPTION
	"Returns the self test bit error count.
	 Valid [i]nterface = 01-06"
    ::= { uas7626DiagEntry 3 }


uas7626ResetTestResults	OBJECT-TYPE
    SYNTAX  INTEGER {
		norm(1),   -- read-only
		reset(2)   -- write-only
    }
    ACCESS  read-write
    STATUS  mandatory
    DESCRIPTION
	"Resets the self test bit error count.
	 A value of norm(1) cannot be set by management
	 and is always returned on a read.
	 Valid [i]nterface = 01-06"
    ::= { uas7626DiagEntry 4 }

--
-- ********************************************************************
-- GDC uas7626 Alarm Object Identifier Definitions
-- ********************************************************************


uas7626NoResponseAlm		    OBJECT IDENTIFIER ::= {uas7626Alarms 1}
uas7626DiagRxErrAlm		    OBJECT IDENTIFIER ::= {uas7626Alarms 2}
uas7626PowerUpAlm		    OBJECT IDENTIFIER ::= {uas7626Alarms 3}
uas7626LossofTransmitClockAlm	    OBJECT IDENTIFIER ::= {uas7626Alarms 4}
uas7626OutofSyncAlm		    OBJECT IDENTIFIER ::= {uas7626Alarms 5}
uas7626SealingCurrentNoContAlm	    OBJECT IDENTIFIER ::= {uas7626Alarms 6}
uas7626UASAlm			    OBJECT IDENTIFIER ::= {uas7626Alarms 7}
uas7626ESAlm			    OBJECT IDENTIFIER ::= {uas7626Alarms 8}
uas7626MajorBERAlm		    OBJECT IDENTIFIER ::= {uas7626Alarms 9}
uas7626MinorBERAlm		    OBJECT IDENTIFIER ::= {uas7626Alarms 10}

-- ALARM				Mask- Valid   Thres
--					able   int   
-- ============================================================================
-- uas7626NoResponseAlm			no      0      no
-- uas7626DiagRxErrAlm			no      0      no
-- uas7626PowerUpAlm			no      0      no
-- uas7626LossofTransmitClockAlm	yes    1-6     no 
-- uas7626OutofSyncAlm		        yes    1-6     no 
-- uas7626SealingCurrentNoContAlm	yes    1-6     no 
-- uas7626UASAlm			yes    1-6     no 
-- uas7626ESAlm				yes    1-6     no 
-- uas7626MajorBERAlm			yes    1-6     yes
-- uas7626MinorBERAlm			yes    1-6     yes

--
-- ********************************************************************
-- GDC uas7626 Alarm Configuration
-- ********************************************************************

uas7626AlarmConfigTable OBJECT-TYPE
    SYNTAX  SEQUENCE OF Uas7626AlarmConfigEntry
    ACCESS  not-accessible
    STATUS  mandatory
    DESCRIPTION
	    "This table contains entries that configure Alarm reporting."
    ::= { uas7626AlarmConfig 1 }

uas7626AlarmConfigEntry OBJECT-TYPE
    SYNTAX  Uas7626AlarmConfigEntry
    ACCESS  not-accessible
    STATUS  mandatory
    DESCRIPTION
	    "An entry in the uas7626 Alarm Configuration table."
    INDEX { uas7626AlarmConfigIndex, uas7626AlarmConfigIdentifier }
    ::= { uas7626AlarmConfigTable 1 }

Uas7626AlarmConfigEntry ::=
    SEQUENCE {
	uas7626AlarmConfigIndex		SCinstance,
	uas7626AlarmConfigIdentifier	OBJECT IDENTIFIER,
	uas7626AlarmCountThreshold	INTEGER
    }

uas7626AlarmConfigIndex OBJECT-TYPE
    SYNTAX  SCinstance
    ACCESS  read-only
    STATUS  mandatory
    DESCRIPTION
        "Integer value which uniquely identifies the UAS7626 to which this
         entry is applicable. SCinstance is defined to be SLDi where:
         S (byte value) - physical shelf slot location (01-32)
         L (byte value) - line number (01)
         D (byte value) - drop number (00)
         i (byte value) - loop or interface number (00-06)"
    ::= { uas7626AlarmConfigEntry 1 }

uas7626AlarmConfigIdentifier OBJECT-TYPE
    SYNTAX  OBJECT IDENTIFIER
    ACCESS  read-only
    STATUS  mandatory
    DESCRIPTION
    "format: iso.org.dod.internet.private.enterprises.gdc.
             bql2.uas7626.uas7626Alarms.ALM
     example:  1.3.6.1.4.1.498.12.12.7.ALM
     where ALM = 1 for uas7626NoResponse alarm, 2 for uas7626DiagRxErr alarm,
                 etc., as specified in the Alarm Definitions above."
    ::= { uas7626AlarmConfigEntry 2 }

uas7626AlarmCountThreshold OBJECT-TYPE
    SYNTAX  INTEGER {
		thres10E03(1),   
		thres10E04(2),   
		thres10E05(3),   
		thres10E06(4)   
	    }
    ACCESS  read-write
    STATUS  mandatory
    DESCRIPTION
	"This function sets/reads the alarm threshold criteria.
	 This threshold is used along with the the alarm window to 
	 determine the number of instances in a given time frame for
	 an alarm to occur before the alarm is considered active.
	 Valid [i]nterface = 01-06"
    ::= { uas7626AlarmConfigEntry 3 }

--
-- ********************************************************************
-- GDC LOCAL uas7626 Alarm Configuration
-- ********************************************************************
-- Local Alarms are alarms that optionally activate the backplane
-- Major or Minor buses. These alarms changes are never reported in an
-- unsolicited message to the proxy agent hence, the reason for the alarm
-- card. These alarms are different from the previously defined alarms
-- in that the mask state has three possible values.

uas7626LocalAlarmConfigTable OBJECT-TYPE
    SYNTAX SEQUENCE OF Uas7626LocalAlarmConfigEntry
    ACCESS not-accessible
    STATUS mandatory
    DESCRIPTION
	    "The uas7626LocalAlarmConfigTable contains entries 
	    that configure alarm reporting to the alarm card."
    ::= { uas7626AlarmConfig 2 }

uas7626LocalAlarmConfigEntry OBJECT-TYPE
    SYNTAX Uas7626LocalAlarmConfigEntry
    ACCESS not-accessible
    STATUS mandatory
    DESCRIPTION
	    "An entry in the GDC Local Alarm Configuration table."
    INDEX { uas7626LocalAlarmConfigIndex }
    ::= { uas7626LocalAlarmConfigTable 1 }

Uas7626LocalAlarmConfigEntry ::=
    SEQUENCE {
	uas7626LocalAlarmConfigIndex	SCinstance,
	uas7626LossOfClockLocal		INTEGER,
	uas7626ESLocal			INTEGER,
	uas7626UASLocal			INTEGER,
	uas7626OutofSyncLocal		INTEGER,
	uas7626NoSealingCurrentLocal	INTEGER
    }

uas7626LocalAlarmConfigIndex OBJECT-TYPE
    SYNTAX  SCinstance
    ACCESS  read-only
    STATUS  mandatory
    DESCRIPTION
        "Integer value which uniquely identifies the UAS7626 to which this
         entry is applicable. SCinstance is defined to be SLDi where:
         S (byte value) - physical shelf slot location (01-32)
         L (byte value) - line number (01)
         D (byte value) - drop number (00)
         i (byte value) - loop or interface number (00-06)"
      ::= { uas7626LocalAlarmConfigEntry 1 }

uas7626LossOfClockLocal OBJECT-TYPE
    SYNTAX  INTEGER {
		disabled(1),
		enabledMinor(2),
		enabledMajor(3)
	    }
    ACCESS  read-write
    STATUS  mandatory
    DESCRIPTION
	"Disables or enables the alarm on the Major buss or Minor Buss.
	 Valid [i]nterface = 01-06"
      ::= { uas7626LocalAlarmConfigEntry 2 }

uas7626ESLocal OBJECT-TYPE
    SYNTAX  INTEGER {
		disabled(1),
		enabledMinor(2),
		enabledMajor(3)
	    }
    ACCESS  read-write
    STATUS  mandatory
    DESCRIPTION
	"Disables or enables the alarm on the Major buss or Minor Buss.
	 Valid [i]nterface = 01-06"
      ::= { uas7626LocalAlarmConfigEntry 3 }

uas7626UASLocal OBJECT-TYPE
    SYNTAX  INTEGER {
		disabled(1),
		enabledMinor(2),
		enabledMajor(3)
	    }
    ACCESS  read-write
    STATUS  mandatory
    DESCRIPTION
	"Disables or enables the alarm on the Major buss or Minor Buss.
	 Valid [i]nterface = 01-06"
    ::= { uas7626LocalAlarmConfigEntry 4 }

uas7626OutofSyncLocal OBJECT-TYPE
    SYNTAX  INTEGER {
		disabled(1),
		enabledMinor(2),
		enabledMajor(3)
	    }
    ACCESS  read-write
    STATUS  mandatory
    DESCRIPTION
	"Disables or enables the alarm on the Major buss or Minor Buss.
	 Valid [i]nterface = 01-06"
    ::= { uas7626LocalAlarmConfigEntry 5 }

uas7626NoSealingCurrentLocal       OBJECT-TYPE
    SYNTAX  INTEGER {
		disabled(1),
		enabledMinor(2),
		enabledMajor(3)
	    }
    ACCESS  read-write
    STATUS  mandatory
    DESCRIPTION
	"Disables or enables the alarm on the Major buss or Minor Buss.
	 Valid [i]nterface = 01-06"
    ::= { uas7626LocalAlarmConfigEntry 6 }

--
-- ********************************************************************
-- ATT Current Performance Table
-- ********************************************************************

uas7626CurrentTable OBJECT-TYPE
    SYNTAX  SEQUENCE OF Uas7626CurrentEntry
    ACCESS  not-accessible
    STATUS  mandatory
    DESCRIPTION
	    "The uas7626 Current table contains various statistics being
	    collected for the current 15 minute interval."
    ::= { uas7626Performance 3 }


uas7626CurrentEntry OBJECT-TYPE
    SYNTAX  Uas7626CurrentEntry
    ACCESS  not-accessible
    STATUS  mandatory
    DESCRIPTION
	    "An entry in the uas7626 Current table."
    INDEX   { uas7626CurrentIndex }
    ::= { uas7626CurrentTable 1 }

Uas7626CurrentEntry ::=
    SEQUENCE {
	uas7626CurrentIndex SCinstance,
	uas7626CurrentStat  OCTET STRING
    }

uas7626CurrentIndex OBJECT-TYPE
    SYNTAX  SCinstance
    ACCESS  read-only
    STATUS  mandatory
    DESCRIPTION
        "Integer value which uniquely identifies the UAS7626 to which this
         entry is applicable. SCinstance is defined to be SLDi where:
         S (byte value) - physical shelf slot location (01-32)
         L (byte value) - line number (01)
         D (byte value) - drop number (00)
         i (byte value) - loop or interface number (00-06)"
    ::= { uas7626CurrentEntry 1 }

uas7626CurrentStat  OBJECT-TYPE
    SYNTAX  OCTET STRING (SIZE(10))
    ACCESS  read-only
    STATUS  mandatory
    DESCRIPTION
	"Returns a bitwise snapshot of the current 15 minute
	 statistics:

		 Octet 1 bit 7 - not used
			 bit 6 - future use
			 bit 5 - future use
			 bit 4 - 2^4
			 bit 3 - 2^3
			 bit 2 - 2^2
			 bit 1 - 2^1
			 bit 0 - 2^0  Loop ID  

		 Octet 2 bit 7 - not used
			 bit 6 - future use
			 bit 5 - future use
			 bit 4 - future use
			 bit 3 - future use
			 bit 2 - 2^9   
			 bit 1 - 2^8
			 bit 0 - 2^7

		 Octet 3 bit 7 - not used
			 bit 6 - 2^6
			 bit 5 - 2^5 
			 bit 4 - 2^4 
			 bit 3 - 2^3 
			 bit 2 - 2^2 
			 bit 1 - 2^1
			 bit 0 - 2^0  Errored Seconds

		 Octet 4 bit 7 - not used
			 bit 6 - future use
			 bit 5 - future use
			 bit 4 - future use
			 bit 3 - future use
			 bit 2 - 2^9   
			 bit 1 - 2^8
			 bit 0 - 2^7

		 Octet 5 bit 7 - not used
			 bit 6 - 2^6
			 bit 5 - 2^5 
			 bit 4 - 2^4 
			 bit 3 - 2^3 
			 bit 2 - 2^2 
			 bit 1 - 2^1
			 bit 0 - 2^0  Severely Errored Seconds

		 Octet 6 bit 7 - not used
			 bit 6 - future use
			 bit 5 - future use
			 bit 4 - future use
			 bit 3 - future use
			 bit 2 - 2^9   
			 bit 1 - 2^8
			 bit 0 - 2^7

		 Octet 7 bit 7 - not used
			 bit 6 - 2^6
			 bit 5 - 2^5 
			 bit 4 - 2^4 
			 bit 3 - 2^3 
			 bit 2 - 2^2 
			 bit 1 - 2^1
			 bit 0 - 2^0   Unavailable Seconds

		 Octet 8 bit 7 - not used
			 bit 6 - future use
			 bit 5 - future use 
			 bit 4 - future use 
			 bit 3 - future use 
			 bit 2 - 2^16
			 bit 1 - 2^15
			 bit 0 - 2^14  

		 Octet 9 bit 7 - not used
			 bit 6 - 2^13
			 bit 5 - 2^12
			 bit 4 - 2^11
			 bit 3 - 2^10
			 bit 2 - 2^9 
			 bit 1 - 2^8
			 bit 0 - 2^7   

		Octet 10 bit 7 - not used
			 bit 6 - 2^6
			 bit 5 - 2^5 
			 bit 4 - 2^4 
			 bit 3 - 2^3 
			 bit 2 - 2^2 
			 bit 1 - 2^1
			 bit 0 - 2^0   FEBE (Far End Block Error Count)

	 Valid [i]nterface = 01-06"
    ::= {uas7626CurrentEntry 2 }


--
-- ********************************************************************
-- ATT Interval Performance Table
-- ********************************************************************

uas7626IntervalTable OBJECT-TYPE
    SYNTAX  SEQUENCE OF Uas7626IntervalEntry
    ACCESS  not-accessible
    STATUS  mandatory
    DESCRIPTION
	    "The uas7626 Interval table contains various statistics 
	    collected by each Interface over the last 16 15-minute
	    intervals."
    ::= { uas7626Performance 4 }


uas7626IntervalEntry OBJECT-TYPE
    SYNTAX  Uas7626IntervalEntry
    ACCESS  not-accessible
    STATUS  mandatory
    DESCRIPTION
	    "An entry in the Interval table."
    INDEX   { uas7626IntervalIndex, uas7626IntervalNumber }
    ::= { uas7626IntervalTable 1 }

Uas7626IntervalEntry ::=
    SEQUENCE {
	uas7626IntervalIndex	SCinstance,
	uas7626IntervalNumber	INTEGER,
	uas7626IntervalStat	OCTET STRING
    }

uas7626IntervalIndex OBJECT-TYPE
    SYNTAX  SCinstance
    ACCESS  read-only
    STATUS  mandatory
    DESCRIPTION
        "Integer value which uniquely identifies the UAS7626 to which this
         entry is applicable. SCinstance is defined to be SLDi where:
         S (byte value) - physical shelf slot location (01-32)
         L (byte value) - line number (01)
         D (byte value) - drop number (00)
         i (byte value) - loop or interface number (00-06)"
    ::= { uas7626IntervalEntry 1 }

uas7626IntervalNumber OBJECT-TYPE
    SYNTAX  INTEGER (1..16)
    ACCESS  read-only
    STATUS  mandatory
    DESCRIPTION
	"The interval number 1- 16.
	 Valid [i]nterface = 01-06"
    ::= { uas7626IntervalEntry 2 }

uas7626IntervalStat OBJECT-TYPE
    SYNTAX  OCTET STRING (SIZE(11))
    ACCESS  read-only
    STATUS  mandatory
    DESCRIPTION
	"Returns a bitwise snapshot of the interval statistics.

		 Octet 1 bit 7 - not used
			 bit 6 - future use
			 bit 5 - future use
			 bit 4 - 2^4
			 bit 3 - 2^3
			 bit 2 - 2^2
			 bit 1 - 2^1
			 bit 0 - 2^0  Loop ID  

		 Octet 2 bit 7 - not used
			 bit 6 - future use
			 bit 5 - future use
			 bit 4 - future use
			 bit 3 - 2^3        
			 bit 2 - 2^2       
			 bit 1 - 2^1
			 bit 0 - 2^0  Interval 

		 Octet 3 bit 7 - not used
			 bit 6 - future use
			 bit 5 - future use
			 bit 4 - future use
			 bit 3 - future use
			 bit 2 - 2^9   
			 bit 1 - 2^8
			 bit 0 - 2^7

		 Octet 4 bit 7 - not used
			 bit 6 - 2^6
			 bit 5 - 2^5 
			 bit 4 - 2^4 
			 bit 3 - 2^3 
			 bit 2 - 2^2 
			 bit 1 - 2^1
			 bit 0 - 2^0  Errored Seconds

		 Octet 5 bit 7 - not used
			 bit 6 - future use
			 bit 5 - future use
			 bit 4 - future use
			 bit 3 - future use
			 bit 2 - 2^9   
			 bit 1 - 2^8
			 bit 0 - 2^7

		 Octet 6 bit 7 - not used
			 bit 6 - 2^6
			 bit 5 - 2^5 
			 bit 4 - 2^4 
			 bit 3 - 2^3 
			 bit 2 - 2^2 
			 bit 1 - 2^1
			 bit 0 - 2^0  Severely Errored Seconds

		 Octet 7 bit 7 - not used
			 bit 6 - future use
			 bit 5 - future use
			 bit 4 - future use
			 bit 3 - future use
			 bit 2 - 2^9   
			 bit 1 - 2^8
			 bit 0 - 2^7

		 Octet 8 bit 7 - not used
			 bit 6 - 2^6
			 bit 5 - 2^5 
			 bit 4 - 2^4 
			 bit 3 - 2^3 
			 bit 2 - 2^2 
			 bit 1 - 2^1
			 bit 0 - 2^0   Unavailable Seconds

		 Octet 9 bit 7 - not used
			 bit 6 - future use
			 bit 5 - future use 
			 bit 4 - future use 
			 bit 3 - future use 
			 bit 2 - 2^16
			 bit 1 - 2^15
			 bit 0 - 2^14  

		Octet 10 bit 7 - not used
			 bit 6 - 2^13
			 bit 5 - 2^12
			 bit 4 - 2^11
			 bit 3 - 2^10
			 bit 2 - 2^9 
			 bit 1 - 2^8
			 bit 0 - 2^7   

		Octet 11 bit 7 - not used
			 bit 6 - 2^6
			 bit 5 - 2^5 
			 bit 4 - 2^4 
			 bit 3 - 2^3 
			 bit 2 - 2^2 
			 bit 1 - 2^1
			 bit 0 - 2^0   	FEBE (Far End Block Error Count)

	 Valid [i]nterface = 01-06"
    ::= {uas7626IntervalEntry 3 }

--
-- ********************************************************************
-- ATT Total Performance Table
-- ********************************************************************

uas7626TotalTable OBJECT-TYPE
    SYNTAX  SEQUENCE OF Uas7626TotalEntry
    ACCESS  not-accessible
    STATUS  mandatory
    DESCRIPTION
	"The uas7626 Total Table contains the totals of the various 
	 statistics collected for the current 24 hour period
	 for each interface."
    ::= { uas7626Performance 5 }

uas7626TotalEntry OBJECT-TYPE
    SYNTAX  Uas7626TotalEntry
    ACCESS  not-accessible
    STATUS  mandatory
    DESCRIPTION
	    "An entry in the uas7626 Total table."
    INDEX   { uas7626TotalIndex }
    ::= { uas7626TotalTable 1 }

Uas7626TotalEntry ::=
    SEQUENCE {
	uas7626TotalIndex	SCinstance,
	uas7626TotalStat	OCTET STRING
    }

uas7626TotalIndex OBJECT-TYPE
    SYNTAX  SCinstance
    ACCESS  read-only
    STATUS  mandatory
    DESCRIPTION
        "Integer value which uniquely identifies the UAS7626 to which this
         entry is applicable. SCinstance is defined to be SLDi where:
         S (byte value) - physical shelf slot location (01-32)
         L (byte value) - line number (01)
         D (byte value) - drop number (00)
         i (byte value) - loop or interface number (00-06)"
    ::= { uas7626TotalEntry 1 }

uas7626TotalStat OBJECT-TYPE
    SYNTAX  OCTET STRING (SIZE(14))
    ACCESS  read-only
    STATUS  mandatory
    DESCRIPTION
	"Returns a bitwise snapshot of the current 24 hour statistics.

		 Octet 1 bit 7 - not used
			 bit 6 - future use
			 bit 5 - future use
			 bit 4 - 2^4
			 bit 3 - 2^3
			 bit 2 - 2^2
			 bit 1 - 2^1
			 bit 0 - 2^0  Loop ID  

		 Octet 2 bit 7 - not used
			 bit 6 - future use
			 bit 5 - future use
			 bit 4 - future use
			 bit 3 - future use
			 bit 2 - >65535
			 bit 1 - 2^15
			 bit 0 - 2^14

		 Octet 3 bit 7 - not used
			 bit 6 - 2^13
			 bit 5 - 2^12
			 bit 4 - 2^11
			 bit 3 - 2^10
			 bit 2 - 2^9
			 bit 1 - 2^8
			 bit 0 - 2^7

		 Octet 4 bit 7 - not used
			 bit 6 - 2^6 
			 bit 5 - 2^5 
			 bit 4 - 2^4 
			 bit 3 - 2^3 
			 bit 2 - 2^2 
			 bit 1 - 2^1 
			 bit 0 - 2^0    Errored  Seconds

		 Octet 5 bit 7 - not used
			 bit 6 - future use
			 bit 5 - future use
			 bit 4 - future use
			 bit 3 - future use
			 bit 2 - >65535
			 bit 1 - 2^15
			 bit 0 - 2^14

		 Octet 6 bit 7 - not used
			 bit 6 - 2^13
			 bit 5 - 2^12
			 bit 4 - 2^11
			 bit 3 - 2^10
			 bit 2 - 2^9
			 bit 1 - 2^8
			 bit 0 - 2^7

		 Octet 7 bit 7 - not used
			 bit 6 - 2^6 
			 bit 5 - 2^5 
			 bit 4 - 2^4 
			 bit 3 - 2^3 
			 bit 2 - 2^2 
			 bit 1 - 2^1 
			 bit 0 - 2^0    Severely Errored Seconds

		 Octet 8 bit 7 - not used
			 bit 6 - future use
			 bit 5 - future use
			 bit 4 - future use
			 bit 3 - future use
			 bit 2 - >65535
			 bit 1 - 2^15
			 bit 0 - 2^14

		 Octet 9 bit 7 - not used
			 bit 6 - 2^13
			 bit 5 - 2^12
			 bit 4 - 2^11
			 bit 3 - 2^10
			 bit 2 - 2^9
			 bit 1 - 2^8
			 bit 0 - 2^7

        	Octet 10 bit 7 - not used
			 bit 6 - 2^6 
			 bit 5 - 2^5 
			 bit 4 - 2^4 
			 bit 3 - 2^3 
			 bit 2 - 2^2 
			 bit 1 - 2^1 
			 bit 0 - 2^0    Unavailable Seconds

		Octet 11 bit 7 - not used
			 bit 6 - future use
			 bit 5 - future use
			 bit 4 - future use
			 bit 3 - future use
			 bit 2 - 2^23
			 bit 1 - 2^22
			 bit 0 - 2^21  

		Octet 12 bit 7 - not used
			 bit 6 - 2^20
			 bit 5 - 2^19
			 bit 4 - 2^18
			 bit 3 - 2^17
			 bit 2 - 2^16
			 bit 1 - 2^15
			 bit 0 - 2^14   

		Octet 13 bit 7 - not used
			 bit 6 - 2^13
			 bit 5 - 2^12
			 bit 4 - 2^11
			 bit 3 - 2^10
			 bit 2 - 2^9 
			 bit 1 - 2^8
			 bit 0 - 2^7   

		Octet 14 bit 7 - not used
			 bit 6 - 2^6
			 bit 5 - 2^5 
			 bit 4 - 2^4 
			 bit 3 - 2^3 
			 bit 2 - 2^2 
			 bit 1 - 2^1
			 bit 0 - 2^0    FEBE (Far End Block Error Count)

	 Valid [i]nterface = 01-06"
    ::= {uas7626TotalEntry 2 }

--
-- ********************************************************************
--  GDC 7626 Recent 24 Hour Performance Table
-- ********************************************************************

uas7626Recent24HrTable OBJECT-TYPE
    SYNTAX  SEQUENCE OF Uas7626Recent24HrEntry
    ACCESS  not-accessible
    STATUS  mandatory
    DESCRIPTION
	"The Recent 24 Hour table contains the totals of the various 
	 statistics collected for the previous 24 hour period
	 for each interface."
 ::= { uas7626Performance 6 }

uas7626Recent24HrEntry OBJECT-TYPE
    SYNTAX  Uas7626Recent24HrEntry
    ACCESS  not-accessible
    STATUS  mandatory
    DESCRIPTION
	    "An entry in the Recent24Hr table."
    INDEX   { uas7626Recent24HrIndex }
    ::= { uas7626Recent24HrTable 1 }

Uas7626Recent24HrEntry ::=
    SEQUENCE {
	uas7626Recent24HrIndex	SCinstance,
	uas7626Recent24HrStat	OCTET STRING
    }

uas7626Recent24HrIndex OBJECT-TYPE
    SYNTAX  SCinstance
    ACCESS  read-only
    STATUS  mandatory
    DESCRIPTION
        "Integer value which uniquely identifies the UAS7626 to which this
         entry is applicable. SCinstance is defined to be SLDi where:
         S (byte value) - physical shelf slot location (01-32)
         L (byte value) - line number (01)
         D (byte value) - drop number (00)
         i (byte value) - loop or interface number (00-06)"
    ::= { uas7626Recent24HrEntry 1 }

uas7626Recent24HrStat OBJECT-TYPE
    SYNTAX  OCTET STRING (SIZE (14))
    ACCESS  read-only
    STATUS  mandatory
    DESCRIPTION
	"Returns a bitwise snapshot of the recent 24 hour statistics.

		 Octet 1 bit 7 - not used
			 bit 6 - future use
			 bit 5 - future use
			 bit 4 - 2^4
			 bit 3 - 2^3
			 bit 2 - 2^2
			 bit 1 - 2^1
			 bit 0 - 2^0  Loop ID  

		 Octet 2 bit 7 - not used
			 bit 6 - future use
			 bit 5 - future use
			 bit 4 - future use
			 bit 3 - future use
			 bit 2 - >65535
			 bit 1 - 2^15
			 bit 0 - 2^14

		 Octet 3 bit 7 - not used
			 bit 6 - 2^13
			 bit 5 - 2^12
			 bit 4 - 2^11
			 bit 3 - 2^10
			 bit 2 - 2^9
			 bit 1 - 2^8
			 bit 0 - 2^7

		 Octet 4 bit 7 - not used
			 bit 6 - 2^6 
			 bit 5 - 2^5 
			 bit 4 - 2^4 
			 bit 3 - 2^3 
			 bit 2 - 2^2 
			 bit 1 - 2^1 
			 bit 0 - 2^0    Errored  Seconds

		 Octet 5 bit 7 - not used
			 bit 6 - future use
			 bit 5 - future use
			 bit 4 - future use
			 bit 3 - future use
			 bit 2 - >65535
			 bit 1 - 2^15
			 bit 0 - 2^14

		 Octet 6 bit 7 - not used
			 bit 6 - 2^13
			 bit 5 - 2^12
			 bit 4 - 2^11
			 bit 3 - 2^10
			 bit 2 - 2^9
			 bit 1 - 2^8
			 bit 0 - 2^7

		 Octet 7 bit 7 - not used
			 bit 6 - 2^6 
			 bit 5 - 2^5 
			 bit 4 - 2^4 
			 bit 3 - 2^3 
			 bit 2 - 2^2 
			 bit 1 - 2^1 
			 bit 0 - 2^0    Severely Errored Seconds

		 Octet 8 bit 7 - not used
			 bit 6 - future use
			 bit 5 - future use
			 bit 4 - future use
			 bit 3 - future use
			 bit 2 - >65535
			 bit 1 - 2^15
			 bit 0 - 2^14

		 Octet 9 bit 7 - not used
			 bit 6 - 2^13
			 bit 5 - 2^12
			 bit 4 - 2^11
			 bit 3 - 2^10
			 bit 2 - 2^9
			 bit 1 - 2^8
			 bit 0 - 2^7

        	Octet 10 bit 7 - not used
			 bit 6 - 2^6 
			 bit 5 - 2^5 
			 bit 4 - 2^4 
			 bit 3 - 2^3 
			 bit 2 - 2^2 
			 bit 1 - 2^1 
			 bit 0 - 2^0    Unavailable Seconds

		Octet 11 bit 7 - not used
			 bit 6 - future use
			 bit 5 - future use
			 bit 4 - future use
			 bit 3 - future use
			 bit 2 - 2^23
			 bit 1 - 2^22
			 bit 0 - 2^21  

		Octet 12 bit 7 - not used
			 bit 6 - 2^20
			 bit 5 - 2^19
			 bit 4 - 2^18
			 bit 3 - 2^17
			 bit 2 - 2^16
			 bit 1 - 2^15
			 bit 0 - 2^14   

		Octet 13 bit 7 - not used
			 bit 6 - 2^13
			 bit 5 - 2^12
			 bit 4 - 2^11
			 bit 3 - 2^10
			 bit 2 - 2^9 
			 bit 1 - 2^8
			 bit 0 - 2^7   

		Octet 14 bit 7 - not used
			 bit 6 - 2^6
			 bit 5 - 2^5 
			 bit 4 - 2^4 
			 bit 3 - 2^3 
			 bit 2 - 2^2 
			 bit 1 - 2^1
			 bit 0 - 2^0    FEBE (Far End Block Error Count)

	 Valid [i]nterface = 01-06"
    ::= {uas7626Recent24HrEntry 2 }

--
-- ********************************************************************
--  GDC 7626 Unavailable Time Registers Table
-- ********************************************************************

uas7626UnavailableTimeRegTable OBJECT-TYPE
    SYNTAX SEQUENCE OF Uas7626UnavailableTimeRegEntry
    ACCESS not-accessible
    STATUS mandatory
    DESCRIPTION
	"The 7626 Unavailable Time Register table."
    ::= { uas7626Performance 7 }

uas7626UnavailableTimeRegEntry OBJECT-TYPE
    SYNTAX Uas7626UnavailableTimeRegEntry
    ACCESS not-accessible
    STATUS mandatory
    DESCRIPTION
	"An entry in the Unavailable Time Register table."
    INDEX {uas7626UnavailableTimeRegIndex,uas7626UnavailableTimeRegNumber}
    ::= { uas7626UnavailableTimeRegTable 1 }

Uas7626UnavailableTimeRegEntry ::=
    SEQUENCE {
	 uas7626UnavailableTimeRegIndex	    SCinstance,
	 uas7626UnavailableTimeRegNumber    INTEGER,
	 uas7626UnavailableTimeRegStart	    INTEGER,
	 uas7626UnavailableTimeRegStop	    INTEGER
    }

uas7626UnavailableTimeRegIndex OBJECT-TYPE
    SYNTAX SCinstance
    ACCESS read-only
    STATUS mandatory
    DESCRIPTION
        "Integer value which uniquely identifies the UAS7626 to which this
         entry is applicable. SCinstance is defined to be SLDi where:
         S (byte value) - physical shelf slot location (01-32)
         L (byte value) - line number (01)
         D (byte value) - drop number (00)
         i (byte value) - loop or interface number (00-06)"
    ::= { uas7626UnavailableTimeRegEntry 1 }

uas7626UnavailableTimeRegNumber OBJECT-TYPE
    SYNTAX INTEGER (1..6)
    ACCESS read-only
    STATUS mandatory
    DESCRIPTION
	"A number between 1 and 6, where the number is the number of the
	 Unavailable Time Register."
    ::= { uas7626UnavailableTimeRegEntry 2 }

uas7626UnavailableTimeRegStart OBJECT-TYPE
    SYNTAX INTEGER (1..2147483647)
    ACCESS read-only
    STATUS mandatory
    DESCRIPTION
        "Start time of one of the Unavailable Time Registers."
    ::= { uas7626UnavailableTimeRegEntry 3 }

uas7626UnavailableTimeRegStop OBJECT-TYPE
    SYNTAX INTEGER (1..2147483647)
    ACCESS read-only
    STATUS mandatory
    DESCRIPTION
	"Stop time of one of the Unavailable Time Registers."
    ::= { uas7626UnavailableTimeRegEntry 4 }


-- ****************************************************************************
--                       mib definitions end
-- ****************************************************************************
END
