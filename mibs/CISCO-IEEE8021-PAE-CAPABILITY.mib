-- *****************************************************************
-- CISCO-IEEE8021-PAE-CAPABILITY.my:
-- Cisco IEEE8021-PAE-MIB AGENT-CAPABILITIES
--
-- September 2003, Binh Le
--
-- Copyright (c) 2003-2004 by Cisco Systems, Inc.
-- All rights reserved.
-- *****************************************************************

CISCO-IEEE8021-PAE-CAPABILITY DEFINITIONS ::= BEGIN

IMPORTS
        MODULE-IDENTITY
                FROM SNMPv2-SMI
        AGENT-CAPABILITIES
                FROM SNMPv2-CONF
        TruthValue 
                FROM SNMPv2-TC
        ciscoAgentCapability
                FROM CISCO-SMI;

ciscoIeee8021PaeCapability MODULE-IDENTITY
        LAST-UPDATED    "200401130000Z"
        ORGANIZATION    "Cisco Systems, Inc."
        CONTACT-INFO
                "       Cisco Systems
                        Customer Service

                Postal: 170 West Tasman Drive
                        San Jose, CA  95134
                        USA

                   Tel: +1 800 553-NETS

                E-mail: cs-lan-switch-snmp@cisco.com"
        DESCRIPTION
                "The capabilities description of IEEE8021-PAE-MIB."

        REVISION        "200401130000Z"
        DESCRIPTION
                "Added capability statement
                 ciscoIeee8021PaeCapCatOSV08R0301."

        REVISION        "200309160000Z"
        DESCRIPTION
                "Initial version of this MIB module."
        ::= { ciscoAgentCapability 314 }

cIeee8021PaeCapV12R0111bEXCat6K AGENT-CAPABILITIES
    PRODUCT-RELEASE      "Cisco IOS 12.1(11b)EX on Catalyst 6000/6500
                          and Cisco 7600 series devices."
    STATUS               current
    DESCRIPTION          "IEEE8021-PAE-MIB capabilities."

    SUPPORTS             IEEE8021-PAE-MIB
        INCLUDES         { dot1xPaeSystemGroup, dot1xPaeAuthConfigGroup,
                           dot1xPaeAuthStatsGroup }

        VARIATION        dot1xAuthAdminControlledDirections
            SYNTAX       INTEGER { both(0) }
            DESCRIPTION  "Only support both(0)."

        VARIATION        dot1xAuthOperControlledDirections
            SYNTAX       INTEGER { both(0) }
            DESCRIPTION  "Only support both(0)."

        VARIATION        dot1xPaePortCapabilities
            SYNTAX       BITS { dot1xPaePortAuthCapable(0) }
            DESCRIPTION  "Only support dot1xPaePortAuthCapable(0)."

        VARIATION        dot1xAuthKeyTxEnabled
            SYNTAX       TruthValue { false(2) }
            DESCRIPTION  "Only support false(2)."

    ::= { ciscoIeee8021PaeCapability 1 }

ciscoIeee8021PaeCapCatOSV07R0101 AGENT-CAPABILITIES
    PRODUCT-RELEASE      "Cisco CatOS 7.1(1)."
    STATUS               current
    DESCRIPTION          "IEEE8021-PAE-MIB capabilities."

    SUPPORTS             IEEE8021-PAE-MIB
        INCLUDES         { dot1xPaeSystemGroup, dot1xPaeAuthConfigGroup,
                           dot1xPaeAuthStatsGroup }

        VARIATION        dot1xAuthAdminControlledDirections
            SYNTAX       INTEGER { both(0) }
            DESCRIPTION  "Only support both(0)."

        VARIATION        dot1xAuthOperControlledDirections
            SYNTAX       INTEGER { both(0) }
            DESCRIPTION  "Only support both(0)."

        VARIATION        dot1xPaePortCapabilities
            SYNTAX       BITS { dot1xPaePortAuthCapable(0) }
            DESCRIPTION  "Only support dot1xPaePortAuthCapable(0)."

        VARIATION        dot1xAuthKeyTxEnabled
            SYNTAX       TruthValue { false(2) }
            DESCRIPTION  "Only support false(2)."

    ::= { ciscoIeee8021PaeCapability 2 }

ciscoIeee8021PaeCapCatOSV08R0301 AGENT-CAPABILITIES
    PRODUCT-RELEASE      "Cisco CatOS 8.3(1) on Catalyst 6000/6500
                          and Cisco 7600 series devices."
    STATUS               current
    DESCRIPTION          "IEEE8021-PAE-MIB capabilities."

    SUPPORTS             IEEE8021-PAE-MIB
        INCLUDES         { dot1xPaeSystemGroup, dot1xPaeAuthConfigGroup,
                           dot1xPaeAuthStatsGroup }

        VARIATION        dot1xPaePortCapabilities
            SYNTAX       BITS { dot1xPaePortAuthCapable(0) }
            DESCRIPTION  "Only support dot1xPaePortAuthCapable(0)."

        VARIATION        dot1xAuthKeyTxEnabled
            SYNTAX       TruthValue { false(2) }
            DESCRIPTION  "Only support false(2)."

    ::= { ciscoIeee8021PaeCapability 3 }

END
