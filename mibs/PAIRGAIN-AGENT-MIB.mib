-- File: pgagtmib.txt

-- Common MIB Release 1.1
-- Revision 05/21/97

-- Copyright 1994 PairGain Technologies, Inc.  All Rights
-- Reserved.  Reproduction of this document is authorized on
-- condition that the foregoing copyright notice is included.
-- This PairGain SNMP Management Information Base Specification
-- (Specification) embodies PairGain's confidential and
-- proprietary intellectual property.  PairGain retains all
-- title and ownership in the Specification, including any
-- revisions.
--
-- It is PairGain’s intent to encourage the widespread use of
-- this Specification in connection with the management of
-- PairGain products. PairGain grants vendors, end-users,
-- and other interested parties a non-exclusive license to
-- use this Specification in connection with the management
-- of PairGain products.
--
-- This Specification is supplied "AS IS," and PairGain makes
-- no warranty, either expressed or implied, as to the use,
-- operation, condition, or performance of the Specification.


PAIRGAIN-AGENT-MIB DEFINITIONS ::= BEGIN


-- Imports

IMPORTS
	IpAddress			FROM RFC1155-SMI
	OBJECT-TYPE			FROM RFC-1212
	pgainAgent			FROM PAIRGAIN-COMMON-HD-MIB;
	DisplayString ::= OCTET STRING

pgAgentSw			OBJECT IDENTIFIER ::=	{ pgainAgent 1 }
pgAgentNetProtocol		OBJECT IDENTIFIER ::=	{ pgainAgent 2 }
pgSnmpAgent			OBJECT IDENTIFIER ::=	{ pgainAgent 3 }
pgAgentHw			OBJECT IDENTIFIER ::=	{ pgainAgent 4 }
pgAgentLocImage			OBJECT IDENTIFIER ::=	{ pgainAgent 5 }


-- Agent Software Group
-- Implementation of this group is mandatory for all PairGain agents

pgAgentType OBJECT-TYPE
	SYNTAX	INTEGER {
		other(1),		-- none of the following
		pgCMU(2),		-- Campus Management Unit
		pgHMU(3),		-- HiGain Managemet Unit
		pgEMU(4),		-- HiGain Int'l Management Unit
                pgDMU(5),               -- DSLAM Management Unit
                pgMBMTiger(6)           -- Megabit Modem Tiger
	}
	ACCESS	read-only
	STATUS	mandatory
	DESCRIPTION
		"The agent's Unit type."
	::= {pgAgentSw  1 }

pgAgentFwVer OBJECT-TYPE
	SYNTAX	INTEGER
	ACCESS	read-only
	STATUS	mandatory
	DESCRIPTION
		"The agent's Unit major firmware version number
		0=Rev. A, 1=Rev. B, etc."
	::= { pgAgentSw 2 }

pgAgentSwVer OBJECT-TYPE
        SYNTAX  DisplayString
	ACCESS	read-only
	STATUS	mandatory
	DESCRIPTION
		"The agent's’  software version number in string format:
                1.1 = major swftware version number 1, minor version 2.

                For pgAgentType = pgDMU, the format is XX.YY.ZZ where

                XX  represents the software feature release:
                    10-20  MuxWare
                    30-40  SwitchWare
                    50-60  Interware
                YY  is incremented to indicate major changes that may
                    affect backward compatibility.
                ZZ  is incremented to represent minor changes to the
                    system.

                When a string of zero length is returned, it means either
                the version.txt file is missing or the string format in the
                file is incorrect."
	::= { pgAgentSw 3 }

pgAgentBootProtocol OBJECT-TYPE
	SYNTAX	INTEGER {
		other(1),		-- boot protocol not listed here
		bootp-tftp(2),
		tftp-only(3),
		ftp-only(4),
		proprietary(5)	-- supported proprietary boot protocol
	}
	ACCESS	read-only
	STATUS	mandatory
	DESCRIPTION
		"Boot protocol used to load the Unit with its image software."
	::= {pgAgentSw 4 }

pgAgentBootFile OBJECT-TYPE
	SYNTAX	DisplayString (SIZE(0..64))
	ACCESS	read-write
	STATUS	mandatory
	DESCRIPTION
		"The name of the boot file that is sent to the file server
		during boot time. The actual boot protocol used to retrieve the
		file is determined by pgAgentBootProtocol."
	::= { pgAgentSw 5 }

pgAgentAuthTraps OBJECT-TYPE
	SYNTAX	INTEGER {
		disable(2),		-- disable authentication traps
		enable(1)		-- enable authentication traps
	}
	ACCESS	read-write
	STATUS	mandatory
	DESCRIPTION
		"Enable or disable the use of authentication error trap
		generation."
	::= { pgAgentSw 6 }

pgAgentTraps OBJECT-TYPE
	SYNTAX	INTEGER {
		disable(2),		-- disable all  traps
		enable(1)		-- enable all traps
	}
	ACCESS	read-write
	STATUS	mandatory
	DESCRIPTION
		"Enable or disable the use of all trap generation."
	::= { pgAgentSw 7 }

pgAgentMibLevel OBJECT-TYPE
	SYNTAX	INTEGER
	ACCESS	read-only
	STATUS	mandatory
	DESCRIPTION
		"Used to determine current MIB release supported by agent.  The
		encoding of this object is of the following form: xyy, where x
		is the major version number and yy is the minor version number.
		Thus, version 3.0 would be represented as 300,  version 3.01
		would be 301 and 3.1 would be 310.  Object is in decimal."
	::= { pgAgentSw 8 }

pgAgentMySlotId OBJECT-TYPE
	SYNTAX	INTEGER
	ACCESS	read-only
	STATUS	mandatory
	DESCRIPTION
		"Slot where this agent currently resides.  If hardware is
		unable to determine then a 0 should be returned.  This object
		is useful if multiple management units are installed in
		different slots of a PairGain chassis."
	::= { pgAgentSw 9 }


-- Agent Network Protocol Group
-- Implementation of this group is mandatory for all PairGain agents.

pgAgentIpAddr OBJECT-TYPE
	SYNTAX	IpAddress
	ACCESS	read-write
	STATUS	mandatory
	DESCRIPTION
		"The network management unit's administrative IP address.
		The current operational IP address can be obtained by the
		ipAdEntAddr entry in the ipAddrTable."
	::= { pgAgentNetProtocol 1 }

pgAgentNetMask OBJECT-TYPE
	SYNTAX	IpAddress
	ACCESS	read-write
	STATUS	mandatory
	DESCRIPTION
		"The network management unit’s administrative subnet mask.
		The current operational subnet mask can be obtained by the
		ipAdEntNetMask entry in the ipAddrTable."
	::= { pgAgentNetProtocol 2 }

pgAgentDefaultGateway OBJECT-TYPE
	SYNTAX	IpAddress
	ACCESS	read-write
	STATUS	mandatory
	DESCRIPTION
		"The network management unit’s administrative default
		gateway IP address.  The current operational default gateway's
		IP address can be obtained from the ipRoutingTable."
	::= { pgAgentNetProtocol 3 }

pgAgentBootServerAddr OBJECT-TYPE
	SYNTAX	IpAddress
	ACCESS	read-write
	STATUS	mandatory
	DESCRIPTION
		"The IP address to which the requests for boot files are sent.
		The protocol used to retrieve the boot files is determined by
		object pgAgentBootProtocol."
	::= { pgAgentNetProtocol 4 }

--
-- PairGain Agent Trap Receiver Table
-- Implementation of this group is mandatory for all PairGain agents

pgAgentTrapReceiverTable OBJECT-TYPE
	SYNTAX	SEQUENCE OF PgAgentTrapReceiverEntry
	ACCESS	not-accessible
	STATUS	optional
	DESCRIPTION
		"Table containing list of NMS's that are to receive traps
		generated by this agent."
	::= { pgSnmpAgent 1 }

pgAgentTrapReceiverEntry OBJECT-TYPE
	SYNTAX	PgAgentTrapReceiverEntry
	ACCESS	not-accessible
	STATUS	optional
	DESCRIPTION
		"A destination address and community string to a particular
		trap server, along with a trap filter and entry aging
		capability."
	INDEX	{ pgAgentTrapRcvrNetAddress }
	::= { pgAgentTrapReceiverTable 1 }

PgAgentTrapReceiverEntry ::= SEQUENCE {
	pgAgentTrapRcvrStatus
		INTEGER,
	pgAgentTrapRcvrNetAddress
		IpAddress,
	pgAgentTrapRcvrComm
		DisplayString
}

pgAgentTrapRcvrStatus OBJECT-TYPE
	SYNTAX	INTEGER {
		other (1),		-- none of the following
		valid (2),		-- a valid address
		invalid (3)		-- an invalid address
	}
	ACCESS	read-write
	STATUS	optional
	DESCRIPTION
		"Setting this object to the value invalid(3) has the effect
		of invalidating the corresponding entry in the
		pgAgentTrapReceiverTable. That is, it effectively disassociates
 		the address identified with the entry by removing the entry
		from the table. On a read the value of valid(2) should be
		returned if the entry contains a valid record, or invalid(3)
		should be returned if the entry contains an invalid record."
	::= { pgAgentTrapReceiverEntry 1 }

pgAgentTrapRcvrNetAddress OBJECT-TYPE
	SYNTAX  IpAddress
	ACCESS	read-write
	STATUS	optional
	DESCRIPTION
		"IP address for trap server that is to receive the trap."
	::= { pgAgentTrapReceiverEntry  2 }

pgAgentTrapRcvrComm OBJECT-TYPE
	SYNTAX	DisplayString (SIZE(0..20))
	ACCESS	read-write
	STATUS	optional
	DESCRIPTION
		"Community string used for traps sent to this trap receiver."
	::= { pgAgentTrapReceiverEntry  3 }


-- PairGain Agent Hardware Group
-- Implementation of this group is mandatory for all PairGain agents.

pgAgentReset OBJECT-TYPE
	SYNTAX	INTEGER {
		noReset(1),	-- not resetting
		reset(2)		-- reset
	}
	ACCESS	read-write
	STATUS	mandatory
	DESCRIPTION
		"Network management unit reset status.  Writing a reset(2)
		to this object will reset the agent and perform a download and
		restart."
	::= { pgAgentHw 1 }

pgAgentRestart OBJECT-TYPE
	SYNTAX	INTEGER {
		noRestart(1),	-- not restarting
		restart(2)		-- restart
	}
	ACCESS	read-write
	STATUS	optional
	DESCRIPTION
		"Network management unit restart status.  Writing a
		restart(2) to this object will restart the agent.  This
		initializes all the counters, re-reads the NVRAM data
		structure and starts executing from the beginning of the code."
	::= { pgAgentHw 2 }

pgAgentBootMode OBJECT-TYPE
	SYNTAX	INTEGER {
		nvram(1),		-- get boot info from local nvram
		network(2)	-- or from a boot protocol
	}
	ACCESS	read-write
	STATUS	mandatory
	DESCRIPTION
		"The method for obtaining boot parameter information.
		This parameter will not take effect until written into NVRAM
		(pgAgentWriteNvram) and a reset (pgAgentReset) is issued."
	::= { pgAgentHw 3 }

pgAgentWriteNvram OBJECT-TYPE
	SYNTAX	INTEGER {
		noWriteNvram(1),		-- not writing NVRAM
		writeNvram(2)		-- write NVRAM
	}
	ACCESS	read-write
	STATUS	mandatory
	DESCRIPTION
		"Network management unit NVRAM write status.  Writing a
		(2) to this object will write the contents of current NVRAM
		data structure in the NVRAM."
	::= { pgAgentHw 4 }


-- PairGain Agent Local Image Group
-- This group is mandatory for agents with image code stored in local FLASH.

pgLocImageValid OBJECT-TYPE
	SYNTAX	INTEGER {
		other(1),			-- unknown status
		localImageValid(2),		-- local image is valid
		localImageInvalid(3)		-- local image is invalid
	}
	ACCESS	read-only
	STATUS	optional
	DESCRIPTION
		"This indicates whether the agent has a valid local code
		image on board. A FLASH checksum failure would cause the
		agent to return localImageInvalid(3)."
	::= { pgAgentLocImage 1 }

pgLocImageVersion OBJECT-TYPE
	SYNTAX  DisplayString(SIZE(6))
	ACCESS	read-only
	STATUS	optional
	DESCRIPTION
		"The major and minor software version number of the
		locally-stored image in string format.
  		This object applies only to agents with valid local image.
		Other agents should return zero."
	::= { pgAgentLocImage 2 }

pgLocImageLoadMode OBJECT-TYPE
	SYNTAX	INTEGER {
		other(1),			-- unknown status
		network(2),		-- use net, not local image
		localBoot(3),		-- boot from local image, not net
		localAsBackup(4)		-- try net, if fails use local
	}
	ACCESS	read-write
	STATUS	optional
	DESCRIPTION
		"This indicates whether the agent should get code from the
		network, use a local image, or try the network first and then
		fall back to local image if the network boot fails."
	::= { pgAgentLocImage 3 }

pgLocImageActualSource OBJECT-TYPE
	SYNTAX	INTEGER {
		other(1),			-- unknown status
		remoteImage(2),		-- downloaded code from network
		localImage(3)		-- loaded code from local FLASH
	}
	ACCESS	read-only
	STATUS	optional
	DESCRIPTION
		"This indicates whether the agent loaded code from the network
 		or used a local image.  When the the ImageLoadMode is
		localAsBackup, this variable indicates whether the network
		load was successful."
	::= { pgAgentLocImage 4 }

END
