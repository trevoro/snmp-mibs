NETFINITYSERVICES-MIB DEFINITIONS ::= BEGIN


 -- This group contains information about NetFinity Services.

IMPORTS
    OBJECT-TYPE	FROM RFC-1212
	enterprises FROM RFC1155-SMI;

DmiInteger              ::= INTEGER
DmiDisplaystring	::= OCTET STRING (SIZE (100))
DmiDate                 ::= OCTET STRING (SIZE (28))
DmiComponentIndex       ::= INTEGER

ibm			OBJECT IDENTIFIER ::= { enterprises 2 }
ibmProd                 OBJECT IDENTIFIER ::= { ibm 6 }
netFinity               OBJECT IDENTIFIER ::= { ibmProd 71 }
dmiMibs			OBJECT IDENTIFIER ::= { netFinity 200 }
netFinityServicesMIB    OBJECT IDENTIFIER ::= { dmiMibs 2 }
dmtfGroups3             OBJECT IDENTIFIER ::= { netFinityServicesMIB  1}

SComponentid ::= SEQUENCE {
        a1Manufacturer                                  DmiDisplaystring,
        a1Product                                       DmiDisplaystring,
        a1Version                                       DmiDisplaystring,
        a1SerialNumber                                  DmiDisplaystring
}

tComponentid3 OBJECT-TYPE
        SYNTAX          SEQUENCE OF SComponentid
        ACCESS          not-accessible
        STATUS          mandatory
        DESCRIPTION     "This group defines attributes common to all components.This
group is required."
        ::= {dmtfGroups3 1}

eComponentid3 OBJECT-TYPE
        SYNTAX          SComponentid
        ACCESS          not-accessible
        STATUS          mandatory
        DESCRIPTION     ""
        INDEX           {DmiComponentIndex}
        ::= {tComponentid3 1}

a1Manufacturer OBJECT-TYPE
        SYNTAX          DmiDisplaystring
        ACCESS          read-only
        STATUS          mandatory
        DESCRIPTION     "The name of the manufacturer that produces this component."
        ::= {eComponentid3 1}

a1Product OBJECT-TYPE
        SYNTAX          DmiDisplaystring
        ACCESS          read-only
        STATUS          mandatory
        DESCRIPTION     "The name of the component."
        ::= {eComponentid3 2}

a1Version OBJECT-TYPE
        SYNTAX          DmiDisplaystring
        ACCESS          read-only
        STATUS          mandatory
        DESCRIPTION     "The version for the component."
        ::= {eComponentid3 3}

a1SerialNumber OBJECT-TYPE
        SYNTAX          DmiDisplaystring
        ACCESS          read-only
        STATUS          mandatory
        DESCRIPTION     "The serial number for this instance of this component."
        ::= {eComponentid3 4}


SNetfinityAlert ::= SEQUENCE {
        a2AlertText                                     DmiDisplaystring,
        a2Severity                                      DmiInteger,
        a2AlertType                                     DmiDisplaystring,
        a2ApplicationId                                 DmiDisplaystring,
        a2ApplicationAlertType                          DmiInteger,
        a2AlertTimeAndDate                              DmiDate,
        a2AlertSender                                   DmiDisplaystring,
        a2AlertSystemName                               DmiDisplaystring
}

tNetfinityAlert OBJECT-TYPE
        SYNTAX          SEQUENCE OF SNetfinityAlert
        ACCESS          not-accessible
        STATUS          mandatory
        DESCRIPTION     "NetFinity Alert data fields."
        ::= {dmtfGroups3 2}

eNetfinityAlert OBJECT-TYPE
        SYNTAX          SNetfinityAlert
        ACCESS          not-accessible
        STATUS          mandatory
        DESCRIPTION     ""
        INDEX           {DmiComponentIndex}
        ::= {tNetfinityAlert 1}

a2AlertText OBJECT-TYPE
        SYNTAX          DmiDisplaystring
        ACCESS          read-only
        STATUS          mandatory
        DESCRIPTION     "Text associated with the NetFinity Alert."
        ::= {eNetfinityAlert 1}

a2Severity OBJECT-TYPE
        SYNTAX          DmiInteger
        ACCESS          read-only
        STATUS          mandatory
        DESCRIPTION     "Alert severity level (0 = highest, 7 = lowest)."
        ::= {eNetfinityAlert 2}

a2AlertType OBJECT-TYPE
        SYNTAX          DmiDisplaystring
        ACCESS          read-only
        STATUS          mandatory
        DESCRIPTION     "Standard alert ID and type."
        ::= {eNetfinityAlert 3}

a2ApplicationId OBJECT-TYPE
        SYNTAX          DmiDisplaystring
        ACCESS          read-only
        STATUS          mandatory
        DESCRIPTION     "Identity of the application which issued the alert."
        ::= {eNetfinityAlert 4}

a2ApplicationAlertType OBJECT-TYPE
        SYNTAX          DmiInteger
        ACCESS          read-only
        STATUS          mandatory
        DESCRIPTION     "Application-specific alert ID."
        ::= {eNetfinityAlert 5}

a2AlertTimeAndDate OBJECT-TYPE
        SYNTAX          DmiDate
        ACCESS          read-only
        STATUS          mandatory
        DESCRIPTION     "Time and date when alert was issued."
        ::= {eNetfinityAlert 6}

a2AlertSender OBJECT-TYPE
        SYNTAX          DmiDisplaystring
        ACCESS          read-only
        STATUS          mandatory
        DESCRIPTION     "Network path to system which created alert, if not local
system."
        ::= {eNetfinityAlert 7}

a2AlertSystemName OBJECT-TYPE
        SYNTAX          DmiDisplaystring
        ACCESS          read-only
        STATUS          mandatory
        DESCRIPTION     "System name of system which created alert."
        ::= {eNetfinityAlert 8}

SNetfinityMonitorAttributes ::= SEQUENCE {
        a3AttributeId                                   DmiInteger,
        a3AttributeName                                 DmiDisplaystring,
        a3CurrentValueInteger                           DmiInteger,
        a3CurrentValueThousandths                       DmiInteger,
        a3CurrentValueString                            DmiDisplaystring,
        a3ValueUnits                                    DmiDisplaystring
}

tNetfinityMonitorAttributes OBJECT-TYPE
        SYNTAX          SEQUENCE OF SNetfinityMonitorAttributes
        ACCESS          not-accessible
        STATUS          mandatory
        DESCRIPTION     "Current values of NetFinity Monitor Attributes."
        ::= {dmtfGroups3 3}

eNetfinityMonitorAttributes OBJECT-TYPE
        SYNTAX          SNetfinityMonitorAttributes
        ACCESS          not-accessible
        STATUS          mandatory
        DESCRIPTION     ""
        INDEX           {DmiComponentIndex, a3AttributeId}
        ::= {tNetfinityMonitorAttributes 1}

a3AttributeId OBJECT-TYPE
        SYNTAX          DmiInteger
        ACCESS          read-only
        STATUS          mandatory
        DESCRIPTION     "Unique ID for monitored attribute."
        ::= {eNetfinityMonitorAttributes 1}

a3AttributeName OBJECT-TYPE
        SYNTAX          DmiDisplaystring
        ACCESS          read-only
        STATUS          mandatory
        DESCRIPTION     "Textual name of the monitored attribute."
        ::= {eNetfinityMonitorAttributes 2}

a3CurrentValueInteger OBJECT-TYPE
        SYNTAX          DmiInteger
        ACCESS          read-only
        STATUS          mandatory
        DESCRIPTION     "Integral portion of current value of attribute."
        ::= {eNetfinityMonitorAttributes 3}

a3CurrentValueThousandths OBJECT-TYPE
        SYNTAX          DmiInteger
        ACCESS          read-only
        STATUS          mandatory
        DESCRIPTION     "Fraction portion of current value of attribute, in units
of 1/1000th"
        ::= {eNetfinityMonitorAttributes 4}

a3CurrentValueString OBJECT-TYPE
        SYNTAX          DmiDisplaystring
        ACCESS          read-only
        STATUS          mandatory
        DESCRIPTION     "Current value of attribute, as display string."
        ::= {eNetfinityMonitorAttributes 5}

a3ValueUnits OBJECT-TYPE
        SYNTAX          DmiDisplaystring
        ACCESS          read-only
        STATUS          mandatory
        DESCRIPTION     "Textual label for value units."
        ::= {eNetfinityMonitorAttributes 6}

A3NetfinityMonitorValues ::= SEQUENCE {
        a3CpuUsage                                      DmiInteger,
        a3DiskUsage					DmiInteger,
        a3DiskFree                            		DmiInteger,
        a3NumUsers					DmiInteger,
        a3PageFaults					DmiInteger,
        a3PhysMemUsed					DmiInteger
}

a3NetfinityValueGroup	OBJECT-TYPE
        SYNTAX          SEQUENCE OF A3NetfinityMonitorValues
        ACCESS          not-accessible
        STATUS          mandatory
        DESCRIPTION     "Current values of NetFinity Value Parms. Had to make this up b/c IBM
			had no such features in their MIBS"
        ::= { a3CurrentValueInteger 1 }

SNetfinityAttributeGroups ::= SEQUENCE {
        a4AttributeGroupId                              DmiInteger,
        a4AttributeId                                   DmiInteger,
        a4AttributeGroupName                            DmiDisplaystring,
        a4AttributeName                                 DmiDisplaystring,
        a4CurrentValueTextual                           DmiDisplaystring,
        a4CurrentValueIndex                             DmiInteger
}

tNetfinityAttributeGroups OBJECT-TYPE
        SYNTAX          SEQUENCE OF SNetfinityAttributeGroups
        ACCESS          not-accessible
        STATUS          mandatory
        DESCRIPTION     "Current values of NetFinity Attribute Groups."
        ::= {dmtfGroups3 4}

eNetfinityAttributeGroups OBJECT-TYPE
        SYNTAX          SNetfinityAttributeGroups
        ACCESS          not-accessible
        STATUS          mandatory
        DESCRIPTION     ""
        INDEX           {DmiComponentIndex, a4AttributeGroupId, a4AttributeId}
        ::= {tNetfinityAttributeGroups 1}

a4AttributeGroupId OBJECT-TYPE
        SYNTAX          DmiInteger
        ACCESS          read-only
        STATUS          mandatory
        DESCRIPTION     "Unique ID for attribute group."
        ::= {eNetfinityAttributeGroups 1}

a4AttributeId OBJECT-TYPE
        SYNTAX          DmiInteger
        ACCESS          read-only
        STATUS          mandatory
        DESCRIPTION     "Unique ID for attribute within attribute group."
        ::= {eNetfinityAttributeGroups 2}

a4AttributeGroupName OBJECT-TYPE
        SYNTAX          DmiDisplaystring
        ACCESS          read-only
        STATUS          mandatory
        DESCRIPTION     "Textual name of the attribute group."
        ::= {eNetfinityAttributeGroups 3}

a4AttributeName OBJECT-TYPE
        SYNTAX          DmiDisplaystring
        ACCESS          read-only
        STATUS          mandatory
        DESCRIPTION     "Textual name of the attribute within the attribute group."
        ::= {eNetfinityAttributeGroups 4}

a4CurrentValueTextual OBJECT-TYPE
        SYNTAX          DmiDisplaystring
        ACCESS          read-only
        STATUS          mandatory
        DESCRIPTION     "Current value of attribute, as text."
        ::= {eNetfinityAttributeGroups 5}

a4CurrentValueIndex OBJECT-TYPE
        SYNTAX          DmiInteger
        ACCESS          read-only
        STATUS          mandatory
        DESCRIPTION     "Index of current value of attribute. Index = -1 if attribute's
value is not indexed."
        ::= {eNetfinityAttributeGroups 6}

END
