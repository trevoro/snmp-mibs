-- extracted from draft-nelson-rfc2618bis-00.txt
-- at Tue Feb 15 06:24:48 2005

     RADIUS-AUTH-CLIENT-MIB-IPV6 DEFINITIONS ::= BEGIN

   IMPORTS
          MODULE-IDENTITY, OBJECT-TYPE, OBJECT-IDENTITY,
          mib-2 FROM SNMPv2-SMI
          InetAddressType, InetAddress, InetPortNumber
          FROM INET-ADDRESS-MIB
          MODULE-COMPLIANCE, OBJECT-GROUP  FROM SNMPv2-CONF
          radiusAuthServerEntry FROM RADIUS-AUTH-CLIENT-MIB;

   radiusAuthClientExtMIB MODULE-IDENTITY
          LAST-UPDATED "200502072051Z"  -- Mon Feb  7 20:51 GMT 2005
          ORGANIZATION "IETF RADIUS Extensions Working Group."
          CONTACT-INFO
                 " David B. Nelson
                   Enterasys Networks
                   50 Minutemann Road
                   Andover, MA 01810
                   US

                   Phone: +1 978 684 1000
                   EMail: dnelson@eterasys.com"
          DESCRIPTION
                "An extension to the MIB module for entities
                 implementing the client side of the Remote Access
                 Dialin User Service (RADIUS) authentication protocol,
                 using IPv6 addressing formats. Updates RFC 2618."
          REVISION "200502072051Z"  -- Mon Feb  7 20:51 GMT 2005
          DESCRIPTION "Initial version, published as RFC xxxx."

   -- RFC Editor: replace xxx with actual RFC number at the time of
   -- publication, and remove this note.

          ::= { mib-2 1 }

   -- RFC Editor: replace TBA with IANA assigned OID value, and
   -- remove this note.

   radiusAuthClientExtMIBNotifications  OBJECT IDENTIFIER
               ::= { radiusAuthClientExtMIB 0 }

   radiusAuthClientExtMIBObjects        OBJECT IDENTIFIER
               ::= { radiusAuthClientExtMIB 1 }

   radiusAuthClientExtMIBConformance    OBJECT IDENTIFIER
               ::= { radiusAuthClientExtMIB 2 }

   -- MIB objects

   radiusAuthServerExtTable OBJECT-TYPE
         SYNTAX      SEQUENCE OF RadiusAuthServerExtEntry
         MAX-ACCESS  not-accessible
         STATUS      current
         DESCRIPTION
              "The (conceptual) table listing the RADIUS
               authentication servers with which the client
               shares a secret."
         ::= { radiusAuthClientExtMIBObjects 1 }

   radiusAuthServerExtEntry OBJECT-TYPE
         SYNTAX     RadiusAuthServerExtEntry
         MAX-ACCESS not-accessible
         STATUS     current
         DESCRIPTION
               "An entry (conceptual row) representing a RADIUS
                authentication server with which the client shares
                a secret."
         AUGMENTS      { radiusAuthServerEntry }
         ::= { radiusAuthServerExtTable 1 }

   RadiusAuthServerExtEntry ::= SEQUENCE {
         radiusAuthServerInetAddressType      InetAddressType,
         radiusAuthServerInetAddress          InetAddress,
         radiusAuthClientServerInetPortNumber InetPortNumber
   }

   radiusAuthServerInetAddressType OBJECT-TYPE
         SYNTAX     InetAddressType
         MAX-ACCESS read-only
         STATUS     current
         DESCRIPTION
               "The type of address format used for the
                radiusAuthServerInetAddress object."
         ::= { radiusAuthServerExtEntry 1 }

   radiusAuthServerInetAddress OBJECT-TYPE
         SYNTAX     InetAddress
         MAX-ACCESS read-only
         STATUS     current
         DESCRIPTION
               "The IP address of the RADIUS authentication
                server referred to in this table entry, using
                the IPv6 adddess format."
         ::= { radiusAuthServerExtEntry 2 }

   radiusAuthClientServerInetPortNumber  OBJECT-TYPE
         SYNTAX InetPortNumber
         MAX-ACCESS read-only
         STATUS current
         DESCRIPTION
               "The UDP port the client is using to send requests
                to this server."
         ::= { radiusAuthServerExtEntry 3 }

   -- conformance information

   radiusAuthClientExtMIBCompliances OBJECT IDENTIFIER
         ::= { radiusAuthClientExtMIBConformance 1 }

   radiusAuthClientExtMIBGroups      OBJECT IDENTIFIER
         ::= { radiusAuthClientExtMIBConformance 2 }

   -- compliance statements

   radiusAuthClientExtMIBCompliance MODULE-COMPLIANCE
        STATUS  current
        DESCRIPTION
              "The compliance statement for authentication
               clients implementing the RADIUS Authentication
               Client IPv6 Extensions MIB."
        MODULE  -- this module
               MANDATORY-GROUPS { radiusAuthClientExtMIBGroup }

        ::= { radiusAuthClientExtMIBCompliances 1 }

   -- units of conformance

   radiusAuthClientExtMIBGroup OBJECT-GROUP
        OBJECTS { radiusAuthServerInetAddressType,
                  radiusAuthServerInetAddress,
                  radiusAuthClientServerInetPortNumber
               }
        STATUS  current
        DESCRIPTION
              "The collection of extended objects providing
               management of RADIUS Authentication Clients
               using IPv6 address format."
        ::= { radiusAuthClientExtMIBGroups 1 }

   END

-- 
--    Copyright (C) The Internet Society (2005).  This document is subject
--    to the rights, licenses and restrictions contained in BCP 78, and
--    except as set forth therein, the authors retain all their rights.
-- 
-- 
-- Acknowledgment
-- 
--    Funding for the RFC Editor function is currently provided by the
--    Internet Society.
