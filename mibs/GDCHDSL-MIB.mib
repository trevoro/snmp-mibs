-- Copyright 1994- 1998 General DataComm Inc., Inc. All Rights Reserved.
--
-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive license to use
-- this Specification in connection with the management of GDC's products.
--
-- This Specification is supplied "AS IS," and GDC makes no warranty,
-- either expressed or implied, as to the use operation, condition, or
-- performance of the Specification.

-- Revision History
-- Version   Date	Name		Description
-- 1.00A     14-Oct-94  E. Moreno-Leon  Initial Revision
-- 1.00B     30-Jan-95  M. Cyr          Reformatted entire mib.      
-- 1.00C     10-Feb-95  M. Cyr          Changes to Diagnostics and Status Tables
-- 1.00D     14-Feb-95  M. Cyr          Added Linecoding to E1 Config Table
--                                      Added TxClkSource to DTE Config Table
-- 1.00E     31-Mar-95  E. Moreno-Leon  Swap values in DTECTS
-- 1.00F     04-Apr-95  E. Moreno-Leon  Introduce new object gdcHdslLedStatus
-- 1.00G     10-Apr-95  R. Strempel	Changed diagnostics
-- 1.00H     03-May-95  E. Moreno-Leon  Change name of 720 mibs from D to G.
-- 1.00J     15-Jun-95  E. Moreno-Leon  Added multipoint support.
-- 1.00K     22-Jun-95  E. Moreno-Leon  Added 702g2 product
-- 1.00L     01-Sep-95  C. Amorossi	Added Interface Comments
-- 1.00M     27-Sep-95  E. Moreno-Leon  Added gdcHdslAlarmStatus
--					Added V.54 commands and change slots to 18
-- 1.00N    29-Jan-96   S.Sankaran   	Added changes for 710D2 product.
--                                   	Added new table for statistics (octet string).
-- 1.00P    14-Mar-96   E. Moreno-Leon  Added  710D2RP, 720G2RP and 730D2RP product.
--					
-- 1.00Q    02-Apr-96   C. Amorossi     Changed enums for gdcHdslResetMajorAlarm and
--                                      gdcHdslResetMinorAlarm
-- 1.00R    17-May-96   S.Sankaran   	Added changes for T1 products
-- 	    05-Sep-96   D.Baylis        Deleted ANSI performance reporting				
-- 	    06-Oct-96   D.Baylis        Changed gdcHdslT1FDLMode to read only		
-- 1.00S    27-Jan-98   C. Amorossi     Added gdcHdslDownloadtable, hdsl700AG2 and
--					hdsl700AG2NZ
-- 1.00T    11-Feb-98   C. Amorossi     Increase range of gdcHdslDteDataRate to
--					include 0
-- 1.00U    04-May-98   C. Amorossi     Added gdcHdslEraseFlash
--
-- 1.00V    03-Jun-98   M. Cyr          Added LL,ST&RL to gdcHdslLedStatus1
--                                     
-- 1.00W    30-Jul-98   P. Jin  Added   7722 product.
--					
-- 2.00A    25-Aug-98   C. Amorossi     Changed hdslGT1000 to hdslGT1030 and 
--					hdslGT2000 to hdslGT2030
-- 2.00B    15-Oct-98   C. Amorossi     Added hdslGT1020 and hdslGT2020 and fixed
--					description of gdcHdslLedStatus1
-- 2.00C    26-Oct-98   C. Amorossi     Added hdsl711D2

GDCHDSL-MIB DEFINITIONS ::= BEGIN

IMPORTS
	Gauge,enterprises,TimeTicks	FROM RFC1155-SMI
	OBJECT-TYPE			FROM RFC-1212
	DisplayString			FROM RFC1213-MIB
	SCinstance			FROM GDCMACRO-MIB;

gdc 		         OBJECT IDENTIFIER ::= { enterprises 498 }
hdsl		         OBJECT IDENTIFIER ::= { gdc 11 }
gdcHdslSystem	         OBJECT IDENTIFIER ::= { hdsl 1 }

hdsl700G2                OBJECT IDENTIFIER ::= { hdsl 2 }
hdsl700G3                OBJECT IDENTIFIER ::= { hdsl 3 }
hdsl730D1                OBJECT IDENTIFIER ::= { hdsl 4 }
hdsl730D2                OBJECT IDENTIFIER ::= { hdsl 5 }
hdsl720G1                OBJECT IDENTIFIER ::= { hdsl 6 }
hdsl720G2                OBJECT IDENTIFIER ::= { hdsl 7 }
hdsl702G2                OBJECT IDENTIFIER ::= { hdsl 8 }
hdsl710D2                OBJECT IDENTIFIER ::= { hdsl 9 }
hdsl700G2RP              OBJECT IDENTIFIER ::= { hdsl 10}
hdsl710D2RP              OBJECT IDENTIFIER ::= { hdsl 11}
hdsl720G2RP              OBJECT IDENTIFIER ::= { hdsl 12}
hdsl730D2RP              OBJECT IDENTIFIER ::= { hdsl 13}
hdsl701T2                OBJECT IDENTIFIER ::= { hdsl 14}
hdsl701T2RP              OBJECT IDENTIFIER ::= { hdsl 15}
hdsl721T1    	         OBJECT IDENTIFIER ::= { hdsl 16}
hdsl721T2    	         OBJECT IDENTIFIER ::= { hdsl 17}
hdsl721T2RP    	         OBJECT IDENTIFIER ::= { hdsl 18}
hdsl731D1    	         OBJECT IDENTIFIER ::= { hdsl 19}
hdsl731D2    	         OBJECT IDENTIFIER ::= { hdsl 20}
hdsl731D2RP    	         OBJECT IDENTIFIER ::= { hdsl 21}
hdsl700AG2               OBJECT IDENTIFIER ::= { hdsl 22}
hdsl700AG2NZ             OBJECT IDENTIFIER ::= { hdsl 23}
hdslGT1030               OBJECT IDENTIFIER ::= { hdsl 25}
hdslGT2030               OBJECT IDENTIFIER ::= { hdsl 26}
uas7722               	 OBJECT IDENTIFIER ::= { hdsl 27}
hdslGT1020               OBJECT IDENTIFIER ::= { hdsl 28}
hdslGT2020               OBJECT IDENTIFIER ::= { hdsl 29}
hdsl711D2    	         OBJECT IDENTIFIER ::= { hdsl 30}

gdcHdslVersion		 OBJECT IDENTIFIER ::= { gdcHdslSystem 1 }
gdcHdslMaintenance	 OBJECT IDENTIFIER ::= { gdcHdslSystem 2 }
gdcHdslConfiguration	 OBJECT IDENTIFIER ::= { gdcHdslSystem 3 }
gdcHdslDiagnostics	 OBJECT IDENTIFIER ::= { gdcHdslSystem 4 }
gdcHdslPerformance 	 OBJECT IDENTIFIER ::= { gdcHdslSystem 5 }
gdcHdslStatus		 OBJECT IDENTIFIER ::= { gdcHdslSystem 6 }
gdcHdslDiagnosticResults OBJECT IDENTIFIER ::= { gdcHdslSystem 7 }
gdcFractional		 OBJECT IDENTIFIER ::= { gdcHdslSystem 8 }
gdcHdslAlarmThresholds 	 OBJECT IDENTIFIER ::= { gdcHdslSystem 9 }


-- This MIB module uses the extended OBJECT-TYPE macro as
-- defined in RFC 1212.

-- Note:  All rows in all tables defined within this MIB module are
-- virtual.  They can neither be created or deleted by management
-- operations.

-- The Version Group. This group identifies the version information
-- for the MIB.

-- *************************************************************************
-- The Interfaces are defined as follows:
-- 700G2:	700G3:		730D1/GT1000:		730D2/GT2000:	
-- Unit	  0	Unit  	0	Unit	0		Unit	0
-- E1	  1	E1     	1	DTE	1		DTE	1
-- Loop1  2	Loop1  	2	Loop1	2		Loop1	2
-- Loop2  3	Loop2  	3				Loop2	3
-- 		Loop3  	4		
--
-- 702G2:	720G1/GT1020:	720G2/GT2020:	710D2/711D2:    701T2 & 721T2
-- Unit   0	Unit	0	Unit	0	Unit	0       Unit     0
-- E1     1	E1	1	E1	1	DTE	1	T1       1
-- Loop1  2	Loop1	2	Loop1	2	Loop1	2       Loop1    2 
-- Loop2  3			Loop2	3	Loop2	3	Loop2	 3

-- 700AG2:	700AG2NZ:	7722		
-- Unit   0	Unit    0	Unit	0  	
-- E1     1	E1      1	Loop1	2	
-- Loop1  2	Loop1   2	Loop2	3	
-- Loop2  3	Loop2   3			
-- 721T1 is same as 721T2, except that this is only one loop
-- 731d1 & 731d2 is same as 730d1 & 730d2 resp., except that these have a max. of 12 DS0s on each.
-- All rp products have remote power feed feature.
-- *************************************************************************

 gdcHdslSystemMIBversion OBJECT-TYPE
     	SYNTAX DisplayString (SIZE (5))
     	ACCESS read-only
     	STATUS mandatory
     	DESCRIPTION
     		"Identifies the version of the MIB. The format of the version
     		is x.yzT, where 'x' identifies the major revision number, 'y'
     		identifies the minor revision number, 'z' identifies the
     		typographical revision, and T identifies the test revision.
     		Acceptable values for the individual revision components are
     		as follows:
 
     		x: 1 - 9
     		y: 0 - 9
     		z: 0 - 9
     		T: A - Z
 
     		Upon formal release, no designation for the test revision will
     		be present."
     	::= { gdcHdslVersion 1 }

 gdcHdslVersionTable OBJECT-TYPE
 	SYNTAX	SEQUENCE OF GdcHdslVersionEntry
 	ACCESS	not-accessible
 	STATUS	mandatory
 	DESCRIPTION " "
	::= { gdcHdslVersion 2  }
 
 gdcHdslVersionEntry OBJECT-TYPE
 	SYNTAX	GdcHdslVersionEntry
 	ACCESS	not-accessible
 	STATUS	mandatory
 	DESCRIPTION
 		"An entry in the GDC Hdsl Version Table."
 	INDEX	{ gdcHdslVersionIndex }
 	::= { gdcHdslVersionTable 1 }
 
 GdcHdslVersionEntry ::=
 	SEQUENCE {
 		 	gdcHdslVersionIndex
 				SCinstance,
 		 	gdcHdslFirmwareRev
 				DisplayString,
 			gdcHdslModelNumber
 				DisplayString
 		}
 
 gdcHdslVersionIndex OBJECT-TYPE
 	SYNTAX	SCinstance
 	ACCESS	read-only
 	STATUS	mandatory
 	DESCRIPTION
    		"The index value which uniquely identifies the interface to
    		which this entry is applicable.  This has the form of a
    		SCinstance which defines the slot, line, drop, and sub-identifier.
		The table describes the maintenance objects for 
		the unit and references the unit interface (cc = 00)."
 	::= { gdcHdslVersionEntry 1 }
 
 gdcHdslFirmwareRev OBJECT-TYPE
 	SYNTAX	DisplayString (SIZE(2))
 	ACCESS	read-only
 	STATUS	mandatory
 	DESCRIPTION
 		"The version number of the firmware, to allow products to know which 
 		revision is installed.  The released version number is sequenced from 
 		, A-, ... AA, ... ZZ.  Test versions are numerical from 01 to 99."
 	::= { gdcHdslVersionEntry 2 }
 
 gdcHdslModelNumber		OBJECT-TYPE
 	SYNTAX	DisplayString (SIZE(0..16))
 	ACCESS	read-only
 	STATUS	mandatory
 	DESCRIPTION
 		"This variable is used to determine the type
 		of card family installed ex. "
 	::= { gdcHdslVersionEntry 3 }
 
-- ********************************************************************
-- GDC HDSL Download Table
-- ********************************************************************

gdcHdslDownloadTable OBJECT-TYPE
    SYNTAX  SEQUENCE OF GdcHdslDownloadEntry
    ACCESS  not-accessible
    STATUS  mandatory
    DESCRIPTION 
	    "The Hdsl download table "
    ::= { gdcHdslVersion 3  }

gdcHdslDownloadEntry OBJECT-TYPE
    SYNTAX  GdcHdslDownloadEntry
    ACCESS  not-accessible
    STATUS  mandatory
    DESCRIPTION
	    "An entry in the GDC gdcHdslSystem Download Table."
    INDEX  { gdcHdslDownloadIndex }
    ::= { gdcHdslDownloadTable 1 }
									
GdcHdslDownloadEntry ::=
    SEQUENCE {
	gdcHdslDownloadIndex         SCinstance,
	gdcHdslActiveFirmwareRev     DisplayString,
	gdcHdslStoredFirmwareRev     DisplayString,
	gdcHdslStoredFirmwareStatus  INTEGER,
	gdcHdslSwitchActiveFirmware  INTEGER,
	gdcHdslDownloadingMode       INTEGER,
	gdcHdslEraseFlash            INTEGER
	}

gdcHdslDownloadIndex OBJECT-TYPE
    SYNTAX  SCinstance
    ACCESS  read-only
    STATUS  mandatory
    DESCRIPTION
        "Integer value which uniquely identifies the GDCHDSL to which this
         entry is applicable. SCinstance is defined to be SLDi where:
         S (byte value) - physical shelf slot location (01-32)
         L (byte value) - line number (01)
         D (byte value) - drop number (00-31)
         i (byte value) - loop or interface number (00-03)"
    ::= { gdcHdslDownloadEntry 1 }

gdcHdslActiveFirmwareRev OBJECT-TYPE
    SYNTAX  DisplayString (SIZE(8))
    ACCESS  read-only
    STATUS  mandatory
    DESCRIPTION
        "The version number of the firmware currently executing.
	 The format is MM.NN.BB where:
		MM: Major Revision (0-99)
		NN: Minor Revision (0-99)
		BB: Bug Fix Revision (0-99)
	 Valid [i]nterface = 0"
    ::= { gdcHdslDownloadEntry 2 }

gdcHdslStoredFirmwareRev OBJECT-TYPE
    SYNTAX DisplayString (SIZE(8))
    ACCESS read-only
    STATUS mandatory
    DESCRIPTION
        "The version number of the firmware stored (in a compressed format) 
         but not currently executing.
		MM: Major Revision (0-99)
		NN: Minor Revision (0-99)
		BB: Bug Fix Revision (0-99)
	 Valid [i]nterface = 0"
    ::= { gdcHdslDownloadEntry 3 }

gdcHdslStoredFirmwareStatus OBJECT-TYPE
    SYNTAX INTEGER {
        statBlank(1),                       
        statDownLoading(2),
	statOK(3),
	statCheckSumBad(4),    
	statUnZipping(5),
	statBadUnZip(6),
	statDownloadAborted(7)
                    
    }
    ACCESS read-only
    STATUS mandatory
    DESCRIPTION
        "This object represents the state of the Non-Active or Stored firmware:

         statBlank(1)    	Factory Default                  
         statDownLoading(2)	In process of downloading firmware
	 statOK(3)		Zipped version checksum succesful (OK to switch)
				(can set gdcHdslSwitchActiveFirmware to	
				switchActive(2))
	 statCheckSumBad(4)    	Failed checksum after download
	 statUnZipping(5)	In process of uncompressing into active area
	 statBadUnZip(6)      	Failed last uncompress 
	 statDownloadAborted(7) Download aborted by user             

	 Valid [i]nterface = 0"
    ::= { gdcHdslDownloadEntry 4 }


gdcHdslSwitchActiveFirmware OBJECT-TYPE
    SYNTAX INTEGER {
        switchNorm(1),                  -- Read only
        switchActive(2)			-- Write only
    }
    ACCESS read-write
    STATUS mandatory
    DESCRIPTION
        "This object is used to switch the active executing firmware from 
	 the version in gdcHdslActiveFirmwareRev to the version in 
	 gdcHdslStoredFirmwareRev.

	 When a  switchActive(2) is set (write only) the element will:
		1) reboot
		2) uncompress stored code into active area
		3) perform checksum on active area
		4) Set gdcHdslStoredStatus object to indicate results
		5) If succesfull:
		    update gdcHdslActiveFirmwareRev and gdcHdslStoredFirmwareRev
		    and begin executing
		   If failed: 
		    replace active area with previous revision

	 The switchNorm(1) enumeration will always be read. 

	 Setting switchActive(2) when the gdcHdslStoredFirmwareStatus is 
	 not statOK(3) will result in an error.
	 Valid [i]nterface = 0"
    ::= { gdcHdslDownloadEntry 5 }


gdcHdslDownloadingMode OBJECT-TYPE
    SYNTAX INTEGER {
        disableAll(1),
        enableAndWait(2),
	enableAndSwitch(3)
    }
    ACCESS read-write
    STATUS mandatory
    DESCRIPTION
        "This object is used to configure the download mode:

         disableAll(1)	       Prevents any firmware downloading to GDCHDSL

         enableAndWait(2)      Allows downloading zipped code to be stored only!
								
	 enableAndSwitch(3)    Allows downloading and then unzips and begins executing
			       the new code
	 Valid [i]nterface = 0"
    ::= { gdcHdslDownloadEntry 6 }


gdcHdslEraseFlash OBJECT-TYPE
    SYNTAX INTEGER {
        normal(1),    -- read-only
        erase(2)      -- write-only
    }
    ACCESS read-write
    STATUS mandatory
    DESCRIPTION
        "A set of this object to erase(2) will erase the application
         stored in flash.  After setting this object, there should
         be a delay of at least 2 minutes before downloading the 
	 unit."
    ::= { gdcHdslDownloadEntry 7}



-- ********************************************************************
-- GDC HDSL Maintenance Table
-- ********************************************************************

gdcHdslMaintenanceTable OBJECT-TYPE
	SYNTAX	SEQUENCE OF GdcHdslMaintenanceEntry
	ACCESS	not-accessible
	STATUS	mandatory
	DESCRIPTION
		"The table describes the maintenance objects for 
		the unit and references the unit interface (cc = 00)."
	::= { gdcHdslMaintenance 1  }

gdcHdslMaintenanceEntry OBJECT-TYPE
	SYNTAX	GdcHdslMaintenanceEntry
	ACCESS	not-accessible
	STATUS	mandatory
	DESCRIPTION
		"An entry in the GDC HDSL Maintenance Configuration Table."
	INDEX	{ gdcHdslMaintenanceLineIndex }
	::= { gdcHdslMaintenanceTable 1 }

GdcHdslMaintenanceEntry ::=
	SEQUENCE {
                        gdcHdslMaintenanceLineIndex
				SCinstance,
			gdcHdslSoftReset
				INTEGER,
			gdcHdslConfigMode
				INTEGER,
			gdcHdslSysUpTime
				TimeTicks,
        		gdcHdslUnitType 
				INTEGER,
		 	gdcHdslDefaultInit
				INTEGER,
           		 gdcHdslDataType
              			INTEGER,
			gdcHdslLoopProvision
		                INTEGER,
			gdcHdslNumberofLoops
				INTEGER,
			gdcHdslFrontPanel
				INTEGER,
			gdcHdslRoutingConfig
				INTEGER,
			gdcHdslPrivateStorage1
				DisplayString,
			gdcHdslPrivateStorage2
				DisplayString,
			gdcHdslPrivateStorage3
				DisplayString,
			gdcHdslLedStatus
				OCTET STRING,
	  		fracExecution
		 		INTEGER,
			gdcHdslAlarmStatus
				OCTET STRING,
			gdcHdslV54Config
				INTEGER,
			gdcHdslFPRDLConfig
				INTEGER,
       			gdcHdslRLTimeOut
				INTEGER,
			gdcHdslRPEnable
				INTEGER,
			gdcHdslLedStatus1
				OCTET STRING				
		}

gdcHdslMaintenanceLineIndex OBJECT-TYPE
	SYNTAX	SCinstance
	ACCESS	read-only
	STATUS	mandatory
	DESCRIPTION
    		"The index value which uniquely identifies the interface to
    		which this entry is applicable.  This has the form of a
    		SCinstance which defines the slot, line, drop, and sub-identifier.
		The table describes the maintenance objects for 
		the unit and references the unit interface (cc = 00)."
	::= { gdcHdslMaintenanceEntry 1 }

 gdcHdslSoftReset 	OBJECT-TYPE
	SYNTAX	INTEGER {
			reset(1),
			norm(2)
		}
	ACCESS	read-write
	STATUS	mandatory
	DESCRIPTION
		"Supports the action of soft resetting the unit.  When this
		object is set to reset(1), then the unit performs a soft
		reset, whose meaning is specific to the type of unit being
		managed. The value norm(2) can not be set by management."
	::= { gdcHdslMaintenanceEntry 2 }

gdcHdslConfigMode 	OBJECT-TYPE
	SYNTAX	INTEGER {
			software(1),
			hardware(2)
		}
	ACCESS	read-only
	STATUS	mandatory
	DESCRIPTION
		"The hardware configuration mode of the unit. A unit may
		be configured through hardware switches, jumper, straps, etc.
		The value software(1) indicates that the unit is software
		configurable.  The value of hardware(2) indicates that some options
		are hard configured and that software configuration is not
		permitted of these options."
	::= { gdcHdslMaintenanceEntry 3 }

 gdcHdslSysUpTime 	OBJECT-TYPE
	SYNTAX	TimeTicks
	ACCESS	read-only
	STATUS	mandatory
	DESCRIPTION
		"This variable is used to report the elapsed system tick
		time for conversion to real time at the controller and is
		not related to the sysUpTime referenced in MIB-II.
		Upon power-up of the unit, the elapsed time is cleared.
		The elapsed time counter rolls over upon reaching the
		maximum count."
	::= { gdcHdslMaintenanceEntry 4 }

gdcHdslUnitType OBJECT-TYPE
	SYNTAX	INTEGER {
			ltu(1),
			ntu(2)
		}
        ACCESS  read-write
      	STATUS  mandatory
        DESCRIPTION  " This variable is used to define HDSL unit type.
		When this object is set to ltu(1), the unit is a Line Terminating
		Unit and serves as master. When this object is set to ntu(2), the unit
		is a network terminating unit."

	::= { gdcHdslMaintenanceEntry 5 }

gdcHdslDefaultInit	OBJECT-TYPE
	SYNTAX	INTEGER {
			factoryDefault(1),
			normal(2)
		}
	ACCESS	read-write
	STATUS	mandatory
	DESCRIPTION
		"This is used to allow the NonVolatile Configuration to 
		be set to a factory default state.  When this value is set to
		factoryDefault(1) the unit will perform
		a reset to make the default configuration take affect. 
		The value of normal(2) will be returned when the initialization
		is complete.
		The value normal(2) can not be set by management."
	::= { gdcHdslMaintenanceEntry 6  }


gdcHdslDataType OBJECT-TYPE
	SYNTAX	INTEGER {
			voice(1),
			data(2)
		}
        ACCESS  read-write
      	STATUS  mandatory
       	DESCRIPTION
               	" This variable is used to define the HDSL data type. When this
		object is set to data(2) the data pass through the unit is digital
		data. When is set to voice(1) the data pass rhrough the unit is 
		voice data. "
	::= { gdcHdslMaintenanceEntry 7  }


gdcHdslLoopProvision OBJECT-TYPE
	SYNTAX INTEGER {
			pointopoint(1),
			pointomultipoint(2) 
		 }
    	ACCESS read-write
    	STATUS mandatory
    	DESCRIPTION
    		" This variable is used to define HDSL unit loop provision.
		When this variable is set to pointopoint(1), the unit is connected
		to another HDSL unit. When is set to pointomultipoint(2), the unit
		is connected to more than one other HDSL units or data grooming. "
	::= { gdcHdslMaintenanceEntry 8  }

gdcHdslNumberofLoops OBJECT-TYPE
	SYNTAX INTEGER {
			oneLoop(1),
			twoLoops(2),
			threeLoops(3) 
		 }
    	ACCESS read-write
    	STATUS mandatory
    	DESCRIPTION
    		" This variable is used to define HDSL unit loop configuration.
		It can be set for one to threee loops."
	::= { gdcHdslMaintenanceEntry 9  }

gdcHdslFrontPanel OBJECT-TYPE
	SYNTAX INTEGER {
			inhibit(1),
			enable(2) 
		 }
    	ACCESS read-write
    	STATUS mandatory
    	DESCRIPTION
    		" This variable is used to define the front Panel operation."
	::= { gdcHdslMaintenanceEntry 10  }

gdcHdslRoutingConfig OBJECT-TYPE
	SYNTAX INTEGER {
			twoLoops(1),
			threeLoops(2) 
		 }
    	ACCESS read-write
    	STATUS mandatory
    	DESCRIPTION
    		" This variable is used to define HDSL ......"
	::= { gdcHdslMaintenanceEntry 11  }


gdcHdslPrivateStorage1	OBJECT-TYPE
	SYNTAX DisplayString (SIZE(16))
    	ACCESS read-write
    	STATUS mandatory
    	DESCRIPTION
    		" This variable is used for general purpose storage."
	::= { gdcHdslMaintenanceEntry 12  }

gdcHdslPrivateStorage2	OBJECT-TYPE
	SYNTAX DisplayString (SIZE(16))
    	ACCESS read-write
    	STATUS mandatory
    	DESCRIPTION
    		" This variable is used for general purpose storage."
	::= { gdcHdslMaintenanceEntry 13  }

gdcHdslPrivateStorage3	OBJECT-TYPE
	SYNTAX DisplayString (SIZE(16))
    	ACCESS read-write
    	STATUS mandatory
    	DESCRIPTION
    		" This variable is used for general purpose storage."
	::= { gdcHdslMaintenanceEntry 14  }

gdcHdslLedStatus OBJECT-TYPE
	 SYNTAX  OCTET STRING (SIZE(2))
	 ACCESS  read-only
	 STATUS  mandatory
	 DESCRIPTION
		 "Returns a bitwise snapshot of the front panel LED state.
		 Octet 1 bit 7 - not used
			 bit 6 - not used
			 bit 5 - not used
			 bit 4 - not used
			 bit 3 - NORM E1
			 bit 2 - ES E1
			 bit 1 - AL
			 bit 0 - TM

		 Octet 2 bit 7 - not used
			 bit 6 - not used
			 bit 5 - NORM L3
			 bit 4 - ES L3
			 bit 3 - NORM L2
			 bit 2 - ES L2
			 bit 1 - NORM L1
			 bit 0 - ES L1"
	::= { gdcHdslMaintenanceEntry 15  }

fracExecution OBJECT-TYPE
        SYNTAX  INTEGER {
       		execute(1),
			norm(2)
			}
        ACCESS  read-write
        STATUS  mandatory
        DESCRIPTION
                " For Set, only execute is allowed."
	::= { gdcHdslMaintenanceEntry 16  }

gdcHdslAlarmStatus  OBJECT-TYPE
	SYNTAX	  OCTET STRING (SIZE (1..255))
	ACCESS	  read-only
	STATUS	  mandatory
	DESCRIPTION
		"The current alarms of the unit without the alarm masks."
	::= { gdcHdslMaintenanceEntry 17 }

gdcHdslV54Config	OBJECT-TYPE
	SYNTAX	INTEGER {
			inhibit(1),
			enabled(2)
			}
	ACCESS	  read-write
	STATUS	  mandatory
	DESCRIPTION
		"This object selects the ability of the unit to recognize
         	V.54 pattern. Only applicable to DC730 & DC731 units."
	::= { gdcHdslMaintenanceEntry 18 }

gdcHdslFPRDLConfig	OBJECT-TYPE
	SYNTAX	INTEGER {
			eoc(1),
			v54(2)
			}
	ACCESS	  read-write
	STATUS	  mandatory
	DESCRIPTION
		"This object selects the pattern to be transmitted when 
		RDL test is selected via the front panel RDL switch.
		Only applicable to DC730 & DC731 units."
	::= { gdcHdslMaintenanceEntry 19 }

gdcHdslRLTimeOut	OBJECT-TYPE
	SYNTAX	INTEGER {
			none(1),
			mins10(2)
			}
	ACCESS	  read-write
	STATUS	  mandatory
	DESCRIPTION
		"This object selects the RLTimeOut to be disabled(1)
		or set to 10 minutes(2). Only applicable to SC710D2 units."
	::= { gdcHdslMaintenanceEntry 20 }

gdcHdslRPEnable 	OBJECT-TYPE
	SYNTAX	INTEGER {
			inhibit(1),
			enable(2)
			}
	ACCESS	  read-write
	STATUS	  mandatory
	DESCRIPTION
		"This object selects the Remote power to be enabled(2)
		or disabled(1). Only applicable RP products which are on the shelf."
	::= { gdcHdslMaintenanceEntry 21 }	

gdcHdslLedStatus1 OBJECT-TYPE
	 SYNTAX  OCTET STRING (SIZE(3))
	 ACCESS  read-only
	 STATUS  mandatory
	 DESCRIPTION
		 "Returns a bitwise snapshot of the front panel LED state.
		  This mib object is only used for the new HDSl elements.
		 Octet 1 bit 7 - not used
			 bit 6 - EIA RD
			 bit 5 - EIA CO
			 bit 4 - EIA RS
			 bit 3 - NORM E1/T1 NORM
			 bit 2 - ES E1/T1 ER
			 bit 1 - AL
			 bit 0 - TM

		 Octet 2 bit 7 - not used
			 bit 6 - EIA SD
			 bit 5 - NORM L3
			 bit 4 - ES L3
			 bit 3 - NORM L2
			 bit 2 - ES L2
			 bit 1 - NORM L1
			 bit 0 - ES L1

		 Octet 3 bit 7 - not used
			 bit 6 - not used
			 bit 5 - ST  (GT10xx, GT20xx)
			 bit 4 - RL  (GT10xx, GT20xx)
			 bit 3 - LL  (GT10xx, GT20xx)
			 bit 2 - INS (uas7722) 
			 bit 1 - RPF FAULT
			 bit 0 - RPF NORM	"

	::= { gdcHdslMaintenanceEntry 22  }


-- ********************************************************************
-- The GDC HDSL Configuration Tables
-- ********************************************************************

--                      E1 CONFIGURATION TABLE //  Not applicable for T1 and DTE products                           
--

 gdcHdslE1ConfigTable OBJECT-TYPE
     	SYNTAX SEQUENCE OF GdcHdslE1ConfigEntry
     	ACCESS not-accessible
     	STATUS mandatory
     	DESCRIPTION
     		"The GDC E1 Configuration table.  Information in the entries
     		of this table are used to configure E1 interface."
         ::= { gdcHdslConfiguration 1 }

 gdcHdslE1ConfigEntry OBJECT-TYPE
     	SYNTAX GdcHdslE1ConfigEntry
     	ACCESS not-accessible
     	STATUS mandatory
     	DESCRIPTION
     		"The GDC E1 Configuration table entry.  The information in
     		this entry augments are used to configure E1 interface. "
     	INDEX { gdcHdslE1ConfigIndex }
     	::= { gdcHdslE1ConfigTable 1 }
 
 GdcHdslE1ConfigEntry ::=
     	SEQUENCE {
 		        gdcHdslE1ConfigIndex SCinstance,
 		        gdcHdslE1FramingMode INTEGER,
 		        gdcHdslE1LineUnit INTEGER,
			gdcHdslE1LineCoding INTEGER
 	    }

 gdcHdslE1ConfigIndex OBJECT-TYPE
     	SYNTAX SCinstance
     	ACCESS read-only
     	STATUS mandatory
     	DESCRIPTION
     		"The index value which uniquely identifies the interface to
     		which this entry is applicable.  This has the form of a
     		SCinstance which defines the slot, line, drop, and sub-identifier.
              In which this case is an E1 interface (cc=01)."
     	::= { gdcHdslE1ConfigEntry 1 }
 

 gdcHdslE1FramingMode OBJECT-TYPE
     	SYNTAX INTEGER {
 			framed(1),		
     		unframed(2)
 	    }
     	ACCESS read-write
     	STATUS mandatory
     	DESCRIPTION 
     		" This variable is used to determine E1 framing mode. "
     	::= { gdcHdslE1ConfigEntry 2 }
 
 gdcHdslE1LineUnit OBJECT-TYPE
     	SYNTAX INTEGER {
     			tlu(1),	
 		     	ilu(2)
 	    }
     	ACCESS read-write
     	STATUS mandatory
     	DESCRIPTION
     		" This variable is used to determine operating mode of the
 		  HDSL system with respect to E1 trunk. When this variable
 		  is set to tlu(1), the system operates as a termination line
 		  unit. When this variable is set to ilu(2) the system operates
 		  as an intermediate line unit."
     	::= { gdcHdslE1ConfigEntry 3 }

 gdcHdslE1LineCoding OBJECT-TYPE
           SYNTAX  INTEGER {
                       ami (1),
                       hdb3 (2)
                   }
           ACCESS  read-write
           STATUS  mandatory
           DESCRIPTION
              "This variable describes the  variety  of  Zero
              Code  Suppression  used  on  the link, which in
              turn affects a number of its characteristics.

              E1 links, with or without CRC, use HDB3  or
              AMI.

              AMI refers to a mode wherein no  zero  code
              suppression  is  present  and the line encoding
              does not solve the problem directly.   In  this
              application, the higher layer must provide data
              which meets or exceeds the  pulse  density  re-
              quirements, such as inverting HDLC data."
          ::= { gdcHdslE1ConfigEntry 4 }

 
 
-- *********************************************************************
--                     DTE CONFIGURATION TABLE  //Not applicable for T1 and E1 products
-- *********************************************************************
 gdcHdslDteConfigTable OBJECT-TYPE
     SYNTAX SEQUENCE OF GdcHdslDteConfigEntry
     ACCESS not-accessible
     STATUS mandatory
     DESCRIPTION
     	"The GDC DTE Configuration table.  "
     ::= { gdcHdslConfiguration 2 }
 
 gdcHdslDteConfigEntry OBJECT-TYPE
     SYNTAX GdcHdslDteConfigEntry
     ACCESS not-accessible
     STATUS mandatory
     DESCRIPTION
     	"The GDC DTE Configuration table entry. "
     INDEX { gdcHdslDteConfigIndex }
     ::= { gdcHdslDteConfigTable 1 }

 GdcHdslDteConfigEntry ::= 
     SEQUENCE {
 	        	gdcHdslDteConfigIndex SCinstance,
 	        	gdcHdslDteCtsMode INTEGER,
 	       	    	gdcHdslDteDataRate INTEGER,
                  	gdcHdslDteTxClkSource INTEGER
     		}
 
 gdcHdslDteConfigIndex OBJECT-TYPE
    SYNTAX SCinstance
     ACCESS read-only
     STATUS mandatory
     DESCRIPTION
     	"The index value which uniquely identifies the interface to
     	which this entry is applicable.  This has the form of a
     	SCinstance which defines the slot, line, drop. "
     ::= { gdcHdslDteConfigEntry 1 }
 
 gdcHdslDteCtsMode OBJECT-TYPE
     SYNTAX INTEGER { 
            forcedOn(1),
 			onWithRts(2)
 		}
     ACCESS read-write
     STATUS mandatory
     DESCRIPTION
     	" This variable controls the function of CTS. "
 
     ::= { gdcHdslDteConfigEntry 2 }
 
 gdcHdslDteDataRate OBJECT-TYPE
     	SYNTAX INTEGER  (0..32) 
     	ACCESS read-write
     	STATUS mandatory
     	DESCRIPTION
     		" This variable represents the DTE data Rate in 64K increments."
     ::= { gdcHdslDteConfigEntry 3 }

    gdcHdslDteTxClkSource OBJECT-TYPE
             SYNTAX  INTEGER {
                         externalTiming (1),
                         internalTiming (2),
                         loopTiming (3)
                     }
             ACCESS  read-write
             STATUS  mandatory
             DESCRIPTION
                "The source of Tranmit Clock.

                 'ExternalTiming' indicates that  recovered  re-
                ceive  clock  from another interface is used as
                the transmit clock.

                 'InternalTiming' indicates  that  a  local  clock
                source is used.

                 'loopTiming' indicates that the recovered  re-
                ceive clock is used as the transmit clock."
            ::= {gdcHdslDteConfigEntry 4 }

-- ********************************************************************
-- The GDC HDSL T1 Configuration Tables   // applicable only to 701Ts, 721Ts
-- ********************************************************************

--                      T1 CONFIGURATION TABLE
--

 gdcHdslT1ConfigTable OBJECT-TYPE
     	SYNTAX SEQUENCE OF GdcHdslT1ConfigEntry
     	ACCESS not-accessible
     	STATUS mandatory
     	DESCRIPTION
     		"The GDC T1 Configuration table.  Information in the entries
     		of this table are used to configure T1 interface."
         ::= { gdcHdslConfiguration 3 }

 gdcHdslT1ConfigEntry OBJECT-TYPE
     	SYNTAX GdcHdslT1ConfigEntry
     	ACCESS not-accessible
     	STATUS mandatory
     	DESCRIPTION
     		"The GDC T1 Configuration table entry.  The information in
     		this entry augments are used to configure T1 interface. "
     	INDEX { gdcHdslT1ConfigIndex }
     	::= { gdcHdslT1ConfigTable 1 }
 
 GdcHdslT1ConfigEntry ::=
     	SEQUENCE {
 		        gdcHdslT1ConfigIndex SCinstance,
				gdcHdslT1InterfaceType INTEGER,
 		        gdcHdslT1FramingMode INTEGER,
				gdcHdslT1TxPreequalization INTEGER,
				gdcHdslT1TxBulidOut INTEGER,
				gdcHdslT1InbandLBType INTEGER,
				gdcHdslT1FDLMode INTEGER,
				gdcHdslT1LineCoding INTEGER,
				gdcHdslT1TxClkSource INTEGER,
 		        gdcHdslT1LineCoding INTEGER
 	    }

 gdcHdslT1ConfigIndex OBJECT-TYPE
     	SYNTAX SCinstance
     	ACCESS read-only
     	STATUS mandatory
     	DESCRIPTION
     		"The index value which uniquely identifies the interface to
     		which this entry is applicable.  This has the form of a
     		SCinstance which defines the slot, line, drop, and sub-identifier.
              In which this case is an T1 interface (cc=01)."
     	::= { gdcHdslT1ConfigEntry 1 }
 
 gdcHdslT1InterfaceType OBJECT-TYPE
           SYNTAX  INTEGER {
                       dsx1(1),
                       ds1(2)
	           }
           ACCESS  read-write
           STATUS  mandatory
           DESCRIPTION
              "This variable is used to set T1 Interface Type "
          ::= { gdcHdslT1ConfigEntry 2 }

 gdcHdslT1FramingMode OBJECT-TYPE
     	SYNTAX INTEGER {
 			esfANSI(1),		
			esf54016(2),
			sf(3),
     		unframed(4)
 	    }
     	ACCESS read-write
     	STATUS mandatory
     	DESCRIPTION 
     		" This variable is used to determine T1 framing mode. "
     	::= { gdcHdslT1ConfigEntry 3 }
 
 
gdcHdslT1TxPreequalization OBJECT-TYPE
           SYNTAX  INTEGER {
               		preq0to133ft(1),
               		preq133to266ft(2),
	           	preq266to399ft(3),
	           	preq399to533ft(4),
			preq533to655ft(5)
	           }
           ACCESS  read-write
           STATUS  mandatory
           DESCRIPTION
              "This variable is used to set T1 Tx Line Preequalization "
          ::= { gdcHdslT1ConfigEntry 4 }


gdcHdslT1TxBulidOut OBJECT-TYPE
           SYNTAX  INTEGER {
                   bo0dB(1),
                   bo75dB(2),
	           bo150dB(3),
	           bo225dB(4)
	           }
           ACCESS  read-write
           STATUS  mandatory
           DESCRIPTION
              "This variable is used to set T1 Tx Line Bulid Out "
          ::= { gdcHdslT1ConfigEntry 5 }

gdcHdslT1InbandLBType OBJECT-TYPE
           SYNTAX  INTEGER {
                   inhibit (1),
                   lineloopback (2),
	           payloadloopback (3)
                   }
           ACCESS  read-write
           STATUS  mandatory
           DESCRIPTION
              "This variable is used to set T1 Inband LoopBack Type or Inhibit(1) this loopback"
          ::= { gdcHdslT1ConfigEntry 6 }

gdcHdslT1FDLMode OBJECT-TYPE
           SYNTAX  INTEGER {
                       enable(1),
                       disable(2)
	           }
           ACCESS  read-only
           STATUS  mandatory
           DESCRIPTION
              "This variable is used to enable/disable T1 FDL Mode"
          ::= { gdcHdslT1ConfigEntry 7 }



gdcHdslT1AISLoopdownTime OBJECT-TYPE
           SYNTAX  INTEGER {
                   inhibit(1),
                   ld5secs(2),
	           ld10secs(3),
	           ld20secs(4),
	           ld40secs(5),
		   ld60secs(6)
	           }
           ACCESS  read-write
           STATUS  mandatory
           DESCRIPTION
              "This variable is used to set T1 AIS Loopdown Time "
          ::= { gdcHdslT1ConfigEntry 8 }


 gdcHdslT1LineCoding OBJECT-TYPE
           SYNTAX  INTEGER {
                       ami (1),
                       b8zs (2)
                   }
           ACCESS  read-write
           STATUS  mandatory
           DESCRIPTION
              "This variable describes the  variety  of  Zero
              Code  Suppression  used  on  the link, which in
              turn affects a number of its characteristics.

              E1 links, with or without CRC, use HDB3  or
              AMI.

              AMI refers to a mode wherein no  zero  code
              suppression  is  present  and the line encoding
              does not solve the problem directly.   In  this
              application, the higher layer must provide data
              which meets or exceeds the  pulse  density  re-
              quirements, such as inverting HDLC data."
          ::= { gdcHdslT1ConfigEntry 9 }


gdcHdslT1TxClkSource OBJECT-TYPE
             SYNTAX  INTEGER {
                         externalTiming (1),
                         internalTiming (2),
                         loopTiming (3)
                     }
             ACCESS  read-write
             STATUS  mandatory
             DESCRIPTION
                "The source of Tranmit Clock.

                 'ExternalTiming' indicates that  recovered  re-
                ceive  clock  from another interface is used as
                the transmit clock.

                 'InternalTiming' indicates  that  a  local  clock
                source is used.

                 'loopTiming' indicates that the recovered  re-
                ceive clock is used as the transmit clock."
            ::= {gdcHdslT1ConfigEntry 10 }

-- ********************************************************************
-- GDC HDSL Diagnostics
-- ********************************************************************

-- Diagnostics pertain to the E1/T1 and Loop interfaces only.
--

gdcHdslDiagTable OBJECT-TYPE
    	SYNTAX SEQUENCE OF GdcHdslDiagEntry
    	ACCESS not-accessible
    	STATUS mandatory
    	DESCRIPTION
    		"The GDC HDSL Diagnostics table. "
	::= { gdcHdslDiagnostics 1 }

gdcHdslDiagEntry OBJECT-TYPE
    	SYNTAX GdcHdslDiagEntry
    	ACCESS not-accessible
    	STATUS mandatory
    	DESCRIPTION
    		"The GDC HDSL Diagnostics table entry. "
	INDEX { gdcHdslDiagIndex }
    	::= { gdcHdslDiagTable 1 }

GdcHdslDiagEntry ::= 
    	SEQUENCE {
                        gdcHdslDiagIndex SCinstance,
			gdcHdslLoopback INTEGER,
			gdcHdslBertTest INTEGER
	    }

gdcHdslDiagIndex OBJECT-TYPE
    	SYNTAX SCinstance
    	ACCESS read-only
    	STATUS mandatory
    	DESCRIPTION
    		"The index value which uniquely identifies the interface to
	    	which this entry is applicable.  This has the form of a
	    	SCinstance which defines the slot, line, drop, and sub-identifier,
	    	which in this case is a network interface."
    	::= { gdcHdslDiagEntry 1 }

gdcHdslLoopback OBJECT-TYPE
    	SYNTAX INTEGER {
			noLoop(1),
			lineLoop(2),
			localLoop(3),
			lineandlocalLoop(4),
--			payload(5)
			dataLoop(6),
			remoteLoop(7)
			}
    	ACCESS read-write
    	STATUS mandatory
    	DESCRIPTION
    		" This variable supports the action of a diagnostic loop 
		  at the point indicated.
		  dataLoop & remoteLoop are only supported by uas7722 "
    	::= { gdcHdslDiagEntry 2 }

gdcHdslBertTest OBJECT-TYPE
    	SYNTAX INTEGER {
			inhibit(1),
			enable(2),
			reset(3)
	        }			
    	ACCESS read-write
    	STATUS mandatory
    	DESCRIPTION
    		" This variable supports the action of Bit error rate test. When
		set to inhibit(1) no bert test is in process. When set to enable (2)
		BERT is in process"

    	::= { gdcHdslDiagEntry 3 }


-- ********************************************************************
-- GDC HDSL Diagnostic Results
-- ********************************************************************

gdcHdslDiagResultsTable OBJECT-TYPE
    	SYNTAX SEQUENCE OF GdcHdslDiagResultsEntry
    	ACCESS not-accessible
    	STATUS mandatory
    	DESCRIPTION
    		"The GDC HDSL Diagnostics table. "
	::= { gdcHdslDiagnosticResults 1 }

gdcHdslDiagResultsEntry OBJECT-TYPE
    	SYNTAX GdcHdslDiagResultsEntry
    	ACCESS not-accessible
    	STATUS mandatory
    	DESCRIPTION
    		"The GDC HDSL Diagnostics table entry. "
	INDEX { gdcHdslDiagResultsIndex }
    	::= { gdcHdslDiagResultsTable 1 }

GdcHdslDiagResultsEntry ::= 
    	SEQUENCE {
                        gdcHdslDiagResultsIndex SCinstance,
		        gdcHdslTestExecutionStatus INTEGER,
			gdcHdslDiagResultErr INTEGER,
		        gdcHdslDiagResultInterval INTEGER,
			gdcHdslV54RDLTest	INTEGER
	    }

gdcHdslDiagResultsIndex OBJECT-TYPE
    	SYNTAX SCinstance
    	ACCESS read-only
    	STATUS mandatory
    	DESCRIPTION
    		"The index value which uniquely identifies the interface to
	    	which this entry is applicable.  This has the form of a
	    	SCinstance which defines the slot, line, drop, and sub-identifier,
	    	which in this case is a network interface."
    	::= { gdcHdslDiagResultsEntry 1 }

gdcHdslTestExecutionStatus OBJECT-TYPE
    	SYNTAX INTEGER {
    			inSync(1),		
    			notInSync(2)
    		}
    	ACCESS read-only
    	STATUS mandatory
    	DESCRIPTION
    		"The current execution status of the diagnostic test.
		When set to inSync(1), BERT test is in sync and BER rate is valid.
		When set to notInSync(2), BERT test is not in Sync and BER rate is 
		not valid. "
    	::= { gdcHdslDiagResultsEntry 2 }

gdcHdslDiagResultErr OBJECT-TYPE
    	SYNTAX INTEGER (0..65535)
    	ACCESS read-only
    	STATUS mandatory
    	DESCRIPTION
    		"The results of the last diagnostic test.  This can be the
	    	current test running or the last completed test.

    		Note that the interpretation of these results may be affected
	    	by the value of the gdcTestExecutionStatus object."
    	::= { gdcHdslDiagResultsEntry 3 }

gdcHdslDiagResultInterval OBJECT-TYPE
    	SYNTAX INTEGER (0..65535)
    	ACCESS read-only
    	STATUS mandatory
    	DESCRIPTION
    		"This variable represents the Ber test intervals.
		A time interval is defined as the time required for transmission
		of a block of 2^24 bits. "
    	::= { gdcHdslDiagResultsEntry 4 }

gdcHdslV54RDLTest OBJECT-TYPE
    	SYNTAX INTEGER {
    			notInV54Test(1),		
    			txV54Test(2)
    		}
    	ACCESS read-only
    	STATUS mandatory
    	DESCRIPTION
    		"This variable indicates that the front panel RL button is selected
		and transmitting a V54 pattern. Applicable only to DC730 units."
    	::= { gdcHdslDiagResultsEntry 5 }


-- ********************************************************************
-- HDSL Current Performance Tables  //Not applicable for T1 interface
-- ********************************************************************
-- The current table contains various statistics being
-- collected for the current 15 minute interval.
  
gdcHdslCurrentTable OBJECT-TYPE
	SYNTAX  SEQUENCE OF GdcHdslCurrentEntry
        ACCESS  not-accessible
        STATUS  mandatory
        DESCRIPTION
		"The GDC Hdsl Current Performance table.  Information
		 in the entries of this table support the HDSL Scheduled
		 Performance Reports."
        ::= { gdcHdslPerformance 1 }

gdcHdslCurrentEntry OBJECT-TYPE
	SYNTAX  GdcHdslCurrentEntry
        ACCESS  not-accessible
        STATUS  mandatory
        DESCRIPTION
                "An entry in the Current table."
        INDEX   { gdcHdslCurrentIndex }
        ::= { gdcHdslCurrentTable 1 }

GdcHdslCurrentEntry ::=
         SEQUENCE {
             gdcHdslCurrentIndex
                 SCinstance,
             gdcHdslCurrentESs
                 Gauge,
             gdcHdslCurrentSESs
                 Gauge,
             gdcHdslCurrentUASs
                 Gauge,
             gdcHdslCurrentDMs
                 Gauge,
             gdcHdslCurrentFEBEs
                 Gauge,
	     gdcHdslCurrentStats
		 OCTET STRING
         }

gdcHdslCurrentIndex OBJECT-TYPE
	SYNTAX SCinstance
        ACCESS  read-only
        STATUS  mandatory
        DESCRIPTION
    		"The index value which uniquely identifies the interface to
    		which this entry is applicable.  This has the form of a
    		SCinstance which defines the slot, line, drop, and interface,
    		which in this case can be an E1 or Loop interface."
        ::= { gdcHdslCurrentEntry 1 }

gdcHdslCurrentESs OBJECT-TYPE
        SYNTAX  Gauge
        ACCESS  read-only
        STATUS  mandatory
        DESCRIPTION
                "The number of Errored Seconds, encountered  by
                an E1 or Loop interface in the current 15 minute inter-
                val."
        ::= { gdcHdslCurrentEntry 2 }

gdcHdslCurrentSESs OBJECT-TYPE
        SYNTAX  Gauge
        ACCESS  read-only
        STATUS  mandatory
        DESCRIPTION
                "The number of Severely Errored Seconds encoun-
                tered  by  a Loop or E1 interface  in the current 15
                minute interval."
        ::= { gdcHdslCurrentEntry 3 }

gdcHdslCurrentUASs OBJECT-TYPE
        SYNTAX  Gauge
        ACCESS  read-only
        STATUS  mandatory
        DESCRIPTION
                "The number of Unavailable Seconds  encountered
                by a Loop or E1 interface in the current 15 minute in-
                terval."
        ::= { gdcHdslCurrentEntry 4 }

gdcHdslCurrentDMs OBJECT-TYPE
        SYNTAX Gauge
        ACCESS read-only
        STATUS mandatory
        DESCRIPTION
                "The number of Degraded Minutes  (DMs)  encoun-
                tered  by  a Loop or E1  interface  in the current 15
                minute interval."
        ::= { gdcHdslCurrentEntry 5 }

gdcHdslCurrentFEBEs OBJECT-TYPE
        SYNTAX Gauge
        ACCESS read-only
        STATUS mandatory
        DESCRIPTION
                "The number of Far End Block Errors encountered
                by a Loop or E1 interface in the current 15
                minute interval."
        ::= {gdcHdslCurrentEntry 6 }

gdcHdslCurrentStats OBJECT-TYPE
        SYNTAX OCTET STRING (SIZE(15))
        ACCESS read-only
        STATUS mandatory
        DESCRIPTION
               "The number of Current ES, SES, UAS, DM and FEBE's
		encountered by a Loop or E1 interface in the current 15
                minute interval."
        ::= {gdcHdslCurrentEntry 7 }


-- ********************************************************************
-- HDSL Interval  Performance Tables   //Not applicable for T1 interface
-- ********************************************************************
-- The Interval Table contains various statistics
-- collected by each Loop or E1 Interface over the previous 24 hours of
-- operation.  The past 24 hours are broken into 96 completed
-- 15 minute intervals.

gdcHdslIntervalTable OBJECT-TYPE
	SYNTAX  SEQUENCE OF GdcHdslIntervalEntry
        ACCESS  not-accessible
        STATUS  mandatory
        DESCRIPTION
                "The Loop or E1 Interval table."
        ::= { gdcHdslPerformance 2 }

gdcHdslIntervalEntry OBJECT-TYPE
        SYNTAX  GdcHdslIntervalEntry
        ACCESS  not-accessible
        STATUS  mandatory
        DESCRIPTION
                "An entry in the Interval table."
        INDEX   { gdcHdslIntervalIndex, gdcHdslIntervalNumber }
        ::= { gdcHdslIntervalTable 1 }

GdcHdslIntervalEntry ::=
         SEQUENCE {
             gdcHdslIntervalIndex
                 SCinstance,
             gdcHdslIntervalNumber
                 INTEGER,
             gdcHdslIntervalESs
                 Gauge,
            gdcHdslIntervalSESs
                 Gauge,
             gdcHdslIntervalUASs
                 Gauge,
             gdcHdslIntervalDMs
                 Gauge,
             gdcHdslIntervalFEBEs
                 Gauge,
	     gdcHdslIntervalStats
		 OCTET STRING
         }

gdcHdslIntervalIndex OBJECT-TYPE
	SYNTAX  SCinstance
        ACCESS  read-only
        STATUS  mandatory
        DESCRIPTION
    		"The index value which uniquely identifies the interface to
    		which this entry is applicable.  This has the form of a
    		SCinstance which defines the slot, line, drop, and interface,
    		which in this case is a Loop or E1 interface."
    	::= { gdcHdslIntervalEntry 1 }    	   

gdcHdslIntervalNumber OBJECT-TYPE
	SYNTAX  INTEGER (1..96)
        ACCESS  read-only
        STATUS  mandatory
        DESCRIPTION
                "A number between 1 and 96, where 1 is the most
                recently completed 15 minute interval and 96 is
                the least recently completed 15 minutes  inter-
                val   (assuming   that  all  96  intervals  are
                valid)."
        ::= { gdcHdslIntervalEntry 2 }


gdcHdslIntervalESs OBJECT-TYPE
        SYNTAX  Gauge
        ACCESS  read-only
        STATUS  mandatory
        DESCRIPTION
                "The number of Errored Seconds encountered by a
                Loop or E1  interface in one of the previous 96, indi-
                vidual 15 minute, intervals."
        ::= { gdcHdslIntervalEntry 3 }

gdcHdslIntervalSESs OBJECT-TYPE
        SYNTAX  Gauge
        ACCESS  read-only
        STATUS  mandatory
        DESCRIPTION
                "The number of Severely Errored Seconds encoun-
                tered by a Loop or E1 interface in one of the previous
                96, individual 15 minute, intervals."
        ::= { gdcHdslIntervalEntry 4 }

gdcHdslIntervalUASs OBJECT-TYPE
        SYNTAX  Gauge
        ACCESS  read-only
        STATUS  mandatory
        DESCRIPTION
                "The number of Unavailable Seconds  encountered
                by  a  Loop or E1 interface in one of the previous 96,
                individual 15 minute, intervals."
        ::= { gdcHdslIntervalEntry 5 }

gdcHdslIntervalDMs OBJECT-TYPE
        SYNTAX Gauge
        ACCESS read-only
        STATUS mandatory
        DESCRIPTION
                "The number of Degraded Minutes  (DMs)  encoun-
                tered by a Loop or E1 interface in one of the previous
                96, individual 15 minute, intervals."
        ::= { gdcHdslIntervalEntry 6 }

gdcHdslIntervalFEBEs OBJECT-TYPE
        SYNTAX Gauge
        ACCESS read-only
        STATUS mandatory
        DESCRIPTION
    		" This variable represents the HDSL loops Far end block errors."
    	::= { gdcHdslIntervalEntry 7 }

gdcHdslIntervalStats OBJECT-TYPE
        SYNTAX OCTET STRING (SIZE(15))
        ACCESS read-only
        STATUS mandatory
        DESCRIPTION
    		" This variable represents stats at the HDSL loops."
    	::= { gdcHdslIntervalEntry 8 }


-- ********************************************************************
-- HDSL Total Performance Tables	//Not applicable for T1 interface
-- ********************************************************************
-- The Loop/E1 Total Table contains the cumulative sum of the
-- various statistics for the 24 hour period preceding the
-- current interval.

gdcHdslTotalTable OBJECT-TYPE
	SYNTAX  SEQUENCE OF GdcHdslTotalEntry
        ACCESS  not-accessible
        STATUS  mandatory
        DESCRIPTION
	"The GDC HDSL Total Performance table.  Information 
	 in the entries of this table support the HDSL 
	 Scheduled Performance Reports. 24 hour interval."
        ::= { gdcHdslPerformance 3 }

gdcHdslTotalEntry OBJECT-TYPE
        SYNTAX  GdcHdslTotalEntry
        ACCESS  not-accessible
        STATUS  mandatory
        DESCRIPTION
           "An entry in the Total table."
        INDEX   { gdcHdslTotalIndex }
           ::= { gdcHdslTotalTable 1 }

GdcHdslTotalEntry ::=
         SEQUENCE {
             gdcHdslTotalIndex
                 SCinstance,
             gdcHdslTotalESs
                 Gauge,
             gdcHdslTotalSESs
                 Gauge,
             gdcHdslTotalUASs
                 Gauge,
             gdcHdslTotalDMs
                 Gauge,
             gdcHdslTotalFEBEs
                 Gauge,
             gdcHdslTotalStats
                 OCTET STRING
         }

gdcHdslTotalIndex OBJECT-TYPE
	SYNTAX  SCinstance
        ACCESS  read-only
        STATUS  mandatory
        DESCRIPTION
    		"The index value which uniquely identifies the interface to
    		which this entry is applicable.  This has the form of a
    		SCinstance which defines the slot, line, drop, and interface,
    		which in this case is a Loop or E1 interface."
        ::= { gdcHdslTotalEntry 1 }

gdcHdslTotalESs OBJECT-TYPE
        SYNTAX  Gauge
        ACCESS  read-only
        STATUS  mandatory
        DESCRIPTION
                "The number of Errored Seconds encountered by a
                Loop or E1interface in the previous 24 hour interval"
        ::= { gdcHdslTotalEntry 2 }

gdcHdslTotalSESs OBJECT-TYPE
        SYNTAX  Gauge
        ACCESS  read-only
        STATUS  mandatory
        DESCRIPTION
                "The number of Severely Errored Seconds encoun-
                tered  by  a  Loop or E1 interface in the previous 24
                hour interval."
        ::= { gdcHdslTotalEntry 3 }

gdcHdslTotalUASs OBJECT-TYPE
        SYNTAX  Gauge
        ACCESS  read-only
        STATUS  mandatory
        DESCRIPTION
                "The number of Unavailable Seconds  encountered
                by  a Loop or E1 interface in the previous 24 hour in-
                terval."
        ::= { gdcHdslTotalEntry 4 }

gdcHdslTotalDMs OBJECT-TYPE
        SYNTAX Gauge
        ACCESS read-only
        STATUS mandatory
        DESCRIPTION
                "The number of Degraded Minutes  (DMs)  encoun-
                tered  by  a  Loop or E1  interface in the previous 24
                hour interval."
        ::= { gdcHdslTotalEntry 5 }

gdcHdslTotalFEBEs OBJECT-TYPE
        SYNTAX Gauge
        ACCESS read-only
        STATUS mandatory
        DESCRIPTION
                "The number of Far End Block Errors  en-
                countered  by a Loop or E1 interface in the current 15
                minute interval."
        ::= {gdcHdslTotalEntry 6 }

gdcHdslTotalStats OBJECT-TYPE
        SYNTAX OCTET STRING (SIZE(15))
        ACCESS read-only
        STATUS mandatory
        DESCRIPTION
                "The number of Total stats encountered  by a Loop or E1
		 interface in the current 15 minute interval."
        ::= {gdcHdslTotalEntry 7 }



--*******************************************************************
-- Loop/E1/T1 Performance Interval Maintenace Table
--*******************************************************************

gdcHdslIntervalMaintenanceTable OBJECT-TYPE
	SYNTAX SEQUENCE OF GdcHdslIntervalMaintenanceEntry
     	ACCESS not-accessible
     	STATUS mandatory
    	DESCRIPTION
     		"The GDC Loop/E1/T1 Interval  table. "
         ::= { gdcHdslPerformance 4 }
 	
gdcHdslIntervalMaintenanceEntry OBJECT-TYPE
 	SYNTAX GdcHdslIntervalMaintenanceEntry
     	ACCESS not-accessible
     	STATUS mandatory
     	DESCRIPTION
     		"The GDC Loop/E1/T1  Interval table entry. "
     	INDEX { gdcHdslIntervalMaintenanceIndex }
     	::= { gdcHdslIntervalMaintenanceTable 1 }
 
GdcHdslIntervalMaintenanceEntry ::= 
     	SEQUENCE {
     	    		gdcHdslIntervalMaintenanceIndex SCinstance,
         		gdcHdslResetIntervals INTEGER,
			gdcHdslNumberofValidIntervals INTEGER,
			gdcHdslResetMajorAlarm	INTEGER,
			gdcHdslResetMinorAlarm	INTEGER			
     		}
 
gdcHdslIntervalMaintenanceIndex OBJECT-TYPE
     	SYNTAX SCinstance
     	ACCESS read-only
     	STATUS mandatory
     	DESCRIPTION
     		"The index value which uniquely identifies the interface to
     		which this entry is applicable.  This has the form of a
     		SCinstance which defines the slot, line, drop, and interface,
     		which in this case is a Loop or E1/T1 interface."
     	::= { gdcHdslIntervalMaintenanceEntry 1 }  

 
gdcHdslResetIntervals OBJECT-TYPE
     	SYNTAX INTEGER {
     			norm(1),
     			reset(2)	
     		}
     	ACCESS read-write 
     	STATUS mandatory
         DESCRIPTION " This variable is used to reset Loop/E1/T1 performance intervals.
 			When it is set to reset, the Loop/E1/T1 performance tables are
 			reset to zero."
     	::= { gdcHdslIntervalMaintenanceEntry 2 }

gdcHdslNumberofValidIntervals OBJECT-TYPE
     	SYNTAX INTEGER (1..96)
     	ACCESS read-only 
     	STATUS mandatory
         DESCRIPTION " This variable is used to read the number of intervals collected.
		       Each interval is an increment of 15 minutes."
     	::= { gdcHdslIntervalMaintenanceEntry 3 }

gdcHdslResetMajorAlarm	OBJECT-TYPE
	SYNTAX	INTEGER {
			clearAlarm(1), -- write only
			normalAlarm(2) -- read only
			}
     	ACCESS read-write 
     	STATUS mandatory
         DESCRIPTION " This variable is used to reset alarm per Loop basis."
     	::= { gdcHdslIntervalMaintenanceEntry 4 }
 
gdcHdslResetMinorAlarm	OBJECT-TYPE
	SYNTAX	INTEGER {
			clearAlarm(1), -- write only
			normalAlarm(2) -- read only
			}
     	ACCESS read-write 
     	STATUS mandatory
         DESCRIPTION " This variable is used to reset alarm per Loop basis."
     	::= { gdcHdslIntervalMaintenanceEntry 5 }

--
-- ********************************************************************
-- HDSL T1 Current Performance Tables  // applicable for T1 interface only
-- ********************************************************************
-- The current table contains various statistics being
-- collected for the current 15 minute interval.
  
gdcHdslT1CurrentTable OBJECT-TYPE
	SYNTAX  SEQUENCE OF GdcHdslT1CurrentEntry
        ACCESS  not-accessible
        STATUS  mandatory
        DESCRIPTION
		"The GDC Hdsl Current Performance table.  Information
		 in the entries of this table support the HDSL Scheduled
		 Performance Reports."
        ::= { gdcHdslPerformance 5 }

gdcHdslT1CurrentEntry OBJECT-TYPE
	SYNTAX  GdcHdslT1CurrentEntry
        ACCESS  not-accessible
        STATUS  mandatory
        DESCRIPTION
                "An entry in the Current table."
        INDEX   { gdcHdslT1CurrentIndex }
        ::= { gdcHdslT1CurrentTable 1 }

GdcHdslT1CurrentEntry ::=
         SEQUENCE {
                 gdcHdslT1CurrentIndex
                 SCinstance,
        	 gdcHdslT1CurrentStats
		 OCTET STRING
         }

gdcHdslT1CurrentIndex OBJECT-TYPE
	SYNTAX SCinstance
        ACCESS  read-only
        STATUS  mandatory
        DESCRIPTION
    		"The index value which uniquely identifies the interface to
    		which this entry is applicable.  This has the form of a
    		SCinstance which defines the slot, line, drop, and interface,
    		which in this case can be an T1 interface."
        ::= { gdcHdslT1CurrentEntry 1 }


gdcHdslT1CurrentStats OBJECT-TYPE
        SYNTAX OCTET STRING (SIZE(16))
        ACCESS read-only
        STATUS mandatory
        DESCRIPTION
               "The number of Current ES, SES, UAS, BES,LOFC,CSS.
		encountered by  T1 interface in the current 15
                minute interval."
        ::= {gdcHdslT1CurrentEntry 2 }



-- ********************************************************************
-- HDSL T1 Interval  Performance Tables	  // applicable for T1 interface only
-- ********************************************************************
-- The Interval Table contains various statistics
-- collected by each T1 Interface over the previous 24 hours of
-- operation.  The past 24 hours are broken into 96 completed
-- 15 minute intervals.

gdcHdslT1IntervalTable OBJECT-TYPE
	SYNTAX  SEQUENCE OF GdcHdslT1IntervalEntry
        ACCESS  not-accessible
        STATUS  mandatory
        DESCRIPTION
                "The  T1 Interval table."
        ::= { gdcHdslPerformance 6 }

gdcHdslT1IntervalEntry OBJECT-TYPE
        SYNTAX  GdcHdslT1IntervalEntry
        ACCESS  not-accessible
        STATUS  mandatory
        DESCRIPTION
                "An entry in the Interval table."
        INDEX   { gdcHdslT1IntervalIndex, gdcHdslT1IntervalNumber }
        ::= { gdcHdslT1IntervalTable 1 }

GdcHdslT1IntervalEntry ::=
         SEQUENCE {
             gdcHdslT1IntervalIndex
                 SCinstance,
             gdcHdslT1IntervalNumber
                 INTEGER,
              gdcHdslT1IntervalStats
	 OCTET STRING
         }

gdcHdslT1IntervalIndex OBJECT-TYPE
	SYNTAX  SCinstance
        ACCESS  read-only
        STATUS  mandatory
        DESCRIPTION
    		"The index value which uniquely identifies the interface to
    		which this entry is applicable.  This has the form of a
    		SCinstance which defines the slot, line, drop, and interface,
    		which in this case is T1 interface."
    	::= { gdcHdslT1IntervalEntry 1 }    	   

gdcHdslT1IntervalNumber OBJECT-TYPE
	SYNTAX  INTEGER (1..96)
        ACCESS  read-only
        STATUS  mandatory
        DESCRIPTION
                "A number between 1 and 96, where 1 is the most
                recently completed 15 minute interval and 96 is
                the least recently completed 15 minutes  inter-
                val   (assuming   that  all  96  intervals  are
                valid)."
        ::= { gdcHdslT1IntervalEntry 2 }


gdcHdslT1IntervalStats OBJECT-TYPE
        SYNTAX OCTET STRING (SIZE(16))
        ACCESS read-only
        STATUS mandatory
        DESCRIPTION
    		" This variable represents stats(ES, SES, UAS, BES,LOFC,CSS.) for T1 interface."
    	::= { gdcHdslT1IntervalEntry 3}


-- ********************************************************************
-- HDSL T1 Total Performance Tables	  // applicable for T1 interface only
-- ********************************************************************
-- The T1 Total Table contains the cumulative sum of the
-- various statistics for the 24 hour period preceding the
-- current interval.

gdcHdslT1TotalTable OBJECT-TYPE
	SYNTAX  SEQUENCE OF GdcHdslT1TotalEntry
        ACCESS  not-accessible
        STATUS  mandatory
        DESCRIPTION
	"The GDC HDSL Total Performance table.  Information 
	 in the entries of this table support the HDSL 
	 Scheduled Performance Reports. 24 hour interval."
        ::= { gdcHdslPerformance 7 }

gdcHdslT1TotalEntry OBJECT-TYPE
        SYNTAX  GdcHdslT1TotalEntry
        ACCESS  not-accessible
        STATUS  mandatory
        DESCRIPTION
           "An entry in the Total table."
        INDEX   { gdcHdslT1TotalIndex }
           ::= { gdcHdslT1TotalTable 1 }

GdcHdslT1TotalEntry ::=
         SEQUENCE {
             gdcHdslT1TotalIndex
                 SCinstance,
             gdcHdslT1TotalStats
                 OCTET STRING
         }

gdcHdslT1TotalIndex OBJECT-TYPE
	SYNTAX  SCinstance
        ACCESS  read-only
        STATUS  mandatory
        DESCRIPTION
    		"The index value which uniquely identifies the interface to
    		which this entry is applicable.  This has the form of a
    		SCinstance which defines the slot, line, drop, and interface,
    		which in this case is T1 interface."
        ::= { gdcHdslT1TotalEntry 1 }

gdcHdslT1TotalStats OBJECT-TYPE
        SYNTAX OCTET STRING (SIZE(16))
        ACCESS read-only
        STATUS mandatory
        DESCRIPTION
                "The number of Total stats encountered  by T1
		 interface in the current 15 minute interval."
        ::= {gdcHdslT1TotalEntry 2 }




-- ********************************************************************
-- GDC HDSL Status Tables
-- ********************************************************************

-- Loop Status Table.  This table pertains to the Loop interfaces only.

gdcHdslLoopStatusTable OBJECT-TYPE
	SYNTAX	SEQUENCE OF GdcHdslLoopStatusEntry
	ACCESS	not-accessible
	STATUS	mandatory
	DESCRIPTION
		"The table describes the Status objects for 
		the loops and references the loop interfaces (cc = 02-04)."
	::= { gdcHdslStatus 1  }

gdcHdslLoopStatusEntry OBJECT-TYPE
	SYNTAX	GdcHdslLoopStatusEntry
	ACCESS	not-accessible
	STATUS	mandatory
	DESCRIPTION
		"An entry in the GDC HDSL Status Configuration Table."
        INDEX   { gdcHdslLoopStatusLineIndex }
	::= { gdcHdslLoopStatusTable 1 }

GdcHdslLoopStatusEntry ::=
	SEQUENCE {
            gdcHdslLoopStatusLineIndex
				SCinstance,
			gdcHdslLoopStartUp
				INTEGER,
			gdcHdslLoopTipRingReversalMode
				INTEGER,
			gdcHdslLoopSignaltoNoiseMargin
				INTEGER,
			gdcHdslLoopSNFrac
				INTEGER,
			gdcHdslLoopSNAttenSense
				INTEGER,
			gdcHdslLoopPulseAtten
				INTEGER,
			gdcHdslLoopPulseAttenFrac
				INTEGER,
			gdcHdslLoopGain 
				INTEGER,
			gdcHdslLoopExchange
				INTEGER
		}

gdcHdslLoopStatusLineIndex OBJECT-TYPE
	SYNTAX	SCinstance
	ACCESS	read-only
	STATUS	mandatory
	DESCRIPTION
		"This object identifies Status parameters associated
		with the managed object."
	::= { gdcHdslLoopStatusEntry 1 }

gdcHdslLoopStartUp 	OBJECT-TYPE
	SYNTAX	INTEGER {
			norm(1),
			start(2),
			cancel(3)
		}
	ACCESS	read-write
	STATUS	mandatory
	DESCRIPTION
		" Supports the action of initializing HDSL loop startup sequence.
		When set to start(2), HDSL unit will reinitialize the start up sequence.
		When set to cancel(3), the unit will abort the start up sequence.
		When set to norm(1), the unit will operate normal."

	::= { gdcHdslLoopStatusEntry 2 }

gdcHdslLoopTipRingReversalMode 	OBJECT-TYPE
	SYNTAX	INTEGER {
			norm(1),
			reversed(2)
		}
	ACCESS	read-only
	STATUS	mandatory
	DESCRIPTION
                "Signals the loop Tip and Ring status.
		When norm(1), loop operates normal.
		When reverse(2), loop Tip and Ring have been reversed.  "
	::= { gdcHdslLoopStatusEntry 3 }

gdcHdslLoopSignaltoNoiseMargin 	OBJECT-TYPE
	SYNTAX	INTEGER ( 0..127 )
	ACCESS	read-only
	STATUS	mandatory
	DESCRIPTION
              " Represents the loop signal to noise margin in dB units."
	::= { gdcHdslLoopStatusEntry 4 }

gdcHdslLoopSNFrac 	OBJECT-TYPE
	SYNTAX	INTEGER ( 0..5 )
	ACCESS	read-only
	STATUS	mandatory
	DESCRIPTION
              " This variable is used to be used with the 
		gdcHdslLoopSignaltoNoiseMargin variable if the following 
		manor:
		  a) Only the values 0 and 5 are allowed.
		  b) The value of zero means gdcHdslLoopSignaltoNoiseMargin
		     is a whole number.
		  c) The value of five means gdcHdslLoopSignaltoNoiseMargin
		     is a real number and that 0.5 must be added to it."
	::= { gdcHdslLoopStatusEntry 5 }

gdcHdslLoopSNAttenSense		OBJECT-TYPE
	SYNTAX INTEGER {
			positive(1),
			negative(2)
			}
	ACCESS read-only
	STATUS mandatory
	DESCRIPTION
		" This variable identifies the sense of the
		  gdcHdslLoopSignaltoNoiseMargin variable. "
	::= { gdcHdslLoopStatusEntry 6 }

gdcHdslLoopPulseAtten 	OBJECT-TYPE
	SYNTAX  INTEGER	( 0..100)
	ACCESS  read-only
	STATUS  mandatory
	DESCRIPTION
                " Represents twice the HDSL loop Pulse Attenuation level 
                  in dB units."
	::= { gdcHdslLoopStatusEntry 7 }

gdcHdslLoopPulseAttenFrac 	OBJECT-TYPE
	SYNTAX	INTEGER ( 0..5 )
	ACCESS	read-only
	STATUS	mandatory
	DESCRIPTION
              " This variable is used to be used with the 
		gdcHdslLoopPulseAtten variable if the following 
		manor:
		  a) Only the values 0 and 5 are allowed.
		  b) The value of zero means gdcHdslLoopPulseAtten
		     is a whole number.
		  c) The value of five means gdcHdslLoopPulseAtten
		     is a real number and that 0.5 must be added to it."
	::= { gdcHdslLoopStatusEntry 8 }

gdcHdslLoopGain OBJECT-TYPE
	SYNTAX	INTEGER {
			low(1),
			high(2),
			ok(3)
		}
        ACCESS  read-only
      	STATUS  mandatory
       	DESCRIPTION
                  " Represents the HDSL loop gain setting. "
	::= { gdcHdslLoopStatusEntry 9 }

gdcHdslLoopExchange OBJECT-TYPE
	SYNTAX	INTEGER {
			norm(1),
			exchange(2)
		}
        ACCESS  read-only
      	STATUS  mandatory
       	DESCRIPTION
                    " This variable is used to represent the HDSL loop status.
		When the value is returned to norm(1), HDSL loops are correctly
		connected. 
		When the value is returned as exchange(2), the HDSl loop has been
		interchange by error."
	::= { gdcHdslLoopStatusEntry 10 } 

--*****************************************************************
-- DTE STATUS TABLE
--*****************************************************************
-- The DteStatusTable pertains to the DTE interface only

gdcHdslDteStatusTable OBJECT-TYPE
	SYNTAX SEQUENCE OF GdcHdslDteStatusEntry
	ACCESS not-accessible
	STATUS mandatory
	DESCRIPTION
     		"The GDC DTE Status table.  "
	::= { gdcHdslStatus 2 }
 
gdcHdslDteStatusEntry OBJECT-TYPE
	SYNTAX GdcHdslDteStatusEntry
	ACCESS not-accessible
	STATUS mandatory
	DESCRIPTION
     		"The GDC DTE Configuration table entry. "
	INDEX { gdcHdslDteStatusIndex }
	::= { gdcHdslDteStatusTable 1 }
 
GdcHdslDteStatusEntry ::= 
	SEQUENCE {
 	        	gdcHdslDteStatusIndex 
 				SCinstance,
 			gdcHdslDteDTRstatus
 				INTEGER,
 		        gdcHdslDteDCDstatus
 				INTEGER,
 			gdcHdslDteRTSstatus
 				INTEGER,
 			gdcHdslDteDSRstatus
 				INTEGER,
			gdcHdslDteStatus
				OCTET STRING
     		}

gdcHdslDteStatusIndex OBJECT-TYPE
	SYNTAX SCinstance
	ACCESS read-only
	STATUS mandatory
	DESCRIPTION
     		"The index value which uniquely identifies the interface to
     		which this entry is applicable.  This has the form of a
     		SCinstance which defines the slot, line, drop. "
	::= { gdcHdslDteStatusEntry 1 }
 
gdcHdslDteDTRstatus OBJECT-TYPE
	SYNTAX	INTEGER {
 			off(1),
 			on(2)
 		}
        ACCESS	read-only
        STATUS	mandatory
        DESCRIPTION
 		"DTR EIA status indicator "
        ::={ gdcHdslDteStatusEntry 2 }
 

 gdcHdslDteDCDstatus OBJECT-TYPE
         SYNTAX	INTEGER {
 			off(1),
 			on(2)
 		}
         ACCESS	read-only
         STATUS	mandatory
         DESCRIPTION
 		"CO EIA status indicator "
         ::={ gdcHdslDteStatusEntry 3 }
 
gdcHdslDteRTSstatus OBJECT-TYPE
         SYNTAX	INTEGER {
 			off(1),
 			on(2)
 		}
         ACCESS	read-only
         STATUS	mandatory
         DESCRIPTION
 		"RTS EIA indicator"
         ::={ gdcHdslDteStatusEntry 4 }

gdcHdslDteDSRstatus OBJECT-TYPE
         SYNTAX	INTEGER {
 			off(1),
 			on(2)
 		}
         ACCESS	read-only
         STATUS	mandatory
         DESCRIPTION
 		"DSR EIA indicator"
         ::={ gdcHdslDteStatusEntry 5 }
 
gdcHdslDteStatus	OBJECT-TYPE	
	 SYNTAX		OCTET STRING (SIZE(1))
         ACCESS	read-only
         STATUS	mandatory
         DESCRIPTION
			"Dte leads status
		P1.7 not used
		  .6 EIA DCD
		  .5 EIA DTR
		  .4 EIA RTS
		  .3 EIA DSR
		  .2 not used
		  .1 not used
		  .0 not used     "

         ::={ gdcHdslDteStatusEntry 6 } 

-- ********************************************************************
-- GDC HDSL Fractionalization
-- ********************************************************************

hdslFracTable OBJECT-TYPE
	SYNTAX  SEQUENCE OF HdslFracEntry
        ACCESS  not-accessible
        STATUS  mandatory
        DESCRIPTION
                "The DS1 Fractional table."
        ::= { gdcFractional 1 }

hdslFracEntry OBJECT-TYPE
        SYNTAX  HdslFracEntry
        ACCESS  not-accessible
        STATUS  mandatory
        DESCRIPTION
                "An entry in the DS1 Fractional table."
        INDEX   { hdslFracIndex }
        ::= { hdslFracTable 1 }

HdslFracEntry ::=
        SEQUENCE {
             hdslFracIndex
                 SCinstance,
             channelmapping
                 INTEGER,
	     gdcHdslHighway
		 INTEGER,
             gdcHdslTimeSlot16
                 INTEGER
--           numberofTimeSlots
--                 INTEGER
         }

hdslFracIndex OBJECT-TYPE
        SYNTAX SCinstance
        ACCESS read-only
        STATUS mandatory
        DESCRIPTION
     		"The index value which uniquely identifies the interface to
     		which this entry is applicable.  This has the form of a
     		SCinstance which defines the slot, line, drop. "
        ::= { hdslFracEntry 1 }

channelmapping OBJECT-TYPE
        SYNTAX  INTEGER 
        ACCESS  read-write
        STATUS  mandatory
        DESCRIPTION
                "The object contains the channel mapping for multipoint. Time slot 0 is used
		  in all loops.

		P1.8 f/u
		P1.7 \
		P1.6  \
		P1.5   \
		P1.4    \   This byte contains the starting time slot
		P1.3    /
		P1.2   /
		P1.1  /
		P1.0 /

		P2.8 f/u
		P2.7 \
		P2.6  \
		P2.5   \
		P2.4    \   This byte contains the number of consecutive time slots
		P2.3    /
		P2.2   /
		P2.1  /
		P2.0 /"

        ::= { hdslFracEntry 2 }

gdcHdslHighway      OBJECT-TYPE
    SYNTAX INTEGER {
        notAssigned(1),
        highway1(2),
        highway2(3),
        highway3(4),
        highway4(5),
        highway5(6),
        highway6(7),
        highway7(8),
        highway8(9)
       }
    ACCESS read-write
    STATUS mandatory
    DESCRIPTION
        "Object to select the data highway for Loop n."
    ::= { hdslFracEntry 3 }

gdcHdslTimeSlot16  OBJECT-TYPE
    SYNTAX INTEGER {
               used(1),
               skipped(2)
    }
    ACCESS read-write
    STATUS mandatory
    DESCRIPTION
        "Object to select if Time Slot 16 is being used either to pass data,
         or skipped from passing any data for Loop n."
    ::= { hdslFracEntry 4 }

--numberofTimeSlots OBJECT-TYPE
--        SYNTAX  INTEGER (1..18)
--        ACCESS  read-write
--        STATUS  mandatory
--        DESCRIPTION
--                "Number of consecutive time slots for this entry."
--        ::= { hdslFracEntry 3 }

--*****************************************************************************
--       Alarm Config  Table FOR New Products.(currently SC710D2 is supported)
--*****************************************************************************
hdslAlarmConfigTable OBJECT-TYPE
     SYNTAX SEQUENCE OF HdslAlarmConfigEntry
     ACCESS not-accessible
     STATUS mandatory
     DESCRIPTION
	 "The hdslAlarmConfigTable contains entries that configure alarm
	 reporting.  The structure of the table is such that alarm
	 configuration is supported on a unit and interface basis, and
	 then on an alarm type basis within the interface.  For
	 simplicity sake alarms, be they unit or interface
	 related, are represented in one table."
     ::= { gdcHdslAlarmThresholds 1 }

hdslAlarmConfigEntry OBJECT-TYPE
     SYNTAX HdslAlarmConfigEntry
     ACCESS not-accessible
     STATUS mandatory
     DESCRIPTION
	 "An entry in the hdslAlarmConfigTable table."
     INDEX { hdslAlarmConfigIndex, hdslAlarmConfigIdentifier }
    ::= { hdslAlarmConfigTable 1 }

HdslAlarmConfigEntry ::=
     SEQUENCE {
	 hdslAlarmConfigIndex
     SCinstance,
	 hdslAlarmConfigIdentifier
	     OBJECT IDENTIFIER,
	 hdslAlarmThreshold
	     INTEGER
	     }

hdslAlarmConfigIndex OBJECT-TYPE
     SYNTAX SCinstance
     ACCESS read-only
     STATUS mandatory
     DESCRIPTION
	 "The index value which uniquely identifies the interface to
	 which this entry is applicable."
     ::= { hdslAlarmConfigEntry 1 }

hdslAlarmConfigIdentifier OBJECT-TYPE
     SYNTAX OBJECT IDENTIFIER
     ACCESS read-only
     STATUS mandatory
     DESCRIPTION
	 "The unique alarm identifier assigned to this alarm type.
	 The format of this identifier is an OBJECT IDENTIFIER that has
	 the following format: {iso(1) org(3) dod(6) internet(1)
	 private(4) enterprises(1) gdc(498) xxx(x) alarm(z) yyy(y) 
	 where xxx(x) is the administratively assigned family object 
	 identifier (z) is the object identifier for alarms in the family
	 defined MIB and yyy(y) is the administratively assigned alarm 
	 type identifier for this alarm."
     ::= { hdslAlarmConfigEntry 2 }

hdslAlarmThreshold OBJECT-TYPE
    SYNTAX INTEGER {
			thres1E04(1),
			thres1E05(2),
			thres1E06(3),
			thres1E07(4),
			thres1E08(5)
--			thres1E09(6)
		}
	ACCESS  read-write
	STATUS  mandatory
	DESCRIPTION
		"This function sets/reads the Major or Minor BER alarm threshold criteria."
   ::= { hdslAlarmConfigEntry 3 }

END
