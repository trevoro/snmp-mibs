--
-- OPCD-CONNECTORS-MIB-V2
-- Last Modified: Oct 10, 2007
--


OPCD-CONNECTORS-MIB-V2 DEFINITIONS ::= BEGIN


--  OPCD-CONNECTORS-MIB:
--    A private enterprise mib for Opencode connector applications.


IMPORTS
	MODULE-IDENTITY, OBJECT-TYPE, NOTIFICATION-TYPE, enterprises	FROM SNMPv2-SMI
	DisplayString							FROM SNMPv2-TC
	opencode-systems 					      	FROM OPCD-SUPPORT-MIB-V2;



--  opencode ussdbrowser branch: 30374.16
--  opencode ussdbrowser traps branch: 30374.16.1

occonnectors		OBJECT IDENTIFIER ::= { opencode-systems 16 }
occonnectors-traps	OBJECT IDENTIFIER ::= { occonnectors 1 }

definitions 		OBJECT IDENTIFIER ::= { occonnectors-traps 0 }
vars	 		OBJECT IDENTIFIER ::= { occonnectors-traps 1 }




--
-- Node definitions
--




mcr-Host OBJECT-TYPE
	SYNTAX DisplayString (SIZE (0..255))
	MAX-ACCESS accessible-for-notify
	STATUS current
	DESCRIPTION
		"String containing hostname of fault node."
	::= { vars 1 }


mcr-Severity OBJECT-TYPE
	SYNTAX INTEGER{
		critical(1),
		major(2),
		minor(3),
		normal(4),
		warning(5)
	}
	MAX-ACCESS accessible-for-notify
	STATUS mandatory
	DESCRIPTION
		"Alarm severity."
	::= { vars 2 }


mcr-Text OBJECT-TYPE
	SYNTAX DisplayString (SIZE (0..255))
	MAX-ACCESS accessible-for-notify
	STATUS current
	DESCRIPTION
		"String containing text of the alarm."
	::= { vars 3 }


--
-- Traps
--
------------------------------------------------------------------------------------------
-----------------------------------------------------------------------------------------------


-- USSD Browser External connectors 
	
-- 1.3.6......0.2
occonectors-LdapConnector NOTIFICATION-TYPE
	OBJECTS	{ mcr-Host, mcr-Severity, mcr-Text}	
	STATUS	current
	DESCRIPTION	"LDAP Connector is down!"
	--#SUMMARY   "Alarm on host: $1 (connectors application) :  $3"
	--#CATEGORY  "Error Alarms"
        --#ARGUMENTS {}
        --#SEVERITY  CRITICAL
	::= { definitions 2 }


-- 1.3.6......0.3
occonectors-LdapConnector-Canceled NOTIFICATION-TYPE
	OBJECTS	{ mcr-Host, mcr-Severity, mcr-Text}	
	STATUS	current
	DESCRIPTION	"LDAP Connector is down-Canceled"
	--#SUMMARY   "Alarm on host: $1 (connectors application) :  $3"
	--#CATEGORY  "Error Alarms"
        --#ARGUMENTS {}
        --#SEVERITY  NORMAL
	::= { definitions 3 }


-- 1.3.6......0.4
occonectors-MmlConnector NOTIFICATION-TYPE
	OBJECTS	{ mcr-Host, mcr-Severity, mcr-Text}	
	STATUS  current
	DESCRIPTION  "MML Connector is down!"
	--#SUMMARY   "Alarm on host: $1 (connectors application) :  $3"
	--#CATEGORY  "Error Alarms"
        --#ARGUMENTS {}
        --#SEVERITY  CRITICAL
	::= { definitions 4 }


-- 1.3.6......0.5
occonectors-MmlConnector-Canceled NOTIFICATION-TYPE
	OBJECTS	{ mcr-Host, mcr-Severity, mcr-Text}	
	STATUS  current
	DESCRIPTION  "MML Connector is down-Canceled"
	--#SUMMARY   "Alarm on host: $1 (connectors application) :  $3"
	--#CATEGORY  "Error Alarms"
        --#ARGUMENTS {}
        --#SEVERITY  NORMAL
	::= { definitions 5 }


-- 1.3.6......0.6
occonectors-UcpConnector NOTIFICATION-TYPE
	OBJECTS	{ mcr-Host, mcr-Severity, mcr-Text}	
	STATUS  current
	DESCRIPTION  "UCP Connector is down!"
	--#SUMMARY   "Alarm on host: $1 (connectors application) :  $3"
	--#CATEGORY  "Error Alarms"
        --#ARGUMENTS {}
        --#SEVERITY  CRITICAL
	::= { definitions 6 }


-- 1.3.6......0.7
occonectors-UcpConnector-Canceled NOTIFICATION-TYPE
	OBJECTS	{ mcr-Host, mcr-Severity, mcr-Text}	
	STATUS  current
	DESCRIPTION  "UCP Connector is down-Canceled"
	--#SUMMARY   "Alarm on host: $1 (connectors application) :  $3"
	--#CATEGORY  "Error Alarms"
        --#ARGUMENTS {}
        --#SEVERITY  NORMAL
	::= { definitions 7 }

-- 1.3.6......0.8
occonectors-UcipConnector NOTIFICATION-TYPE
	OBJECTS	{ mcr-Host, mcr-Severity, mcr-Text}	
	STATUS  current
	DESCRIPTION  "UCIP Connector is down!"
	--#SUMMARY   "Alarm on host: $1 (connectors application) :  $3"
	--#CATEGORY  "Error Alarms"
        --#ARGUMENTS {}
        --#SEVERITY  CRITICAL
	::= { definitions 8 }


-- 1.3.6......0.9
occonectors-UcipConnector-Canceled NOTIFICATION-TYPE
	OBJECTS	{ mcr-Host, mcr-Severity, mcr-Text}	
	STATUS  current
	DESCRIPTION  "UCIP Connector is down-Canceled"
	--#SUMMARY   "Alarm on host: $1 (connectors application) :  $3"
	--#CATEGORY  "Error Alarms"
        --#ARGUMENTS {}
        --#SEVERITY  NORMAL
	::= { definitions 9 }


-- 1.3.6......0.10
occonectors-CaiConnector NOTIFICATION-TYPE
	OBJECTS	{ mcr-Host, mcr-Severity, mcr-Text}	
	STATUS  current
	DESCRIPTION  "CAI Connector is down!"
	--#SUMMARY   "Alarm on host: $1 (connectors application) :  $3"
	--#CATEGORY  "Error Alarms"
        --#ARGUMENTS {}
        --#SEVERITY  CRITICAL
	::= { definitions 10 }


-- 1.3.6......0.11
occonectors-CaiConnector-Canceled NOTIFICATION-TYPE
	OBJECTS	{ mcr-Host, mcr-Severity, mcr-Text}	
	STATUS  current
	DESCRIPTION  "CAI Connector is down-Canceled"
	--#SUMMARY   "Alarm on host: $1 (connectors application) :  $3"
	--#CATEGORY  "Error Alarms"
        --#ARGUMENTS {}
        --#SEVERITY  NORMAL
	::= { definitions 11 }

-- 1.3.6......0.12
occonectors-SoapConnectorTimeout NOTIFICATION-TYPE
	OBJECTS	{ mcr-Host, mcr-Severity, mcr-Text}	
	STATUS  current
	DESCRIPTION  "SOAP connector timeout."
	--#SUMMARY   "Alarm on host: $1 (connectors application) :  $3"
	--#CATEGORY  "Error Alarms"
        --#ARGUMENTS {}
        --#SEVERITY  CRITICAL
	::= { definitions 12 }


-- 1.3.6......0.13
occonectors-SoapConnectorTimeout-Canceled NOTIFICATION-TYPE
	OBJECTS	{ mcr-Host, mcr-Severity, mcr-Text}	
	STATUS  current
	DESCRIPTION  "SOAP connector timeout-Canceled"
	--#SUMMARY   "Alarm on host: $1 (connectors application) :  $3"
	--#CATEGORY  "Error Alarms"
        --#ARGUMENTS {}
        --#SEVERITY  NORMAL
	::= { definitions 13 }


-- 1.3.6......0.14
occonectors-SoapConnectorLimit NOTIFICATION-TYPE
	OBJECTS	{ mcr-Host, mcr-Severity, mcr-Text}	
	STATUS  current
	DESCRIPTION  "SOAP connector session limit is exceeded."
	--#SUMMARY   "Alarm on host: $1 (connectors application) :  $3"
	--#CATEGORY  "Error Alarms"
        --#ARGUMENTS {}
        --#SEVERITY  CRITICAL
	::= { definitions 14 }


-- 1.3.6......0.15
occonectors-SoapConnectorLimit-Canceled NOTIFICATION-TYPE
	OBJECTS	{ mcr-Host, mcr-Severity, mcr-Text}	
	STATUS  current
	DESCRIPTION  "SOAP connector session limit is exceeded-Canceled"
	--#SUMMARY   "Alarm on host: $1 (connectors application) :  $3"
	--#CATEGORY  "Error Alarms"
        --#ARGUMENTS {}
        --#SEVERITY  NORMAL
	::= { definitions 15 }


-- 1.3.6......0.16
occonectors-CorbaSib NOTIFICATION-TYPE
	OBJECTS	{ mcr-Host, mcr-Severity, mcr-Text}	
	STATUS  current
	DESCRIPTION  "Cannot connect to CORBA-CIB server."
	--#SUMMARY   "Alarm on host: $1 (connectors application) :  $3"
	--#CATEGORY  "Error Alarms"
        --#ARGUMENTS {}
        --#SEVERITY  CRITICAL
	::= { definitions 16 }


-- 1.3.6......0.17
occonectors-CorbaSib-Canceled NOTIFICATION-TYPE
	OBJECTS	{ mcr-Host, mcr-Severity, mcr-Text}	
	STATUS  current
	DESCRIPTION  "Cannot connect to CORBA-CIB server-Canceled"
	--#SUMMARY   "Alarm on host: $1 (connectors application) :  $3"
	--#CATEGORY  "Error Alarms"
        --#ARGUMENTS {}
        --#SEVERITY  NORMAL
	::= { definitions 17 }


-- 1.3.6......0.18
occonectors-CorbaSmaf NOTIFICATION-TYPE
	OBJECTS	{ mcr-Host, mcr-Severity, mcr-Text}	
	STATUS  current
	DESCRIPTION  "Cannot connect to CORBA-SMAF server."
	--#SUMMARY   "Alarm on host: $1 (connectors application) :  $3"
	--#CATEGORY  "Error Alarms"
        --#ARGUMENTS {}
        --#SEVERITY  CRITICAL
	::= { definitions 18 }

-- 1.3.6......0.19
occonectors-CorbaSmaf-Canceled NOTIFICATION-TYPE
	OBJECTS	{ mcr-Host, mcr-Severity, mcr-Text}	
	STATUS  current
	DESCRIPTION  "Cannot connect to CORBA-SMAF server-Canceled"
	--#SUMMARY   "Alarm on host: $1 (connectors application) :  $3"
	--#CATEGORY  "Error Alarms"
        --#ARGUMENTS {}
        --#SEVERITY  NORMAL
	::= { definitions 19 }


-- 1.3.6......0.20
occonectors-CorbaSih NOTIFICATION-TYPE
	OBJECTS	{ mcr-Host, mcr-Severity, mcr-Text}	
	STATUS  current
	DESCRIPTION  "Cannot connect to CORBA-SIH server."
	--#SUMMARY   "Alarm on host: $1 (connectors application) :  $3"
	--#CATEGORY  "Error Alarms"
        --#ARGUMENTS {}
        --#SEVERITY  CRITICAL
	::= { definitions 20 }


-- 1.3.6......0.21
occonectors-CorbaSih-Canceled NOTIFICATION-TYPE
	OBJECTS	{ mcr-Host, mcr-Severity, mcr-Text}	
	STATUS  current
	DESCRIPTION  "Cannot connect to CORBA-SIH server-Canceled"
	--#SUMMARY   "Alarm on host: $1 (connectors application) :  $3"
	--#CATEGORY  "Error Alarms"
        --#ARGUMENTS {}
        --#SEVERITY  NORMAL
	::= { definitions 21 }


-- 1.3.6......0.22
occonectors-XMLConnectorTimeout NOTIFICATION-TYPE
	OBJECTS	{ mcr-Host, mcr-Severity, mcr-Text}	
	STATUS  current
	DESCRIPTION  "XML connector timeout."
	--#SUMMARY   "Alarm on host: $1 (connectors application) :  $3"
	--#CATEGORY  "Error Alarms"
        --#ARGUMENTS {}
        --#SEVERITY  CRITICAL
	::= { definitions 22 }

-- 1.3.6......0.23
occonectors-XMLConnectorTimeout-Canceled NOTIFICATION-TYPE
	OBJECTS	{ mcr-Host, mcr-Severity, mcr-Text}	
	STATUS  current
	DESCRIPTION  "XML connector timeout-Canceled"
	--#SUMMARY   "Alarm on host: $1 (connectors application) :  $3"
	--#CATEGORY  "Error Alarms"
        --#ARGUMENTS {}
        --#SEVERITY  NORMAL
	::= { definitions 23 }


-- 1.3.6......0.24
occonectors-XMLConnectorLimit NOTIFICATION-TYPE
	OBJECTS	{ mcr-Host, mcr-Severity, mcr-Text}	
	STATUS  current
	DESCRIPTION  "XML connector session limit is exceeded."
	--#SUMMARY   "Alarm on host: $1 (connectors application) :  $3"
	--#CATEGORY  "Error Alarms"
        --#ARGUMENTS {}
        --#SEVERITY  CRITICAL
	::= { definitions 24 }


-- 1.3.6......0.25
occonectors-XMLConnectorLimit-Canceled NOTIFICATION-TYPE
	OBJECTS	{ mcr-Host, mcr-Severity, mcr-Text}	
	STATUS  current
	DESCRIPTION  "XML connector session limit is exceeded-Canceled"
	--#SUMMARY   "Alarm on host: $1 (connectors application) :  $3"
	--#CATEGORY  "Error Alarms"
        --#ARGUMENTS {}
        --#SEVERITY  NORMAL
	::= { definitions 25 }


-- 1.3.6......0.26
occonectors-ORACLEConnector NOTIFICATION-TYPE
	OBJECTS	{ mcr-Host, mcr-Severity, mcr-Text}	
	STATUS  current
	DESCRIPTION  "Oracle connector is down"
	--#SUMMARY   "Alarm on host: $1 (connectors application) :  $3"
	--#CATEGORY  "Error Alarms"
        --#ARGUMENTS {}
        --#SEVERITY  CRITICAL
	::= { definitions 26 }


-- 1.3.6......0.27
occonectors-ORACLEConnector-Canceled NOTIFICATION-TYPE
	OBJECTS	{ mcr-Host, mcr-Severity, mcr-Text}	
	STATUS  current
	DESCRIPTION  "Oracle connector is down-Canceled"
	--#SUMMARY   "Alarm on host: $1 (connectors application) :  $3"
	--#CATEGORY  "Error Alarms"
        --#ARGUMENTS {}
        --#SEVERITY  NORMAL
	::= { definitions 27 }


-- 1.3.6......0.28
occonectors-MYSQL-connector-CONNECT NOTIFICATION-TYPE
        OBJECTS	{ mcr-Host, mcr-Severity, mcr-Text}	
	    STATUS  current
        DESCRIPTION  "No connection to MYSQL server


		      1.Check the connector's log file in order to find the reason for this alarm.
		      2.Check if there is ping to MySQL server.
		      3.Check MySQL logs for the possible reason for refusing connections from the connector"
        --#SUMMARY   "Alarm on host: $1 (connectors application) :  $3"
        --#CATEGORY  "Error Alarms"
        --#ARGUMENTS {}
        --#SEVERITY  CRITICAL
        ::= { definitions 28 }


-- 1.3.6......0.29
occonectors-MYSQL-connector-CONNECT-Canceled NOTIFICATION-TYPE
        OBJECTS	{ mcr-Host, mcr-Severity, mcr-Text}	
	    STATUS  current
        DESCRIPTION  "No connection to MYSQL server-Canceled"
        --#SUMMARY   "Alarm on host: $1 (connectors application) :  $3"
        --#CATEGORY  "Error Alarms"
        --#ARGUMENTS {}
        --#SEVERITY  NORMAL
        ::= { definitions 29 }


-- 1.3.6......0.30
occonectors-SMPP-SERVER-connector-CONNECT NOTIFICATION-TYPE
        OBJECTS	{ mcr-Host, mcr-Severity, mcr-Text}	
	    STATUS  current
        DESCRIPTION  "No connection to SMPP server


		      	1.Check the connector's log file in order to find the reason for this alarm.
		      	2.Check if there is ping to SMPP server.
			3.Check SMPP server logs for the possible reason for refusing connections from the connector"
        --#SUMMARY   "Alarm on host: $1 (connectors application) :  $3"
        --#CATEGORY  "Error Alarms"
        --#ARGUMENTS {}
        --#SEVERITY  CRITICAL
        ::= { definitions 30 }


-- 1.3.6......0.31
occonectors-SMPP-SERVER-connector-CONNECT-Canceled NOTIFICATION-TYPE
        OBJECTS	{ mcr-Host, mcr-Severity, mcr-Text}	
	    STATUS  current
        DESCRIPTION  "No connection to SMPP server-Canceled"
        --#SUMMARY   "Alarm on host: $1 (connectors application) :  $3"
        --#CATEGORY  "Error Alarms"
        --#ARGUMENTS {}
        --#SEVERITY  NORMAL
        ::= { definitions 31 }


-- 1.3.6......0.32
occonectors-TELNET-connector-CONNECT NOTIFICATION-TYPE
        OBJECTS	{ mcr-Host, mcr-Severity, mcr-Text}	
	    STATUS  current
        DESCRIPTION  "No connection to TELNET server
		      	1.Check the connector's log file in order to find the reason for this alarm.
		      	2.Check if there is ping to TELNET server.
			3.Check TELNET server logs for the possible reason for refusing connections from the connector"
        --#SUMMARY   "Alarm on host: $1 (connectors application) :  $3"
        --#CATEGORY  "Error Alarms"
        --#ARGUMENTS {}
        --#SEVERITY  CRITICAL
        ::= { definitions 32 }


-- 1.3.6......0.33
occonectors-TELNET-connector-CONNECT-Canceled NOTIFICATION-TYPE
        OBJECTS	{ mcr-Host, mcr-Severity, mcr-Text}	
	    STATUS  current
        DESCRIPTION  "No connection to TELNET server-Canceled"
        --#SUMMARY   "Alarm on host: $1 (connectors application) :  $3"
        --#CATEGORY  "Error Alarms"
        --#ARGUMENTS {}
        --#SEVERITY  NORMAL
        ::= { definitions 33 }



-- 1.3.6......0.34
occonectors-CORBA-SMAF-connector-CONNECT NOTIFICATION-TYPE
        OBJECTS	{ mcr-Host, mcr-Severity, mcr-Text}	
	    STATUS  current
        DESCRIPTION  "No connection to CORBA SMAF server
		      	1.Check the connector's log file in order to find the reason for this alarm.
		      	2.Check if there is ping to CORBA SMAF server.
			3.Check CORBA SMAF server logs for the possible reason for refusing connections from the connector"
        --#SUMMARY   "Alarm on host: $1 (connectors application) :  $3"
        --#CATEGORY  "Error Alarms"
        --#ARGUMENTS {}
        --#SEVERITY  CRITICAL
        ::= { definitions 34 }

-- 1.3.6......0.35
occonectors-CORBA-SMAF-connector-CONNECT-Canceled NOTIFICATION-TYPE
        OBJECTS	{ mcr-Host, mcr-Severity, mcr-Text}	
	    STATUS  current
        DESCRIPTION  "No connection to CORBA SMAF server - Canceled"
        --#SUMMARY   "Alarm on host: $1 (connectors application) :  $3"
        --#CATEGORY  "Error Alarms"
        --#ARGUMENTS {}
        --#SEVERITY  NORMAL
        ::= { definitions 35 }

-- 1.3.6......0.36
occonectors-CORBA-SIH-connector-CONNECT NOTIFICATION-TYPE
        OBJECTS	{ mcr-Host, mcr-Severity, mcr-Text}	
	    STATUS  current
        DESCRIPTION  "No connection to CORBA SIH server
		      	1.Check the connector's log file in order to find the reason for this alarm.
		      	2.Check if there is ping to CORBA SIH server.
			3.Check CORBA SIH server logs for the possible reason for refusing connections from the connector"
        --#SUMMARY   "Alarm on host: $1 (connectors application) :  $3"
        --#CATEGORY  "Error Alarms"
        --#ARGUMENTS {}
        --#SEVERITY  CRITICAL
        ::= { definitions 36 }


-- 1.3.6......0.37
occonectors-CORBA-SIH-connector-CONNECT-Canceled NOTIFICATION-TYPE
        OBJECTS	{ mcr-Host, mcr-Severity, mcr-Text}	
	    STATUS  current
        DESCRIPTION  "No connection to CORBA SIH server-Canceled"
        --#SUMMARY   "Alarm on host: $1 (connectors application) :  $3"
        --#CATEGORY  "Error Alarms"
        --#ARGUMENTS {}
        --#SEVERITY  NORMAL
        ::= { definitions 37 }


-- 1.3.6......0.38
occonectors-CORBA-CX-connector-CONNECT NOTIFICATION-TYPE
        OBJECTS	{ mcr-Host, mcr-Severity, mcr-Text}	
	    STATUS  current
        DESCRIPTION  "No connection to CORBA CX server
		      	1.Check the connector's log file in order to find the reason for this alarm.
		      	2.Check if there is ping to CORBA CX server.
			3.Check CORBA CX server logs for the possible reason for refusing connections from the connector"
        --#SUMMARY   "Alarm on host: $1 (connectors application) :  $3"
        --#CATEGORY  "Error Alarms"
        --#ARGUMENTS {}
        --#SEVERITY  CRITICAL
        ::= { definitions 38 }


-- 1.3.6......0.39
occonectors-CORBA-CX-connector-CONNECT-Canceled NOTIFICATION-TYPE
        OBJECTS	{ mcr-Host, mcr-Severity, mcr-Text}	
	    STATUS  current
        DESCRIPTION  "No connection to CORBA CX server
		      	1.Check the connector's log file in order to find the reason for this alarm.
		      	2.Check if there is ping to CORBA CX server.
			3.Check CORBA CX server logs for the possible reason for refusing connections from the connector"
        --#SUMMARY   "Alarm on host: $1 (connectors application) :  $3"
        --#CATEGORY  "Error Alarms"
        --#ARGUMENTS {}
        --#SEVERITY  NORMAL
        ::= { definitions 39 }


-- 1.3.6......0.40
occonectors-CORBA-CIB-connector-CONNECT NOTIFICATION-TYPE
        OBJECTS	{ mcr-Host, mcr-Severity, mcr-Text}	
	    STATUS  current
        DESCRIPTION  "No connection to CORBA CIB server
		      	1.Check the connector's log file in order to find the reason for this alarm.
		      	2.Check if there is ping to CORBA CIB server.
			3.Check CORBA CIB server logs for the possible reason for refusing connections from the connector"
        --#SUMMARY   "Alarm on host: $1 (connectors application) :  $3"
        --#CATEGORY  "Error Alarms"
        --#ARGUMENTS {}
        --#SEVERITY  CRITICAL
        ::= { definitions 40 }


-- 1.3.6......0.41
occonectors-CORBA-CIB-connector-CONNECT-Canceled NOTIFICATION-TYPE
        OBJECTS	{ mcr-Host, mcr-Severity, mcr-Text}	
	    STATUS  current
        DESCRIPTION  "No connection to CORBA CIB server-Canceled"
        --#SUMMARY   "Alarm on host: $1 (connectors application) :  $3"
        --#CATEGORY  "Error Alarms"
        --#ARGUMENTS {}
        --#SEVERITY  NORMAL
        ::= { definitions 41 }


-- 1.3.6......0.42
occonectors-CORBA-ALCATEL-connector-CONNECT NOTIFICATION-TYPE
        OBJECTS	{ mcr-Host, mcr-Severity, mcr-Text}	
	    STATUS  current
        DESCRIPTION  "No connection to CORBA(Alcatel) server
		      	1.Check the connector's log file in order to find the reason for this alarm.
		      	2.Check if there is ping to CORBA(Alcatel) server.
			3.Check CORBA(Alcatel) server logs for the possible reason for refusing connections from the connector"
        --#SUMMARY   "Alarm on host: $1 (connectors application) :  $3"
        --#CATEGORY  "Error Alarms"
        --#ARGUMENTS {}
        --#SEVERITY  CRITICAL
        ::= { definitions 42 }


-- 1.3.6......0.43
occonectors-CORBA-ALCATEL-connector-CONNECT-Canceled NOTIFICATION-TYPE
        OBJECTS	{ mcr-Host, mcr-Severity, mcr-Text}	
	    STATUS  current
        DESCRIPTION  "No connection to CORBA(Alcatel) server -Canceled"
        --#SUMMARY   "Alarm on host: $1 (connectors application) :  $3"
        --#CATEGORY  "Error Alarms"
        --#ARGUMENTS {}
        --#SEVERITY  NORMAL
        ::= { definitions 43 }


-- 1.3.6......0.44
occonectors-CAI-connector-CONNECT NOTIFICATION-TYPE
        OBJECTS	{ mcr-Host, mcr-Severity, mcr-Text}	
	    STATUS  current
        DESCRIPTION  "No connection to CAI server
		      	1.Check the connector's log file in order to find the reason for this alarm.
		      	2.Check if there is ping to CAI server.
			3.Check CAI server logs for the possible reason for refusing connections from the connector"
        --#SUMMARY   "Alarm on host: $1 (connectors application) :  $3"
        --#CATEGORY  "Error Alarms"
        --#ARGUMENTS {}
        --#SEVERITY  CRITICAL
        ::= { definitions 44 }


-- 1.3.6......0.45
occonectors-CAI-connector-CONNECT-Canceled NOTIFICATION-TYPE
        OBJECTS	{ mcr-Host, mcr-Severity, mcr-Text}	
	    STATUS  current
        DESCRIPTION  "No connection to CAI server
		      	1.Check the connector's log file in order to find the reason for this alarm.
		      	2.Check if there is ping to CAI server.
			3.Check CAI server logs for the possible reason for refusing connections from the connector"
        --#SUMMARY   "Alarm on host: $1 (connectors application) :  $3"
        --#CATEGORY  "Error Alarms"
        --#ARGUMENTS {}
        --#SEVERITY  NORMAL
        ::= { definitions 45 }



-- 1.3.6......0.46
occonectors-BROADCAST-connector-CONNECT NOTIFICATION-TYPE
        OBJECTS	{ mcr-Host, mcr-Severity, mcr-Text}	
	    STATUS  current
        DESCRIPTION  "No connection to MYSQL server


                      1.Check the connector's log file in order to find the reason for this alarm.
                      2.Check if there is ping to MySQL server.
                      3.Check MySQL logs for the possible reason for refusing connections from the connector"
        --#SUMMARY   "Alarm on host: $1 (connectors application) :  $3"
        --#CATEGORY  "Error Alarms"
        --#ARGUMENTS {}
        --#SEVERITY  MAJOR
        ::= { definitions 46 }


-- 1.3.6......0.47
occonectors-BROADCAST-connector-CONNECT-Canceled NOTIFICATION-TYPE
        OBJECTS	{ mcr-Host, mcr-Severity, mcr-Text}	
	    STATUS  current
        DESCRIPTION  "No connection to MYSQL server-Canceled"
        --#SUMMARY   "Alarm on host: $1 (connectors application) :  $3"
        --#CATEGORY  "Error Alarms"
        --#ARGUMENTS {}
        --#SEVERITY  NORMAL
        ::= { definitions 47 }


-- 1.3.6......0.48
occonectors-LDAP-connector-CONNECT NOTIFICATION-TYPE
        OBJECTS	{ mcr-Host, mcr-Severity, mcr-Text}	
	    STATUS  current
        DESCRIPTION  "No connection to LDAP server


                      1.Check the connector's log file in order to find the reason for this alarm.
                      2.Check if there is ping to LDAP server.
                      3.Check LDAP logs for the possible reason for refusing connections from the connector"
        --#SUMMARY   "Alarm on host: $1 (connectors application) :  $3"
        --#CATEGORY  "Error Alarms"
        --#ARGUMENTS {}
        --#SEVERITY  CRITICAL
        ::= { definitions 48 }



-- 1.3.6......0.49
occonectors-LDAP-connector-CONNECT-Canceled NOTIFICATION-TYPE
        OBJECTS	{ mcr-Host, mcr-Severity, mcr-Text}	
	    STATUS  current
        DESCRIPTION  "No connection to LDAP server-Canceled"
        --#SUMMARY   "Alarm on host: $1 (connectors application) :  $3"
        --#CATEGORY  "Error Alarms"
        --#ARGUMENTS {}
        --#SEVERITY  NORMAL
        ::= { definitions 49 }


-- 1.3.6......0.50
occonectors-DIAMETER-connector-CONNECT NOTIFICATION-TYPE
        OBJECTS	{ mcr-Host, mcr-Severity, mcr-Text}	
	    STATUS  current
        DESCRIPTION  "No connection to DIAMETER server


                      1.Check the connector's log file in order to find the reason for this alarm.
                      2.Check if there is ping to DIAMETER server.
                      3.Check DIAMTER server logs for the possible reason for refusing connections from the connector"
        --#SUMMARY   "Alarm on host: $1 (connectors application) :  $3"
        --#CATEGORY  "Error Alarms"
        --#ARGUMENTS {}
        --#SEVERITY  CRITICAL
        ::= { definitions 50 }


-- 1.3.6......0.51
occonectors-DIAMETER-connector-CONNECT-Canceled NOTIFICATION-TYPE
        OBJECTS	{ mcr-Host, mcr-Severity, mcr-Text}	
	    STATUS  current
        DESCRIPTION  "No connection to DIAMETER server-Canceled"
        --#SUMMARY   "Alarm on host: $1 (connectors application) :  $3"
        --#CATEGORY  "Error Alarms"
        --#ARGUMENTS {}
        --#SEVERITY  NORMAL
        ::= { definitions 51 }


-- 1.3.6......0.52
occonectors-HTTPCLIENT-connector-CONNECT NOTIFICATION-TYPE
        OBJECTS	{ mcr-Host, mcr-Severity, mcr-Text}	
	    STATUS  current
        DESCRIPTION  "No connection to HTTP server


                      1.Check the connector's log file in order to find the reason for this alarm.
                      2.Check if there is ping to HTTP server.
                      3.Check HTTP server logs for the possible reason for refusing connections from the connector"
        --#SUMMARY   "Alarm on host: $1 (connectors application) :  $3"
        --#CATEGORY  "Error Alarms"
        --#ARGUMENTS {}
        --#SEVERITY  CRITICAL
        ::= { definitions 52 }


-- 1.3.6......0.53
occonectors-HTTPCLIENT-connector-CONNECT-Canceled NOTIFICATION-TYPE
        OBJECTS	{ mcr-Host, mcr-Severity, mcr-Text}	
	    STATUS  current
        DESCRIPTION  "No connection to HTTP server-Canceled"
        --#SUMMARY   "Alarm on host: $1 (connectors application) :  $3"
        --#CATEGORY  "Error Alarms"
        --#ARGUMENTS {}
        --#SEVERITY  NORMAL
        ::= { definitions 53 }


-- 1.3.6......0.54
occonectors-BOOKMARK-connector-CONNECT NOTIFICATION-TYPE
        OBJECTS	{ mcr-Host, mcr-Severity, mcr-Text}	
	    STATUS  current
        DESCRIPTION  "No connection to MYSQL server


			1.Check the connector's log file in order to find the reason for this alarm.
			2.Check if there is ping to MySQL server.
			3.Check MySQL logs for the possible reason for refusing connections from the
connector"
        --#SUMMARY   "Alarm on host: $1 (connectors application) :  $3"
        --#CATEGORY  "Error Alarms"
        --#ARGUMENTS {}
        --#SEVERITY  CRITICAL
        ::= { definitions 54 }


-- 1.3.6......0.55
occonectors-BOOKMARK-connector-CONNECT-Canceled NOTIFICATION-TYPE
        OBJECTS	{ mcr-Host, mcr-Severity, mcr-Text}	
	    STATUS  current
        DESCRIPTION  "No connection to MYSQL server-Canceled"
        --#SUMMARY   "Alarm on host: $1 (connectors application) :  $3"
        --#CATEGORY  "Error Alarms"
        --#ARGUMENTS {}
        --#SEVERITY  NORMAL
        ::= { definitions 55 }


-- 1.3.6......0.56
occonectors-CORBA-INPAYMENT-connector-CONNECT NOTIFICATION-TYPE
        OBJECTS	{ mcr-Host, mcr-Severity, mcr-Text}	
	    STATUS  current
        DESCRIPTION  "No connection to IN(Payment) server
			1.Check the connector's log file in order to find the reason for this alarm.
			2.Check if there is ping to IN server.
			3.Check IN logs for the possible reason for refusing connections from the
connector"
        --#SUMMARY   "Alarm on host: $1 (connectors application) :  $3"
        --#CATEGORY  "Error Alarms"
        --#ARGUMENTS {}
        --#SEVERITY  CRITICAL
        ::= { definitions 56 }


-- 1.3.6......0.57
occonectors-CORBA-INPAYMENT-connector-CONNECT-Canceled NOTIFICATION-TYPE
        OBJECTS	{ mcr-Host, mcr-Severity, mcr-Text}	
	    STATUS  current
        DESCRIPTION  "No connection to IN(Payment) server-Canceled"
        --#SUMMARY   "Alarm on host: $1 (connectors application) :  $3"
        --#CATEGORY  "Error Alarms"
        --#ARGUMENTS {}
        --#SEVERITY  NORMAL
        ::= { definitions 57 }


-- 1.3.6......0.58
occonectors-CORBA-PPSERVER-connector-CONNECT NOTIFICATION-TYPE
        OBJECTS	{ mcr-Host, mcr-Severity, mcr-Text}	
	    STATUS  current
        DESCRIPTION  "No connection to CORBA PP server
			1.Check the connector's log file in order to find the reason for this alarm.
			2.Check if there is ping to CORBA server.
			3.Check CORBA logs for the possible reason for refusing connections from the
connector"
        --#SUMMARY   "Alarm on host: $1 (connectors application) :  $3"
        --#CATEGORY  "Error Alarms"
        --#ARGUMENTS {}
        --#SEVERITY  CRITICAL
        ::= { definitions 58 }


-- 1.3.6......0.59
occonectors-CORBA-PPSERVER-connector-CONNECT-Canceled NOTIFICATION-TYPE
        OBJECTS	{ mcr-Host, mcr-Severity, mcr-Text}	
	    STATUS  current
        DESCRIPTION  "No connection to CORBA PP server-Canceled"
        --#SUMMARY   "Alarm on host: $1 (connectors application) :  $3"
        --#CATEGORY  "Error Alarms"
        --#ARGUMENTS {}
        --#SEVERITY  NORMAL
        ::= { definitions 59 }


-- 1.3.6......0.60
occonectors-ecm-CONNECTOR-CRASHED NOTIFICATION-TYPE
        OBJECTS	{ mcr-Host, mcr-Severity, mcr-Text}	
	    STATUS  current
        DESCRIPTION  "Connector monitored by ECM crashed"
        --#SUMMARY   "Alarm on host: $1 (connectors application) :  $3"
        --#CATEGORY  "Error Alarms"
        --#ARGUMENTS {}
        --#SEVERITY  MAJOR
        ::= { definitions 60 }

-- 1.3.6......0.61
occonectors-ecm-CONNECTOR-CRASHED-Canceled NOTIFICATION-TYPE
        OBJECTS	{ mcr-Host, mcr-Severity, mcr-Text}	
	    STATUS  current
        DESCRIPTION  "Connector monitored by ECM crashed-Canceled"
        --#SUMMARY   "Alarm on host: $1 (connectors application) :  $3"
        --#CATEGORY  "Error Alarms"
        --#ARGUMENTS {}
        --#SEVERITY  NORMAL
        ::= { definitions 61 }

-- 1.3.6......0.62
occonectors-ecm-CONNECTOR-DISABLED NOTIFICATION-TYPE
        OBJECTS	{ mcr-Host, mcr-Severity, mcr-Text}	
	    STATUS  current
        DESCRIPTION  "Connector disabled."
        --#SUMMARY   "Alarm on host: $1 (connectors application) :  $3"
        --#CATEGORY  "Error Alarms"
        --#ARGUMENTS {}
        --#SEVERITY  WARNING
        ::= { definitions 62 }

-- 1.3.6......0.63
occonectors-ecm-CONNECTOR-DISABLED-Canceled NOTIFICATION-TYPE
        OBJECTS	{ mcr-Host, mcr-Severity, mcr-Text}	
	    STATUS  current
        DESCRIPTION  "Connector disabled-Canceled"
        --#SUMMARY   "Alarm on host: $1 (connectors application) :  $3"
        --#CATEGORY  "Error Alarms"
        --#ARGUMENTS {}
        --#SEVERITY  NORMAL
        ::= { definitions 63 }


-- 1.3.6......0.64
occonectors-MMLAUC-connector-CONNECT NOTIFICATION-TYPE
        OBJECTS	{ mcr-Host, mcr-Severity, mcr-Text}	
	    STATUS  current
        DESCRIPTION  "No connection to MML server"
        --#SUMMARY   "Alarm on host: $1 (connectors application) :  $3"
        --#CATEGORY  "Error Alarms"
        --#ARGUMENTS {}
        --#SEVERITY  MAJOR
        ::= { definitions 64 }


-- 1.3.6......0.65
occonectors-MMLAUC-connector-CONNECT-Canceled NOTIFICATION-TYPE
        OBJECTS	{ mcr-Host, mcr-Severity, mcr-Text}	
	    STATUS  current
        DESCRIPTION  "No connection to MML server"
        --#SUMMARY   "Alarm on host: $1 (connectors application) :  $3"
        --#CATEGORY  "Error Alarms"
        --#ARGUMENTS {}
        --#SEVERITY  NORMAL
        ::= { definitions 65 }


-- 1.3.6......0.66
occonectors-ecm-CONNECTOR-PROBLEM NOTIFICATION-TYPE
        OBJECTS	{ mcr-Host, mcr-Severity, mcr-Text}	
	    STATUS  current
        DESCRIPTION  "The alarm is turned ON if any connector is not working properly: 
			1.all subconnectos or all IPC connections are not working 
			2.it exited unexpectedly 
			3.it is disabled by ECM because of too much retries to start"
        --#SUMMARY   "Alarm on host: $1 (connectors application) :  $3"
        --#CATEGORY  "Error Alarms"
        --#ARGUMENTS {}
        --#SEVERITY  MAJOR
        ::= { definitions 66 }


-- 1.3.6......0.67
occonectors-ecm-CONNECTOR-PROBLEM-Canceled NOTIFICATION-TYPE
        OBJECTS	{ mcr-Host, mcr-Severity, mcr-Text}	
	    STATUS  current
        DESCRIPTION  "The alarm is turned ON if any connector is not working properly: 
			1.all subconnectos or all IPC connections are not working 
			2.it exited unexpectedly 
			3.it is disabled by ECM because of too much retries to start"
        --#SUMMARY   "Alarm on host: $1 (connectors application) :  $3"
        --#CATEGORY  "Error Alarms"
        --#ARGUMENTS {}
        --#SEVERITY  NORMAL
        ::= { definitions 67 }


-- 1.3.6......0.68
mcr-HTTP-SERVER-connector-CONNECT NOTIFICATION-TYPE
        OBJECTS	{ mcr-Host, mcr-Severity, mcr-Text}	
	    STATUS  current
        DESCRIPTION  "The alarm is turned ON if any connector is not working properly: 
			1.all subconnectos or all IPC connections are not working 
			2.it exited unexpectedly 
			3.it is disabled by ECM because of too much retries to start"
        --#SUMMARY   "Alarm on host: $1 (connectors application) :  $3"
        --#CATEGORY  "Error Alarms"
        --#ARGUMENTS {}
        --#SEVERITY  MAJOR
        ::= { definitions 68 }


-- 1.3.6......0.69
mcr-HTTP-SERVER-connector-CONNECT-Canceled NOTIFICATION-TYPE
        OBJECTS	{ mcr-Host, mcr-Severity, mcr-Text}	
	    STATUS  current
        DESCRIPTION  "The alarm is turned ON if any connector is not working properly: 
			1.all subconnectos or all IPC connections are not working 
			2.it exited unexpectedly 
			3.it is disabled by ECM because of too much retries to start"
        --#SUMMARY   "Alarm on host: $1 (connectors application) :  $3"
        --#CATEGORY  "Error Alarms"
        --#ARGUMENTS {}
        --#SEVERITY  NORMAL
        ::= { definitions 69 }


-- 1.3.6......0.70
mcr-SPEECHLAB-TTS-connector-CONNECT NOTIFICATION-TYPE
        OBJECTS	{ mcr-Host, mcr-Severity, mcr-Text}	
	    STATUS  current
        DESCRIPTION  "The alarm is turned ON if any connector is not working properly: 
			1.all subconnectos or all IPC connections are not working 
			2.it exited unexpectedly 
			3.it is disabled by ECM because of too much retries to start"
        --#SUMMARY   "Alarm on host: $1 (connectors application) :  $3"
        --#CATEGORY  "Error Alarms"
        --#ARGUMENTS {}
        --#SEVERITY  MAJOR
        ::= { definitions 70 }

-- 1.3.6......0.71
mcr-SPEECHLAB-TTS-connector-CONNECT-Canceled NOTIFICATION-TYPE
        OBJECTS	{ mcr-Host, mcr-Severity, mcr-Text}	
	     STATUS  current
        DESCRIPTION  "The alarm is turned ON if any connector is not working properly: 
			1.all subconnectos or all IPC connections are not working 
			2.it exited unexpectedly 
			3.it is disabled by ECM because of too much retries to start"
        --#SUMMARY   "Alarm on host: $1 (connectors application) :  $3"
        --#CATEGORY  "Error Alarms"
        --#ARGUMENTS {}
        --#SEVERITY  NORMAL
        ::= { definitions 71 }

-- 1.3.6......0.72
mcr-CIMD2-connector-CONNECT NOTIFICATION-TYPE
        OBJECTS	{ mcr-Host, mcr-Severity, mcr-Text}	
	    STATUS  current
        DESCRIPTION  "The alarm is turned ON if any connector is not working properly: 
			1.all subconnectos or all IPC connections are not working 
			2.it exited unexpectedly 
			3.it is disabled by ECM because of too much retries to start"
        --#SUMMARY   "Alarm on host: $1 (connectors application) :  $3"
        --#CATEGORY  "Error Alarms"
        --#ARGUMENTS {}
        --#SEVERITY  MAJOR
        ::= { definitions 72 }


-- 1.3.6......0.73
mcr-CIMD2-connector-CONNECT-Canceled NOTIFICATION-TYPE
        OBJECTS	{ mcr-Host, mcr-Severity, mcr-Text}	
	    STATUS  current
        DESCRIPTION  "The alarm is turned ON if any connector is not working properly: 
			1.all subconnectos or all IPC connections are not working 
			2.it exited unexpectedly 
			3.it is disabled by ECM because of too much retries to start"
        --#SUMMARY   "Alarm on host: $1 (connectors application) :  $3"
        --#CATEGORY  "Error Alarms"
        --#ARGUMENTS {}
        --#SEVERITY  NORMAL
        ::= { definitions 73 }

-- 1.3.6......0.74
mcr-SOAP-CLIENT-connector-CONNECT NOTIFICATION-TYPE
        OBJECTS	{ mcr-Host, mcr-Severity, mcr-Text}	
	    STATUS  current
        DESCRIPTION  "The alarm is turned ON if any connector is not working properly: 
			1.all subconnectos or all IPC connections are not working 
			2.it exited unexpectedly 
			3.it is disabled by ECM because of too much retries to start"
        --#SUMMARY   "Alarm on host: $1 (connectors application) :  $3"
        --#CATEGORY  "Error Alarms"
        --#ARGUMENTS {}
        --#SEVERITY  MAJOR
        ::= { definitions 74 }

-- 1.3.6......0.75
mcr-SOAP-CLIENT-connector-CONNECT-Canceled NOTIFICATION-TYPE
        OBJECTS	{ mcr-Host, mcr-Severity, mcr-Text}	
	    STATUS  current
        DESCRIPTION  "The alarm is turned ON if any connector is not working properly: 
			1.all subconnectos or all IPC connections are not working 
			2.it exited unexpectedly 
			3.it is disabled by ECM because of too much retries to start"
        --#SUMMARY   "Alarm on host: $1 (connectors application) :  $3"
        --#CATEGORY  "Error Alarms"
        --#ARGUMENTS {}
        --#SEVERITY  NORMAL
        ::= { definitions 75 }


-- 1.3.6......0.76
mcr-BLRATING-connector-CONNECT  NOTIFICATION-TYPE
        OBJECTS	{ mcr-Host, mcr-Severity, mcr-Text}	
	    STATUS  current
        DESCRIPTION  "Alarm of type 'CONNECT' is ON when connector can't
connect to MySQL server or when connected to it and lost connection later. This
alarm is set OFF when connection is restored."
        --#SUMMARY   "Alarm on host: $1 (connectors application) :  $3"
        --#CATEGORY  "Error Alarms"
        --#ARGUMENTS {}
        --#SEVERITY  MAJOR
        ::= { definitions 76 }

-- 1.3.6......0.77
mcr-BLRATING-connector-CONNECT-Canceled  NOTIFICATION-TYPE
        OBJECTS	{ mcr-Host, mcr-Severity, mcr-Text}	
	    STATUS  current
        DESCRIPTION  "Alarm of type 'CONNECT' is ON when connector can't
connect to MySQL server or when connected to it and lost connection later. This
alarm is set OFF when connection is restored."
        --#SUMMARY   "Alarm on host: $1 (connectors application) :  $3"
        --#CATEGORY  "Error Alarms"
        --#ARGUMENTS {}
        --#SEVERITY  NORMAL
        ::= { definitions 77 }

-- 1.3.6......0.78
mcr-DMS-CLIENT-connector-CONNECT  NOTIFICATION-TYPE
        OBJECTS	{ mcr-Host, mcr-Severity, mcr-Text}	
	    STATUS  current
        DESCRIPTION  "Alarm of type 'CONNECT' is ON when connector can't
connect to HTTP server or when connected to it and lost connection later. This alarm is
set OFF when connection is restored."
        --#SUMMARY   "Alarm on host: $1 (connectors application) :  $3"
        --#CATEGORY  "Error Alarms"
        --#ARGUMENTS {}
        --#SEVERITY  MAJOR
        ::= { definitions 78 }

-- 1.3.6......0.79
mcr-DMS-CLIENT-connector-CONNECT-Canceled  NOTIFICATION-TYPE
        OBJECTS	{ mcr-Host, mcr-Severity, mcr-Text}	
	    STATUS  current
        DESCRIPTION  "Alarm of type 'CONNECT' is ON when connector can't
connect to HTTP server or when connected to it and lost connection later. This alarm is
set OFF when connection is restored."
        --#SUMMARY   "Alarm on host: $1 (connectors application) :  $3"
        --#CATEGORY  "Error Alarms"
        --#ARGUMENTS {}
        --#SEVERITY  NORMAL
        ::= { definitions 79 }


-- 1.3.6......0.80
mcr-SMPP-EX-connector-CONNECT  NOTIFICATION-TYPE
        OBJECTS	{ mcr-Host, mcr-Severity, mcr-Text}	
	    STATUS  current
        DESCRIPTION  "- All sessions for all configured clients are broken.
		      - The connector exited unexpectedly.
                      - The connector is disabled by ECM."
        --#SUMMARY   "Alarm on host: $1 (connectors application) :  $3"
        --#CATEGORY  "Error Alarms"
        --#ARGUMENTS {}
        --#SEVERITY  CRITICAL
        ::= { definitions 80 }


-- 1.3.6......0.81
mcr-SMPP-EX-connector-CONNECT-Canceled  NOTIFICATION-TYPE
        OBJECTS	{ mcr-Host, mcr-Severity, mcr-Text}	
	    STATUS  current
        DESCRIPTION  "- The connector has at least one connected session."
        --#SUMMARY   "Alarm on host: $1 (connectors application) :  $3"
        --#CATEGORY  "Error Alarms"
        --#ARGUMENTS {}
        --#SEVERITY  NORMAL
        ::= { definitions 81 }


-- 1.3.6......0.82
mcr-SMPP-EX-connector-CLIENT-SESS  NOTIFICATION-TYPE
        OBJECTS	{ mcr-Host, mcr-Severity, mcr-Text}	
	    STATUS  current
        DESCRIPTION  "- One configured SMPP session is broken."
        --#SUMMARY   "Alarm on host: $1 (connectors application) :  $3"
        --#CATEGORY  "Error Alarms"
        --#ARGUMENTS {}
        --#SEVERITY  MINOR
        ::= { definitions 82 }

-- 1.3.6......0.83
mcr-SMPP-EX-connector-CLIENT-SESS-Canceled  NOTIFICATION-TYPE
        OBJECTS	{ mcr-Host, mcr-Severity, mcr-Text}	
	    STATUS  current
        DESCRIPTION  "- All configured SMPP sessions are connected."
        --#SUMMARY   "Alarm on host: $1 (connectors application) :  $3"
        --#CATEGORY  "Error Alarms"
        --#ARGUMENTS {}
        --#SEVERITY  NORMAL
        ::= { definitions 83 }


-- 1.3.6......0.84
mcr-SMPP-EX-connector-CLIENT-CONN  NOTIFICATION-TYPE
        OBJECTS	{ mcr-Host, mcr-Severity, mcr-Text}	
	    STATUS  current
        DESCRIPTION  "- All sessions for one configured client are broken."
        --#SUMMARY   "Alarm on host: $1 (connectors application) :  $3"
        --#CATEGORY  "Error Alarms"
        --#ARGUMENTS {}
        --#SEVERITY  MAJOR
        ::= { definitions 84 }


-- 1.3.6......0.85
mcr-SMPP-EX-connector-CLIENT-CONN-Canceled  NOTIFICATION-TYPE
        OBJECTS	{ mcr-Host, mcr-Severity, mcr-Text}	
	    STATUS  current
        DESCRIPTION  "- At least one session is connected for this client."
        --#SUMMARY   "Alarm on host: $1 (connectors application) :  $3"
        --#CATEGORY  "Error Alarms"
        --#ARGUMENTS {}
        --#SEVERITY  NORMAL
        ::= { definitions 85 }

-- 1.3.6......0.86
mcr-SMPP-EX-connector-SERVER-CONN  NOTIFICATION-TYPE
        OBJECTS	{ mcr-Host, mcr-Severity, mcr-Text}	
	    STATUS  current
        DESCRIPTION  "- Server cannot be started."
        --#SUMMARY   "Alarm on host: $1 (connectors application) :  $3"
        --#CATEGORY  "Error Alarms"
        --#ARGUMENTS {}
        --#SEVERITY  MAJOR
        ::= { definitions 86 }

-- 1.3.6......0.87
mcr-SMPP-EX-connector-SERVER-CONN-Canceled  NOTIFICATION-TYPE
        OBJECTS	{ mcr-Host, mcr-Severity, mcr-Text}	
	    STATUS  current
        DESCRIPTION  "- Server is started."
        --#SUMMARY   "Alarm on host: $1 (connectors application) :  $3"
        --#CATEGORY  "Error Alarms"
        --#ARGUMENTS {}
        --#SEVERITY  NORMAL
        ::= { definitions 87 }

END


--
-- OPCD-CONNECTORS-MIB-V2
--
