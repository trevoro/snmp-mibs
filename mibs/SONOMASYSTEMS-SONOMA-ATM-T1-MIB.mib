-- |**********************************************************************|
 -- | Copyright 1998 - Sonoma Systems, Inc. Marina del Rey, CA 90292       |
 -- |    Unpublished software - All rights reserved.                       |
 -- |                                                                      |
 -- | The information in this software is subject to change without notice |
 -- | and should not be construed as a commitment by Sonoma Systems, Inc.  |
 -- |                                                                      |
 -- | Sonoma Systems, Inc. assumes no responsibility for the use or        |
 -- | reliability of its software on equipment which is not supplied by    |
 -- | Sonoma Systems, Inc.                                                 |
 -- |                                                                      |
 -- | This software is furnished under a license and may be copied only    |
 -- | under the terms of that license and with the inclusion of this       |
 -- | notice. This software, or any other copies thereof, may not be       |
 -- | provided or otherwise made available to any other person except to   |
 -- | one who agrees to these license terms. Title to and ownership of the |
 -- | software shall at all times remain with Sonoma Systems, Inc.         |
 -- |**********************************************************************|
 --
 -- Sonoma Systems Inc.,
 -- 4640 Admiralty Way, Suite #600,
 -- Marina Del Rey,
 -- California 90292-6695.
 --
 -- Web : www.sonoma-systems.com
 -- Phone:  310.827.8000
 --
 -- NAME        : ds1mib.def
 --
 -- DESCRIPTION : The is the MIB for the Sonoma ATM/DS1 interface.
 --
 -- ARCHIVE : $Archive:   M:\pvcs\pvcsproj\sonoma3\src\mib\ds1mib.dev  $
 -- REVISION: $Revision:   1.6  $
 -- AUTHOR  : $Author:   FREEVE  $
 -- DATE    : $Date:   Nov 13 1998 10:33:24  $

      SONOMASYSTEMS-SONOMA-ATM-T1-MIB DEFINITIONS ::= BEGIN

      IMPORTS
        Counter
        FROM RFC1155-SMI
        OBJECT-TYPE
        FROM RFC-1212
        sonomaATM
        FROM SONOMASYSTEMS-SONOMA-MIB;


    --  This MIB module uses the extended OBJECT-TYPE macro as
    --  defined in [14];
    --
    -- Hierarchy for these groups
    -- enterprises OBJECT IDENTIFIER ::= { private 4 }
    -- sonomaSystems OBJECT IDENTIFIER ::= {  enterprises 2926 }
    -- sonomaSeries OBJECT IDENTIFIER ::= { sonomaSystems 25 }
    -- sonomaATM OBJECT IDENTIFIER ::= { sonomaSeries 7 }
    sonomaT1ATMAdapterGroup OBJECT IDENTIFIER ::= { sonomaATM 5 }
        
    --   Sonoma T1(DS1) ATM Adapter Specific Group MIB groups
      atmDs1ConfGroup OBJECT IDENTIFIER ::= { sonomaT1ATMAdapterGroup 1 }
      atmDs1StatsGroup OBJECT IDENTIFIER ::= { sonomaT1ATMAdapterGroup 2 }

    -- Sonoma T1(DS1) ATM Adapter Specific Group MIB groups

    -- This group contains all informat specificly for
    -- Sonoma Systems DS1 adapter. It includes the configuration and
    -- some statistics information

    --  atmDs1ConfGroup

    atmDs1ConfPhyTable  OBJECT-TYPE
        SYNTAX  SEQUENCE OF AtmDs1ConfPhyEntry
        ACCESS  not-accessible
        STATUS  mandatory
        DESCRIPTION
            "A table of physical layer configuration for the DS1
         interface"
        ::= { atmDs1ConfGroup 1 }

    atmDs1ConfPhyEntry  OBJECT-TYPE
        SYNTAX  AtmDs1ConfPhyEntry
        ACCESS  not-accessible
        STATUS  mandatory
        DESCRIPTION
          "A entry in the table, containing information about the
           physical layer of a DS1 interface"
        INDEX  { atmDs1ConfPhysIndex }
        ::= { atmDs1ConfPhyTable 1 }
    
    AtmDs1ConfPhyEntry ::= SEQUENCE {
      atmDs1ConfPhysIndex     INTEGER,
      atmDs1ConfLoopback      INTEGER,
      atmDs1ConfTxClockSelect   INTEGER,
      atmDs1ConfFillerCells   INTEGER,
      atmDs1ConfLineBuildOut  INTEGER
    }

    atmDs1ConfPhysIndex   OBJECT-TYPE
        SYNTAX  INTEGER
        ACCESS  read-only
        STATUS  mandatory
        DESCRIPTION
            "The physical interface index."
        ::= { atmDs1ConfPhyEntry 1 }   

    atmDs1ConfLoopback OBJECT-TYPE
        SYNTAX  INTEGER { 
                        none(1),
                        payload(2), 
                        line(3),
						local(4)
                        }
        ACCESS  read-write
        STATUS  mandatory
        DESCRIPTION
            "This object is used to modify the state of internal
             loopback...."
          DEFVAL { none }
        ::= { atmDs1ConfPhyEntry 2 }

    atmDs1ConfTxClockSelect OBJECT-TYPE
        SYNTAX  INTEGER {
                        internal(1), 
                        recovered(2) 
                        } 
        ACCESS  read-write
        STATUS  mandatory
        DESCRIPTION
            "Configure the transmit clock."
            DEFVAL { internal }
        ::= { atmDs1ConfPhyEntry 3 }

    atmDs1ConfFillerCells OBJECT-TYPE
        SYNTAX  INTEGER { 
			unassigned(1), 
			idle(2)
			}
        ACCESS  read-write
        STATUS  mandatory
        DESCRIPTION
            "This parameter indicates the type of filler cells to send
             when there are no data cells."
            DEFVAL { unassigned }
        ::= { atmDs1ConfPhyEntry 4 }

    atmDs1ConfLineBuildOut OBJECT-TYPE
        SYNTAX  INTEGER {
			short-haul-0-133-FT(1),	
			short-haul-133-266-FT(2),
			short-haul-266-399-FT(3),
			short-haul-399-533-FT(4),
			short-haul-533-655-FT(5),
            long-haul-0-0-dB(6),
			long-haul-7-5-dB(7),
			long-haul-15-0-dB(8),
			long-haul-22-5-dB(9)
                        }
        ACCESS  read-write
        STATUS  mandatory
        DESCRIPTION
            "This parameter indicates the value selected for the Line Build Out."
            DEFVAL { long-haul-0-0-dB }
        ::= { atmDs1ConfPhyEntry 5 }

    --  atmDs1StatsGroup

    atmDs1StatsTable  OBJECT-TYPE
        SYNTAX  SEQUENCE OF AtmDs1StatsEntry
        ACCESS  not-accessible
        STATUS  mandatory
        DESCRIPTION
            "A table of physical layer statistics information for the DS1 
         interface"
        ::= { atmDs1StatsGroup 1 }

    atmDs1StatsEntry  OBJECT-TYPE
        SYNTAX  AtmDs1StatsEntry
        ACCESS  not-accessible
        STATUS  mandatory
        DESCRIPTION
          "A entry in the table, containing information about the
           physical layer of a DS1 interface"
        INDEX  { atmDs1StatsPhysIndex }
        ::= { atmDs1StatsTable 1 }
    
    AtmDs1StatsEntry ::= SEQUENCE {
      atmDs1StatsPhysIndex      INTEGER,
      atmDs1StatsNoSignals      Counter,
      atmDs1StatsAISDetects     Counter,
      atmDs1StatsYelAlarmCount  Counter,
      atmDs1StatsLCVErrors      Counter,
      atmDs1StatsPCVErrors      Counter,
      atmDs1StatsMOSErrors      Counter,
      atmDs1StatsSyncLossCount  Counter,
      atmDs1StatsHECErrors      Counter,
      atmDs1StatsSignalLoss       INTEGER,
      atmDs1StatsAISDetect        INTEGER,
      atmDs1StatsYellowAlarm      INTEGER,
      atmDs1StatsSyncLoss          INTEGER,
      atmDs1StatsTxClockLoss         INTEGER,
      atmDs1StatsClearCounters     INTEGER
    }

    atmDs1StatsPhysIndex  OBJECT-TYPE
        SYNTAX  INTEGER
        ACCESS  read-only
        STATUS  mandatory
        DESCRIPTION
            "The physical interface index."
        ::= { atmDs1StatsEntry 1 }  

    atmDs1StatsNoSignals  OBJECT-TYPE
        SYNTAX  Counter
        ACCESS  read-only
        STATUS  mandatory
        DESCRIPTION
            "No signal error counter."
        ::= { atmDs1StatsEntry 2 }

    atmDs1StatsAISDetects  OBJECT-TYPE
        SYNTAX  Counter
        ACCESS  read-only
        STATUS  mandatory
        DESCRIPTION
            "AIS Detect counter."
        ::= {atmDs1StatsEntry 3 }
    
    atmDs1StatsYelAlarmCount  OBJECT-TYPE
        SYNTAX  Counter
        ACCESS  read-only
        STATUS  mandatory
        DESCRIPTION
            "A count of the number of Yellow Alarms."
        ::= { atmDs1StatsEntry 4 }

    atmDs1StatsLCVErrors  OBJECT-TYPE
        SYNTAX  Counter
        ACCESS  read-only
        STATUS  mandatory
        DESCRIPTION
            "LCV (Line Code Violation) error counter."
        ::= { atmDs1StatsEntry 5 }

    atmDs1StatsPCVErrors  OBJECT-TYPE
        SYNTAX  Counter
        ACCESS  read-only
        STATUS  mandatory
        DESCRIPTION
            "PCV (Path Code Violation) error counter."
        ::= { atmDs1StatsEntry 6 }

    atmDs1StatsMOSErrors  OBJECT-TYPE
        SYNTAX  Counter
        ACCESS  read-only
        STATUS  mandatory
        DESCRIPTION
            "Multiframe out of sync error counter."
        ::= { atmDs1StatsEntry 7 }

    atmDs1StatsSyncLossCount  OBJECT-TYPE
        SYNTAX  Counter
        ACCESS  read-only
        STATUS  mandatory
        DESCRIPTION
            "Sync Loss counter."
        ::= { atmDs1StatsEntry 8 }

    atmDs1StatsHECErrors  OBJECT-TYPE
        SYNTAX  Counter
        ACCESS  read-only
        STATUS  mandatory
        DESCRIPTION
            "HEC error counter."
        ::= { atmDs1StatsEntry 9 }

    atmDs1StatsSignalLoss  OBJECT-TYPE
        SYNTAX  INTEGER {
                        true (1), 
                        false (2)
                        }
        ACCESS  read-only
        STATUS  mandatory
        DESCRIPTION
            "Signal loss indication."
        ::= { atmDs1StatsEntry 10 }

    atmDs1StatsAISDetect  OBJECT-TYPE
        SYNTAX  INTEGER {
                        true (1), 
                        false (2)
                        }
        ACCESS  read-only
        STATUS  mandatory
        DESCRIPTION
            "AIS indication."
        ::= { atmDs1StatsEntry 11 }

    atmDs1StatsYellowAlarm  OBJECT-TYPE
        SYNTAX  INTEGER {
                        true (1), 
                        false (2)
                        }
        ACCESS  read-only
        STATUS  mandatory
        DESCRIPTION
            "Yellow Alarm indication."
        ::= { atmDs1StatsEntry 12 }

    atmDs1StatsSyncLoss  OBJECT-TYPE
        SYNTAX  INTEGER {
                        true (1), 
                        false (2)
                        }
        ACCESS  read-only
        STATUS  mandatory
        DESCRIPTION
            "Loss of sync indication."
        ::= { atmDs1StatsEntry 13 }

    atmDs1StatsTxClockLoss  OBJECT-TYPE
        SYNTAX  INTEGER {
                        true (1), 
                        false (2)
                        }
        ACCESS  read-only
        STATUS  mandatory
        DESCRIPTION
            "Loss of transmit clock indication."
        ::= { atmDs1StatsEntry 14 }

    atmDs1StatsClearCounters  OBJECT-TYPE
        SYNTAX  INTEGER {
                        true (1), 
                        false (2)
                        }
        ACCESS  read-write
        STATUS  mandatory
        DESCRIPTION
            "Clear all counters in this group ONLY."
        DEFVAL { false }
        ::= { atmDs1StatsEntry 15 }

END
