Nortel-MsCarrier-MscPassport-SubnetInterfaceMIB
DEFINITIONS ::= BEGIN



IMPORTS

      OBJECT-TYPE
   FROM RFC-1212

      mscPassportMIBs
   FROM Nortel-MsCarrier-MscPassport-UsefulDefinitionsMIB

      DisplayString,
      StorageType,
      RowStatus,
      Integer32,
      Unsigned32
   FROM Nortel-MsCarrier-MscPassport-StandardTextualConventionsMIB

      NonReplicated,
      DigitString
   FROM Nortel-MsCarrier-MscPassport-TextualConventionsMIB

      mscMod,
      mscModIndex
   FROM Nortel-MsCarrier-MscPassport-BaseShelfMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     SubnetInterface Enterprise MIB."

subnetInterfaceMIB OBJECT IDENTIFIER ::= { mscPassportMIBs 45 }










-- 
-- ModuleData Vcs
-- ModuleData VirtualCircuitSystem is used to define a number of 
-- general characteristics for all Vcs that originate from or terminate 
-- on a particular module. As an example, the Vc Window matrix is 
-- defined on a module basis to provide the expected virtual circuit 
-- window sizes to associate with all Vcs on the module. All the 
-- modules in the network should have identical VirtualCircuitSystem 
-- attributes. If these attributes are not consistent across the network 
-- applications which need Vc may not be able to establish calls. 

mscModVcs OBJECT IDENTIFIER ::= { mscMod 2 }



mscModVcsRowStatusTable OBJECT-TYPE
   SYNTAX     SEQUENCE OF MscModVcsRowStatusEntry
   ACCESS     not-accessible
   STATUS     mandatory
   DESCRIPTION
     "This entry controls the addition and deletion of 
      mscModVcs components."
::= { mscModVcs 1 }

mscModVcsRowStatusEntry OBJECT-TYPE
   SYNTAX     MscModVcsRowStatusEntry
   ACCESS     not-accessible
   STATUS     mandatory
   DESCRIPTION
     "A single entry in the table represents a single 
      mscModVcs component."
   INDEX {
      mscModIndex,
      mscModVcsIndex }
::= { mscModVcsRowStatusTable 1 }

MscModVcsRowStatusEntry ::= SEQUENCE {
   mscModVcsRowStatus
      RowStatus,
   mscModVcsComponentName
      DisplayString,
   mscModVcsStorageType
      StorageType,
   mscModVcsIndex
      NonReplicated }

mscModVcsRowStatus OBJECT-TYPE
   SYNTAX     RowStatus 
   ACCESS     read-write
   STATUS     mandatory
   DESCRIPTION
     "This variable is used as the basis for SNMP naming of
      mscModVcs components.
      These components can be added and deleted."
::= { mscModVcsRowStatusEntry 1 }

mscModVcsComponentName OBJECT-TYPE
   SYNTAX     DisplayString 
   ACCESS     read-only
   STATUS     mandatory
   DESCRIPTION
     "This variable provides the component's string name for
      use with the ASCII Console Interface"
::= { mscModVcsRowStatusEntry 2 }

mscModVcsStorageType OBJECT-TYPE
   SYNTAX     StorageType 
   ACCESS     read-only
   STATUS     mandatory
   DESCRIPTION
     "This variable represents the storage type value for the
      mscModVcs tables."
::= { mscModVcsRowStatusEntry 4 }

mscModVcsIndex OBJECT-TYPE
   SYNTAX     NonReplicated 
   ACCESS     not-accessible
   STATUS     mandatory
   DESCRIPTION
     "This variable represents the index for the mscModVcs tables."
::= { mscModVcsRowStatusEntry 10 }

mscModVcsAccOptTable OBJECT-TYPE
   SYNTAX     SEQUENCE OF MscModVcsAccOptEntry
   ACCESS     not-accessible
   STATUS     mandatory
   DESCRIPTION
     "Accounting information is owned by the Vc System; it is stored in 
      the Vc Accounting component, which itself is considered to be a 
      component on the switch. The Accounting Component contains a 
      bit map indicating which of the accounting facilities are to be 
      spooled in the accounting record - for example, bit '0' if set 
      indicates that the accounting facility with facility code H.00 should 
      be spooled if present in the Vc for accounting purposes. The data 
      contained in the Vc Accounting must be identical network wide 
      even though the component can be changed and upgraded on a 
      module by module basis."
::= { mscModVcs 10 }

mscModVcsAccOptEntry OBJECT-TYPE
   SYNTAX     MscModVcsAccOptEntry
   ACCESS     not-accessible
   STATUS     mandatory
   DESCRIPTION
     "An entry in the mscModVcsAccOptTable."
   INDEX {
      mscModIndex,
      mscModVcsIndex }
::= { mscModVcsAccOptTable 1 }

MscModVcsAccOptEntry ::= SEQUENCE {
   mscModVcsSegmentSize
      INTEGER,
   mscModVcsUnitsCounted
      INTEGER,
   mscModVcsAccountingFax
      OCTET STRING,
   mscModVcsGenerationMode
      INTEGER }

mscModVcsSegmentSize OBJECT-TYPE
   SYNTAX     INTEGER  {
                 n1(0),
                 n2(1),
                 n4(2),
                 n8(3),
                 n16(4),
                 n32(5),
                 n64(6),
                 n128(7),
                 n256(8),
                 n512(9),
                 n1024(10),
                 n2048(11),
                 n4096(12) }
   ACCESS     read-write
   STATUS     mandatory
   DESCRIPTION
     "This attribute specifies the segment size for accounting of national 
      calls. Minimum allowed segment size is 1. If data segment is sent 
      which is less than segmentSize it is still counted as one segment."
   DEFVAL     { n128 }
::= { mscModVcsAccOptEntry 1 }

mscModVcsUnitsCounted OBJECT-TYPE
   SYNTAX     INTEGER  {
                 segments(0),
                 frames(1) }
   ACCESS     read-write
   STATUS     mandatory
   DESCRIPTION
     "This attribute specifies what is counted by frame services. If set to 
      frames, frames are counted, else segments are counted."
   DEFVAL     { segments }
::= { mscModVcsAccOptEntry 2 }

mscModVcsAccountingFax OBJECT-TYPE
   SYNTAX     OCTET STRING (SIZE (1))
   ACCESS     read-write
   STATUS     mandatory
   DESCRIPTION
     "Each value corresponds to an accounting facility code, of which 
      there are currently 10 facility codes defined with codes H.00 to 
      H.09, and corresponding to the above 10 facilities.
      
      Each of the above facilities may or may not be present and stored in 
      the Vc for accounting purposes, depending on the nature of the call. 
      For example, only those Vcs where a NUI (Network User Identifier) 
      is used for charging or identification purposes will have a NUI 
      stored in the Vc.

      Description of bits:
      notused0(0)
      notused1(1)
      originalCalledAddressFax(2)"
   DEFVAL     { '20'H }
::= { mscModVcsAccOptEntry 3 }

mscModVcsGenerationMode OBJECT-TYPE
   SYNTAX     INTEGER  {
                 bothEnds(0),
                 singleEnd(1) }
   ACCESS     read-write
   STATUS     mandatory
   DESCRIPTION
     "This attribute specifies part of the rules by which the network 
      generates accounting records. If set to bothEnds, then both ends of 
      the Vc generate accounting records. If set to singleEnd, then the 
      charged end of the Vc generates accounting records. In single end 
      generation mode, if the call does not clear gracefully, both ends of 
      the Vc will generate accounting record."
   DEFVAL     { singleEnd }
::= { mscModVcsAccOptEntry 4 }

mscModVcsAddOptTable OBJECT-TYPE
   SYNTAX     SEQUENCE OF MscModVcsAddOptEntry
   ACCESS     not-accessible
   STATUS     mandatory
   DESCRIPTION
     "The Vc AddressingOptions group describes the addressing 
      parameters. It is currently owned by the Vc.
      
      Most of the data contained in the Vc AddressingOptions group is 
      identical network wide even though the group can be changed and 
      upgraded on a module by module basis."
::= { mscModVcs 12 }

mscModVcsAddOptEntry OBJECT-TYPE
   SYNTAX     MscModVcsAddOptEntry
   ACCESS     not-accessible
   STATUS     mandatory
   DESCRIPTION
     "An entry in the mscModVcsAddOptTable."
   INDEX {
      mscModIndex,
      mscModVcsIndex }
::= { mscModVcsAddOptTable 1 }

MscModVcsAddOptEntry ::= SEQUENCE {
   mscModVcsDefaultNumberingPlan
      INTEGER,
   mscModVcsNetworkIdType
      INTEGER,
   mscModVcsX121Type
      INTEGER,
   mscModVcsNetworkIdCode
      DigitString,
   mscModVcsX121IntlAddresses
      INTEGER,
   mscModVcsX121IntllPrefixDigit
      Unsigned32,
   mscModVcsX121MinAddressLength
      Unsigned32,
   mscModVcsX121MaxAddressLength
      Unsigned32,
   mscModVcsX121ToE164EscapeSignificance
      INTEGER,
   mscModVcsE164IntlFormatAllowed
      INTEGER,
   mscModVcsE164IntlPrefixDigits
      DigitString,
   mscModVcsE164NatlPrefixDigit
      Unsigned32,
   mscModVcsE164LocalAddressLength
      Unsigned32,
   mscModVcsE164TeleCountryCode
      DigitString,
   mscModVcsE164NatlMinAddressLength
      Unsigned32,
   mscModVcsE164NatlMaxAddressLength
      Unsigned32,
   mscModVcsE164IntlMinAddressLength
      Unsigned32,
   mscModVcsE164IntlMaxAddressLength
      Unsigned32,
   mscModVcsE164LocalMinAddressLength
      Unsigned32,
   mscModVcsE164LocalMaxAddressLength
      Unsigned32 }

mscModVcsDefaultNumberingPlan OBJECT-TYPE
   SYNTAX     INTEGER  {
                 x121(0),
                 e164(1) }
   ACCESS     read-write
   STATUS     mandatory
   DESCRIPTION
     "This attribute specifies the numbering plan used which determines 
      the address format: X.121-- the international numbering plan for 
      public packet switched data networks or E.164-- the international 
      numbering plan for ISDN and PSTN.
      
      The default numbering plan does not need to be consistent across all 
      of the nodes in the network."
   DEFVAL     { x121 }
::= { mscModVcsAddOptEntry 3 }

mscModVcsNetworkIdType OBJECT-TYPE
   SYNTAX     INTEGER  {
                 dnic(0),
                 inic(1) }
   ACCESS     read-only
   STATUS     mandatory
   DESCRIPTION
     "This attribute specifies whether the network uses a DNIC or INIC. It 
      is used by X.75 Gateways to indicate whether in network the DNIC 
      or INIC is used in various utilities. If it is DNIC it can be DNIC or 
      DCC type. If it is INIC it can be 4 digits only."
   DEFVAL     { dnic }
::= { mscModVcsAddOptEntry 4 }

mscModVcsX121Type OBJECT-TYPE
   SYNTAX     INTEGER  {
                 dnic(0),
                 dcc(1) }
   ACCESS     read-write
   STATUS     mandatory
   DESCRIPTION
     "This attribute specifies whether DNIC mode or DCC mode is used 
      in X.121 address of international calls.
      
      If DCC is specified, then the first 3 digits of each DNA must be the 
      Network ID Code.
      If this attribute is changed all Dnas in the network must start with 
      this code. Numbering plan is affected by the change."
   DEFVAL     { dnic }
::= { mscModVcsAddOptEntry 5 }

mscModVcsNetworkIdCode OBJECT-TYPE
   SYNTAX     DigitString (SIZE (3..4))
   ACCESS     read-write
   STATUS     mandatory
   DESCRIPTION
     "This attribute specifies the DNIC (Data Network ID Code) of the 
      network or DCC code."
::= { mscModVcsAddOptEntry 6 }

mscModVcsX121IntlAddresses OBJECT-TYPE
   SYNTAX     INTEGER  {
                 disallowed(0),
                 allowed(1) }
   ACCESS     read-write
   STATUS     mandatory
   DESCRIPTION
     "This attribute indicates if any DTE is allowed to signal international 
      addresses."
   DEFVAL     { allowed }
::= { mscModVcsAddOptEntry 7 }

mscModVcsX121IntllPrefixDigit OBJECT-TYPE
   SYNTAX     Unsigned32 (0..9)
   ACCESS     read-write
   STATUS     mandatory
   DESCRIPTION
     "This attribute indicates the prefix digit to be used for X.121 
      international calls. When this digit is provided the call will have full 
      international address."
   DEFVAL     { 9 }
::= { mscModVcsAddOptEntry 8 }

mscModVcsX121MinAddressLength OBJECT-TYPE
   SYNTAX     Unsigned32 (1..16)
   ACCESS     read-write
   STATUS     mandatory
   DESCRIPTION
     "This attribute indicates minimum length of x121 address."
   DEFVAL     { 1 }
::= { mscModVcsAddOptEntry 11 }

mscModVcsX121MaxAddressLength OBJECT-TYPE
   SYNTAX     Unsigned32 (1..16)
   ACCESS     read-write
   STATUS     mandatory
   DESCRIPTION
     "This attribute indicates maximum length of x121 address."
   DEFVAL     { 15 }
::= { mscModVcsAddOptEntry 12 }

mscModVcsX121ToE164EscapeSignificance OBJECT-TYPE
   SYNTAX     INTEGER  {
                 no(0),
                 yes(1) }
   ACCESS     read-write
   STATUS     mandatory
   DESCRIPTION
     "This attribute specifies whether an X.121 to E.164 escape digit has 
      significance in selecting an X.32 (analog) or an ISDN switched 
      path. If two values are significant (the value 0 or the value 9) then 
      yes is set to this attribute. If the value of the originally entered 
      escape digit is not significant in routing the call then value of no is 
      assigned to this attribute."
   DEFVAL     { no }
::= { mscModVcsAddOptEntry 13 }

mscModVcsE164IntlFormatAllowed OBJECT-TYPE
   SYNTAX     INTEGER  {
                 disallowed(0),
                 allowed(1) }
   ACCESS     read-write
   STATUS     mandatory
   DESCRIPTION
     "This attribute indicates whether or not to allow national format 
      E.164 addresses. If this attribute is set to a value of Yes (=1) then 
      national format E.164 addresses are not allowed and international 
      format addresses only are allowed. If this attribute is set to a value 
      of No (=0), then national format E.164 addresses are allowed.
      
      If only international format E.164 addresses are allowed, then the 
      'e164NatlPrefixDigit' attribute is not required, nor is the 
      'e164IntlPrefixDigits' required."
   DEFVAL     { allowed }
::= { mscModVcsAddOptEntry 14 }

mscModVcsE164IntlPrefixDigits OBJECT-TYPE
   SYNTAX     DigitString (SIZE (0..3))
   ACCESS     read-write
   STATUS     mandatory
   DESCRIPTION
     "This attribute specifies the E.164 international prefix digits. If 
      applicable, it is specified as 1 to 3 BCD digits.
      
      The 3 BCD digits are stored with the length of the international 
      prefix in the low order nibble, nibble [0] followed by the most 
      significant digit of the international prefix in the next low order 
      nibble, nibble [1], etc.
      
      This attribute is not required if the corresponding attribute, 
      'e164IntlFormatOnly' is set to a value of Yes (=1)."
   DEFVAL     { '30'H }  -- "0"
::= { mscModVcsAddOptEntry 15 }

mscModVcsE164NatlPrefixDigit OBJECT-TYPE
   SYNTAX     Unsigned32 (0..9)
   ACCESS     read-write
   STATUS     mandatory
   DESCRIPTION
     "This attribute contains the E.164 national prefix which may be 
      added in front of E.164 local or national call. If 
      e164IntlFormatOnly is set to 1, this attribute is not needed."
   DEFVAL     { 1 }
::= { mscModVcsAddOptEntry 16 }

mscModVcsE164LocalAddressLength OBJECT-TYPE
   SYNTAX     Unsigned32 (4..15)
   ACCESS     read-write
   STATUS     mandatory
   DESCRIPTION
     "This attribute indicates the length of a local E.164 DNA on this 
      module. This attribute is not required if the corresponding attribute, 
      e164IntlFormatOnly is set to a value of yes.
      
      This attribute does not need to be consistent across all of the nodes 
      in the network."
   DEFVAL     { 7 }
::= { mscModVcsAddOptEntry 17 }

mscModVcsE164TeleCountryCode OBJECT-TYPE
   SYNTAX     DigitString (SIZE (1..4))
   ACCESS     read-write
   STATUS     mandatory
   DESCRIPTION
     "This attribute specifies the E.164 Telephone Country Code (TCC) 
      for the country in which the network resides. If applicable, it is 
      specified as 1 to 3 BCD digits.
      
      The 3 BCD digits are stored with the length of the TCC in the low 
      order nibble, nibble [0] followed by the most significant digit of the 
      TCC in the next low order nibble, nibble [1], etc."
   DEFVAL     { '31'H }  -- "1"
::= { mscModVcsAddOptEntry 18 }

mscModVcsE164NatlMinAddressLength OBJECT-TYPE
   SYNTAX     Unsigned32 (1..16)
   ACCESS     read-write
   STATUS     mandatory
   DESCRIPTION
     "This attribute indicates minimum length of e164 national address."
   DEFVAL     { 1 }
::= { mscModVcsAddOptEntry 20 }

mscModVcsE164NatlMaxAddressLength OBJECT-TYPE
   SYNTAX     Unsigned32 (1..16)
   ACCESS     read-write
   STATUS     mandatory
   DESCRIPTION
     "This attribute indicates maximum length of e164 national address."
   DEFVAL     { 15 }
::= { mscModVcsAddOptEntry 21 }

mscModVcsE164IntlMinAddressLength OBJECT-TYPE
   SYNTAX     Unsigned32 (1..16)
   ACCESS     read-write
   STATUS     mandatory
   DESCRIPTION
     "This attribute indicates minimum length of e164 international 
      address."
   DEFVAL     { 1 }
::= { mscModVcsAddOptEntry 22 }

mscModVcsE164IntlMaxAddressLength OBJECT-TYPE
   SYNTAX     Unsigned32 (1..16)
   ACCESS     read-write
   STATUS     mandatory
   DESCRIPTION
     "This attribute indicates maximum length of e164 international 
      address."
   DEFVAL     { 15 }
::= { mscModVcsAddOptEntry 23 }

mscModVcsE164LocalMinAddressLength OBJECT-TYPE
   SYNTAX     Unsigned32 (1..16)
   ACCESS     read-write
   STATUS     mandatory
   DESCRIPTION
     "This attribute indicates minimum length of e164 local address."
   DEFVAL     { 1 }
::= { mscModVcsAddOptEntry 24 }

mscModVcsE164LocalMaxAddressLength OBJECT-TYPE
   SYNTAX     Unsigned32 (1..16)
   ACCESS     read-write
   STATUS     mandatory
   DESCRIPTION
     "This attribute indicates maximum length of e164 local address."
   DEFVAL     { 15 }
::= { mscModVcsAddOptEntry 25 }

mscModVcsIntOptTable OBJECT-TYPE
   SYNTAX     SEQUENCE OF MscModVcsIntOptEntry
   ACCESS     not-accessible
   STATUS     mandatory
   DESCRIPTION
     "The Vc InterfaceOptions group defines Vc system parameters 
      common in the network. It is owned by the Vc and is considered to 
      be a module wide component on the switch.
      
      The data contained in the Vc InterfaceOptions group must be 
      identical network wide even though this group can be changed and 
      upgraded on a module by module basis."
::= { mscModVcs 13 }

mscModVcsIntOptEntry OBJECT-TYPE
   SYNTAX     MscModVcsIntOptEntry
   ACCESS     not-accessible
   STATUS     mandatory
   DESCRIPTION
     "An entry in the mscModVcsIntOptTable."
   INDEX {
      mscModIndex,
      mscModVcsIndex }
::= { mscModVcsIntOptTable 1 }

MscModVcsIntOptEntry ::= SEQUENCE {
   mscModVcsHighPriorityPacketSizes
      OCTET STRING,
   mscModVcsMaxSubnetPacketSize
      INTEGER,
   mscModVcsCallSetupTimer
      Unsigned32,
   mscModVcsCallRetryTimer
      Unsigned32,
   mscModVcsDelaySubnetAcks
      INTEGER }

mscModVcsHighPriorityPacketSizes OBJECT-TYPE
   SYNTAX     OCTET STRING (SIZE (2))
   ACCESS     read-only
   STATUS     mandatory
   DESCRIPTION
     "This attribute indicates which packet sizes are supported for high 
      priority calls within the network.

      Description of bits:
      n16(0)
      n32(1)
      n64(2)
      n128(3)
      n256(4)
      n512(5)
      n1024(6)
      n2048(7)
      n4096(8)"
   DEFVAL     { 'ff80'H }
::= { mscModVcsIntOptEntry 1 }

mscModVcsMaxSubnetPacketSize OBJECT-TYPE
   SYNTAX     INTEGER  {
                 n16(4),
                 n32(5),
                 n64(6),
                 n128(7),
                 n256(8),
                 n512(9),
                 n1024(10),
                 n2048(11),
                 n4096(12) }
   ACCESS     read-write
   STATUS     mandatory
   DESCRIPTION
     "This attribute specifies the maximum subnet packet size used for the 
      connections originating or terminating on this module. All modules 
      in the same network should have the same maxSubnetPacketSize.
      
      If this value is not identical throughout the network, the following 
      points need to be considered:
      
      a) When Passport and DPN switches are connected in the same 
      network, the maxSubnetPacketSize on a DPN switch can be at most 
      2048 and the DPN part of the network must be configured with 
      hardware which supports this size:
      
      -  Dedicated PE386 Network link/Trunk
      -  Minimum measured link speed of 256Kbits/sec
      
      This hardware has to be present on every potential data path 
      between connecting end points!
      
      b) The calling end of the connection signals the 
      maxSubnetPacketSize value to the called end. The called end then 
      compares this value to its own provisioned value and selects the 
      smaller value. Note that this smaller value is not signalled back to 
      the calling end. The calling and called ends can therefore have 
      different maxSubnetPacketSize values."
   DEFVAL     { n512 }
::= { mscModVcsIntOptEntry 2 }

mscModVcsCallSetupTimer OBJECT-TYPE
   SYNTAX     Unsigned32 (5..100)
   ACCESS     read-write
   STATUS     mandatory
   DESCRIPTION
     "This attribute specifies the Vc callSetupTimer in units of 1 second 
      ticks. This timer specifies how long the Vc will wait, after sending 
      a subnet Call Request packet into the network, for a response from 
      the remote end of the Vc (in the form of a subnet Raccept packet). 
      If, after sending a subnet Call packet into the network, a response is 
      not received within this time period, the Vc will time out, clearing 
      the call in the assumption that the remote end is unreachable. This 
      timer must be long enough to take into account the time required for 
      routing the subnet Call Request through the Source Call Routing 
      and the Destination Call Routing systems in order to be delivered to 
      the final destination."
   DEFVAL     { 5 }
::= { mscModVcsIntOptEntry 3 }

mscModVcsCallRetryTimer OBJECT-TYPE
   SYNTAX     Unsigned32 (30..300)
   ACCESS     read-write
   STATUS     mandatory
   DESCRIPTION
     "This attribute specifies, for Vc implementing Direct Calls with the 
      auto-call retry feature (including PVCs), the Vc callRetryTimer in 
      units of 1 second ticks. This timer specifies how long the Vc will 
      wait between unsuccessful call attempts."
   DEFVAL     { 60 }
::= { mscModVcsIntOptEntry 4 }

mscModVcsDelaySubnetAcks OBJECT-TYPE
   SYNTAX     INTEGER  {
                 no(0),
                 yes(1) }
   ACCESS     read-write
   STATUS     mandatory
   DESCRIPTION
     "This attribute specifies delay acknowledgment timer mechanism.
      If this attribute is set to no, then the Vc will automatically return 
      acknowledgment packets without delay. If this attribute is set to yes, 
      then the Vc will wait for one second in an attempt to piggyback the 
      acknowledgment packet on another credit or data packet. If the Vc 
      cannot piggyback the acknowledgment packet within this time, then 
      the packet is returned without piggybacking."
   DEFVAL     { no }
::= { mscModVcsIntOptEntry 5 }

mscModVcsWinsTable OBJECT-TYPE
   SYNTAX     SEQUENCE OF MscModVcsWinsEntry
   ACCESS     not-accessible
   STATUS     mandatory
   DESCRIPTION
     "This is the windowSize corresponding to the given packet size and 
      throughput class. All Vcs using the windowSize matrix support 
      large Vc windows on both ends of the Vc, and support the signalling 
      of the chosen Vc window size from the destination (called) end to 
      the source (calling) end. This is the only matrix supported.
      The windowSize should be configured in the same way network 
      wide, though it can be upgraded on a module by module basis. Vcs 
      using the windowSize matrix will run properly if the matrices on 
      different nodes differ since the Vc window is selected by the 
      destination (called) side of the Vc."
::= { mscModVcs 213 }

mscModVcsWinsEntry OBJECT-TYPE
   SYNTAX     MscModVcsWinsEntry
   ACCESS     not-accessible
   STATUS     mandatory
   DESCRIPTION
     "An entry in the mscModVcsWinsTable."
   INDEX {
      mscModIndex,
      mscModVcsIndex,
      mscModVcsWinsPktIndex,
      mscModVcsWinsTptIndex }
::= { mscModVcsWinsTable 1 }

MscModVcsWinsEntry ::= SEQUENCE {
   mscModVcsWinsPktIndex
      INTEGER,
   mscModVcsWinsTptIndex
      Integer32,
   mscModVcsWinsValue
      Unsigned32 }

mscModVcsWinsPktIndex OBJECT-TYPE
   SYNTAX     INTEGER  {
                 n16(0),
                 n32(1),
                 n64(2),
                 n128(3),
                 n256(4),
                 n512(5),
                 n1024(6),
                 n2048(7),
                 n4096(8),
                 n8192(9),
                 n32768(10),
                 n65535(11) }
   ACCESS     not-accessible
   STATUS     mandatory
   DESCRIPTION
     "This variable represents the next to last index for the 
      mscModVcsWinsTable."
::= { mscModVcsWinsEntry 1 }

mscModVcsWinsTptIndex OBJECT-TYPE
   SYNTAX     Integer32 (0..15)
   ACCESS     not-accessible
   STATUS     mandatory
   DESCRIPTION
     "This variable represents the final index for the 
      mscModVcsWinsTable."
::= { mscModVcsWinsEntry 2 }

mscModVcsWinsValue OBJECT-TYPE
   SYNTAX     Unsigned32 (1..63)
   ACCESS     read-write
   STATUS     mandatory
   DESCRIPTION
     "This variable represents an individual value for the
      mscModVcsWinsTable."
::= { mscModVcsWinsEntry 3 }




-- 
-- Version and Compliance statements
-- 



-- Object-Group Statement:
-- A list of all current accessible leaf objects.

-- OBJECTS { mscModVcsGenerationMode,
--           mscModVcsE164NatlMinAddressLength,
--           mscModVcsUnitsCounted,
--           mscModVcsAccountingFax,
--           mscModVcsComponentName,
--           mscModVcsNetworkIdType,
--           mscModVcsX121ToE164EscapeSignificance,
--           mscModVcsHighPriorityPacketSizes,
--           mscModVcsE164TeleCountryCode,
--           mscModVcsStorageType,
--           mscModVcsE164LocalMinAddressLength,
--           mscModVcsX121IntlAddresses,
--           mscModVcsSegmentSize,
--           mscModVcsE164IntlPrefixDigits,
--           mscModVcsE164NatlPrefixDigit,
--           mscModVcsX121MinAddressLength,
--           mscModVcsE164NatlMaxAddressLength,
--           mscModVcsCallSetupTimer,
--           mscModVcsX121Type,
--           mscModVcsMaxSubnetPacketSize,
--           mscModVcsE164IntlMaxAddressLength,
--           mscModVcsE164LocalMaxAddressLength,
--           mscModVcsWinsValue,
--           mscModVcsE164IntlMinAddressLength,
--           mscModVcsE164IntlFormatAllowed,
--           mscModVcsNetworkIdCode,
--           mscModVcsRowStatus,
--           mscModVcsDefaultNumberingPlan,
--           mscModVcsX121MaxAddressLength,
--           mscModVcsX121IntllPrefixDigit,
--           mscModVcsE164LocalAddressLength,
--           mscModVcsCallRetryTimer,
--           mscModVcsDelaySubnetAcks }
-- STATUS  mandatory
-- DESCRIPTION
--   "A list of all current accessible leaf objects."

subnetInterfaceGroup OBJECT IDENTIFIER ::= { subnetInterfaceMIB 1 }
subnetInterfaceGroupCA OBJECT IDENTIFIER ::= { subnetInterfaceGroup 1 }
subnetInterfaceGroupCA02 OBJECT IDENTIFIER ::= { subnetInterfaceGroupCA 3 }
subnetInterfaceGroupCA02A OBJECT IDENTIFIER ::= { subnetInterfaceGroupCA02 2 }



-- Agent-Capabilities Statement:

-- PRODUCT-RELEASE "MscPassport Release 1.2 SubnetInterface."
-- STATUS          mandatory
-- DESCRIPTION     "Carrier Passport SubnetInterface MIB: MIB Version CA02A,
--                  Software Version CA02S9C."
-- SUPPORTS        Nortel-MsCarrier-MscPassport-SubnetInterfaceMIB
--    INCLUDES     { subnetInterfaceGroupCA02A }

subnetInterfaceCapabilities OBJECT IDENTIFIER ::= { subnetInterfaceMIB 3 }
subnetInterfaceCapabilitiesCA OBJECT IDENTIFIER ::= { subnetInterfaceCapabilities 1 }
subnetInterfaceCapabilitiesCA02 OBJECT IDENTIFIER ::= { subnetInterfaceCapabilitiesCA 3 }
subnetInterfaceCapabilitiesCA02A OBJECT IDENTIFIER ::= { subnetInterfaceCapabilitiesCA02 2 }





END
