Wellfleet-TELNET-MIB DEFINITIONS ::= BEGIN

-- Created by mdl2asn version 3.1
-- Creation date: Wed Aug 30 16:49:25 EDT 1995


    IMPORTS

      Counter, Gauge
        FROM RFC1155-SMI
      OBJECT-TYPE
        FROM RFC-1212
      DisplayString
        FROM RFC1213-MIB
      wfTelnetGroup
        FROM Wellfleet-COMMON-MIB;


    wfTelnet	OBJECT IDENTIFIER ::= { wfTelnetGroup 1 }

    wfTelnetDelete OBJECT-TYPE
        SYNTAX	INTEGER {
    		    created(1),
    		    deleted(2)
    		}
        ACCESS	read-write
        STATUS	mandatory
        DESCRIPTION
                "Create/Delete parameter. Default is created.
                Users perform a set operation on this
                object in order to create/delete TELNET."
        DEFVAL	{ created }
        ::= { wfTelnet 1 }

    wfTelnetDisable OBJECT-TYPE
        SYNTAX	INTEGER {
    		    enabled(1),
    		    disabled(2)
    		}
        ACCESS	read-write
        STATUS	mandatory
        DESCRIPTION
                "Enables or Disables TELNET Subsystem"
        DEFVAL	{ enabled }
        ::= { wfTelnet 2 }

    wfTelnetLinesPerScreen OBJECT-TYPE
        SYNTAX	INTEGER
        ACCESS	read-write
        STATUS	mandatory
        DESCRIPTION
                "Number of lines which can be displayed in one screen on the Telnet
                Technician Interface console.
                (Default value if NAWS option not negotiated)"
        DEFVAL	{ 24 }
        ::= { wfTelnet 3 }

    wfTelnetMoreDisable OBJECT-TYPE
        SYNTAX	INTEGER {
    		    enabled(1),
    		    disabled(2)
    		}
        ACCESS	read-write
        STATUS	mandatory
        DESCRIPTION
                "Enable the 'more' feature on the Telnet Technician Interface console"
        DEFVAL	{ enabled }
        ::= { wfTelnet 4 }

    wfTelnetPrompt OBJECT-TYPE
        SYNTAX	DisplayString
        ACCESS	read-write
        STATUS	mandatory
        DESCRIPTION
                "Character string which will be used as the system prompt on
                the Telnet Technician Interface console"
        ::= { wfTelnet 5 }

    wfTelnetLoginTimeOut OBJECT-TYPE
        SYNTAX	INTEGER(1..99)
        ACCESS	read-write
        STATUS	mandatory
        DESCRIPTION
                "Time out in minutes to Disconnect when at the login prompt"
        DEFVAL	{ 1 }
        ::= { wfTelnet 6 }

    wfTelnetPasswordTimeOut OBJECT-TYPE
        SYNTAX	INTEGER(1..99)
        ACCESS	read-write
        STATUS	mandatory
        DESCRIPTION
                "Timout in minutes on Password entry"
        DEFVAL	{ 1 }
        ::= { wfTelnet 7 }

    wfTelnetCommandTimeOut OBJECT-TYPE
        SYNTAX	INTEGER(1..99)
        ACCESS	read-write
        STATUS	mandatory
        DESCRIPTION
                "Time out in minutes to Disconnect when at the command prompt"
        DEFVAL	{ 15 }
        ::= { wfTelnet 8 }

    wfTelnetLoginRetries OBJECT-TYPE
        SYNTAX	INTEGER(1..99)
        ACCESS	read-write
        STATUS	mandatory
        DESCRIPTION
                "Limit # of login attempts then Disconnect"
        DEFVAL	{ 3 }
        ::= { wfTelnet 9 }

    wfTelnetTotalLogins OBJECT-TYPE
        SYNTAX	Counter
        ACCESS	read-only
        STATUS	mandatory
        DESCRIPTION
                "Total number of Telnet TI login attempts"
        ::= { wfTelnet 10 }

    wfTelnetUserLoginErrors OBJECT-TYPE
        SYNTAX	Counter
        ACCESS	read-only
        STATUS	mandatory
        DESCRIPTION
                "Total number of FAILED User login attempts"
        ::= { wfTelnet 11 }

    wfTelnetManagerLoginErrors OBJECT-TYPE
        SYNTAX	Counter
        ACCESS	read-only
        STATUS	mandatory
        DESCRIPTION
                "Total number of FAILED Manager login attempts"
        ::= { wfTelnet 12 }

    wfTelnetOtherLoginErrors OBJECT-TYPE
        SYNTAX	Counter
        ACCESS	read-only
        STATUS	mandatory
        DESCRIPTION
                "Total number of FAILED Other login attempts"
        ::= { wfTelnet 13 }

    wfTelnetActiveSessions OBJECT-TYPE
        SYNTAX	Gauge
        ACCESS	read-only
        STATUS	mandatory
        DESCRIPTION
                "Total number of Telnet TI Sessions"
        ::= { wfTelnet 14 }

    wfTelnetDiagnosticReport OBJECT-TYPE
        SYNTAX	INTEGER {
    		    enabled(1),
    		    disabled(2)
    		}
        ACCESS	read-write
        STATUS	mandatory
        DESCRIPTION
                "Diagnostic Flag: report prints the options
                information, plus some additional information about
                what processing is  going  on"
        DEFVAL	{ disabled }
        ::= { wfTelnet 15 }

    wfTelnetDiagnosticExercise OBJECT-TYPE
        SYNTAX	INTEGER {
    		    enabled(1),
    		    disabled(2)
    		}
        ACCESS	read-write
        STATUS	mandatory
        DESCRIPTION
                "Diagnostic Flag: Not implemented yet."
        DEFVAL	{ disabled }
        ::= { wfTelnet 16 }

    wfTelnetDiagnosticNetworkData OBJECT-TYPE
        SYNTAX	INTEGER {
    		    enabled(1),
    		    disabled(2)
    		}
        ACCESS	read-write
        STATUS	mandatory
        DESCRIPTION
                "Diagnostic Flag: NETDATA displays the data
                stream received by telnetd"
        DEFVAL	{ disabled }
        ::= { wfTelnet 17 }

    wfTelnetDiagnosticPtyData OBJECT-TYPE
        SYNTAX	INTEGER {
    		    enabled(1),
    		    disabled(2)
    		}
        ACCESS	read-write
        STATUS	mandatory
        DESCRIPTION
                "Diagnostic Flag: PTYDATA displays data written to the pty"
        DEFVAL	{ disabled }
        ::= { wfTelnet 18 }

    wfTelnetDiagnosticOptions OBJECT-TYPE
        SYNTAX	INTEGER {
    		    enabled(1),
    		    disabled(2)
    		}
        ACCESS	read-write
        STATUS	mandatory
        DESCRIPTION
                "Diagnostic Flag: OPTIONS prints information about
                the negotiation of TELNET options"
        DEFVAL	{ disabled }
        ::= { wfTelnet 19 }

    wfTelnetInitialSearchPath OBJECT-TYPE
        SYNTAX	DisplayString
        ACCESS	read-write
        STATUS	obsolete
        DESCRIPTION
                "Example:  'A:;1:;2:' or '2:;4:6:;9:"
        ::= { wfTelnet 20 }

    wfTelnetManagerAutoScript OBJECT-TYPE
        SYNTAX	DisplayString
        ACCESS	read-write
        STATUS	mandatory
        DESCRIPTION
                "for each login."
        ::= { wfTelnet 21 }

    wfTelnetUserAutoScript OBJECT-TYPE
        SYNTAX	DisplayString
        ACCESS	read-write
        STATUS	mandatory
        DESCRIPTION
                "for each login."
        ::= { wfTelnet 22 }

    wfTelnetUserAbortLogoutDisable OBJECT-TYPE
        SYNTAX	INTEGER {
    		    enabled(1),
    		    disabled(2)
    		}
        ACCESS	read-write
        STATUS	mandatory
        DESCRIPTION
                "a USER from escaping out of the User Autoscript"
        DEFVAL	{ disabled }
        ::= { wfTelnet 23 }

    wfTelnetHistoryDepth OBJECT-TYPE
        SYNTAX	INTEGER(1..40)
        ACCESS	read-write
        STATUS	mandatory
        DESCRIPTION
                "TI command history table size"
        DEFVAL	{ 20 }
        ::= { wfTelnet 24 }

    wfTelnetReverseEnable OBJECT-TYPE
        SYNTAX  INTEGER {
                   enabled(1),
                   disabled(2)
                }
        ACCESS  read-write
        STATUS  mandatory
        DESCRIPTION
                "Reverse Telnet enabled"
        DEFVAL  { disabled }
        ::= { wfTelnet 25 }
 
     wfTelnetReversePort OBJECT-TYPE
        SYNTAX  INTEGER(1..2)
        ACCESS  read-write
        STATUS  mandatory
        DESCRIPTION
                "Console port to use for reverse telnet"
        DEFVAL  { 1 }
        ::= { wfTelnet 26 }


    END  -- Wellfleet-TELNET-MIB
