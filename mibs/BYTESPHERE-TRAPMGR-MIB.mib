-- *****************************************************************
-- BYTESPHERE-TRAPMGR-MIB.my:  ByteSphere TrapMgr mib file
--
-- October 2007, Nicholas W. Saparoff
--
-- Copyright (c) 2007 by BYTESPHERE TECHNOLOGIES LLC
-- All rights reserved.
-- 
-- *****************************************************************
--

-- This MIB describes information about Trap Manager

BYTESPHERE-TRAPMGR-MIB DEFINITIONS ::= BEGIN

IMPORTS
        MODULE-IDENTITY,
        IpAddress,
        OBJECT-TYPE
                FROM SNMPv2-SMI
        bytesphereMgmt
        	FROM BYTESPHERE-SMI;
                

bytesphereTrapMgrMib MODULE-IDENTITY
        LAST-UPDATED        "200710050000Z"
        ORGANIZATION        "ByteSphere Technologies LLC"
        CONTACT-INFO
                "       ByteSphere Technologies LLC
                Postal: 955 Mass Ave #141
                        Cambridge, MA  02139
                        USA

                E-mail: bscustsupt@bytesphere.com"
                
        DESCRIPTION
                "The MIB module to describe OIDs and 
                behavior for the Trap Manager system."
        REVISION        "200710050000Z"
        DESCRIPTION
                "Initial version of this MIB module."
        ::= { bytesphereMgmt 2 }


bytesphereTrapMgrObjects OBJECT IDENTIFIER ::= { bytesphereTrapMgrMib 1 }


trapMgrSourceHost OBJECT-TYPE
        SYNTAX     IpAddress
        MAX-ACCESS read-only
        STATUS     current
        DESCRIPTION
                "The IP Address of the forwarding Trap Manager Host.
                 This object is added into the varbinds when traps
                 are forwarded from Trap Manager to another host."
        ::= { bytesphereTrapMgrObjects 1 }


END
