ORACLE-AGENT-MIB DEFINITIONS ::= BEGIN


IMPORTS
	TRAP-TYPE
		FROM RFC-1215
	DisplayString
		FROM RFC1213-MIB
	OBJECT-TYPE
		FROM RFC-1212
	enterprises
		FROM RFC1155-SMI;

DateAndTime ::= OCTET STRING (SIZE (8 .. 11))

oracle OBJECT IDENTIFIER ::= { enterprises  111 }

oraAgent OBJECT IDENTIFIER ::= { oracle  12 }

oraAgentObjects OBJECT IDENTIFIER ::= { oraAgent  1 }

oraAgentEventTable OBJECT-TYPE
    SYNTAX  SEQUENCE OF OraAgentEventEntry
    ACCESS  not-accessible
    STATUS  mandatory
    DESCRIPTION
           ""
    ::= { oraAgentObjects  1 }

oraAgentEventEntry OBJECT-TYPE
    SYNTAX  OraAgentEventEntry
    ACCESS  not-accessible
    STATUS  mandatory
    DESCRIPTION
           ""
    INDEX   { oraAgentEventIndex }
    ::= { oraAgentEventTable  1 }

OraAgentEventEntry ::=
    SEQUENCE {
        oraAgentEventIndex
            INTEGER,

        oraAgentEventName
            DisplayString,

        oraAgentEventID
            INTEGER,

        oraAgentEventService
            DisplayString,

        oraAgentEventTime
            DateAndTime,

        oraAgentEventSeverity
            INTEGER,

        oraAgentEventUser
            DisplayString,

        oraAgentEventAppID
            INTEGER,

        oraAgentEventMessage
            DisplayString,

        oraAgentEventArguments
            DisplayString,

        oraAgentEventResults
            DisplayString
    }

oraAgentEventIndex OBJECT-TYPE
    SYNTAX  INTEGER
    ACCESS  read-only
    STATUS  mandatory
    DESCRIPTION
           ""
    ::= { oraAgentEventEntry  1 }

oraAgentEventName OBJECT-TYPE
    SYNTAX  DisplayString
    ACCESS  read-only
    STATUS  mandatory
    DESCRIPTION
           "The name of the event that occurred."
    ::= { oraAgentEventEntry  2 }

oraAgentEventID OBJECT-TYPE
    SYNTAX  INTEGER
    ACCESS  read-only
    STATUS  mandatory
    DESCRIPTION
           "The ID of the registration that generated this event occurrence."
    ::= { oraAgentEventEntry  3 }

oraAgentEventService OBJECT-TYPE
    SYNTAX  DisplayString
    ACCESS  read-only
    STATUS  mandatory
    DESCRIPTION
           "The name of the service (database, SQL*Net listener, etc.) 
          being monitored by this event."
    ::= { oraAgentEventEntry  4 }

oraAgentEventTime OBJECT-TYPE
    SYNTAX  DateAndTime
    ACCESS  read-only
    STATUS  mandatory
    DESCRIPTION
           "The time at which this event was detected."
    ::= { oraAgentEventEntry  5 }

oraAgentEventSeverity OBJECT-TYPE
    SYNTAX  INTEGER {
    warning(1),
    alert(2),
    clear(-1)
}
    ACCESS  read-only
    STATUS  mandatory
    DESCRIPTION
           "A relative measure of the severity of the event."
    ::= { oraAgentEventEntry  6 }

oraAgentEventUser OBJECT-TYPE
    SYNTAX  DisplayString
    ACCESS  read-only
    STATUS  mandatory
    DESCRIPTION
           "The name of the user who registered for this event."
    ::= { oraAgentEventEntry  7 }

oraAgentEventAppID OBJECT-TYPE
    SYNTAX  INTEGER
    ACCESS  read-only
    STATUS  mandatory
    DESCRIPTION
           "The ID of the Enterprise Manager console application through
          which this event was registered."
    ::= { oraAgentEventEntry  8 }

oraAgentEventMessage OBJECT-TYPE
    SYNTAX  DisplayString
    ACCESS  read-only
    STATUS  mandatory
    DESCRIPTION
           "<Isn't this always blank right now?>."
    ::= { oraAgentEventEntry  9 }

oraAgentEventArguments OBJECT-TYPE
    SYNTAX  DisplayString
    ACCESS  read-only
    STATUS  mandatory
    DESCRIPTION
           "The arguments that were passed to the script that detected
          this event."
    ::= { oraAgentEventEntry  10 }

oraAgentEventResults OBJECT-TYPE
    SYNTAX  DisplayString
    ACCESS  read-only
    STATUS  mandatory
    DESCRIPTION
           "The results generated by the script that detected this event."
    ::= { oraAgentEventEntry  11 }

oraAgentTraps OBJECT IDENTIFIER ::= { oraAgent  2 }

oraAgentEventOcc TRAP-TYPE
    ENTERPRISE  oraAgentTraps
    VARIABLES   { oraAgentEventName,  oraAgentEventID,  oraAgentEventService,  oraAgentEventTime,  oraAgentEventSeverity,  oraAgentEventUser,  oraAgentEventAppID,  oraAgentEventMessage,  oraAgentEventArguments,  oraAgentEventResults }
    DESCRIPTION
           "The Enterprise Manager agent has detected an occurrence of
           an event for which it has no specific trap."
    ::= 2


END
