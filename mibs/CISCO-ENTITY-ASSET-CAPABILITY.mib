-- *****************************************************************
-- CISCO-ENTITY-ASSET-CAPABILITY MIB
--
-- AGENT-CAPABILITIES mib for CISCO-ENTITY-ASSET-MIB
-- 
--
-- Apr 2003, Kapil Kataria
--
-- Copyright(c) 2003 by Cisco Systems,Inc.
--
-- *****************************************************************

CISCO-ENTITY-ASSET-CAPABILITY DEFINITIONS ::= BEGIN
IMPORTS
        MODULE-IDENTITY
                FROM SNMPv2-SMI
        AGENT-CAPABILITIES
                FROM SNMPv2-CONF
        ciscoAgentCapability
                FROM CISCO-SMI;   

ciscoEntityAssetCapability MODULE-IDENTITY
        LAST-UPDATED    "200304300000Z"
        ORGANIZATION    "Cisco Systems, Inc."
        CONTACT-INFO
                "       Cisco Systems
                        Customer Service

                Postal: 170 W Tasman Drive
                        San Jose, CA  95134
                        USA

                        Tel: +1 800 553-NETS

                E-mail: cs-wanatm@cisco.com"
        DESCRIPTION
            "The Agent Capabilities for Entity Asset
             mib objects."

        REVISION "200304300000Z"
        DESCRIPTION
            "Initial version of this MIB Module."
        ::= { ciscoAgentCapability 300 }

ceAssetCapabilityV4R00 AGENT-CAPABILITIES
    PRODUCT-RELEASE      "MGX8850 Release 4.0.00"
    STATUS               current
    DESCRIPTION          "Entity Asset Agent capabilities for
                          monitoring the asset information of items
			  in the ENTITY-MIB (RFC 2737) entPhysical Table"

    SUPPORTS   CISCO-ENTITY-ASSET-MIB
    INCLUDES   { ceAssetGroup }

    VARIATION  ceAssetOEMString
    ACCESS     not-implemented
    DESCRIPTION
        "Not supported."

    VARIATION  ceAssetSerialNumber
    ACCESS     not-implemented
    DESCRIPTION
        "Not supported."

    VARIATION  ceAssetOrderablePartNumber
    ACCESS     not-implemented
    DESCRIPTION
        "Not supported."

    VARIATION   ceAssetHardwareRevision
    ACCESS      not-implemented
    DESCRIPTION
        "Not supported."

    VARIATION   ceAssetMfgAssyNumber
    ACCESS      not-implemented
    DESCRIPTION
        "Not supported."

    VARIATION   ceAssetMfgAssyRevision
    ACCESS      not-implemented
    DESCRIPTION
        "Not supported."

    VARIATION   ceAssetFirmwareID
    ACCESS      not-implemented
    DESCRIPTION
        "Not supported."

    VARIATION   ceAssetFirmwareRevision
    ACCESS      not-implemented
    DESCRIPTION
        "Not supported."

    VARIATION   ceAssetSoftwareID
    ACCESS      not-implemented
    DESCRIPTION
        "Not supported."

    VARIATION   ceAssetSoftwareRevision
    ACCESS      not-implemented
    DESCRIPTION
        "Not supported."

    VARIATION   ceAssetAlias
    ACCESS      not-implemented
    DESCRIPTION
        "Not supported."

    VARIATION   ceAssetTag
    ACCESS      not-implemented
    DESCRIPTION
        "Not supported."

    VARIATION   ceAssetIsFRU
    ACCESS      not-implemented
    DESCRIPTION
        "Not supported."

   ::= { ciscoEntityAssetCapability 1 }

END
