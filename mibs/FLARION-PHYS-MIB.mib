-- $Id: FLARION-PHYS-MIB.txt,v 1.5 2004/07/14 20:29:51 csmith Exp $



FLARION-PHYS-MIB DEFINITIONS ::= BEGIN

IMPORTS
        MODULE-IDENTITY, OBJECT-TYPE, NOTIFICATION-TYPE,
        IpAddress, TimeTicks, Unsigned32, Counter32
                FROM SNMPv2-SMI

        enterprises
                FROM RFC1155-SMI

        DisplayString, RowStatus, DateAndTime, TruthValue
                FROM SNMPv2-TC

        AdminState, MoType, rrMib, rrManagedObjs, FloatAsString,
        rrBaseBandUnit
                FROM FLARION-MIB;


rrPhyShelf              OBJECT IDENTIFIER ::= { rrMib 3 }
rrPaShelf               OBJECT IDENTIFIER ::= { rrMib 4 }

rrChassis               OBJECT IDENTIFIER ::= { rrManagedObjs 8 }


-- chassis type
ChassisType ::= INTEGER {
    chassisUnknown(0),
    chassisCpciIndoor(1),
    chassisCpciOutdoor(2),
    chassisEnetIndoor(3),
    chassisEnetOutdoor(4)
}


-- Relay state
RelayState ::= INTEGER {
    relayUnknown(0),
    relayOpen(1),
    relayClosed(2)
}

-- Card operational state
CardOpState ::= INTEGER {
    cardOpStateUnknown(0),
    cardOpStateNotPresent(1),
    cardOpStateStandby(2),
    cardOpStateActive(3),
    cardOpStateDown(4)
}

-- Card fault LED colors
CardFaultLed ::= INTEGER {
    faultLedUnknown(0),
    faultLedRed(1),
    faultLedOrange(2),
    faultLedGreen(3)
}

-- Card temperature status
CardTempStatus ::= INTEGER {
    tempUnknown(0),
    tempNominal(1),
    tempHigh(2),
    tempSevere(3),
    tempCritical(4)
}

-- Card voltage status
CardVoltageStatus ::= INTEGER {
    voltageUnknown(0),
    voltageNominal(1),
    voltageLow(2),
    voltageHigh(3)
}

-- RF band
RfBand ::= INTEGER {
    rfBandUnknown(0),
    rfBandUpper700MHz(1),
    rfBandLow800MHz(2),
    rfBandCellBand(3),
    rfBandSmrBand(4),
    rfBandPcsKorea(5),
    rfBandPcsUs(6),
    rfBandUmts(7),
    rfBand2P3GHz(8),
    rfBandMmds(9)
}


-- PowerAmp RF band
PaRfBand ::= INTEGER {
    paRfBandUnknown(0),
    paRfBand747to770MHz(1),
    paRfBand861to894MHz(2),
    paRfBand1930to1990MHz(3),
    paRfBand2370to2400MHz(4),
    paRfBand2110to2170MHz(5),
    paRfBand2620to2686MHz(6),
    paRfBand740Mto746Hz(7)
}

-- PowerAmp Operational State
PaState ::= INTEGER {
    paStateUnknown(0),
    paStateProbing(1),
    paStateNotPresent(2),
    paStateDisabledByPa(3),
    paStateDisabledByBts(4),
    paStateEnabling(5),
    paStateEnabled(6),
    paStateDisabling(7)
}

-- Assembly Id source
AssemblyIdSource ::= INTEGER {
    aidSourceUnknown(0),
    aidSourceDatabase(1),
    aidSourceTarget(2)
}


--
-- Chassis
--
rrChassisType           OBJECT-TYPE
        SYNTAX          ChassisType
        MAX-ACCESS      read-only
        STATUS          deprecated
        DESCRIPTION     "The chassis revision."
        ::= { rrChassis 1 }

rrChassisRev            OBJECT-TYPE
        SYNTAX          DisplayString
        MAX-ACCESS      read-only
        STATUS          deprecated
        DESCRIPTION     "The chassis revision."
        ::= { rrChassis 2 }

rrChassisMaxSlots       OBJECT-TYPE
        SYNTAX          INTEGER
        MAX-ACCESS      read-only
        STATUS          deprecated
        DESCRIPTION     "Maximum number of slots in the chassis."
        ::= { rrChassis 3 }

rrChassisNumCards       OBJECT-TYPE
        SYNTAX          INTEGER
        MAX-ACCESS      read-only
        STATUS          deprecated
        DESCRIPTION     "Number of cards detected in the chassis."
        ::= { rrChassis 4 }

rrChassisTable          OBJECT-TYPE
        SYNTAX          SEQUENCE OF RrChassisTableEntry
        MAX-ACCESS      not-accessible
        STATUS          current
        DESCRIPTION     "Table containing chassis card information."
        ::= { rrChassis 5 }

rrChassisTableEntry     OBJECT-TYPE
        SYNTAX          RrChassisTableEntry
        MAX-ACCESS      not-accessible
        STATUS          current
        DESCRIPTION     "RadioRouter chassis card table entry."
        INDEX           { rrChassisSlotId }
        ::= { rrChassisTable 1 }

RrChassisTableEntry ::= SEQUENCE {
        rrChassisSlotId         INTEGER,
        rrChassisSlotHwType     MoType,
        rrChassisSlotHwName     DisplayString,
        rrChassisSlotHwStatus   CardOpState,
        rrChassisSlotHwVer      DisplayString,
        rrChassisSlotHwEsn      OCTET STRING,
        rrChassisSlotSwVer      DisplayString
}

rrChassisSlotId         OBJECT-TYPE
        SYNTAX          INTEGER
        MAX-ACCESS      read-only
        STATUS          current
        DESCRIPTION     "The chassis slot of the card."
        ::= { rrChassisTableEntry 1 }

rrChassisSlotHwType     OBJECT-TYPE
        SYNTAX          MoType
        MAX-ACCESS      read-only
        STATUS          current
        DESCRIPTION     "The card type."
        ::= { rrChassisTableEntry 2 }

rrChassisSlotHwName     OBJECT-TYPE
        SYNTAX          DisplayString
        MAX-ACCESS      read-only
        STATUS          current
        DESCRIPTION     "The card name."
        ::= { rrChassisTableEntry 3 }

rrChassisSlotHwStatus   OBJECT-TYPE
        SYNTAX          CardOpState
        MAX-ACCESS      read-only
        STATUS          current
        DESCRIPTION     "The card hardware operational status."
        ::= { rrChassisTableEntry 4 }

rrChassisSlotHwVer      OBJECT-TYPE
        SYNTAX          DisplayString
        MAX-ACCESS      read-only
        STATUS          current
        DESCRIPTION     "The card hardware version number."
        ::= { rrChassisTableEntry 5 }

rrChassisSlotHwEsn      OBJECT-TYPE
        SYNTAX          OCTET STRING (SIZE(8))
        MAX-ACCESS      read-only
        STATUS          current
        DESCRIPTION     "The card Electronic Serial Number."
        ::= { rrChassisTableEntry 6 }

rrChassisSlotSwVer      OBJECT-TYPE
        SYNTAX          DisplayString
        MAX-ACCESS      read-only
        STATUS          current
        DESCRIPTION     "The card IPMI (Intelligent Platform Management Interface)
                        firmware version number."
        ::= { rrChassisTableEntry 8 }


--
-- Physical Layout
--
phyChassisType      OBJECT-TYPE
    SYNTAX          ChassisType
    MAX-ACCESS      read-only
    STATUS          current
    DESCRIPTION     "Chassis type."
    ::= { rrPhyShelf 1 }

phySerialNumber     OBJECT-TYPE
    SYNTAX          DisplayString
    MAX-ACCESS      read-only
    STATUS          current
    DESCRIPTION     "Chassis serial number."
    ::= { rrPhyShelf 2 }

phyProductionDate   OBJECT-TYPE
    SYNTAX          DisplayString
    MAX-ACCESS      read-only
    STATUS          current
    DESCRIPTION     "Chassis production date (mm/dd/yyyy)."
    ::= { rrPhyShelf 3 }

phyPartNumber       OBJECT-TYPE
    SYNTAX          DisplayString
    MAX-ACCESS      read-only
    STATUS          current
    DESCRIPTION     "Chassis part number."
    ::= { rrPhyShelf 4 }

phyHardwareVersion  OBJECT-TYPE
    SYNTAX          DisplayString
    MAX-ACCESS      read-only
    STATUS          current
    DESCRIPTION     "Chassis hardware version."
    ::= { rrPhyShelf 5 }

phyChassisRfBand    OBJECT-TYPE
    SYNTAX          RfBand
    MAX-ACCESS      read-only
    STATUS          current
    DESCRIPTION     "Chassis RF band."
    ::= { rrPhyShelf 6 }

phyAssemblyId       OBJECT-TYPE
    SYNTAX          DisplayString
    MAX-ACCESS      read-only
    STATUS          current
    DESCRIPTION     "Chassis assembly ID."
    ::= { rrPhyShelf 7 }

--
-- Fan Table
--
phyFanTable         OBJECT-TYPE
    SYNTAX          SEQUENCE OF PhyFanEntry
    MAX-ACCESS      not-accessible
    STATUS          current
    DESCRIPTION     ""
    ::= { rrPhyShelf 10 }

phyFanEntry         OBJECT-TYPE
    SYNTAX          PhyFanEntry
    MAX-ACCESS      not-accessible
    STATUS          current
    DESCRIPTION     ""
    INDEX           { phyFanIndex }
    ::= { phyFanTable 1 }

PhyFanEntry ::= SEQUENCE {
    phyFanIndex     INTEGER,
    phyFanOk        TruthValue
}

phyFanIndex         OBJECT-TYPE
    SYNTAX          INTEGER
    MAX-ACCESS      read-only
    STATUS          current
    DESCRIPTION     "Fan index."
    ::= { phyFanEntry 1 }

phyFanOk            OBJECT-TYPE
    SYNTAX          TruthValue
    MAX-ACCESS      read-only
    STATUS          current
    DESCRIPTION     "Fan status."
    ::= { phyFanEntry 2 }

--
-- Relay Table
--
phyRelayTable       OBJECT-TYPE
    SYNTAX          SEQUENCE OF PhyRelayEntry
    MAX-ACCESS      not-accessible
    STATUS          current
    DESCRIPTION     ""
    ::= { rrPhyShelf 11 }

phyRelayEntry       OBJECT-TYPE
    SYNTAX          PhyRelayEntry
    MAX-ACCESS      not-accessible
    STATUS          current
    DESCRIPTION     ""
    INDEX           { phyRelayIndex }
    ::= { phyRelayTable 1 }

PhyRelayEntry ::= SEQUENCE {
    phyRelayIndex   INTEGER,
    phyRelayName    DisplayString,
    phyRelayState   RelayState
}

phyRelayIndex       OBJECT-TYPE
    SYNTAX          INTEGER
    MAX-ACCESS      read-only
    STATUS          current
    DESCRIPTION     "Relay index."
    ::= { phyRelayEntry 1 }

phyRelayName        OBJECT-TYPE
    SYNTAX          DisplayString
    MAX-ACCESS      read-write
    STATUS          current
    DESCRIPTION     "Relay name."
    ::= { phyRelayEntry 2 }

phyRelayState       OBJECT-TYPE
    SYNTAX          RelayState
    MAX-ACCESS      read-only
    STATUS          current
    DESCRIPTION     "Relay state."
    ::= { phyRelayEntry 3 }

--
-- Alarm Input Table
--
phyAlarmInputTable  OBJECT-TYPE
    SYNTAX          SEQUENCE OF PhyAlarmInputEntry
    MAX-ACCESS      not-accessible
    STATUS          current
    DESCRIPTION     ""
    ::= { rrPhyShelf 12 }

phyAlarmInputEntry  OBJECT-TYPE
    SYNTAX          PhyAlarmInputEntry
    MAX-ACCESS      not-accessible
    STATUS          current
    DESCRIPTION     ""
    INDEX           { phyAlarmInputIndex }
    ::= { phyAlarmInputTable 1 }

PhyAlarmInputEntry ::= SEQUENCE {
    phyAlarmInputIndex      INTEGER,
    phyAlarmInputEnable     TruthValue,
    phyAlarmInputName       DisplayString,
    phyAlarmInputState      TruthValue
}

phyAlarmInputIndex  OBJECT-TYPE
    SYNTAX          INTEGER
    MAX-ACCESS      read-only
    STATUS          current
    DESCRIPTION     "AlarmInput index."
    ::= { phyAlarmInputEntry 1 }

phyAlarmInputEnable OBJECT-TYPE
    SYNTAX          TruthValue
    MAX-ACCESS      read-write
    STATUS          current
    DESCRIPTION     "AlarmInput enable."
    ::= { phyAlarmInputEntry 2 }

phyAlarmInputName   OBJECT-TYPE
    SYNTAX          DisplayString
    MAX-ACCESS      read-write
    STATUS          current
    DESCRIPTION     "AlarmInput name."
    ::= { phyAlarmInputEntry 3 }

phyAlarmInputState  OBJECT-TYPE
    SYNTAX          TruthValue
    MAX-ACCESS      read-only
    STATUS          current
    DESCRIPTION     "AlarmInput state."
    ::= { phyAlarmInputEntry 4 }

--
-- Power Controller Unit (PCU) Table
--
phyPcuTable         OBJECT-TYPE
    SYNTAX          SEQUENCE OF PhyPcuEntry
    MAX-ACCESS      not-accessible
    STATUS          current
    DESCRIPTION     ""
    ::= { rrPhyShelf 13 }

phyPcuEntry         OBJECT-TYPE
    SYNTAX          PhyPcuEntry
    MAX-ACCESS      not-accessible
    STATUS          current
    DESCRIPTION     ""
    INDEX           { phyPcuIndex }
    ::= { phyPcuTable 1 }

PhyPcuEntry ::= SEQUENCE {
    phyPcuIndex             INTEGER,
    phyPcuPowerFail         TruthValue
}

phyPcuIndex         OBJECT-TYPE
    SYNTAX          INTEGER
    MAX-ACCESS      read-only
    STATUS          current
    DESCRIPTION     "PCU index."
    ::= { phyPcuEntry 1 }

phyPcuPowerFail     OBJECT-TYPE
    SYNTAX          TruthValue
    MAX-ACCESS      read-only
    STATUS          current
    DESCRIPTION     "PCU power fail."
    ::= { phyPcuEntry 2 }

--
-- Alarm Interface Unit (AIU) Table
--
phyAiuTable         OBJECT-TYPE
    SYNTAX          SEQUENCE OF PhyAiuEntry
    MAX-ACCESS      not-accessible
    STATUS          current
    DESCRIPTION     ""
    ::= { rrPhyShelf 14 }

phyAiuEntry         OBJECT-TYPE
    SYNTAX          PhyAiuEntry
    MAX-ACCESS      not-accessible
    STATUS          current
    DESCRIPTION     ""
    INDEX           { phyAiuIndex }
    ::= { phyAiuTable 1 }

PhyAiuEntry ::= SEQUENCE {
    phyAiuIndex             INTEGER,
    phyAiuOpState           CardOpState,
    phyAiuFaultLed          CardFaultLed,
    phyAiuTempStatus        CardTempStatus,
    phyAiuVoltageStatus     CardVoltageStatus,
    phyAiuSerialNumber      DisplayString,
    phyAiuProductionDate    DisplayString,
    phyAiuPartNumber        DisplayString,
    phyAiuDescription       DisplayString,
    phyAiuHardwareVersion   DisplayString,
    phyAiuIpmiSwVersion     DisplayString,
    phyAiuAssemblyId        DisplayString,
    phyAiuAssemblyIdSrc     AssemblyIdSource,
    phyAiuExcessiveFakeAid  TruthValue,
    phyAiuAdminState        AdminState,
    phyAiuRebootRr          TruthValue
}

phyAiuIndex         OBJECT-TYPE
    SYNTAX          INTEGER
    MAX-ACCESS      read-only
    STATUS          current
    DESCRIPTION     "AIU index."
    ::= { phyAiuEntry 1 }

phyAiuOpState       OBJECT-TYPE
    SYNTAX          CardOpState
    MAX-ACCESS      read-only
    STATUS          current
    DESCRIPTION     "AIU operational state."
    ::= { phyAiuEntry 2 }

phyAiuFaultLed      OBJECT-TYPE
    SYNTAX          CardFaultLed
    MAX-ACCESS      read-only
    STATUS          current
    DESCRIPTION     "AIU fault LED color."
    ::= { phyAiuEntry 3 }

phyAiuTempStatus    OBJECT-TYPE
    SYNTAX          CardTempStatus
    MAX-ACCESS      read-only
    STATUS          current
    DESCRIPTION     "AIU temperature status."
    ::= { phyAiuEntry 4 }

phyAiuVoltageStatus OBJECT-TYPE
    SYNTAX          CardVoltageStatus
    MAX-ACCESS      read-only
    STATUS          current
    DESCRIPTION     "AIU voltage status."
    ::= { phyAiuEntry 5 }

phyAiuSerialNumber  OBJECT-TYPE
    SYNTAX          DisplayString
    MAX-ACCESS      read-only
    STATUS          current
    DESCRIPTION     "AIU serial number."
    ::= { phyAiuEntry 6 }

phyAiuProductionDate    OBJECT-TYPE
    SYNTAX          DisplayString
    MAX-ACCESS      read-only
    STATUS          current
    DESCRIPTION     "AIU production date."
    ::= { phyAiuEntry 7 }

phyAiuPartNumber    OBJECT-TYPE
    SYNTAX          DisplayString
    MAX-ACCESS      read-only
    STATUS          current
    DESCRIPTION     "AIU part number."
    ::= { phyAiuEntry 8 }

phyAiuDescription   OBJECT-TYPE
    SYNTAX          DisplayString
    MAX-ACCESS      read-only
    STATUS          current
    DESCRIPTION     "AIU description."
    ::= { phyAiuEntry 9 }

phyAiuHardwareVersion   OBJECT-TYPE
    SYNTAX          DisplayString
    MAX-ACCESS      read-only
    STATUS          current
    DESCRIPTION     "AIU hardware version."
    ::= { phyAiuEntry 10 }

phyAiuIpmiSwVersion OBJECT-TYPE
    SYNTAX          DisplayString
    MAX-ACCESS      read-only
    STATUS          current
    DESCRIPTION     "AIU IPMI software version."
    ::= { phyAiuEntry 11 }

phyAiuAssemblyId    OBJECT-TYPE
    SYNTAX          DisplayString
    MAX-ACCESS      read-only
    STATUS          current
    DESCRIPTION     "AIU assembly ID."
    ::= { phyAiuEntry 12 }

phyAiuAssemblyIdSrc OBJECT-TYPE
    SYNTAX          AssemblyIdSource
    MAX-ACCESS      read-only
    STATUS          current
    DESCRIPTION     "AIU assembly ID source."
    ::= { phyAiuEntry 13 }

phyAiuExcessiveFakeAid  OBJECT-TYPE
    SYNTAX          TruthValue
    MAX-ACCESS      read-only
    STATUS          current
    DESCRIPTION     "This object is true(1) if the assembly ID is programmed
                    under more than one source."
    ::= { phyAiuEntry 14 }

phyAiuAdminState    OBJECT-TYPE
    SYNTAX          AdminState
    MAX-ACCESS      read-write
    STATUS          current
    DESCRIPTION     "AIU administrative state."
    ::= { phyAiuEntry 20 }

phyAiuRebootRr      OBJECT-TYPE
    SYNTAX          TruthValue
    MAX-ACCESS      read-write
    STATUS          current
    DESCRIPTION     "Setting this object to true(1) will power cycle the
                     RadioRouter chassis!"
    ::= { phyAiuEntry 21 }

--
-- Main Controller Unit (MCU) Table
--
phyMcuTable         OBJECT-TYPE
    SYNTAX          SEQUENCE OF PhyMcuEntry
    MAX-ACCESS      not-accessible
    STATUS          current
    DESCRIPTION     ""
    ::= { rrPhyShelf 15 }

phyMcuEntry         OBJECT-TYPE
    SYNTAX          PhyMcuEntry
    MAX-ACCESS      not-accessible
    STATUS          current
    DESCRIPTION     ""
    INDEX           { phyMcuIndex }
    ::= { phyMcuTable 1 }

PhyMcuEntry ::= SEQUENCE {
    phyMcuIndex             INTEGER,
    phyMcuOpState           CardOpState,
    phyMcuFaultLed          CardFaultLed,
    phyMcuTempStatus        CardTempStatus,
    phyMcuVoltageStatus     CardVoltageStatus,
    phyMcuSerialNumber      DisplayString,
    phyMcuProductionDate    DisplayString,
    phyMcuPartNumber        DisplayString,
    phyMcuDescription       DisplayString,
    phyMcuHardwareVersion   DisplayString,
    phyMcuIpmiSwVersion     DisplayString,
    phyMcuAssemblyId        DisplayString,
    phyMcuAssemblyIdSrc     AssemblyIdSource,
    phyMcuExcessiveFakeAid  TruthValue,
    phyMcuAdminState        AdminState,
    phyCpldVersion          DisplayString
}

phyMcuIndex         OBJECT-TYPE
    SYNTAX          INTEGER
    MAX-ACCESS      read-only
    STATUS          current
    DESCRIPTION     "MCU index."
    ::= { phyMcuEntry 1 }

phyMcuOpState       OBJECT-TYPE
    SYNTAX          CardOpState
    MAX-ACCESS      read-only
    STATUS          current
    DESCRIPTION     "MCU operational state."
    ::= { phyMcuEntry 2 }

phyMcuFaultLed      OBJECT-TYPE
    SYNTAX          CardFaultLed
    MAX-ACCESS      read-only
    STATUS          current
    DESCRIPTION     "MCU fault LED color."
    ::= { phyMcuEntry 3 }

phyMcuTempStatus    OBJECT-TYPE
    SYNTAX          CardTempStatus
    MAX-ACCESS      read-only
    STATUS          current
    DESCRIPTION     "MCU temperature status."
    ::= { phyMcuEntry 4 }

phyMcuVoltageStatus OBJECT-TYPE
    SYNTAX          CardVoltageStatus
    MAX-ACCESS      read-only
    STATUS          current
    DESCRIPTION     "MCU voltage status."
    ::= { phyMcuEntry 5 }

phyMcuSerialNumber  OBJECT-TYPE
    SYNTAX          DisplayString
    MAX-ACCESS      read-only
    STATUS          current
    DESCRIPTION     "MCU serial number."
    ::= { phyMcuEntry 6 }

phyMcuProductionDate    OBJECT-TYPE
    SYNTAX          DisplayString
    MAX-ACCESS      read-only
    STATUS          current
    DESCRIPTION     "MCU production date."
    ::= { phyMcuEntry 7 }

phyMcuPartNumber    OBJECT-TYPE
    SYNTAX          DisplayString
    MAX-ACCESS      read-only
    STATUS          current
    DESCRIPTION     "MCU part number."
    ::= { phyMcuEntry 8 }

phyMcuDescription   OBJECT-TYPE
    SYNTAX          DisplayString
    MAX-ACCESS      read-only
    STATUS          current
    DESCRIPTION     "MCU description."
    ::= { phyMcuEntry 9 }

phyMcuHardwareVersion   OBJECT-TYPE
    SYNTAX          DisplayString
    MAX-ACCESS      read-only
    STATUS          current
    DESCRIPTION     "MCU hardware version."
    ::= { phyMcuEntry 10 }

phyMcuIpmiSwVersion OBJECT-TYPE
    SYNTAX          DisplayString
    MAX-ACCESS      read-only
    STATUS          current
    DESCRIPTION     "MCU IPMI software version."
    ::= { phyMcuEntry 11 }

phyMcuAssemblyId    OBJECT-TYPE
    SYNTAX          DisplayString
    MAX-ACCESS      read-only
    STATUS          current
    DESCRIPTION     "MCU assembly ID."
    ::= { phyMcuEntry 12 }

phyMcuAssemblyIdSrc OBJECT-TYPE
    SYNTAX          AssemblyIdSource
    MAX-ACCESS      read-only
    STATUS          current
    DESCRIPTION     "MCU assembly ID source."
    ::= { phyMcuEntry 13 }

phyMcuExcessiveFakeAid  OBJECT-TYPE
    SYNTAX          TruthValue
    MAX-ACCESS      read-only
    STATUS          current
    DESCRIPTION     "This object is true if the assembly ID is programmed under
                    more than one source."
    ::= { phyMcuEntry 14 }

phyMcuAdminState    OBJECT-TYPE
    SYNTAX          AdminState
    MAX-ACCESS      read-write
    STATUS          current
    DESCRIPTION     "MCU administrative state."
    ::= { phyMcuEntry 20 }

phyCpldVersion      OBJECT-TYPE
    SYNTAX          DisplayString
    MAX-ACCESS      read-only
    STATUS          current
    DESCRIPTION     "MCU CPLD version."
    ::= { phyMcuEntry 21 }


--
-- Base Band Unit (BBU) Table
--
phyBbuTable         OBJECT-TYPE
    SYNTAX          SEQUENCE OF PhyBbuEntry
    MAX-ACCESS      not-accessible
    STATUS          current
    DESCRIPTION     ""
    ::= { rrPhyShelf 16 }

phyBbuEntry         OBJECT-TYPE
    SYNTAX          PhyBbuEntry
    MAX-ACCESS      not-accessible
    STATUS          current
    DESCRIPTION     ""
    INDEX           { phyBbuIndex }
    ::= { phyBbuTable 1 }

PhyBbuEntry ::= SEQUENCE {
    phyBbuIndex             INTEGER,
    phyBbuOpState           CardOpState,
    phyBbuFaultLed          CardFaultLed,
    phyBbuTempStatus        CardTempStatus,
    phyBbuVoltageStatus     CardVoltageStatus,
    phyBbuSerialNumber      DisplayString,
    phyBbuProductionDate    DisplayString,
    phyBbuPartNumber        DisplayString,
    phyBbuDescription       DisplayString,
    phyBbuHardwareVersion   DisplayString,
    phyBbuIpmiSwVersion     DisplayString,
    phyBbuAssemblyId        DisplayString,
    phyBbuAssemblyIdSrc     AssemblyIdSource,
    phyBbuExcessiveFakeAid  TruthValue,
    phyBbuAdminState        AdminState
}

phyBbuIndex         OBJECT-TYPE
    SYNTAX          INTEGER
    MAX-ACCESS      read-only
    STATUS          current
    DESCRIPTION     "BBU index."
    ::= { phyBbuEntry 1 }

phyBbuOpState       OBJECT-TYPE
    SYNTAX          CardOpState
    MAX-ACCESS      read-only
    STATUS          current
    DESCRIPTION     "BBU operational state."
    ::= { phyBbuEntry 2 }

phyBbuFaultLed      OBJECT-TYPE
    SYNTAX          CardFaultLed
    MAX-ACCESS      read-only
    STATUS          current
    DESCRIPTION     "BBU fault LED color."
    ::= { phyBbuEntry 3 }

phyBbuTempStatus    OBJECT-TYPE
    SYNTAX          CardTempStatus
    MAX-ACCESS      read-only
    STATUS          current
    DESCRIPTION     "BBU temperature status."
    ::= { phyBbuEntry 4 }

phyBbuVoltageStatus OBJECT-TYPE
    SYNTAX          CardVoltageStatus
    MAX-ACCESS      read-only
    STATUS          current
    DESCRIPTION     "BBU voltage status."
    ::= { phyBbuEntry 5 }

phyBbuSerialNumber  OBJECT-TYPE
    SYNTAX          DisplayString
    MAX-ACCESS      read-only
    STATUS          current
    DESCRIPTION     "BBU serial number."
    ::= { phyBbuEntry 6 }

phyBbuProductionDate    OBJECT-TYPE
    SYNTAX          DisplayString
    MAX-ACCESS      read-only
    STATUS          current
    DESCRIPTION     "BBU production date."
    ::= { phyBbuEntry 7 }

phyBbuPartNumber    OBJECT-TYPE
    SYNTAX          DisplayString
    MAX-ACCESS      read-only
    STATUS          current
    DESCRIPTION     "BBU part number."
    ::= { phyBbuEntry 8 }

phyBbuDescription   OBJECT-TYPE
    SYNTAX          DisplayString
    MAX-ACCESS      read-only
    STATUS          current
    DESCRIPTION     "BBU description."
    ::= { phyBbuEntry 9 }

phyBbuHardwareVersion   OBJECT-TYPE
    SYNTAX          DisplayString
    MAX-ACCESS      read-only
    STATUS          current
    DESCRIPTION     "BBU hardware version."
    ::= { phyBbuEntry 10 }

phyBbuIpmiSwVersion OBJECT-TYPE
    SYNTAX          DisplayString
    MAX-ACCESS      read-only
    STATUS          current
    DESCRIPTION     "BBU IPMI software version."
    ::= { phyBbuEntry 11 }

phyBbuAssemblyId    OBJECT-TYPE
    SYNTAX          DisplayString
    MAX-ACCESS      read-only
    STATUS          current
    DESCRIPTION     "BBU assembly Id."
    ::= { phyBbuEntry 12 }

phyBbuAssemblyIdSrc OBJECT-TYPE
    SYNTAX          AssemblyIdSource
    MAX-ACCESS      read-only
    STATUS          current
    DESCRIPTION     "BBU assembly Id source."
    ::= { phyBbuEntry 13 }

phyBbuExcessiveFakeAid  OBJECT-TYPE
    SYNTAX          TruthValue
    MAX-ACCESS      read-only
    STATUS          current
    DESCRIPTION     "This object is true if the assembly ID is programmed under
                    more than one source."
    ::= { phyBbuEntry 14 }

phyBbuAdminState    OBJECT-TYPE
    SYNTAX          AdminState
    MAX-ACCESS      read-write
    STATUS          current
    DESCRIPTION     "BBU administrative state."
    ::= { phyBbuEntry 20 }


--
-- RX Unit (RXU) Table
--
phyRxuTable         OBJECT-TYPE
    SYNTAX          SEQUENCE OF PhyRxuEntry
    MAX-ACCESS      not-accessible
    STATUS          current
    DESCRIPTION     ""
    ::= { rrPhyShelf 17 }

phyRxuEntry         OBJECT-TYPE
    SYNTAX          PhyRxuEntry
    MAX-ACCESS      not-accessible
    STATUS          current
    DESCRIPTION     ""
    INDEX           { phyRxuIndex }
    ::= { phyRxuTable 1 }

PhyRxuEntry ::= SEQUENCE {
    phyRxuIndex             INTEGER,
    phyRxuOpState           CardOpState,
    phyRxuFaultLed          CardFaultLed,
    phyRxuTempStatus        CardTempStatus,
    phyRxuVoltageStatus     CardVoltageStatus,
    phyRxuSerialNumber      DisplayString,
    phyRxuProductionDate    DisplayString,
    phyRxuPartNumber        DisplayString,
    phyRxuDescription       DisplayString,
    phyRxuHardwareVersion   DisplayString,
    phyRxuIpmiSwVersion     DisplayString,
    phyRxuAssemblyId        DisplayString,
    phyRxuAssemblyIdSrc     AssemblyIdSource,
    phyRxuExcessiveFakeAid  TruthValue,
    phyRxuAdminState        AdminState,
    phyRxuRfBand            RfBand
}

phyRxuIndex         OBJECT-TYPE
    SYNTAX          INTEGER
    MAX-ACCESS      read-only
    STATUS          current
    DESCRIPTION     "RXU index."
    ::= { phyRxuEntry 1 }

phyRxuOpState       OBJECT-TYPE
    SYNTAX          CardOpState
    MAX-ACCESS      read-only
    STATUS          current
    DESCRIPTION     "RXU operational state."
    ::= { phyRxuEntry 2 }

phyRxuFaultLed      OBJECT-TYPE
    SYNTAX          CardFaultLed
    MAX-ACCESS      read-only
    STATUS          current
    DESCRIPTION     "RXU fault LED color."
    ::= { phyRxuEntry 3 }

phyRxuTempStatus    OBJECT-TYPE
    SYNTAX          CardTempStatus
    MAX-ACCESS      read-only
    STATUS          current
    DESCRIPTION     "RXU temperature status."
    ::= { phyRxuEntry 4 }

phyRxuVoltageStatus OBJECT-TYPE
    SYNTAX          CardVoltageStatus
    MAX-ACCESS      read-only
    STATUS          current
    DESCRIPTION     "RXU voltage status."
    ::= { phyRxuEntry 5 }

phyRxuSerialNumber  OBJECT-TYPE
    SYNTAX          DisplayString
    MAX-ACCESS      read-only
    STATUS          current
    DESCRIPTION     "RXU serial number."
    ::= { phyRxuEntry 6 }

phyRxuProductionDate    OBJECT-TYPE
    SYNTAX          DisplayString
    MAX-ACCESS      read-only
    STATUS          current
    DESCRIPTION     "RXU production date."
    ::= { phyRxuEntry 7 }

phyRxuPartNumber    OBJECT-TYPE
    SYNTAX          DisplayString
    MAX-ACCESS      read-only
    STATUS          current
    DESCRIPTION     "RXU part number."
    ::= { phyRxuEntry 8 }

phyRxuDescription   OBJECT-TYPE
    SYNTAX          DisplayString
    MAX-ACCESS      read-only
    STATUS          current
    DESCRIPTION     "RXU description."
    ::= { phyRxuEntry 9 }

phyRxuHardwareVersion   OBJECT-TYPE
    SYNTAX          DisplayString
    MAX-ACCESS      read-only
    STATUS          current
    DESCRIPTION     "RXU hardware version."
    ::= { phyRxuEntry 10 }

phyRxuIpmiSwVersion OBJECT-TYPE
    SYNTAX          DisplayString
    MAX-ACCESS      read-only
    STATUS          current
    DESCRIPTION     "RXU IPMI software version."
    ::= { phyRxuEntry 11 }

phyRxuAssemblyId    OBJECT-TYPE
    SYNTAX          DisplayString
    MAX-ACCESS      read-only
    STATUS          current
    DESCRIPTION     "RXU assembly ID."
    ::= { phyRxuEntry 12 }

phyRxuAssemblyIdSrc OBJECT-TYPE
    SYNTAX          AssemblyIdSource
    MAX-ACCESS      read-only
    STATUS          current
    DESCRIPTION     "RXU assembly ID source."
    ::= { phyRxuEntry 13 }

phyRxuExcessiveFakeAid  OBJECT-TYPE
    SYNTAX          TruthValue
    MAX-ACCESS      read-only
    STATUS          current
    DESCRIPTION     "This object is true if the assembly ID is programmed under
                    more than one source."
    ::= { phyRxuEntry 14 }

phyRxuAdminState    OBJECT-TYPE
    SYNTAX          AdminState
    MAX-ACCESS      read-write
    STATUS          current
    DESCRIPTION     "RXU administrative state."
    ::= { phyRxuEntry 20 }

phyRxuRfBand        OBJECT-TYPE
    SYNTAX          RfBand
    MAX-ACCESS      read-only
    STATUS          current
    DESCRIPTION     "RXU RF band."
    ::= { phyRxuEntry 21 }



--
-- TX Unit (TXU) Table
--
phyTxuTable         OBJECT-TYPE
    SYNTAX          SEQUENCE OF PhyTxuEntry
    MAX-ACCESS      not-accessible
    STATUS          current
    DESCRIPTION     ""
    ::= { rrPhyShelf 18 }

phyTxuEntry         OBJECT-TYPE
    SYNTAX          PhyTxuEntry
    MAX-ACCESS      not-accessible
    STATUS          current
    DESCRIPTION     ""
    INDEX           { phyTxuIndex }
    ::= { phyTxuTable 1 }

PhyTxuEntry ::= SEQUENCE {
    phyTxuIndex             INTEGER,
    phyTxuOpState           CardOpState,
    phyTxuFaultLed          CardFaultLed,
    phyTxuTempStatus        CardTempStatus,
    phyTxuVoltageStatus     CardVoltageStatus,
    phyTxuSerialNumber      DisplayString,
    phyTxuProductionDate    DisplayString,
    phyTxuPartNumber        DisplayString,
    phyTxuDescription       DisplayString,
    phyTxuHardwareVersion   DisplayString,
    phyTxuIpmiSwVersion     DisplayString,
    phyTxuAssemblyId        DisplayString,
    phyTxuAssemblyIdSrc     AssemblyIdSource,
    phyTxuExcessiveFakeAid  TruthValue,
    phyTxuAdminState        AdminState,
    phyTxuRfBand            RfBand
}

phyTxuIndex         OBJECT-TYPE
    SYNTAX          INTEGER
    MAX-ACCESS      read-only
    STATUS          current
    DESCRIPTION     "TXU index."
    ::= { phyTxuEntry 1 }

phyTxuOpState       OBJECT-TYPE
    SYNTAX          CardOpState
    MAX-ACCESS      read-only
    STATUS          current
    DESCRIPTION     "TXU operational state."
    ::= { phyTxuEntry 2 }

phyTxuFaultLed      OBJECT-TYPE
    SYNTAX          CardFaultLed
    MAX-ACCESS      read-only
    STATUS          current
    DESCRIPTION     "TXU fault LED color."
    ::= { phyTxuEntry 3 }

phyTxuTempStatus    OBJECT-TYPE
    SYNTAX          CardTempStatus
    MAX-ACCESS      read-only
    STATUS          current
    DESCRIPTION     "TXU temperature status."
    ::= { phyTxuEntry 4 }

phyTxuVoltageStatus OBJECT-TYPE
    SYNTAX          CardVoltageStatus
    MAX-ACCESS      read-only
    STATUS          current
    DESCRIPTION     "TXU voltage status."
    ::= { phyTxuEntry 5 }

phyTxuSerialNumber  OBJECT-TYPE
    SYNTAX          DisplayString
    MAX-ACCESS      read-only
    STATUS          current
    DESCRIPTION     "TXU serial number."
    ::= { phyTxuEntry 6 }

phyTxuProductionDate    OBJECT-TYPE
    SYNTAX          DisplayString
    MAX-ACCESS      read-only
    STATUS          current
    DESCRIPTION     "TXU production date."
    ::= { phyTxuEntry 7 }

phyTxuPartNumber    OBJECT-TYPE
    SYNTAX          DisplayString
    MAX-ACCESS      read-only
    STATUS          current
    DESCRIPTION     "TXU part number."
    ::= { phyTxuEntry 8 }

phyTxuDescription   OBJECT-TYPE
    SYNTAX          DisplayString
    MAX-ACCESS      read-only
    STATUS          current
    DESCRIPTION     "TXU description."
    ::= { phyTxuEntry 9 }

phyTxuHardwareVersion   OBJECT-TYPE
    SYNTAX          DisplayString
    MAX-ACCESS      read-only
    STATUS          current
    DESCRIPTION     "TXU hardware version."
    ::= { phyTxuEntry 10 }

phyTxuIpmiSwVersion OBJECT-TYPE
    SYNTAX          DisplayString
    MAX-ACCESS      read-only
    STATUS          current
    DESCRIPTION     "TXU IPMI software version."
    ::= { phyTxuEntry 11 }

phyTxuAssemblyId    OBJECT-TYPE
    SYNTAX          DisplayString
    MAX-ACCESS      read-only
    STATUS          current
    DESCRIPTION     "TXU assembly ID."
    ::= { phyTxuEntry 12 }

phyTxuAssemblyIdSrc OBJECT-TYPE
    SYNTAX          AssemblyIdSource
    MAX-ACCESS      read-only
    STATUS          current
    DESCRIPTION     "TXU assembly ID source."
    ::= { phyTxuEntry 13 }

phyTxuExcessiveFakeAid  OBJECT-TYPE
    SYNTAX          TruthValue
    MAX-ACCESS      read-only
    STATUS          current
    DESCRIPTION     "This object is true if the assembly ID is programmed under
                    more than one source."
    ::= { phyTxuEntry 14 }

phyTxuAdminState    OBJECT-TYPE
    SYNTAX          AdminState
    MAX-ACCESS      read-write
    STATUS          current
    DESCRIPTION     "TXU administrative state."
    ::= { phyTxuEntry 20 }

phyTxuRfBand        OBJECT-TYPE
    SYNTAX          RfBand
    MAX-ACCESS      read-only
    STATUS          current
    DESCRIPTION     "TXU RF band."
    ::= { phyTxuEntry 21 }



--
-- Power Amp
--
paTable            OBJECT-TYPE
    SYNTAX          SEQUENCE OF PaEntry
    MAX-ACCESS      not-accessible
    STATUS          current
    DESCRIPTION     ""
    ::= { rrPaShelf 1 }

paEntry             OBJECT-TYPE
    SYNTAX          PaEntry
    MAX-ACCESS      not-accessible
    STATUS          current
    DESCRIPTION     ""
    INDEX           { paIndex }
    ::= { paTable 1 }

PaEntry ::= SEQUENCE {
    paIndex                 INTEGER,
    paAdminState            AdminState,
    paOpState               CardOpState,
    paTempStatus            CardTempStatus,
    paOutputTxPower         FloatAsString,
    paInputTxPower          FloatAsString,
    paTxReflectedPower      FloatAsString,
    paDcPowerFault          TruthValue,
    paRfOverdriveFault      TruthValue,
    paFeedForwardFault      TruthValue,
    paSerialNumber          DisplayString,
    paRfBand                RfBand,
    paHardwareVersion       DisplayString,
    paTemperature           INTEGER,
    paReflectedPowerFault   TruthValue,
    paUnderPowerFault       TruthValue,
    paTargetOutputTxPower   FloatAsString,
    paOperStatus            PaState,
    paRadioFreqBand         PaRfBand
}

paIndex         OBJECT-TYPE
    SYNTAX          INTEGER
    MAX-ACCESS      read-only
    STATUS          current
    DESCRIPTION     "Power Amp index."
    ::= { paEntry 1 }

paAdminState        OBJECT-TYPE
    SYNTAX          AdminState
    MAX-ACCESS      read-write
    STATUS          current
    DESCRIPTION     "PA administrative state."
    ::= { paEntry 2 }

paOpState           OBJECT-TYPE
    SYNTAX          CardOpState
    MAX-ACCESS      read-only
    STATUS          deprecated
    DESCRIPTION     "PA operational state.

                    This object is deprecated in favor of paOperStatus."
    ::= { paEntry 3 }

paTempStatus        OBJECT-TYPE
    SYNTAX          CardTempStatus
    MAX-ACCESS      read-only
    STATUS          current
    DESCRIPTION     "PA temperature status."
    ::= { paEntry 4 }

paOutputTxPower     OBJECT-TYPE
    SYNTAX          FloatAsString
    MAX-ACCESS      read-only
    STATUS          current
    DESCRIPTION     "PA output transmit power, in dbm."
    ::= { paEntry 5 }

paInputTxPower      OBJECT-TYPE
    SYNTAX          FloatAsString
    MAX-ACCESS      read-only
    STATUS          current
    DESCRIPTION     "PA input transmit power, in dbm."
    ::= { paEntry 6 }

paTxReflectedPower  OBJECT-TYPE
    SYNTAX          FloatAsString
    MAX-ACCESS      read-only
    STATUS          current
    DESCRIPTION     "PA transmit reflected power, in dbm."
    ::= { paEntry 7 }

paDcPowerFault      OBJECT-TYPE
    SYNTAX          TruthValue
    MAX-ACCESS      read-only
    STATUS          current
    DESCRIPTION     "This object indicates if a PA DC power fault exists."
    ::= { paEntry 8 }

paRfOverdriveFault  OBJECT-TYPE
    SYNTAX          TruthValue
    MAX-ACCESS      read-only
    STATUS          current
    DESCRIPTION     "This object indicates if a PA RF overdrive fault exists."
    ::= { paEntry 9 }

paFeedForwardFault  OBJECT-TYPE
    SYNTAX          TruthValue
    MAX-ACCESS      read-only
    STATUS          current
    DESCRIPTION     "This object indicates if a PA feed forward fault exists."
    ::= { paEntry 10 }

paSerialNumber      OBJECT-TYPE
    SYNTAX          DisplayString
    MAX-ACCESS      read-only
    STATUS          current
    DESCRIPTION     "PA serial number."
    ::= { paEntry 11 }

paRfBand            OBJECT-TYPE
    SYNTAX          RfBand
    MAX-ACCESS      read-only
    STATUS          deprecated
    DESCRIPTION     "PA RF band.

                    This object is deprecated in favor of paRadioFreqBand."
    ::= { paEntry 12 }

paHardwareVersion   OBJECT-TYPE
    SYNTAX          DisplayString
    MAX-ACCESS      read-only
    STATUS          current
    DESCRIPTION     "PA hardware version."
    ::= { paEntry 13 }

paTemperature       OBJECT-TYPE
    SYNTAX          INTEGER
    MAX-ACCESS      read-only
    STATUS          current
    DESCRIPTION     "PA temperature (Celcius)."
    ::= { paEntry 14 }

paReflectedPowerFault   OBJECT-TYPE
    SYNTAX          TruthValue
    MAX-ACCESS      read-only
    STATUS          current
    DESCRIPTION     "This object indicates if a reflected power fault exists."
    ::= { paEntry 15 }

paUnderPowerFault   OBJECT-TYPE
    SYNTAX          TruthValue
    MAX-ACCESS      read-only
    STATUS          current
    DESCRIPTION     "This object indicates if an under power fault exists."
    ::= { paEntry 16 }

paTargetOutputTxPower   OBJECT-TYPE
    SYNTAX          FloatAsString
    MAX-ACCESS      read-write
    STATUS          current
    DESCRIPTION     "PA target output Tx power."
    DEFVAL          { "43.0" }
    ::= { paEntry 17 }

paOperStatus        OBJECT-TYPE
    SYNTAX          PaState
    MAX-ACCESS      read-only
    STATUS          current
    DESCRIPTION     "PA operational state."
    ::= { paEntry 18 }

paRadioFreqBand     OBJECT-TYPE
    SYNTAX          PaRfBand
    MAX-ACCESS      read-only
    STATUS          current
    DESCRIPTION     "PA RF band."
    ::= { paEntry 19 }


paFanSpeedOk        OBJECT-TYPE
    SYNTAX          TruthValue
    MAX-ACCESS      read-only
    STATUS          current
    DESCRIPTION     "This object indicates if the PA shelf fan speed is within
                    normal operating limits."
    ::= { rrPaShelf 2 }

paFanTempOk         OBJECT-TYPE
    SYNTAX          TruthValue
    MAX-ACCESS      read-only
    STATUS          current
    DESCRIPTION     "This object indicates if the PA shelf fan temperature is
                    within normal operating limits."
    ::= { rrPaShelf 3 }


paBreakerTripped    OBJECT-TYPE
    SYNTAX          TruthValue
    MAX-ACCESS      read-only
    STATUS          current
    DESCRIPTION     "This object indicates if a PA shelf breaker has been
                    tripped."
    ::= { rrPaShelf 4 }

paSimulcast         OBJECT-TYPE
    SYNTAX          TruthValue
    MAX-ACCESS      read-write
    STATUS          current
    DESCRIPTION     "This object indicates if the PA shelf supports simulcast."
    DEFVAL          { false }
    ::= { rrPaShelf 5 }

paTxCalEnabled      OBJECT-TYPE
    SYNTAX          TruthValue
    MAX-ACCESS      read-write
    STATUS          current
    DESCRIPTION     "This object indicates if PX Gain control loop is enabled."
    DEFVAL          { true }
    ::= { rrPaShelf 6 }


--
-- Power Amp Tx Power 
--
paPowerTable        OBJECT-TYPE
    SYNTAX          SEQUENCE OF PaPowerEntry
    MAX-ACCESS      not-accessible
    STATUS          current
    DESCRIPTION     "This table is used to display PA various Tx power values.
                    These values are store on the system as floating point
                    numbers, but since SNMP cannot display floating point
                    numbers, this table will convert the values to integer."
    ::= { rrPaShelf 7 }

paPowerEntry        OBJECT-TYPE
    SYNTAX          PaPowerEntry
    MAX-ACCESS      not-accessible
    STATUS          current
    DESCRIPTION     ""
    INDEX           { paPowerIndex }
    ::= { paPowerTable 1 }

PaPowerEntry ::= SEQUENCE {
    paPowerIndex        INTEGER,
    paPowerTxOutput     INTEGER,
    paPowerTxInput      INTEGER,
    paPowerTxReflected  INTEGER
}

paPowerIndex        OBJECT-TYPE
    SYNTAX          INTEGER
    MAX-ACCESS      read-only
    STATUS          current
    DESCRIPTION     "PA index."
    ::= { paPowerEntry 1 }

paPowerTxOutput     OBJECT-TYPE
    SYNTAX          INTEGER
    MAX-ACCESS      read-only
    STATUS          current
    DESCRIPTION     "PA output Tx power. In order to retain precision in
                    converting the floating point value into integer, the value                     is first multiplied by 100. For example 43.25dB will be
                    represented as 4325."
    ::= { paPowerEntry 2 }

paPowerTxInput      OBJECT-TYPE
    SYNTAX          INTEGER
    MAX-ACCESS      read-only
    STATUS          current
    DESCRIPTION     "PA input Tx power. In order to retain precision in
                    converting the floating point value into integer, the value 
                    is first multiplied by 100. For example -50.75dB will be
                    represented as -5075."
    ::= { paPowerEntry 3 }

paPowerTxReflected  OBJECT-TYPE
    SYNTAX          INTEGER
    MAX-ACCESS      read-only
    STATUS          current
    DESCRIPTION     "PA reflected Tx power. In order to retain precision in
                    converting the floating point value into integer, the value 
                    is first multiplied by 100. For example 21.00dB will be
                    represented as 2100."
    ::= { paPowerEntry 4 }

--
-- BBU System Table
--
bbuSysTable         OBJECT-TYPE
    SYNTAX          SEQUENCE OF BbuSysEntry
    MAX-ACCESS      not-accessible
    STATUS          current
    DESCRIPTION     "Base Band Unit system information."
    ::= { rrBaseBandUnit 5 }

bbuSysEntry         OBJECT-TYPE
    SYNTAX          BbuSysEntry
    MAX-ACCESS      not-accessible
    STATUS          current
    DESCRIPTION     "Base Band Unit system table entry."
    INDEX           { bbuSysId }
    ::= { bbuSysTable 1 }

BbuSysEntry ::= SEQUENCE {
    bbuSysId                INTEGER,
    bbuDspVer               DisplayString,
    bbuLlcVer               DisplayString,
    bbuTxFpgaVer            DisplayString,
    bbuRxFpgaVer            DisplayString,
    bbuLdpcVer              Unsigned32,
    bbuRfChanNum            INTEGER,
    bbuExtGainTx            INTEGER,
    bbuExtGainRx            INTEGER,
    bbuRfGainRx0            INTEGER,
    bbuRfGainRx1            INTEGER,
    bbuRfBand               INTEGER,
    bbuRfPowerTx0           INTEGER,
    bbuRfPowerTx1           INTEGER,
    bbuRfuEnableMask        INTEGER,
    bbuExtTxGain            FloatAsString,
    bbuExtRxGain            FloatAsString,
    bbuRfRx0Gain            FloatAsString,
    bbuRfRx1Gain            FloatAsString,
    bbuRfTx0Power           FloatAsString,
    bbuRfTx1Power           FloatAsString,
    bbuTxPwrDeviationLimit  INTEGER,
    bbuSlope                INTEGER,
    bbuMcastSnr             INTEGER,
    bbuScmType              INTEGER,
    bbuSleepInactivityTimer INTEGER,
    bbuLuTimer              INTEGER
}

bbuSysId            OBJECT-TYPE
    SYNTAX          INTEGER
    MAX-ACCESS      read-only
    STATUS          current
    DESCRIPTION     "This identifies a single BBU in a basestation."
    ::= { bbuSysEntry 1 }

bbuDspVer           OBJECT-TYPE
    SYNTAX          DisplayString
    MAX-ACCESS      read-only
    STATUS          current
    DESCRIPTION     "The read-only statistic indicates the version number of
                    the DSP software currently operational on the sector in
                    question. It has the major.minor.micro notation."
    ::= { bbuSysEntry 2 }

bbuLlcVer           OBJECT-TYPE
    SYNTAX          DisplayString
    MAX-ACCESS      read-only
    STATUS          current
    DESCRIPTION     "The read-only statistic indicates the version number of
                    the Link List Controller software/firmware currently
                    operational on the sector in question. It has the
                    major.minor notation."
    ::= { bbuSysEntry 3 }

bbuTxFpgaVer        OBJECT-TYPE
    SYNTAX          DisplayString
    MAX-ACCESS      read-only
    STATUS          current
    DESCRIPTION     "The read-only statistic indicates the version number of
                    the Tx FPGA software/firmware currently operational on the
                    sector in question. It has the  major.minor notation."
    ::= { bbuSysEntry 4 }

bbuRxFpgaVer        OBJECT-TYPE
    SYNTAX          DisplayString
    MAX-ACCESS      read-only
    STATUS          current
    DESCRIPTION     "The read-only statistic indicates the version number of
                    the Rx FPGA software/firmware currently operational on the
                    sector in question. It has the  major.minor notation."
    ::= { bbuSysEntry 5 }

bbuLdpcVer          OBJECT-TYPE
    SYNTAX          Unsigned32
    MAX-ACCESS      read-only
    STATUS          current
    DESCRIPTION     "The read-only statistic indicates the version number of
                    the LDPC encoder/decoder software/firmware currently
                    operational on the sector in question. It has the
                    major.minor notation."
    ::= { bbuSysEntry 6 }

bbuRfChanNum        OBJECT-TYPE
    SYNTAX          INTEGER (0..2000)
    MAX-ACCESS      read-write
    STATUS          current
    DESCRIPTION     "The RF channel number, in conjunction with the bbuRffBand
                    object defines the frequency of operation. The channel
                    number follows well-known ITU numbering, and represents
                    50 kHz spacing. The step size depends on the band. In the
                    1.9 GHz band, the step size is 4 (200 kHz). Editable
                    offline."
    DEFVAL          { 295 }
    ::= { bbuSysEntry 50 }

bbuExtGainTx        OBJECT-TYPE
    SYNTAX          INTEGER (-1600..2240)
    MAX-ACCESS      read-write
    STATUS          deprecated
    DESCRIPTION     "Represents the total external gain in the Tx path.
                    Typically it equals PA gain minus any attenuators.
                    The value is in dB * 32 (scaled by 32). E.g., default
                    value is 43 dB, which is the PA gain, and is represented as
                    43*32 = 1376. This parameter is used to assist the mobile
                    in making an access attempt at an appropriate power level.
                    The step size is 1 dB. Editable online."
    DEFVAL          { 1376 }
    ::= { bbuSysEntry 51 }

bbuExtGainRx        OBJECT-TYPE
    SYNTAX          INTEGER (-1600..2240)
    MAX-ACCESS      read-write
    STATUS          deprecated
    DESCRIPTION     "Represents the total external gain in the Rx path.
                    Typically it equals LNA gain minus any attenuators.
                    The value is in dB * 32 (scaled by 32). E.g., default
                    value is 31 dB, which is the LNA gain, and is represented
                    as 31*32 = 992. This parameter is used to assist the mobile
                    in making an access attempt at an appropriate power level.
                    The step size is 1 dB. Editable online."

    DEFVAL          { 992 }
    ::= { bbuSysEntry 52 }

bbuRfGainRx0        OBJECT-TYPE
    SYNTAX          INTEGER (-10..75)
    MAX-ACCESS      read-write
    STATUS          deprecated
    DESCRIPTION     "Represents the gain (in dB) provided by the RF Rx
                    blade(RXU) in the Rx0 path. This gain is in addition to the
                    gain provided by the LNA. This value is typically
                    calibrated and set in the factory. The step size is 1 dB.
                    Editable online."
    DEFVAL          { 42 }
    ::= { bbuSysEntry 53 }

bbuRfGainRx1        OBJECT-TYPE
    SYNTAX          INTEGER (-10..75)
    MAX-ACCESS      read-write
    STATUS          deprecated
    DESCRIPTION     "Represents the gain (in dB) provided by the RF Rx
                    blade(RXU) in the Rx1 path. This gain is in addition to the
                    gain provided by the LNA. This value is typically
                    calibrated and set in the factory. The step size is 1 dB.
                    Editable online."
    DEFVAL          { 42 }
    ::= { bbuSysEntry 54 }

bbuRfBand           OBJECT-TYPE
    SYNTAX          INTEGER (0..255)
    MAX-ACCESS      read-write
    STATUS          current
    DESCRIPTION     "The band of operation, represented by an enumeration.
                    E.g., the 1.9 GHz PCS band has a value of 6, while the
                    2.1 GHz UMTS band has a value of 7. This quantity, in
                    conjunction with the bbuRfChanNum decides the frequency
                    of operation. Editable offline."
    DEFVAL          { 0 }
    ::= { bbuSysEntry 55 }

bbuRfPowerTx0       OBJECT-TYPE
    SYNTAX          INTEGER (-20..10)
    MAX-ACCESS      read-write
    STATUS          deprecated
    DESCRIPTION     "Represents the signal strength in dBm of the Tx signal put
                    out on Tx0 by the TXU. An increase in this implies an
                    increase in the signal input to the PA. Step size is 1 dBm.
                    Editable online."
    DEFVAL          { 0 }
    ::= { bbuSysEntry 56 }

bbuRfPowerTx1       OBJECT-TYPE
    SYNTAX          INTEGER (-20..10)
    MAX-ACCESS      read-write
    STATUS          deprecated
    DESCRIPTION     "Represents the signal strength in dBm of the Tx signal put
                    out on Tx1 by the TXU. An increase in this implies an
                    increase in the signal input to the PA. Step size is 1 dBm.
                    Editable online."
    DEFVAL          { 0 }
    ::= { bbuSysEntry 57 }

bbuRfuEnableMask    OBJECT-TYPE
    SYNTAX          INTEGER (0..15)
    MAX-ACCESS      read-write
    STATUS          current
    DESCRIPTION     "This is a bit mask to choose between the 0 and 1 channels
                    for Rx and Tx. The value should be an OR of the channels
                    selected, where: Tx0 = 0001
                                     Tx1 = 0010
                                     Rx0 = 0100
                                     Rx1 = 1000
                    For example, set this object to 6 if Rx0 and Tx1 need to
                    be enabled."
    DEFVAL          { 15 }
    ::= { bbuSysEntry 59 }

bbuExtTxGain        OBJECT-TYPE
    SYNTAX          FloatAsString
    MAX-ACCESS      read-write
    STATUS          current
    DESCRIPTION     "External Tx gain. Valid range is -50.0 to 70.0."
    DEFVAL          { "43.0" }
    ::= { bbuSysEntry 60 }

bbuExtRxGain        OBJECT-TYPE
    SYNTAX          FloatAsString
    MAX-ACCESS      read-write
    STATUS          current
    DESCRIPTION     "External Rx gain. Valid range is -50.0 to 70.0."
    DEFVAL          { "31.0" }
    ::= { bbuSysEntry 61 }

bbuRfRx0Gain        OBJECT-TYPE
    SYNTAX          FloatAsString
    MAX-ACCESS      read-write
    STATUS          current
    DESCRIPTION     "Represents the gain (in dB) provided by the RF Rx
                    blade(RXU) in the Rx0 path. This gain is in addition to the
                    gain provided by the LNA. This value is typically
                    calibrated and set in the factory. The step size is 1 dB.
                    Valid range is -10.0 to 75.0. Editable online."
    DEFVAL          { "42" }
    ::= { bbuSysEntry 62 }

bbuRfRx1Gain        OBJECT-TYPE
    SYNTAX          FloatAsString
    MAX-ACCESS      read-write
    STATUS          current
    DESCRIPTION     "Represents the gain (in dB) provided by the RF Rx
                    blade(RXU) in the Rx1 path. This gain is in addition to the
                    gain provided by the LNA. This value is typically
                    calibrated and set in the factory. The step size is 1 dB.
                    Valid range is -10.0 to 75.0. Editable online."
    DEFVAL          { "42" }
    ::= { bbuSysEntry 63 }

bbuRfTx0Power       OBJECT-TYPE
    SYNTAX          FloatAsString
    MAX-ACCESS      read-write
    STATUS          current
    DESCRIPTION     "Represents the signal strength in dBm of the Tx signal put
                    out on Tx0 by the TXU. An increase in this implies an
                    increase in the signal input to the PA. Step size is 1 dBm.
                    Valid range is -20.0 to 10.0. Editable online."
    DEFVAL          { "0" }
    ::= { bbuSysEntry 64 }

bbuRfTx1Power       OBJECT-TYPE
    SYNTAX          FloatAsString
    MAX-ACCESS      read-write
    STATUS          current
    DESCRIPTION     "Represents the signal strength in dBm of the Tx signal put
                    out on Tx1 by the TXU. An increase in this implies an
                    increase in the signal input to the PA. Step size is 1 dBm.
                    Valid range is -20.0 to 10.0. Editable online."
    DEFVAL          { "0" }
    ::= { bbuSysEntry 65 }

bbuTxPwrDeviationLimit  OBJECT-TYPE
    SYNTAX          INTEGER (1..10)
    MAX-ACCESS      read-write
    STATUS          current
    DESCRIPTION     ""
    DEFVAL          { 2 }
    ::= { bbuSysEntry 66 }

bbuSlope            OBJECT-TYPE
    SYNTAX          INTEGER (1..112)
    MAX-ACCESS      read-write
    STATUS          current
    DESCRIPTION     "Represents the slope of the RR sector. It is an identifier
                    which allows a mobile to distinguish between signals from
                    different basestations. There are 112 possible slope values,
                    however, only 80 of these are considered valid values.
                    Editable offline."
    DEFVAL          { 10 }
    ::= { bbuSysEntry 70 }

bbuMcastSnr         OBJECT-TYPE
    SYNTAX          INTEGER (-20..35)
    MAX-ACCESS      read-write
    STATUS          current
    DESCRIPTION     ""
    DEFVAL          { 8 }
    ::= { bbuSysEntry 71 }

bbuScmType          OBJECT-TYPE
    SYNTAX          INTEGER (0..1)
    MAX-ACCESS      read-write
    STATUS          current
    DESCRIPTION     ""
    DEFVAL          { 1 }
    ::= { bbuSysEntry 72 }

bbuSleepInactivityTimer OBJECT-TYPE
    SYNTAX          INTEGER (0..3600)
    MAX-ACCESS      read-write
    STATUS          current
    DESCRIPTION     "Represents the amount of time of data inactivity (on the
                    forward or reverse links) after which a mobile moves to the
                    Sleep state. In units of 1/3 seconds [ eg. Value = 180
                    represents 60 seconds]. This time period is conveyed to the
                    mobile at the time of establishing connectivity with the
                    basestation. This quantity is non-linearly quantized, so
                    the actual duration of inactivity before sleep may be
                    slightly different from this value. Step size is 1/3 second.
                    Range is 0 to 20 minutes. 0 means never go to sleep.
                    Recommended value is 180 (i.e., 60sec). Editable online."
    DEFVAL          { 0 }
    ::= { bbuSysEntry 91 }

bbuLuTimer          OBJECT-TYPE
    SYNTAX          INTEGER (0..86400)
    MAX-ACCESS      read-write
    STATUS          current
    DESCRIPTION     "Periodicity, in seconds, of location update done by a
                    stationary mobile. This time period is conveyed to the
                    mobile at the time of establishing connectivity with the RR.
                    This quantity is non-linearly quantized, so the actual
                    duration of location update may be slightly different from
                    this value. Step size is 1 second. Range is 5 seconds to 18
                    hours. Editable online."
    DEFVAL          { 900 }
    ::= { bbuSysEntry 100 }

END
