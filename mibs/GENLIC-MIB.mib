-- =========================================================
-- MIB: Generic License MIB
-- =========================================================
--  Version 1.1.1  22-June-20000 / Itai Zilbershtein
-- =============================================
--  lannet 37 instead of 36
--  Version 1.1  22-June-20000 / Itai Zilbershtein
-- =============================================
-- 1.  Moved from lannet 35 to lannet 36
-- 2.  dashes convereted to = signs in comments
-- Version 1.0 21-June-20000 / Itai Zilbershtein
-- =============================================
-- Post-design review version.
-- 1. licFeatureLicenseStatus replace licFeatureActivationStatus -
--    The mib refleces licensed/unlicensed state, and not active/inactive 
--     feature 
-- 
-- Version 0.9 -8-June-20000
-- =========================
-- Pre-design review version. 
-- 1. MIB placed under Lannet 35
-- 2. licFeatureDescr renamed licFeatureName. Names for known features are
--    presented.
-- 3. enumerations and names for host-based applications added.
--
-- Version 0.1 - 6-June-2000 Itai Zilbershtein
-- ============================================
-- Initial Version
--
-- =========================================================
-- Overview:
--
-- The License MIB provides a way for retrieving & setting license 
-- information.for specific feeatures.
--
GENLIC-MIB DEFINITIONS ::= BEGIN

IMPORTS
            MODULE-IDENTITY, OBJECT-TYPE,
            enterprises       FROM SNMPv2-SMI
	    DisplayString				FROM SNMPv2-TC;

lannet  OBJECT IDENTIFIER ::= { enterprises 81 }


license  MODULE-IDENTITY
        LAST-UPDATED "0006220000Z" -- 22 June. 2000
        ORGANIZATION "Lucent Technologies Inc."
        CONTACT-INFO
	        "Itai Zilbershtein -- izilbers@lucent.com"
	DESCRIPTION
       		"Lucent Common License MIB"
	::= { lannet 37 }

-- Groups
    licensePerModule   OBJECT IDENTIFIER ::= { license 1 }
-- Tanle used 
licModuleIdentTable OBJECT-TYPE
	SYNTAX SEQUENCE OF LicModuleIdentEntry
	MAX-ACCESS not-accessible
	STATUS current
	DESCRIPTION
	"Table of module identifieres used for requesting licenses"
	::= { licensePerModule 1 }

licModuleIdentEntry OBJECT-TYPE
	SYNTAX LicModuleIdentEntry
	MAX-ACCESS not-accessible
	STATUS current
	DESCRIPTION
	"An entry in the table, containing data about a single modules 
	operations." 
 	INDEX  { licModuleIdentIndex }
	::= { licModuleIdentTable 1 }

LicModuleIdentEntry ::=
	SEQUENCE  {
		licModuleIdentIndex		 INTEGER,
		licModuleIdentUniqueID		 OCTET STRING
		}

licModuleIdentIndex OBJECT-TYPE
	SYNTAX INTEGER (1..255)
	MAX-ACCESS read-only
	STATUS current
	DESCRIPTION
	"Index which identifies the module inside the chassis for which this
	entry contains information. Equals the number of the slot by which
	the group is accessed or the stackable index."
	::= { licModuleIdentEntry 1 }

licModuleIdentUniqueID OBJECT-TYPE
	SYNTAX OCTET STRING (SIZE(6))
	MAX-ACCESS read-only
	STATUS current
	DESCRIPTION	
	"The Unique identifier of this module. Example: the MAC Address of the
	agent onboard a P330 module. Must be 6 octets long."
	::= { licModuleIdentEntry 2 }

-- Table used for entering licenses/quering license status of features
licFeatureTable OBJECT-TYPE
	SYNTAX SEQUENCE OF LicFeatureTableEntry
	MAX-ACCESS not-accessible
	STATUS current
	DESCRIPTION
	"Table of features and their licenses as entered to each module."
	::= { licensePerModule 2 }

licFeatureTableEntry OBJECT-TYPE
	SYNTAX LicFeatureTableEntry
	MAX-ACCESS not-accessible
	STATUS current
	DESCRIPTION
	"An entry in the table, containing data about a particular feature
	on a particular module."
 	INDEX  { licModuleIdentIndex, licFeatureId }
	::= { licFeatureTable 1 }

LicFeatureTableEntry  ::=
	SEQUENCE  {
		licFeatureId INTEGER,
		licFeatureModifier OCTET STRING,
		licFeatureName  DisplayString,
		licFeatureLicense OCTET STRING,
		licFeatureLicenseStatus INTEGER
		}
	
licFeatureId OBJECT-TYPE
	SYNTAX INTEGER {
		smon(1),
		richLayer2(2),
		routing(3),
		serverLoadBalance(4),
		rfc1483(5),
		loadBalance(6),
		-- Numbers above 208 (0xD0)are reserved for host-based 
		-- applications. They are included here for completion sake.
		cajunViewPlus(208),
		realNetRules(209)
		}
	MAX-ACCESS read-only
	STATUS current
	DESCRIPTION
	"The basic feature type. Features numbered  208 (0xD0) and above
	 are reserved for host-based applications.
	"
	::= { licFeatureTableEntry 1 }

licFeatureModifier OBJECT-TYPE
	SYNTAX OCTET STRING (SIZE(1))
	MAX-ACCESS read-only
	STATUS current
	DESCRIPTION
	"The FeatureModifier field for this feature. 
	 value Set when a license is entered."
	::= { licFeatureTableEntry 2 }

licFeatureName OBJECT-TYPE
	SYNTAX DisplayString(SIZE(16))
	MAX-ACCESS read-only
	STATUS current
	DESCRIPTION
	"The name of the feature. Used by CLI commands.
	Must be a lowercase string without spaces.
	Feature Names:
	smon 	      - Switch Monitoring
	routing       -	Enable routing functions
	rich-layer-2  - Enable Policy calssifications and actions in 
			a Layer 2 switch
	server-load-balance - Load balancing server traffic.
	rfc-1483            - Enable RFC 1483 functions.
	load-balance        - Enable load balancing.
	cajun-view-plus     - host-based Network Managemnet application
	real-net-rules      - host-based Policy Management application."
	::= { licFeatureTableEntry 3 } 

licFeatureLicense OBJECT-TYPE
	SYNTAX OCTET STRING(SIZE(0..12))
	MAX-ACCESS read-write
	STATUS current
	DESCRIPTION
	"The License needed for this feature. The length serves to
	 diffrentiate between the old SMON scheme and the new versions.
	 9  octet string - license version 0x02 and onwards
	 12 octets string - old SMON license.
	 Note that on pre-configured devices, a feature may be active 
	 without a license key (License key=0)."
        DEFVAL{'0'H}
	::= { licFeatureTableEntry 4 }
licFeatureLicenseStatus OBJECT-TYPE
	SYNTAX INTEGER {
		licensed(1),
		unlicensed(2)
		}
	MAX-ACCESS read-only
	STATUS current
	DESCRIPTION
	"The state of the feature in terms of the licensing mechanism.
	State will change to licensed(1) if a valid license is enetered,
	or if the feature is somhow pre-configured.
	Note that a licensed feature may be inactive. However, an
	unlicened feature cannot be activated."
	::= { licFeatureTableEntry 5 }
END
