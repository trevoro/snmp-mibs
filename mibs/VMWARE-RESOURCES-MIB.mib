VMWARE-RESOURCES-MIB DEFINITIONS ::= BEGIN

IMPORTS
   OBJECT-TYPE 
      FROM RFC1155-SMI

   DisplayString 
      FROM RFC1213-MIB 

   vmwResources -- OBJECT IDENTIFIER ::= { vmware 3 }  
      FROM VMWARE-ROOT-MIB;

--      "This file contains the VMware MIB's subtree for resource variables.
--       Note: Throughout this file, the term 'machine' is used to refer to the
--       physical machine (on which the ESX Server is running). "

-- CPU subtree

vmwCPU OBJECT IDENTIFIER ::= { vmwResources 1 }

numCPUs OBJECT-TYPE
   SYNTAX	INTEGER
   ACCESS      	read-only
   STATUS      	mandatory
   DESCRIPTION
      "Number of physical CPUs on the system."
   ::= { vmwCPU 1 }

cpuTable OBJECT-TYPE
   SYNTAX	SEQUENCE OF CpuEntry
   ACCESS    	not-accessible	
   STATUS    	mandatory
   DESCRIPTION
      "CPU Usage table by virtual machine."
   ::= { vmwCPU 2 }

cpuEntry OBJECT-TYPE
   SYNTAX	CpuEntry
   ACCESS    	not-accessible	
   STATUS    	mandatory
   DESCRIPTION
      "A record for CPU usage by a single virtual machine."
   INDEX	{ cpuVMID }
   ::= { cpuTable 1 }

CpuEntry    ::= SEQUENCE
{
   cpuVMID 	INTEGER,
   cpuShares	INTEGER,
   cpuUtil	INTEGER
}

cpuVMID OBJECT-TYPE
   SYNTAX	INTEGER (0..1023)
   ACCESS    	read-only
   STATUS    	mandatory
   DESCRIPTION
      "ID allocated to running vm by the vmkernel."
   ::= { cpuEntry 1 }

cpuShares OBJECT-TYPE
   SYNTAX	INTEGER
   ACCESS    	read-only
   STATUS    	mandatory
   DESCRIPTION
      "Share of CPU allocated to vm by vmkernel."
   ::= { cpuEntry 2 }

cpuUtil OBJECT-TYPE
   SYNTAX       INTEGER	
   ACCESS    	read-only
   STATUS    	mandatory
   DESCRIPTION
      "Time the virtual machine has been running on the CPU (seconds)."
   ::= { cpuEntry 3 }

-- Memory subtree 

vmwMemory OBJECT IDENTIFIER ::= { vmwResources 2 }

memSize OBJECT-TYPE
   SYNTAX	INTEGER
   ACCESS    	read-only
   STATUS    	mandatory
   DESCRIPTION
      "Amount of physical memory present on machine (KB)."
   ::= { vmwMemory 1 }

memCOS OBJECT-TYPE
   SYNTAX	INTEGER
   ACCESS    	read-only
   STATUS    	mandatory
   DESCRIPTION
      "Amount of physical memory used by the console OS (KB)."
   ::= { vmwMemory 2 }

memAvail OBJECT-TYPE
   SYNTAX	INTEGER
   ACCESS    	read-only
   STATUS    	mandatory
   DESCRIPTION
      "Amount of physical memory available/free (KB)."
   ::= { vmwMemory 3 }

memTable OBJECT-TYPE
   SYNTAX	SEQUENCE OF MemEntry
   ACCESS    	not-accessible	
   STATUS    	mandatory
   DESCRIPTION
      "Table of memory usage by virtual machine."
   ::= { vmwMemory 4 }

memEntry OBJECT-TYPE
   SYNTAX	MemEntry
   ACCESS    	not-accessible	
   STATUS    	mandatory
   DESCRIPTION
      "A record for memory usage by a single virtual machine."
   INDEX	{ memVMID }
   ::= { memTable 1 }

MemEntry    ::= SEQUENCE
{
   memVMID		INTEGER,
   memShares	INTEGER,
   memConfigured INTEGER,
   memUtil      INTEGER	
}

memVMID OBJECT-TYPE
   SYNTAX	INTEGER (0..1023)
   ACCESS    	read-only
   STATUS    	mandatory
   DESCRIPTION
      "ID allocated to running vm by the vmkernel."
   ::= { memEntry 1 }

memShares OBJECT-TYPE
   SYNTAX	INTEGER
   ACCESS    	read-only
   STATUS    	mandatory
   DESCRIPTION
      "Shares of memory allocated to vm by vmkernel."
   ::= { memEntry 2 }

memConfigured OBJECT-TYPE
   SYNTAX	INTEGER
   ACCESS    	read-only
   STATUS    	mandatory
   DESCRIPTION
      "Amount of memory the vm was configured with. (KB)"
   ::= { memEntry 3 }

memUtil OBJECT-TYPE
   SYNTAX	INTEGER
   ACCESS    	read-only
   STATUS    	mandatory
   DESCRIPTION
      "Amount of memory utilized by the vm. (KB; instantaneous)"
   ::= { memEntry 4 }

-- Disk subtree --

vmwHBATable OBJECT-TYPE
   SYNTAX	SEQUENCE OF HbaEntry
   ACCESS    	not-accessible	
   STATUS    	mandatory
   DESCRIPTION
      "Disk adapter and target information table."
   ::= { vmwResources 3 }

hbaEntry OBJECT-TYPE
   SYNTAX	HbaEntry
   ACCESS     	not-accessible	
   STATUS    	mandatory
   DESCRIPTION
      "A record for a single hba on the machine."
   INDEX	{ hbaIdx }
   ::= { vmwHBATable 1 }

HbaEntry     ::= SEQUENCE
{
   hbaIdx  	INTEGER,
   hbaName	DisplayString,
   hbaVMID	INTEGER,
   diskShares	INTEGER,
   numReads	INTEGER,
   kbRead	INTEGER,
   numWrites	INTEGER,
   kbWritten	INTEGER
}


hbaIdx OBJECT-TYPE
   SYNTAX	INTEGER (0..255)
   ACCESS    	read-only
   STATUS    	mandatory
   DESCRIPTION
      "Index for HBA table."
   ::= { hbaEntry 1 }

hbaName OBJECT-TYPE
   SYNTAX	DisplayString	
   ACCESS    	read-only
   STATUS    	mandatory
   DESCRIPTION
      "String describing the disk. Format: <devname#>:<tgt>:<lun> "
   ::= { hbaEntry 2 }

hbaVMID OBJECT-TYPE
   SYNTAX	INTEGER
   ACCESS    	read-only
   STATUS    	mandatory
   DESCRIPTION
      "ID assigned to running vm by the vmkernel."
   ::= { hbaEntry 3 }

diskShares OBJECT-TYPE
   SYNTAX	INTEGER
   ACCESS    	read-only
   STATUS    	mandatory
   DESCRIPTION
      "Share of disk bandwidth allocated to this vm."
   ::= { hbaEntry 4 }

numReads OBJECT-TYPE
   SYNTAX	INTEGER
   ACCESS    	read-only
   STATUS    	mandatory
   DESCRIPTION
      "Number of reads to this disk since disk module was loaded."
   ::= { hbaEntry 5 }

kbRead OBJECT-TYPE
   SYNTAX	INTEGER	
   ACCESS    	read-only
   STATUS    	mandatory
   DESCRIPTION
      "Kilobytes read from this disk since disk module was loaded."
   ::= { hbaEntry 6 }

numWrites OBJECT-TYPE
   SYNTAX	INTEGER
   ACCESS    	read-only
   STATUS    	mandatory
   DESCRIPTION
      "Number of writes to this disk since disk module was loaded." 
   ::= { hbaEntry 7 }

kbWritten OBJECT-TYPE
   SYNTAX	INTEGER	
   ACCESS    	read-only
   STATUS    	mandatory
   DESCRIPTION
      "Kilobytes written to this disk since disk module was loaded."
   ::= { hbaEntry 8 }

-- Net subtree

vmwNetTable OBJECT-TYPE
   SYNTAX	SEQUENCE OF NetEntry
   ACCESS    	not-accessible	
   STATUS    	mandatory
   DESCRIPTION
      "Network adapter statistics."
   ::= { vmwResources 4 }

netEntry OBJECT-TYPE
   SYNTAX	NetEntry
   ACCESS     	not-accessible	
   STATUS    	mandatory
   DESCRIPTION
      "A record for a single nic on the machine."
   INDEX	{ netIdx }
   ::= { vmwNetTable 1 }

NetEntry     ::= SEQUENCE
{
   netIdx  	INTEGER,
   netName	DisplayString,
   netVMID	INTEGER,
   ifAddr       DisplayString,
   netShares	INTEGER,
   pktsTx       INTEGER,
   kbTx         INTEGER,
   pktsRx       INTEGER,
   kbRx         INTEGER
}


netIdx OBJECT-TYPE
   SYNTAX	INTEGER (0..255)
   ACCESS    	read-only
   STATUS    	mandatory
   DESCRIPTION
      "Index for net table."
   ::= { netEntry 1 }

netName OBJECT-TYPE
   SYNTAX	DisplayString	
   ACCESS    	read-only
   STATUS    	mandatory
   DESCRIPTION
      "String describing the network adapter. Format: vmnic*" 
   ::= { netEntry 2 }

netVMID OBJECT-TYPE
   SYNTAX	INTEGER
   ACCESS    	read-only
   STATUS    	mandatory
   DESCRIPTION
      "ID assigned to running vm by the vmkernel."
   ::= { netEntry 3 }

ifAddr OBJECT-TYPE
   SYNTAX	DisplayString	
   ACCESS    	read-only
   STATUS    	mandatory
   DESCRIPTION
      "MAC address of vm's virtual NIC." 
   ::= { netEntry 4 }

netShares OBJECT-TYPE
   SYNTAX       INTEGER 
   ACCESS       not-accessible	
   STATUS    	mandatory
   DESCRIPTION
      "Share of net bandwidth allocated to this vm. (NOT IMPLEMENTED)"
   ::= { netEntry 5 }

pktsTx OBJECT-TYPE
   SYNTAX	INTEGER
   ACCESS    	read-only
   STATUS    	mandatory
   DESCRIPTION
      "Number of pkts transmitted on this NIC since network module was loaded."
   ::= { netEntry 6 }

kbTx OBJECT-TYPE
   SYNTAX	INTEGER	
   ACCESS    	read-only
   STATUS    	mandatory
   DESCRIPTION
      "Kilobytes sent from this NIC since network module was loaded."
   ::= { netEntry 7 }

pktsRx OBJECT-TYPE
   SYNTAX	INTEGER
   ACCESS    	read-only
   STATUS    	mandatory
   DESCRIPTION
      "Number of pkts received on this NIC since network module was loaded."
   ::= { netEntry 8 }

kbRx OBJECT-TYPE
   SYNTAX	INTEGER	
   ACCESS    	read-only
   STATUS    	mandatory
   DESCRIPTION
      "Kilobytes received on this NIC since network module was loaded."
   ::= { netEntry 9 }

END
