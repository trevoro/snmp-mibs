-- File Name : Netrake.mib
-- Date      : Wed May 25 19:10:29 CDT 2005
-- Author    : AdventNet AgentToolkit (C Edition) - MibEditor 5.0

Netrake-MIB	DEFINITIONS ::= BEGIN
	IMPORTS
		DisplayString, DateAndTime, RowStatus
			FROM SNMPv2-TC
		DisplayString
			FROM RFC1213-MIB
		Gauge32, Counter32, Integer32, enterprises, MODULE-IDENTITY, OBJECT-TYPE, IpAddress, NOTIFICATION-TYPE, TimeTicks, Counter64
			FROM SNMPv2-SMI;

	netrake	MODULE-IDENTITY
		LAST-UPDATED	"200612131005Z"
		ORGANIZATION	"Netrake
                                 3000 Technology Drive
                                 Suite 100
                                 Plano, Texas 75074
                                 phone: 214 291 1000
                                 fax: 214 291 1010"
		CONTACT-INFO	"Netrake Corporation
                                 support@netrake.com, 
                                 www.netrake.com"
		DESCRIPTION	"nCite MIB"
		REVISION	"200109201005Z"
		DESCRIPTION	"0.1"
		REVISION	"200612131005Z"
		DESCRIPTION	"Add SIP Common and SIP Event Dialog
                                 statistics. Deprecate obsolete stats."
		REVISION	"200701051005Z"
		DESCRIPTION	"Deprecate diagnostics, add object identifiers."
		::=  {  enterprises  10950  }

	org	OBJECT IDENTIFIER
		::=  {  iso  3  }

	dod	OBJECT IDENTIFIER
		::=  {  org  6  }

	internet	OBJECT IDENTIFIER
		::=  {  dod  1  }

	private	OBJECT IDENTIFIER
		::=  {  internet  4  }

	enterprises	OBJECT IDENTIFIER
		::=  {  private  1  }

	products	OBJECT IDENTIFIER
		::=  {  netrake  1  }

	nCite	OBJECT IDENTIFIER
		::=  {  products  1  }

	chassis	OBJECT IDENTIFIER
		::=  {  nCite  1  }

	nCiteSystem	OBJECT IDENTIFIER
		::=  {  nCite  2  }

	alarm	OBJECT IDENTIFIER
		::=  {  nCite  3  }

	switchNotifications	OBJECT IDENTIFIER
		::=  {  nCite  4  }

	nCiteRedundant	OBJECT IDENTIFIER
		::=  {  nCite  5  }

	nCiteStats	OBJECT IDENTIFIER
		::=  {  nCite  6  }

	diagnostics	OBJECT IDENTIFIER
		::=  {  nCite  7  }

	policyProvisioning	OBJECT IDENTIFIER
		::=  {  nCite  8  }

	nCiteStaticRoutes	OBJECT IDENTIFIER
		::=  {  nCite  9  }

	nCiteArpConfig	OBJECT IDENTIFIER
		::=  {  nCite  10  }

	ipPortConfig	OBJECT IDENTIFIER
		::=  {  nCite  11  }

	nCiteOutSyncFlag	OBJECT-TYPE	
		SYNTAX			INTEGER  { no ( 0 ) , yes ( 1 ) } 
		MAX-ACCESS		read-write
		STATUS			deprecated
		DESCRIPTION		"This is currently not used."
		::=  {  nCite  12  }

	trapAckEnable	OBJECT-TYPE	
		SYNTAX			INTEGER  { disable ( 0 ) , enable ( 1 ) } 
		MAX-ACCESS		read-write
		STATUS			current
		DESCRIPTION		"Trap acknowledgement enable/disable flag"
		::=  {  nCite  13  }

	linkUpTrapAck	OBJECT-TYPE	
		SYNTAX			INTEGER  { notAck ( 0 ) , ack ( 1 ) } 
		MAX-ACCESS		read-write
		STATUS			current
		DESCRIPTION		"Notification when link state changes to up."
		::=  {  nCite  14  }

	linkDownTrapAck	OBJECT-TYPE	
		SYNTAX			INTEGER  { notAck ( 0 ) , ack ( 1 ) } 
		MAX-ACCESS		read-write
		STATUS			current
		DESCRIPTION		"Notificatin when link state changes to down."
		::=  {  nCite  15  }

	nCiteNTA	OBJECT IDENTIFIER
		::=  {  nCite  16  }

	nCiteRogue	OBJECT IDENTIFIER
		::=  {  nCite  17  }

	licenseInfo	OBJECT IDENTIFIER
		::=  {  nCite  18  }

	nCiteRIPConfig	OBJECT IDENTIFIER
		::=  {  nCite  19  }

	nCiteAuthConfig	OBJECT IDENTIFIER
		::=  {  nCite  20  }

	linkUpTrapAckSource	OBJECT-TYPE	
		SYNTAX			IpAddress
		MAX-ACCESS		read-write
		STATUS			current
		DESCRIPTION		"Identifies the Snmp Manager which sets the trap ack."
		::=  {  nCite  21  }

	linkDownTrapAckSource	OBJECT-TYPE	
		SYNTAX			IpAddress
		MAX-ACCESS		read-write
		STATUS			current
		DESCRIPTION		"Identifies the Snmp Manager which sets the trap ack."
		::=  {  nCite  22  }

	chasGen	OBJECT IDENTIFIER
		::=  {  chassis  1  }

	chasPwr	OBJECT IDENTIFIER
		::=  {  chassis  2  }

	chasFan	OBJECT IDENTIFIER
		::=  {  chassis  3  }

	chasBrd	OBJECT IDENTIFIER
		::=  {  chassis  4  }

	resourceUsageTable	OBJECT-TYPE
		SYNTAX		SEQUENCE  OF  ResourceUsageEntry
		MAX-ACCESS	not-accessible
		STATUS		current
		DESCRIPTION	"Description"
		::=  { nCiteSystem  1 }

	resourceUsageEntry	OBJECT-TYPE
		SYNTAX		ResourceUsageEntry
		MAX-ACCESS	not-accessible
		STATUS		current
		DESCRIPTION	"Row Description"
		INDEX		{  processorIndex  }
		::=  { resourceUsageTable 1 }

	ResourceUsageEntry  ::=  SEQUENCE {
		processorIndex  INTEGER,
		memTotal  Integer32,
		memUsed  Integer32,
		cpuUsage  Integer32
		}


	processorIndex	OBJECT-TYPE	
		SYNTAX			INTEGER  { managementProc ( 1 ) , controlProcA ( 2 ) , controlProcB ( 3 ) } 
		MAX-ACCESS		read-only
		STATUS			current
		DESCRIPTION		"There are three processors. This table contains the        
resource usage for each processor"
		::=  {  resourceUsageEntry  1  }


	memTotal	OBJECT-TYPE	
		SYNTAX			Integer32  ( -2147483648 .. 2147483647  ) 
		MAX-ACCESS		read-only
		STATUS			current
		DESCRIPTION		"Total amount of memory available."
		::=  {  resourceUsageEntry  2  }


	memUsed	OBJECT-TYPE	
		SYNTAX			Integer32
		MAX-ACCESS		read-only
		STATUS			current
		DESCRIPTION		"This is the percentage of memory in use at the time that   
the value is requested."
		::=  {  resourceUsageEntry  3  }


	cpuUsage	OBJECT-TYPE	
		SYNTAX			Integer32
		MAX-ACCESS		read-only
		STATUS			current
		DESCRIPTION		"This is the amount of CPU in use at the time this value is 
requested."
		::=  {  resourceUsageEntry  4  }

	systemSoftwareVersion	OBJECT-TYPE	
		SYNTAX			DisplayString
		MAX-ACCESS		read-only
		STATUS			current
		DESCRIPTION		"Software Version of the nCite"
		::=  {  nCiteSystem  2  }

	systemRestoreFlag	OBJECT-TYPE	
		SYNTAX			INTEGER  { normal ( 0 ) , outOfSync ( 1 ) , refreshStarted ( 2 ) } 
		MAX-ACCESS		read-write
		STATUS			deprecated
		DESCRIPTION		"Tells the EMS whether to push or pull the configuration.   
If the value is default(0) then the EMS pulls.  If the      
value is restore(1) then the EMS pushes."
		DEFVAL			{ normal }
		::=  {  nCiteSystem  3  }

	systemOperState	OBJECT-TYPE	
		SYNTAX			DisplayString
		MAX-ACCESS		read-only
		STATUS			current
		DESCRIPTION		"Operational state of the nCite"
		::=  {  nCiteSystem  4  }

	systemAdminState	OBJECT-TYPE	
		SYNTAX			INTEGER  { enable ( 1 ) , disable ( 2 ) } 
		MAX-ACCESS		read-write
		STATUS			current
		DESCRIPTION		"Administrative state of the nCite. Disabling the nCite     
stops all traffic from passing through the box."
		::=  {  nCiteSystem  5  }

	systemOperStateChangeTrap	NOTIFICATION-TYPE
		OBJECTS			{ systemOperState  }
		STATUS			current
		DESCRIPTION		"This trap is sent when the operational state of the nCite  
changes."
		::=  {  nCiteSystem  6  }

	systemOperStateChangeTrapAck	OBJECT-TYPE	
		SYNTAX			INTEGER  { notAck ( 0 ) , ack ( 1 ) } 
		MAX-ACCESS		read-write
		STATUS			current
		DESCRIPTION		"System operation state change trap flag"
		::=  {  nCiteSystem  7  }

	systemOperStateChangeTrapAckSource	OBJECT-TYPE	
		SYNTAX			IpAddress
		MAX-ACCESS		read-write
		STATUS			current
		DESCRIPTION		"Identifies the Snmp Manager which sets the trap ack."
		::=  {  nCiteSystem  8  }

	systemTrapAckTable	OBJECT-TYPE
		SYNTAX		SEQUENCE  OF  SystemTrapAckEntry
		MAX-ACCESS	not-accessible
		STATUS		current
		DESCRIPTION	"Table of SNMP Mgrs that are sending acknowledgements"
		::=  { nCiteSystem  9 }

	systemTrapAckEntry	OBJECT-TYPE
		SYNTAX		SystemTrapAckEntry
		MAX-ACCESS	not-accessible
		STATUS		current
		DESCRIPTION	"Row Description"
		INDEX		{  systemSnmpMgrIpAddress  }
		::=  { systemTrapAckTable 1 }

	SystemTrapAckEntry  ::=  SEQUENCE {
		systemSnmpMgrIpAddress  IpAddress,
		systemTrapNoAck  INTEGER
		}


	systemSnmpMgrIpAddress	OBJECT-TYPE	
		SYNTAX			IpAddress
		MAX-ACCESS		read-only
		STATUS			current
		DESCRIPTION		"IP address of SNMP Mgr that is sending Acks for traps"
		::=  {  systemTrapAckEntry  1  }


	systemTrapNoAck	OBJECT-TYPE	
		SYNTAX			INTEGER  { ok ( 0 ) , ackNotReceived ( 1 ) } 
		MAX-ACCESS		read-write
		STATUS			current
		DESCRIPTION		"When trap is not acknowledges the  value get set to      
ackNoReceived; EMS will set to OK upon refresh."
		::=  {  systemTrapAckEntry  2  }

	activeAlarmTable	OBJECT-TYPE
		SYNTAX		SEQUENCE  OF  ActiveAlarmEntry
		MAX-ACCESS	not-accessible
		STATUS		current
		DESCRIPTION	"Description"
		::=  { alarm  1 }

	activeAlarmEntry	OBJECT-TYPE
		SYNTAX		ActiveAlarmEntry
		MAX-ACCESS	not-accessible
		STATUS		current
		DESCRIPTION	"Row Description"
		INDEX		{  activeAlarmIndex  }
		::=  { activeAlarmTable 1 }

	ActiveAlarmEntry  ::=  SEQUENCE {
		activeAlarmIndex  Integer32,
		activeAlarmId  Integer32,
		activeAlarmType  Integer32,
		activeAlarmServiceAffecting  INTEGER,
		activeAlarmCategory  INTEGER,
		activeAlarmTimeStamp  DateAndTime,
		activeAlarmSlotNum  Integer32,
		activeAlarmPortNum  Integer32,
		activeAlarmSysUpTime  TimeTicks,
		activeAlarmDevType  INTEGER,
		activeAlarmAdditionalInfo  DisplayString,
		activeAlarmOccurances  Integer32,
		acitveAlarmReportingSource  Integer32,
		activeAlarmSeverity  INTEGER,
		activeAlarmDisplayString  DisplayString,
		activeAlarmSubType  Integer32,
		activeAlarmEventFlag  INTEGER
		}


	activeAlarmIndex	OBJECT-TYPE	
		SYNTAX			Integer32  ( -2147483648 .. 2147483647  ) 
		MAX-ACCESS		read-only
		STATUS			current
		DESCRIPTION		"Index into table for a specific alarm instance can change"
		::=  {  activeAlarmEntry  1  }


	activeAlarmId	OBJECT-TYPE	
		SYNTAX			Integer32  ( -2147483648 .. 2147483647  ) 
		MAX-ACCESS		read-only
		STATUS			current
		DESCRIPTION		"Unique identifier assigned to aninstance of an alarm."
		::=  {  activeAlarmEntry  2  }


	activeAlarmType	OBJECT-TYPE	
		SYNTAX			Integer32  ( -2147483648 .. 2147483647  ) 
		MAX-ACCESS		read-only
		STATUS			current
		DESCRIPTION		"Unique identifier associated with the alarm description"
		::=  {  activeAlarmEntry  3  }


	activeAlarmServiceAffecting	OBJECT-TYPE	
		SYNTAX			INTEGER  { notServiceAffecting ( 1 ) , serviceAffecting ( 2 ) } 
		MAX-ACCESS		read-only
		STATUS			current
		DESCRIPTION		"Indicates whether the alarm is service affecting"
		::=  {  activeAlarmEntry  4  }


	activeAlarmCategory	OBJECT-TYPE	
		SYNTAX			INTEGER  { hardware ( 1 ) , software ( 2 ) , service ( 3 ) } 
		MAX-ACCESS		read-only
		STATUS			current
		DESCRIPTION		"Categorizes the alarm into a class of alarms"
		::=  {  activeAlarmEntry  5  }


	activeAlarmTimeStamp	OBJECT-TYPE	
		SYNTAX			DateAndTime
		MAX-ACCESS		read-only
		STATUS			current
		DESCRIPTION		"Date and time that the alarm condition is detected"
		::=  {  activeAlarmEntry  6  }


	activeAlarmSlotNum	OBJECT-TYPE	
		SYNTAX			Integer32  ( 1 .. 14  ) 
		MAX-ACCESS		read-only
		STATUS			current
		DESCRIPTION		"Slot number of the card that has the condition being       
alarmed"
		::=  {  activeAlarmEntry  7  }


	activeAlarmPortNum	OBJECT-TYPE	
		SYNTAX			Integer32  ( 1 .. 48  ) 
		MAX-ACCESS		read-only
		STATUS			current
		DESCRIPTION		"If condition is against a port, this will hold the port    
number.  Otherwise it will be defaulted to 0."
		::=  {  activeAlarmEntry  8  }


	activeAlarmSysUpTime	OBJECT-TYPE	
		SYNTAX			TimeTicks
		MAX-ACCESS		read-only
		STATUS			current
		DESCRIPTION		"Value of system up time as reported in MIBII at the time   
that  the condition began"
		::=  {  activeAlarmEntry  9  }


	activeAlarmDevType	OBJECT-TYPE	
		SYNTAX			INTEGER  { managementProc ( 1 ) , controlProc ( 2 ) , netrakeControlProcessor ( 3 ) , gigE ( 4 ) , fastEther ( 5 ) , chassisFan ( 6 ) , chassisPowerSupply ( 7 ) , oc12 ( 8 ) , unknown ( 0 ) } 
		MAX-ACCESS		read-only
		STATUS			current
		DESCRIPTION		"Description"
		DEFVAL			{ unknown }
		::=  {  activeAlarmEntry  10  }


	activeAlarmAdditionalInfo	OBJECT-TYPE	
		SYNTAX			DisplayString  ( SIZE ( 0 .. 255  ) ) 
		MAX-ACCESS		read-only
		STATUS			current
		DESCRIPTION		"Additional information to be included in the alarm         
description"
		::=  {  activeAlarmEntry  11  }


	activeAlarmOccurances	OBJECT-TYPE	
		SYNTAX			Integer32  ( -2147483648 .. 2147483647  ) 
		MAX-ACCESS		read-only
		STATUS			current
		DESCRIPTION		"Number of times the condition has re-occurred since it     
was originated"
		::=  {  activeAlarmEntry  12  }


	acitveAlarmReportingSource	OBJECT-TYPE	
		SYNTAX			Integer32
		MAX-ACCESS		read-only
		STATUS			deprecated
		DESCRIPTION		"This has been deprecated"
		::=  {  activeAlarmEntry  13  }


	activeAlarmSeverity	OBJECT-TYPE	
		SYNTAX			INTEGER  { critical ( 1 ) , unknown ( 0 ) , major ( 2 ) , minor ( 3 ) , warning ( 4 ) , clear ( 5 ) , info ( 6 ) } 
		MAX-ACCESS		read-only
		STATUS			current
		DESCRIPTION		"Severity of the alarm"
		::=  {  activeAlarmEntry  14  }


	activeAlarmDisplayString	OBJECT-TYPE	
		SYNTAX			DisplayString
		MAX-ACCESS		read-only
		STATUS			current
		DESCRIPTION		"Description of the alarm to be used to display on the GUI"
		::=  {  activeAlarmEntry  15  }


	activeAlarmSubType	OBJECT-TYPE	
		SYNTAX			Integer32
		MAX-ACCESS		read-only
		STATUS			current
		DESCRIPTION		"Sub-type is used to distinguish alarms by a separate       
criteria such as customer ID or policy ID"
		::=  {  activeAlarmEntry  16  }


	activeAlarmEventFlag	OBJECT-TYPE	
		SYNTAX			INTEGER  { alarm ( 1 ) , event ( 2 ) } 
		MAX-ACCESS		read-only
		STATUS			current
		DESCRIPTION		"Description"
		::=  {  activeAlarmEntry  17  }

	histEvent	OBJECT IDENTIFIER
		::=  {  alarm  2  }

	postAlarm	NOTIFICATION-TYPE
		OBJECTS			{ acitveAlarmReportingSource ,activeAlarmAdditionalInfo ,activeAlarmCategory ,activeAlarmDevType ,activeAlarmDisplayString ,activeAlarmId ,activeAlarmOccurances ,activeAlarmPortNum ,activeAlarmServiceAffecting ,activeAlarmSeverity ,activeAlarmSlotNum ,activeAlarmSysUpTime ,activeAlarmTimeStamp ,activeAlarmType ,activeAlarmSubType ,activeAlarmEventFlag  }
		STATUS			current
		DESCRIPTION		"This notification is sent when an alarm becomes active"
		::=  {  alarm  3  }

	postEvent	OBJECT IDENTIFIER
		::=  {  alarm  4  }

	activeAlarmAcknowledge	OBJECT-TYPE	
		SYNTAX			INTEGER  { acknowledge ( 1 ) , cleared ( 0 ) } 
		MAX-ACCESS		read-write
		STATUS			current
		DESCRIPTION		"Value is set to acknowledged by the EMS when the alarm is  
received. It is set back to cleared by the agent"
		::=  {  alarm  5  }

	activeAlarmID	OBJECT-TYPE	
		SYNTAX			Integer32  ( -2147483648 .. 2147483647  ) 
		MAX-ACCESS		read-write
		STATUS			current
		DESCRIPTION		"Alarm ID of the alarm being acknowledged"
		::=  {  alarm  6  }

	eventAcknowledge	OBJECT IDENTIFIER
		::=  {  alarm  7  }

	eventID	OBJECT-TYPE	
		SYNTAX			Integer32  ( -2147483648 .. 2147483647  ) 
		MAX-ACCESS		read-write
		STATUS			deprecated
		DESCRIPTION		"Event ID for the event that is being acknowledged"
		::=  {  alarm  8  }

	activeAlarmAcknowledgeSource	OBJECT-TYPE	
		SYNTAX			IpAddress
		MAX-ACCESS		read-write
		STATUS			current
		DESCRIPTION		"Identifies the Snmp Manager which sets the alarm ack."
		::=  {  alarm  9  }

	coldStartTrapEnable	OBJECT-TYPE	
		SYNTAX			INTEGER  { enable ( 1 ) , disable ( 2 ) } 
		MAX-ACCESS		read-write
		STATUS			current
		DESCRIPTION		"Is used to disable the cold start trap"
		::=  {  switchNotifications  1  }

	coldStartTrap	NOTIFICATION-TYPE
		OBJECTS			{ systemRestoreFlag ,systemSoftwareVersion  }
		STATUS			current
		DESCRIPTION		"This trap is sent if trap is enabled when the Management   
Processor comes up from a cold start"
		::=  {  switchNotifications  2  }

	coldStartTrapAck	OBJECT-TYPE	
		SYNTAX			INTEGER  { notAck ( 0 ) , ack ( 1 ) } 
		MAX-ACCESS		read-write
		STATUS			current
		DESCRIPTION		"Cold start trap acknowledge flag"
		::=  {  switchNotifications  3  }

	coldStartTrapAckSource	OBJECT-TYPE	
		SYNTAX			IpAddress
		MAX-ACCESS		read-write
		STATUS			current
		DESCRIPTION		"Identifies the Snmp Manager which sets the trap ack."
		::=  {  switchNotifications  4  }

	redundantPort1IpAddr	OBJECT-TYPE	
		SYNTAX			IpAddress
		MAX-ACCESS		read-write
		STATUS			current
		DESCRIPTION		"IP address of the redundant port of the nCite MP"
		::=  {  nCiteRedundant  1  }

	redundantPort2IpAddr	OBJECT-TYPE	
		SYNTAX			IpAddress
		MAX-ACCESS		read-write
		STATUS			current
		DESCRIPTION		"Redundant port 2 IP address for the nCite MP"
		::=  {  nCiteRedundant  2  }

	redundantAdminState	OBJECT-TYPE	
		SYNTAX			INTEGER  { standAlone ( 1 ) , redundant ( 2 ) } 
		MAX-ACCESS		read-write
		STATUS			current
		DESCRIPTION		"Administrative state for redundancy."
		::=  {  nCiteRedundant  3  }

	redundantMateName	OBJECT-TYPE	
		SYNTAX			DisplayString  ( SIZE ( 0 .. 255  ) ) 
		MAX-ACCESS		read-write
		STATUS			current
		DESCRIPTION		"The name of the redundant nCite. This will be the chassis  
serial number when redundancy is enabled. If redundancy is  
not configured, then this field will be blank."
		::=  {  nCiteRedundant  4  }

	redundantConfigChangeTrapAck	OBJECT-TYPE	
		SYNTAX			INTEGER  { notAck ( 0 ) , ack ( 1 ) } 
		MAX-ACCESS		read-write
		STATUS			current
		DESCRIPTION		"Redundant config change trap acknowledge flag"
		::=  {  nCiteRedundant  6  }

	redundantConfigChangeTrap	NOTIFICATION-TYPE
		OBJECTS			{ redundantPairName ,redundantPort1IpAddr ,redundantPort2IpAddr ,redundantAdminState ,redundantPort1NetMask ,redundantPort2NetMask  }
		STATUS			current
		DESCRIPTION		"This trap is sent whenever the redundant configuration is  
modified"
		::=  {  nCiteRedundant  7  }

	redundantPort1NetMask	OBJECT-TYPE	
		SYNTAX			IpAddress
		MAX-ACCESS		read-write
		STATUS			current
		DESCRIPTION		"Net mask"
		::=  {  nCiteRedundant  8  }

	redundantPort2NetMask	OBJECT-TYPE	
		SYNTAX			IpAddress
		MAX-ACCESS		read-write
		STATUS			current
		DESCRIPTION		"Net mask"
		::=  {  nCiteRedundant  9  }

	redundantFailbackThresh	OBJECT-TYPE	
		SYNTAX			Integer32  ( 0 .. 50000  ) 
		MAX-ACCESS		read-write
		STATUS			current
		DESCRIPTION		"Failback threshold"
		::=  {  nCiteRedundant  10  }

	redundantRedirectorFlag	OBJECT-TYPE	
		SYNTAX			INTEGER  { disabled ( 0 ) , enabled ( 1 ) } 
		MAX-ACCESS		read-write
		STATUS			current
		DESCRIPTION		"When set to enable(1), the nCite supports load balancing   
on equal cost routes"
		::=  {  nCiteRedundant  11  }

	redundantFailbackThreshChangeTrap	NOTIFICATION-TYPE
		OBJECTS			{ redundantFailbackThresh  }
		STATUS			current
		DESCRIPTION		"This trap is sent whenever the failback threshold is       
modified"
		::=  {  nCiteRedundant  12  }

	redundantFailbackThreshChangeTrapAck	OBJECT-TYPE	
		SYNTAX			INTEGER  { default ( 0 ) , ack ( 1 ) } 
		MAX-ACCESS		read-write
		STATUS			current
		DESCRIPTION		"This value is set to acknowledge the redundant failback    
threshold change trap"
		::=  {  nCiteRedundant  13  }

	redundantRedirectorFlagChangeTrap	NOTIFICATION-TYPE
		OBJECTS			{ redundantRedirectorFlag  }
		STATUS			current
		DESCRIPTION		"This trap is sent whenever the redirector flag is changed"
		::=  {  nCiteRedundant  14  }

	redundantRedirectorFlagChangeTrapAck	OBJECT-TYPE	
		SYNTAX			INTEGER  { default ( 0 ) , ack ( 1 ) } 
		MAX-ACCESS		read-write
		STATUS			current
		DESCRIPTION		"Used to acknowledge the redirector flag change trap"
		::=  {  nCiteRedundant  15  }

	redundantAutoFailbackFlag	OBJECT-TYPE	
		SYNTAX			INTEGER  { disabled ( 0 ) , enabled ( 1 ) } 
		MAX-ACCESS		read-write
		STATUS			current
		DESCRIPTION		"When set to enable(1), the nCite supports automatic        
failback"
		::=  {  nCiteRedundant  16  }

	redundantAutoFailbackChangeTrap	NOTIFICATION-TYPE
		OBJECTS			{ redundantAutoFailbackFlag  }
		STATUS			current
		DESCRIPTION		"This trap is sent whenever the automatic failback flag is  
changed"
		::=  {  nCiteRedundant  17  }

	redundantAutoFailbackFlagChangeTrapAck	OBJECT-TYPE	
		SYNTAX			INTEGER  { default ( 0 ) , ack ( 1 ) } 
		MAX-ACCESS		read-write
		STATUS			current
		DESCRIPTION		"Used to acknowledge the automatic failback flag change     
trap"
		::=  {  nCiteRedundant  18  }

	redundantConfigChangeTrapAckSource	OBJECT-TYPE	
		SYNTAX			IpAddress
		MAX-ACCESS		read-write
		STATUS			current
		DESCRIPTION		"Identifies the Snmp Manager which sets the trap ack."
		::=  {  nCiteRedundant  19  }

	redundantFailbackThreshChangeTrapAckSource	OBJECT-TYPE	
		SYNTAX			IpAddress
		MAX-ACCESS		read-write
		STATUS			current
		DESCRIPTION		"Identifies the Snmp Manager which sets the trap ack flag."
		::=  {  nCiteRedundant  20  }

	redundantRedirectorFlagChangeTrapAckSource	OBJECT-TYPE	
		SYNTAX			IpAddress
		MAX-ACCESS		read-write
		STATUS			current
		DESCRIPTION		"Identifies the Snmp Manager which sets the trap ack."
		::=  {  nCiteRedundant  21  }

	redundantAutoFailbackFlagChangeTrapAckSource	OBJECT-TYPE	
		SYNTAX			IpAddress
		MAX-ACCESS		read-write
		STATUS			current
		DESCRIPTION		"Identifies the Snmp Manager which sets the trap ack."
		::=  {  nCiteRedundant  22  }

	globalCounters	OBJECT IDENTIFIER
		::=  {  nCiteStats  1  }

	gigEStats	OBJECT IDENTIFIER
		::=  {  nCiteStats  2  }

	serviceStats	OBJECT IDENTIFIER
		::=  {  nCiteStats  3  }

	redundancyStats	OBJECT IDENTIFIER
		::=  {  nCiteStats  4  }

	policyStats	OBJECT IDENTIFIER
		::=  {  nCiteStats  5  }

	sipStats	OBJECT IDENTIFIER
		::=  {  nCiteStats  6  }

	vlanStats	OBJECT IDENTIFIER
		::=  {  nCiteStats  7  }

	custSipStats	OBJECT IDENTIFIER
		::=  {  nCiteStats  8  }

	nCiteStatsConfigReset	OBJECT-TYPE	
		SYNTAX			INTEGER  { default ( 0 ) , reset ( 1 ) } 
		MAX-ACCESS		read-write
		STATUS			current
		DESCRIPTION		"This value is set whenever the equipment configuration     
changes(i.e. a line card is added or removed)."
		::=  {  nCiteStats  9  }

	nCiteSessionDetailRecord	OBJECT IDENTIFIER
		::=  {  nCiteStats  10  }

	registrationStats	OBJECT IDENTIFIER
		::=  {  nCiteStats  11  }

	custRegStats	OBJECT IDENTIFIER
		::=  {  nCiteStats  12  }

	ntsStats	OBJECT IDENTIFIER
		::=  {  nCiteStats  13  }

	rogueStats	OBJECT IDENTIFIER
		::=  {  nCiteStats  14  }

	nCiteStatsReset	OBJECT-TYPE	
		SYNTAX			INTEGER  { default ( 0 ) , 
                                                sipStats ( 1 ) , 
                                                registrationStats ( 2 ) , 
                                                rogueStats ( 3 ) , 
                                                ntsStats ( 4 ) , 
                                                voIpStats ( 5 ) , 
                                                sipH323Stats ( 6 ) , 
                                                h323Stats ( 7 ) , 
                                                h323RegStats ( 8 ) , 
                                                mediaStats ( 9 ),
                                                sipCommonStats ( 10 ),
                                                sipEvtDlgStats (11)
                                        } 
		MAX-ACCESS		read-write
		STATUS			current
		DESCRIPTION		
                        "This value is set when a group of statistics has been
                        requested to be reset"
		::=  {  nCiteStats  15  }

	custNtsStats	OBJECT IDENTIFIER
		::=  {  nCiteStats  16  }

	sipH323Stats	OBJECT IDENTIFIER
		::=  {  nCiteStats  17  }

	h323Stats	OBJECT IDENTIFIER
		::=  {  nCiteStats  18  }

	voIpStats	OBJECT IDENTIFIER
		::=  {  nCiteStats  19  }

	custSipH323Stats	OBJECT IDENTIFIER
		::=  {  nCiteStats  20  }

	custH323Stats	OBJECT IDENTIFIER
		::=  {  nCiteStats  21  }

	custVoIpStats	OBJECT IDENTIFIER
		::=  {  nCiteStats  22  }

	mediaStats	OBJECT IDENTIFIER
		::=  {  nCiteStats  23  }

	h323RegStats	OBJECT IDENTIFIER
		::=  {  nCiteStats  24  }

	custH323RegStats	OBJECT IDENTIFIER
		::=  {  nCiteStats  25  }

        sipCommonStats OBJECT IDENTIFIER
                ::= { nCiteStats 26 }
        
        sipEvtDlgStats OBJECT IDENTIFIER
                ::= { nCiteStats 27 }
                                
	runDiagGroup	OBJECT IDENTIFIER
		::=  {  diagnostics  2  }

	diagResultsTable	OBJECT-TYPE
		SYNTAX		SEQUENCE  OF  DiagResultsEntry
		MAX-ACCESS	not-accessible
		STATUS		deprecated
		DESCRIPTION	"Table contains historical results of diagnostics"
		::=  { diagnostics  3 }

	diagResultsEntry	OBJECT-TYPE
		SYNTAX		DiagResultsEntry
		MAX-ACCESS	not-accessible
		STATUS		deprecated
		DESCRIPTION	"Row Description"
		INDEX		{  diagRsltIndex  }
		::=  { diagResultsTable 1 }

	DiagResultsEntry  ::=  SEQUENCE {
		diagRsltIndex  Integer32,
		diagRsltStartTimeStamp  DateAndTime,
		diagRsltCompleteTimeStamp  DateAndTime,
		diagRsltDesc  DisplayString,
		diagRsltType  INTEGER,
		diagRsltDeviceSlotNum  Integer32,
		diagRsltDevicePortNum  Integer32
		}


	diagRsltIndex	OBJECT-TYPE	
		SYNTAX			Integer32
		MAX-ACCESS		read-only
		STATUS			deprecated
		DESCRIPTION		"Column Description"
		::=  {  diagResultsEntry  1  }


	diagRsltStartTimeStamp	OBJECT-TYPE	
		SYNTAX			DateAndTime
		MAX-ACCESS		read-only
		STATUS			deprecated
		DESCRIPTION		"Time that the diagnostic was started"
		::=  {  diagResultsEntry  2  }


	diagRsltCompleteTimeStamp	OBJECT-TYPE	
		SYNTAX			DateAndTime
		MAX-ACCESS		read-only
		STATUS			deprecated
		DESCRIPTION		"Date/time the diagnostic completed"
		::=  {  diagResultsEntry  3  }


	diagRsltDesc	OBJECT-TYPE	
		SYNTAX			DisplayString  ( SIZE ( 0 .. 255  ) ) 
		MAX-ACCESS		read-only
		STATUS			deprecated
		DESCRIPTION		"Description of the results"
		::=  {  diagResultsEntry  4  }


	diagRsltType	OBJECT-TYPE	
		SYNTAX			INTEGER  { nCiteFullIntLoopback ( 1 ) , nCiteFullExtLoopback ( 2 ) , nCiteInterfaceIntLoopback ( 3 ) , nCiteInterfaceExtLoopback ( 4 ) , cardIntLoopback ( 5 ) , cardExtLoopback ( 6 ) , portIntLoopback ( 7 ) , portExtLoopback ( 8 ) } 
		MAX-ACCESS		read-only
		STATUS			deprecated
		DESCRIPTION		"Description"
		::=  {  diagResultsEntry  5  }


	diagRsltDeviceSlotNum	OBJECT-TYPE	
		SYNTAX			Integer32  ( 1 .. 14  ) 
		MAX-ACCESS		read-only
		STATUS			deprecated
		DESCRIPTION		"Device slot number 					 that 					 					 					 executed   
					  					the  					 diagnostic"
		::=  {  diagResultsEntry  6  }


	diagRsltDevicePortNum	OBJECT-TYPE	
		SYNTAX			Integer32  ( 1 .. 48  ) 
		MAX-ACCESS		read-only
		STATUS			deprecated
		DESCRIPTION		"Device port number"
		::=  {  diagResultsEntry  7  }

	diagStartedTrap	NOTIFICATION-TYPE
		OBJECTS			{ diagType  }
		STATUS			deprecated
		DESCRIPTION		"This trap is sent when the diagnostic is started"
		::=  {  diagnostics  4  }

	diagCompleteTrap	NOTIFICATION-TYPE
		OBJECTS			{ diagRsltIndex ,diagRsltCompleteTimeStamp ,diagRsltDesc ,diagRsltDevicePortNum ,diagRsltDeviceSlotNum ,diagRsltType  }
		STATUS			deprecated
		DESCRIPTION		"This trap is sent when the diagnostic has completed"
		::=  {  diagnostics  5  }

	diagRsltID	OBJECT-TYPE	
		SYNTAX			Integer32
		MAX-ACCESS		read-write
		STATUS			deprecated
		DESCRIPTION		"Table entry to delete"
		::=  {  diagnostics  6  }

	diagRsltAcknowledge	OBJECT-TYPE	
		SYNTAX			INTEGER  { default ( 0 ) , acknowledge ( 1 ) } 
		MAX-ACCESS		read-write
		STATUS			deprecated
		DESCRIPTION		"Acknowledge for diagnostic"
		::=  {  diagnostics  7  }

	diagStartedTrapAck	OBJECT-TYPE	
		SYNTAX			INTEGER  { notAck ( 0 ) , ack ( 1 ) } 
		MAX-ACCESS		read-write
		STATUS			deprecated
		DESCRIPTION		"Diag start trap acknowledge flag"
		::=  {  diagnostics  8  }

	diagCompleteTrapAck	OBJECT-TYPE	
		SYNTAX			INTEGER  { notAck ( 0 ) , ack ( 1 ) } 
		MAX-ACCESS		read-write
		STATUS			deprecated
		DESCRIPTION		"Diag complete trap acknowledge flag"
		::=  {  diagnostics  9  }

	diagStartedTrapAckSource	OBJECT-TYPE	
		SYNTAX			IpAddress
		MAX-ACCESS		read-write
		STATUS			deprecated
		DESCRIPTION		"Identifies the Snmp Manager which sets the trap ack."
		::=  {  diagnostics  10  }

	diagCompleteTrapAckSource	OBJECT-TYPE	
		SYNTAX			IpAddress
		MAX-ACCESS		read-write
		STATUS			deprecated
		DESCRIPTION		"Identifies the Snmp Manager which sets the trap ack."
		::=  {  diagnostics  11  }

	activeImgName	OBJECT-TYPE	
		SYNTAX			DisplayString  ( SIZE ( 0 .. 255  ) ) 
		MAX-ACCESS		read-only
		STATUS			current
		DESCRIPTION		"Name of the XML file that is currently active on the nCite"
		::=  {  policyProvisioning  1  }

	activeImgPidSideAFilename	OBJECT-TYPE	
		SYNTAX			DisplayString  ( SIZE ( 0 .. 255  ) ) 
		MAX-ACCESS		read-only
		STATUS			deprecated
		DESCRIPTION		"Filename of the PID map for side A"
		::=  {  policyProvisioning  2  }

	activeImgPidSideBFilename	OBJECT-TYPE	
		SYNTAX			DisplayString  ( SIZE ( 0 .. 255  ) ) 
		MAX-ACCESS		read-only
		STATUS			deprecated
		DESCRIPTION		"Filename of the PID map for side B"
		::=  {  policyProvisioning  3  }

	activeImgDwnldTimeStamp	OBJECT-TYPE	
		SYNTAX			DateAndTime
		MAX-ACCESS		read-only
		STATUS			current
		DESCRIPTION		"Date/time that the active image file was downloaded"
		::=  {  policyProvisioning  4  }

	activeImgBuildStartTimeStamp	OBJECT-TYPE	
		SYNTAX			DateAndTime
		MAX-ACCESS		read-only
		STATUS			deprecated
		DESCRIPTION		"Date/time that the active image started building"
		::=  {  policyProvisioning  5  }

	activeImgBuildCompleteTimeStamp	OBJECT-TYPE	
		SYNTAX			DateAndTime
		MAX-ACCESS		read-only
		STATUS			deprecated
		DESCRIPTION		"Date/time that the active image completed  building"
		::=  {  policyProvisioning  6  }

	activeImgActivatedTimeStamp	OBJECT-TYPE	
		SYNTAX			DateAndTime
		MAX-ACCESS		read-only
		STATUS			current
		DESCRIPTION		"Date/time that the active image was activated"
		::=  {  policyProvisioning  7  }

	commitImgName	OBJECT-TYPE	
		SYNTAX			DisplayString  ( SIZE ( 0 .. 255  ) ) 
		MAX-ACCESS		read-only
		STATUS			current
		DESCRIPTION		"Name of the XML file that was committed"
		::=  {  policyProvisioning  8  }

	commitImgDwnldTimeStamp	OBJECT-TYPE	
		SYNTAX			DateAndTime
		MAX-ACCESS		read-only
		STATUS			deprecated
		DESCRIPTION		"Date/time that the committed image was downloaded"
		::=  {  policyProvisioning  9  }

	commitImgBuildStartTimeStamp	OBJECT-TYPE	
		SYNTAX			DateAndTime
		MAX-ACCESS		read-only
		STATUS			deprecated
		DESCRIPTION		"Date/time that the committed image started building"
		::=  {  policyProvisioning  10  }

	commitImgBuildCompleteTimeStamp	OBJECT-TYPE	
		SYNTAX			DateAndTime
		MAX-ACCESS		read-only
		STATUS			deprecated
		DESCRIPTION		"Date/time that the committed image completed building"
		::=  {  policyProvisioning  11  }

	commitImgActivatedTimeStamp	OBJECT-TYPE	
		SYNTAX			DateAndTime
		MAX-ACCESS		read-only
		STATUS			current
		DESCRIPTION		"Date/time that the committed image was activated"
		::=  {  policyProvisioning  12  }

	commitImgTimeStamp	OBJECT-TYPE	
		SYNTAX			DateAndTime
		MAX-ACCESS		read-only
		STATUS			current
		DESCRIPTION		"Date/time that the image was committed"
		::=  {  policyProvisioning  13  }

	newActiveImgTrap	NOTIFICATION-TYPE
		OBJECTS			{ activeImgActivatedTimeStamp ,activeImgName ,activeImgPidSideAFilename ,activeImgPidSideBFilename  }
		STATUS			current
		DESCRIPTION		"This trap is sent whenever a new image activated"
		::=  {  policyProvisioning  14  }

	newCommittedImgTrap	NOTIFICATION-TYPE
		OBJECTS			{ commitImgTimeStamp ,commitImgName  }
		STATUS			current
		DESCRIPTION		"This trap is sent whenever an active image is committed"
		::=  {  policyProvisioning  15  }

	nextImgName	OBJECT-TYPE	
		SYNTAX			DisplayString  ( SIZE ( 0 .. 255  ) ) 
		MAX-ACCESS		read-only
		STATUS			deprecated
		DESCRIPTION		"Name of the xml file that has been downloaded for a build"
		::=  {  policyProvisioning  16  }

	nextImgState	OBJECT-TYPE	
		SYNTAX			INTEGER  { cleared ( 0 ) , buildInProgress ( 1 ) , buildComplete ( 2 ) } 
		MAX-ACCESS		read-only
		STATUS			deprecated
		DESCRIPTION		"This reflects the state of the next image."
		::=  {  policyProvisioning  17  }

	nextImgDwnldTimeStamp	OBJECT-TYPE	
		SYNTAX			DateAndTime
		MAX-ACCESS		read-only
		STATUS			deprecated
		DESCRIPTION		"Date/time that the image was downloaded"
		::=  {  policyProvisioning  18  }

	nextImgBuildStartTimeStamp	OBJECT-TYPE	
		SYNTAX			DateAndTime
		MAX-ACCESS		read-only
		STATUS			deprecated
		DESCRIPTION		"Date/time that the next image started building.  This      
field will be defaulted if building has not started"
		::=  {  policyProvisioning  19  }

	nextImgBuildCompleteTimeStamp	OBJECT-TYPE	
		SYNTAX			DateAndTime
		MAX-ACCESS		read-only
		STATUS			deprecated
		DESCRIPTION		"Date/time that the next image completed building.  This    
field will be defaulted of it was not built."
		::=  {  policyProvisioning  20  }

	buildStartedTrap	NOTIFICATION-TYPE
		OBJECTS			{ nextImg ,nextImgState }
		STATUS			deprecated
		DESCRIPTION		"Trap sent when a build is started on the nCite"
		::=  {  policyProvisioning  21  }

	buildCompleteTrap	NOTIFICATION-TYPE
		OBJECTS			{ nextImgName ,nextImgState ,nextImgBuildCompleteTimeStamp }
		STATUS			deprecated
		DESCRIPTION		"Description"
		::=  {  policyProvisioning  22  }

	newNextTrap	NOTIFICATION-TYPE
		OBJECTS			{ nextImgName ,nextImgState }
		STATUS			deprecated
		DESCRIPTION		"This trap is sent whenever an XML file is downloaded to    
the nCite"
		::=  {  policyProvisioning  23  }

	newActiveImgTrapAck	OBJECT-TYPE	
		SYNTAX			INTEGER  { notAck ( 0 ) , ack ( 1 ) } 
		MAX-ACCESS		read-write
		STATUS			current
		DESCRIPTION		"New active image trap acknowledge flag"
		::=  {  policyProvisioning  24  }

	newCommittedImgTrapAck	OBJECT-TYPE	
		SYNTAX			INTEGER  { notAck ( 0 ) , ack ( 1 ) } 
		MAX-ACCESS		read-write
		STATUS			current
		DESCRIPTION		"New committed image trap acknowlege flag"
		::=  {  policyProvisioning  25  }

	buildStartedTrapAck	OBJECT-TYPE	
		SYNTAX			INTEGER  { notAck ( 0 ) , ack ( 1 ) } 
		MAX-ACCESS		read-write
		STATUS			deprecated
		DESCRIPTION		"Build started trap acknowledge flag"
		::=  {  policyProvisioning  26  }

	buildCompleteTrapAck	OBJECT-TYPE	
		SYNTAX			INTEGER  { notAck ( 0 ) , ack ( 1 ) } 
		MAX-ACCESS		read-write
		STATUS			deprecated
		DESCRIPTION		"Build complete trap acknowledge flag"
		::=  {  policyProvisioning  27  }

	newNextTrapAck	OBJECT-TYPE	
		SYNTAX			INTEGER  { notAck ( 0 ) , ack ( 1 ) } 
		MAX-ACCESS		read-write
		STATUS			deprecated
		DESCRIPTION		"New next trap acknowledge flag"
		::=  {  policyProvisioning  28  }

	newActiveImgTrapAckSource	OBJECT-TYPE	
		SYNTAX			IpAddress
		MAX-ACCESS		read-write
		STATUS			current
		DESCRIPTION		"Identifies the Snmp Manager which sets the trap ack."
		::=  {  policyProvisioning  29  }

	newCommittedImgTrapAckSource	OBJECT-TYPE	
		SYNTAX			IpAddress
		MAX-ACCESS		read-write
		STATUS			current
		DESCRIPTION		"Identifies the Snmp Manager which sets the trap ack."
		::=  {  policyProvisioning  30  }

	buildStartedTrapAckSource	OBJECT-TYPE	
		SYNTAX			IpAddress
		MAX-ACCESS		read-write
		STATUS			deprecated
		DESCRIPTION		"Identifies the Snmp Manager that sets the trap ack."
		::=  {  policyProvisioning  31  }

	buildCompleteTrapAckSource	OBJECT-TYPE	
		SYNTAX			IpAddress
		MAX-ACCESS		read-write
		STATUS			deprecated
		DESCRIPTION		"Identifies the Snmp Manager which sets the trap ack."
		::=  {  policyProvisioning  32  }

	newNextTrapAckSource	OBJECT-TYPE	
		SYNTAX			IpAddress
		MAX-ACCESS		read-write
		STATUS			deprecated
		DESCRIPTION		"Identifies the Snmp Manager which sets the trap ack."
		::=  {  policyProvisioning  33  }

	staticRoutesTable	OBJECT-TYPE
		SYNTAX		SEQUENCE  OF  StaticRoutesEntry
		MAX-ACCESS	not-accessible
		STATUS		current
		DESCRIPTION	"Description"
		::=  { nCiteStaticRoutes  1 }

	staticRoutesEntry	OBJECT-TYPE
		SYNTAX		StaticRoutesEntry
		MAX-ACCESS	not-accessible
		STATUS		current
		DESCRIPTION	"Row Description"
		INDEX		{  staticRouteDest, staticRouteNextHop, staticRouteNetMask  }
		::=  { staticRoutesTable 1 }

	StaticRoutesEntry  ::=  SEQUENCE {
		staticRouteDest  IpAddress,
		staticRouteNextHop  IpAddress,
		staticRouteNetMask  IpAddress,
		staticRouteIngressVlanTag  Integer32,
		staticRouteMetric1  Integer32,
		staticRouteAdminState  INTEGER,
		staticRouteIngressProtocol  INTEGER,
		staticRouteOperState  DisplayString,
		staticRouteType  INTEGER,
		staticRouteRowStatus  RowStatus,
		staticRouteVrdTag  Integer32,
		staticRouteEgressVlan  Integer32
		}


	staticRouteDest	OBJECT-TYPE	
		SYNTAX			IpAddress
		MAX-ACCESS		read-write
		STATUS			current
		DESCRIPTION		"Column Description"
		::=  {  staticRoutesEntry  1  }


	staticRouteNextHop	OBJECT-TYPE	
		SYNTAX			IpAddress
		MAX-ACCESS		read-write
		STATUS			current
		DESCRIPTION		"Next hop ip address"
		::=  {  staticRoutesEntry  2  }


	staticRouteNetMask	OBJECT-TYPE	
		SYNTAX			IpAddress
		MAX-ACCESS		read-write
		STATUS			current
		DESCRIPTION		"Network mask"
		DEFVAL			{ '00000000'h }
		::=  {  staticRoutesEntry  3  }


	staticRouteIngressVlanTag	OBJECT-TYPE	
		SYNTAX			Integer32  ( 0 .. 4096  ) 
		MAX-ACCESS		read-write
		STATUS			deprecated
		DESCRIPTION		"Static route Ingress VLAN tag; 4096 when not applicable"
		DEFVAL			{ 0 }
		::=  {  staticRoutesEntry  4  }


	staticRouteMetric1	OBJECT-TYPE	
		SYNTAX			Integer32  ( -1 .. 255  ) 
		MAX-ACCESS		read-write
		STATUS			current
		DESCRIPTION		"The primary routing metric for this static route; -1 if    
not applicable"
		DEFVAL			{ -1 }
		::=  {  staticRoutesEntry  5  }


	staticRouteAdminState	OBJECT-TYPE	
		SYNTAX			INTEGER  { enable ( 1 ) , disable ( 2 ) } 
		MAX-ACCESS		read-write
		STATUS			current
		DESCRIPTION		"Enables/disables the route"
		DEFVAL			{ enable }
		::=  {  staticRoutesEntry  6  }


	staticRouteIngressProtocol	OBJECT-TYPE	
		SYNTAX			INTEGER  { general ( 0 ) , vlan ( 1 ) } 
		MAX-ACCESS		read-write
		STATUS			deprecated
		DESCRIPTION		"Description"
		DEFVAL			{ general }
		::=  {  staticRoutesEntry  7  }


	staticRouteOperState	OBJECT-TYPE	
		SYNTAX			DisplayString
		MAX-ACCESS		read-only
		STATUS			current
		DESCRIPTION		"Operational state of static route"
		::=  {  staticRoutesEntry  8  }


	staticRouteType	OBJECT-TYPE	
		SYNTAX			INTEGER  { userDefined ( 1 ) , discovered ( 2 ) , defaultRoute ( 3 ) , mgmtRoute ( 4 ) , dcHostRoute ( 5 ) , dcNetRoute ( 6 ) } 
		MAX-ACCESS		read-only
		STATUS			current
		DESCRIPTION		"userDefined = Static Route; user can not modify           
discovered, DC Host, or DC Net routes"
		::=  {  staticRoutesEntry  9  }


	staticRouteRowStatus	OBJECT-TYPE	
		SYNTAX			RowStatus
		MAX-ACCESS		read-create
		STATUS			current
		DESCRIPTION		"Allows adding and deleting of entries"
		::=  {  staticRoutesEntry  10  }


	staticRouteVrdTag	OBJECT-TYPE	
		SYNTAX			Integer32  ( 0 .. 4095  ) 
		MAX-ACCESS		read-only
		STATUS			current
		DESCRIPTION		"Virtual Routing Domain associated with the interface for   
this route"
		::=  {  staticRoutesEntry  11  }


	staticRouteEgressVlan	OBJECT-TYPE	
		SYNTAX			Integer32  ( 0 .. 4095  ) 
		MAX-ACCESS		read-only
		STATUS			current
		DESCRIPTION		"Egress Vlan associated with interface"
		::=  {  staticRoutesEntry  12  }

	staticRouteChange	NOTIFICATION-TYPE
		OBJECTS			{ staticRouteAdminState ,staticRouteDest ,staticRouteIngressVlanTag ,staticRouteIngressProtocol ,staticRouteMetric1 ,staticRouteNetMask ,staticRouteNextHop ,staticRouteOperState ,staticRouteRowStatus ,staticRouteType  }
		STATUS			current
		DESCRIPTION		"This trap is sent whenever changes are made to a static    
route"
		::=  {  nCiteStaticRoutes  2  }

	staticRoutesRefreshNeeded	OBJECT-TYPE	
		SYNTAX			INTEGER  { default ( 0 ) , refresh ( 1 ) } 
		MAX-ACCESS		read-write
		STATUS			current
		DESCRIPTION		"This field indicates that changes were made to the static  
routes"
		::=  {  nCiteStaticRoutes  3  }

	staticRoutesRefreshTrap	NOTIFICATION-TYPE
		OBJECTS			{ staticRoutesRefreshNeeded  }
		STATUS			current
		DESCRIPTION		"This trap is sent whenever static route states change"
		::=  {  nCiteStaticRoutes  4  }

	staticRouteChangeTrapAck	OBJECT-TYPE	
		SYNTAX			INTEGER  { notAck ( 0 ) , ack ( 1 ) } 
		MAX-ACCESS		read-write
		STATUS			current
		DESCRIPTION		"Static route change trap acknowledge flag"
		::=  {  nCiteStaticRoutes  5  }

	staticRouteRefreshTrapAck	OBJECT-TYPE	
		SYNTAX			INTEGER  { notAck ( 0 ) , ack ( 1 ) } 
		MAX-ACCESS		read-write
		STATUS			current
		DESCRIPTION		"Static route change trap acknowledge flag"
		::=  {  nCiteStaticRoutes  6  }

	staticRouteChangeTrapAckSource	OBJECT-TYPE	
		SYNTAX			IpAddress
		MAX-ACCESS		read-write
		STATUS			current
		DESCRIPTION		"Identifies the Snmp Manager which sets the trap ack."
		::=  {  nCiteStaticRoutes  7  }

	staticRouteRefreshTrapAckSource	OBJECT-TYPE	
		SYNTAX			IpAddress
		MAX-ACCESS		read-write
		STATUS			current
		DESCRIPTION		"Identifies the Snmp Manager which sets the trap ack."
		::=  {  nCiteStaticRoutes  8  }

	arpVerifTimerRetryCount	OBJECT-TYPE	
		SYNTAX			Integer32  ( 1 .. 3600  ) 
		MAX-ACCESS		read-write
		STATUS			current
		DESCRIPTION		"Defines how often the nCite performs ARPs"
		DEFVAL			{ 1 }
		::=  {  nCiteArpConfig  1  }

	arpNextHopIP	OBJECT-TYPE	
		SYNTAX			IpAddress
		MAX-ACCESS		read-only
		STATUS			current
		DESCRIPTION		"Next hop ip address"
		::=  {  nCiteArpConfig  2  }

	arpMacAddr	OBJECT-TYPE	
		SYNTAX			DisplayString
		MAX-ACCESS		read-only
		STATUS			current
		DESCRIPTION		"mac address"
		::=  {  nCiteArpConfig  3  }

	arpRefreshNeeded	OBJECT-TYPE	
		SYNTAX			Integer32  ( -2147483648 .. 2147483647  ) 
		MAX-ACCESS		read-write
		STATUS			current
		DESCRIPTION		"This value is used in a trap to notifiy the EMS when the   
ARP table needs to be refreshed."
		::=  {  nCiteArpConfig  4  }

	arpRefreshTrap	NOTIFICATION-TYPE
		OBJECTS			{ arpRefreshNeeded  }
		STATUS			current
		DESCRIPTION		"This trap is sent whenever the ARP table changes on the    
nCite"
		::=  {  nCiteArpConfig  5  }

	arpRefreshTrapAck	OBJECT-TYPE	
		SYNTAX			INTEGER  { notAck ( 0 ) , ack ( 1 ) } 
		MAX-ACCESS		read-write
		STATUS			current
		DESCRIPTION		"This value is set when the EMS acknowledges receipt of the 
trap"
		::=  {  nCiteArpConfig  6  }

	arpUpdateMacTrap	NOTIFICATION-TYPE
		OBJECTS			{ arpMacAddr ,arpNextHopIP ,arpTrapOper  }
		STATUS			current
		DESCRIPTION		"This trap is sent to update the mac address for a specific 
next hop address"
		::=  {  nCiteArpConfig  7  }

	arpUpdateMacTrapAck	OBJECT-TYPE	
		SYNTAX			INTEGER  { noAck ( 0 ) , ack ( 1 ) } 
		MAX-ACCESS		read-write
		STATUS			current
		DESCRIPTION		"Acknowledge field for update mac trap"
		::=  {  nCiteArpConfig  8  }

	arpTrapOper	OBJECT-TYPE	
		SYNTAX			INTEGER  { addUpdate ( 0 ) , delete ( 1 ) } 
		MAX-ACCESS		read-only
		STATUS			current
		DESCRIPTION		"If value is addUpdate(0) then ARP entry should be created  
with next hop and mac address provided. If value is         
delete[1] then next hop and associated fields should be     
removed from the table."
		::=  {  nCiteArpConfig  9  }

	arpOperTimerFreq	OBJECT-TYPE	
		SYNTAX			Integer32  ( 1 .. 60  ) 
		MAX-ACCESS		read-write
		STATUS			current
		DESCRIPTION		"ARP Verification Timer Retry Count"
		::=  {  nCiteArpConfig  10  }

	arpOperTimerRetryCount	OBJECT-TYPE	
		SYNTAX			Integer32  ( 1 .. 600  ) 
		MAX-ACCESS		read-write
		STATUS			current
		DESCRIPTION		"ARP Operational Timer Frequency"
		::=  {  nCiteArpConfig  11  }

	arpVerifTimerChangeTrap	NOTIFICATION-TYPE
		OBJECTS			{ arpVerifTimerRetryCount  }
		STATUS			current
		DESCRIPTION		"This trap is sent whenever the ARP verification timers are 
changed"
		::=  {  nCiteArpConfig  12  }

	arpVerifTimerChangeTrapAck	OBJECT-TYPE	
		SYNTAX			INTEGER  { default ( 0 ) , ack ( 1 ) } 
		MAX-ACCESS		read-write
		STATUS			current
		DESCRIPTION		"Used to acknowledge the ARP verification timer change trap"
		::=  {  nCiteArpConfig  13  }

	arpOperTimerChangeTrap	NOTIFICATION-TYPE
		OBJECTS			{ arpOperTimerFreq ,arpOperTimerRetryCount  }
		STATUS			current
		DESCRIPTION		"This trap is sent whenever a change is made to the ARP     
Operational Timer"
		::=  {  nCiteArpConfig  14  }

	arpOperTimerChangeTrapAck	OBJECT-TYPE	
		SYNTAX			INTEGER  { default ( 0 ) , ack ( 1 ) } 
		MAX-ACCESS		read-write
		STATUS			current
		DESCRIPTION		"This is used to acknowledge the ARP Operational Timer      
Change Trap"
		::=  {  nCiteArpConfig  15  }

	arpRefreshTrapAckSource	OBJECT-TYPE	
		SYNTAX			IpAddress
		MAX-ACCESS		read-write
		STATUS			current
		DESCRIPTION		"Identifies the Snmp Manager which sets the trap ack."
		::=  {  nCiteArpConfig  16  }

	arpUpdateMacTrapAckSource	OBJECT-TYPE	
		SYNTAX			IpAddress
		MAX-ACCESS		read-write
		STATUS			current
		DESCRIPTION		"Identifies the Snmp Manager which sets the trap ack."
		::=  {  nCiteArpConfig  17  }

	arpVerifTimerChangeTrapAckSource	OBJECT-TYPE	
		SYNTAX			IpAddress
		MAX-ACCESS		read-write
		STATUS			current
		DESCRIPTION		"Identifies the Snmp Manager which sets the trap ack."
		::=  {  nCiteArpConfig  18  }

	arpOperTimerChangeTrapAckSource	OBJECT-TYPE	
		SYNTAX			IpAddress
		MAX-ACCESS		read-write
		STATUS			current
		DESCRIPTION		"Identifies the Snmp Manager which sets the trap ack."
		::=  {  nCiteArpConfig  19  }

	ipPortConfigTable	OBJECT-TYPE
		SYNTAX		SEQUENCE  OF  IpPortConfigEntry
		MAX-ACCESS	not-accessible
		STATUS		current
		DESCRIPTION	"This table contains the IP configuration for each port"
		::=  { ipPortConfig  1 }

	ipPortConfigEntry	OBJECT-TYPE
		SYNTAX		IpPortConfigEntry
		MAX-ACCESS	not-accessible
		STATUS		current
		DESCRIPTION	"Row Description"
		INDEX		{  ipPortConfigSlotNum, ipPortConfigPortNum, ipPortConfigIpAddr  }
		::=  { ipPortConfigTable 1 }

	IpPortConfigEntry  ::=  SEQUENCE {
		ipPortConfigSlotNum  Integer32,
		ipPortConfigPortNum  Integer32,
		ipPortConfigIpAddr  IpAddress,
		ipPortVlanTag  Integer32,
		ipPortConfigNetMask  IpAddress,
		ipPortConfigAdminState  INTEGER,
		ipPortConfigOperState  INTEGER,
		ipPortRowStatus  RowStatus,
		ipPortVrdTag  Integer32
		}


	ipPortConfigSlotNum	OBJECT-TYPE	
		SYNTAX			Integer32  ( 1 .. 14  ) 
		MAX-ACCESS		read-write
		STATUS			current
		DESCRIPTION		"Slot number of line card"
		::=  {  ipPortConfigEntry  1  }


	ipPortConfigPortNum	OBJECT-TYPE	
		SYNTAX			Integer32  ( 1 .. 48  ) 
		MAX-ACCESS		read-write
		STATUS			current
		DESCRIPTION		"Port Number"
		::=  {  ipPortConfigEntry  2  }


	ipPortConfigIpAddr	OBJECT-TYPE	
		SYNTAX			IpAddress
		MAX-ACCESS		read-write
		STATUS			current
		DESCRIPTION		"IP address of the physical port."
		::=  {  ipPortConfigEntry  3  }


	ipPortVlanTag	OBJECT-TYPE	
		SYNTAX			Integer32  ( 0 .. 4097  ) 
		MAX-ACCESS		read-write
		STATUS			current
		DESCRIPTION		"VLAN associated with interface"
		::=  {  ipPortConfigEntry  4  }


	ipPortConfigNetMask	OBJECT-TYPE	
		SYNTAX			IpAddress
		MAX-ACCESS		read-write
		STATUS			current
		DESCRIPTION		"Net mask for the physical address"
		::=  {  ipPortConfigEntry  5  }


	ipPortConfigAdminState	OBJECT-TYPE	
		SYNTAX			INTEGER  { enable ( 1 ) , disable ( 2 ) } 
		MAX-ACCESS		read-write
		STATUS			current
		DESCRIPTION		"Administrative state of the interface"
		::=  {  ipPortConfigEntry  6  }


	ipPortConfigOperState	OBJECT-TYPE	
		SYNTAX			INTEGER  { enable ( 1 ) , disable ( 2 ) } 
		MAX-ACCESS		read-only
		STATUS			current
		DESCRIPTION		"Operational state of the interface"
		::=  {  ipPortConfigEntry  7  }


	ipPortRowStatus	OBJECT-TYPE	
		SYNTAX			RowStatus
		MAX-ACCESS		read-create
		STATUS			current
		DESCRIPTION		"This is used to add/remove items to the table"
		::=  {  ipPortConfigEntry  8  }


	ipPortVrdTag	OBJECT-TYPE	
		SYNTAX			Integer32  ( 0 .. 4095  ) 
		MAX-ACCESS		read-write
		STATUS			current
		DESCRIPTION		"Virtual Routing Domain"
		::=  {  ipPortConfigEntry  9  }

	ipPortConfigChangeTrap	NOTIFICATION-TYPE
		OBJECTS			{ ipPortConfigIpAddr ,ipPortConfigNetMask ,ipPortConfigOperState ,ipPortConfigPortNum ,ipPortConfigSlotNum ,ipPortVlanTag ,ipPortVrdTag ,ipPortConfigAdminState ,ipPortRowStatus  }
		STATUS			current
		DESCRIPTION		"This trap is sent whenever the IP config changes"
		::=  {  ipPortConfig  2  }

	ipPortConfigChangeTrapAck	OBJECT-TYPE	
		SYNTAX			INTEGER  { notAck ( 0 ) , ack ( 1 ) } 
		MAX-ACCESS		read-write
		STATUS			current
		DESCRIPTION		"IP port config change trap acknowledge flag"
		::=  {  ipPortConfig  3  }

	ipPortPlaceHolder	OBJECT-TYPE	
		SYNTAX			Integer32
		MAX-ACCESS		read-only
		STATUS			current
		DESCRIPTION		"Placeholder - not used"
		::=  {  ipPortConfig  4  }

	ipPortRefreshOpStates	OBJECT-TYPE	
		SYNTAX			Integer32
		MAX-ACCESS		read-only
		STATUS			current
		DESCRIPTION		"This is  used in a trap to tell the EMS to refresh the     
operational states associated with an interface"
		::=  {  ipPortConfig  5  }

	ipPortRefreshTrap	NOTIFICATION-TYPE
		OBJECTS			{ ipPortRefreshOpStates  }
		STATUS			current
		DESCRIPTION		"This trap is sent when the operational states of the       
interfaces has changed"
		::=  {  ipPortConfig  6  }

	ipPortRefreshTrapAck	OBJECT-TYPE	
		SYNTAX			INTEGER  { noAck ( 0 ) , ack ( 1 ) } 
		MAX-ACCESS		read-write
		STATUS			current
		DESCRIPTION		"This value is set to acknowledge a trap from the nCite"
		::=  {  ipPortConfig  7  }

	ipPortAutoNegTable	OBJECT-TYPE
		SYNTAX		SEQUENCE  OF  IpPortAutoNegEntry
		MAX-ACCESS	not-accessible
		STATUS		current
		DESCRIPTION	"This table is used to configure the auto-negotiate flag    
per port"
		::=  { ipPortConfig  8 }

	ipPortAutoNegEntry	OBJECT-TYPE
		SYNTAX		IpPortAutoNegEntry
		MAX-ACCESS	not-accessible
		STATUS		current
		DESCRIPTION	"Row Description"
		INDEX		{  ipPortAutoNegSlotNum, ipPortAutoNegPortNum  }
		::=  { ipPortAutoNegTable 1 }

	IpPortAutoNegEntry  ::=  SEQUENCE {
		ipPortAutoNegSlotNum  Integer32,
		ipPortAutoNegPortNum  Integer32,
		ipPortAutoNegFlag  INTEGER
		}


	ipPortAutoNegSlotNum	OBJECT-TYPE	
		SYNTAX			Integer32
		MAX-ACCESS		read-write
		STATUS			current
		DESCRIPTION		"Column Description"
		::=  {  ipPortAutoNegEntry  1  }


	ipPortAutoNegPortNum	OBJECT-TYPE	
		SYNTAX			Integer32
		MAX-ACCESS		read-only
		STATUS			current
		DESCRIPTION		"Column Description"
		::=  {  ipPortAutoNegEntry  2  }


	ipPortAutoNegFlag	OBJECT-TYPE	
		SYNTAX			INTEGER  { disable ( 0 ) , enable ( 1 ) } 
		MAX-ACCESS		read-write
		STATUS			current
		DESCRIPTION		"Enables/disabled auto-negotiation on the port"
		::=  {  ipPortAutoNegEntry  3  }

	ipPortAutoNegChangeTrap	NOTIFICATION-TYPE
		OBJECTS			{ ipPortAutoNegFlag ,ipPortAutoNegPortNum ,ipPortAutoNegSlotNum  }
		STATUS			current
		DESCRIPTION		"This trap is sent whenever a port's auto-negotiation       
configuration is changed"
		::=  {  ipPortConfig  9  }

	ipPortAutoNegChangeTrapAck	OBJECT-TYPE	
		SYNTAX			INTEGER  { default ( 0 ) , ack ( 1 ) } 
		MAX-ACCESS		read-write
		STATUS			current
		DESCRIPTION		"This value is set to acknowlege the              
ipPortAutoNegChangeTrap"
		::=  {  ipPortConfig  10  }

	ipPortConfigChangeTrapAckSource	OBJECT-TYPE	
		SYNTAX			IpAddress
		MAX-ACCESS		read-write
		STATUS			current
		DESCRIPTION		"Identifies the Snmp Manager which sets the trap ack."
		::=  {  ipPortConfig  11  }

	ipPortRefreshTrapAckSource	OBJECT-TYPE	
		SYNTAX			IpAddress
		MAX-ACCESS		read-write
		STATUS			current
		DESCRIPTION		"Identifies the Snmp Manager which sets the trap ack."
		::=  {  ipPortConfig  12  }

	ipPortAutoNegChangeTrapAckSource	OBJECT-TYPE	
		SYNTAX			IpAddress
		MAX-ACCESS		read-write
		STATUS			current
		DESCRIPTION		"Identifies the Snmp Manager which sets the trap ack."
		::=  {  ipPortConfig  13  }

	nCiteNTATable	OBJECT-TYPE
		SYNTAX		SEQUENCE  OF  NCiteNTAEntry
		MAX-ACCESS	not-accessible
		STATUS		current
		DESCRIPTION	"This table provides the state associated with each         
customer's NTA"
		::=  { nCiteNTA  1 }

	nCiteNTAEntry	OBJECT-TYPE
		SYNTAX		NCiteNTAEntry
		MAX-ACCESS	not-accessible
		STATUS		current
		DESCRIPTION	"Row Description"
		INDEX		{  nCiteNTACustomerId  }
		::=  { nCiteNTATable 1 }

	NCiteNTAEntry  ::=  SEQUENCE {
		nCiteNTACustomerId  Integer32,
		nCiteNTAStatus  INTEGER
		}


	nCiteNTACustomerId	OBJECT-TYPE	
		SYNTAX			Integer32
		MAX-ACCESS		read-only
		STATUS			current
		DESCRIPTION		"Unique identifier associated with the customer. This is    
provided to the nCite via the XML file."
		::=  {  nCiteNTAEntry  1  }


	nCiteNTAStatus	OBJECT-TYPE	
		SYNTAX			INTEGER  { noNTSClient ( 0 ) , configured ( 1 ) , connected ( 2 ) } 
		MAX-ACCESS		read-only
		STATUS			current
		DESCRIPTION		"Status associated with the connection to the NTA for each  
customer."
		::=  {  nCiteNTAEntry  2  }

	nCiteNTAReset	NOTIFICATION-TYPE
		STATUS			current
		DESCRIPTION		"Notifies the SNMP agent when a new XML file has been       
activated so the table can be reset."
		::=  {  nCiteNTA  2  }

	edrQuarantineListTable	OBJECT-TYPE
		SYNTAX		SEQUENCE  OF  EdrQuarantineListEntry
		MAX-ACCESS	not-accessible
		STATUS		current
		DESCRIPTION	"Table that contains the list of calls that have been       
detected rogue"
		::=  { nCiteRogue  1 }

	edrQuarantineListEntry	OBJECT-TYPE
		SYNTAX		EdrQuarantineListEntry
		MAX-ACCESS	not-accessible
		STATUS		current
		DESCRIPTION	"Row Description"
		INDEX		{  erdQLUniqueId  }
		::=  { edrQuarantineListTable 1 }

	EdrQuarantineListEntry  ::=  SEQUENCE {
		erdQLUniqueId  Integer32,
		edrQLCallId  DisplayString,
		edrQLTimestamp  DateAndTime,
		edrQLFrom  DisplayString,
		edrQLTo  DisplayString,
		edrQLRequestURI  DisplayString,
		edrQLSrcMediaIpPort  DisplayString,
		edrQLDestMediaAnchorIpPort  DisplayString,
		edrQLDestMediaIpPort  DisplayString,
		edrQLRogueStatus  DisplayString,
		edrQLPerformGarbageCollection  INTEGER,
		erdQL2SrcMediaIpPort  DisplayString,
		erdQL2DestMediaAnchorIpPort  DisplayString,
		erdQL2DestMediaIpPort  DisplayString
		}


	erdQLUniqueId	OBJECT-TYPE	
		SYNTAX			Integer32
		MAX-ACCESS		read-only
		STATUS			current
		DESCRIPTION		"Unique identifier for the call"
		::=  {  edrQuarantineListEntry  1  }


	edrQLCallId	OBJECT-TYPE	
		SYNTAX			DisplayString  ( SIZE ( 0 .. 255  ) ) 
		MAX-ACCESS		read-only
		STATUS			current
		DESCRIPTION		"Call Id"
		::=  {  edrQuarantineListEntry  2  }


	edrQLTimestamp	OBJECT-TYPE	
		SYNTAX			DateAndTime
		MAX-ACCESS		read-only
		STATUS			current
		DESCRIPTION		"Date/time that the call was detected as rogue"
		::=  {  edrQuarantineListEntry  3  }


	edrQLFrom	OBJECT-TYPE	
		SYNTAX			DisplayString
		MAX-ACCESS		read-only
		STATUS			current
		DESCRIPTION		"From"
		::=  {  edrQuarantineListEntry  4  }


	edrQLTo	OBJECT-TYPE	
		SYNTAX			DisplayString
		MAX-ACCESS		read-only
		STATUS			current
		DESCRIPTION		"To"
		::=  {  edrQuarantineListEntry  5  }


	edrQLRequestURI	OBJECT-TYPE	
		SYNTAX			DisplayString
		MAX-ACCESS		read-only
		STATUS			current
		DESCRIPTION		"Request URI"
		::=  {  edrQuarantineListEntry  6  }


	edrQLSrcMediaIpPort	OBJECT-TYPE	
		SYNTAX			DisplayString
		MAX-ACCESS		read-only
		STATUS			current
		DESCRIPTION		"Source Media Ip Port"
		::=  {  edrQuarantineListEntry  7  }


	edrQLDestMediaAnchorIpPort	OBJECT-TYPE	
		SYNTAX			DisplayString
		MAX-ACCESS		read-only
		STATUS			current
		DESCRIPTION		"Destination Media Anchor IP Port"
		::=  {  edrQuarantineListEntry  8  }


	edrQLDestMediaIpPort	OBJECT-TYPE	
		SYNTAX			DisplayString
		MAX-ACCESS		read-only
		STATUS			current
		DESCRIPTION		"Destination Media IP Port"
		::=  {  edrQuarantineListEntry  9  }


	edrQLRogueStatus	OBJECT-TYPE	
		SYNTAX			DisplayString  ( SIZE ( 0 .. 255  ) ) 
		MAX-ACCESS		read-only
		STATUS			current
		DESCRIPTION		"Status of last check of traffic on the call; ROGUE means   
that traffic was detected; CLEAN means that no traffic was  
detected"
		::=  {  edrQuarantineListEntry  10  }


	edrQLPerformGarbageCollection	OBJECT-TYPE	
		SYNTAX			INTEGER  { default ( 0 ) , start ( 1 ) } 
		MAX-ACCESS		read-write
		STATUS			current
		DESCRIPTION		"Description"
		::=  {  edrQuarantineListEntry  11  }


	erdQL2SrcMediaIpPort	OBJECT-TYPE	
		SYNTAX			DisplayString
		MAX-ACCESS		read-only
		STATUS			current
		DESCRIPTION		"Source Media IP port in opposite direction"
		::=  {  edrQuarantineListEntry  12  }


	erdQL2DestMediaAnchorIpPort	OBJECT-TYPE	
		SYNTAX			DisplayString
		MAX-ACCESS		read-only
		STATUS			current
		DESCRIPTION		"opposite flow's media anchor IP port"
		::=  {  edrQuarantineListEntry  13  }


	erdQL2DestMediaIpPort	OBJECT-TYPE	
		SYNTAX			DisplayString
		MAX-ACCESS		read-only
		STATUS			current
		DESCRIPTION		"Opposite flow's destination media IP port"
		::=  {  edrQuarantineListEntry  14  }

	edrGarbageCollectionState	OBJECT-TYPE	
		SYNTAX			DisplayString
		MAX-ACCESS		read-only
		STATUS			current
		DESCRIPTION		"Garbage collection state: In Progress, Success"
		::=  {  nCiteRogue  2  }

	edrLastGarbageCollection	OBJECT-TYPE	
		SYNTAX			DateAndTime
		MAX-ACCESS		read-only
		STATUS			current
		DESCRIPTION		"Date/time of last garbage collection"
		::=  {  nCiteRogue  3  }

	edrNextTrafficCheck	OBJECT-TYPE	
		SYNTAX			DateAndTime
		MAX-ACCESS		read-only
		STATUS			current
		DESCRIPTION		"Date/time of next check for traffic on each call in the    
quarantine list"
		::=  {  nCiteRogue  4  }

	edrPerformGarbageCollection	OBJECT-TYPE	
		SYNTAX			INTEGER  { default ( 0 ) , start ( 1 ) } 
		MAX-ACCESS		read-write
		STATUS			current
		DESCRIPTION		"This OID is used to command the nCite to perform EDR       
garbage collection"
		::=  {  nCiteRogue  5  }

	edrGarbageCollectionStatus	OBJECT-TYPE	
		SYNTAX			INTEGER  { success ( 0 ) , entryNotFound ( 1 ) } 
		MAX-ACCESS		read-only
		STATUS			current
		DESCRIPTION		"Return status associated with last perform garbage         
collection request"
		::=  {  nCiteRogue  6  }

	edrGarbageCollectionComplete	NOTIFICATION-TYPE
		OBJECTS			{ edrGarbageCollectionStatus ,edrGarbageCollectionState ,edrLastGarbageCollection ,edrNextTrafficCheck  }
		STATUS			current
		DESCRIPTION		"Description"
		::=  {  nCiteRogue  7  }

	edrGarbageCollectionCompleteTrapAck	OBJECT-TYPE	
		SYNTAX			INTEGER  { notAck ( 0 ) , ack ( 1 ) } 
		MAX-ACCESS		read-write
		STATUS			current
		DESCRIPTION		"Description"
		::=  {  nCiteRogue  8  }

	lrdTable	OBJECT-TYPE
		SYNTAX		SEQUENCE  OF  LrdEntry
		MAX-ACCESS	not-accessible
		STATUS		current
		DESCRIPTION	"Description"
		::=  { nCiteRogue  9 }

	lrdEntry	OBJECT-TYPE
		SYNTAX		LrdEntry
		MAX-ACCESS	not-accessible
		STATUS		current
		DESCRIPTION	"Row Description"
		INDEX		{  lrdUniqueId  }
		::=  { lrdTable 1 }

	LrdEntry  ::=  SEQUENCE {
		lrdUniqueId  Integer32,
		lrdCallId  DisplayString,
		lrdRequestURI  DisplayString,
		lrdFrom  DisplayString,
		lrdTo  DisplayString,
		lrdCallerState  DisplayString,
		lrdCallerMediaAnchorIPPort  DisplayString,
		lrdCallerDestIPPort  DisplayString,
		lrdCallerSourceIPPort1  DisplayString,
		lrdCallerSourceIPPort2  DisplayString,
		lrdCallerReason  DisplayString,
		lrdCallerTimeDetect  DateAndTime,
		lrdCalleeState  DisplayString,
		lrdCalleeMediaAnchorIPPort  DisplayString,
		lrdCalleeDestIPPort  DisplayString,
		lrdCalleeSourceIPPort1  DisplayString,
		lrdCalleeSourceIPPort2  DisplayString,
		lrdCalleeReason  DisplayString,
		lrdCalleeTimeDetect  DisplayString
		}


	lrdUniqueId	OBJECT-TYPE	
		SYNTAX			Integer32  ( -2147483648 .. 2147483647  ) 
		MAX-ACCESS		read-only
		STATUS			current
		DESCRIPTION		"Unique identifier for the call"
		::=  {  lrdEntry  1  }


	lrdCallId	OBJECT-TYPE	
		SYNTAX			DisplayString
		MAX-ACCESS		read-only
		STATUS			current
		DESCRIPTION		"Call ID"
		::=  {  lrdEntry  2  }


	lrdRequestURI	OBJECT-TYPE	
		SYNTAX			DisplayString
		MAX-ACCESS		read-only
		STATUS			current
		DESCRIPTION		"Request-URI"
		::=  {  lrdEntry  3  }


	lrdFrom	OBJECT-TYPE	
		SYNTAX			DisplayString
		MAX-ACCESS		read-only
		STATUS			current
		DESCRIPTION		"From"
		::=  {  lrdEntry  4  }


	lrdTo	OBJECT-TYPE	
		SYNTAX			DisplayString
		MAX-ACCESS		read-only
		STATUS			current
		DESCRIPTION		"To"
		::=  {  lrdEntry  5  }


	lrdCallerState	OBJECT-TYPE	
		SYNTAX			DisplayString
		MAX-ACCESS		read-only
		STATUS			current
		DESCRIPTION		"Rogue/Clean"
		::=  {  lrdEntry  6  }


	lrdCallerMediaAnchorIPPort	OBJECT-TYPE	
		SYNTAX			DisplayString
		MAX-ACCESS		read-only
		STATUS			current
		DESCRIPTION		"Media Anchor IP address and port"
		::=  {  lrdEntry  7  }


	lrdCallerDestIPPort	OBJECT-TYPE	
		SYNTAX			DisplayString
		MAX-ACCESS		read-only
		STATUS			current
		DESCRIPTION		"Caller Destination IP address/port"
		::=  {  lrdEntry  8  }


	lrdCallerSourceIPPort1	OBJECT-TYPE	
		SYNTAX			DisplayString
		MAX-ACCESS		read-only
		STATUS			current
		DESCRIPTION		"Caller IP address/Port"
		::=  {  lrdEntry  9  }


	lrdCallerSourceIPPort2	OBJECT-TYPE	
		SYNTAX			DisplayString
		MAX-ACCESS		read-only
		STATUS			current
		DESCRIPTION		"Caller Source IP address/Port"
		::=  {  lrdEntry  10  }


	lrdCallerReason	OBJECT-TYPE	
		SYNTAX			DisplayString
		MAX-ACCESS		read-only
		STATUS			current
		DESCRIPTION		"Caller Reason"
		::=  {  lrdEntry  11  }


	lrdCallerTimeDetect	OBJECT-TYPE	
		SYNTAX			DateAndTime
		MAX-ACCESS		read-only
		STATUS			current
		DESCRIPTION		"Caller Time of Rogue Detection"
		::=  {  lrdEntry  12  }


	lrdCalleeState	OBJECT-TYPE	
		SYNTAX			DisplayString
		MAX-ACCESS		read-only
		STATUS			current
		DESCRIPTION		"Rogue/Clean"
		::=  {  lrdEntry  13  }


	lrdCalleeMediaAnchorIPPort	OBJECT-TYPE	
		SYNTAX			DisplayString
		MAX-ACCESS		read-only
		STATUS			current
		DESCRIPTION		"Callee Media Achor IP adress/Port"
		::=  {  lrdEntry  14  }


	lrdCalleeDestIPPort	OBJECT-TYPE	
		SYNTAX			DisplayString
		MAX-ACCESS		read-only
		STATUS			current
		DESCRIPTION		"Callee Destination IP address/Port"
		::=  {  lrdEntry  15  }


	lrdCalleeSourceIPPort1	OBJECT-TYPE	
		SYNTAX			DisplayString
		MAX-ACCESS		read-only
		STATUS			current
		DESCRIPTION		"Callee Source IP Address/Port 1"
		::=  {  lrdEntry  16  }


	lrdCalleeSourceIPPort2	OBJECT-TYPE	
		SYNTAX			DisplayString
		MAX-ACCESS		read-only
		STATUS			current
		DESCRIPTION		"Callee Source IP Address/Port 2"
		::=  {  lrdEntry  17  }


	lrdCalleeReason	OBJECT-TYPE	
		SYNTAX			DisplayString
		MAX-ACCESS		read-only
		STATUS			current
		DESCRIPTION		"Callee Reason"
		::=  {  lrdEntry  18  }


	lrdCalleeTimeDetect	OBJECT-TYPE	
		SYNTAX			DisplayString
		MAX-ACCESS		read-only
		STATUS			current
		DESCRIPTION		"Callee Time of rogue detection"
		::=  {  lrdEntry  19  }

	edrGarbageCollectionCompleteTrapAckSource	OBJECT-TYPE	
		SYNTAX			IpAddress
		MAX-ACCESS		read-write
		STATUS			current
		DESCRIPTION		"Identifies the Snmp Manager which sets the trap ack."
		::=  {  nCiteRogue  10  }

	licenseTable	OBJECT-TYPE
		SYNTAX		SEQUENCE  OF  LicenseEntry
		MAX-ACCESS	not-accessible
		STATUS		current
		DESCRIPTION	"Description"
		::=  { licenseInfo  1 }

	licenseEntry	OBJECT-TYPE
		SYNTAX		LicenseEntry
		MAX-ACCESS	not-accessible
		STATUS		current
		DESCRIPTION	"Name value pair that describes the feature licensed"
		INDEX		{  licenseIndex  }
		::=  { licenseTable 1 }

	LicenseEntry  ::=  SEQUENCE {
		licenseIndex  Integer32,
		licenseFeatureName  INTEGER,
		licenseValue  Integer32,
		licenseInstallDate  DateAndTime,
		licenseExpirationDate  DateAndTime,
		licenseFeatureDisplayName  DisplayString
		}


	licenseIndex	OBJECT-TYPE	
		SYNTAX			Integer32
		MAX-ACCESS		read-only
		STATUS			current
		DESCRIPTION		"Column Description"
		::=  {  licenseEntry  1  }


	licenseFeatureName	OBJECT-TYPE	
		SYNTAX			INTEGER  { globalCac ( 0 ) , redundancy ( 1 ) , nts ( 2 ) , rogueDetect ( 3 ) , totalCust ( 4 ) , totalNtsCust ( 5 ) , totalVlanCust ( 6 ) , globalReg ( 7 ) } 
		MAX-ACCESS		read-only
		STATUS			deprecated
		DESCRIPTION		"Encumerated value that can be used to translate into a     
descriptive name of feature that was licensed"
		::=  {  licenseEntry  2  }


	licenseValue	OBJECT-TYPE	
		SYNTAX			Integer32  ( 0 .. 1000  ) 
		MAX-ACCESS		read-only
		STATUS			current
		DESCRIPTION		"Value associated with licensed feature. If the license is  
just to enable/disable, the value for enable = 1, the value 
for disable = 2."
		::=  {  licenseEntry  3  }


	licenseInstallDate	OBJECT-TYPE	
		SYNTAX			DateAndTime
		MAX-ACCESS		read-only
		STATUS			current
		DESCRIPTION		"Date/time that the license was installed"
		::=  {  licenseEntry  4  }


	licenseExpirationDate	OBJECT-TYPE	
		SYNTAX			DateAndTime
		MAX-ACCESS		read-only
		STATUS			current
		DESCRIPTION		"Date/time that the license will expire. This field is      
currently not used."
		::=  {  licenseEntry  5  }


	licenseFeatureDisplayName	OBJECT-TYPE	
		SYNTAX			DisplayString
		MAX-ACCESS		read-only
		STATUS			current
		DESCRIPTION		"The display name for the feature"
		::=  {  licenseEntry  6  }

	licenseFileName	OBJECT-TYPE	
		SYNTAX			DisplayString
		MAX-ACCESS		read-only
		STATUS			current
		DESCRIPTION		"Name of the license file on the nCite"
		::=  {  licenseInfo  2  }

	licenseFileChangeTrap	NOTIFICATION-TYPE
		OBJECTS			{ licenseFileName  }
		STATUS			current
		DESCRIPTION		"This trap is sent whenever a new license file is loaded    
onto the nCite"
		::=  {  licenseInfo  3  }

	licenseFileChangeTrapAck	OBJECT-TYPE	
		SYNTAX			INTEGER  { notAck ( 0 ) , ack ( 1 ) } 
		MAX-ACCESS		read-write
		STATUS			current
		DESCRIPTION		"This OID is used to acknowledge the receipt of the license 
file change trap."
		::=  {  licenseInfo  4  }

	licenseFileChangeTrapAckSource	OBJECT-TYPE	
		SYNTAX			IpAddress
		MAX-ACCESS		read-write
		STATUS			current
		DESCRIPTION		"Identifies the Snmp Manager which sets the trap ack."
		::=  {  licenseInfo  5  }

	nCiteRipState	OBJECT-TYPE	
		SYNTAX			INTEGER  { off ( 0 ) , on ( 1 ) } 
		MAX-ACCESS		read-only
		STATUS			current
		DESCRIPTION		"State of RIP on the nCite; off = RIP is not running; on =  
RIP is running"
		::=  {  nCiteRIPConfig  1  }

	nCiteRipPortConfigTable	OBJECT-TYPE
		SYNTAX		SEQUENCE  OF  NCiteRipPortConfigEntry
		MAX-ACCESS	not-accessible
		STATUS		current
		DESCRIPTION	"Ports are specified as primary or secondary"
		::=  { nCiteRIPConfig  2 }

	nCiteRipPortConfigEntry	OBJECT-TYPE
		SYNTAX		NCiteRipPortConfigEntry
		MAX-ACCESS	not-accessible
		STATUS		current
		DESCRIPTION	"Row Description"
		INDEX		{  nCiteRipPortSlotNum, nCiteRipPortNum  }
		::=  { nCiteRipPortConfigTable 1 }

	NCiteRipPortConfigEntry  ::=  SEQUENCE {
		nCiteRipPortSlotNum  Integer32,
		nCiteRipPortNum  Integer32,
		nCiteRipPortPrimary  INTEGER
		}


	nCiteRipPortSlotNum	OBJECT-TYPE	
		SYNTAX			Integer32
		MAX-ACCESS		read-only
		STATUS			current
		DESCRIPTION		"Card slot"
		::=  {  nCiteRipPortConfigEntry  1  }


	nCiteRipPortNum	OBJECT-TYPE	
		SYNTAX			Integer32
		MAX-ACCESS		read-write
		STATUS			current
		DESCRIPTION		"Port ID"
		::=  {  nCiteRipPortConfigEntry  2  }


	nCiteRipPortPrimary	OBJECT-TYPE	
		SYNTAX			INTEGER  { default ( 0 ) , primary ( 1 ) , secondary ( 2 ) } 
		MAX-ACCESS		read-only
		STATUS			current
		DESCRIPTION		"Port is either primary or secondary"
		::=  {  nCiteRipPortConfigEntry  3  }

	nCiteRipInterfacesTable	OBJECT-TYPE
		SYNTAX		SEQUENCE  OF  NCiteRipInterfacesEntry
		MAX-ACCESS	not-accessible
		STATUS		current
		DESCRIPTION	"This table is the list of interfaces on which RIP is       
enabled"
		::=  { nCiteRIPConfig  3 }

	nCiteRipInterfacesEntry	OBJECT-TYPE
		SYNTAX		NCiteRipInterfacesEntry
		MAX-ACCESS	not-accessible
		STATUS		current
		DESCRIPTION	"Row Description"
		INDEX		{  nCiteRipInterafacesSlotNum, nCiteRipInterfacesPortNum, nCiteRipInterfacesIPAddr  }
		::=  { nCiteRipInterfacesTable 1 }

	NCiteRipInterfacesEntry  ::=  SEQUENCE {
		nCiteRipInterafacesSlotNum  Integer32,
		nCiteRipInterfacesPortNum  Integer32,
		nCiteRipInterfacesIPAddr  IpAddress
		}


	nCiteRipInterafacesSlotNum	OBJECT-TYPE	
		SYNTAX			Integer32
		MAX-ACCESS		read-only
		STATUS			current
		DESCRIPTION		"Slot Number"
		::=  {  nCiteRipInterfacesEntry  1  }


	nCiteRipInterfacesPortNum	OBJECT-TYPE	
		SYNTAX			Integer32
		MAX-ACCESS		read-only
		STATUS			current
		DESCRIPTION		"Port number"
		::=  {  nCiteRipInterfacesEntry  2  }


	nCiteRipInterfacesIPAddr	OBJECT-TYPE	
		SYNTAX			IpAddress
		MAX-ACCESS		read-only
		STATUS			current
		DESCRIPTION		"IP address for which RIP is enabed"
		::=  {  nCiteRipInterfacesEntry  3  }

	authConfigLocalOverride	OBJECT-TYPE	
		SYNTAX			INTEGER  { disabled ( 0 ) , enabled ( 1 ) } 
		MAX-ACCESS		read-only
		STATUS			current
		DESCRIPTION		"Local override is used to have a different RADIUS server   
configuration than the EMS"
		::=  {  nCiteAuthConfig  1  }

	authConfigRadiusRetryCount	OBJECT-TYPE	
		SYNTAX			Integer32  ( 1 .. 5  ) 
		MAX-ACCESS		read-only
		STATUS			current
		DESCRIPTION		"Number of retries for RADIUS Server communications"
		::=  {  nCiteAuthConfig  2  }

	authConfigRadiusRetryInterval	OBJECT-TYPE	
		SYNTAX			Integer32  ( 1 .. 10  ) 
		MAX-ACCESS		read-only
		STATUS			current
		DESCRIPTION		"Number of seconds to wait for RADIUS Server response"
		::=  {  nCiteAuthConfig  3  }

	authConfigRadiusServersTable	OBJECT-TYPE
		SYNTAX		SEQUENCE  OF  AuthConfigRadiusServersEntry
		MAX-ACCESS	not-accessible
		STATUS		current
		DESCRIPTION	"Table containing the list of RADIUS servers configured on  
the nCite"
		::=  { nCiteAuthConfig  4 }

	authConfigRadiusServersEntry	OBJECT-TYPE
		SYNTAX		AuthConfigRadiusServersEntry
		MAX-ACCESS	not-accessible
		STATUS		current
		DESCRIPTION	"Row Description"
		INDEX		{  authConfigRadiusServerIp  }
		::=  { authConfigRadiusServersTable 1 }

	AuthConfigRadiusServersEntry  ::=  SEQUENCE {
		authConfigRadiusServerIp  IpAddress,
		authConfigRadiusServerPort  Integer32,
		authConfigRadiusServerPriority  Integer32
		}


	authConfigRadiusServerIp	OBJECT-TYPE	
		SYNTAX			IpAddress
		MAX-ACCESS		read-only
		STATUS			current
		DESCRIPTION		"IP address of RADIUS Server"
		::=  {  authConfigRadiusServersEntry  1  }


	authConfigRadiusServerPort	OBJECT-TYPE	
		SYNTAX			Integer32
		MAX-ACCESS		read-only
		STATUS			current
		DESCRIPTION		"RADIUS Server's Port"
		::=  {  authConfigRadiusServersEntry  2  }


	authConfigRadiusServerPriority	OBJECT-TYPE	
		SYNTAX			Integer32  ( 1 .. 5  ) 
		MAX-ACCESS		read-only
		STATUS			current
		DESCRIPTION		"Priority (order) with which the RADIUS Server is used for  
user authentication."
		::=  {  authConfigRadiusServersEntry  3  }

	chasSerNum	OBJECT-TYPE	
		SYNTAX			DisplayString
		MAX-ACCESS		read-only
		STATUS			current
		DESCRIPTION		"Serial number of the chassis"
		::=  {  chasGen  1  }

	chasLedStatus	OBJECT-TYPE	
		SYNTAX			Integer32  ( -2147483648 .. 2147483647  ) 
		MAX-ACCESS		read-only
		STATUS			current
		DESCRIPTION		"Bit array that contains the chassis LED status"
		::=  {  chasGen  2  }

	chasPOSTMode	OBJECT-TYPE	
		SYNTAX			INTEGER  { fastPOST ( 0 ) , fullPost ( 1 ) } 
		MAX-ACCESS		read-write
		STATUS			current
		DESCRIPTION		"Used to set the mode of the power on self test; Currently  
not supported."
		DEFVAL			{ fastPOST }
		::=  {  chasGen  3  }

	chasType	OBJECT-TYPE	
		SYNTAX			INTEGER  { unknown ( 0 ) , bff ( 1 ) , sff ( 2 ) } 
		MAX-ACCESS		read-only
		STATUS			current
		DESCRIPTION		"Description"
		::=  {  chasGen  4  }

	chasPwrSupplyTable	OBJECT-TYPE
		SYNTAX		SEQUENCE  OF  ChasPwrSupplyEntry
		MAX-ACCESS	not-accessible
		STATUS		current
		DESCRIPTION	"Table of power supplies"
		::=  { chasPwr  1 }

	chasPwrSupplyEntry	OBJECT-TYPE
		SYNTAX		ChasPwrSupplyEntry
		MAX-ACCESS	not-accessible
		STATUS		current
		DESCRIPTION	"Row Description"
		INDEX		{  chasPwrSupplyIndex  }
		::=  { chasPwrSupplyTable 1 }

	ChasPwrSupplyEntry  ::=  SEQUENCE {
		chasPwrSupplyIndex  Integer32,
		chasPwrSupplyOperStatus  INTEGER,
		chasPwrSupplyDesc  DisplayString
		}


	chasPwrSupplyIndex	OBJECT-TYPE	
		SYNTAX			Integer32
		MAX-ACCESS		read-only
		STATUS			current
		DESCRIPTION		"Index to the power supply table"
		::=  {  chasPwrSupplyEntry  1  }


	chasPwrSupplyOperStatus	OBJECT-TYPE	
		SYNTAX			INTEGER  { unknown ( 1 ) , normal ( 2 ) , fault ( 3 ) , notPresent ( 4 ) } 
		MAX-ACCESS		read-only
		STATUS			current
		DESCRIPTION		"Column Description"
		::=  {  chasPwrSupplyEntry  2  }


	chasPwrSupplyDesc	OBJECT-TYPE	
		SYNTAX			DisplayString
		MAX-ACCESS		read-only
		STATUS			current
		DESCRIPTION		"Description of power supply"
		::=  {  chasPwrSupplyEntry  3  }

	chasPwrTrap	NOTIFICATION-TYPE
		OBJECTS			{ chasPwrSupplyIndex ,chasPwrSupplyOperStatus  }
		STATUS			current
		DESCRIPTION		"This trap is sent whenever the status of a power supply    
changes"
		::=  {  chasPwr  2  }

	chasPwrTrapAck	OBJECT-TYPE	
		SYNTAX			INTEGER  { notAck ( 0 ) , ack ( 1 ) } 
		MAX-ACCESS		read-write
		STATUS			current
		DESCRIPTION		"Chase power trap acknowledge flag"
		::=  {  chasPwr  3  }

	chasPwrTrapAckSource	OBJECT-TYPE	
		SYNTAX			IpAddress
		MAX-ACCESS		read-write
		STATUS			current
		DESCRIPTION		"Identifies the Snmp Manager which sets the trap ack."
		::=  {  chasPwr  4  }

	chasFanTable	OBJECT-TYPE
		SYNTAX		SEQUENCE  OF  ChasFanEntry
		MAX-ACCESS	not-accessible
		STATUS		current
		DESCRIPTION	"Table contains the list of fans"
		::=  { chasFan  1 }

	chasFanEntry	OBJECT-TYPE
		SYNTAX		ChasFanEntry
		MAX-ACCESS	not-accessible
		STATUS		current
		DESCRIPTION	"Row Description"
		INDEX		{  chasFanIndex  }
		::=  { chasFanTable 1 }

	ChasFanEntry  ::=  SEQUENCE {
		chasFanIndex  Integer32,
		chasFanOperStatus  INTEGER,
		chasFanDescription  DisplayString
		}


	chasFanIndex	OBJECT-TYPE	
		SYNTAX			Integer32
		MAX-ACCESS		read-only
		STATUS			current
		DESCRIPTION		"Column Description"
		::=  {  chasFanEntry  1  }


	chasFanOperStatus	OBJECT-TYPE	
		SYNTAX			INTEGER  { dev-ok ( 0 ) , dev-fail ( 1 ) , dev-present ( 2 ) , dev-not-present ( 3 ) , unknown ( 4 ) } 
		MAX-ACCESS		read-only
		STATUS			current
		DESCRIPTION		"Operational status of the fan"
		::=  {  chasFanEntry  2  }


	chasFanDescription	OBJECT-TYPE	
		SYNTAX			DisplayString
		MAX-ACCESS		read-only
		STATUS			current
		DESCRIPTION		"Description of fan"
		::=  {  chasFanEntry  3  }

	chasFanTrap	NOTIFICATION-TYPE
		OBJECTS			{ chasFanIndex ,chasFanOperStatus  }
		STATUS			current
		DESCRIPTION		"This trap is sent whenever the status of a fan changes"
		::=  {  chasFan  2  }

	chasFanTrapAck	OBJECT-TYPE	
		SYNTAX			INTEGER  { notAck ( 0 ) , ack ( 1 ) } 
		MAX-ACCESS		read-write
		STATUS			current
		DESCRIPTION		"Chase fan trap acknowledge flag"
		::=  {  chasFan  3  }

	chasFanTrapAckSource	OBJECT-TYPE	
		SYNTAX			IpAddress
		MAX-ACCESS		read-write
		STATUS			current
		DESCRIPTION		"Identifies the Snmp Manager which sets the trap ack."
		::=  {  chasFan  4  }

	chasBrdTable	OBJECT-TYPE
		SYNTAX		SEQUENCE  OF  ChasBrdEntry
		MAX-ACCESS	not-accessible
		STATUS		current
		DESCRIPTION	"Table containing the description of each board present in  
the chassis"
		::=  { chasBrd  1 }

	chasBrdEntry	OBJECT-TYPE
		SYNTAX		ChasBrdEntry
		MAX-ACCESS	not-accessible
		STATUS		current
		DESCRIPTION	"Row Description"
		INDEX		{  chasBrdSlotNum  }
		::=  { chasBrdTable 1 }

	ChasBrdEntry  ::=  SEQUENCE {
		chasBrdSlotNum  Integer32,
		chasBrdDescription  DisplayString,
		chasBrdType  INTEGER,
		chasBrdOccSlots  Integer32,
		chasBrdMaxPorts  Integer32,
		chasBrdSlotLabel  DisplayString,
		chasBrdStatusLeds  Integer32,
		chasBrdState  DisplayString,
		chasBrdPwr  INTEGER,
		chasBrdIfIndex  Integer32,
		chasBrdSerialNum  DisplayString,
		chasBrdReset  INTEGER
		}


	chasBrdSlotNum	OBJECT-TYPE	
		SYNTAX			Integer32  ( 1 .. 14  ) 
		MAX-ACCESS		read-only
		STATUS			current
		DESCRIPTION		"Starting slot number of the board"
		::=  {  chasBrdEntry  1  }


	chasBrdDescription	OBJECT-TYPE	
		SYNTAX			DisplayString
		MAX-ACCESS		read-only
		STATUS			current
		DESCRIPTION		"Description of the board"
		::=  {  chasBrdEntry  2  }


	chasBrdType	OBJECT-TYPE	
		SYNTAX			INTEGER  { managementProc ( 1 ) , controlProc ( 2 ) , netrakeControlProcessor ( 3 ) , gigE ( 4 ) , fastEther ( 5 ) , noBoardPresent ( 0 ) } 
		MAX-ACCESS		read-only
		STATUS			current
		DESCRIPTION		"Board type"
		::=  {  chasBrdEntry  3  }


	chasBrdOccSlots	OBJECT-TYPE	
		SYNTAX			Integer32  ( -2147483648 .. 2147483647  ) 
		MAX-ACCESS		read-only
		STATUS			current
		DESCRIPTION		"Number of slots that the board occupies"
		::=  {  chasBrdEntry  4  }


	chasBrdMaxPorts	OBJECT-TYPE	
		SYNTAX			Integer32
		MAX-ACCESS		read-only
		STATUS			current
		DESCRIPTION		"Number of ports that the card supports"
		::=  {  chasBrdEntry  5  }


	chasBrdSlotLabel	OBJECT-TYPE	
		SYNTAX			DisplayString
		MAX-ACCESS		read-only
		STATUS			current
		DESCRIPTION		"Label on the chassis"
		::=  {  chasBrdEntry  6  }


	chasBrdStatusLeds	OBJECT-TYPE	
		SYNTAX			Integer32  ( -2147483648 .. 2147483647  ) 
		MAX-ACCESS		read-only
		STATUS			current
		DESCRIPTION		"Bit-map that contains the value of the front panel LEDS."
		::=  {  chasBrdEntry  7  }


	chasBrdState	OBJECT-TYPE	
		SYNTAX			DisplayString
		MAX-ACCESS		read-only
		STATUS			current
		DESCRIPTION		"Board state"
		::=  {  chasBrdEntry  8  }


	chasBrdPwr	OBJECT-TYPE	
		SYNTAX			INTEGER  { default ( 0 ) , powerOn ( 1 ) , powerOff ( 2 ) } 
		MAX-ACCESS		read-write
		STATUS			current
		DESCRIPTION		"Is used to power on and off line cards and indicates power 
state of board"
		DEFVAL			{ powerOn }
		::=  {  chasBrdEntry  9  }


	chasBrdIfIndex	OBJECT-TYPE	
		SYNTAX			Integer32
		MAX-ACCESS		read-only
		STATUS			current
		DESCRIPTION		"This is the value of the index to the IF table of the      
first port of the line card"
		DEFVAL			{ 0 }
		::=  {  chasBrdEntry  10  }


	chasBrdSerialNum	OBJECT-TYPE	
		SYNTAX			DisplayString
		MAX-ACCESS		read-only
		STATUS			current
		DESCRIPTION		"Serial number of the board"
		::=  {  chasBrdEntry  11  }


	chasBrdReset	OBJECT-TYPE	
		SYNTAX			INTEGER  { default ( 0 ) , resetCold ( 1 ) , resetWarm ( 2 ) } 
		MAX-ACCESS		read-write
		STATUS			current
		DESCRIPTION		"This OID is set when the nCite is commanded to perform a   
board reset"
		::=  {  chasBrdEntry  12  }

	chasBrdStateChangeTrap	NOTIFICATION-TYPE
		OBJECTS			{ chasBrdSlotNum ,chasBrdType ,chasBrdState  }
		STATUS			current
		DESCRIPTION		"This trap is sent when the state of line card changes      
state"
		::=  {  chasBrd  2  }

	chasBrdStateChangeTrapAck	OBJECT-TYPE	
		SYNTAX			INTEGER  { notAck ( 0 ) , ack ( 1 ) } 
		MAX-ACCESS		read-write
		STATUS			current
		DESCRIPTION		"Chase board state change trap acknowledge flag"
		::=  {  chasBrd  3  }

	chasBrdStateChangeTrapAckSource	OBJECT-TYPE	
		SYNTAX			IpAddress
		MAX-ACCESS		read-write
		STATUS			current
		DESCRIPTION		"Identifies the Snmp Manager which sets the trap ack."
		::=  {  chasBrd  4  }

	totalPacketsXmitCPA	OBJECT-TYPE	
		SYNTAX			Counter64
		MAX-ACCESS		read-only
		STATUS			current
		DESCRIPTION		"Total number of packets transmitted by CP side A"
		::=  {  globalCounters  1  }

	numPacketsDiscardCPA	OBJECT-TYPE	
		SYNTAX			Counter64
		MAX-ACCESS		read-only
		STATUS			current
		DESCRIPTION		"Number of packets discarded by CP side A"
		::=  {  globalCounters  2  }

	totalPacketsXmitCPB	OBJECT-TYPE	
		SYNTAX			Counter64
		MAX-ACCESS		read-only
		STATUS			current
		DESCRIPTION		"Total number of packets transmitted by CP side B"
		::=  {  globalCounters  3  }

	numPacketsDiscardCPB	OBJECT-TYPE	
		SYNTAX			Counter64
		MAX-ACCESS		read-only
		STATUS			current
		DESCRIPTION		"Number of packets discarded by CP side B"
		::=  {  globalCounters  4  }

	totalPacketsXmit	OBJECT-TYPE	
		SYNTAX			Counter64
		MAX-ACCESS		read-only
		STATUS			current
		DESCRIPTION		"This counter applies to nCites that do not have 'sides'"
		::=  {  globalCounters  5  }

	totalPacketsDiscard	OBJECT-TYPE	
		SYNTAX			Counter64
		MAX-ACCESS		read-only
		STATUS			current
		DESCRIPTION		"This counter applies to nCites that do have have 'sides'"
		::=  {  globalCounters  6  }

	gigEStatsTable	OBJECT-TYPE
		SYNTAX		SEQUENCE  OF  GigEStatsEntry
		MAX-ACCESS	not-accessible
		STATUS		current
		DESCRIPTION	"Table containing the counters available for every gigE     
card in the nCite."
		::=  { gigEStats  1 }

	gigEStatsEntry	OBJECT-TYPE
		SYNTAX		GigEStatsEntry
		MAX-ACCESS	not-accessible
		STATUS		current
		DESCRIPTION	"Row Description"
		INDEX		{  gigEStatsPortIndex, gigEStatsSlotNum  }
		::=  { gigEStatsTable 1 }

	GigEStatsEntry  ::=  SEQUENCE {
		gigEStatsPortIndex  Integer32,
		gigEStatsSlotNum  Integer32,
		linkStatusChanges  Counter64,
		framesRcvdOkCount  Counter64,
		octetsRcvdOkCount  Counter64,
		framesRcvdCount  Counter64,
		octetsRcvdCount  Counter64,
		frameSeqErrCount  Counter64,
		lostFramesMacErrCount  Counter64,
		rcvdFrames64Octets  Counter64,
		octetsRcvd1519toMax  Counter64,
		xmitFrames64Octets  Counter64,
		octetsXmit1024to1518  Counter64,
		octetsXmitCount  Counter64,
		unicastFramesXmitOk  Counter64,
		unicastFramesRcvdOk  Counter64,
		broadcastFramesXmitOk  Counter64,
		broadcastFramesRcvdOk  Counter64,
		multicastFramesXmitOk  Counter64,
		multicastFramesRcvdOk  Counter64,
		octetsRcvd65to127  Counter64,
		octetsXmit65to127  Counter64,
		octetRcvd128to255  Counter64,
		octetsXmit128to255  Counter64,
		octetsRcvd256to511  Counter64,
		octetsXmit256to511  Counter64,
		octetsRcvd512to1023  Counter64,
		octetsXmit512to1023  Counter64,
		octetsRcvd1024to1518  Counter64,
		octetsXmit1519toMax  Counter64,
		underSizeFramesRcvd  Counter64,
		jabbersRcvd  Counter64
		}


	gigEStatsPortIndex	OBJECT-TYPE	
		SYNTAX			Integer32  ( 1 .. 48  ) 
		MAX-ACCESS		read-only
		STATUS			current
		DESCRIPTION		"Index to table"
		::=  {  gigEStatsEntry  1  }


	gigEStatsSlotNum	OBJECT-TYPE	
		SYNTAX			Integer32  ( 0 .. 14  ) 
		MAX-ACCESS		read-only
		STATUS			current
		DESCRIPTION		"Slot number of gigE line card that the statistics          
correspond"
		::=  {  gigEStatsEntry  2  }


	linkStatusChanges	OBJECT-TYPE	
		SYNTAX			Counter64
		MAX-ACCESS		read-only
		STATUS			current
		DESCRIPTION		"Total number of link status changes"
		::=  {  gigEStatsEntry  3  }


	framesRcvdOkCount	OBJECT-TYPE	
		SYNTAX			Counter64
		MAX-ACCESS		read-only
		STATUS			current
		DESCRIPTION		"Total number of good frames received"
		::=  {  gigEStatsEntry  4  }


	octetsRcvdOkCount	OBJECT-TYPE	
		SYNTAX			Counter64
		MAX-ACCESS		read-only
		STATUS			current
		DESCRIPTION		"Total number of good octets received"
		::=  {  gigEStatsEntry  5  }


	framesRcvdCount	OBJECT-TYPE	
		SYNTAX			Counter64
		MAX-ACCESS		read-only
		STATUS			current
		DESCRIPTION		"Total number of frames received"
		::=  {  gigEStatsEntry  6  }


	octetsRcvdCount	OBJECT-TYPE	
		SYNTAX			Counter64
		MAX-ACCESS		read-only
		STATUS			current
		DESCRIPTION		"Total number of octets received"
		::=  {  gigEStatsEntry  7  }


	frameSeqErrCount	OBJECT-TYPE	
		SYNTAX			Counter64
		MAX-ACCESS		read-only
		STATUS			current
		DESCRIPTION		"Total number of frame sequence errors"
		::=  {  gigEStatsEntry  8  }


	lostFramesMacErrCount	OBJECT-TYPE	
		SYNTAX			Counter64
		MAX-ACCESS		read-only
		STATUS			current
		DESCRIPTION		"Total number of frames lost due to  internal MAX  errors"
		::=  {  gigEStatsEntry  9  }


	rcvdFrames64Octets	OBJECT-TYPE	
		SYNTAX			Counter64
		MAX-ACCESS		read-only
		STATUS			current
		DESCRIPTION		"Description"
		::=  {  gigEStatsEntry  10  }


	octetsRcvd1519toMax	OBJECT-TYPE	
		SYNTAX			Counter64
		MAX-ACCESS		read-only
		STATUS			current
		DESCRIPTION		"Description"
		::=  {  gigEStatsEntry  11  }


	xmitFrames64Octets	OBJECT-TYPE	
		SYNTAX			Counter64
		MAX-ACCESS		read-only
		STATUS			current
		DESCRIPTION		"Description"
		::=  {  gigEStatsEntry  12  }


	octetsXmit1024to1518	OBJECT-TYPE	
		SYNTAX			Counter64
		MAX-ACCESS		read-only
		STATUS			current
		DESCRIPTION		"Description"
		::=  {  gigEStatsEntry  13  }


	octetsXmitCount	OBJECT-TYPE	
		SYNTAX			Counter64
		MAX-ACCESS		read-only
		STATUS			current
		DESCRIPTION		"Number of octets transmitted on the physical port"
		::=  {  gigEStatsEntry  14  }


	unicastFramesXmitOk	OBJECT-TYPE	
		SYNTAX			Counter64
		MAX-ACCESS		read-only
		STATUS			current
		DESCRIPTION		"Number of unicast frames transmitted  OK on the physical   
port"
		::=  {  gigEStatsEntry  15  }


	unicastFramesRcvdOk	OBJECT-TYPE	
		SYNTAX			Counter64
		MAX-ACCESS		read-only
		STATUS			current
		DESCRIPTION		"Unicast Frames Received OK"
		::=  {  gigEStatsEntry  16  }


	broadcastFramesXmitOk	OBJECT-TYPE	
		SYNTAX			Counter64
		MAX-ACCESS		read-only
		STATUS			current
		DESCRIPTION		"Broadcast Frames Transmitted OK"
		::=  {  gigEStatsEntry  17  }


	broadcastFramesRcvdOk	OBJECT-TYPE	
		SYNTAX			Counter64
		MAX-ACCESS		read-only
		STATUS			current
		DESCRIPTION		"Broadcast Frames Received OK"
		::=  {  gigEStatsEntry  18  }


	multicastFramesXmitOk	OBJECT-TYPE	
		SYNTAX			Counter64
		MAX-ACCESS		read-only
		STATUS			current
		DESCRIPTION		"Multicast Frames tranmistted OK"
		::=  {  gigEStatsEntry  19  }


	multicastFramesRcvdOk	OBJECT-TYPE	
		SYNTAX			Counter64
		MAX-ACCESS		read-only
		STATUS			current
		DESCRIPTION		"Multicast Frames Received OK"
		::=  {  gigEStatsEntry  20  }


	octetsRcvd65to127	OBJECT-TYPE	
		SYNTAX			Counter64
		MAX-ACCESS		read-only
		STATUS			current
		DESCRIPTION		"65 To 127 Octet Frames Received"
		::=  {  gigEStatsEntry  21  }


	octetsXmit65to127	OBJECT-TYPE	
		SYNTAX			Counter64
		MAX-ACCESS		read-only
		STATUS			current
		DESCRIPTION		"128 To 255 Octet Frames Transmitted"
		::=  {  gigEStatsEntry  22  }


	octetRcvd128to255	OBJECT-TYPE	
		SYNTAX			Counter64
		MAX-ACCESS		read-only
		STATUS			current
		DESCRIPTION		"128 To 255 Octet Frames Received"
		::=  {  gigEStatsEntry  23  }


	octetsXmit128to255	OBJECT-TYPE	
		SYNTAX			Counter64
		MAX-ACCESS		read-only
		STATUS			current
		DESCRIPTION		"128 To 255 Octet Frames Transmitted"
		::=  {  gigEStatsEntry  24  }


	octetsRcvd256to511	OBJECT-TYPE	
		SYNTAX			Counter64
		MAX-ACCESS		read-only
		STATUS			current
		DESCRIPTION		"Description 256 To 511 Octet Frames Received"
		::=  {  gigEStatsEntry  25  }


	octetsXmit256to511	OBJECT-TYPE	
		SYNTAX			Counter64
		MAX-ACCESS		read-only
		STATUS			current
		DESCRIPTION		"256 To 511 Octet Frames Transmitted"
		::=  {  gigEStatsEntry  26  }


	octetsRcvd512to1023	OBJECT-TYPE	
		SYNTAX			Counter64
		MAX-ACCESS		read-only
		STATUS			current
		DESCRIPTION		"512 To 1023 Octet Frames Received"
		::=  {  gigEStatsEntry  27  }


	octetsXmit512to1023	OBJECT-TYPE	
		SYNTAX			Counter64
		MAX-ACCESS		read-only
		STATUS			current
		DESCRIPTION		"512 To 1023 Octet Frames Transmitted"
		::=  {  gigEStatsEntry  28  }


	octetsRcvd1024to1518	OBJECT-TYPE	
		SYNTAX			Counter64
		MAX-ACCESS		read-only
		STATUS			current
		DESCRIPTION		"1024 To 1518 Octet Frames Received"
		::=  {  gigEStatsEntry  29  }


	octetsXmit1519toMax	OBJECT-TYPE	
		SYNTAX			Counter64
		MAX-ACCESS		read-only
		STATUS			current
		DESCRIPTION		"1519 To Max Octed Frames Transmitted"
		::=  {  gigEStatsEntry  30  }


	underSizeFramesRcvd	OBJECT-TYPE	
		SYNTAX			Counter64
		MAX-ACCESS		read-only
		STATUS			current
		DESCRIPTION		"Under Sized Frames Received"
		::=  {  gigEStatsEntry  31  }


	jabbersRcvd	OBJECT-TYPE	
		SYNTAX			Counter64
		MAX-ACCESS		read-only
		STATUS			current
		DESCRIPTION		"Jabbers Received"
		::=  {  gigEStatsEntry  32  }

	serviceStatsTable	OBJECT-TYPE
		SYNTAX		SEQUENCE  OF  ServiceStatsEntry
		MAX-ACCESS	not-accessible
		STATUS		current
		DESCRIPTION	"Description"
		::=  { serviceStats  1 }

	serviceStatsEntry	OBJECT-TYPE
		SYNTAX		ServiceStatsEntry
		MAX-ACCESS	not-accessible
		STATUS		current
		DESCRIPTION	"Row Description"
		INDEX		{  serviceStatsPortIndex, serviceStatsSlotId  }
		::=  { serviceStatsTable 1 }

	ServiceStatsEntry  ::=  SEQUENCE {
		serviceStatsPortIndex  Integer32,
		serviceStatsSlotId  Integer32,
		realTimeTotalPackets  Counter64,
		realTimeDiscardPackets  Counter64,
		nrtTotalPackets  Counter64,
		nrtDiscardPackets  Counter64,
		bestEffortTotalPackets  Counter64,
		bestEffortDiscardPackets  Counter64
		}


	serviceStatsPortIndex	OBJECT-TYPE	
		SYNTAX			Integer32  ( -2147483648 .. 2147483647  ) 
		MAX-ACCESS		read-only
		STATUS			current
		DESCRIPTION		"Maps to a physical port on the nCite"
		::=  {  serviceStatsEntry  1  }


	serviceStatsSlotId	OBJECT-TYPE	
		SYNTAX			Integer32
		MAX-ACCESS		read-only
		STATUS			current
		DESCRIPTION		"Slot number of the line card"
		::=  {  serviceStatsEntry  2  }


	realTimeTotalPackets	OBJECT-TYPE	
		SYNTAX			Counter64
		MAX-ACCESS		read-only
		STATUS			current
		DESCRIPTION		"Total number of real time packets processed"
		::=  {  serviceStatsEntry  3  }


	realTimeDiscardPackets	OBJECT-TYPE	
		SYNTAX			Counter64
		MAX-ACCESS		read-only
		STATUS			current
		DESCRIPTION		"Number of real time packets discarded"
		::=  {  serviceStatsEntry  4  }


	nrtTotalPackets	OBJECT-TYPE	
		SYNTAX			Counter64
		MAX-ACCESS		read-only
		STATUS			current
		DESCRIPTION		"Total number of near real time packets processed"
		::=  {  serviceStatsEntry  5  }


	nrtDiscardPackets	OBJECT-TYPE	
		SYNTAX			Counter64
		MAX-ACCESS		read-only
		STATUS			current
		DESCRIPTION		"Number of near real time packets discarded"
		::=  {  serviceStatsEntry  6  }


	bestEffortTotalPackets	OBJECT-TYPE	
		SYNTAX			Counter64
		MAX-ACCESS		read-only
		STATUS			current
		DESCRIPTION		"Total number of best effort packets processed"
		::=  {  serviceStatsEntry  7  }


	bestEffortDiscardPackets	OBJECT-TYPE	
		SYNTAX			Counter64
		MAX-ACCESS		read-only
		STATUS			current
		DESCRIPTION		"Number of best effort packets discarded"
		::=  {  serviceStatsEntry  8  }

	redundPairedModeTimeTicks	OBJECT-TYPE	
		SYNTAX			Counter64
		MAX-ACCESS		read-only
		STATUS			current
		DESCRIPTION		"Number of time ticks spent in duplex mode"
		::=  {  redundancyStats  1  }

	redundRecoveryModeTimeTicks	OBJECT-TYPE	
		SYNTAX			Counter64
		MAX-ACCESS		read-only
		STATUS			current
		DESCRIPTION		"Number of time ticks spent in recovery mode"
		::=  {  redundancyStats  2  }

	redundNumRedundLinkFailures	OBJECT-TYPE	
		SYNTAX			Counter64
		MAX-ACCESS		read-only
		STATUS			current
		DESCRIPTION		"Number of times the out of band link for redundancy has    
failed"
		::=  {  redundancyStats  3  }

	redundActiveMateCalls	OBJECT-TYPE	
		SYNTAX			Counter64
		MAX-ACCESS		read-only
		STATUS			current
		DESCRIPTION		"Number of flows established flows associated with the mate 
system"
		::=  {  redundancyStats  4  }

	redundActiveMateRegist	OBJECT-TYPE	
		SYNTAX			Counter64
		MAX-ACCESS		read-only
		STATUS			current
		DESCRIPTION		"Total number of active registrations"
		::=  {  redundancyStats  5  }

	policyCountersTable	OBJECT-TYPE
		SYNTAX		SEQUENCE  OF  PolicyCountersEntry
		MAX-ACCESS	not-accessible
		STATUS		current
		DESCRIPTION	"Policy statistics."
		::=  { policyStats  1 }

	policyCountersEntry	OBJECT-TYPE
		SYNTAX		PolicyCountersEntry
		MAX-ACCESS	not-accessible
		STATUS		current
		DESCRIPTION	"Row Description"
		INDEX		{  policyIndex  }
		::=  { policyCountersTable 1 }

	PolicyCountersEntry  ::=  SEQUENCE {
		policyIndex  OCTET STRING,
		policyTotalPacketsA  Counter64,
		policyTotalPacketsB  Counter64,
		policyTotalPackets  Counter64
		}


	policyIndex	OBJECT-TYPE	
		SYNTAX			OCTET STRING
		MAX-ACCESS		read-only
		STATUS			current
		DESCRIPTION		"This field reflects the policy name."
		::=  {  policyCountersEntry  1  }


	policyTotalPacketsA	OBJECT-TYPE	
		SYNTAX			Counter64
		MAX-ACCESS		read-only
		STATUS			current
		DESCRIPTION		"Total number of packets processed for the policy on side A"
		::=  {  policyCountersEntry  2  }


	policyTotalPacketsB	OBJECT-TYPE	
		SYNTAX			Counter64
		MAX-ACCESS		read-only
		STATUS			current
		DESCRIPTION		"Total number of packets processed for the policy on side B"
		::=  {  policyCountersEntry  3  }


	policyTotalPackets	OBJECT-TYPE	
		SYNTAX			Counter64
		MAX-ACCESS		read-only
		STATUS			current
		DESCRIPTION		"This field applies to nCites that do not have 'sides'"
		::=  {  policyCountersEntry  4  }

	policyStatsReset	OBJECT-TYPE	
		SYNTAX			Integer32  ( -2147483648 .. 2147483647  ) 
		MAX-ACCESS		read-write
		STATUS			current
		DESCRIPTION		"Set to reset when the policy configuration is changed"
		::=  {  policyStats  2  }

	sipStatCallsInitiating	OBJECT-TYPE	
		SYNTAX			Counter64
		MAX-ACCESS		read-only
		STATUS			current
		DESCRIPTION		"Real-time stat of calls that are being initiated after     
receiving the initial INVITE SIP request."
		::=  {  sipStats  1  }

	sipStatNonLocalActiveCalls	OBJECT-TYPE	
		SYNTAX			Counter64
		MAX-ACCESS		read-only
		STATUS			deprecated
		DESCRIPTION		"Real-time stat of calls that are currently in the ACTIVE   
state that are non-local calls"
		::=  {  sipStats  2  }

	sipStatLocalActiveCalls	OBJECT-TYPE	
		SYNTAX			Counter64
		MAX-ACCESS		read-only
		STATUS			current
		DESCRIPTION		"Real-time stat that is the number of active calls that are 
local"
		::=  {  sipStats  3  }

	sipStatTermCalls	OBJECT-TYPE	
		SYNTAX			Counter64
		MAX-ACCESS		read-only
		STATUS			current
		DESCRIPTION		"Real-time stat that is the number of calls in the          
TERMINATING state after a BYE SIP request."
		::=  {  sipStats  4  }

	sipStatPeakActiveCalls	OBJECT-TYPE	
		SYNTAX			Counter64
		MAX-ACCESS		read-only
		STATUS			deprecated
		DESCRIPTION		"Peak number of active calls since the last nCite reboot."
		::=  {  sipStats  5  }

	sipStatTotalActiveCalls	OBJECT-TYPE	
		SYNTAX			Counter64
		MAX-ACCESS		read-only
		STATUS			current
		DESCRIPTION		"Total number of active calls. sipStatLocalActvieCalls +    
sipStatNonLocalActiveCalls"
		::=  {  sipStats  6  }

	sipStatCallsCompletedSuccess	OBJECT-TYPE	
		SYNTAX			Counter64
		MAX-ACCESS		read-only
		STATUS			current
		DESCRIPTION		"Total number of calls that have been completed             
successfully since the last time the nCIte was reboot."
		::=  {  sipStats  7  }

	sipStatCallsFailed	OBJECT-TYPE	
		SYNTAX			Counter64
		MAX-ACCESS		read-only
		STATUS			current
		DESCRIPTION		"Total number of calls that completed due to some failure   
since the last time the nCite was reboot."
		::=  {  sipStats  8  }

	sipStatCallsAbandoned	OBJECT-TYPE	
		SYNTAX			Counter64
		MAX-ACCESS		read-only
		STATUS			current
		DESCRIPTION		"Total number of calls that did not transition to active    
state because of normal termination since the last time the 
nCIte was reboot."
		::=  {  sipStats  9  }

	sipStatCallsDropped	OBJECT-TYPE	
		SYNTAX			Counter64
		MAX-ACCESS		read-only
		STATUS			deprecated
		DESCRIPTION		"Total number of calls that were dropped due to exceeding   
adminision control since the last time the nCite was        
reboot."
		::=  {  sipStats  10  }

	sipStatCallsDegraded	OBJECT-TYPE	
		SYNTAX			Counter64
		MAX-ACCESS		read-only
		STATUS			current
		DESCRIPTION		"Total number of calls that were processed in a degraded    
state due to exceeding admission control since the last     
time the nCIte was reboot."
		::=  {  sipStats  11  }

	sipStatAuthFailures	OBJECT-TYPE	
		SYNTAX			Counter64
		MAX-ACCESS		read-only
		STATUS			deprecated
		DESCRIPTION		"Total number of calls that were rejected because they      
could not be autenticated against a valid customer          
definition since the last time the nCite was reboot."
		::=  {  sipStats  12  }

	sipStatCallMediaTimeouts	OBJECT-TYPE	
		SYNTAX			Counter64
		MAX-ACCESS		read-only
		STATUS			current
		DESCRIPTION		"Total number of times a call was terminated because of a   
RTP media timeout since the last time the nCIte was reboot."
		::=  {  sipStats  13  }

	sipStatCallInitTimeouts	OBJECT-TYPE	
		SYNTAX			Counter64
		MAX-ACCESS		read-only
		STATUS			current
		DESCRIPTION		"Total number of times a SIP timout occurred after the      
receipt of the initial INVITE and before the ACK is         
received for the INVITE since the last time the nCite was   
reboot."
		::=  {  sipStats  14  }

	sipStatTermTimeouts	OBJECT-TYPE	
		SYNTAX			Counter64
		MAX-ACCESS		read-only
		STATUS			current
		DESCRIPTION		"Total number of times a SIP timout occurred after the      
receipt of the BYE and before the ACK is received for the   
BYE since the last time the nCIte was reboot."
		::=  {  sipStats  15  }

	sipStatMsgErrs	OBJECT-TYPE	
		SYNTAX			Counter64
		MAX-ACCESS		read-only
		STATUS			deprecated
		DESCRIPTION		"Total number of times a SIP error message was received     
since the last time the nCite was reboot."
		::=  {  sipStats  16  }

	sipStatCallsProcessed	OBJECT-TYPE	
		SYNTAX			Counter64
		MAX-ACCESS		read-only
		STATUS			current
		DESCRIPTION		"Total number of calls that have been processed since the   
nCIte was last reboot. This iwll be the sum of              
sipStatCallsCompletedSuccess, sipStatCallsFailed,           
sipStatCallsAbandoned, sipStatCallsDropped,                 
sipStatAuthFailures"
		::=  {  sipStats  17  }

	sipStatPeakNonLocalCalls	OBJECT-TYPE	
		SYNTAX			Counter64
		MAX-ACCESS		read-only
		STATUS			deprecated
		DESCRIPTION		"Real-time statistics that is the peak number of non-local  
active calls."
		::=  {  sipStats  18  }

	sipStatPeakLocalCalls	OBJECT-TYPE	
		SYNTAX			Counter64
		MAX-ACCESS		read-only
		STATUS			current
		DESCRIPTION		"Real-time statistic that is the peak number of active      
local calls."
		::=  {  sipStats  19  }

	sipStatRedirectSuccess	OBJECT-TYPE	
		SYNTAX			Counter64
		MAX-ACCESS		read-only
		STATUS			deprecated
		DESCRIPTION		"Total number of successful redirects"
		::=  {  sipStats  20  }

	sipStatRedirectFailures	OBJECT-TYPE	
		SYNTAX			Counter64
		MAX-ACCESS		read-only
		STATUS			deprecated
		DESCRIPTION		"Total number of failed redirects"
		::=  {  sipStats  21  }

	sipStatMessageRoutingFailures	OBJECT-TYPE	
		SYNTAX			Counter64
		MAX-ACCESS		read-only
		STATUS			deprecated
		DESCRIPTION		"Failures due to route lookup - no enabled route found"
		::=  {  sipStats  22  }

	sipStatAuthenticationChallenges	OBJECT-TYPE	
		SYNTAX			Counter64
		MAX-ACCESS		read-only
		STATUS			current
		DESCRIPTION		"Number of Authentication Challenges"
		::=  {  sipStats  23  }

	sipStatRTPFWTraversalTimeouts	OBJECT-TYPE	
		SYNTAX			Counter64
		MAX-ACCESS		read-only
		STATUS			current
		DESCRIPTION		"Number of RTP forward traversal timeouts"
		::=  {  sipStats  24  }

	sipStatMessagesReroutedToMate	OBJECT-TYPE	
		SYNTAX			Counter64
		MAX-ACCESS		read-only
		STATUS			deprecated
		DESCRIPTION		"Number of messages rerouted to mate"
		::=  {  sipStats  25  }

	sipStatSameSideActiveCalls	OBJECT-TYPE	
		SYNTAX			Counter64
		MAX-ACCESS		read-only
		STATUS			current
		DESCRIPTION		"Same side actvie calls"
		::=  {  sipStats  26  }

	sipStatNormalActiveCalls	OBJECT-TYPE	
		SYNTAX			Counter64
		MAX-ACCESS		read-only
		STATUS			current
		DESCRIPTION		"Normal active calls"
		::=  {  sipStats  27  }

	sipStatPeakSameSideActiveCalls	OBJECT-TYPE	
		SYNTAX			Counter64
		MAX-ACCESS		read-only
		STATUS			current
		DESCRIPTION		"Peak same side active calls"
		::=  {  sipStats  28  }

	sipStatPeakNormalActiveCalls	OBJECT-TYPE	
		SYNTAX			Counter64
		MAX-ACCESS		read-only
		STATUS			current
		DESCRIPTION		"Peak normal active calls"
		::=  {  sipStats  29  }

	sipStatCurrentFaxSessions	OBJECT-TYPE	
		SYNTAX			Counter64
		MAX-ACCESS		read-only
		STATUS			deprecated
		DESCRIPTION		"Current number of FAX Sessions that are active"
		::=  {  sipStats  30  }

	sipStatPeakFaxSessions	OBJECT-TYPE	
		SYNTAX			Counter64
		MAX-ACCESS		read-only
		STATUS			deprecated
		DESCRIPTION		"Maximum number of FAX sessions active at any point in time 
since the statistics were last reset"
		::=  {  sipStats  31  }

	sipStatTotalFaxSessions	OBJECT-TYPE	
		SYNTAX			Counter64
		MAX-ACCESS		read-only
		STATUS			deprecated
		DESCRIPTION		"The total number of FAX sessions that have occurred since  
the statistics were last reset"
		::=  {  sipStats  32  }

	sipStatPeakTotalActiveCalls	OBJECT-TYPE	
		SYNTAX			Counter64
		MAX-ACCESS		read-only
		STATUS			current
		DESCRIPTION		"Peak number of total active calls on the nCite since the   
statistics were last reset"
		::=  {  sipStats  33  }

	vlanStatsTable	OBJECT-TYPE
		SYNTAX		SEQUENCE  OF  VlanStatsEntry
		MAX-ACCESS	not-accessible
		STATUS		current
		DESCRIPTION	"Description"
		::=  { vlanStats  2 }

	vlanStatsEntry	OBJECT-TYPE
		SYNTAX		VlanStatsEntry
		MAX-ACCESS	not-accessible
		STATUS		current
		DESCRIPTION	"Row Description"
		INDEX		{  vlanStatsSlotNum, vlanStatsPortNum, vlanStatsVlanLabel  }
		::=  { vlanStatsTable 1 }

	VlanStatsEntry  ::=  SEQUENCE {
		vlanStatsSlotNum  Integer32,
		vlanStatsPortNum  Integer32,
		vlanStatsVlanLabel  Integer32,
		vlanTotalPacketsXmit  Counter64,
		vlanTotalPacketsRcvd  Counter64
		}


	vlanStatsSlotNum	OBJECT-TYPE	
		SYNTAX			Integer32  ( 0 .. 14  ) 
		MAX-ACCESS		read-only
		STATUS			current
		DESCRIPTION		"Slot number of line card"
		::=  {  vlanStatsEntry  1  }


	vlanStatsPortNum	OBJECT-TYPE	
		SYNTAX			Integer32  ( 1 .. 48  ) 
		MAX-ACCESS		read-only
		STATUS			current
		DESCRIPTION		"Port number for the vlan stats"
		::=  {  vlanStatsEntry  2  }


	vlanStatsVlanLabel	OBJECT-TYPE	
		SYNTAX			Integer32
		MAX-ACCESS		read-only
		STATUS			current
		DESCRIPTION		"Unique identifier of the VLAN"
		::=  {  vlanStatsEntry  3  }


	vlanTotalPacketsXmit	OBJECT-TYPE	
		SYNTAX			Counter64
		MAX-ACCESS		read-only
		STATUS			current
		DESCRIPTION		"Number of packets transmitted on a VLAN"
		::=  {  vlanStatsEntry  4  }


	vlanTotalPacketsRcvd	OBJECT-TYPE	
		SYNTAX			Counter64
		MAX-ACCESS		read-only
		STATUS			current
		DESCRIPTION		"Number of packets receivedon the given VLAN"
		::=  {  vlanStatsEntry  5  }

	vlanStatsReset	OBJECT-TYPE	
		SYNTAX			INTEGER  { default ( 0 ) , reset ( 1 ) } 
		MAX-ACCESS		read-write
		STATUS			current
		DESCRIPTION		"Set to reset when the 					 					 					 policy  					      
					 image  					 					  					 					changes"
		DEFVAL			{ default }
		::=  {  vlanStats  3  }

	custSipStatsTable	OBJECT-TYPE
		SYNTAX		SEQUENCE  OF  CustSipStatsEntry
		MAX-ACCESS	not-accessible
		STATUS		current
		DESCRIPTION	"Description"
		::=  { custSipStats  1 }

	custSipStatsEntry	OBJECT-TYPE
		SYNTAX		CustSipStatsEntry
		MAX-ACCESS	not-accessible
		STATUS		current
		DESCRIPTION	"Row Description"
		INDEX		{  custSipStatId  }
		::=  { custSipStatsTable 1 }

	CustSipStatsEntry  ::=  SEQUENCE {
		custSipStatId  Integer32,
		custSipStatCallsInitiating  Counter64,
		custSipStatNonLocalActiveCalls  Counter64,
		custSipStatLocalActiveCalls  Counter64,
		custSipStatTermCalls  Counter64,
		custSipStatPeakActiveCalls  Counter64,
		custSipStatTotalActiveCalls  Counter64,
		custSipStatCallsCompletedSuccess  Counter64,
		custSipStatCallsFailed  Counter64,
		custSipStatCallsAbandoned  Counter64,
		custSipStatCallsDropped  Counter64,
		custSipStatCallsDegraded  Counter64,
		custSipStatCallMediaTimeouts  Counter64,
		custSipStatCallInitTimeouts  Counter64,
		custSipStatTermTimeouts  Counter64,
		custSipStatCallsProcessed  Counter64,
		custSipPeakNonLocalCalls  Counter64,
		custSipPeakLocalCalls  Counter64,
		custSipAuthenticationChallenges  Counter64,
		custSipRTPFWTraversalTimeouts  Counter64,
		custSipSameSideActiveCalls  Counter64,
		custSipNormalActiveCalls  Counter64,
		custSipPeakNormalActiveCalls  Counter64,
		custSipPeakTotalActive  Counter64
		}


	custSipStatId	OBJECT-TYPE	
		SYNTAX			Integer32
		MAX-ACCESS		read-only
		STATUS			current
		DESCRIPTION		"Customer ID as it is defined in the EMS database and the   
XML file provisioned to the nCIte"
		::=  {  custSipStatsEntry  1  }


	custSipStatCallsInitiating	OBJECT-TYPE	
		SYNTAX			Counter64
		MAX-ACCESS		read-only
		STATUS			current
		DESCRIPTION		"Real-time stat of calls that are being initiated after     
receiving the initial INVITE SIP request."
		::=  {  custSipStatsEntry  2  }


	custSipStatNonLocalActiveCalls	OBJECT-TYPE	
		SYNTAX			Counter64
		MAX-ACCESS		read-only
		STATUS			deprecated
		DESCRIPTION		"Real-time stat of calls that are currently in the ACTIVE   
state that are non-local calls"
		::=  {  custSipStatsEntry  3  }


	custSipStatLocalActiveCalls	OBJECT-TYPE	
		SYNTAX			Counter64
		MAX-ACCESS		read-only
		STATUS			current
		DESCRIPTION		"Real-time stat that is the number of active calls that are 
local"
		::=  {  custSipStatsEntry  4  }


	custSipStatTermCalls	OBJECT-TYPE	
		SYNTAX			Counter64
		MAX-ACCESS		read-only
		STATUS			current
		DESCRIPTION		"Real-time stat that is the number of calls in the          
TERMINATING state after a BYE SIP request."
		::=  {  custSipStatsEntry  5  }


	custSipStatPeakActiveCalls	OBJECT-TYPE	
		SYNTAX			Counter64
		MAX-ACCESS		read-only
		STATUS			deprecated
		DESCRIPTION		"Peak number of active calls since the last nCite reboot."
		::=  {  custSipStatsEntry  6  }


	custSipStatTotalActiveCalls	OBJECT-TYPE	
		SYNTAX			Counter64
		MAX-ACCESS		read-only
		STATUS			current
		DESCRIPTION		"Total number of active calls. custSipStatLocalActvieCalls  
+  custSipStatNonLocalActiveCalls"
		::=  {  custSipStatsEntry  7  }


	custSipStatCallsCompletedSuccess	OBJECT-TYPE	
		SYNTAX			Counter64
		MAX-ACCESS		read-only
		STATUS			current
		DESCRIPTION		"Total number of calls that have been completed             
successfully since the last time the nCIte was reboot."
		::=  {  custSipStatsEntry  8  }


	custSipStatCallsFailed	OBJECT-TYPE	
		SYNTAX			Counter64
		MAX-ACCESS		read-only
		STATUS			current
		DESCRIPTION		"Total number of calls that completed due to some failure   
since the last time the nCite was reboot."
		::=  {  custSipStatsEntry  9  }


	custSipStatCallsAbandoned	OBJECT-TYPE	
		SYNTAX			Counter64
		MAX-ACCESS		read-only
		STATUS			current
		DESCRIPTION		"Total number of calls that did not transition to active    
state because of normal termination since the last time the 
nCIte was reboot."
		::=  {  custSipStatsEntry  10  }


	custSipStatCallsDropped	OBJECT-TYPE	
		SYNTAX			Counter64
		MAX-ACCESS		read-only
		STATUS			deprecated
		DESCRIPTION		"Total number of calls that were dropped due to exceeding   
adminision control since the last time the nCite was        
reboot."
		::=  {  custSipStatsEntry  11  }


	custSipStatCallsDegraded	OBJECT-TYPE	
		SYNTAX			Counter64
		MAX-ACCESS		read-only
		STATUS			current
		DESCRIPTION		"Total number of calls that were processed in a degraded    
state due to exceeding admission control since the last     
time the nCIte was reboot."
		::=  {  custSipStatsEntry  12  }


	custSipStatCallMediaTimeouts	OBJECT-TYPE	
		SYNTAX			Counter64
		MAX-ACCESS		read-only
		STATUS			current
		DESCRIPTION		"Total number of times a call was terminated because of a   
RTP media timeout since the last time the nCIte was reboot."
		::=  {  custSipStatsEntry  13  }


	custSipStatCallInitTimeouts	OBJECT-TYPE	
		SYNTAX			Counter64
		MAX-ACCESS		read-only
		STATUS			current
		DESCRIPTION		"Total number of times a SIP timout occurred after the      
receipt of the initial INVITE and before the ACK is         
received for the INVITE since the last time the nCite was   
reboot."
		::=  {  custSipStatsEntry  14  }


	custSipStatTermTimeouts	OBJECT-TYPE	
		SYNTAX			Counter64
		MAX-ACCESS		read-only
		STATUS			current
		DESCRIPTION		"Total number of times a SIP timout occurred after the      
receipt of the BYE and before the ACK is received for the   
BYE since the last time the nCIte was reboot."
		::=  {  custSipStatsEntry  15  }


	custSipStatCallsProcessed	OBJECT-TYPE	
		SYNTAX			Counter64
		MAX-ACCESS		read-only
		STATUS			current
		DESCRIPTION		"Total number of calls that have been processed since the   
nCIte was last reboot. This iwll be the sum of              
custSipStatCallsCompletedSuccess, custSipStatCallsFailed,   
custSipStatCallsAbandoned, custSipStatCallsDropped,         
custSipStatAuthFailures"
		::=  {  custSipStatsEntry  16  }


	custSipPeakNonLocalCalls	OBJECT-TYPE	
		SYNTAX			Counter64
		MAX-ACCESS		read-only
		STATUS			deprecated
		DESCRIPTION		"Peak number of non-local calls since the ncite was reboot  
or the statistics were cleared"
		::=  {  custSipStatsEntry  17  }


	custSipPeakLocalCalls	OBJECT-TYPE	
		SYNTAX			Counter64
		MAX-ACCESS		read-only
		STATUS			current
		DESCRIPTION		"Peak number of local calls"
		::=  {  custSipStatsEntry  18  }


	custSipAuthenticationChallenges	OBJECT-TYPE	
		SYNTAX			Counter64
		MAX-ACCESS		read-only
		STATUS			current
		DESCRIPTION		"Number of authentication challanges"
		::=  {  custSipStatsEntry  19  }


	custSipRTPFWTraversalTimeouts	OBJECT-TYPE	
		SYNTAX			Counter64
		MAX-ACCESS		read-only
		STATUS			current
		DESCRIPTION		"Number of RTP forward traversal timeouts"
		::=  {  custSipStatsEntry  20  }


	custSipSameSideActiveCalls	OBJECT-TYPE	
		SYNTAX			Counter64
		MAX-ACCESS		read-only
		STATUS			current
		DESCRIPTION		"Number of same side active calls"
		::=  {  custSipStatsEntry  21  }


	custSipNormalActiveCalls	OBJECT-TYPE	
		SYNTAX			Counter64
		MAX-ACCESS		read-only
		STATUS			current
		DESCRIPTION		"Number of normal active calls"
		::=  {  custSipStatsEntry  22  }


	custSipPeakNormalActiveCalls	OBJECT-TYPE	
		SYNTAX			Counter64
		MAX-ACCESS		read-only
		STATUS			current
		DESCRIPTION		"Maximum number of active normal calls since the statistics 
were last reset."
		::=  {  custSipStatsEntry  23  }


	custSipPeakTotalActive	OBJECT-TYPE	
		SYNTAX			Counter64
		MAX-ACCESS		read-only
		STATUS			current
		DESCRIPTION		"Peak number of total active calls since the statistics     
were last reset"
		::=  {  custSipStatsEntry  24  }

	nCiteSDRCollectionCycle	OBJECT-TYPE	
		SYNTAX			Integer32
		MAX-ACCESS		read-only
		STATUS			current
		DESCRIPTION		"The number of minutes that data is collected per file."
		DEFVAL			{ 5 }
		::=  {  nCiteSessionDetailRecord  1  }

	nCIteSDRLastSent	OBJECT-TYPE	
		SYNTAX			DateAndTime
		MAX-ACCESS		read-only
		STATUS			current
		DESCRIPTION		"Date and time that the last SDR file was sent to the EMS"
		::=  {  nCiteSessionDetailRecord  2  }

	nCiteSDREnable	OBJECT-TYPE	
		SYNTAX			INTEGER  { disabled ( 0 ) , enabled ( 1 ) } 
		MAX-ACCESS		read-only
		STATUS			current
		DESCRIPTION		"Indicates whether SDR generation is enabled"
		::=  {  nCiteSessionDetailRecord  3  }

	nCiteSDRSentTrap	NOTIFICATION-TYPE
		OBJECTS			{ nCIteSDRLastSent  }
		STATUS			current
		DESCRIPTION		"Description"
		::=  {  nCiteSessionDetailRecord  4  }

	nCiteSDRSentTrapAck	OBJECT-TYPE	
		SYNTAX			INTEGER  { notAck ( 0 ) , ack ( 1 ) } 
		MAX-ACCESS		read-write
		STATUS			current
		DESCRIPTION		"nCite SDR sent trap acknowledge flag"
		::=  {  nCiteSessionDetailRecord  5  }

	nCiteSDRSentTrapAckSource	OBJECT-TYPE	
		SYNTAX			IpAddress
		MAX-ACCESS		read-write
		STATUS			current
		DESCRIPTION		"Identifies the Snmp Manager which sets the trap ack."
		::=  {  nCiteSessionDetailRecord  6  }

	regStatNumInitiating	OBJECT-TYPE	
		SYNTAX			Counter64
		MAX-ACCESS		read-only
		STATUS			current
		DESCRIPTION		"Real-time statistic that is the number of Registrations    
that are currently in the Initiated state."
		::=  {  registrationStats  1  }

	regStatNumActive	OBJECT-TYPE	
		SYNTAX			Counter64
		MAX-ACCESS		read-only
		STATUS			current
		DESCRIPTION		"Real-time statistic that is the number of active           
registrations."
		::=  {  registrationStats  2  }

	regStatPeak	OBJECT-TYPE	
		SYNTAX			Counter64
		MAX-ACCESS		read-only
		STATUS			current
		DESCRIPTION		"Real-time statistic that is the peak number of active      
registrations."
		::=  {  registrationStats  3  }

	regStatUpdateSuccess	OBJECT-TYPE	
		SYNTAX			Counter64
		MAX-ACCESS		read-only
		STATUS			current
		DESCRIPTION		"Total number of successful registration updates since the  
last time the nCite was reboot"
		::=  {  registrationStats  4  }

	regStatUpdateFailed	OBJECT-TYPE	
		SYNTAX			Counter64
		MAX-ACCESS		read-only
		STATUS			current
		DESCRIPTION		"Total number of registration update requests that have     
failed since the nCite was last reboot."
		::=  {  registrationStats  5  }

	regStatExpired	OBJECT-TYPE	
		SYNTAX			Counter64
		MAX-ACCESS		read-only
		STATUS			current
		DESCRIPTION		"Total number of registration timeouts that have occurred   
since the nCite was last reboot."
		::=  {  registrationStats  6  }

	regStatDropped	OBJECT-TYPE	
		SYNTAX			Counter64
		MAX-ACCESS		read-only
		STATUS			deprecated
		DESCRIPTION		"Total number of registrations that were dropped due to     
exceeding admission control since the nCIte was last        
reboot."
		::=  {  registrationStats  7  }

	regStatAuthFailures	OBJECT-TYPE	
		SYNTAX			Counter64
		MAX-ACCESS		read-only
		STATUS			current
		DESCRIPTION		"Total number of registrations that were rejected because   
they could not be authenticated against a valid customer    
definition."
		::=  {  registrationStats  8  }

	regStatInitSipTimeouts	OBJECT-TYPE	
		SYNTAX			Counter64
		MAX-ACCESS		read-only
		STATUS			current
		DESCRIPTION		"Total number of times a SIP timeout occurred after the     
receipt of the initial registration and before the ACK is   
received for the Registration since the last time the nCIte 
was reboot."
		::=  {  registrationStats  9  }

	regStatTermSipTimeouts	OBJECT-TYPE	
		SYNTAX			Counter64
		MAX-ACCESS		read-only
		STATUS			current
		DESCRIPTION		"Total number of times a DIP timeout occurred after the     
receipt of the terminate registration and before the ACK is 
received since the last time the nCIte was reboot."
		::=  {  registrationStats  10  }

	regStatTerminating	OBJECT-TYPE	
		SYNTAX			Counter64
		MAX-ACCESS		read-only
		STATUS			current
		DESCRIPTION		"Number of terminating registrations"
		::=  {  registrationStats  11  }

	regStatFailed	OBJECT-TYPE	
		SYNTAX			Counter64
		MAX-ACCESS		read-only
		STATUS			current
		DESCRIPTION		"Number of failed registrations"
		::=  {  registrationStats  12  }

	regStatAuthenticationChallenges	OBJECT-TYPE	
		SYNTAX			Counter64
		MAX-ACCESS		read-only
		STATUS			current
		DESCRIPTION		"Registration authentication challenges"
		::=  {  registrationStats  13  }

	regStatUnauthReg	OBJECT-TYPE	
		SYNTAX			Counter64
		MAX-ACCESS		read-only
		STATUS			current
		DESCRIPTION		"Total number of accumulated unauthorized registrations"
		::=  {  registrationStats  14  }

	custRegStatsTable	OBJECT-TYPE
		SYNTAX		SEQUENCE  OF  CustRegStatsEntry
		MAX-ACCESS	not-accessible
		STATUS		current
		DESCRIPTION	"Description"
		::=  { custRegStats  1 }

	custRegStatsEntry	OBJECT-TYPE
		SYNTAX		CustRegStatsEntry
		MAX-ACCESS	not-accessible
		STATUS		current
		DESCRIPTION	"Row Description"
		INDEX		{  custRegStatId  }
		::=  { custRegStatsTable 1 }

	CustRegStatsEntry  ::=  SEQUENCE {
		custRegStatId  Integer32,
		custRegStatNumInitiated  Counter64,
		custRegStatNumActive  Counter64,
		custRegStatPeak  Counter64,
		custRegStatUpdateSuccess  Counter64,
		custRegStatUpdateFailed  Counter64,
		custRegStatExpired  Counter64,
		custRegStatDropped  Counter64,
		custRegStatInitSipTimeouts  Counter64,
		custRegStatTermSipTimeouts  Counter64,
		custRegStatTerminating  Counter64,
		custRegStatFailed  Counter64,
		custRegAuthenticationChallenges  Counter64,
		custRegStatUnauthorizedReg  Counter64
		}


	custRegStatId	OBJECT-TYPE	
		SYNTAX			Integer32
		MAX-ACCESS		read-only
		STATUS			current
		DESCRIPTION		"Customer ID as it is defined in the EMS database and the   
XML file provisioned to the nCIte"
		::=  {  custRegStatsEntry  1  }


	custRegStatNumInitiated	OBJECT-TYPE	
		SYNTAX			Counter64
		MAX-ACCESS		read-only
		STATUS			current
		DESCRIPTION		"Real-time statistic that is the number of Registrations    
that are currently in the Initiated state."
		::=  {  custRegStatsEntry  2  }


	custRegStatNumActive	OBJECT-TYPE	
		SYNTAX			Counter64
		MAX-ACCESS		read-only
		STATUS			current
		DESCRIPTION		"Real-time statistic that is the number of active           
registrations."
		::=  {  custRegStatsEntry  3  }


	custRegStatPeak	OBJECT-TYPE	
		SYNTAX			Counter64
		MAX-ACCESS		read-only
		STATUS			current
		DESCRIPTION		"Real-time statistic that is the peak number of active      
registrations."
		::=  {  custRegStatsEntry  4  }


	custRegStatUpdateSuccess	OBJECT-TYPE	
		SYNTAX			Counter64
		MAX-ACCESS		read-only
		STATUS			current
		DESCRIPTION		"Total number of successful registration updates since the  
last time the nCite was reboot"
		::=  {  custRegStatsEntry  5  }


	custRegStatUpdateFailed	OBJECT-TYPE	
		SYNTAX			Counter64
		MAX-ACCESS		read-only
		STATUS			current
		DESCRIPTION		"Total number of registration update requests that have     
failed since the nCite was last reboot."
		::=  {  custRegStatsEntry  6  }


	custRegStatExpired	OBJECT-TYPE	
		SYNTAX			Counter64
		MAX-ACCESS		read-only
		STATUS			current
		DESCRIPTION		"Total number of registration timeouts that have occurred   
since the nCite was last reboot."
		::=  {  custRegStatsEntry  7  }


	custRegStatDropped	OBJECT-TYPE	
		SYNTAX			Counter64
		MAX-ACCESS		read-only
		STATUS			deprecated
		DESCRIPTION		"Total number of registrations that were dropped due to     
exceeding admission control since the nCIte was last        
reboot."
		::=  {  custRegStatsEntry  8  }


	custRegStatInitSipTimeouts	OBJECT-TYPE	
		SYNTAX			Counter64
		MAX-ACCESS		read-only
		STATUS			current
		DESCRIPTION		"Total number of times a SIP timeout occurred after the     
receipt of the initial registration and before the ACK is   
received for the Registration since the last time the nCIte 
was reboot."
		::=  {  custRegStatsEntry  9  }


	custRegStatTermSipTimeouts	OBJECT-TYPE	
		SYNTAX			Counter64
		MAX-ACCESS		read-only
		STATUS			current
		DESCRIPTION		"Total number of times a DIP timeout occurred after the     
receipt of the terminate registration and before the ACK is 
received since the last time the nCIte was reboot."
		::=  {  custRegStatsEntry  10  }


	custRegStatTerminating	OBJECT-TYPE	
		SYNTAX			Counter64
		MAX-ACCESS		read-only
		STATUS			current
		DESCRIPTION		"Number of customer registrations terminating"
		::=  {  custRegStatsEntry  11  }


	custRegStatFailed	OBJECT-TYPE	
		SYNTAX			Counter64
		MAX-ACCESS		read-only
		STATUS			current
		DESCRIPTION		"Number of customer registrations that have failed"
		::=  {  custRegStatsEntry  12  }


	custRegAuthenticationChallenges	OBJECT-TYPE	
		SYNTAX			Counter64
		MAX-ACCESS		read-only
		STATUS			current
		DESCRIPTION		"Customer Authentication challenges"
		::=  {  custRegStatsEntry  13  }


	custRegStatUnauthorizedReg	OBJECT-TYPE	
		SYNTAX			Counter64
		MAX-ACCESS		read-only
		STATUS			current
		DESCRIPTION		"Number of accumulated unauthorized registrations for a   
customer"
		::=  {  custRegStatsEntry  14  }

	ntsStatNumCust	OBJECT-TYPE	
		SYNTAX			Counter64
		MAX-ACCESS		read-only
		STATUS			current
		DESCRIPTION		"Total number of customers for which NTS Clients are        
enabled."
		::=  {  ntsStats  1  }

	ntsStatAuthFailures	OBJECT-TYPE	
		SYNTAX			Counter64
		MAX-ACCESS		read-only
		STATUS			current
		DESCRIPTION		"Total number of times NTS Client connections were rejected 
because of authentication failures since the last time the  
nCIte was reboot."
		::=  {  ntsStats  2  }

	ntsStatCustConnected	OBJECT-TYPE	
		SYNTAX			Counter64
		MAX-ACCESS		read-only
		STATUS			current
		DESCRIPTION		"Number of NTS Clients that are currently connected."
		::=  {  ntsStats  3  }

	edrCurrentCallCount	OBJECT-TYPE	
		SYNTAX			Counter64
		MAX-ACCESS		read-only
		STATUS			current
		DESCRIPTION		"Current number of calls that have been detected as rogue"
		::=  {  rogueStats  1  }

	edrPeakCallCount	OBJECT-TYPE	
		SYNTAX			Counter64
		MAX-ACCESS		read-only
		STATUS			current
		DESCRIPTION		"Peak number of calls that have been declared rogue"
		::=  {  rogueStats  2  }

	edrTotalCallsRogue	OBJECT-TYPE	
		SYNTAX			Counter64
		MAX-ACCESS		read-only
		STATUS			current
		DESCRIPTION		"Total number of calls that have been detected as rogue     
since the last time the nCite was restarted"
		::=  {  rogueStats  3  }

	edrLastDetection	OBJECT-TYPE	
		SYNTAX			DateAndTime
		MAX-ACCESS		read-only
		STATUS			current
		DESCRIPTION		"Date/time of the last time that a call was detected as     
rogue"
		::=  {  rogueStats  4  }

	lrdCurrentCallCount	OBJECT-TYPE	
		SYNTAX			Counter64
		MAX-ACCESS		read-only
		STATUS			current
		DESCRIPTION		"Current number of LRD rogue calls"
		::=  {  rogueStats  5  }

	lrdPeakCallCount	OBJECT-TYPE	
		SYNTAX			Counter64
		MAX-ACCESS		read-only
		STATUS			current
		DESCRIPTION		"Maximum number of active rogue calls since the last time   
the stats were reset"
		::=  {  rogueStats  6  }

	lrdTotalCallsRogue	OBJECT-TYPE	
		SYNTAX			Counter64
		MAX-ACCESS		read-only
		STATUS			current
		DESCRIPTION		"The cumulative number of rogue calls detected since the    
stats were reset"
		::=  {  rogueStats  7  }

	lrdLastDetection	OBJECT-TYPE	
		SYNTAX			DateAndTime
		MAX-ACCESS		read-only
		STATUS			current
		DESCRIPTION		"Date/time that the last LRD rogue call was detected"
		::=  {  rogueStats  8  }

	custNtsStatsTable	OBJECT-TYPE
		SYNTAX		SEQUENCE  OF  CustNtsStatsEntry
		MAX-ACCESS	not-accessible
		STATUS		current
		DESCRIPTION	"NTS Customer statistics table"
		::=  { custNtsStats  1 }

	custNtsStatsEntry	OBJECT-TYPE
		SYNTAX		CustNtsStatsEntry
		MAX-ACCESS	not-accessible
		STATUS		current
		DESCRIPTION	"Row Description"
		INDEX		{  custNtsStatId  }
		::=  { custNtsStatsTable 1 }

	CustNtsStatsEntry  ::=  SEQUENCE {
		custNtsStatId  Integer32,
		custNtsAuthorizationFailed  Counter64
		}


	custNtsStatId	OBJECT-TYPE	
		SYNTAX			Integer32
		MAX-ACCESS		read-only
		STATUS			current
		DESCRIPTION		"Customer location ID"
		::=  {  custNtsStatsEntry  1  }


	custNtsAuthorizationFailed	OBJECT-TYPE	
		SYNTAX			Counter64
		MAX-ACCESS		read-only
		STATUS			current
		DESCRIPTION		"Number of authorizatin failures for NTS customer"
		::=  {  custNtsStatsEntry  2  }

	sipH323CallsInitiating	OBJECT-TYPE	
		SYNTAX			Counter64
		MAX-ACCESS		read-only
		STATUS			current
		DESCRIPTION		"Real-time stat of calls that are being initiated after     
receiving the initial INVITE SIP request."
		::=  {  sipH323Stats  1  }

	sipH323LocalActiveCalls	OBJECT-TYPE	
		SYNTAX			Counter64
		MAX-ACCESS		read-only
		STATUS			current
		DESCRIPTION		"Real-time stat that is the number of active calls that are 
local"
		::=  {  sipH323Stats  2  }

	sipH323TermCalls	OBJECT-TYPE	
		SYNTAX			Counter64
		MAX-ACCESS		read-only
		STATUS			current
		DESCRIPTION		"Real-time stat that is the number of calls in the          
TERMINATING state after a BYE SIP request."
		::=  {  sipH323Stats  3  }

	sipH323PeakTotalActiveCalls	OBJECT-TYPE	
		SYNTAX			Counter64
		MAX-ACCESS		read-only
		STATUS			current
		DESCRIPTION		"Peak number of active calls since the last nCite reboot."
		::=  {  sipH323Stats  4  }

	sipH323TotalActiveCalls	OBJECT-TYPE	
		SYNTAX			Counter64
		MAX-ACCESS		read-only
		STATUS			current
		DESCRIPTION		"Total number of active calls. sipH323LocalActvieCalls +    
sipH323NonLocalActiveCalls"
		::=  {  sipH323Stats  5  }

	sipH323CallsCompletedSuccess	OBJECT-TYPE	
		SYNTAX			Counter64
		MAX-ACCESS		read-only
		STATUS			current
		DESCRIPTION		"Total number of calls that have been completed             
successfully since the last time the nCIte was reboot."
		::=  {  sipH323Stats  6  }

	sipH323CallsFailed	OBJECT-TYPE	
		SYNTAX			Counter64
		MAX-ACCESS		read-only
		STATUS			current
		DESCRIPTION		"Total number of calls that completed due to some failure   
since the last time the nCite was reboot."
		::=  {  sipH323Stats  7  }

	sipH323CallsAbandoned	OBJECT-TYPE	
		SYNTAX			Counter64
		MAX-ACCESS		read-only
		STATUS			current
		DESCRIPTION		"Total number of calls that did not transition to active    
state because of normal termination since the last time the 
nCIte was reboot."
		::=  {  sipH323Stats  8  }

	sipH323CallsDropped	OBJECT-TYPE	
		SYNTAX			Counter64
		MAX-ACCESS		read-only
		STATUS			deprecated
		DESCRIPTION		"Total number of calls that were dropped due to exceeding   
adminision control since the last time the nCite was        
reboot."
		::=  {  sipH323Stats  9  }

	sipH323CallsDegraded	OBJECT-TYPE	
		SYNTAX			Counter64
		MAX-ACCESS		read-only
		STATUS			current
		DESCRIPTION		"Total number of calls that were processed in a degraded    
state due to exceeding admission control since the last     
time the nCIte was reboot."
		::=  {  sipH323Stats  10  }

	sipH323AuthFailures	OBJECT-TYPE	
		SYNTAX			Counter64
		MAX-ACCESS		read-only
		STATUS			current
		DESCRIPTION		"Total number of calls that were rejected because they      
could not be autenticated against a valid customer          
definition since the last time the nCite was reboot."
		::=  {  sipH323Stats  11  }

	sipH323CallMediaTimeouts	OBJECT-TYPE	
		SYNTAX			Counter64
		MAX-ACCESS		read-only
		STATUS			current
		DESCRIPTION		"Total number of times a call was terminated because of a   
RTP media timeout since the last time the nCIte was reboot."
		::=  {  sipH323Stats  12  }

	sipH323CallInitTimeouts	OBJECT-TYPE	
		SYNTAX			Counter64
		MAX-ACCESS		read-only
		STATUS			current
		DESCRIPTION		"Total number of times a SIP timout occurred after the      
receipt of the initial INVITE and before the ACK is         
received for the INVITE since the last time the nCite was   
reboot."
		::=  {  sipH323Stats  13  }

	sipH323TermTimeouts	OBJECT-TYPE	
		SYNTAX			Counter64
		MAX-ACCESS		read-only
		STATUS			current
		DESCRIPTION		"Total number of times a SIP timout occurred after the      
receipt of the BYE and before the ACK is received for the   
BYE since the last time the nCIte was reboot."
		::=  {  sipH323Stats  14  }

	sipH323MsgErrs	OBJECT-TYPE	
		SYNTAX			Counter64
		MAX-ACCESS		read-only
		STATUS			current
		DESCRIPTION		"Total number of times a SIP error message was received     
since the last time the nCite was reboot."
		::=  {  sipH323Stats  15  }

	sipH323CallsProcessed	OBJECT-TYPE	
		SYNTAX			Counter64
		MAX-ACCESS		read-only
		STATUS			current
		DESCRIPTION		"Total number of calls that have been processed since the   
nCIte was last reboot. This iwll be the sum of              
sipH323CallsCompletedSuccess, sipH323CallsFailed,           
sipH323CallsAbandoned, sipH323CallsDropped,                 
sipH323AuthFailures"
		::=  {  sipH323Stats  16  }

	sipH323PeakLocalCalls	OBJECT-TYPE	
		SYNTAX			Counter64
		MAX-ACCESS		read-only
		STATUS			current
		DESCRIPTION		"Real-time statistic that is the peak number of active      
local calls."
		::=  {  sipH323Stats  17  }

	sipH323RedirectSuccess	OBJECT-TYPE	
		SYNTAX			Counter64
		MAX-ACCESS		read-only
		STATUS			deprecated
		DESCRIPTION		"Total number of successful redirects"
		::=  {  sipH323Stats  18  }

	sipH323RedirectFailures	OBJECT-TYPE	
		SYNTAX			Counter64
		MAX-ACCESS		read-only
		STATUS			deprecated
		DESCRIPTION		"Total number of failed redirects"
		::=  {  sipH323Stats  19  }

	sipH323MessageRoutingFailures	OBJECT-TYPE	
		SYNTAX			Counter64
		MAX-ACCESS		read-only
		STATUS			current
		DESCRIPTION		"Failures due to route lookup - no enabled route found"
		::=  {  sipH323Stats  20  }

	sipH323AuthenticationChallenges	OBJECT-TYPE	
		SYNTAX			Counter64
		MAX-ACCESS		read-only
		STATUS			current
		DESCRIPTION		"Number of Authentication Challenges"
		::=  {  sipH323Stats  21  }

	sipH323RTPFWTraversalTimeouts	OBJECT-TYPE	
		SYNTAX			Counter64
		MAX-ACCESS		read-only
		STATUS			current
		DESCRIPTION		"Number of RTP forward traversal timeouts"
		::=  {  sipH323Stats  22  }

	sipH323MessagesReroutedToMate	OBJECT-TYPE	
		SYNTAX			Counter64
		MAX-ACCESS		read-only
		STATUS			deprecated
		DESCRIPTION		"Number of messages rerouted to mate"
		::=  {  sipH323Stats  23  }

	sipH323SameSideActiveCalls	OBJECT-TYPE	
		SYNTAX			Counter64
		MAX-ACCESS		read-only
		STATUS			current
		DESCRIPTION		"Same side actvie calls"
		::=  {  sipH323Stats  24  }

	sipH323NormalActiveCalls	OBJECT-TYPE	
		SYNTAX			Counter64
		MAX-ACCESS		read-only
		STATUS			current
		DESCRIPTION		"Normal active calls"
		::=  {  sipH323Stats  25  }

	sipH323PeakSameSideActiveCalls	OBJECT-TYPE	
		SYNTAX			Counter64
		MAX-ACCESS		read-only
		STATUS			current
		DESCRIPTION		"Peak same side active calls"
		::=  {  sipH323Stats  26  }

	sipH323PeakNormalActiveCalls	OBJECT-TYPE	
		SYNTAX			Counter64
		MAX-ACCESS		read-only
		STATUS			current
		DESCRIPTION		"Peak normal active calls"
		::=  {  sipH323Stats  27  }

	sipH323CurrentFaxSessions	OBJECT-TYPE	
		SYNTAX			Counter64
		MAX-ACCESS		read-only
		STATUS			deprecated
		DESCRIPTION		"Current number of FAX Sessions that are active"
		::=  {  sipH323Stats  28  }

	sipH323PeakFaxSessions	OBJECT-TYPE	
		SYNTAX			Counter64
		MAX-ACCESS		read-only
		STATUS			deprecated
		DESCRIPTION		"Maximum number of FAX sessions active at any point in time 
since the statistics were last reset"
		::=  {  sipH323Stats  29  }

	sipH323TotalFaxSessions	OBJECT-TYPE	
		SYNTAX			Counter64
		MAX-ACCESS		read-only
		STATUS			deprecated
		DESCRIPTION		"The total number of FAX sessions that have occurred since  
the statistics were last reset"
		::=  {  sipH323Stats  30  }

	h323CallsInitiating	OBJECT-TYPE	
		SYNTAX			Counter64
		MAX-ACCESS		read-only
		STATUS			current
		DESCRIPTION		"Real-time stat of calls that are being initiated after     
receiving the initial INVITE SIP request."
		::=  {  h323Stats  1  }

	h323LocalActiveCalls	OBJECT-TYPE	
		SYNTAX			Counter64
		MAX-ACCESS		read-only
		STATUS			current
		DESCRIPTION		"Real-time stat that is the number of active calls that are 
local"
		::=  {  h323Stats  2  }

	h323TermCalls	OBJECT-TYPE	
		SYNTAX			Counter64
		MAX-ACCESS		read-only
		STATUS			current
		DESCRIPTION		"Real-time stat that is the number of calls in the          
TERMINATING state after a BYE SIP request."
		::=  {  h323Stats  3  }

	h323PeakTotalActiveCalls	OBJECT-TYPE	
		SYNTAX			Counter64
		MAX-ACCESS		read-only
		STATUS			current
		DESCRIPTION		"Peak number of active calls since the last nCite reboot."
		::=  {  h323Stats  4  }

	h323TotalActiveCalls	OBJECT-TYPE	
		SYNTAX			Counter64
		MAX-ACCESS		read-only
		STATUS			current
		DESCRIPTION		"Total number of active calls. h323LocalActvieCalls +       
h323NonLocalActiveCalls"
		::=  {  h323Stats  5  }

	h323CallsCompletedSuccess	OBJECT-TYPE	
		SYNTAX			Counter64
		MAX-ACCESS		read-only
		STATUS			current
		DESCRIPTION		"Total number of calls that have been completed             
successfully since the last time the nCIte was reboot."
		::=  {  h323Stats  6  }

	h323CallsFailed	OBJECT-TYPE	
		SYNTAX			Counter64
		MAX-ACCESS		read-only
		STATUS			current
		DESCRIPTION		"Total number of calls that completed due to some failure   
since the last time the nCite was reboot."
		::=  {  h323Stats  7  }

	h323CallsAbandoned	OBJECT-TYPE	
		SYNTAX			Counter64
		MAX-ACCESS		read-only
		STATUS			current
		DESCRIPTION		"Total number of calls that did not transition to active    
state because of normal termination since the last time the 
nCIte was reboot."
		::=  {  h323Stats  8  }

	h323CallsDropped	OBJECT-TYPE	
		SYNTAX			Counter64
		MAX-ACCESS		read-only
		STATUS			deprecated
		DESCRIPTION		"Total number of calls that were dropped due to exceeding   
adminision control since the last time the nCite was        
reboot."
		::=  {  h323Stats  9  }

	h323CallsDegraded	OBJECT-TYPE	
		SYNTAX			Counter64
		MAX-ACCESS		read-only
		STATUS			current
		DESCRIPTION		"Total number of calls that were processed in a degraded    
state due to exceeding admission control since the last     
time the nCIte was reboot."
		::=  {  h323Stats  10  }

	h323AuthFailures	OBJECT-TYPE	
		SYNTAX			Counter64
		MAX-ACCESS		read-only
		STATUS			current
		DESCRIPTION		"Total number of calls that were rejected because they      
could not be autenticated against a valid customer          
definition since the last time the nCite was reboot."
		::=  {  h323Stats  11  }

	h323CallMediaTimeouts	OBJECT-TYPE	
		SYNTAX			Counter64
		MAX-ACCESS		read-only
		STATUS			current
		DESCRIPTION		"Total number of times a call was terminated because of a   
RTP media timeout since the last time the nCIte was reboot."
		::=  {  h323Stats  12  }

	h323CallInitTimeouts	OBJECT-TYPE	
		SYNTAX			Counter64
		MAX-ACCESS		read-only
		STATUS			current
		DESCRIPTION		"Total number of times a SIP timout occurred after the      
receipt of the initial INVITE and before the ACK is         
received for the INVITE since the last time the nCite was   
reboot."
		::=  {  h323Stats  13  }

	h323TermTimeouts	OBJECT-TYPE	
		SYNTAX			Counter64
		MAX-ACCESS		read-only
		STATUS			current
		DESCRIPTION		"Total number of times a SIP timout occurred after the      
receipt of the BYE and before the ACK is received for the   
BYE since the last time the nCIte was reboot."
		::=  {  h323Stats  14  }

	h323MsgErrs	OBJECT-TYPE	
		SYNTAX			Counter64
		MAX-ACCESS		read-only
		STATUS			current
		DESCRIPTION		"Total number of times a SIP error message was received     
since the last time the nCite was reboot."
		::=  {  h323Stats  15  }

	h323CallsProcessed	OBJECT-TYPE	
		SYNTAX			Counter64
		MAX-ACCESS		read-only
		STATUS			current
		DESCRIPTION		"Total number of calls that have been processed since the   
nCIte was last reboot. This iwll be the sum of              
h323CallsCompletedSuccess, h323CallsFailed,                 
h323CallsAbandoned, h323CallsDropped,                       
h323AuthFailures"
		::=  {  h323Stats  16  }

	h323PeakLocalCalls	OBJECT-TYPE	
		SYNTAX			Counter64
		MAX-ACCESS		read-only
		STATUS			current
		DESCRIPTION		"Real-time statistic that is the peak number of active      
local calls."
		::=  {  h323Stats  17  }

	h323MessageRoutingFailures	OBJECT-TYPE	
		SYNTAX			Counter64
		MAX-ACCESS		read-only
		STATUS			current
		DESCRIPTION		"Failures due to route lookup - no enabled route found"
		::=  {  h323Stats  18  }

	h323AuthenticationChallenges	OBJECT-TYPE	
		SYNTAX			Counter64
		MAX-ACCESS		read-only
		STATUS			current
		DESCRIPTION		"Number of Authentication Challenges"
		::=  {  h323Stats  19  }

	h323RTPFWTraversalTimeouts	OBJECT-TYPE	
		SYNTAX			Counter64
		MAX-ACCESS		read-only
		STATUS			current
		DESCRIPTION		"Number of RTP forward traversal timeouts"
		::=  {  h323Stats  20  }

	h323SameSideActiveCalls	OBJECT-TYPE	
		SYNTAX			Counter64
		MAX-ACCESS		read-only
		STATUS			current
		DESCRIPTION		"Same side actvie calls"
		::=  {  h323Stats  21  }

	h323NormalActiveCalls	OBJECT-TYPE	
		SYNTAX			Counter64
		MAX-ACCESS		read-only
		STATUS			current
		DESCRIPTION		"Normal active calls"
		::=  {  h323Stats  22  }

	h323PeakSameSideActiveCalls	OBJECT-TYPE	
		SYNTAX			Counter64
		MAX-ACCESS		read-only
		STATUS			current
		DESCRIPTION		"Peak same side active calls"
		::=  {  h323Stats  23  }

	h323PeakNormalActiveCalls	OBJECT-TYPE	
		SYNTAX			Counter64
		MAX-ACCESS		read-only
		STATUS			current
		DESCRIPTION		"Peak normal active calls"
		::=  {  h323Stats  24  }

	h323CurrentFaxSessions	OBJECT-TYPE	
		SYNTAX			Counter64
		MAX-ACCESS		read-only
		STATUS			deprecated
		DESCRIPTION		"Current number of FAX Sessions that are active"
		::=  {  h323Stats  25  }

	h323PeakFaxSessions	OBJECT-TYPE	
		SYNTAX			Counter64
		MAX-ACCESS		read-only
		STATUS			deprecated
		DESCRIPTION		"Maximum number of FAX sessions active at any point in time 
since the statistics were last reset"
		::=  {  h323Stats  26  }

	h323TotalFaxSessions	OBJECT-TYPE	
		SYNTAX			Counter64
		MAX-ACCESS		read-only
		STATUS			deprecated
		DESCRIPTION		"The total number of FAX sessions that have occurred since  
the statistics were last reset"
		::=  {  h323Stats  27  }

	voIpCallsInitiating	OBJECT-TYPE	
		SYNTAX			Counter64
		MAX-ACCESS		read-only
		STATUS			current
		DESCRIPTION		"Real-time stat of calls that are being initiated after     
receiving the initial INVITE SIP request."
		::=  {  voIpStats  1  }

	voIpLocalActiveCalls	OBJECT-TYPE	
		SYNTAX			Counter64
		MAX-ACCESS		read-only
		STATUS			current
		DESCRIPTION		"Real-time stat that is the number of active calls that are 
local"
		::=  {  voIpStats  2  }

	voIpTermCalls	OBJECT-TYPE	
		SYNTAX			Counter64
		MAX-ACCESS		read-only
		STATUS			current
		DESCRIPTION		"Real-time stat that is the number of calls in the          
TERMINATING state after a BYE SIP request."
		::=  {  voIpStats  3  }

	voIpPeakTotalActiveCalls	OBJECT-TYPE	
		SYNTAX			Counter64
		MAX-ACCESS		read-only
		STATUS			current
		DESCRIPTION		"Peak number of active calls since the last nCite reboot."
		::=  {  voIpStats  4  }

	voIpTotalActiveCalls	OBJECT-TYPE	
		SYNTAX			Counter64
		MAX-ACCESS		read-only
		STATUS			current
		DESCRIPTION		"Total number of active calls. voIpLocalActvieCalls +       
voIpNonLocalActiveCalls"
		::=  {  voIpStats  5  }

	voIpCallsCompletedSuccess	OBJECT-TYPE	
		SYNTAX			Counter64
		MAX-ACCESS		read-only
		STATUS			current
		DESCRIPTION		"Total number of calls that have been completed             
successfully since the last time the nCIte was reboot."
		::=  {  voIpStats  6  }

	voIpCallsFailed	OBJECT-TYPE	
		SYNTAX			Counter64
		MAX-ACCESS		read-only
		STATUS			current
		DESCRIPTION		"Total number of calls that completed due to some failure   
since the last time the nCite was reboot."
		::=  {  voIpStats  7  }

	voIpCallsAbandoned	OBJECT-TYPE	
		SYNTAX			Counter64
		MAX-ACCESS		read-only
		STATUS			current
		DESCRIPTION		"Total number of calls that did not transition to active    
state because of normal termination since the last time the 
nCIte was reboot."
		::=  {  voIpStats  8  }

	voIpCallsDropped	OBJECT-TYPE	
		SYNTAX			Counter64
		MAX-ACCESS		read-only
		STATUS			deprecated
		DESCRIPTION		"Total number of calls that were dropped due to exceeding   
adminision control since the last time the nCite was        
reboot."
		::=  {  voIpStats  9  }

	voIpCallsDegraded	OBJECT-TYPE	
		SYNTAX			Counter64
		MAX-ACCESS		read-only
		STATUS			current
		DESCRIPTION		"Total number of calls that were processed in a degraded    
state due to exceeding admission control since the last     
time the nCIte was reboot."
		::=  {  voIpStats  10  }

	voIpAuthFailures	OBJECT-TYPE	
		SYNTAX			Counter64
		MAX-ACCESS		read-only
		STATUS			current
		DESCRIPTION		"Total number of calls that were rejected because they      
could not be autenticated against a valid customer          
definition since the last time the nCite was reboot."
		::=  {  voIpStats  11  }

	voIpCallMediaTimeouts	OBJECT-TYPE	
		SYNTAX			Counter64
		MAX-ACCESS		read-only
		STATUS			current
		DESCRIPTION		"Total number of times a call was terminated because of a   
RTP media timeout since the last time the nCIte was reboot."
		::=  {  voIpStats  12  }

	voIpCallInitTimeouts	OBJECT-TYPE	
		SYNTAX			Counter64
		MAX-ACCESS		read-only
		STATUS			current
		DESCRIPTION		"Total number of times a SIP timout occurred after the      
receipt of the initial INVITE and before the ACK is         
received for the INVITE since the last time the nCite was   
reboot."
		::=  {  voIpStats  13  }

	voIpTermTimeouts	OBJECT-TYPE	
		SYNTAX			Counter64
		MAX-ACCESS		read-only
		STATUS			current
		DESCRIPTION		"Total number of times a SIP timout occurred after the      
receipt of the BYE and before the ACK is received for the   
BYE since the last time the nCIte was reboot."
		::=  {  voIpStats  14  }

	voIpMsgErrs	OBJECT-TYPE	
		SYNTAX			Counter64
		MAX-ACCESS		read-only
		STATUS			current
		DESCRIPTION		"Total number of times a SIP error message was received     
since the last time the nCite was reboot."
		::=  {  voIpStats  15  }

	voIpCallsProcessed	OBJECT-TYPE	
		SYNTAX			Counter64
		MAX-ACCESS		read-only
		STATUS			current
		DESCRIPTION		"Total number of calls that have been processed since the   
nCIte was last reboot. This iwll be the sum of              
voIpCallsCompletedSuccess, voIpCallsFailed,                 
voIpCallsAbandoned, voIpCallsDropped,                       
voIpAuthFailures"
		::=  {  voIpStats  16  }

	voIpPeakLocalCalls	OBJECT-TYPE	
		SYNTAX			Counter64
		MAX-ACCESS		read-only
		STATUS			current
		DESCRIPTION		"Real-time statistic that is the peak number of active      
local calls."
		::=  {  voIpStats  17  }

	voIpRedirectSuccess	OBJECT-TYPE	
		SYNTAX			Counter64
		MAX-ACCESS		read-only
		STATUS			deprecated
		DESCRIPTION		"Total number of successful redirects"
		::=  {  voIpStats  18  }

	voIpRedirectFailures	OBJECT-TYPE	
		SYNTAX			Counter64
		MAX-ACCESS		read-only
		STATUS			deprecated
		DESCRIPTION		"Total number of failed redirects"
		::=  {  voIpStats  19  }

	voIpMessageRoutingFailures	OBJECT-TYPE	
		SYNTAX			Counter64
		MAX-ACCESS		read-only
		STATUS			current
		DESCRIPTION		"Failures due to route lookup - no enabled route found"
		::=  {  voIpStats  20  }

	voIpAuthenticationChallenges	OBJECT-TYPE	
		SYNTAX			Counter64
		MAX-ACCESS		read-only
		STATUS			current
		DESCRIPTION		"Number of Authentication Challenges"
		::=  {  voIpStats  21  }

	voIpRTPFWTraversalTimeouts	OBJECT-TYPE	
		SYNTAX			Counter64
		MAX-ACCESS		read-only
		STATUS			current
		DESCRIPTION		"Number of RTP forward traversal timeouts"
		::=  {  voIpStats  22  }

	voIpMessagesReroutedToMate	OBJECT-TYPE	
		SYNTAX			Counter64
		MAX-ACCESS		read-only
		STATUS			deprecated
		DESCRIPTION		"Number of messages rerouted to mate"
		::=  {  voIpStats  23  }

	voIpSameSideActiveCalls	OBJECT-TYPE	
		SYNTAX			Counter64
		MAX-ACCESS		read-only
		STATUS			current
		DESCRIPTION		"Same side actvie calls"
		::=  {  voIpStats  24  }

	voIpNormalActiveCalls	OBJECT-TYPE	
		SYNTAX			Counter64
		MAX-ACCESS		read-only
		STATUS			current
		DESCRIPTION		"Normal active calls"
		::=  {  voIpStats  25  }

	voIpPeakSameSideActiveCalls	OBJECT-TYPE	
		SYNTAX			Counter64
		MAX-ACCESS		read-only
		STATUS			current
		DESCRIPTION		"Peak same side active calls"
		::=  {  voIpStats  26  }

	voIpPeakNormalActiveCalls	OBJECT-TYPE	
		SYNTAX			Counter64
		MAX-ACCESS		read-only
		STATUS			current
		DESCRIPTION		"Peak normal active calls"
		::=  {  voIpStats  27  }

	voIpCurrentFaxSessions	OBJECT-TYPE	
		SYNTAX			Counter64
		MAX-ACCESS		read-only
		STATUS			deprecated
		DESCRIPTION		"Current number of FAX Sessions that are active"
		::=  {  voIpStats  28  }

	voIpPeakFaxSessions	OBJECT-TYPE	
		SYNTAX			Counter64
		MAX-ACCESS		read-only
		STATUS			deprecated
		DESCRIPTION		"Maximum number of FAX sessions active at any point in time 
since the statistics were last reset"
		::=  {  voIpStats  29  }

	voIpTotalFaxSessions	OBJECT-TYPE	
		SYNTAX			Counter64
		MAX-ACCESS		read-only
		STATUS			deprecated
		DESCRIPTION		"The total number of FAX sessions that have occurred since  
the statistics were last reset"
		::=  {  voIpStats  30  }

	custSipH323StatsTable	OBJECT-TYPE
		SYNTAX		SEQUENCE  OF  CustSipH323StatsEntry
		MAX-ACCESS	not-accessible
		STATUS		current
		DESCRIPTION	"Description"
		::=  { custSipH323Stats  1 }

	custSipH323StatsEntry	OBJECT-TYPE
		SYNTAX		CustSipH323StatsEntry
		MAX-ACCESS	not-accessible
		STATUS		current
		DESCRIPTION	"Row Description"
		INDEX		{  custSipH323Id  }
		::=  { custSipH323StatsTable 1 }

	CustSipH323StatsEntry  ::=  SEQUENCE {
		custSipH323Id  Integer32,
		custSipH323CallsInitiating  Counter64,
		custSipH323LocalActiveCalls  Counter64,
		custSipH323TermCalls  Counter64,
		custSipH323PeakTotalActiveCalls  Counter64,
		custSipH323TotalActiveCalls  Counter64,
		custSipH323CallsCompletedSuccess  Counter64,
		custSipH323CallsFailed  Counter64,
		custSipH323CallsAbandoned  Counter64,
		custSipH323CallsDropped  Counter64,
		custSipH323CallsDegraded  Counter64,
		custSipH323CallMediaTimeouts  Counter64,
		custSipH323CallInitTimeouts  Counter64,
		custSipH323TermTimeouts  Counter64,
		custSipH323CallsProcessed  Counter64,
		custSipH323PeakLocalCalls  Counter64,
		custSipH323AuthenticationChallenges  Counter64,
		custSipH323RTPFWTraversalTimeouts  Counter64,
		custSipH323SameSideActiveCalls  Counter64,
		custSipH323NormalActiveCalls  Counter64,
		custSipH323PeakNormalActiveCalls  Counter64
		}


	custSipH323Id	OBJECT-TYPE	
		SYNTAX			Integer32
		MAX-ACCESS		read-only
		STATUS			current
		DESCRIPTION		"Customer ID as it is defined in the EMS database and the   
XML file provisioned to the nCIte"
		::=  {  custSipH323StatsEntry  1  }


	custSipH323CallsInitiating	OBJECT-TYPE	
		SYNTAX			Counter64
		MAX-ACCESS		read-only
		STATUS			current
		DESCRIPTION		"Real-time stat of calls that are being initiated after     
receiving the initial INVITE SIP request."
		::=  {  custSipH323StatsEntry  2  }


	custSipH323LocalActiveCalls	OBJECT-TYPE	
		SYNTAX			Counter64
		MAX-ACCESS		read-only
		STATUS			current
		DESCRIPTION		"Real-time stat that is the number of active calls that are 
local"
		::=  {  custSipH323StatsEntry  3  }


	custSipH323TermCalls	OBJECT-TYPE	
		SYNTAX			Counter64
		MAX-ACCESS		read-only
		STATUS			current
		DESCRIPTION		"Real-time stat that is the number of calls in the          
TERMINATING state after a BYE SIP request."
		::=  {  custSipH323StatsEntry  4  }


	custSipH323PeakTotalActiveCalls	OBJECT-TYPE	
		SYNTAX			Counter64
		MAX-ACCESS		read-only
		STATUS			current
		DESCRIPTION		"Peak number of total active calls since the last nCite     
reboot."
		::=  {  custSipH323StatsEntry  5  }


	custSipH323TotalActiveCalls	OBJECT-TYPE	
		SYNTAX			Counter64
		MAX-ACCESS		read-only
		STATUS			current
		DESCRIPTION		"Total number of active calls.        
custSipH323StatLocalActvieCalls   +         
custSipH323StatNonLocalActiveCalls"
		::=  {  custSipH323StatsEntry  6  }


	custSipH323CallsCompletedSuccess	OBJECT-TYPE	
		SYNTAX			Counter64
		MAX-ACCESS		read-only
		STATUS			current
		DESCRIPTION		"Total number of calls that have been completed             
successfully since the last time the nCIte was reboot."
		::=  {  custSipH323StatsEntry  7  }


	custSipH323CallsFailed	OBJECT-TYPE	
		SYNTAX			Counter64
		MAX-ACCESS		read-only
		STATUS			current
		DESCRIPTION		"Total number of calls that completed due to some failure   
since the last time the nCite was reboot."
		::=  {  custSipH323StatsEntry  8  }


	custSipH323CallsAbandoned	OBJECT-TYPE	
		SYNTAX			Counter64
		MAX-ACCESS		read-only
		STATUS			current
		DESCRIPTION		"Total number of calls that did not transition to active    
state because of normal termination since the last time the 
nCIte was reboot."
		::=  {  custSipH323StatsEntry  9  }


	custSipH323CallsDropped	OBJECT-TYPE	
		SYNTAX			Counter64
		MAX-ACCESS		read-only
		STATUS			deprecated
		DESCRIPTION		"Total number of calls that were dropped due to exceeding   
adminision control since the last time the nCite was        
reboot."
		::=  {  custSipH323StatsEntry  10  }


	custSipH323CallsDegraded	OBJECT-TYPE	
		SYNTAX			Counter64
		MAX-ACCESS		read-only
		STATUS			current
		DESCRIPTION		"Total number of calls that were processed in a degraded    
state due to exceeding admission control since the last     
time the nCIte was reboot."
		::=  {  custSipH323StatsEntry  11  }


	custSipH323CallMediaTimeouts	OBJECT-TYPE	
		SYNTAX			Counter64
		MAX-ACCESS		read-only
		STATUS			current
		DESCRIPTION		"Total number of times a call was terminated because of a   
RTP media timeout since the last time the nCIte was reboot."
		::=  {  custSipH323StatsEntry  12  }


	custSipH323CallInitTimeouts	OBJECT-TYPE	
		SYNTAX			Counter64
		MAX-ACCESS		read-only
		STATUS			current
		DESCRIPTION		"Total number of times a SIP timout occurred after the      
receipt of the initial INVITE and before the ACK is         
received for the INVITE since the last time the nCite was   
reboot."
		::=  {  custSipH323StatsEntry  13  }


	custSipH323TermTimeouts	OBJECT-TYPE	
		SYNTAX			Counter64
		MAX-ACCESS		read-only
		STATUS			current
		DESCRIPTION		"Total number of times a SIP timout occurred after the      
receipt of the BYE and before the ACK is received for the   
BYE since the last time the nCIte was reboot."
		::=  {  custSipH323StatsEntry  14  }


	custSipH323CallsProcessed	OBJECT-TYPE	
		SYNTAX			Counter64
		MAX-ACCESS		read-only
		STATUS			current
		DESCRIPTION		"Total number of calls that have been processed since the   
nCIte was last reboot. This will be the sum of              
custSipH323CallsCompletedSuccess, custSipH323CallsFailed,   
custSipH323CallsAbandoned, custSipH323CallsDropped,         
custSipH323AuthFailures"
		::=  {  custSipH323StatsEntry  15  }


	custSipH323PeakLocalCalls	OBJECT-TYPE	
		SYNTAX			Counter64
		MAX-ACCESS		read-only
		STATUS			current
		DESCRIPTION		"Peak number of local calls"
		::=  {  custSipH323StatsEntry  16  }


	custSipH323AuthenticationChallenges	OBJECT-TYPE	
		SYNTAX			Counter64
		MAX-ACCESS		read-only
		STATUS			current
		DESCRIPTION		"Number of authentication challanges"
		::=  {  custSipH323StatsEntry  17  }


	custSipH323RTPFWTraversalTimeouts	OBJECT-TYPE	
		SYNTAX			Counter64
		MAX-ACCESS		read-only
		STATUS			current
		DESCRIPTION		"Number of RTP forward traversal timeouts"
		::=  {  custSipH323StatsEntry  18  }


	custSipH323SameSideActiveCalls	OBJECT-TYPE	
		SYNTAX			Counter64
		MAX-ACCESS		read-only
		STATUS			current
		DESCRIPTION		"Number of same side active calls"
		::=  {  custSipH323StatsEntry  19  }


	custSipH323NormalActiveCalls	OBJECT-TYPE	
		SYNTAX			Counter64
		MAX-ACCESS		read-only
		STATUS			current
		DESCRIPTION		"Number of normal active calls"
		::=  {  custSipH323StatsEntry  20  }


	custSipH323PeakNormalActiveCalls	OBJECT-TYPE	
		SYNTAX			Counter64
		MAX-ACCESS		read-only
		STATUS			current
		DESCRIPTION		"Maximum number of active normal calls since the statistics 
were last reset."
		::=  {  custSipH323StatsEntry  21  }

	custH323StatsTable	OBJECT-TYPE
		SYNTAX		SEQUENCE  OF  CustH323StatsEntry
		MAX-ACCESS	not-accessible
		STATUS		current
		DESCRIPTION	"Description"
		::=  { custH323Stats  1 }

	custH323StatsEntry	OBJECT-TYPE
		SYNTAX		CustH323StatsEntry
		MAX-ACCESS	not-accessible
		STATUS		current
		DESCRIPTION	"Row Description"
		INDEX		{  custH323Id  }
		::=  { custH323StatsTable 1 }

	CustH323StatsEntry  ::=  SEQUENCE {
		custH323Id  Integer32,
		custH323CallsInitiating  Counter64,
		custH323LocalActiveCalls  Counter64,
		custH323TermCalls  Counter64,
		custH323PeakTotalActiveCalls  Counter64,
		custH323TotalActiveCalls  Counter64,
		custH323CallsCompletedSuccess  Counter64,
		custH323CallsFailed  Counter64,
		custH323CallsAbandoned  Counter64,
		custH323CallsDropped  Counter64,
		custH323CallsDegraded  Counter64,
		custH323CallMediaTimeouts  Counter64,
		custH323CallInitTimeouts  Counter64,
		custH323TermTimeouts  Counter64,
		custH323CallsProcessed  Counter64,
		custH323PeakLocalCalls  Counter64,
		custH323AuthenticationChallenges  Counter64,
		custH323RTPFWTraversalTimeouts  Counter64,
		custH323SameSideActiveCalls  Counter64,
		custH323NormalActiveCalls  Counter64,
		custH323PeakNormalActiveCalls  Counter64
		}


	custH323Id	OBJECT-TYPE	
		SYNTAX			Integer32
		MAX-ACCESS		read-only
		STATUS			current
		DESCRIPTION		"Customer ID as it is defined in the EMS database and the   
XML file provisioned to the nCIte"
		::=  {  custH323StatsEntry  1  }


	custH323CallsInitiating	OBJECT-TYPE	
		SYNTAX			Counter64
		MAX-ACCESS		read-only
		STATUS			current
		DESCRIPTION		"Real-time stat of calls that are being initiated after     
receiving the initial INVITE SIP request."
		::=  {  custH323StatsEntry  2  }


	custH323LocalActiveCalls	OBJECT-TYPE	
		SYNTAX			Counter64
		MAX-ACCESS		read-only
		STATUS			current
		DESCRIPTION		"Real-time stat that is the number of active calls that are 
local"
		::=  {  custH323StatsEntry  3  }


	custH323TermCalls	OBJECT-TYPE	
		SYNTAX			Counter64
		MAX-ACCESS		read-only
		STATUS			current
		DESCRIPTION		"Real-time stat that is the number of calls in the          
TERMINATING state after a BYE SIP request."
		::=  {  custH323StatsEntry  4  }


	custH323PeakTotalActiveCalls	OBJECT-TYPE	
		SYNTAX			Counter64
		MAX-ACCESS		read-only
		STATUS			current
		DESCRIPTION		"Peak number of total active calls since the last nCite     
reboot."
		::=  {  custH323StatsEntry  5  }


	custH323TotalActiveCalls	OBJECT-TYPE	
		SYNTAX			Counter64
		MAX-ACCESS		read-only
		STATUS			current
		DESCRIPTION		"Total number of active calls.        
custH323StatLocalActvieCalls   +         
custH323StatNonLocalActiveCalls"
		::=  {  custH323StatsEntry  6  }


	custH323CallsCompletedSuccess	OBJECT-TYPE	
		SYNTAX			Counter64
		MAX-ACCESS		read-only
		STATUS			current
		DESCRIPTION		"Total number of calls that have been completed             
successfully since the last time the nCIte was reboot."
		::=  {  custH323StatsEntry  7  }


	custH323CallsFailed	OBJECT-TYPE	
		SYNTAX			Counter64
		MAX-ACCESS		read-only
		STATUS			current
		DESCRIPTION		"Total number of calls that completed due to some failure   
since the last time the nCite was reboot."
		::=  {  custH323StatsEntry  8  }


	custH323CallsAbandoned	OBJECT-TYPE	
		SYNTAX			Counter64
		MAX-ACCESS		read-only
		STATUS			current
		DESCRIPTION		"Total number of calls that did not transition to active    
state because of normal termination since the last time the 
nCIte was reboot."
		::=  {  custH323StatsEntry  9  }


	custH323CallsDropped	OBJECT-TYPE	
		SYNTAX			Counter64
		MAX-ACCESS		read-only
		STATUS			deprecated
		DESCRIPTION		"Total number of calls that were dropped due to exceeding   
adminision control since the last time the nCite was        
reboot."
		::=  {  custH323StatsEntry  10  }


	custH323CallsDegraded	OBJECT-TYPE	
		SYNTAX			Counter64
		MAX-ACCESS		read-only
		STATUS			current
		DESCRIPTION		"Total number of calls that were processed in a degraded    
state due to exceeding admission control since the last     
time the nCIte was reboot."
		::=  {  custH323StatsEntry  11  }


	custH323CallMediaTimeouts	OBJECT-TYPE	
		SYNTAX			Counter64
		MAX-ACCESS		read-only
		STATUS			current
		DESCRIPTION		"Total number of times a call was terminated because of a   
RTP media timeout since the last time the nCIte was reboot."
		::=  {  custH323StatsEntry  12  }


	custH323CallInitTimeouts	OBJECT-TYPE	
		SYNTAX			Counter64
		MAX-ACCESS		read-only
		STATUS			current
		DESCRIPTION		"Total number of times a SIP timout occurred after the      
receipt of the initial INVITE and before the ACK is         
received for the INVITE since the last time the nCite was   
reboot."
		::=  {  custH323StatsEntry  13  }


	custH323TermTimeouts	OBJECT-TYPE	
		SYNTAX			Counter64
		MAX-ACCESS		read-only
		STATUS			current
		DESCRIPTION		"Total number of times a SIP timout occurred after the      
receipt of the BYE and before the ACK is received for the   
BYE since the last time the nCIte was reboot."
		::=  {  custH323StatsEntry  14  }


	custH323CallsProcessed	OBJECT-TYPE	
		SYNTAX			Counter64
		MAX-ACCESS		read-only
		STATUS			current
		DESCRIPTION		"Total number of calls that have been processed since the   
nCIte was last reboot. This will be the sum of              
custH323CallsCompletedSuccess, custH323CallsFailed,         
custH323CallsAbandoned, custH323CallsDropped,               
custH323AuthFailures"
		::=  {  custH323StatsEntry  15  }


	custH323PeakLocalCalls	OBJECT-TYPE	
		SYNTAX			Counter64
		MAX-ACCESS		read-only
		STATUS			current
		DESCRIPTION		"Peak number of local calls"
		::=  {  custH323StatsEntry  16  }


	custH323AuthenticationChallenges	OBJECT-TYPE	
		SYNTAX			Counter64
		MAX-ACCESS		read-only
		STATUS			current
		DESCRIPTION		"Number of authentication challanges"
		::=  {  custH323StatsEntry  17  }


	custH323RTPFWTraversalTimeouts	OBJECT-TYPE	
		SYNTAX			Counter64
		MAX-ACCESS		read-only
		STATUS			current
		DESCRIPTION		"Number of RTP forward traversal timeouts"
		::=  {  custH323StatsEntry  18  }


	custH323SameSideActiveCalls	OBJECT-TYPE	
		SYNTAX			Counter64
		MAX-ACCESS		read-only
		STATUS			current
		DESCRIPTION		"Number of same side active calls"
		::=  {  custH323StatsEntry  19  }


	custH323NormalActiveCalls	OBJECT-TYPE	
		SYNTAX			Counter64
		MAX-ACCESS		read-only
		STATUS			current
		DESCRIPTION		"Number of normal active calls"
		::=  {  custH323StatsEntry  20  }


	custH323PeakNormalActiveCalls	OBJECT-TYPE	
		SYNTAX			Counter64
		MAX-ACCESS		read-only
		STATUS			current
		DESCRIPTION		"Maximum number of active normal calls since the statistics 
were last reset."
		::=  {  custH323StatsEntry  21  }

	custVoIpStatsTable	OBJECT-TYPE
		SYNTAX		SEQUENCE  OF  CustVoIpStatsEntry
		MAX-ACCESS	not-accessible
		STATUS		current
		DESCRIPTION	"Description"
		::=  { custVoIpStats  1 }

	custVoIpStatsEntry	OBJECT-TYPE
		SYNTAX		CustVoIpStatsEntry
		MAX-ACCESS	not-accessible
		STATUS		current
		DESCRIPTION	"Row Description"
		INDEX		{  custVoIpId  }
		::=  { custVoIpStatsTable 1 }

	CustVoIpStatsEntry  ::=  SEQUENCE {
		custVoIpId  Integer32,
		custVoIpCallsInitiating  Counter64,
		custVoIpLocalActiveCalls  Counter64,
		custVoIpTermCalls  Counter64,
		custVoIpPeakTotalActiveCalls  Counter64,
		custVoIpTotalActiveCalls  Counter64,
		custVoIpCallsCompletedSuccess  Counter64,
		custVoIpCallsFailed  Counter64,
		custVoIpCallsAbandoned  Counter64,
		custVoIpCallsDropped  Counter64,
		custVoIpCallsDegraded  Counter64,
		custVoIpCallMediaTimeouts  Counter64,
		custVoIpCallInitTimeouts  Counter64,
		custVoIpTermTimeouts  Counter64,
		custVoIpCallsProcessed  Counter64,
		custVoIpPeakLocalCalls  Counter64,
		custVoIpAuthenticationChallenges  Counter64,
		custVoIpRTPFWTraversalTimeouts  Counter64,
		custVoIpSameSideActiveCalls  Counter64,
		custVoIpNormalActiveCalls  Counter64,
		custVoIpPeakNormalActiveCalls  Counter64
		}


	custVoIpId	OBJECT-TYPE	
		SYNTAX			Integer32
		MAX-ACCESS		read-only
		STATUS			current
		DESCRIPTION		"Customer ID as it is defined in the EMS database and the   
XML file provisioned to the nCIte"
		::=  {  custVoIpStatsEntry  1  }


	custVoIpCallsInitiating	OBJECT-TYPE	
		SYNTAX			Counter64
		MAX-ACCESS		read-only
		STATUS			current
		DESCRIPTION		"Real-time stat of calls that are being initiated after     
receiving the initial INVITE SIP request."
		::=  {  custVoIpStatsEntry  2  }


	custVoIpLocalActiveCalls	OBJECT-TYPE	
		SYNTAX			Counter64
		MAX-ACCESS		read-only
		STATUS			current
		DESCRIPTION		"Real-time stat that is the number of active calls that are 
local"
		::=  {  custVoIpStatsEntry  3  }


	custVoIpTermCalls	OBJECT-TYPE	
		SYNTAX			Counter64
		MAX-ACCESS		read-only
		STATUS			current
		DESCRIPTION		"Real-time stat that is the number of calls in the          
TERMINATING state after a BYE SIP request."
		::=  {  custVoIpStatsEntry  4  }


	custVoIpPeakTotalActiveCalls	OBJECT-TYPE	
		SYNTAX			Counter64
		MAX-ACCESS		read-only
		STATUS			current
		DESCRIPTION		"Peak number of total active calls since the last nCite     
reboot."
		::=  {  custVoIpStatsEntry  5  }


	custVoIpTotalActiveCalls	OBJECT-TYPE	
		SYNTAX			Counter64
		MAX-ACCESS		read-only
		STATUS			current
		DESCRIPTION		"Total number of active calls.        
custVoIpStatLocalActvieCalls   +         
custVoIpStatNonLocalActiveCalls"
		::=  {  custVoIpStatsEntry  6  }


	custVoIpCallsCompletedSuccess	OBJECT-TYPE	
		SYNTAX			Counter64
		MAX-ACCESS		read-only
		STATUS			current
		DESCRIPTION		"Total number of calls that have been completed             
successfully since the last time the nCIte was reboot."
		::=  {  custVoIpStatsEntry  7  }


	custVoIpCallsFailed	OBJECT-TYPE	
		SYNTAX			Counter64
		MAX-ACCESS		read-only
		STATUS			current
		DESCRIPTION		"Total number of calls that completed due to some failure   
since the last time the nCite was reboot."
		::=  {  custVoIpStatsEntry  8  }


	custVoIpCallsAbandoned	OBJECT-TYPE	
		SYNTAX			Counter64
		MAX-ACCESS		read-only
		STATUS			current
		DESCRIPTION		"Total number of calls that did not transition to active    
state because of normal termination since the last time the 
nCIte was reboot."
		::=  {  custVoIpStatsEntry  9  }


	custVoIpCallsDropped	OBJECT-TYPE	
		SYNTAX			Counter64
		MAX-ACCESS		read-only
		STATUS			deprecated
		DESCRIPTION		"Total number of calls that were dropped due to exceeding   
adminision control since the last time the nCite was        
reboot."
		::=  {  custVoIpStatsEntry  10  }


	custVoIpCallsDegraded	OBJECT-TYPE	
		SYNTAX			Counter64
		MAX-ACCESS		read-only
		STATUS			current
		DESCRIPTION		"Total number of calls that were processed in a degraded    
state due to exceeding admission control since the last     
time the nCIte was reboot."
		::=  {  custVoIpStatsEntry  11  }


	custVoIpCallMediaTimeouts	OBJECT-TYPE	
		SYNTAX			Counter64
		MAX-ACCESS		read-only
		STATUS			current
		DESCRIPTION		"Total number of times a call was terminated because of a   
RTP media timeout since the last time the nCIte was reboot."
		::=  {  custVoIpStatsEntry  12  }


	custVoIpCallInitTimeouts	OBJECT-TYPE	
		SYNTAX			Counter64
		MAX-ACCESS		read-only
		STATUS			current
		DESCRIPTION		"Total number of times a SIP timout occurred after the      
receipt of the initial INVITE and before the ACK is         
received for the INVITE since the last time the nCite was   
reboot."
		::=  {  custVoIpStatsEntry  13  }


	custVoIpTermTimeouts	OBJECT-TYPE	
		SYNTAX			Counter64
		MAX-ACCESS		read-only
		STATUS			current
		DESCRIPTION		"Total number of times a SIP timout occurred after the      
receipt of the BYE and before the ACK is received for the   
BYE since the last time the nCIte was reboot."
		::=  {  custVoIpStatsEntry  14  }


	custVoIpCallsProcessed	OBJECT-TYPE	
		SYNTAX			Counter64
		MAX-ACCESS		read-only
		STATUS			current
		DESCRIPTION		"Total number of calls that have been processed since the   
nCIte was last reboot. This will be the sum of              
custVoIpCallsCompletedSuccess, custVoIpCallsFailed,         
custVoIpCallsAbandoned, custVoIpCallsDropped,               
custVoIpAuthFailures"
		::=  {  custVoIpStatsEntry  15  }


	custVoIpPeakLocalCalls	OBJECT-TYPE	
		SYNTAX			Counter64
		MAX-ACCESS		read-only
		STATUS			current
		DESCRIPTION		"Peak number of local calls"
		::=  {  custVoIpStatsEntry  16  }


	custVoIpAuthenticationChallenges	OBJECT-TYPE	
		SYNTAX			Counter64
		MAX-ACCESS		read-only
		STATUS			current
		DESCRIPTION		"Number of authentication challanges"
		::=  {  custVoIpStatsEntry  17  }


	custVoIpRTPFWTraversalTimeouts	OBJECT-TYPE	
		SYNTAX			Counter64
		MAX-ACCESS		read-only
		STATUS			current
		DESCRIPTION		"Number of RTP forward traversal timeouts"
		::=  {  custVoIpStatsEntry  18  }


	custVoIpSameSideActiveCalls	OBJECT-TYPE	
		SYNTAX			Counter64
		MAX-ACCESS		read-only
		STATUS			current
		DESCRIPTION		"Number of same side active calls"
		::=  {  custVoIpStatsEntry  19  }


	custVoIpNormalActiveCalls	OBJECT-TYPE	
		SYNTAX			Counter64
		MAX-ACCESS		read-only
		STATUS			current
		DESCRIPTION		"Number of normal active calls"
		::=  {  custVoIpStatsEntry  20  }


	custVoIpPeakNormalActiveCalls	OBJECT-TYPE	
		SYNTAX			Counter64
		MAX-ACCESS		read-only
		STATUS			current
		DESCRIPTION		"Maximum number of active normal calls since the statistics 
were last reset."
		::=  {  custVoIpStatsEntry  21  }

	mediaStatCurrentAudioSessions	OBJECT-TYPE	
		SYNTAX			Counter64
		MAX-ACCESS		read-only
		STATUS			current
		DESCRIPTION		"Current number of active audio sessions"
		::=  {  mediaStats  1  }

	mediaStatPeakAudioSessions	OBJECT-TYPE	
		SYNTAX			Counter64
		MAX-ACCESS		read-only
		STATUS			current
		DESCRIPTION		"Peak number of audio sessions"
		::=  {  mediaStats  2  }

	mediaStatTotalAudioSessions	OBJECT-TYPE	
		SYNTAX			Counter64
		MAX-ACCESS		read-only
		STATUS			current
		DESCRIPTION		"Total accumulated audio sessions"
		::=  {  mediaStats  3  }

	mediaStatCurrentVideoSessions	OBJECT-TYPE	
		SYNTAX			Counter64
		MAX-ACCESS		read-only
		STATUS			current
		DESCRIPTION		"Current number of active video sessions"
		::=  {  mediaStats  4  }

	mediaStatPeakVideoSessions	OBJECT-TYPE	
		SYNTAX			Counter64
		MAX-ACCESS		read-only
		STATUS			current
		DESCRIPTION		"Peak number of video sessions"
		::=  {  mediaStats  5  }

	mediaStatTotalVideoSessions	OBJECT-TYPE	
		SYNTAX			Counter64
		MAX-ACCESS		read-only
		STATUS			current
		DESCRIPTION		"Total accumulated video sessions"
		::=  {  mediaStats  6  }

	mediaStatCurrentFaxSessions	OBJECT-TYPE	
		SYNTAX			Counter64
		MAX-ACCESS		read-only
		STATUS			current
		DESCRIPTION		"Current number of active fax sessions"
		::=  {  mediaStats  7  }

	mediaStatPeakFaxSessions	OBJECT-TYPE	
		SYNTAX			Counter64
		MAX-ACCESS		read-only
		STATUS			current
		DESCRIPTION		"Peak number of fax sessions"
		::=  {  mediaStats  8  }

	mediaStatTotalFaxSessions	OBJECT-TYPE	
		SYNTAX			Counter64
		MAX-ACCESS		read-only
		STATUS			current
		DESCRIPTION		"Total accumulated number of fax sessions"
		::=  {  mediaStats  9  }

	mediaStatTotalFailures	OBJECT-TYPE	
		SYNTAX			Counter64
		MAX-ACCESS		read-only
		STATUS			current
		DESCRIPTION		"Total accumulated number of media failures"
		::=  {  mediaStats  10  }

	h323RegStatActiveReg	OBJECT-TYPE	
		SYNTAX			Counter64
		MAX-ACCESS		read-only
		STATUS			current
		DESCRIPTION		"Current number of active H.323 registrations"
		::=  {  h323RegStats  1  }

	h323RegStatExpiredReg	OBJECT-TYPE	
		SYNTAX			Counter64
		MAX-ACCESS		read-only
		STATUS			current
		DESCRIPTION		"Number of expired H.323 registrations"
		::=  {  h323RegStats  2  }

	h323RegStatUnauthorizedReg	OBJECT-TYPE	
		SYNTAX			Counter64
		MAX-ACCESS		read-only
		STATUS			current
		DESCRIPTION		"Number of unauthorized H.323 regristrations"
		::=  {  h323RegStats  3  }

	h323RegStatPeakActiveReg	OBJECT-TYPE	
		SYNTAX			Counter64
		MAX-ACCESS		read-only
		STATUS			current
		DESCRIPTION		"Peak number of active H.323 registrations"
		::=  {  h323RegStats  4  }

	h323RegStatUpdateComplete	OBJECT-TYPE	
		SYNTAX			Counter64
		MAX-ACCESS		read-only
		STATUS			current
		DESCRIPTION		"Number of H.323 registration updates completed     
successfully"
		::=  {  h323RegStats  5  }

	h323RegStatUpdateFailures	OBJECT-TYPE	
		SYNTAX			Counter64
		MAX-ACCESS		read-only
		STATUS			current
		DESCRIPTION		"Number of H.323 registration update failures"
		::=  {  h323RegStats  6  }

	h323RegStatAuthFailures	OBJECT-TYPE	
		SYNTAX			Counter64
		MAX-ACCESS		read-only
		STATUS			current
		DESCRIPTION		"Number of H.323 registration authentication failures"
		::=  {  h323RegStats  7  }

	custH323RegStatsTable	OBJECT-TYPE
		SYNTAX		SEQUENCE  OF  CustH323RegStatsEntry
		MAX-ACCESS	not-accessible
		STATUS		current
		DESCRIPTION	"Description"
		::=  { custH323RegStats  1 }

	custH323RegStatsEntry	OBJECT-TYPE
		SYNTAX		CustH323RegStatsEntry
		MAX-ACCESS	not-accessible
		STATUS		current
		DESCRIPTION	"Row Description"
		INDEX		{  custH323RegStatId  }
		::=  { custH323RegStatsTable 1 }

	CustH323RegStatsEntry  ::=  SEQUENCE {
		custH323RegStatId  Integer32,
		custH323RegStatActiveReg  Counter64,
		custH323RegStatExpiredReg  Counter64,
		custH323RegStatUnauthorizedReg  Counter64,
		custH323RegStatPeakActiveReg  Counter64,
		custH323RegStatUpdateComplete  Counter64,
		custH323RegStatUpdateFailures  Counter64,
		custH323RegStatAuthFailures  Counter64
		}


	custH323RegStatId	OBJECT-TYPE	
		SYNTAX			Integer32
		MAX-ACCESS		read-only
		STATUS			current
		DESCRIPTION		"Unique identifier for this customer as specified in the   
XML file"
		::=  {  custH323RegStatsEntry  1  }


	custH323RegStatActiveReg	OBJECT-TYPE	
		SYNTAX			Counter64
		MAX-ACCESS		read-only
		STATUS			current
		DESCRIPTION		"Current number of active H.323 registrations for a   
customer"
		::=  {  custH323RegStatsEntry  2  }


	custH323RegStatExpiredReg	OBJECT-TYPE	
		SYNTAX			Counter64
		MAX-ACCESS		read-only
		STATUS			current
		DESCRIPTION		"Current number of expired H.323 registrations for a   
customer"
		::=  {  custH323RegStatsEntry  3  }


	custH323RegStatUnauthorizedReg	OBJECT-TYPE	
		SYNTAX			Counter64
		MAX-ACCESS		read-only
		STATUS			current
		DESCRIPTION		"The accumulated number of unauthorized H.323 registrations 
for a customer"
		::=  {  custH323RegStatsEntry  4  }


	custH323RegStatPeakActiveReg	OBJECT-TYPE	
		SYNTAX			Counter64
		MAX-ACCESS		read-only
		STATUS			current
		DESCRIPTION		"Peak number of active H.323 registrations for a customer"
		::=  {  custH323RegStatsEntry  5  }


	custH323RegStatUpdateComplete	OBJECT-TYPE	
		SYNTAX			Counter64
		MAX-ACCESS		read-only
		STATUS			current
		DESCRIPTION		"The accumulated number of updated H.323 registrations for  
a customer"
		::=  {  custH323RegStatsEntry  6  }


	custH323RegStatUpdateFailures	OBJECT-TYPE	
		SYNTAX			Counter64
		MAX-ACCESS		read-only
		STATUS			current
		DESCRIPTION		"The accumulated number of failed H.323 registration   
updates for a customer"
		::=  {  custH323RegStatsEntry  7  }


	custH323RegStatAuthFailures	OBJECT-TYPE	
		SYNTAX			Counter64
		MAX-ACCESS		read-only
		STATUS			current
		DESCRIPTION		"The accumulated number of H.323 registration   
authentication faliures for a customer"
		::=  {  custH323RegStatsEntry  8  }

                
        --
        -- SIP Common Stats
        --
        sipCommonStatsDiscontinuityTimer OBJECT-TYPE
		SYNTAX			TimeTicks
		MAX-ACCESS		read-only
		STATUS			current
		DESCRIPTION		
                        "The number of centi-seconds since the sipCommonStats
                        were last reset. When the value of this attribute is
                        reset a discontinuity of all of the counters in the
                        sipCommonStats has occured. This should cause the
                        management application to not compute deltas for the
                        current polling interval. These statistics can be reset 
                        using the 'clear stats common sip' command on the 
                        nCite CLI. These statistics can also be cleared by 
                        issuing an SNMP Set to nCiteStatsReset with the value
                        of sipCommonStats ( 10 )."
               	::=  {  sipCommonStats  1  }

        sipCommonStatsScalars OBJECT IDENTIFIER
        	::=  {  sipCommonStats  2  }

        sipCommonStatsTotalMessageErrors OBJECT-TYPE
		SYNTAX			Counter32
		MAX-ACCESS		read-only
		STATUS			current
		DESCRIPTION		
                        "Cumulative tally, since sipCommonStatsDiscontinuityTimer
                        was reset, of SIP message errors encountered.
                        
                        Discontinuities in this counter can be detected by the
                        value of sipCommonStatsDiscontinuityTimer being reset."
                ::= { sipCommonStatsScalars 1 }
        
        sipCommonStatsTotalMessageRoutingFailures OBJECT-TYPE
		SYNTAX			Counter32
		MAX-ACCESS		read-only
		STATUS			current
		DESCRIPTION		
                        "Cumulative tally, since sipCommonStatsDiscontinuityTimer
                        was reset, of failures to determine routing for a SIP 
                        message.
                        
                        Discontinuities in this counter can be detected by the
                        value of sipCommonStatsDiscontinuityTimer being reset."
                ::= { sipCommonStatsScalars 2 }
        
        sipCommonStatsTotalMessageTransmitFailures OBJECT-TYPE
		SYNTAX			Counter32
		MAX-ACCESS		read-only
		STATUS			current
		DESCRIPTION		
                        "Cumulative tally, since sipCommonStatsDiscontinuityTimer 
                        was reset, of failures to transmit a SIP message.
                        
                        Discontinuities in this counter can be detected by the
                        value of sipCommonStatsDiscontinuityTimer being reset."
                ::= { sipCommonStatsScalars 3 }
        
        sipCommonStatsTotalAuthenticationFailures OBJECT-TYPE
		SYNTAX			Counter32
		MAX-ACCESS		read-only
		STATUS			current
		DESCRIPTION		
                        "Cumulative tally, since sipCommonStatsDiscontinuityTimer 
                        was reset, of SIP messages that failed Customer 
                        Authentication, Sender or Target.
                        
                        Discontinuities in this counter can be detected by the
                        value of sipCommonStatsDiscontinuityTimer being reset."
                ::= { sipCommonStatsScalars 4 }
        
        
        --
        -- SIP Event Dialog Stats
        --
        sipEvtDlgStatsDiscontinuityTimer OBJECT-TYPE
		SYNTAX			TimeTicks
		MAX-ACCESS		read-only
		STATUS			current
		DESCRIPTION		
                        "The number of centi-seconds since the sipEvtDlgStats
                        were last reset. When the value of this attribute is
                        reset a discontinuity of all of the counters in the
                        sipEvtDlgStats has occured. This should cause the
                        management application to not compute deltas for the
                        current polling interval. These statistics can be reset 
                        using the 'clear stats eventdialog' command on the 
                        nCite CLI.These statistics can also be cleared by 
                        issuing an SNMP Set to nCiteStatsReset with the value
                        of sipEvtDlgStats ( 11 )."
               	::=  {  sipEvtDlgStats  1  }

        sipEvtDlgStatsScalars OBJECT IDENTIFIER
        	::=  {  sipEvtDlgStats  2  }
                
        sipEvtDlgStatsActiveDialogs OBJECT-TYPE
		SYNTAX			Gauge32
		MAX-ACCESS		read-only
		STATUS			current
		DESCRIPTION		
                        "The current number of Event Dialogs successfully 
                        created by a SUBSCRIBE request."
                ::= { sipEvtDlgStatsScalars 1 }
        
        sipEvtDlgStatsPeakActiveDialogs OBJECT-TYPE
		SYNTAX			Gauge32
		MAX-ACCESS		read-only
		STATUS			current
		DESCRIPTION		
                        "The peak number of Active Dialogs at one time since
                        startup or the last clear."
                ::= { sipEvtDlgStatsScalars 2 }
        
        sipEvtDlgStatsTerminatedDialogs OBJECT-TYPE
		SYNTAX			Counter32
		MAX-ACCESS		read-only
		STATUS			current
		DESCRIPTION		
                        "Cumulative tally, since sipEvtDlgStatsDiscontinuityTimer
                        was reset, of Event Dialogs that were terminated via 
                        NOTIFY with Subscription-state of “terminated”, or du
                        e to User Delete.
                        
                        Discontinuities in this counter can be detected by the
                        value of sipEvtDlgStatsDiscontinuityTimer being reset."
                ::= { sipEvtDlgStatsScalars 3 }
        
        sipEvtDlgStatsExpiredDialogs OBJECT-TYPE
		SYNTAX			Counter32
		MAX-ACCESS		read-only
		STATUS			current
		DESCRIPTION		
                        "Cumulative tally, since sipEvtDlgStatsDiscontinuityTimer
                        was reset, of Event Dialogs that were terminated due to 
                        expiration for the entire system.
                        
                        Discontinuities in this counter can be detected by the
                        value of sipEvtDlgStatsDiscontinuityTimer being reset."
                ::= { sipEvtDlgStatsScalars 4 }
        
        sipEvtDlgStatsFailedDialogs OBJECT-TYPE
		SYNTAX			Counter32
		MAX-ACCESS		read-only
		STATUS			current
		DESCRIPTION		
                        "Cumulative tally, since sipEvtDlgStatsDiscontinuityTimer
                        was reset, of Event Dialogs that were terminated due to
                        error reponse to establishing SUBSCRIBE, an Abort Response
                        to mid-dialog SUBSCRIBE or NOTIFY, a Challenge Answer
                        Timeout, or a Transaction Timeout on any SUBSCRIBE or
                        NOTIFY for the entire system.
                        
                        Discontinuities in this counter can be detected by the
                        value of sipEvtDlgStatsDiscontinuityTimer being reset."
                ::= { sipEvtDlgStatsScalars 5 }
        
        sipEvtDlgStatsUnauthorizedDialogs OBJECT-TYPE
		SYNTAX			Counter32
		MAX-ACCESS		read-only
		STATUS			current
		DESCRIPTION		
                        "Cumulative tally, since sipEvtDlgStatsDiscontinuityTimer
                        was reset, of Event Dialogs that were not created or 
                        were terminated due to failing authorization (exceeding
                        Global Event Dialog SAC or Customer Event Dialog SAC)
                        for the entire system.
                        
                        Discontinuities in this counter can be detected by the
                        value of sipEvtDlgStatsDiscontinuityTimer being reset."
                ::= { sipEvtDlgStatsScalars 6 }
        
        sipEvtDlgStatsAuthenticationChallenges OBJECT-TYPE
		SYNTAX			Counter32
		MAX-ACCESS		read-only
		STATUS			current
		DESCRIPTION		
                        "Cumulative tally, since sipEvtDlgStatsDiscontinuityTimer
                        was reset, of Event Dialogs that received an Authentication
                        Challenge response (401/407) to the establishing SUBSCRIBE
                        for the entire system.
                        
                        Discontinuities in this counter can be detected by the
                        value of sipEvtDlgStatsDiscontinuityTimer being reset."
                ::= { sipEvtDlgStatsScalars 7 }
        
        --
        -- SIP Event Dialog Stats for each Customer
        --
	sipEvtDlgCustStatsTable	OBJECT-TYPE
		SYNTAX		SEQUENCE  OF  SipEvtDlgCustStatsEntry
		MAX-ACCESS	not-accessible
		STATUS		current
		DESCRIPTION	"Description"
		::=  { sipEvtDlgStats  3 }

	sipEvtDlgCustStatsEntry	OBJECT-TYPE
		SYNTAX		SipEvtDlgCustStatsEntry
		MAX-ACCESS	not-accessible
		STATUS		current
		DESCRIPTION	"Row Description"
		INDEX		{  sipEvtDlgCustStatsIndex  }
		::=  { sipEvtDlgCustStatsTable 1 }

	SipEvtDlgCustStatsEntry  ::=  SEQUENCE {
		sipEvtDlgCustStatsIndex                     Integer32,
                sipEvtDlgCustStatsActiveDialogs             Gauge32,
                sipEvtDlgCustStatsPeakActiveDialogs         Gauge32,
                sipEvtDlgCustStatsTerminatedDialogs         Counter32,
                sipEvtDlgCustStatsExpiredDialogs            Counter32,
                sipEvtDlgCustStatsFailedDialogs             Counter32,
                sipEvtDlgCustStatsUnauthorizedDialogs       Counter32,
                sipEvtDlgCustStatsAuthenticationChallenges  Counter32
		}
                
	sipEvtDlgCustStatsIndex	OBJECT-TYPE	
		SYNTAX			Integer32
		MAX-ACCESS		read-only
		STATUS			current
		DESCRIPTION		
                        "Customer ID as it is defined in the EMS database and the   
                        XML file provisioned to the nCIte"
		::=  {  sipEvtDlgCustStatsEntry  1  }
  
        sipEvtDlgCustStatsActiveDialogs OBJECT-TYPE
		SYNTAX			Gauge32
		MAX-ACCESS		read-only
		STATUS			current
		DESCRIPTION		
                        "The current number of Event Dialogs successfully 
                        created by a SUBSCRIBE request for this customer."
                ::= { sipEvtDlgCustStatsEntry 2 }
        
        sipEvtDlgCustStatsPeakActiveDialogs OBJECT-TYPE
		SYNTAX			Gauge32
		MAX-ACCESS		read-only
		STATUS			current
		DESCRIPTION		
                        "The peak number of Active Dialogs at one time since
                        startup or the last clear for this customer."
                ::= { sipEvtDlgCustStatsEntry 3 }
        
        sipEvtDlgCustStatsTerminatedDialogs OBJECT-TYPE
		SYNTAX			Counter32
		MAX-ACCESS		read-only
		STATUS			current
		DESCRIPTION		
                        "Cumulative tally, since sipEvtDlgStatsDiscontinuityTimer
                        was reset, of Event Dialogs that were terminated via 
                        NOTIFY with Subscription-state of “terminated”, or due
                        to User Delete for this customer.
                        
                        Discontinuities in this counter can be detected by the
                        value of sipEvtDlgStatsDiscontinuityTimer being reset."
                ::= { sipEvtDlgCustStatsEntry 4 }
        
        sipEvtDlgCustStatsExpiredDialogs OBJECT-TYPE
		SYNTAX			Counter32
		MAX-ACCESS		read-only
		STATUS			current
		DESCRIPTION		
                        "Cumulative tally, since sipEvtDlgStatsDiscontinuityTimer
                        was reset, of Event Dialogs that were terminated due to
                        expiration for this customer.
                        
                        Discontinuities in this counter can be detected by the
                        value of sipEvtDlgStatsDiscontinuityTimer being reset."
                ::= { sipEvtDlgCustStatsEntry 5 }
        
        sipEvtDlgCustStatsFailedDialogs OBJECT-TYPE
		SYNTAX			Counter32
		MAX-ACCESS		read-only
		STATUS			current
		DESCRIPTION		
                        "Cumulative tally, since sipEvtDlgStatsDiscontinuityTimer
                        was reset, of Event Dialogs that were terminated due to
                        error reponse to establishing SUBSCRIBE, an Abort Response
                        to mid-dialog SUBSCRIBE or NOTIFY, a Challenge Answer 
                        Timeout, or a Transaction Timeout on any SUBSCRIBE or 
                        NOTIFY for this customer.
                        
                        Discontinuities in this counter can be detected by the
                        value of sipEvtDlgStatsDiscontinuityTimer being reset."
                ::= { sipEvtDlgCustStatsEntry 6 }
        
        sipEvtDlgCustStatsUnauthorizedDialogs OBJECT-TYPE
		SYNTAX			Counter32
		MAX-ACCESS		read-only
		STATUS			current
		DESCRIPTION		
                        "Cumulative tally, since sipEvtDlgStatsDiscontinuityTimer
                        was reset, of Event Dialogs that were not created or were 
                        terminated due to failing authorization (exceeding Global 
                        Event Dialog SAC or Customer Event Dialog SAC) for this 
                        customer.
                        
                        Discontinuities in this counter can be detected by the
                        value of sipEvtDlgStatsDiscontinuityTimer being reset."
                ::= { sipEvtDlgCustStatsEntry 7 }
        
        sipEvtDlgCustStatsAuthenticationChallenges OBJECT-TYPE
		SYNTAX			Counter32
		MAX-ACCESS		read-only
		STATUS			current
		DESCRIPTION		
                        "Cumulative tally, since sipEvtDlgStatsDiscontinuityTimer
                        was reset, of Event Dialogs that received an Authentication
                        Challenge response (401/407) to the establishing 
                        SUBSCRIBE for this customer.
                        
                        Discontinuities in this counter can be detected by the
                        value of sipEvtDlgStatsDiscontinuityTimer being reset."
                ::= { sipEvtDlgCustStatsEntry 8 }
               
                
                
	diagType	OBJECT-TYPE	
		SYNTAX			INTEGER  { nCiteFullIntLoopback ( 1 ) , nCiteFullExtLoopback ( 2 ) , nCiteInterfaceIntLoopback ( 3 ) , nCiteInterfaceExtLoopback ( 4 ) , cardIntLoopback ( 5 ) , cardExtLoopback ( 6 ) , portIntLoopback ( 7 ) , portExtLoopback ( 8 ) } 
		MAX-ACCESS		read-write
		STATUS			deprecated
		DESCRIPTION		"Diagnostic Type"
		::=  {  runDiagGroup  1  }

	diagDeviceSlotNum	OBJECT-TYPE	
		SYNTAX			Integer32  ( 1 .. 14  ) 
		MAX-ACCESS		read-write
		STATUS			deprecated
		DESCRIPTION		"Slot that contains the device"
		::=  {  runDiagGroup  2  }

	diagDevPortNum	OBJECT-TYPE	
		SYNTAX			Integer32  ( 1 .. 48  ) 
		MAX-ACCESS		read-write
		STATUS			deprecated
		DESCRIPTION		"Port number used for the diagnostic. Should be defaulted   
if not used."
		::=  {  runDiagGroup  3  }

	diagStartCmd	OBJECT-TYPE	
		SYNTAX			INTEGER  { default ( 0 ) , runDiag ( 1 ) } 
		MAX-ACCESS		read-write
		STATUS			deprecated
		DESCRIPTION		"Setting of this value causes the nCite to  perform the     
requested diagnostic"
		::=  {  runDiagGroup  4  }

       	nrObjectIDs OBJECT IDENTIFIER
		::=  { netrake  3 }

        nrSessionBorderController OBJECT IDENTIFIER
		::=  { nrObjectIDs 1 }

        nrSBCSE OBJECT IDENTIFIER
		::=  { nrSessionBorderController 1 }

        nrSBCwNcp OBJECT IDENTIFIER
		::=  { nrSBCSE 1 }

        nrSBCwNte OBJECT IDENTIFIER
		::=  { nrSBCSE 2 }

        nrSBCDE OBJECT IDENTIFIER
		::=  { nrSessionBorderController 2 }

END
