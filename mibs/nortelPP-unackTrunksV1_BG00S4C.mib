Nortel-Magellan-Passport-UnackTrunksMIB
DEFINITIONS ::= BEGIN



IMPORTS

      OBJECT-TYPE
   FROM RFC-1212

      passportMIBs
   FROM Nortel-Magellan-Passport-UsefulDefinitionsMIB

      Counter32,
      DisplayString,
      StorageType,
      RowStatus,
      Gauge32,
      Unsigned32
   FROM Nortel-Magellan-Passport-StandardTextualConventionsMIB

      NonReplicated,
      Link
   FROM Nortel-Magellan-Passport-TextualConventionsMIB

      trkIndex,
      trk
   FROM Nortel-Magellan-Passport-TrunksMIB;




-- LAST-UPDATED   "9808030000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     UnackTrunks Enterprise MIB."

unackTrunksMIB OBJECT IDENTIFIER ::= { passportMIBs 22 }










-- Trunk/n Unacknowledged
-- The Unacknowledged component provides a Layer 2 protocol that 
-- adds the minimum of overhead to data on the link. A Framer 
-- subcomponent is automatically added providing the underlying 
-- HDLC framing and associated hardware that the Unacknowledged 
-- component will use.

trkUnAcked OBJECT IDENTIFIER ::= { trk 2 }



trkUnAckedRowStatusTable OBJECT-TYPE
   SYNTAX     SEQUENCE OF TrkUnAckedRowStatusEntry
   ACCESS     not-accessible
   STATUS     mandatory
   DESCRIPTION
     "This entry controls the addition and deletion of 
      trkUnAcked components."
::= { trkUnAcked 1 }

trkUnAckedRowStatusEntry OBJECT-TYPE
   SYNTAX     TrkUnAckedRowStatusEntry
   ACCESS     not-accessible
   STATUS     mandatory
   DESCRIPTION
     "A single entry in the table represents a single 
      trkUnAcked component."
   INDEX {
      trkIndex,
      trkUnAckedIndex }
::= { trkUnAckedRowStatusTable 1 }

TrkUnAckedRowStatusEntry ::= SEQUENCE {
   trkUnAckedRowStatus
      RowStatus,
   trkUnAckedComponentName
      DisplayString,
   trkUnAckedStorageType
      StorageType,
   trkUnAckedIndex
      NonReplicated }

trkUnAckedRowStatus OBJECT-TYPE
   SYNTAX     RowStatus 
   ACCESS     read-write
   STATUS     mandatory
   DESCRIPTION
     "This variable is used as the basis for SNMP naming of
      trkUnAcked components.
      These components can be added and deleted."
::= { trkUnAckedRowStatusEntry 1 }

trkUnAckedComponentName OBJECT-TYPE
   SYNTAX     DisplayString 
   ACCESS     read-only
   STATUS     mandatory
   DESCRIPTION
     "This variable provides the component's string name for
      use with the ASCII Console Interface"
::= { trkUnAckedRowStatusEntry 2 }

trkUnAckedStorageType OBJECT-TYPE
   SYNTAX     StorageType 
   ACCESS     read-only
   STATUS     mandatory
   DESCRIPTION
     "This variable represents the storage type value for the
      trkUnAcked tables."
::= { trkUnAckedRowStatusEntry 4 }

trkUnAckedIndex OBJECT-TYPE
   SYNTAX     NonReplicated 
   ACCESS     not-accessible
   STATUS     mandatory
   DESCRIPTION
     "This variable represents the index for the trkUnAcked tables."
::= { trkUnAckedRowStatusEntry 10 }

trkUnAckedProvTable OBJECT-TYPE
   SYNTAX     SEQUENCE OF TrkUnAckedProvEntry
   ACCESS     not-accessible
   STATUS     mandatory
   DESCRIPTION
     "This group of provisionable attributes contains the parameters used 
      by Unacknowledged, Utp, and FrAccess for monitoring link quality."
::= { trkUnAcked 10 }

trkUnAckedProvEntry OBJECT-TYPE
   SYNTAX     TrkUnAckedProvEntry
   ACCESS     not-accessible
   STATUS     mandatory
   DESCRIPTION
     "An entry in the trkUnAckedProvTable."
   INDEX {
      trkIndex,
      trkUnAckedIndex }
::= { trkUnAckedProvTable 1 }

TrkUnAckedProvEntry ::= SEQUENCE {
   trkUnAckedMaximumErroredInterval
      Unsigned32,
   trkUnAckedReceiveErrorSensitivity
      Unsigned32 }

trkUnAckedMaximumErroredInterval OBJECT-TYPE
   SYNTAX     Unsigned32 (0 | 1..15)
   ACCESS     read-write
   STATUS     mandatory
   DESCRIPTION
     "This attribute specifies the interval time over which the error 
      threshold (as specified by receiveErrorSensitivity) must be 
      continuously exceeded before the Unacknowledged, Utp, or 
      FrAccess component can be degraded. Once the error interval count 
      exceeds the provisioned value, the Unacknowledged, Utp, or 
      FrAccess component issues an alarm indicating that link quality has 
      degraded, and it disables its parent component. The exception to 
      this is a value of zero, the default, which indicates that the 
      mechanism is completely disabled."
   DEFVAL     { 0 }
::= { trkUnAckedProvEntry 1 }

trkUnAckedReceiveErrorSensitivity OBJECT-TYPE
   SYNTAX     Unsigned32 (0 | 1..10)
   ACCESS     read-write
   STATUS     mandatory
   DESCRIPTION
     "This attribute is the allowable error rate beyond which the 
      Unacknowledged, Utp, or FrAccess component can be degraded if it 
      persists for a duration longer than the maximumErrorInterval. The 
      threshold is expressed as a percentage of number of errored frames 
      in the last interval per number of frames received in the last interval. 
      The exception to this is a value of zero, which indicates that the 
      mechanism is completely disabled. The configurable values are:
      0 = the mechanism is completely disabled
      1 = 1/(2**1)
      2 = 1/(2**2)
      3 = 1/(2**3)
      :
      10 = 1/(2**10)"
   DEFVAL     { 3 }
::= { trkUnAckedProvEntry 2 }

trkUnAckedStateTable OBJECT-TYPE
   SYNTAX     SEQUENCE OF TrkUnAckedStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { trkUnAcked 11 }

trkUnAckedStateEntry OBJECT-TYPE
   SYNTAX     TrkUnAckedStateEntry
   ACCESS     not-accessible
   STATUS     mandatory
   DESCRIPTION
     "An entry in the trkUnAckedStateTable."
   INDEX {
      trkIndex,
      trkUnAckedIndex }
::= { trkUnAckedStateTable 1 }

TrkUnAckedStateEntry ::= SEQUENCE {
   trkUnAckedAdminState
      INTEGER,
   trkUnAckedOperationalState
      INTEGER,
   trkUnAckedUsageState
      INTEGER,
   trkUnAckedAvailabilityStatus
      OCTET STRING,
   trkUnAckedProceduralStatus
      OCTET STRING,
   trkUnAckedControlStatus
      OCTET STRING,
   trkUnAckedAlarmStatus
      OCTET STRING,
   trkUnAckedStandbyStatus
      INTEGER,
   trkUnAckedUnknownStatus
      INTEGER }

trkUnAckedAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { trkUnAckedStateEntry 1 }

trkUnAckedOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { trkUnAckedStateEntry 2 }

trkUnAckedUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { trkUnAckedStateEntry 3 }

trkUnAckedAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { trkUnAckedStateEntry 4 }

trkUnAckedProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { trkUnAckedStateEntry 5 }

trkUnAckedControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { trkUnAckedStateEntry 6 }

trkUnAckedAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { trkUnAckedStateEntry 7 }

trkUnAckedStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { trkUnAckedStateEntry 8 }

trkUnAckedUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { trkUnAckedStateEntry 9 }


-- 
-- Trunk/n Unack Framer
-- 
-- The Framer component controls link layer framing for application 
-- components sending and receiving data on a link interface. It is also 
-- through Framer, that an application component is associated with a 
-- specific hardware link interface.
-- 
-- The Framer component provides provisionable attributes related to 
-- datapath aspects of the hardware interface (such as crc and frame 
-- length) rather than interface specific attributes (such as modem 
-- leads and clocking) which are associated with specific hardware 
-- components (such as V35/n or DS1/n). The Framer component also 
-- provides a provisionable attribute which binds the application 
-- component to a specific hardware component.
-- 
-- The Framer component contains operational attributes for link 
-- interface datapath statistics (such as frame counts and aborts).
-- 

trkUnAckedFramer OBJECT IDENTIFIER ::= { trkUnAcked 2 }



trkUnAckedFramerRowStatusTable OBJECT-TYPE
   SYNTAX     SEQUENCE OF TrkUnAckedFramerRowStatusEntry
   ACCESS     not-accessible
   STATUS     mandatory
   DESCRIPTION
     "This entry controls the addition and deletion of 
      trkUnAckedFramer components."
::= { trkUnAckedFramer 1 }

trkUnAckedFramerRowStatusEntry OBJECT-TYPE
   SYNTAX     TrkUnAckedFramerRowStatusEntry
   ACCESS     not-accessible
   STATUS     mandatory
   DESCRIPTION
     "A single entry in the table represents a single 
      trkUnAckedFramer component."
   INDEX {
      trkIndex,
      trkUnAckedIndex,
      trkUnAckedFramerIndex }
::= { trkUnAckedFramerRowStatusTable 1 }

TrkUnAckedFramerRowStatusEntry ::= SEQUENCE {
   trkUnAckedFramerRowStatus
      RowStatus,
   trkUnAckedFramerComponentName
      DisplayString,
   trkUnAckedFramerStorageType
      StorageType,
   trkUnAckedFramerIndex
      NonReplicated }

trkUnAckedFramerRowStatus OBJECT-TYPE
   SYNTAX     RowStatus 
   ACCESS     read-only
   STATUS     mandatory
   DESCRIPTION
     "This variable is used as the basis for SNMP naming of
      trkUnAckedFramer components.
      These components cannot be added nor deleted."
::= { trkUnAckedFramerRowStatusEntry 1 }

trkUnAckedFramerComponentName OBJECT-TYPE
   SYNTAX     DisplayString 
   ACCESS     read-only
   STATUS     mandatory
   DESCRIPTION
     "This variable provides the component's string name for
      use with the ASCII Console Interface"
::= { trkUnAckedFramerRowStatusEntry 2 }

trkUnAckedFramerStorageType OBJECT-TYPE
   SYNTAX     StorageType 
   ACCESS     read-only
   STATUS     mandatory
   DESCRIPTION
     "This variable represents the storage type value for the
      trkUnAckedFramer tables."
::= { trkUnAckedFramerRowStatusEntry 4 }

trkUnAckedFramerIndex OBJECT-TYPE
   SYNTAX     NonReplicated 
   ACCESS     not-accessible
   STATUS     mandatory
   DESCRIPTION
     "This variable represents the index for the trkUnAckedFramer tables."
::= { trkUnAckedFramerRowStatusEntry 10 }

trkUnAckedFramerProvTable OBJECT-TYPE
   SYNTAX     SEQUENCE OF TrkUnAckedFramerProvEntry
   ACCESS     not-accessible
   STATUS     mandatory
   DESCRIPTION
     "This group contains the base provisioning data for the Framer 
      component. Application or hardware interface specific provisioning 
      data is contained in other provisionable Framer groups."
::= { trkUnAckedFramer 10 }

trkUnAckedFramerProvEntry OBJECT-TYPE
   SYNTAX     TrkUnAckedFramerProvEntry
   ACCESS     not-accessible
   STATUS     mandatory
   DESCRIPTION
     "An entry in the trkUnAckedFramerProvTable."
   INDEX {
      trkIndex,
      trkUnAckedIndex,
      trkUnAckedFramerIndex }
::= { trkUnAckedFramerProvTable 1 }

TrkUnAckedFramerProvEntry ::= SEQUENCE {
   trkUnAckedFramerInterfaceName
      Link }

trkUnAckedFramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { trkUnAckedFramerProvEntry 1 }

trkUnAckedFramerLinkTable OBJECT-TYPE
   SYNTAX     SEQUENCE OF TrkUnAckedFramerLinkEntry
   ACCESS     not-accessible
   STATUS     mandatory
   DESCRIPTION
     "This group contains attributes defining the framing of data on the 
      link interface."
::= { trkUnAckedFramer 11 }

trkUnAckedFramerLinkEntry OBJECT-TYPE
   SYNTAX     TrkUnAckedFramerLinkEntry
   ACCESS     not-accessible
   STATUS     mandatory
   DESCRIPTION
     "An entry in the trkUnAckedFramerLinkTable."
   INDEX {
      trkIndex,
      trkUnAckedIndex,
      trkUnAckedFramerIndex }
::= { trkUnAckedFramerLinkTable 1 }

TrkUnAckedFramerLinkEntry ::= SEQUENCE {
   trkUnAckedFramerFramingType
      INTEGER,
   trkUnAckedFramerDataInversion
      INTEGER,
   trkUnAckedFramerFrameCrcType
      INTEGER,
   trkUnAckedFramerFlagsBetweenFrames
      Unsigned32 }

trkUnAckedFramerFramingType OBJECT-TYPE
   SYNTAX     INTEGER  {
                 hdlc(0),
                 interrupting(1) }
   ACCESS     read-write
   STATUS     mandatory
   DESCRIPTION
     "This attribute specifies the type of framing protocol that will be 
      used for frames transmitted to the link interface and received from 
      the link interface. If the value of this attribute is set to the default 
      interrupting, then a Proprietary hdlc protocol is used which allows 
      for voice cells to interrupt transmission of data frames, transmit the 
      voice cell, and then continue transmitting the data frame. If the 
      value of this attribute is set to hdlc, then the standard hdlc procotol 
      is used for the sequential transmission of individual frames."
   DEFVAL     { interrupting }
::= { trkUnAckedFramerLinkEntry 1 }

trkUnAckedFramerDataInversion OBJECT-TYPE
   SYNTAX     INTEGER  {
                 off(0),
                 on(16) }
   ACCESS     read-write
   STATUS     mandatory
   DESCRIPTION
     "This attribute determines whether data bits are to be inverted (1 to 0 
      and 0 to 1) before transmission of frames to the interface. If the 
      value of this attribute is On, the incoming data bits will also be 
      inverted when frames are received from the link before being 
      processed.
      
      This option is typically used in hdlc framing mode when inversion 
      is used to guarantee 1's density.
      
      Note that aborts (in hdlc and interrupting modes) are corrupted 
      when data is inverted."
   DEFVAL     { off }
::= { trkUnAckedFramerLinkEntry 2 }

trkUnAckedFramerFrameCrcType OBJECT-TYPE
   SYNTAX     INTEGER  {
                 crc16(0),
                 crc32(1),
                 noCrc(2) }
   ACCESS     read-write
   STATUS     mandatory
   DESCRIPTION
     "This attribute defines the type of CRC used. 
      
      The CRC value calculated is appended to the end of the frames 
      transmitted to the link. The CRC value is removed from the end of 
      frames received from the link and checked for correctness.
      NoCrc means that CRC is not used."
   DEFVAL     { crc16 }
::= { trkUnAckedFramerLinkEntry 3 }

trkUnAckedFramerFlagsBetweenFrames OBJECT-TYPE
   SYNTAX     Unsigned32 (1..16)
   ACCESS     read-write
   STATUS     mandatory
   DESCRIPTION
     "This attribute defines the number of flags that are inserted between 
      frames sent to the link interface."
   DEFVAL     { 1 }
::= { trkUnAckedFramerLinkEntry 4 }

trkUnAckedFramerStateTable OBJECT-TYPE
   SYNTAX     SEQUENCE OF TrkUnAckedFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { trkUnAckedFramer 12 }

trkUnAckedFramerStateEntry OBJECT-TYPE
   SYNTAX     TrkUnAckedFramerStateEntry
   ACCESS     not-accessible
   STATUS     mandatory
   DESCRIPTION
     "An entry in the trkUnAckedFramerStateTable."
   INDEX {
      trkIndex,
      trkUnAckedIndex,
      trkUnAckedFramerIndex }
::= { trkUnAckedFramerStateTable 1 }

TrkUnAckedFramerStateEntry ::= SEQUENCE {
   trkUnAckedFramerAdminState
      INTEGER,
   trkUnAckedFramerOperationalState
      INTEGER,
   trkUnAckedFramerUsageState
      INTEGER }

trkUnAckedFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { trkUnAckedFramerStateEntry 1 }

trkUnAckedFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { trkUnAckedFramerStateEntry 2 }

trkUnAckedFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { trkUnAckedFramerStateEntry 3 }

trkUnAckedFramerStatsTable OBJECT-TYPE
   SYNTAX     SEQUENCE OF TrkUnAckedFramerStatsEntry
   ACCESS     not-accessible
   STATUS     mandatory
   DESCRIPTION
     "This group contains the operational statistics data for a 
      Unacknowledge Framer component."
::= { trkUnAckedFramer 13 }

trkUnAckedFramerStatsEntry OBJECT-TYPE
   SYNTAX     TrkUnAckedFramerStatsEntry
   ACCESS     not-accessible
   STATUS     mandatory
   DESCRIPTION
     "An entry in the trkUnAckedFramerStatsTable."
   INDEX {
      trkIndex,
      trkUnAckedIndex,
      trkUnAckedFramerIndex }
::= { trkUnAckedFramerStatsTable 1 }

TrkUnAckedFramerStatsEntry ::= SEQUENCE {
   trkUnAckedFramerFrmFromIf
      Counter32,
   trkUnAckedFramerOctetFromIf
      Counter32,
   trkUnAckedFramerAborts
      Counter32,
   trkUnAckedFramerCrcErrors
      Counter32,
   trkUnAckedFramerLrcErrors
      Counter32,
   trkUnAckedFramerNonOctetErrors
      Counter32,
   trkUnAckedFramerOverruns
      Counter32,
   trkUnAckedFramerUnderruns
      Counter32,
   trkUnAckedFramerLargeFrmErrors
      Counter32,
   trkUnAckedFramerFrmModeErrors
      Counter32,
   trkUnAckedFramerOutOfSequenceFrm
      Counter32,
   trkUnAckedFramerRepeatedFrm
      Counter32 }

trkUnAckedFramerFrmFromIf OBJECT-TYPE
   SYNTAX     Counter32 
   ACCESS     read-only
   STATUS     mandatory
   DESCRIPTION
     "The number of frames received from the link interface by Framer."
::= { trkUnAckedFramerStatsEntry 2 }

trkUnAckedFramerOctetFromIf OBJECT-TYPE
   SYNTAX     Counter32 
   ACCESS     read-only
   STATUS     mandatory
   DESCRIPTION
     "The number of bytes received from the link interface by Framer."
::= { trkUnAckedFramerStatsEntry 3 }

trkUnAckedFramerAborts OBJECT-TYPE
   SYNTAX     Counter32 
   ACCESS     read-only
   STATUS     mandatory
   DESCRIPTION
     "This attribute is the total number of aborts received."
::= { trkUnAckedFramerStatsEntry 4 }

trkUnAckedFramerCrcErrors OBJECT-TYPE
   SYNTAX     Counter32 
   ACCESS     read-only
   STATUS     mandatory
   DESCRIPTION
     "This attribute is the total number of frames with with CRC errors."
::= { trkUnAckedFramerStatsEntry 5 }

trkUnAckedFramerLrcErrors OBJECT-TYPE
   SYNTAX     Counter32 
   ACCESS     read-only
   STATUS     mandatory
   DESCRIPTION
     "This attribute is the total number of frames with LRC errors."
::= { trkUnAckedFramerStatsEntry 6 }

trkUnAckedFramerNonOctetErrors OBJECT-TYPE
   SYNTAX     Counter32 
   ACCESS     read-only
   STATUS     mandatory
   DESCRIPTION
     "This attribute is the total number of frames that were non octet 
      aligned."
::= { trkUnAckedFramerStatsEntry 7 }

trkUnAckedFramerOverruns OBJECT-TYPE
   SYNTAX     Counter32 
   ACCESS     read-only
   STATUS     mandatory
   DESCRIPTION
     "This attribute is the total number of frames received from the link 
      for which overruns occurred."
::= { trkUnAckedFramerStatsEntry 8 }

trkUnAckedFramerUnderruns OBJECT-TYPE
   SYNTAX     Counter32 
   ACCESS     read-only
   STATUS     mandatory
   DESCRIPTION
     "This attribute is the total number of frames transmitted to the link 
      for which underruns occurred."
::= { trkUnAckedFramerStatsEntry 9 }

trkUnAckedFramerLargeFrmErrors OBJECT-TYPE
   SYNTAX     Counter32 
   ACCESS     read-only
   STATUS     mandatory
   DESCRIPTION
     "This attribute is the total number of frames received which were too 
      large. The frame execeeded the maximumFrameLengthLimit 
      provisioned attribute or it contained more than the 255 block 
      hardware limit."
::= { trkUnAckedFramerStatsEntry 10 }

trkUnAckedFramerFrmModeErrors OBJECT-TYPE
   SYNTAX     Counter32 
   ACCESS     read-only
   STATUS     mandatory
   DESCRIPTION
     "This attribute is the total number of frames detected with framing 
      mode errors. A framingModeError is flagged when frames are 
      inconsistent with the specified framingType, that is when 
      interrupting frames are used while running in hdlc mode."
::= { trkUnAckedFramerStatsEntry 11 }

trkUnAckedFramerOutOfSequenceFrm OBJECT-TYPE
   SYNTAX     Counter32 
   ACCESS     read-only
   STATUS     mandatory
   DESCRIPTION
     "This attribute is the total number of out of sequence frames in 
      interrupting mode that have been received from the link."
::= { trkUnAckedFramerStatsEntry 12 }

trkUnAckedFramerRepeatedFrm OBJECT-TYPE
   SYNTAX     Counter32 
   ACCESS     read-only
   STATUS     mandatory
   DESCRIPTION
     "This attribute is the total number of repeated frames (frames with 
      the same sequence number) in interrupting mode that have been 
      received from the link."
::= { trkUnAckedFramerStatsEntry 13 }

trkUnAckedFramerUtilTable OBJECT-TYPE
   SYNTAX     SEQUENCE OF TrkUnAckedFramerUtilEntry
   ACCESS     not-accessible
   STATUS     mandatory
   DESCRIPTION
     "This group contains the link utilization operational data for a 
      Framer component."
::= { trkUnAckedFramer 14 }

trkUnAckedFramerUtilEntry OBJECT-TYPE
   SYNTAX     TrkUnAckedFramerUtilEntry
   ACCESS     not-accessible
   STATUS     mandatory
   DESCRIPTION
     "An entry in the trkUnAckedFramerUtilTable."
   INDEX {
      trkIndex,
      trkUnAckedIndex,
      trkUnAckedFramerIndex }
::= { trkUnAckedFramerUtilTable 1 }

TrkUnAckedFramerUtilEntry ::= SEQUENCE {
   trkUnAckedFramerNormPrioLinkUtilToIf
      Gauge32,
   trkUnAckedFramerHighPrioLinkUtilToIf
      Gauge32,
   trkUnAckedFramerNormPrioLinkUtilFromIf
      Gauge32,
   trkUnAckedFramerHighPrioLinkUtilFromIf
      Gauge32 }

trkUnAckedFramerNormPrioLinkUtilToIf OBJECT-TYPE
   SYNTAX     Gauge32 (0..100)
   ACCESS     read-only
   STATUS     mandatory
   DESCRIPTION
     "This attribute is the utilization of the normal and high priority data 
      traffic (interruptable traffic) sent to the link as a percentage of the 
      available bandwidth on the link. Note that this includes traffic with 
      Transfer Priorities (TP) of 0, 6 and 9 and/or Emission Priority of 2 
      and 3. The utilization is the average for the last minute."
   DEFVAL     { 0 }
::= { trkUnAckedFramerUtilEntry 1 }

trkUnAckedFramerHighPrioLinkUtilToIf OBJECT-TYPE
   SYNTAX     Gauge32 (0..100)
   ACCESS     read-only
   STATUS     mandatory
   DESCRIPTION
     "This attribute is the utilization of the interrupting priority data traffic 
      sent to the link as a percentage of the available bandwidth on the 
      link. Note that this includes traffic with a Transfer Priority (TP) of 
      11 and/or Emission Priority of 1. The utilization is the average for 
      the last minute."
   DEFVAL     { 0 }
::= { trkUnAckedFramerUtilEntry 2 }

trkUnAckedFramerNormPrioLinkUtilFromIf OBJECT-TYPE
   SYNTAX     Gauge32 (0..100)
   ACCESS     read-only
   STATUS     mandatory
   DESCRIPTION
     "This attribute is the utilization of the normal and high priority data 
      traffic (interruptable traffic) received from the link as a percentage 
      of the available bandwidth on the link. Note that this includes traffic 
      with Transfer Priorities (TP) of 0, 6 and 9 and/or Emission Priority 
      of 2 and 3. The utilization is the average for the last minute."
   DEFVAL     { 0 }
::= { trkUnAckedFramerUtilEntry 3 }

trkUnAckedFramerHighPrioLinkUtilFromIf OBJECT-TYPE
   SYNTAX     Gauge32 (0..100)
   ACCESS     read-only
   STATUS     mandatory
   DESCRIPTION
     "This attribute is the utilization of the interrupting priority data 
      (interrupting traffic) received from the link as a percentage of the 
      available bandwidth on the link. Note that this includes traffic with 
      a Transfer Priority (TP) of 11 and/or Emission Priority of 1. The 
      utilization is the average for the last minute."
   DEFVAL     { 0 }
::= { trkUnAckedFramerUtilEntry 4 }

trkUnAckedFramerUtilThresholdTable OBJECT-TYPE
   SYNTAX     SEQUENCE OF TrkUnAckedFramerUtilThresholdEntry
   ACCESS     not-accessible
   STATUS     mandatory
   DESCRIPTION
     "This group contains all of the provisioning data required to set the 
      link utilization alarm thresholds. All thresholds are percentages 
      which can take on any value in the range of 0% through 100%. The 
      value 100% is used to disable an individual threshold. For values 
      other than 100%, a semantic check ensures that the minor alarm 
      threshold is less than the other thresholds and that the major alarm 
      threshold is less than the critical alarm threshold."
::= { trkUnAckedFramer 15 }

trkUnAckedFramerUtilThresholdEntry OBJECT-TYPE
   SYNTAX     TrkUnAckedFramerUtilThresholdEntry
   ACCESS     not-accessible
   STATUS     mandatory
   DESCRIPTION
     "An entry in the trkUnAckedFramerUtilThresholdTable."
   INDEX {
      trkIndex,
      trkUnAckedIndex,
      trkUnAckedFramerIndex }
::= { trkUnAckedFramerUtilThresholdTable 1 }

TrkUnAckedFramerUtilThresholdEntry ::= SEQUENCE {
   trkUnAckedFramerMinorLinkUtilAlarmThreshold
      Unsigned32,
   trkUnAckedFramerMajorLinkUtilAlarmThreshold
      Unsigned32,
   trkUnAckedFramerCriticalLinkUtilAlarmThreshold
      Unsigned32,
   trkUnAckedFramerLinkUtilAlarmStatus
      INTEGER }

trkUnAckedFramerMinorLinkUtilAlarmThreshold OBJECT-TYPE
   SYNTAX     Unsigned32 (0..100)
   ACCESS     read-write
   STATUS     mandatory
   DESCRIPTION
     "This attribute provides the threshold value which defines when a 
      minor alarm would be issued, denoting a sustained total average 
      link utilization. The total average link utilization is calculated based 
      on the number of received bytes. The Set alarm is issued after 3 
      minutes of utilization greater than the given threshold. The 
      corresponding Clear alarm is issued after a subsequent 3 minutes of 
      utilization less than or equal to the given threshold.
      The value 100% is used to disable an individual threshold. For 
      values other than 100%, a semantic check ensures that the minor 
      alarm threshold is less than the other thresholds."
   DEFVAL     { 75 }
::= { trkUnAckedFramerUtilThresholdEntry 1 }

trkUnAckedFramerMajorLinkUtilAlarmThreshold OBJECT-TYPE
   SYNTAX     Unsigned32 (0..100)
   ACCESS     read-write
   STATUS     mandatory
   DESCRIPTION
     "This attribute provides the threshold value which defines when a 
      major alarm would be issued, denoting a sustained total average 
      link utilization. The total average link utilization is calculated based 
      on the number of received bytes. The Set alarm is issued after 3 
      minutes of utilization greater than the given threshold. The 
      corresponding Clear alarm is issued after a subsequent 3 minutes of 
      utilization less than or equal to the given threshold.
      The value 100% is used to disable an individual threshold. For 
      values other than 100%, a semantic check ensures that the major 
      alarm threshold is greater than the minor threshold and less than the 
      critical threshold."
   DEFVAL     { 85 }
::= { trkUnAckedFramerUtilThresholdEntry 2 }

trkUnAckedFramerCriticalLinkUtilAlarmThreshold OBJECT-TYPE
   SYNTAX     Unsigned32 (0..100)
   ACCESS     read-write
   STATUS     mandatory
   DESCRIPTION
     "This attribute provides the threshold value which defines when a 
      critical alarm would be issued, denoting a sustained total average 
      link utilization. The total average link utilization is calculated based 
      on the number of received bytes. The Set alarm is issued after 3 
      minutes of utilization greater than the given threshold. The 
      corresponding Clear alarm is issued after a subsequent 3 minutes of 
      utilization less than or equal to the given threshold.
      The value 100% is used to disable an individual threshold. For 
      values other than 100%, a semantic check ensures that the critical 
      alarm threshold is greater than the other thresholds."
   DEFVAL     { 95 }
::= { trkUnAckedFramerUtilThresholdEntry 3 }

trkUnAckedFramerLinkUtilAlarmStatus OBJECT-TYPE
   SYNTAX     INTEGER  {
                 disabled(0),
                 enabled(1) }
   ACCESS     read-write
   STATUS     mandatory
   DESCRIPTION
     "This attribute provides control of the generation of link utilization 
      alarms. If the value is disabled, none of the alarms are generated 
      (this is equivalent to setting all of the thresholds to 100%). If the 
      value is enabled, the individual thresholds are handled."
   DEFVAL     { disabled }
::= { trkUnAckedFramerUtilThresholdEntry 4 }




-- 
-- Version and Compliance statements
-- 



-- Object-Group Statement:
-- A list of all current accessible leaf objects.

-- OBJECTS { trkUnAckedComponentName,
--           trkUnAckedStandbyStatus,
--           trkUnAckedFramerOutOfSequenceFrm,
--           trkUnAckedFramerFramingType,
--           trkUnAckedFramerDataInversion,
--           trkUnAckedFramerFlagsBetweenFrames,
--           trkUnAckedStorageType,
--           trkUnAckedFramerOperationalState,
--           trkUnAckedFramerMajorLinkUtilAlarmThreshold,
--           trkUnAckedFramerHighPrioLinkUtilFromIf,
--           trkUnAckedFramerOctetFromIf,
--           trkUnAckedFramerRepeatedFrm,
--           trkUnAckedOperationalState,
--           trkUnAckedFramerFrmModeErrors,
--           trkUnAckedUnknownStatus,
--           trkUnAckedAlarmStatus,
--           trkUnAckedFramerFrameCrcType,
--           trkUnAckedFramerAdminState,
--           trkUnAckedMaximumErroredInterval,
--           trkUnAckedFramerLrcErrors,
--           trkUnAckedFramerLargeFrmErrors,
--           trkUnAckedControlStatus,
--           trkUnAckedAdminState,
--           trkUnAckedFramerStorageType,
--           trkUnAckedFramerRowStatus,
--           trkUnAckedFramerAborts,
--           trkUnAckedFramerLinkUtilAlarmStatus,
--           trkUnAckedRowStatus,
--           trkUnAckedFramerOverruns,
--           trkUnAckedFramerNormPrioLinkUtilToIf,
--           trkUnAckedProceduralStatus,
--           trkUnAckedFramerMinorLinkUtilAlarmThreshold,
--           trkUnAckedAvailabilityStatus,
--           trkUnAckedFramerNonOctetErrors,
--           trkUnAckedReceiveErrorSensitivity,
--           trkUnAckedFramerUsageState,
--           trkUnAckedFramerHighPrioLinkUtilToIf,
--           trkUnAckedFramerCrcErrors,
--           trkUnAckedFramerNormPrioLinkUtilFromIf,
--           trkUnAckedFramerCriticalLinkUtilAlarmThreshold,
--           trkUnAckedFramerUnderruns,
--           trkUnAckedFramerComponentName,
--           trkUnAckedUsageState,
--           trkUnAckedFramerFrmFromIf,
--           trkUnAckedFramerInterfaceName }
-- STATUS  mandatory
-- DESCRIPTION
--   "A list of all current accessible leaf objects."

unackTrunksGroup OBJECT IDENTIFIER ::= { unackTrunksMIB 1 }
unackTrunksGroupBE OBJECT IDENTIFIER ::= { unackTrunksGroup 5 }
unackTrunksGroupBE00 OBJECT IDENTIFIER ::= { unackTrunksGroupBE 1 }
unackTrunksGroupBE00A OBJECT IDENTIFIER ::= { unackTrunksGroupBE00 2 }



-- Agent-Capabilities Statement:

-- PRODUCT-RELEASE "Passport Release 7.0 UnackTrunks."
-- STATUS          mandatory
-- DESCRIPTION     "UnackTrunks MIB: MIB Version BE00A,
--                  Software Version BG00S4C."
-- SUPPORTS        Nortel-Magellan-Passport-UnackTrunksMIB
--    INCLUDES     { unackTrunksGroupBE00A }

unackTrunksCapabilities OBJECT IDENTIFIER ::= { unackTrunksMIB 3 }
unackTrunksCapabilitiesBE OBJECT IDENTIFIER ::= { unackTrunksCapabilities 5 }
unackTrunksCapabilitiesBE00 OBJECT IDENTIFIER ::= { unackTrunksCapabilitiesBE 1 }
unackTrunksCapabilitiesBE00A OBJECT IDENTIFIER ::= { unackTrunksCapabilitiesBE00 2 }





END
