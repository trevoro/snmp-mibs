ASYNC-MIB DEFINITIONS ::= BEGIN

-- Copyright (C) 1997 Intel Corporation. All rights reserved.
--
-- Intel Async MIB, 11-04-1997
-- This MIB provides objects that describes
-- asynchronous PC Card (PCMCIA) interfaces
--
-- Change History:
-- <date> <change>
--

IMPORTS
    Counter             FROM RFC1155-SMI
    scanet              FROM SCANET-MIB
    OBJECT-TYPE         FROM RFC-1212;


  async             OBJECT IDENTIFIER ::= { scanet 45 }
  asyncConfig       OBJECT IDENTIFIER ::= { async 1 }
  asyncMon          OBJECT IDENTIFIER ::= { async 2 }
  asyncPcmcia       OBJECT IDENTIFIER ::= { async 3 }


asyncConfigTable OBJECT-TYPE
    SYNTAX SEQUENCE OF AsyncConfigEntry
    ACCESS not-accessible
    STATUS mandatory
    DESCRIPTION "A list of configuration entries. Each entry contains
                 the configuration of a PCMCIA interface when this
                 is used with an asynchronous modem."
    ::= { asyncConfig 1 }

asyncConfigEntry OBJECT-TYPE
    SYNTAX AsyncConfigEntry
    ACCESS not-accessible
    STATUS mandatory
    DESCRIPTION "Every configuration option available for the PC-Card
                 modem driver."
    INDEX { asyncConfigIndex }
    ::= { asyncConfigTable 1 }

AsyncConfigEntry ::= SEQUENCE {
                        asyncConfigIndex
                           INTEGER,
                        asyncConfigDialMode
                           INTEGER,
                        asyncConfigAutoInit
                           INTEGER,
                        asyncConfigDialString
                           OCTET STRING,
                        asyncConfigInitString1
                           OCTET STRING,
                        asyncConfigInitString2
                           OCTET STRING
                        }

asyncConfigIndex OBJECT-TYPE
    SYNTAX INTEGER
    ACCESS read-only
    STATUS mandatory
    DESCRIPTION "The ifIndex for the modem interface."
    ::= { asyncConfigEntry 1 }

asyncConfigDialMode OBJECT-TYPE
    SYNTAX INTEGER { tone(1), pulse(2) }
    ACCESS read-write
    STATUS mandatory
    DESCRIPTION "The dialing mode. Note that the pulse mode may not
                 be compatible with all countries unless advanced
                 country information is setup with the init strings."
    ::= { asyncConfigEntry 2 }

asyncConfigAutoInit OBJECT-TYPE
    SYNTAX INTEGER { enabled(1), disabled(2)}
    ACCESS read-write
    STATUS mandatory
    DESCRIPTION "When auto-init is enabled the modem brand is detected
                 and a predefined init string suited to the modem is
                 used. When auto-init is disabled the user editable init
                 string is used."
    ::= { asyncConfigEntry 3 }

asyncConfigDialString OBJECT-TYPE
    SYNTAX OCTET STRING (SIZE(40))
    ACCESS read-write
    STATUS mandatory
    DESCRIPTION "The phone number to dial, with special characters
                 to control the dialing, like pauses and waits for
                 new dial tones. The special characters may vary
                 amongst the modem brands."
    ::= { asyncConfigEntry 4 }

asyncConfigInitString1 OBJECT-TYPE
    SYNTAX OCTET STRING (SIZE(40))
    ACCESS read-write
    STATUS mandatory
    DESCRIPTION "The first half of the user-editable init string. The
                 two init strings are combined before use."
    ::= { asyncConfigEntry 5 }

asyncConfigInitString2 OBJECT-TYPE
    SYNTAX OCTET STRING (SIZE(40))
    ACCESS read-write
    STATUS mandatory
    DESCRIPTION "The second half of the user-editable init string."
    ::= { asyncConfigEntry 6 }

asyncMonTable OBJECT-TYPE
    SYNTAX SEQUENCE OF AsyncMonEntry
    ACCESS not-accessible
    STATUS mandatory
    DESCRIPTION "A list of monitor entries. Each entry contains
                 the monitorable data of a PCMCIA interface when
                 this is used with an asynchronous modem."
    ::= { asyncMon 1 }

asyncMonEntry OBJECT-TYPE
    SYNTAX AsyncMonEntry
    ACCESS not-accessible
    STATUS mandatory
    DESCRIPTION "Every value that can be monitored for the PCMCIA
                 interface."
    INDEX { asyncMonIndex }
    ::= { asyncMonTable 1 }

AsyncMonEntry ::= SEQUENCE {
                        asyncMonIndex
                           INTEGER,
                        asyncMonMode
                           INTEGER,
                        asyncMonTransmitFailedErrors
                           Counter,
                        asyncMonTransmitCongestions
                           Counter,
                        asyncMonReceiveLostEndMarkers
                           Counter,
                        asyncMonReceiveOverflows
                           Counter,
                        asyncMonReceiveStuffingErrors
                           Counter,
                        asyncMonReceiveCRCErrors
                           Counter,
                        asyncMonReceiveShortPackets
                           Counter,
                        asyncMonReceiveLongPackets
                           Counter,
                        asyncMonReceiveUartOverrunErrors
                           Counter,
                        asyncMonReceiveUartParityErrors
                           Counter,
                        asyncMonReceiveUartFramingErrors
                           Counter,
                        asyncMonReceiveUartBreakErrors
                           Counter,
                        asyncMonCallDirection
                           INTEGER
                        }

asyncMonIndex OBJECT-TYPE
    SYNTAX INTEGER
    ACCESS read-only
    STATUS mandatory
    DESCRIPTION "The ifIndex for the modem interface."
    ::= { asyncMonEntry 1 }

asyncMonMode OBJECT-TYPE
    SYNTAX INTEGER {
             noConfiguration(1),
             noValidModem(2),
             initializingModem(3),
             resettingModem(4),
             waitingForResetAck(5),
             hangingUp(6),
             waitingForHangupAck(7),
             standBy(8),
             acceptingCall(9),
             connected(10),
             reserved(11),
             dialing(12),
             waitingForAnswer(13),
             other(14)
        }

    ACCESS read-only
    STATUS mandatory
    DESCRIPTION "The current internal state of the modem driver."
    ::= { asyncMonEntry 2 }

asyncMonTransmitFailedErrors OBJECT-TYPE
    SYNTAX Counter
    ACCESS read-only
    STATUS mandatory
    DESCRIPTION "The number of aborted packet transmits due to a
                 disconnect while packets were queued for
                 transmission."
    ::= { asyncMonEntry 3 }

asyncMonTransmitCongestions OBJECT-TYPE
    SYNTAX Counter
    ACCESS read-only
    STATUS mandatory
    DESCRIPTION "The number of packet transmissions that failed due
                 to lack of resources."
    ::= { asyncMonEntry 4 }

asyncMonReceiveLostEndMarkers OBJECT-TYPE
    SYNTAX Counter
    ACCESS read-only
    STATUS mandatory
    DESCRIPTION "The number of packets discarded because the
                 packet end signature was missing."
    ::= { asyncMonEntry 5 }

asyncMonReceiveOverflows OBJECT-TYPE
    SYNTAX Counter
    ACCESS read-only
    STATUS mandatory
    DESCRIPTION "The number of packets discarded due to lack of
                 free receive buffers."
    ::= { asyncMonEntry 6 }

asyncMonReceiveStuffingErrors OBJECT-TYPE
    SYNTAX Counter
    ACCESS read-only
    STATUS mandatory
    DESCRIPTION "In data transmissions via an asynchrounous modem,
                 certain characters are reserved for use with the
                 modem, e.g. to indicate the start and end of data
                 packets. If these reserved characters occur in the
                 data stream, an 'Escape character' followed by a
                 'Substitute character' are used to represent it.
                 This is known as stuffing. This parameter shows
                 the number of packets discarded due to illegal
                 combinations of the Escape character with
                 Substitute characters."
    ::= { asyncMonEntry 7 }

asyncMonReceiveCRCErrors OBJECT-TYPE
    SYNTAX Counter
    ACCESS read-only
    STATUS mandatory
    DESCRIPTION "The number of packets discarded due to errors
                 in the packet detected using the packet checksum."
    ::= { asyncMonEntry 8 }

asyncMonReceiveShortPackets OBJECT-TYPE
    SYNTAX Counter
    ACCESS read-only
    STATUS mandatory
    DESCRIPTION "The number of packets discarded because the packets
                 were shorter than the minimum legal packet length."
    ::= { asyncMonEntry 9 }

asyncMonReceiveLongPackets OBJECT-TYPE
    SYNTAX Counter
    ACCESS read-only
    STATUS mandatory
    DESCRIPTION "The number of packets discarded because the packets
                 were larger than the maximum legal packet length."
    ::= { asyncMonEntry 10 }

asyncMonReceiveUartOverrunErrors OBJECT-TYPE
    SYNTAX Counter
    ACCESS read-only
    STATUS mandatory
    DESCRIPTION "The number of packets discarded because the
                 incoming data exceeded the receive buffer size
                 in the UART."
    ::= { asyncMonEntry 11 }

asyncMonReceiveUartParityErrors OBJECT-TYPE
    SYNTAX Counter
    ACCESS read-only
    STATUS mandatory
    DESCRIPTION "The number of packets discarded because of errors
                 in the packet detected using the parity bit."
    ::= { asyncMonEntry 12 }

asyncMonReceiveUartFramingErrors OBJECT-TYPE
    SYNTAX Counter
    ACCESS read-only
    STATUS mandatory
    DESCRIPTION "The number of packets discarded because of errors
                 during receiving the bit stream."
    ::= { asyncMonEntry 13 }

asyncMonReceiveUartBreakErrors OBJECT-TYPE
    SYNTAX Counter
    ACCESS read-only
    STATUS mandatory
    DESCRIPTION "The number of packets discarded because of a
                 temporary loss of the received data flow."
    ::= { asyncMonEntry 14 }

asyncMonCallDirection OBJECT-TYPE
    SYNTAX INTEGER { incoming(1), outgoing(2), none(3) }
    ACCESS read-only
    STATUS mandatory
    DESCRIPTION "Direction of the current call."
    ::= { asyncMonEntry 15 }




asyncPcmciaTable OBJECT-TYPE
    SYNTAX SEQUENCE OF AsyncPcmciaEntry
    ACCESS not-accessible
    STATUS mandatory
    DESCRIPTION "A list of PC-Card (PCMCIA) information entries.
                 Each entry contains the information available from
                 the modems PCMCIA-interface."
    ::= { asyncPcmcia 1 }

asyncPcmciaEntry OBJECT-TYPE
    SYNTAX AsyncPcmciaEntry
    ACCESS not-accessible
    STATUS mandatory
    DESCRIPTION ""
    INDEX { asyncPcmciaIndex }
    ::= { asyncPcmciaTable 1 }

AsyncPcmciaEntry ::= SEQUENCE {
                        asyncPcmciaIndex
                           INTEGER,
                        asyncPcmciaManufacturerName
                           OCTET STRING,
                        asyncPcmciaProductName
                           OCTET STRING,
                        asyncPcmciaProductVersionMajor
                           INTEGER,
                        asyncPcmciaProductVersionMinor
                           INTEGER,
                        asyncPcmciaPcmciaSupported
                           INTEGER
                        }

asyncPcmciaIndex OBJECT-TYPE
    SYNTAX INTEGER
    ACCESS read-only
    STATUS mandatory
    DESCRIPTION "The ifIndex for the modem interface."
    ::= { asyncPcmciaEntry 1 }

asyncPcmciaManufacturerName OBJECT-TYPE
    SYNTAX OCTET STRING (SIZE(100))
    ACCESS read-only
    STATUS mandatory
    DESCRIPTION "The company name of the modem manufacturer."
    ::= { asyncPcmciaEntry 2 }

asyncPcmciaProductName OBJECT-TYPE
    SYNTAX OCTET STRING (SIZE(100))
    ACCESS read-only
    STATUS mandatory
    DESCRIPTION "The brand name of the modem."
    ::= { asyncPcmciaEntry 3 }

asyncPcmciaProductVersionMajor OBJECT-TYPE
    SYNTAX INTEGER
    ACCESS read-only
    STATUS mandatory
    DESCRIPTION "The modem hardware major version number."
    ::= { asyncPcmciaEntry 4 }

asyncPcmciaProductVersionMinor OBJECT-TYPE
    SYNTAX INTEGER
    ACCESS read-only
    STATUS mandatory
    DESCRIPTION "The modem hardware minor version number."
    ::= { asyncPcmciaEntry 5 }

asyncPcmciaPcmciaSupported OBJECT-TYPE
    SYNTAX INTEGER { yes(1), no(2) }
    ACCESS read-only
    STATUS mandatory
    DESCRIPTION "This value is yes when the modem can be used with
                 the router."
    ::= { asyncPcmciaEntry 6 }

END
