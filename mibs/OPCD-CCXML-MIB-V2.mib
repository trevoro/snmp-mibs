--
-- OPCD-CCXML-MIB-V2
-- Last Modified: Monday, August 08, 2005
--


OPCD-CCXML-MIB-V2 DEFINITIONS ::= BEGIN


--  OPCD-CCXML-MIB:
--    A private enterprise mib for Opencode CCXML Browser application.


IMPORTS
	MODULE-IDENTITY, OBJECT-TYPE, NOTIFICATION-TYPE, enterprises	FROM SNMPv2-SMI
	DisplayString							FROM SNMPv2-TC
	opencode-systems 					      	FROM OPCD-SUPPORT-MIB-V2;




--  opencode ccxml  branch: 30374.12
--  opencode ccxml traps branch: 30374.12.1



  occcxml		OBJECT IDENTIFIER ::= { opencode-systems 12 }
  occcxml-traps		OBJECT IDENTIFIER ::= { occcxml 1 }

  definitions 		OBJECT IDENTIFIER ::= { occcxml-traps 0 }
  vars	 		OBJECT IDENTIFIER ::= { occcxml-traps 1 }
--
--


mcr-Host OBJECT-TYPE
	SYNTAX DisplayString (SIZE (0..255))
	MAX-ACCESS accessible-for-notify
	STATUS current
	DESCRIPTION
		"String containing hostname of fault node."
	::= { vars 1 }


mcr-Severity OBJECT-TYPE
	SYNTAX INTEGER{
		critical(1),
		major(2),
		minor(3),
		normal(4),
		warning(5)
	}
	MAX-ACCESS accessible-for-notify
	STATUS mandatory
	DESCRIPTION
		"Alarm severity."
	::= { vars 2 }


mcr-Text OBJECT-TYPE
	SYNTAX DisplayString (SIZE (0..255))
	MAX-ACCESS accessible-for-notify
	STATUS current
	DESCRIPTION
		"String containing text of the alarm."
	::= { vars 3 }


--
-- Traps
--
-----------------------------------------------------------------------------------------------


------------------------------------------------------------------------------------------


-- 1.3.6......0.2
occcxml-Crash NOTIFICATION-TYPE
	OBJECTS	{ mcr-Host, mcr-Severity, mcr-Text}	
	STATUS	current
	DESCRIPTION	"CCXML Browser crashed and was restarted by watch dog."
	--#SUMMARY   "Alarm on host: $1 (ccxml applications) :  $3"
	--#CATEGORY  "Error Alarms"
        --#ARGUMENTS {}
        --#SEVERITY  MAJOR
	::= { definitions 2 }

-- 1.3.6......0.3
occcxml-Crash-Canceled NOTIFICATION-TYPE
	OBJECTS	{ mcr-Host, mcr-Severity, mcr-Text}	
		STATUS	current
	DESCRIPTION	"CCXML Browser crashed -Canceled"
	--#SUMMARY   "Alarm on host: $1 (ccxml applications) :  $3"
	--#CATEGORY  "Error Alarms"
        --#ARGUMENTS {}
        --#SEVERITY  NORMAL
	::= { definitions 3 }



-- 1.3.6......0.4
occcxml-ipc-ISUPGW-ConnProblem NOTIFICATION-TYPE
	OBJECTS	{ mcr-Host, mcr-Severity, mcr-Text}	
	STATUS	current
	DESCRIPTION	"CCXML Browser ISUP Gateway connection problem."
	--#SUMMARY   "Alarm on host: $1 (ccxml applications) :  $3"
	--#CATEGORY  "Error Alarms"
        --#ARGUMENTS {}
        --#SEVERITY  CRITICAL
	::= { definitions 4 }


-- 1.3.6......0.5
occcxml-ipc-ISUPGW-ConnProblem-Canceled NOTIFICATION-TYPE
	OBJECTS	{ mcr-Host, mcr-Severity, mcr-Text}	
	STATUS	current
	DESCRIPTION	"CCXML Browser ISUP Gateway connection problem-Canceled"
	--#SUMMARY   "Alarm on host: $1 (ccxml applications) :  $3"
	--#CATEGORY  "Error Alarms"
        --#ARGUMENTS {}
        --#SEVERITY  NORMAL
	::= { definitions 5 }


-- 1.3.6......0.6
occcxml-ipc-MEDIAGW-ConnProblem NOTIFICATION-TYPE
	OBJECTS	{ mcr-Host, mcr-Severity, mcr-Text}	
	STATUS	current
	DESCRIPTION	"CCXML Browser MEDIA Gateway connection problem."
	--#SUMMARY   "Alarm on host: $1 (ccxml applications) :  $3"
	--#CATEGORY  "Error Alarms"
        --#ARGUMENTS {}
        --#SEVERITY  CRITICAL
	::= { definitions 6 }


-- 1.3.6......0.7
occcxml-ipc-MEDIAGW-ConnProblem-Canceled NOTIFICATION-TYPE
	OBJECTS	{ mcr-Host, mcr-Severity, mcr-Text}	
	STATUS	current
	DESCRIPTION	"CCXML Browser MEDIA Gateway connection problem-Canceled"
	--#SUMMARY   "Alarm on host: $1 (ccxml applications) :  $3"
	--#CATEGORY  "Error Alarms"
        --#ARGUMENTS {}
        --#SEVERITY  NORMAL
	::= { definitions 7 }


-- 1.3.6......0.8
occcxml-ipc-VXML-ConnProblem NOTIFICATION-TYPE
	OBJECTS	{ mcr-Host, mcr-Severity, mcr-Text}	
	STATUS	current
	DESCRIPTION  "CCXML Browser VMXL connection problem."
	--#SUMMARY   "Alarm on host: $1 (ccxml applications) :  $3"
	--#CATEGORY  "Error Alarms"
        --#ARGUMENTS {}
        --#SEVERITY  CRITICAL
	::= { definitions 8 }


-- 1.3.6......0.9
occcxml-ipc-VXML-ConnProblem-Canceled NOTIFICATION-TYPE
	OBJECTS	{ mcr-Host, mcr-Severity, mcr-Text}	
	STATUS	current
	DESCRIPTION  "CCXML Browser VMXL connection problem-Canceled"
	--#SUMMARY   "Alarm on host: $1 (ccxml applications) :  $3"
	--#CATEGORY  "Error Alarms"
        --#ARGUMENTS {}
        --#SEVERITY  NORMAL
	::= { definitions 9 }


-- 1.3.6......0.10
occcxml-ipc-USSDBR-ConnProblem NOTIFICATION-TYPE
	OBJECTS	{ mcr-Host, mcr-Severity, mcr-Text}	
	STATUS	current
	DESCRIPTION  "CCXML Browser USSD Browser connection problem."
	--#SUMMARY   "Alarm on host: $1 (ccxml applications) :  $3"
	--#CATEGORY  "Error Alarms"
        --#ARGUMENTS {}
        --#SEVERITY  CRITICAL
	::= { definitions 10 }

-- 1.3.6......0.11
occcxml-ipc-USSDBR-ConnProblem-Canceled NOTIFICATION-TYPE
	OBJECTS	{ mcr-Host, mcr-Severity, mcr-Text}	
	STATUS	current
	DESCRIPTION  "CCXML Browser USSD Browser connection problem-Canceled"
	--#SUMMARY   "Alarm on host: $1 (ccxml applications) :  $3"
	--#CATEGORY  "Error Alarms"
        --#ARGUMENTS {}
        --#SEVERITY  NORMAL
	::= { definitions 11 }



-- 1.3.6......0.12
occcxml-Loading-plugin-Failed NOTIFICATION-TYPE
	OBJECTS	{ mcr-Host, mcr-Severity, mcr-Text}	
	STATUS	current
	DESCRIPTION  "CCXML Browser loading plugin failed."
	--#SUMMARY   "Alarm on host: $1 (ccxml applications) :  $3"
	--#CATEGORY  "Error Alarms"
        --#ARGUMENTS {}
        --#SEVERITY  CRITICAL
	::= { definitions 12 }

-- 1.3.6......0.13
occcxml-Loading-plugin-Failed-Canceled NOTIFICATION-TYPE
	OBJECTS	{ mcr-Host, mcr-Severity, mcr-Text}	
	STATUS	current
	DESCRIPTION  "CCXML Browser loading plugin failed-Canceled"
	--#SUMMARY   "Alarm on host: $1 (ccxml applications) :  $3"
	--#CATEGORY  "Error Alarms"
        --#ARGUMENTS {}
        --#SEVERITY  NORMAL
	::= { definitions 13 }


-- 1.3.6......0.14
occcxml-CDRSubsys-Problem NOTIFICATION-TYPE
	OBJECTS	{ mcr-Host, mcr-Severity, mcr-Text}	
	    STATUS  current
        DESCRIPTION  "Problem with cdr subsystem."
        --#SUMMARY   "Alarm on host: $1 (ccxml applications) :  $3"
        --#CATEGORY  "Error Alarms"
        --#ARGUMENTS {}
        --#SEVERITY  CRITICAL
        ::= { definitions 14 }

-- 1.3.6......0.15
occcxml-CDRSubsys-Problem-Canceled NOTIFICATION-TYPE
	OBJECTS	{ mcr-Host, mcr-Severity, mcr-Text}	
	    STATUS  current
        DESCRIPTION  "Problem with cdr subsystem-Canceled"
        --#SUMMARY   "Alarm on host: $1 (ccxml applications) :  $3"
        --#CATEGORY  "Error Alarms"
        --#ARGUMENTS {}
        --#SEVERITY  NORMAL
        ::= { definitions 15 }


END


--
-- OPCD-CCXML-MIB-V2
--
