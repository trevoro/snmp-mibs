--			Ascend mibhdsl2 MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBHDSL2-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibhdsl2DslLineStatus  OBJECT IDENTIFIER ::= { configuration 159}

	-- The mibhdsl2DslLineStatus table
	--
	-- This table contains parameters for the mibhdsl2DslLineStatus profile
	--

    mibhdsl2DslLineStatusTable	OBJECT-TYPE
	SYNTAX		SEQUENCE OF Mibhdsl2DslLineStatusEntry
	ACCESS		not-accessible
	STATUS		mandatory
	DESCRIPTION	"A list of mibhdsl2DslLineStatus profile entries."
	::= { mibhdsl2DslLineStatus 1 }

    mibhdsl2DslLineStatusEntry	OBJECT-TYPE
	SYNTAX		Mibhdsl2DslLineStatusEntry
	ACCESS		not-accessible
	STATUS		mandatory
	DESCRIPTION	"A mibhdsl2DslLineStatus entry containing objects that
			 maps to the parameters of mibhdsl2DslLineStatus profile."
	INDEX		{ hdsl2DslLineStatus-Shelf-o, hdsl2DslLineStatus-Slot-o, hdsl2DslLineStatus-Item-o }
	::= { mibhdsl2DslLineStatusTable 1 }

    Mibhdsl2DslLineStatusEntry ::=
	SEQUENCE {
	    hdsl2DslLineStatus-Shelf-o
		INTEGER,
	    hdsl2DslLineStatus-Slot-o
		INTEGER,
	    hdsl2DslLineStatus-Item-o
		INTEGER,
	    hdsl2DslLineStatus-PhysicalAddress-Shelf
		INTEGER,
	    hdsl2DslLineStatus-PhysicalAddress-Slot
		INTEGER,
	    hdsl2DslLineStatus-PhysicalAddress-ItemNumber
		INTEGER,
	    hdsl2DslLineStatus-LineState
		INTEGER,
	    hdsl2DslLineStatus-SparePhysicalAddress-Shelf
		INTEGER,
	    hdsl2DslLineStatus-SparePhysicalAddress-Slot
		INTEGER,
	    hdsl2DslLineStatus-SparePhysicalAddress-ItemNumber
		INTEGER,
	    hdsl2DslLineStatus-SparingState
		INTEGER,
	    hdsl2DslLineStatus-SparingChangeReason
		INTEGER,
	    hdsl2DslLineStatus-SparingChangeTime
		INTEGER,
	    hdsl2DslLineStatus-SparingChangeCounter
		INTEGER,
	    hdsl2DslLineStatus-VpiVciRange
		INTEGER,
	    hdsl2DslLineStatus-VpSwitchingVpi
		INTEGER,
	    hdsl2DslLineStatus-PhysicalStatus-IfGroupIndex
		INTEGER,
	    hdsl2DslLineStatus-PhysicalStatus-UnitType
		INTEGER,
	    hdsl2DslLineStatus-PhysicalStatus-InterfaceType
		INTEGER,
	    hdsl2DslLineStatus-PhysicalStatus-DevLineState
		INTEGER,
	    hdsl2DslLineStatus-PhysicalStatus-OperationalRate
		INTEGER,
	    hdsl2DslLineStatus-PhysicalStatus-FirmwareVer
		DisplayString,
	    hdsl2DslLineStatus-PhysicalStatus-HardwareVer
		INTEGER,
	    hdsl2DslLineStatus-PhysicalStatus-NetworkType
		INTEGER,
	    hdsl2DslLineStatus-PhysicalStatistic-LineUpTimer-Days
		INTEGER,
	    hdsl2DslLineStatus-PhysicalStatistic-LineUpTimer-Hours
		INTEGER,
	    hdsl2DslLineStatus-PhysicalStatistic-LineUpTimer-Minutes
		INTEGER,
	    hdsl2DslLineStatus-PhysicalStatistic-RxSignalPresent
		INTEGER,
	    hdsl2DslLineStatus-PhysicalStatistic-LineQuality
		INTEGER,
	    hdsl2DslLineStatus-PhysicalStatistic-UpDwnCntr
		INTEGER,
	    hdsl2DslLineStatus-PhysicalStatistic-SelfTest
		INTEGER,
	    hdsl2DslLineStatus-PhysicalStatistic-TransmitPower
		INTEGER,
	    hdsl2DslLineStatus-PhysicalStatistic-FramerSyncStatus
		INTEGER,
	    hdsl2DslLineStatus-PhysicalStatistic-CodeViolations
		INTEGER,
	    hdsl2DslLineStatus-PhysicalStatistic-ErroredSecond
		INTEGER,
	    hdsl2DslLineStatus-PhysicalStatistic-SeverelyErroredSecond
		INTEGER,
	    hdsl2DslLineStatus-PhysicalStatistic-LoswSecond
		INTEGER,
	    hdsl2DslLineStatus-PhysicalStatistic-UnavailableSecond
		INTEGER,
	    hdsl2DslLineStatus-PhysicalStatistic-LoopAttenuation
		INTEGER,
	    hdsl2DslLineStatus-PhysicalStatistic-Snr
		INTEGER,
	    hdsl2DslLineStatus-PhysicalStatistic-SturLoopAttenuation
		INTEGER,
	    hdsl2DslLineStatus-PhysicalStatistic-SturSnr
		INTEGER,
	    hdsl2DslLineStatus-Action-o
		INTEGER
	}

    hdsl2DslLineStatus-Shelf-o	OBJECT-TYPE
	SYNTAX	INTEGER
	ACCESS	read-only
	STATUS	mandatory
	DESCRIPTION	""
	::= { mibhdsl2DslLineStatusEntry 1 }

    hdsl2DslLineStatus-Slot-o	OBJECT-TYPE
	SYNTAX	INTEGER
	ACCESS	read-only
	STATUS	mandatory
	DESCRIPTION	""
	::= { mibhdsl2DslLineStatusEntry 2 }

    hdsl2DslLineStatus-Item-o	OBJECT-TYPE
	SYNTAX	INTEGER
	ACCESS	read-only
	STATUS	mandatory
	DESCRIPTION	""
	::= { mibhdsl2DslLineStatusEntry 3 }

    hdsl2DslLineStatus-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibhdsl2DslLineStatusEntry 4 }

    hdsl2DslLineStatus-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibhdsl2DslLineStatusEntry 5 }

    hdsl2DslLineStatus-PhysicalAddress-ItemNumber	OBJECT-TYPE
	SYNTAX	INTEGER
	ACCESS	read-write
	STATUS	mandatory
	DESCRIPTION	"A number that specifies an addressable entity within the context of shelf and slot."
	::= { mibhdsl2DslLineStatusEntry 6 }

    hdsl2DslLineStatus-LineState	OBJECT-TYPE
	SYNTAX	INTEGER {
		    doesNotExist (1),
		    disabled (2),
		    active (3)
		}
	ACCESS	read-only
	STATUS	mandatory
	DESCRIPTION	"The overall state of the line."
	::= { mibhdsl2DslLineStatusEntry 7 }

    hdsl2DslLineStatus-SparePhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibhdsl2DslLineStatusEntry 8 }

    hdsl2DslLineStatus-SparePhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibhdsl2DslLineStatusEntry 9 }

    hdsl2DslLineStatus-SparePhysicalAddress-ItemNumber	OBJECT-TYPE
	SYNTAX	INTEGER
	ACCESS	read-write
	STATUS	mandatory
	DESCRIPTION	"A number that specifies an addressable entity within the context of shelf and slot."
	::= { mibhdsl2DslLineStatusEntry 10 }

    hdsl2DslLineStatus-SparingState	OBJECT-TYPE
	SYNTAX	INTEGER {
		    sparingNone (1),
		    primaryActive (2),
		    primaryInactive (3),
		    secondaryActive (4),
		    secondaryInactive (5)
		}
	ACCESS	read-only
	STATUS	mandatory
	DESCRIPTION	"The sparing state of the line."
	::= { mibhdsl2DslLineStatusEntry 11 }

    hdsl2DslLineStatus-SparingChangeReason	OBJECT-TYPE
	SYNTAX	INTEGER {
		    unknown (1),
		    manual (2),
		    automatic (3),
		    test (4)
		}
	ACCESS	read-only
	STATUS	mandatory
	DESCRIPTION	"The reason for the last sparing state change."
	::= { mibhdsl2DslLineStatusEntry 12 }

    hdsl2DslLineStatus-SparingChangeTime	OBJECT-TYPE
	SYNTAX	INTEGER
	ACCESS	read-only
	STATUS	mandatory
	DESCRIPTION	"The time of the last sparing state change."
	::= { mibhdsl2DslLineStatusEntry 13 }

    hdsl2DslLineStatus-SparingChangeCounter	OBJECT-TYPE
	SYNTAX	INTEGER
	ACCESS	read-only
	STATUS	mandatory
	DESCRIPTION	"The number of sparing state changes."
	::= { mibhdsl2DslLineStatusEntry 14 }

    hdsl2DslLineStatus-VpiVciRange	OBJECT-TYPE
	SYNTAX	INTEGER {
		    vpi01Vci321023 (6),
		    vpi03Vci32511 (1),
		    vpi07Vci32255 (2),
		    vpi015Vci32127 (3),
		    vpi031Vci3263 (4),
		    notApplicable (5)
		}
	ACCESS	read-only
	STATUS	mandatory
	DESCRIPTION	"The valid range of vpi and vci for the circuits established for the line. This range can change only after LIM reboot."
	::= { mibhdsl2DslLineStatusEntry 15 }

    hdsl2DslLineStatus-VpSwitchingVpi	OBJECT-TYPE
	SYNTAX	INTEGER
	ACCESS	read-only
	STATUS	mandatory
	DESCRIPTION	"VPI to be used for the VP switching. Rest of the VPIs will be used for the VC switching."
	::= { mibhdsl2DslLineStatusEntry 16 }

    hdsl2DslLineStatus-PhysicalStatus-IfGroupIndex	OBJECT-TYPE
	SYNTAX	INTEGER
	ACCESS	read-only
	STATUS	mandatory
	DESCRIPTION	"Interface groups index assigned to this physical port."
	::= { mibhdsl2DslLineStatusEntry 17 }

    hdsl2DslLineStatus-PhysicalStatus-UnitType	OBJECT-TYPE
	SYNTAX	INTEGER {
		    coe (1),
		    cpe (2)
		}
	ACCESS	read-only
	STATUS	mandatory
	DESCRIPTION	"Unit types defines if the node is operating Central Office or Customer Premise equipment software."
	::= { mibhdsl2DslLineStatusEntry 18 }

    hdsl2DslLineStatus-PhysicalStatus-InterfaceType	OBJECT-TYPE
	SYNTAX	INTEGER {
		    default (1),
		    gShdsl (2),
		    hdsl2 (3)
		}
	ACCESS	read-only
	STATUS	mandatory
	DESCRIPTION	"Interface type defines if the node is operating on HDSL2 or GSHDSL"
	::= { mibhdsl2DslLineStatusEntry 19 }

    hdsl2DslLineStatus-PhysicalStatus-DevLineState	OBJECT-TYPE
	SYNTAX	INTEGER {
		    portUp (2),
		    test (3),
		    startupHandshake (4),
		    startupTraining (5),
		    startupDownload (6),
		    idle (7),
		    down (8),
		    outOfService (9),
		    unknown (10),
		    analogLoopback (11),
		    digitalLoopback (12)
		}
	ACCESS	read-only
	STATUS	mandatory
	DESCRIPTION	"Display of current interface state."
	::= { mibhdsl2DslLineStatusEntry 20 }

    hdsl2DslLineStatus-PhysicalStatus-OperationalRate	OBJECT-TYPE
	SYNTAX	INTEGER
	ACCESS	read-only
	STATUS	mandatory
	DESCRIPTION	"Operational up and down stream rate. Zero means unknown."
	::= { mibhdsl2DslLineStatusEntry 21 }

    hdsl2DslLineStatus-PhysicalStatus-FirmwareVer	OBJECT-TYPE
	SYNTAX	DisplayString
	ACCESS	read-only
	STATUS	mandatory
	DESCRIPTION	"Firmware version ID."
	::= { mibhdsl2DslLineStatusEntry 22 }

    hdsl2DslLineStatus-PhysicalStatus-HardwareVer	OBJECT-TYPE
	SYNTAX	INTEGER
	ACCESS	read-only
	STATUS	mandatory
	DESCRIPTION	"Hardware chip version."
	::= { mibhdsl2DslLineStatusEntry 23 }

    hdsl2DslLineStatus-PhysicalStatus-NetworkType	OBJECT-TYPE
	SYNTAX	INTEGER {
		    no (1),
		    yes (2)
		}
	ACCESS	read-only
	STATUS	mandatory
	DESCRIPTION	"Current Standard Network type. Either Annex A, Annex B or Annex B ANFP."
	::= { mibhdsl2DslLineStatusEntry 43 }

    hdsl2DslLineStatus-PhysicalStatistic-LineUpTimer-Days	OBJECT-TYPE
	SYNTAX	INTEGER
	ACCESS	read-only
	STATUS	mandatory
	DESCRIPTION	"Number of days that the DSL line has been up."
	::= { mibhdsl2DslLineStatusEntry 24 }

    hdsl2DslLineStatus-PhysicalStatistic-LineUpTimer-Hours	OBJECT-TYPE
	SYNTAX	INTEGER
	ACCESS	read-only
	STATUS	mandatory
	DESCRIPTION	"Number of hours that the DSL line has been up."
	::= { mibhdsl2DslLineStatusEntry 25 }

    hdsl2DslLineStatus-PhysicalStatistic-LineUpTimer-Minutes	OBJECT-TYPE
	SYNTAX	INTEGER
	ACCESS	read-only
	STATUS	mandatory
	DESCRIPTION	"Number of minutes that the DSL line has been up."
	::= { mibhdsl2DslLineStatusEntry 26 }

    hdsl2DslLineStatus-PhysicalStatistic-RxSignalPresent	OBJECT-TYPE
	SYNTAX	INTEGER {
		    yes (3),
		    no (2)
		}
	ACCESS	read-only
	STATUS	mandatory
	DESCRIPTION	"State if the receive signal is present or not."
	::= { mibhdsl2DslLineStatusEntry 27 }

    hdsl2DslLineStatus-PhysicalStatistic-LineQuality	OBJECT-TYPE
	SYNTAX	INTEGER
	ACCESS	read-only
	STATUS	mandatory
	DESCRIPTION	"While the port is in the up state, this parameter displays the line quality."
	::= { mibhdsl2DslLineStatusEntry 28 }

    hdsl2DslLineStatus-PhysicalStatistic-UpDwnCntr	OBJECT-TYPE
	SYNTAX	INTEGER
	ACCESS	read-only
	STATUS	mandatory
	DESCRIPTION	"Interface Up Down counter value displays the number of times the interface trasitions from a down to up state."
	::= { mibhdsl2DslLineStatusEntry 29 }

    hdsl2DslLineStatus-PhysicalStatistic-SelfTest	OBJECT-TYPE
	SYNTAX	INTEGER {
		    passed (1),
		    selfTestFailed (2),
		    localLoopBackFailed (3)
		}
	ACCESS	read-only
	STATUS	mandatory
	DESCRIPTION	"Hardware/firmware self test results."
	::= { mibhdsl2DslLineStatusEntry 30 }

    hdsl2DslLineStatus-PhysicalStatistic-TransmitPower	OBJECT-TYPE
	SYNTAX	INTEGER
	ACCESS	read-only
	STATUS	mandatory
	DESCRIPTION	"Transmit power in DB."
	::= { mibhdsl2DslLineStatusEntry 31 }

    hdsl2DslLineStatus-PhysicalStatistic-FramerSyncStatus	OBJECT-TYPE
	SYNTAX	INTEGER {
		    inSync (2),
		    outOfSync (1)
		}
	ACCESS	read-only
	STATUS	mandatory
	DESCRIPTION	"Framer sync status"
	::= { mibhdsl2DslLineStatusEntry 32 }

    hdsl2DslLineStatus-PhysicalStatistic-CodeViolations	OBJECT-TYPE
	SYNTAX	INTEGER
	ACCESS	read-only
	STATUS	mandatory
	DESCRIPTION	"Line is defined as a count of HDSL2 CRC anomalies occuring during the accumuation period."
	::= { mibhdsl2DslLineStatusEntry 33 }

    hdsl2DslLineStatus-PhysicalStatistic-ErroredSecond	OBJECT-TYPE
	SYNTAX	INTEGER
	ACCESS	read-only
	STATUS	mandatory
	DESCRIPTION	"Errored second is defined as a count of 1 second intervals during which one or more CRC anomalies are declaired and/or one or more LOSW defects are declared."
	::= { mibhdsl2DslLineStatusEntry 34 }

    hdsl2DslLineStatus-PhysicalStatistic-SeverelyErroredSecond	OBJECT-TYPE
	SYNTAX	INTEGER
	ACCESS	read-only
	STATUS	mandatory
	DESCRIPTION	"Line is defined as a count of 1 second intervals for during which at least 50 CRC anomalies are declared or one or more LOSW defects are declared."
	::= { mibhdsl2DslLineStatusEntry 35 }

    hdsl2DslLineStatus-PhysicalStatistic-LoswSecond	OBJECT-TYPE
	SYNTAX	INTEGER
	ACCESS	read-only
	STATUS	mandatory
	DESCRIPTION	"Line is defined as a count of 1 second intervals during which one or more HDSL2 LOSW defects are declared."
	::= { mibhdsl2DslLineStatusEntry 36 }

    hdsl2DslLineStatus-PhysicalStatistic-UnavailableSecond	OBJECT-TYPE
	SYNTAX	INTEGER
	ACCESS	read-only
	STATUS	mandatory
	DESCRIPTION	"Line is a count of 1 second intervals for which the HDSL2 line is unavailable. The HDSL2 line becomes unavailable at the onset of 10 contiguous SES-L's. Once unavailable the HDSL2 line becomes available at the onset of 10 contiguous seconds with no SES-L's."
	::= { mibhdsl2DslLineStatusEntry 37 }

    hdsl2DslLineStatus-PhysicalStatistic-LoopAttenuation	OBJECT-TYPE
	SYNTAX	INTEGER
	ACCESS	read-only
	STATUS	mandatory
	DESCRIPTION	"Current loop attenuation in DB. "
	::= { mibhdsl2DslLineStatusEntry 38 }

    hdsl2DslLineStatus-PhysicalStatistic-Snr	OBJECT-TYPE
	SYNTAX	INTEGER
	ACCESS	read-only
	STATUS	mandatory
	DESCRIPTION	"While the port is in the up state, this parameter displays the Signal to Noise Ratio."
	::= { mibhdsl2DslLineStatusEntry 40 }

    hdsl2DslLineStatus-PhysicalStatistic-SturLoopAttenuation	OBJECT-TYPE
	SYNTAX	INTEGER
	ACCESS	read-only
	STATUS	mandatory
	DESCRIPTION	"Current loop attenuation in DB from the STU-R. "
	::= { mibhdsl2DslLineStatusEntry 41 }

    hdsl2DslLineStatus-PhysicalStatistic-SturSnr	OBJECT-TYPE
	SYNTAX	INTEGER
	ACCESS	read-only
	STATUS	mandatory
	DESCRIPTION	"While the port is in the up state, this parameter displays the Signal to Noise Ratio from the STU-R."
	::= { mibhdsl2DslLineStatusEntry 42 }

    hdsl2DslLineStatus-Action-o	OBJECT-TYPE
	SYNTAX	INTEGER {
		    noAction (1),
		    createProfile (2),
		    deleteProfile (3)
		}
	ACCESS	read-write
	STATUS	mandatory
	DESCRIPTION	""
	::= { mibhdsl2DslLineStatusEntry 39 }

END
