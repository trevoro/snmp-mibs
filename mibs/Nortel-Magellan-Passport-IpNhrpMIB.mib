Nortel-Magellan-Passport-IpNhrpMIB
DEFINITIONS ::= BEGIN



IMPORTS

      OBJECT-TYPE
   FROM RFC-1212

      IpAddress
   FROM RFC1155-SMI

      passportMIBs
   FROM Nortel-Magellan-Passport-UsefulDefinitionsMIB

      Counter32,
      RowPointer,
      DisplayString,
      StorageType,
      RowStatus,
      Integer32,
      Unsigned32
   FROM Nortel-Magellan-Passport-StandardTextualConventionsMIB

      NonReplicated,
      HexString
   FROM Nortel-Magellan-Passport-TextualConventionsMIB

      vrIpIndex,
      vrPpIpPortIndex,
      vrIp,
      vrPpIpPortLogicalIf,
      vrPpIpPortLogicalIfAddressIndex
   FROM Nortel-Magellan-Passport-IpMIB

      vrIndex,
      vrPpIndex
   FROM Nortel-Magellan-Passport-VirtualRouterMIB;




-- LAST-UPDATED   "9906090000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     IpNhrp Enterprise MIB."

ipNhrpMIB OBJECT IDENTIFIER ::= { passportMIBs 77 }










-- Vr/x Pp/x IpPort LogicalIf/<ipAddress> NhrpInterface
-- This component is used to configure a LogicalIf to run NHRP 
-- protocol.

vrPpIpPortLogicalIfNhrpIf OBJECT IDENTIFIER ::= { vrPpIpPortLogicalIf 4 }



vrPpIpPortLogicalIfNhrpIfRowStatusTable OBJECT-TYPE
   SYNTAX     SEQUENCE OF VrPpIpPortLogicalIfNhrpIfRowStatusEntry
   ACCESS     not-accessible
   STATUS     mandatory
   DESCRIPTION
     "This entry controls the addition and deletion of 
      vrPpIpPortLogicalIfNhrpIf components."
::= { vrPpIpPortLogicalIfNhrpIf 1 }

vrPpIpPortLogicalIfNhrpIfRowStatusEntry OBJECT-TYPE
   SYNTAX     VrPpIpPortLogicalIfNhrpIfRowStatusEntry
   ACCESS     not-accessible
   STATUS     mandatory
   DESCRIPTION
     "A single entry in the table represents a single 
      vrPpIpPortLogicalIfNhrpIf component."
   INDEX {
      vrIndex,
      vrPpIndex,
      vrPpIpPortIndex,
      vrPpIpPortLogicalIfAddressIndex,
      vrPpIpPortLogicalIfNhrpIfIndex }
::= { vrPpIpPortLogicalIfNhrpIfRowStatusTable 1 }

VrPpIpPortLogicalIfNhrpIfRowStatusEntry ::= SEQUENCE {
   vrPpIpPortLogicalIfNhrpIfRowStatus
      RowStatus,
   vrPpIpPortLogicalIfNhrpIfComponentName
      DisplayString,
   vrPpIpPortLogicalIfNhrpIfStorageType
      StorageType,
   vrPpIpPortLogicalIfNhrpIfIndex
      NonReplicated }

vrPpIpPortLogicalIfNhrpIfRowStatus OBJECT-TYPE
   SYNTAX     RowStatus 
   ACCESS     read-write
   STATUS     mandatory
   DESCRIPTION
     "This variable is used as the basis for SNMP naming of
      vrPpIpPortLogicalIfNhrpIf components.
      These components can be added and deleted."
::= { vrPpIpPortLogicalIfNhrpIfRowStatusEntry 1 }

vrPpIpPortLogicalIfNhrpIfComponentName OBJECT-TYPE
   SYNTAX     DisplayString 
   ACCESS     read-only
   STATUS     mandatory
   DESCRIPTION
     "This variable provides the component's string name for
      use with the ASCII Console Interface"
::= { vrPpIpPortLogicalIfNhrpIfRowStatusEntry 2 }

vrPpIpPortLogicalIfNhrpIfStorageType OBJECT-TYPE
   SYNTAX     StorageType 
   ACCESS     read-only
   STATUS     mandatory
   DESCRIPTION
     "This variable represents the storage type value for the
      vrPpIpPortLogicalIfNhrpIf tables."
::= { vrPpIpPortLogicalIfNhrpIfRowStatusEntry 4 }

vrPpIpPortLogicalIfNhrpIfIndex OBJECT-TYPE
   SYNTAX     NonReplicated 
   ACCESS     not-accessible
   STATUS     mandatory
   DESCRIPTION
     "This variable represents the index for the vrPpIpPortLogicalIfNhrpIf tables."
::= { vrPpIpPortLogicalIfNhrpIfRowStatusEntry 10 }


-- Vr/<string> Ip NextHopResolutionProtocol
-- This component represents a co-located NHRP Client and Server as 
-- specified in RFC2332. NHRP provides a method for a station 
-- connected to a Non-Broadcast Multiple Access (NBMA) 
-- subnetwork to determine the internetworking layer address and 
-- NBMA subnetwork address of the "next hop" towards a destination 
-- station. NHRP reduces or eliminates the extra hops required by the 
-- existing logically independent IP subnet (LIS) model.

vrIpNhrp OBJECT IDENTIFIER ::= { vrIp 19 }



vrIpNhrpRowStatusTable OBJECT-TYPE
   SYNTAX     SEQUENCE OF VrIpNhrpRowStatusEntry
   ACCESS     not-accessible
   STATUS     mandatory
   DESCRIPTION
     "This entry controls the addition and deletion of 
      vrIpNhrp components."
::= { vrIpNhrp 1 }

vrIpNhrpRowStatusEntry OBJECT-TYPE
   SYNTAX     VrIpNhrpRowStatusEntry
   ACCESS     not-accessible
   STATUS     mandatory
   DESCRIPTION
     "A single entry in the table represents a single 
      vrIpNhrp component."
   INDEX {
      vrIndex,
      vrIpIndex,
      vrIpNhrpIndex }
::= { vrIpNhrpRowStatusTable 1 }

VrIpNhrpRowStatusEntry ::= SEQUENCE {
   vrIpNhrpRowStatus
      RowStatus,
   vrIpNhrpComponentName
      DisplayString,
   vrIpNhrpStorageType
      StorageType,
   vrIpNhrpIndex
      NonReplicated }

vrIpNhrpRowStatus OBJECT-TYPE
   SYNTAX     RowStatus 
   ACCESS     read-write
   STATUS     mandatory
   DESCRIPTION
     "This variable is used as the basis for SNMP naming of
      vrIpNhrp components.
      These components can be added and deleted."
::= { vrIpNhrpRowStatusEntry 1 }

vrIpNhrpComponentName OBJECT-TYPE
   SYNTAX     DisplayString 
   ACCESS     read-only
   STATUS     mandatory
   DESCRIPTION
     "This variable provides the component's string name for
      use with the ASCII Console Interface"
::= { vrIpNhrpRowStatusEntry 2 }

vrIpNhrpStorageType OBJECT-TYPE
   SYNTAX     StorageType 
   ACCESS     read-only
   STATUS     mandatory
   DESCRIPTION
     "This variable represents the storage type value for the
      vrIpNhrp tables."
::= { vrIpNhrpRowStatusEntry 4 }

vrIpNhrpIndex OBJECT-TYPE
   SYNTAX     NonReplicated 
   ACCESS     not-accessible
   STATUS     mandatory
   DESCRIPTION
     "This variable represents the index for the vrIpNhrp tables."
::= { vrIpNhrpRowStatusEntry 10 }

vrIpNhrpAdminControlTable OBJECT-TYPE
   SYNTAX     SEQUENCE OF VrIpNhrpAdminControlEntry
   ACCESS     not-accessible
   STATUS     mandatory
   DESCRIPTION
     "This group includes the Administrative Control attribute. This 
      attribute defines the current administrative state of this component."
::= { vrIpNhrp 10 }

vrIpNhrpAdminControlEntry OBJECT-TYPE
   SYNTAX     VrIpNhrpAdminControlEntry
   ACCESS     not-accessible
   STATUS     mandatory
   DESCRIPTION
     "An entry in the vrIpNhrpAdminControlTable."
   INDEX {
      vrIndex,
      vrIpIndex,
      vrIpNhrpIndex }
::= { vrIpNhrpAdminControlTable 1 }

VrIpNhrpAdminControlEntry ::= SEQUENCE {
   vrIpNhrpSnmpAdminStatus
      INTEGER }

vrIpNhrpSnmpAdminStatus OBJECT-TYPE
   SYNTAX     INTEGER  {
                 up(1),
                 down(2),
                 testing(3) }
   ACCESS     read-write
   STATUS     mandatory
   DESCRIPTION
     "The desired state of the interface. The up state indicates the 
      interface is operational and packet forwarding is allowed. The down 
      state indicates the interface is not operational and packet forwarding 
      is unavailable. The testing state indicates that no operational 
      packets can be passed."
   DEFVAL     { up }
::= { vrIpNhrpAdminControlEntry 1 }

vrIpNhrpProvTable OBJECT-TYPE
   SYNTAX     SEQUENCE OF VrIpNhrpProvEntry
   ACCESS     not-accessible
   STATUS     mandatory
   DESCRIPTION
     "This group contains the provisionable attributes of the Nhrp 
      component."
::= { vrIpNhrp 11 }

vrIpNhrpProvEntry OBJECT-TYPE
   SYNTAX     VrIpNhrpProvEntry
   ACCESS     not-accessible
   STATUS     mandatory
   DESCRIPTION
     "An entry in the vrIpNhrpProvTable."
   INDEX {
      vrIndex,
      vrIpIndex,
      vrIpNhrpIndex }
::= { vrIpNhrpProvTable 1 }

VrIpNhrpProvEntry ::= SEQUENCE {
   vrIpNhrpMaxResCacheEntries
      Unsigned32,
   vrIpNhrpFwdTransitRecord
      INTEGER,
   vrIpNhrpRevTransitRecord
      INTEGER }

vrIpNhrpMaxResCacheEntries OBJECT-TYPE
   SYNTAX     Unsigned32 (32..1024)
   ACCESS     read-write
   STATUS     mandatory
   DESCRIPTION
     "This attribute specifies the maximum number of ResCacheEntry 
      components which may exist under the Nhrp component at any one 
      time. Reducing the value of this attribute will not clear existing 
      entries."
   DEFVAL     { 512 }
::= { vrIpNhrpProvEntry 1 }

vrIpNhrpFwdTransitRecord OBJECT-TYPE
   SYNTAX     INTEGER  {
                 enabled(1),
                 disabled(2) }
   ACCESS     read-write
   STATUS     mandatory
   DESCRIPTION
     "This attribute specifies whether to attach a forward transit record 
      extension to NHRP packets (Resolution and Purge requests) that 
      Passport originates. This extension along with NHRP debug tracing 
      set to 'verbose' can be used in tracing the path the NHRP packet 
      takes from source to destination."
   DEFVAL     { disabled }
::= { vrIpNhrpProvEntry 2 }

vrIpNhrpRevTransitRecord OBJECT-TYPE
   SYNTAX     INTEGER  {
                 enabled(1),
                 disabled(2) }
   ACCESS     read-write
   STATUS     mandatory
   DESCRIPTION
     "This attribute specifies whether to attach a reverse transit record 
      extension to Resolution Request packets that Passport originates. 
      This extension along with NHRP debug tracing set to 'verbose' can 
      be used in tracing the path the NHRP packet takes from destination 
      to source."
   DEFVAL     { disabled }
::= { vrIpNhrpProvEntry 3 }

vrIpNhrpStateTable OBJECT-TYPE
   SYNTAX     SEQUENCE OF VrIpNhrpStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { vrIpNhrp 13 }

vrIpNhrpStateEntry OBJECT-TYPE
   SYNTAX     VrIpNhrpStateEntry
   ACCESS     not-accessible
   STATUS     mandatory
   DESCRIPTION
     "An entry in the vrIpNhrpStateTable."
   INDEX {
      vrIndex,
      vrIpIndex,
      vrIpNhrpIndex }
::= { vrIpNhrpStateTable 1 }

VrIpNhrpStateEntry ::= SEQUENCE {
   vrIpNhrpAdminState
      INTEGER,
   vrIpNhrpOperationalState
      INTEGER,
   vrIpNhrpUsageState
      INTEGER }

vrIpNhrpAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { vrIpNhrpStateEntry 1 }

vrIpNhrpOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { vrIpNhrpStateEntry 2 }

vrIpNhrpUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { vrIpNhrpStateEntry 3 }

vrIpNhrpOperStatusTable OBJECT-TYPE
   SYNTAX     SEQUENCE OF VrIpNhrpOperStatusEntry
   ACCESS     not-accessible
   STATUS     mandatory
   DESCRIPTION
     "This group includes the Operational Status attribute. This attribute 
      defines the current operational state of this component."
::= { vrIpNhrp 14 }

vrIpNhrpOperStatusEntry OBJECT-TYPE
   SYNTAX     VrIpNhrpOperStatusEntry
   ACCESS     not-accessible
   STATUS     mandatory
   DESCRIPTION
     "An entry in the vrIpNhrpOperStatusTable."
   INDEX {
      vrIndex,
      vrIpIndex,
      vrIpNhrpIndex }
::= { vrIpNhrpOperStatusTable 1 }

VrIpNhrpOperStatusEntry ::= SEQUENCE {
   vrIpNhrpSnmpOperStatus
      INTEGER }

vrIpNhrpSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { vrIpNhrpOperStatusEntry 1 }

vrIpNhrpOperTable OBJECT-TYPE
   SYNTAX     SEQUENCE OF VrIpNhrpOperEntry
   ACCESS     not-accessible
   STATUS     mandatory
   DESCRIPTION
     "This group contains the operational attributes of the Nhrp 
      component."
::= { vrIpNhrp 15 }

vrIpNhrpOperEntry OBJECT-TYPE
   SYNTAX     VrIpNhrpOperEntry
   ACCESS     not-accessible
   STATUS     mandatory
   DESCRIPTION
     "An entry in the vrIpNhrpOperTable."
   INDEX {
      vrIndex,
      vrIpIndex,
      vrIpNhrpIndex }
::= { vrIpNhrpOperTable 1 }

VrIpNhrpOperEntry ::= SEQUENCE {
   vrIpNhrpCurrResCacheEntries
      Unsigned32,
   vrIpNhrpPeakResCacheEntries
      Unsigned32 }

vrIpNhrpCurrResCacheEntries OBJECT-TYPE
   SYNTAX     Unsigned32 (0..4292967295)
   ACCESS     read-only
   STATUS     mandatory
   DESCRIPTION
     "This attribute indicates the current number of entries in the NHRP 
      resolution cache table."
::= { vrIpNhrpOperEntry 1 }

vrIpNhrpPeakResCacheEntries OBJECT-TYPE
   SYNTAX     Unsigned32 (0..4292967295)
   ACCESS     read-only
   STATUS     mandatory
   DESCRIPTION
     "This attribute indicates the peak value of currResCacheEntries 
      since the Nhrp snmpOperStatus attribute last became up."
::= { vrIpNhrpOperEntry 2 }


-- Vr/<string> Ip Nhrp NextHopServer
-- This component represents the NHRP server. The server performs 
-- the NHRP service within the NBMA cloud.

vrIpNhrpNhs OBJECT IDENTIFIER ::= { vrIpNhrp 2 }



vrIpNhrpNhsRowStatusTable OBJECT-TYPE
   SYNTAX     SEQUENCE OF VrIpNhrpNhsRowStatusEntry
   ACCESS     not-accessible
   STATUS     mandatory
   DESCRIPTION
     "This entry controls the addition and deletion of 
      vrIpNhrpNhs components."
::= { vrIpNhrpNhs 1 }

vrIpNhrpNhsRowStatusEntry OBJECT-TYPE
   SYNTAX     VrIpNhrpNhsRowStatusEntry
   ACCESS     not-accessible
   STATUS     mandatory
   DESCRIPTION
     "A single entry in the table represents a single 
      vrIpNhrpNhs component."
   INDEX {
      vrIndex,
      vrIpIndex,
      vrIpNhrpIndex,
      vrIpNhrpNhsIndex }
::= { vrIpNhrpNhsRowStatusTable 1 }

VrIpNhrpNhsRowStatusEntry ::= SEQUENCE {
   vrIpNhrpNhsRowStatus
      RowStatus,
   vrIpNhrpNhsComponentName
      DisplayString,
   vrIpNhrpNhsStorageType
      StorageType,
   vrIpNhrpNhsIndex
      NonReplicated }

vrIpNhrpNhsRowStatus OBJECT-TYPE
   SYNTAX     RowStatus 
   ACCESS     read-only
   STATUS     mandatory
   DESCRIPTION
     "This variable is used as the basis for SNMP naming of
      vrIpNhrpNhs components.
      These components cannot be added nor deleted."
::= { vrIpNhrpNhsRowStatusEntry 1 }

vrIpNhrpNhsComponentName OBJECT-TYPE
   SYNTAX     DisplayString 
   ACCESS     read-only
   STATUS     mandatory
   DESCRIPTION
     "This variable provides the component's string name for
      use with the ASCII Console Interface"
::= { vrIpNhrpNhsRowStatusEntry 2 }

vrIpNhrpNhsStorageType OBJECT-TYPE
   SYNTAX     StorageType 
   ACCESS     read-only
   STATUS     mandatory
   DESCRIPTION
     "This variable represents the storage type value for the
      vrIpNhrpNhs tables."
::= { vrIpNhrpNhsRowStatusEntry 4 }

vrIpNhrpNhsIndex OBJECT-TYPE
   SYNTAX     NonReplicated 
   ACCESS     not-accessible
   STATUS     mandatory
   DESCRIPTION
     "This variable represents the index for the vrIpNhrpNhs tables."
::= { vrIpNhrpNhsRowStatusEntry 10 }

vrIpNhrpNhsStatsTable OBJECT-TYPE
   SYNTAX     SEQUENCE OF VrIpNhrpNhsStatsEntry
   ACCESS     not-accessible
   STATUS     mandatory
   DESCRIPTION
     "This group contains the statistics attributes of the Nhs component."
::= { vrIpNhrpNhs 10 }

vrIpNhrpNhsStatsEntry OBJECT-TYPE
   SYNTAX     VrIpNhrpNhsStatsEntry
   ACCESS     not-accessible
   STATUS     mandatory
   DESCRIPTION
     "An entry in the vrIpNhrpNhsStatsTable."
   INDEX {
      vrIndex,
      vrIpIndex,
      vrIpNhrpIndex,
      vrIpNhrpNhsIndex }
::= { vrIpNhrpNhsStatsTable 1 }

VrIpNhrpNhsStatsEntry ::= SEQUENCE {
   vrIpNhrpNhsRxResolveReq
      Counter32,
   vrIpNhrpNhsTxResolveReplyAck
      Counter32,
   vrIpNhrpNhsTxResolveReplyNakProhibited
      Counter32,
   vrIpNhrpNhsTxResolveReplyNakInsufResources
      Counter32,
   vrIpNhrpNhsTxResolveReplyNakNoBinding
      Counter32,
   vrIpNhrpNhsTxResolveReplyNakNotUnique
      Counter32,
   vrIpNhrpNhsRxRegisterReq
      Counter32,
   vrIpNhrpNhsRxPurgeReq
      Counter32,
   vrIpNhrpNhsTxPurgeReq
      Counter32,
   vrIpNhrpNhsRxPurgeReply
      Counter32,
   vrIpNhrpNhsTxPurgeReply
      Counter32,
   vrIpNhrpNhsRxErrUnrecognizedExtension
      Counter32,
   vrIpNhrpNhsRxErrLoopDetected
      Counter32,
   vrIpNhrpNhsRxErrProtoAddrUnreachable
      Counter32,
   vrIpNhrpNhsRxErrProtoError
      Counter32,
   vrIpNhrpNhsRxErrSduSizeExceeded
      Counter32,
   vrIpNhrpNhsRxErrInvalidExtension
      Counter32,
   vrIpNhrpNhsRxErrInvalidResReplyReceived
      Counter32,
   vrIpNhrpNhsRxErrAuthenticationFailure
      Counter32,
   vrIpNhrpNhsRxErrHopCountExceeded
      Counter32,
   vrIpNhrpNhsTxErrUnrecognizedExtension
      Counter32,
   vrIpNhrpNhsTxErrLoopDetected
      Counter32,
   vrIpNhrpNhsTxErrProtoAddrUnreachable
      Counter32,
   vrIpNhrpNhsTxErrProtoError
      Counter32,
   vrIpNhrpNhsTxErrSduSizeExceeded
      Counter32,
   vrIpNhrpNhsTxErrInvalidExtension
      Counter32,
   vrIpNhrpNhsTxErrAuthenticationFailure
      Counter32,
   vrIpNhrpNhsTxErrHopCountExceeded
      Counter32,
   vrIpNhrpNhsFwdResolveReq
      Counter32,
   vrIpNhrpNhsFwdResolveReply
      Counter32,
   vrIpNhrpNhsFwdRegisterReq
      Counter32,
   vrIpNhrpNhsFwdRegisterReply
      Counter32,
   vrIpNhrpNhsFwdPurgeReq
      Counter32,
   vrIpNhrpNhsFwdPurgeReply
      Counter32,
   vrIpNhrpNhsFwdErrorIndication
      Counter32 }

vrIpNhrpNhsRxResolveReq OBJECT-TYPE
   SYNTAX     Counter32 
   ACCESS     read-only
   STATUS     mandatory
   DESCRIPTION
     "This attribute counts the NHRP Resolution Requests received by 
      this server. 
      This counter wraps to zero when the maximum value is exceeded."
::= { vrIpNhrpNhsStatsEntry 1 }

vrIpNhrpNhsTxResolveReplyAck OBJECT-TYPE
   SYNTAX     Counter32 
   ACCESS     read-only
   STATUS     mandatory
   DESCRIPTION
     "This attribute counts the positively acknowledged NHRP Resolution 
      Replies transmitted by this server. 
      This counter wraps to zero when the maximum value is exceeded."
::= { vrIpNhrpNhsStatsEntry 2 }

vrIpNhrpNhsTxResolveReplyNakProhibited OBJECT-TYPE
   SYNTAX     Counter32 
   ACCESS     read-only
   STATUS     mandatory
   DESCRIPTION
     "This attribute counts the NAK NHRP Resolution Replies 
      transmitted by this server with the code 'Administratively 
      Prohibited'. 
      This counter wraps to zero when the maximum value is exceeded."
::= { vrIpNhrpNhsStatsEntry 3 }

vrIpNhrpNhsTxResolveReplyNakInsufResources OBJECT-TYPE
   SYNTAX     Counter32 
   ACCESS     read-only
   STATUS     mandatory
   DESCRIPTION
     "This attribute counts the NAK NHRP Resolution Replies 
      transmitted by this server with the code 'Insufficient Resources'. 
      This counter wraps to zero when the maximum value is exceeded."
::= { vrIpNhrpNhsStatsEntry 4 }

vrIpNhrpNhsTxResolveReplyNakNoBinding OBJECT-TYPE
   SYNTAX     Counter32 
   ACCESS     read-only
   STATUS     mandatory
   DESCRIPTION
     "This attribute counts the NAK NHRP Resolution Replies 
      transmitted by this server with the code 'No Internetworking Layer 
      Address to NBMA Address Binding Exists'. 
      This counter wraps to zero when the maximum value is exceeded."
::= { vrIpNhrpNhsStatsEntry 5 }

vrIpNhrpNhsTxResolveReplyNakNotUnique OBJECT-TYPE
   SYNTAX     Counter32 
   ACCESS     read-only
   STATUS     mandatory
   DESCRIPTION
     "This attribute counts the NAK NHRP Resolution Replies 
      transmitted by this server with the code 'Binding Exists But Is Not 
      Unique'. 
      This counter wraps to zero when the maximum value is exceeded."
::= { vrIpNhrpNhsStatsEntry 6 }

vrIpNhrpNhsRxRegisterReq OBJECT-TYPE
   SYNTAX     Counter32 
   ACCESS     read-only
   STATUS     mandatory
   DESCRIPTION
     "This attribute counts the NHRP Registration Requests received by 
      this server. Registration is not supported, therefore all NHRP 
      Registration Requests are silently dropped.
      This counter wraps to zero when the maximum value is exceeded."
::= { vrIpNhrpNhsStatsEntry 7 }

vrIpNhrpNhsRxPurgeReq OBJECT-TYPE
   SYNTAX     Counter32 
   ACCESS     read-only
   STATUS     mandatory
   DESCRIPTION
     "This attribute counts the NHRP Purge Requests received by this 
      server.
      This counter wraps to zero when the maximum value is exceeded."
::= { vrIpNhrpNhsStatsEntry 12 }

vrIpNhrpNhsTxPurgeReq OBJECT-TYPE
   SYNTAX     Counter32 
   ACCESS     read-only
   STATUS     mandatory
   DESCRIPTION
     "This attribute counts the NHRP Purge Requests transmitted by this 
      server. 
      This counter wraps to zero when the maximum value is exceeded."
::= { vrIpNhrpNhsStatsEntry 13 }

vrIpNhrpNhsRxPurgeReply OBJECT-TYPE
   SYNTAX     Counter32 
   ACCESS     read-only
   STATUS     mandatory
   DESCRIPTION
     "This attribute counts the NHRP Purge Replies received by this 
      server. 
      This counter wraps to zero when the maximum value is exceeded."
::= { vrIpNhrpNhsStatsEntry 14 }

vrIpNhrpNhsTxPurgeReply OBJECT-TYPE
   SYNTAX     Counter32 
   ACCESS     read-only
   STATUS     mandatory
   DESCRIPTION
     "This attribute counts the NHRP Purge Replies transmitted by this 
      server. 
      This counter wraps to zero when the maximum value is exceeded."
::= { vrIpNhrpNhsStatsEntry 15 }

vrIpNhrpNhsRxErrUnrecognizedExtension OBJECT-TYPE
   SYNTAX     Counter32 
   ACCESS     read-only
   STATUS     mandatory
   DESCRIPTION
     "This attribute counts the NHRP Error Indication packets received by 
      this server with the error code 'Unrecognized Extension'. 
      This counter wraps to zero when the maximum value is exceeded."
::= { vrIpNhrpNhsStatsEntry 16 }

vrIpNhrpNhsRxErrLoopDetected OBJECT-TYPE
   SYNTAX     Counter32 
   ACCESS     read-only
   STATUS     mandatory
   DESCRIPTION
     "This attribute counts the NHRP Error Indication packets received by 
      this server with the error code 'NHRP Loop Detected'. 
      This counter wraps to zero when the maximum value is exceeded."
::= { vrIpNhrpNhsStatsEntry 17 }

vrIpNhrpNhsRxErrProtoAddrUnreachable OBJECT-TYPE
   SYNTAX     Counter32 
   ACCESS     read-only
   STATUS     mandatory
   DESCRIPTION
     "This attribute counts the NHRP Error Indication packets received by 
      this server with the error code 'Protocol Address Unreachable'. 
      This counter wraps to zero when the maximum value is exceeded."
::= { vrIpNhrpNhsStatsEntry 18 }

vrIpNhrpNhsRxErrProtoError OBJECT-TYPE
   SYNTAX     Counter32 
   ACCESS     read-only
   STATUS     mandatory
   DESCRIPTION
     "This attribute counts the NHRP Error Indication packets received by 
      this server with the error code 'Protocol Error'.
      This counter wraps to zero when the maximum value is exceeded."
::= { vrIpNhrpNhsStatsEntry 19 }

vrIpNhrpNhsRxErrSduSizeExceeded OBJECT-TYPE
   SYNTAX     Counter32 
   ACCESS     read-only
   STATUS     mandatory
   DESCRIPTION
     "This attribute counts the NHRP Error Indication packets received by 
      this server with the error code 'NHRP SDU Size Exceeded'. 
      This counter wraps to zero when the maximum value is exceeded."
::= { vrIpNhrpNhsStatsEntry 20 }

vrIpNhrpNhsRxErrInvalidExtension OBJECT-TYPE
   SYNTAX     Counter32 
   ACCESS     read-only
   STATUS     mandatory
   DESCRIPTION
     "This attribute counts the NHRP Error Indication packets received by 
      this server with the error code 'Invalid Extension'. 
      This counter wraps to zero when the maximum value is exceeded."
::= { vrIpNhrpNhsStatsEntry 21 }

vrIpNhrpNhsRxErrInvalidResReplyReceived OBJECT-TYPE
   SYNTAX     Counter32 
   ACCESS     read-only
   STATUS     mandatory
   DESCRIPTION
     "This attribute counts the NHRP Error Indication packets received by 
      this server with the error code 'Invalid Resolution Reply Received'. 
      This counter wraps to zero when the maximum value is exceeded."
::= { vrIpNhrpNhsStatsEntry 22 }

vrIpNhrpNhsRxErrAuthenticationFailure OBJECT-TYPE
   SYNTAX     Counter32 
   ACCESS     read-only
   STATUS     mandatory
   DESCRIPTION
     "This attribute counts the NHRP Error Indication packets received by 
      this server with the error code 'Authentication Failure'. 
      This counter wraps to zero when the maximum value is exceeded."
::= { vrIpNhrpNhsStatsEntry 23 }

vrIpNhrpNhsRxErrHopCountExceeded OBJECT-TYPE
   SYNTAX     Counter32 
   ACCESS     read-only
   STATUS     mandatory
   DESCRIPTION
     "This attribute counts the NHRP Error Indication packets received by 
      this server with the error code 'Hop Count Exceeded'.
      This counter wraps to zero when the maximum value is exceeded."
::= { vrIpNhrpNhsStatsEntry 24 }

vrIpNhrpNhsTxErrUnrecognizedExtension OBJECT-TYPE
   SYNTAX     Counter32 
   ACCESS     read-only
   STATUS     mandatory
   DESCRIPTION
     "This attribute counts the NHRP Error Indication packets transmitted 
      by this server with the error code 'Unrecognized Extension'. 
      This counter wraps to zero when the maximum value is exceeded."
::= { vrIpNhrpNhsStatsEntry 25 }

vrIpNhrpNhsTxErrLoopDetected OBJECT-TYPE
   SYNTAX     Counter32 
   ACCESS     read-only
   STATUS     mandatory
   DESCRIPTION
     "This attribute counts the NHRP Error Indication packets transmitted 
      by this server with the error code 'NHRP Loop Detected'. 
      This counter wraps to zero when the maximum value is exceeded."
::= { vrIpNhrpNhsStatsEntry 26 }

vrIpNhrpNhsTxErrProtoAddrUnreachable OBJECT-TYPE
   SYNTAX     Counter32 
   ACCESS     read-only
   STATUS     mandatory
   DESCRIPTION
     "This attribute counts the NHRP Error Indication packets transmitted 
      by this server with the error code 'Protocol Address Unreachable'. 
      This counter wraps to zero when the maximum value is exceeded."
::= { vrIpNhrpNhsStatsEntry 27 }

vrIpNhrpNhsTxErrProtoError OBJECT-TYPE
   SYNTAX     Counter32 
   ACCESS     read-only
   STATUS     mandatory
   DESCRIPTION
     "This attribute counts the NHRP Error Indication packets transmitted 
      by this server with the error code 'Protocol Error'.
      This counter wraps to zero when the maximum value is exceeded."
::= { vrIpNhrpNhsStatsEntry 28 }

vrIpNhrpNhsTxErrSduSizeExceeded OBJECT-TYPE
   SYNTAX     Counter32 
   ACCESS     read-only
   STATUS     mandatory
   DESCRIPTION
     "This attribute counts the NHRP Error Indication packets transmitted 
      by this server with the error code 'NHRP SDU Size Exceeded'. 
      This counter wraps to zero when the maximum value is exceeded."
::= { vrIpNhrpNhsStatsEntry 29 }

vrIpNhrpNhsTxErrInvalidExtension OBJECT-TYPE
   SYNTAX     Counter32 
   ACCESS     read-only
   STATUS     mandatory
   DESCRIPTION
     "This attribute counts the NHRP Error Indication packets transmitted 
      by this server with the error code 'Invalid Extension'. 
      This counter wraps to zero when the maximum value is exceeded."
::= { vrIpNhrpNhsStatsEntry 30 }

vrIpNhrpNhsTxErrAuthenticationFailure OBJECT-TYPE
   SYNTAX     Counter32 
   ACCESS     read-only
   STATUS     mandatory
   DESCRIPTION
     "This attribute counts the NHRP Error Indication packets transmitted 
      by this server with the error code 'Authentication Failure'. 
      This counter wraps to zero when the maximum value is exceeded."
::= { vrIpNhrpNhsStatsEntry 31 }

vrIpNhrpNhsTxErrHopCountExceeded OBJECT-TYPE
   SYNTAX     Counter32 
   ACCESS     read-only
   STATUS     mandatory
   DESCRIPTION
     "This attribute counts the NHRP Error Indication packets transmitted 
      by this server with the error code 'Hop Count Exceeded'. 
      This counter wraps to zero when the maximum value is exceeded."
::= { vrIpNhrpNhsStatsEntry 32 }

vrIpNhrpNhsFwdResolveReq OBJECT-TYPE
   SYNTAX     Counter32 
   ACCESS     read-only
   STATUS     mandatory
   DESCRIPTION
     "This attribute counts the NHRP Resolution Requests forwarded by 
      this server acting as a transit NHS. 
      This counter wraps to zero when the maximum value is exceeded."
::= { vrIpNhrpNhsStatsEntry 33 }

vrIpNhrpNhsFwdResolveReply OBJECT-TYPE
   SYNTAX     Counter32 
   ACCESS     read-only
   STATUS     mandatory
   DESCRIPTION
     "This attribute counts the NHRP Resolution Replies forwarded by 
      this server acting as a transit NHS. 
      This counter wraps to zero when the maximum value is exceeded."
::= { vrIpNhrpNhsStatsEntry 34 }

vrIpNhrpNhsFwdRegisterReq OBJECT-TYPE
   SYNTAX     Counter32 
   ACCESS     read-only
   STATUS     mandatory
   DESCRIPTION
     "This attribute counts the NHRP Registration Requests forwarded by 
      this server acting as a transit NHS. 
      This counter wraps to zero when the maximum value is exceeded."
::= { vrIpNhrpNhsStatsEntry 35 }

vrIpNhrpNhsFwdRegisterReply OBJECT-TYPE
   SYNTAX     Counter32 
   ACCESS     read-only
   STATUS     mandatory
   DESCRIPTION
     "This attribute counts the NHRP Registration Replies forwarded by 
      this server acting as a transit NHS. 
      This counter wraps to zero when the maximum value is exceeded."
::= { vrIpNhrpNhsStatsEntry 36 }

vrIpNhrpNhsFwdPurgeReq OBJECT-TYPE
   SYNTAX     Counter32 
   ACCESS     read-only
   STATUS     mandatory
   DESCRIPTION
     "This attribute counts the NHRP Purge Requests forwarded by this 
      server acting as a transit NHS. 
      This counter wraps to zero when the maximum value is exceeded."
::= { vrIpNhrpNhsStatsEntry 37 }

vrIpNhrpNhsFwdPurgeReply OBJECT-TYPE
   SYNTAX     Counter32 
   ACCESS     read-only
   STATUS     mandatory
   DESCRIPTION
     "This attribute counts the NHRP Purge Replies forwarded by this 
      server acting as a transit NHS. 
      This counter wraps to zero when the maximum value is exceeded."
::= { vrIpNhrpNhsStatsEntry 38 }

vrIpNhrpNhsFwdErrorIndication OBJECT-TYPE
   SYNTAX     Counter32 
   ACCESS     read-only
   STATUS     mandatory
   DESCRIPTION
     "This attribute counts the NHRP Error Indication packets forwarded 
      by this server acting as a transit NHS. 
      This counter wraps to zero when the maximum value is exceeded."
::= { vrIpNhrpNhsStatsEntry 39 }


-- Vr/<string> Ip Nhrp Nhs EgressPolicy/n
-- This component represents an egress policy on this server.
-- The server has the following default egress policies which may be 
-- overridden by any provisioned egress policies: 1. NAK resolution 
-- request for any remotely attached destination regardless of source, 
-- 2. ACK resolution request for any locally attached destination 
-- regardless of source.

vrIpNhrpNhsEp OBJECT IDENTIFIER ::= { vrIpNhrpNhs 2 }



vrIpNhrpNhsEpRowStatusTable OBJECT-TYPE
   SYNTAX     SEQUENCE OF VrIpNhrpNhsEpRowStatusEntry
   ACCESS     not-accessible
   STATUS     mandatory
   DESCRIPTION
     "This entry controls the addition and deletion of 
      vrIpNhrpNhsEp components."
::= { vrIpNhrpNhsEp 1 }

vrIpNhrpNhsEpRowStatusEntry OBJECT-TYPE
   SYNTAX     VrIpNhrpNhsEpRowStatusEntry
   ACCESS     not-accessible
   STATUS     mandatory
   DESCRIPTION
     "A single entry in the table represents a single 
      vrIpNhrpNhsEp component."
   INDEX {
      vrIndex,
      vrIpIndex,
      vrIpNhrpIndex,
      vrIpNhrpNhsIndex,
      vrIpNhrpNhsEpIndex }
::= { vrIpNhrpNhsEpRowStatusTable 1 }

VrIpNhrpNhsEpRowStatusEntry ::= SEQUENCE {
   vrIpNhrpNhsEpRowStatus
      RowStatus,
   vrIpNhrpNhsEpComponentName
      DisplayString,
   vrIpNhrpNhsEpStorageType
      StorageType,
   vrIpNhrpNhsEpIndex
      Integer32 }

vrIpNhrpNhsEpRowStatus OBJECT-TYPE
   SYNTAX     RowStatus 
   ACCESS     read-write
   STATUS     mandatory
   DESCRIPTION
     "This variable is used as the basis for SNMP naming of
      vrIpNhrpNhsEp components.
      These components can be added and deleted."
::= { vrIpNhrpNhsEpRowStatusEntry 1 }

vrIpNhrpNhsEpComponentName OBJECT-TYPE
   SYNTAX     DisplayString 
   ACCESS     read-only
   STATUS     mandatory
   DESCRIPTION
     "This variable provides the component's string name for
      use with the ASCII Console Interface"
::= { vrIpNhrpNhsEpRowStatusEntry 2 }

vrIpNhrpNhsEpStorageType OBJECT-TYPE
   SYNTAX     StorageType 
   ACCESS     read-only
   STATUS     mandatory
   DESCRIPTION
     "This variable represents the storage type value for the
      vrIpNhrpNhsEp tables."
::= { vrIpNhrpNhsEpRowStatusEntry 4 }

vrIpNhrpNhsEpIndex OBJECT-TYPE
   SYNTAX     Integer32 (0..65535)
   ACCESS     not-accessible
   STATUS     mandatory
   DESCRIPTION
     "This variable represents the index for the vrIpNhrpNhsEp tables."
::= { vrIpNhrpNhsEpRowStatusEntry 10 }

vrIpNhrpNhsEpProvTable OBJECT-TYPE
   SYNTAX     SEQUENCE OF VrIpNhrpNhsEpProvEntry
   ACCESS     not-accessible
   STATUS     mandatory
   DESCRIPTION
     "This group contains the provisionable attributes of the EgressPolicy 
      component."
::= { vrIpNhrpNhsEp 10 }

vrIpNhrpNhsEpProvEntry OBJECT-TYPE
   SYNTAX     VrIpNhrpNhsEpProvEntry
   ACCESS     not-accessible
   STATUS     mandatory
   DESCRIPTION
     "An entry in the vrIpNhrpNhsEpProvTable."
   INDEX {
      vrIndex,
      vrIpIndex,
      vrIpNhrpIndex,
      vrIpNhrpNhsIndex,
      vrIpNhrpNhsEpIndex }
::= { vrIpNhrpNhsEpProvTable 1 }

VrIpNhrpNhsEpProvEntry ::= SEQUENCE {
   vrIpNhrpNhsEpAction
      INTEGER,
   vrIpNhrpNhsEpProtocol
      INTEGER }

vrIpNhrpNhsEpAction OBJECT-TYPE
   SYNTAX     INTEGER  {
                 ack(1),
                 nak(2) }
   ACCESS     read-write
   STATUS     mandatory
   DESCRIPTION
     "This attribute specifies how the server should handle the NHRP 
      Resolution Request if it matches this policy. The possible actions 
      are:
      ack - Send a positive acknowledgement (ACK Reply) for the 
      request.
      nak - Send a negative acknowledgement (NAK Reply) for the 
      request."
   DEFVAL     { nak }
::= { vrIpNhrpNhsEpProvEntry 1 }

vrIpNhrpNhsEpProtocol OBJECT-TYPE
   SYNTAX     INTEGER  {
                 default(0),
                 staticLocal(1) }
   ACCESS     read-write
   STATUS     mandatory
   DESCRIPTION
     "This attribute species the reachability type (that is, protocol) of the 
      destination in the NHRP Resolution Request. The possible 
      protocols:
      default - This value is a 'wildcard' and matches any protocol. A 
      policy with a 'wildcard' protocol is less preferred than a policy with 
      a protocol which matches exactly.
      staticLocal - The destination is on a locally attached network."
   DEFVAL     { default }
::= { vrIpNhrpNhsEpProvEntry 2 }


-- Vr/<string> Ip Nhrp Nhs Ep/n NetworkAddress/n
-- This component represents the source and destination address pairs 
-- for an NHRP egress policy.

vrIpNhrpNhsEpNetAddr OBJECT IDENTIFIER ::= { vrIpNhrpNhsEp 2 }



vrIpNhrpNhsEpNetAddrRowStatusTable OBJECT-TYPE
   SYNTAX     SEQUENCE OF VrIpNhrpNhsEpNetAddrRowStatusEntry
   ACCESS     not-accessible
   STATUS     mandatory
   DESCRIPTION
     "This entry controls the addition and deletion of 
      vrIpNhrpNhsEpNetAddr components."
::= { vrIpNhrpNhsEpNetAddr 1 }

vrIpNhrpNhsEpNetAddrRowStatusEntry OBJECT-TYPE
   SYNTAX     VrIpNhrpNhsEpNetAddrRowStatusEntry
   ACCESS     not-accessible
   STATUS     mandatory
   DESCRIPTION
     "A single entry in the table represents a single 
      vrIpNhrpNhsEpNetAddr component."
   INDEX {
      vrIndex,
      vrIpIndex,
      vrIpNhrpIndex,
      vrIpNhrpNhsIndex,
      vrIpNhrpNhsEpIndex,
      vrIpNhrpNhsEpNetAddrIndex }
::= { vrIpNhrpNhsEpNetAddrRowStatusTable 1 }

VrIpNhrpNhsEpNetAddrRowStatusEntry ::= SEQUENCE {
   vrIpNhrpNhsEpNetAddrRowStatus
      RowStatus,
   vrIpNhrpNhsEpNetAddrComponentName
      DisplayString,
   vrIpNhrpNhsEpNetAddrStorageType
      StorageType,
   vrIpNhrpNhsEpNetAddrIndex
      Integer32 }

vrIpNhrpNhsEpNetAddrRowStatus OBJECT-TYPE
   SYNTAX     RowStatus 
   ACCESS     read-write
   STATUS     mandatory
   DESCRIPTION
     "This variable is used as the basis for SNMP naming of
      vrIpNhrpNhsEpNetAddr components.
      These components can be added and deleted."
::= { vrIpNhrpNhsEpNetAddrRowStatusEntry 1 }

vrIpNhrpNhsEpNetAddrComponentName OBJECT-TYPE
   SYNTAX     DisplayString 
   ACCESS     read-only
   STATUS     mandatory
   DESCRIPTION
     "This variable provides the component's string name for
      use with the ASCII Console Interface"
::= { vrIpNhrpNhsEpNetAddrRowStatusEntry 2 }

vrIpNhrpNhsEpNetAddrStorageType OBJECT-TYPE
   SYNTAX     StorageType 
   ACCESS     read-only
   STATUS     mandatory
   DESCRIPTION
     "This variable represents the storage type value for the
      vrIpNhrpNhsEpNetAddr tables."
::= { vrIpNhrpNhsEpNetAddrRowStatusEntry 4 }

vrIpNhrpNhsEpNetAddrIndex OBJECT-TYPE
   SYNTAX     Integer32 (0..65535)
   ACCESS     not-accessible
   STATUS     mandatory
   DESCRIPTION
     "This variable represents the index for the vrIpNhrpNhsEpNetAddr tables."
::= { vrIpNhrpNhsEpNetAddrRowStatusEntry 10 }

vrIpNhrpNhsEpNetAddrProvTable OBJECT-TYPE
   SYNTAX     SEQUENCE OF VrIpNhrpNhsEpNetAddrProvEntry
   ACCESS     not-accessible
   STATUS     mandatory
   DESCRIPTION
     "This group contains the provisionable attributes of the 
      NetworkAddress component."
::= { vrIpNhrpNhsEpNetAddr 10 }

vrIpNhrpNhsEpNetAddrProvEntry OBJECT-TYPE
   SYNTAX     VrIpNhrpNhsEpNetAddrProvEntry
   ACCESS     not-accessible
   STATUS     mandatory
   DESCRIPTION
     "An entry in the vrIpNhrpNhsEpNetAddrProvTable."
   INDEX {
      vrIndex,
      vrIpIndex,
      vrIpNhrpIndex,
      vrIpNhrpNhsIndex,
      vrIpNhrpNhsEpIndex,
      vrIpNhrpNhsEpNetAddrIndex }
::= { vrIpNhrpNhsEpNetAddrProvTable 1 }

VrIpNhrpNhsEpNetAddrProvEntry ::= SEQUENCE {
   vrIpNhrpNhsEpNetAddrSourceAddress
      IpAddress,
   vrIpNhrpNhsEpNetAddrSourceMask
      IpAddress,
   vrIpNhrpNhsEpNetAddrDestinationAddress
      IpAddress,
   vrIpNhrpNhsEpNetAddrDestinationMask
      IpAddress }

vrIpNhrpNhsEpNetAddrSourceAddress OBJECT-TYPE
   SYNTAX     IpAddress 
   ACCESS     read-write
   STATUS     mandatory
   DESCRIPTION
     "This attribute specifies the internetwork address of the source. This 
      is used to match a source internetwork address in an NHRP 
      Resolution Request."
   DEFVAL     { '00000000'H }  -- "0.0.0.0"
::= { vrIpNhrpNhsEpNetAddrProvEntry 1 }

vrIpNhrpNhsEpNetAddrSourceMask OBJECT-TYPE
   SYNTAX     IpAddress 
   ACCESS     read-write
   STATUS     mandatory
   DESCRIPTION
     "This attribute specifies the netmask for the source internetwork 
      address."
   DEFVAL     { '00000000'H }  -- "0.0.0.0"
::= { vrIpNhrpNhsEpNetAddrProvEntry 2 }

vrIpNhrpNhsEpNetAddrDestinationAddress OBJECT-TYPE
   SYNTAX     IpAddress 
   ACCESS     read-write
   STATUS     mandatory
   DESCRIPTION
     "This attribute specifies the internetwork address of the destination. 
      This is used to match a destination internetwork address in an 
      NHRP Resolution Request."
   DEFVAL     { '00000000'H }  -- "0.0.0.0"
::= { vrIpNhrpNhsEpNetAddrProvEntry 3 }

vrIpNhrpNhsEpNetAddrDestinationMask OBJECT-TYPE
   SYNTAX     IpAddress 
   ACCESS     read-write
   STATUS     mandatory
   DESCRIPTION
     "This attribute specifies the netmask for the destination internetwork 
      address."
   DEFVAL     { '00000000'H }  -- "0.0.0.0"
::= { vrIpNhrpNhsEpNetAddrProvEntry 4 }


-- Vr/<string> Ip Nhrp NextHopClient
-- This component represents the NHRP client. The client initiates 
-- NHRP requests of various types in order to obtain access to the 
-- NHRP service.

vrIpNhrpNhc OBJECT IDENTIFIER ::= { vrIpNhrp 3 }



vrIpNhrpNhcRowStatusTable OBJECT-TYPE
   SYNTAX     SEQUENCE OF VrIpNhrpNhcRowStatusEntry
   ACCESS     not-accessible
   STATUS     mandatory
   DESCRIPTION
     "This entry controls the addition and deletion of 
      vrIpNhrpNhc components."
::= { vrIpNhrpNhc 1 }

vrIpNhrpNhcRowStatusEntry OBJECT-TYPE
   SYNTAX     VrIpNhrpNhcRowStatusEntry
   ACCESS     not-accessible
   STATUS     mandatory
   DESCRIPTION
     "A single entry in the table represents a single 
      vrIpNhrpNhc component."
   INDEX {
      vrIndex,
      vrIpIndex,
      vrIpNhrpIndex,
      vrIpNhrpNhcIndex }
::= { vrIpNhrpNhcRowStatusTable 1 }

VrIpNhrpNhcRowStatusEntry ::= SEQUENCE {
   vrIpNhrpNhcRowStatus
      RowStatus,
   vrIpNhrpNhcComponentName
      DisplayString,
   vrIpNhrpNhcStorageType
      StorageType,
   vrIpNhrpNhcIndex
      NonReplicated }

vrIpNhrpNhcRowStatus OBJECT-TYPE
   SYNTAX     RowStatus 
   ACCESS     read-only
   STATUS     mandatory
   DESCRIPTION
     "This variable is used as the basis for SNMP naming of
      vrIpNhrpNhc components.
      These components cannot be added nor deleted."
::= { vrIpNhrpNhcRowStatusEntry 1 }

vrIpNhrpNhcComponentName OBJECT-TYPE
   SYNTAX     DisplayString 
   ACCESS     read-only
   STATUS     mandatory
   DESCRIPTION
     "This variable provides the component's string name for
      use with the ASCII Console Interface"
::= { vrIpNhrpNhcRowStatusEntry 2 }

vrIpNhrpNhcStorageType OBJECT-TYPE
   SYNTAX     StorageType 
   ACCESS     read-only
   STATUS     mandatory
   DESCRIPTION
     "This variable represents the storage type value for the
      vrIpNhrpNhc tables."
::= { vrIpNhrpNhcRowStatusEntry 4 }

vrIpNhrpNhcIndex OBJECT-TYPE
   SYNTAX     NonReplicated 
   ACCESS     not-accessible
   STATUS     mandatory
   DESCRIPTION
     "This variable represents the index for the vrIpNhrpNhc tables."
::= { vrIpNhrpNhcRowStatusEntry 10 }

vrIpNhrpNhcProvTable OBJECT-TYPE
   SYNTAX     SEQUENCE OF VrIpNhrpNhcProvEntry
   ACCESS     not-accessible
   STATUS     mandatory
   DESCRIPTION
     "This group contains the provisionable attributes of the Nhc 
      component."
::= { vrIpNhrpNhc 10 }

vrIpNhrpNhcProvEntry OBJECT-TYPE
   SYNTAX     VrIpNhrpNhcProvEntry
   ACCESS     not-accessible
   STATUS     mandatory
   DESCRIPTION
     "An entry in the vrIpNhrpNhcProvTable."
   INDEX {
      vrIndex,
      vrIpIndex,
      vrIpNhrpIndex,
      vrIpNhrpNhcIndex }
::= { vrIpNhrpNhcProvTable 1 }

VrIpNhrpNhcProvEntry ::= SEQUENCE {
   vrIpNhrpNhcFlowDetectPacketCount
      Unsigned32,
   vrIpNhrpNhcFlowDetectTimePeriod
      INTEGER,
   vrIpNhrpNhcIdleDetectPacketCount
      Unsigned32,
   vrIpNhrpNhcIdleDetectTimePeriod
      Unsigned32,
   vrIpNhrpNhcAtmFlowDetection
      INTEGER }

vrIpNhrpNhcFlowDetectPacketCount OBJECT-TYPE
   SYNTAX     Unsigned32 (1..4292967295)
   ACCESS     read-write
   STATUS     mandatory
   DESCRIPTION
     "This attribute, along with flowDetectTimePeriod, specifies the IP 
      traffic flow detection threshold; If the number of IP packets sent to a 
      particular destination within the time interval specified by 
      flowDetectTimePeriod exceeds the value specified by 
      flowDetectPacketCount, then an NHRP Resolution Request will be 
      triggerred. If successful, a shortcut will be set up."
   DEFVAL     { 600 }
::= { vrIpNhrpNhcProvEntry 1 }

vrIpNhrpNhcFlowDetectTimePeriod OBJECT-TYPE
   SYNTAX     INTEGER (10 | 20 | 30 | 40 | 50 | 60)
   ACCESS     read-write
   STATUS     mandatory
   DESCRIPTION
     "This attribute, along with flowDetectPacketCount, specifies the IP 
      traffic flow detection threshold; If the number of IP packets sent to a 
      particular destination within the time interval specified by 
      flowDetectTimePeriod exceeds the value specified by 
      flowDetectPacketCount, then an NHRP Resolution Request will be 
      triggerred. If successful, a shortcut will be set up."
   DEFVAL     { 60 }
::= { vrIpNhrpNhcProvEntry 2 }

vrIpNhrpNhcIdleDetectPacketCount OBJECT-TYPE
   SYNTAX     Unsigned32 (1..4292967295)
   ACCESS     read-write
   STATUS     mandatory
   DESCRIPTION
     "This attribute, along with idleDetectTimePeriod, specifies the idle 
      shortcut threshold; If the number of frames transmitted over an 
      outgoing shortcut, or received over an incoming shortcut, within the 
      time interval specified by idleDetectTimePeriod falls below the 
      value specified by idleDetectPacketCount, then the shortcut 
      connection will be released."
   DEFVAL     { 900 }
::= { vrIpNhrpNhcProvEntry 3 }

vrIpNhrpNhcIdleDetectTimePeriod OBJECT-TYPE
   SYNTAX     Unsigned32 (1..30)
   ACCESS     read-write
   STATUS     mandatory
   DESCRIPTION
     "This attribute, along with idleDetectPacketCount, specifies the idle 
      shortcut threshold; If the number of frames transmitted over an 
      outgoing shortcut, or received over an incoming shortcut, within the 
      time interval specified by idleDetectTimePeriod falls below the 
      value specified by idleDetectPacketCount, then the shortcut 
      connection will be released."
   DEFVAL     { 3 }
::= { vrIpNhrpNhcProvEntry 4 }

vrIpNhrpNhcAtmFlowDetection OBJECT-TYPE
   SYNTAX     INTEGER  {
                 enabled(1),
                 disabled(2) }
   ACCESS     read-write
   STATUS     mandatory
   DESCRIPTION
     "This attribute specifies whether flow detection should be performed 
      for IP traffic received on ATM cards. This attribute does not apply 
      to IP traffic received on LAN or non-ATM WAN cards."
   DEFVAL     { disabled }
::= { vrIpNhrpNhcProvEntry 5 }

vrIpNhrpNhcStatsTable OBJECT-TYPE
   SYNTAX     SEQUENCE OF VrIpNhrpNhcStatsEntry
   ACCESS     not-accessible
   STATUS     mandatory
   DESCRIPTION
     "This group contains the statistics attributes of the Nhc component."
::= { vrIpNhrpNhc 11 }

vrIpNhrpNhcStatsEntry OBJECT-TYPE
   SYNTAX     VrIpNhrpNhcStatsEntry
   ACCESS     not-accessible
   STATUS     mandatory
   DESCRIPTION
     "An entry in the vrIpNhrpNhcStatsTable."
   INDEX {
      vrIndex,
      vrIpIndex,
      vrIpNhrpIndex,
      vrIpNhrpNhcIndex }
::= { vrIpNhrpNhcStatsTable 1 }

VrIpNhrpNhcStatsEntry ::= SEQUENCE {
   vrIpNhrpNhcTxResolveReq
      Counter32,
   vrIpNhrpNhcRxResolveReplyAck
      Counter32,
   vrIpNhrpNhcRxResolveReplyNakProhibited
      Counter32,
   vrIpNhrpNhcRxResolveReplyNakInsufResources
      Counter32,
   vrIpNhrpNhcRxResolveReplyNakNoBinding
      Counter32,
   vrIpNhrpNhcRxResolveReplyNakNotUnique
      Counter32,
   vrIpNhrpNhcRxPurgeReq
      Counter32,
   vrIpNhrpNhcTxPurgeReq
      Counter32,
   vrIpNhrpNhcRxPurgeReply
      Counter32,
   vrIpNhrpNhcTxPurgeReply
      Counter32,
   vrIpNhrpNhcTxErrIndication
      Counter32,
   vrIpNhrpNhcRxErrUnrecognizedExtension
      Counter32,
   vrIpNhrpNhcRxErrLoopDetected
      Counter32,
   vrIpNhrpNhcRxErrProtoAddrUnreachable
      Counter32,
   vrIpNhrpNhcRxErrProtoError
      Counter32,
   vrIpNhrpNhcRxErrSduSizeExceeded
      Counter32,
   vrIpNhrpNhcRxErrInvalidExtension
      Counter32,
   vrIpNhrpNhcRxErrAuthenticationFailure
      Counter32,
   vrIpNhrpNhcRxErrHopCountExceeded
      Counter32 }

vrIpNhrpNhcTxResolveReq OBJECT-TYPE
   SYNTAX     Counter32 
   ACCESS     read-only
   STATUS     mandatory
   DESCRIPTION
     "This attribute counts the NHRP Resolution Requests transmitted by 
      this client. 
      This counter wraps to zero when the maximum value is exceeded."
::= { vrIpNhrpNhcStatsEntry 1 }

vrIpNhrpNhcRxResolveReplyAck OBJECT-TYPE
   SYNTAX     Counter32 
   ACCESS     read-only
   STATUS     mandatory
   DESCRIPTION
     "This attribute counts the positively acknowledged NHRP Resolution 
      Replies received by this client.
      This counter wraps to zero when the maximum value is exceeded."
::= { vrIpNhrpNhcStatsEntry 2 }

vrIpNhrpNhcRxResolveReplyNakProhibited OBJECT-TYPE
   SYNTAX     Counter32 
   ACCESS     read-only
   STATUS     mandatory
   DESCRIPTION
     "This attribute counts the NAK NHRP Resolution Replies received 
      by this client that contained the code indicating 'Administratively 
      Prohibited'. 
      This counter wraps to zero when the maximum value is exceeded."
::= { vrIpNhrpNhcStatsEntry 3 }

vrIpNhrpNhcRxResolveReplyNakInsufResources OBJECT-TYPE
   SYNTAX     Counter32 
   ACCESS     read-only
   STATUS     mandatory
   DESCRIPTION
     "This attribute counts the NAK NHRP Resolution Replies received 
      by this client that contained the code indicating 'Insufficient 
      Resources'. 
      This counter wraps to zero when the maximum value is exceeded."
::= { vrIpNhrpNhcStatsEntry 4 }

vrIpNhrpNhcRxResolveReplyNakNoBinding OBJECT-TYPE
   SYNTAX     Counter32 
   ACCESS     read-only
   STATUS     mandatory
   DESCRIPTION
     "This attribute counts the NAK NHRP Resolution Replies received 
      by this client that contained the code indicating 'No 
      Internetworking Layer Address to NBMA Address Binding Exists'. 
      This counter wraps to zero when the maximum value is exceeded."
::= { vrIpNhrpNhcStatsEntry 5 }

vrIpNhrpNhcRxResolveReplyNakNotUnique OBJECT-TYPE
   SYNTAX     Counter32 
   ACCESS     read-only
   STATUS     mandatory
   DESCRIPTION
     "This attribute counts the NAK NHRP Resolution Replies received 
      by this client that contained the code indicating 'Binding Exists But 
      Is Not Unique'. 
      This counter wraps to zero when the maximum value is exceeded."
::= { vrIpNhrpNhcStatsEntry 6 }

vrIpNhrpNhcRxPurgeReq OBJECT-TYPE
   SYNTAX     Counter32 
   ACCESS     read-only
   STATUS     mandatory
   DESCRIPTION
     "This attribute counts the NHRP Purge Requests received by this 
      client. 
      This counter wraps to zero when the maximum value is exceeded."
::= { vrIpNhrpNhcStatsEntry 12 }

vrIpNhrpNhcTxPurgeReq OBJECT-TYPE
   SYNTAX     Counter32 
   ACCESS     read-only
   STATUS     mandatory
   DESCRIPTION
     "This attribute counts the NHRP Purge Requests transmitted by this 
      client.
      This counter wraps to zero when the maximum value is exceeded."
::= { vrIpNhrpNhcStatsEntry 13 }

vrIpNhrpNhcRxPurgeReply OBJECT-TYPE
   SYNTAX     Counter32 
   ACCESS     read-only
   STATUS     mandatory
   DESCRIPTION
     "This attribute counts the NHRP Purge Replies received by this 
      client.
      This counter wraps to zero when the maximum value is exceeded."
::= { vrIpNhrpNhcStatsEntry 14 }

vrIpNhrpNhcTxPurgeReply OBJECT-TYPE
   SYNTAX     Counter32 
   ACCESS     read-only
   STATUS     mandatory
   DESCRIPTION
     "This attribute counts the NHRP Purge Replies transmitted by this 
      client.
      This counter wraps to zero when the maximum value is exceeded."
::= { vrIpNhrpNhcStatsEntry 15 }

vrIpNhrpNhcTxErrIndication OBJECT-TYPE
   SYNTAX     Counter32 
   ACCESS     read-only
   STATUS     mandatory
   DESCRIPTION
     "This attribute counts the NHRP Error Indication packets transmitted 
      by this client.
      This counter wraps to zero when the maximum value is exceeded."
::= { vrIpNhrpNhcStatsEntry 16 }

vrIpNhrpNhcRxErrUnrecognizedExtension OBJECT-TYPE
   SYNTAX     Counter32 
   ACCESS     read-only
   STATUS     mandatory
   DESCRIPTION
     "This attribute counts the NHRP Error Indication packets received by 
      this client with the error code 'Unrecognized Extension'. 
      This counter wraps to zero when the maximum value is exceeded."
::= { vrIpNhrpNhcStatsEntry 17 }

vrIpNhrpNhcRxErrLoopDetected OBJECT-TYPE
   SYNTAX     Counter32 
   ACCESS     read-only
   STATUS     mandatory
   DESCRIPTION
     "This attribute counts the NHRP Error Indication packets received by 
      this client with the error code 'NHRP Loop Detected'. 
      This counter wraps to zero when the maximum value is exceeded."
::= { vrIpNhrpNhcStatsEntry 18 }

vrIpNhrpNhcRxErrProtoAddrUnreachable OBJECT-TYPE
   SYNTAX     Counter32 
   ACCESS     read-only
   STATUS     mandatory
   DESCRIPTION
     "This attribute counts the NHRP Error Indication packets received by 
      this client with the error code 'Protocol Address Unreachable'. 
      This counter wraps to zero when the maximum value is exceeded."
::= { vrIpNhrpNhcStatsEntry 19 }

vrIpNhrpNhcRxErrProtoError OBJECT-TYPE
   SYNTAX     Counter32 
   ACCESS     read-only
   STATUS     mandatory
   DESCRIPTION
     "This attribute counts the NHRP Error Indication packets received by 
      this client with the error code 'Protocol Error'. 
      This counter wraps to zero when the maximum value is exceeded."
::= { vrIpNhrpNhcStatsEntry 20 }

vrIpNhrpNhcRxErrSduSizeExceeded OBJECT-TYPE
   SYNTAX     Counter32 
   ACCESS     read-only
   STATUS     mandatory
   DESCRIPTION
     "This attribute counts the NHRP Error Indication packets received by 
      this client with the error code 'NHRP SDU Size Exceeded'. 
      This counter wraps to zero when the maximum value is exceeded."
::= { vrIpNhrpNhcStatsEntry 21 }

vrIpNhrpNhcRxErrInvalidExtension OBJECT-TYPE
   SYNTAX     Counter32 
   ACCESS     read-only
   STATUS     mandatory
   DESCRIPTION
     "This attribute counts the NHRP Error Indication packets received by 
      this client with the error code 'Invalid Extension'.
      This counter wraps to zero when the maximum value is exceeded."
::= { vrIpNhrpNhcStatsEntry 22 }

vrIpNhrpNhcRxErrAuthenticationFailure OBJECT-TYPE
   SYNTAX     Counter32 
   ACCESS     read-only
   STATUS     mandatory
   DESCRIPTION
     "This attribute counts the NHRP Error Indication packets received by 
      this client with the error code 'Authentication Failure'. 
      This counter wraps to zero when the maximum value is exceeded."
::= { vrIpNhrpNhcStatsEntry 23 }

vrIpNhrpNhcRxErrHopCountExceeded OBJECT-TYPE
   SYNTAX     Counter32 
   ACCESS     read-only
   STATUS     mandatory
   DESCRIPTION
     "This attribute counts the NHRP Error Indication packets received by 
      this client with the error code 'Hop Count Exceeded'. 
      This counter wraps to zero when the maximum value is exceeded."
::= { vrIpNhrpNhcStatsEntry 24 }

-- 
-- *** THIS SUBTREE CURRENTLY NOT IMPLEMENTED ***
-- 

-- Vr/<string> Ip Nhrp ResCacheEntry/<ipAddress>,<mask>
-- This component represents an entry in the NHRP resolution cache 
-- table.

vrIpNhrpRce OBJECT IDENTIFIER ::= { vrIpNhrp 4 }



vrIpNhrpRceRowStatusTable OBJECT-TYPE
   SYNTAX     SEQUENCE OF VrIpNhrpRceRowStatusEntry
   ACCESS     not-accessible
   STATUS     mandatory
   DESCRIPTION
     "*** THIS TABLE CURRENTLY NOT IMPLEMENTED ***

      This entry controls the addition and deletion of 
      vrIpNhrpRce components."
::= { vrIpNhrpRce 1 }

vrIpNhrpRceRowStatusEntry OBJECT-TYPE
   SYNTAX     VrIpNhrpRceRowStatusEntry
   ACCESS     not-accessible
   STATUS     mandatory
   DESCRIPTION
     "A single entry in the table represents a single 
      vrIpNhrpRce component."
   INDEX {
      vrIndex,
      vrIpIndex,
      vrIpNhrpIndex,
      vrIpNhrpRceDestAddrIndex,
      vrIpNhrpRceDestMaskIndex }
::= { vrIpNhrpRceRowStatusTable 1 }

VrIpNhrpRceRowStatusEntry ::= SEQUENCE {
   vrIpNhrpRceRowStatus
      RowStatus,
   vrIpNhrpRceComponentName
      DisplayString,
   vrIpNhrpRceStorageType
      StorageType,
   vrIpNhrpRceDestAddrIndex
      IpAddress,
   vrIpNhrpRceDestMaskIndex
      IpAddress }

vrIpNhrpRceRowStatus OBJECT-TYPE
   SYNTAX     RowStatus 
   ACCESS     read-only
   STATUS     mandatory
   DESCRIPTION
     "This variable is used as the basis for SNMP naming of
      vrIpNhrpRce components.
      These components cannot be added nor deleted."
::= { vrIpNhrpRceRowStatusEntry 1 }

vrIpNhrpRceComponentName OBJECT-TYPE
   SYNTAX     DisplayString 
   ACCESS     read-only
   STATUS     mandatory
   DESCRIPTION
     "This variable provides the component's string name for
      use with the ASCII Console Interface"
::= { vrIpNhrpRceRowStatusEntry 2 }

vrIpNhrpRceStorageType OBJECT-TYPE
   SYNTAX     StorageType 
   ACCESS     read-only
   STATUS     mandatory
   DESCRIPTION
     "This variable represents the storage type value for the
      vrIpNhrpRce tables."
::= { vrIpNhrpRceRowStatusEntry 4 }

vrIpNhrpRceDestAddrIndex OBJECT-TYPE
   SYNTAX     IpAddress 
   ACCESS     not-accessible
   STATUS     mandatory
   DESCRIPTION
     "This variable represents an index for the vrIpNhrpRce tables."
::= { vrIpNhrpRceRowStatusEntry 10 }

vrIpNhrpRceDestMaskIndex OBJECT-TYPE
   SYNTAX     IpAddress 
   ACCESS     not-accessible
   STATUS     mandatory
   DESCRIPTION
     "This variable represents an index for the vrIpNhrpRce tables."
::= { vrIpNhrpRceRowStatusEntry 11 }

vrIpNhrpRceOperTable OBJECT-TYPE
   SYNTAX     SEQUENCE OF VrIpNhrpRceOperEntry
   ACCESS     not-accessible
   STATUS     mandatory
   DESCRIPTION
     "*** THIS TABLE CURRENTLY NOT IMPLEMENTED ***

      This group contains the operational attributes of the ResCacheEntry 
      component."
::= { vrIpNhrpRce 10 }

vrIpNhrpRceOperEntry OBJECT-TYPE
   SYNTAX     VrIpNhrpRceOperEntry
   ACCESS     not-accessible
   STATUS     mandatory
   DESCRIPTION
     "An entry in the vrIpNhrpRceOperTable."
   INDEX {
      vrIndex,
      vrIpIndex,
      vrIpNhrpIndex,
      vrIpNhrpRceDestAddrIndex,
      vrIpNhrpRceDestMaskIndex }
::= { vrIpNhrpRceOperTable 1 }

VrIpNhrpRceOperEntry ::= SEQUENCE {
   vrIpNhrpRceNbmaAddress
      HexString,
   vrIpNhrpRceEntryState
      INTEGER,
   vrIpNhrpRceHoldingTime
      Unsigned32,
   vrIpNhrpRceShortcut
      RowPointer }

vrIpNhrpRceNbmaAddress OBJECT-TYPE
   SYNTAX     HexString (SIZE (0..20))
   ACCESS     read-only
   STATUS     mandatory
   DESCRIPTION
     "This attribute indicates the NBMA subnetwork address of the next 
      hop."
::= { vrIpNhrpRceOperEntry 3 }

vrIpNhrpRceEntryState OBJECT-TYPE
   SYNTAX     INTEGER  {
                 incomplete(1),
                 ackReply(2),
                 nakReply(3),
                 noReply(10),
                 localReply(11) }
   ACCESS     read-only
   STATUS     mandatory
   DESCRIPTION
     "This attribute indicates the state of this resolution cache entry. The 
      possible states are:
      incomplete - The client sent the resolution request and is waiting for 
      a reply.
      ackReply - The client sent the resolution request and received an 
      ACK reply.
      nakReply - The client sent the resolution request and received a 
      NAK reply. This entry remains in the cache for 20 minutes thereby 
      preventing subsequent requests during that time period.
      noReply - The client sent the resolution request but did not receive a 
      reply. This entry remains in the cache for 20 minutes thereby 
      preventing subsequent requests during that time period.
      localReply - The client sent the resolution request and received an 
      ACK reply from a locally-attached responder. This entry remains in 
      the cache for 20 minutes thereby preventing subsequent requests 
      during that time period."
::= { vrIpNhrpRceOperEntry 6 }

vrIpNhrpRceHoldingTime OBJECT-TYPE
   SYNTAX     Unsigned32 (0..4294967295)
   ACCESS     read-only
   STATUS     mandatory
   DESCRIPTION
     "This attribute indicates the number of seconds that this entry will 
      remain in the resolution cache table. If the entry has not been 
      refreshed before this time it will be removed from the cache."
::= { vrIpNhrpRceOperEntry 7 }

vrIpNhrpRceShortcut OBJECT-TYPE
   SYNTAX     RowPointer 
   ACCESS     read-only
   STATUS     mandatory
   DESCRIPTION
     "This attribute indicates the component name of the shortcut 
      connection associated with this resolution cache entry. If the 
      component name is empty then no shortcut currently exists."
::= { vrIpNhrpRceOperEntry 8 }




-- 
-- Version and Compliance statements
-- 



-- Object-Group Statement:
-- A list of all current accessible leaf objects.

-- OBJECTS { vrIpNhrpNhsRxErrAuthenticationFailure,
--           vrIpNhrpNhcRowStatus,
--           vrIpNhrpRevTransitRecord,
--           vrIpNhrpNhsFwdErrorIndication,
--           vrIpNhrpNhsRxResolveReq,
--           vrIpNhrpNhsTxPurgeReq,
--           vrIpNhrpNhcFlowDetectPacketCount,
--           vrIpNhrpNhcRxPurgeReply,
--           vrIpNhrpCurrResCacheEntries,
--           vrIpNhrpPeakResCacheEntries,
--           vrIpNhrpNhsRxPurgeReply,
--           vrIpNhrpStorageType,
--           vrIpNhrpNhsEpAction,
--           vrIpNhrpNhcRxResolveReplyNakNoBinding,
--           vrIpNhrpNhsEpNetAddrSourceMask,
--           vrIpNhrpNhsTxErrSduSizeExceeded,
--           vrIpNhrpNhcTxErrIndication,
--           vrIpNhrpNhsFwdPurgeReq,
--           vrIpNhrpNhsRxErrProtoError,
--           vrIpNhrpNhsEpComponentName,
--           vrIpNhrpNhcTxResolveReq,
--           vrIpNhrpNhcRxResolveReplyNakInsufResources,
--           vrIpNhrpRceComponentName,
--           vrPpIpPortLogicalIfNhrpIfComponentName,
--           vrIpNhrpNhsRxErrLoopDetected,
--           vrIpNhrpNhsTxErrInvalidExtension,
--           vrIpNhrpRceNbmaAddress,
--           vrIpNhrpNhcIdleDetectTimePeriod,
--           vrIpNhrpNhcIdleDetectPacketCount,
--           vrIpNhrpRceShortcut,
--           vrIpNhrpNhsFwdRegisterReply,
--           vrIpNhrpNhsTxResolveReplyNakProhibited,
--           vrIpNhrpAdminState,
--           vrIpNhrpNhcTxPurgeReq,
--           vrIpNhrpNhcRxErrProtoAddrUnreachable,
--           vrIpNhrpNhcTxPurgeReply,
--           vrIpNhrpNhsRxPurgeReq,
--           vrIpNhrpNhsTxResolveReplyNakNotUnique,
--           vrIpNhrpNhsTxErrUnrecognizedExtension,
--           vrIpNhrpNhsEpNetAddrDestinationAddress,
--           vrIpNhrpNhcAtmFlowDetection,
--           vrIpNhrpRowStatus,
--           vrIpNhrpNhsTxErrAuthenticationFailure,
--           vrIpNhrpSnmpAdminStatus,
--           vrIpNhrpNhsEpProtocol,
--           vrIpNhrpNhsRxErrInvalidExtension,
--           vrIpNhrpNhcRxErrAuthenticationFailure,
--           vrIpNhrpNhsRxErrSduSizeExceeded,
--           vrIpNhrpNhsTxResolveReplyNakNoBinding,
--           vrIpNhrpNhcComponentName,
--           vrIpNhrpNhsEpNetAddrComponentName,
--           vrIpNhrpNhsTxErrProtoAddrUnreachable,
--           vrIpNhrpNhsStorageType,
--           vrIpNhrpUsageState,
--           vrIpNhrpNhsTxResolveReplyNakInsufResources,
--           vrIpNhrpNhsRxErrInvalidResReplyReceived,
--           vrIpNhrpNhsTxErrHopCountExceeded,
--           vrIpNhrpNhcRxErrProtoError,
--           vrIpNhrpRceRowStatus,
--           vrIpNhrpComponentName,
--           vrIpNhrpNhsEpStorageType,
--           vrIpNhrpNhcRxErrLoopDetected,
--           vrIpNhrpNhcRxPurgeReq,
--           vrIpNhrpNhsEpNetAddrRowStatus,
--           vrIpNhrpNhsFwdRegisterReq,
--           vrPpIpPortLogicalIfNhrpIfStorageType,
--           vrIpNhrpNhsEpNetAddrStorageType,
--           vrIpNhrpNhsRxErrUnrecognizedExtension,
--           vrIpNhrpNhsTxResolveReplyAck,
--           vrPpIpPortLogicalIfNhrpIfRowStatus,
--           vrIpNhrpOperationalState,
--           vrIpNhrpNhsTxPurgeReply,
--           vrIpNhrpNhsEpRowStatus,
--           vrIpNhrpNhsEpNetAddrDestinationMask,
--           vrIpNhrpNhcRxResolveReplyNakNotUnique,
--           vrIpNhrpNhcRxErrHopCountExceeded,
--           vrIpNhrpRceStorageType,
--           vrIpNhrpRceEntryState,
--           vrIpNhrpNhcRxErrSduSizeExceeded,
--           vrIpNhrpNhcRxErrInvalidExtension,
--           vrIpNhrpNhsRxRegisterReq,
--           vrIpNhrpNhsRowStatus,
--           vrIpNhrpNhsFwdPurgeReply,
--           vrIpNhrpMaxResCacheEntries,
--           vrIpNhrpNhsRxErrHopCountExceeded,
--           vrIpNhrpNhcFlowDetectTimePeriod,
--           vrIpNhrpNhsFwdResolveReq,
--           vrIpNhrpNhsFwdResolveReply,
--           vrIpNhrpNhsTxErrProtoError,
--           vrIpNhrpNhcRxResolveReplyAck,
--           vrIpNhrpNhcRxErrUnrecognizedExtension,
--           vrIpNhrpNhcStorageType,
--           vrIpNhrpNhsTxErrLoopDetected,
--           vrIpNhrpFwdTransitRecord,
--           vrIpNhrpNhsEpNetAddrSourceAddress,
--           vrIpNhrpRceHoldingTime,
--           vrIpNhrpNhcRxResolveReplyNakProhibited,
--           vrIpNhrpSnmpOperStatus,
--           vrIpNhrpNhsComponentName,
--           vrIpNhrpNhsRxErrProtoAddrUnreachable }
-- STATUS  mandatory
-- DESCRIPTION
--   "A list of all current accessible leaf objects."

ipNhrpGroup OBJECT IDENTIFIER ::= { ipNhrpMIB 1 }
ipNhrpGroupBE OBJECT IDENTIFIER ::= { ipNhrpGroup 5 }
ipNhrpGroupBE01 OBJECT IDENTIFIER ::= { ipNhrpGroupBE 2 }
ipNhrpGroupBE01A OBJECT IDENTIFIER ::= { ipNhrpGroupBE01 2 }



-- Agent-Capabilities Statement:

-- PRODUCT-RELEASE "Passport Release 7.0 IpNhrp."
-- STATUS          mandatory
-- DESCRIPTION     "IpNhrp MIB: MIB Version BE01A,
--                  Software Version BG00S4C."
-- SUPPORTS        Nortel-Magellan-Passport-IpNhrpMIB
--    INCLUDES     { ipNhrpGroupBE01A }

ipNhrpCapabilities OBJECT IDENTIFIER ::= { ipNhrpMIB 3 }
ipNhrpCapabilitiesBE OBJECT IDENTIFIER ::= { ipNhrpCapabilities 5 }
ipNhrpCapabilitiesBE01 OBJECT IDENTIFIER ::= { ipNhrpCapabilitiesBE 2 }
ipNhrpCapabilitiesBE01A OBJECT IDENTIFIER ::= { ipNhrpCapabilitiesBE01 2 }





END
