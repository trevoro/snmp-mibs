Nortel-Magellan-Passport-CircuitEmulationServiceMIB
DEFINITIONS ::= BEGIN



IMPORTS

      OBJECT-TYPE
   FROM RFC-1212

      components,
      passportMIBs
   FROM Nortel-Magellan-Passport-UsefulDefinitionsMIB

      Counter32,
      DisplayString,
      StorageType,
      RowStatus,
      PassportCounter64,
      Gauge32,
      Integer32,
      Unsigned32
   FROM Nortel-Magellan-Passport-StandardTextualConventionsMIB

      AsciiString,
      Hex,
      NonReplicated,
      EnterpriseDateAndTime,
      Link
   FROM Nortel-Magellan-Passport-TextualConventionsMIB;




-- LAST-UPDATED   "9702280000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     CircuitEmulationService Enterprise MIB."

circuitEmulationServiceMIB OBJECT IDENTIFIER ::= { passportMIBs 55 }










-- Aal11CircuitEmulationService/n
-- 
-- An Aal1Ces component identifies an instance of the AAL1 
-- Circuit Emulation Service provided by Magellan Passport.
-- 
-- A separate instance of this component is required for each 
-- logical channel of a port which is offering a constant bit 
-- rate service to a customer.
-- 
-- Instance numbers, which are used to uniquely identify 
-- Aal1Ces component instances, are arbitrary.

aal1Ces OBJECT IDENTIFIER ::= { components 119 }



aal1CesRowStatusTable OBJECT-TYPE
   SYNTAX     SEQUENCE OF Aal1CesRowStatusEntry
   ACCESS     not-accessible
   STATUS     mandatory
   DESCRIPTION
     "This entry controls the addition and deletion of 
      aal1Ces components."
::= { aal1Ces 1 }

aal1CesRowStatusEntry OBJECT-TYPE
   SYNTAX     Aal1CesRowStatusEntry
   ACCESS     not-accessible
   STATUS     mandatory
   DESCRIPTION
     "A single entry in the table represents a single 
      aal1Ces component."
   INDEX {
      aal1CesIndex }
::= { aal1CesRowStatusTable 1 }

Aal1CesRowStatusEntry ::= SEQUENCE {
   aal1CesRowStatus
      RowStatus,
   aal1CesComponentName
      DisplayString,
   aal1CesStorageType
      StorageType,
   aal1CesIndex
      Integer32 }

aal1CesRowStatus OBJECT-TYPE
   SYNTAX     RowStatus 
   ACCESS     read-write
   STATUS     mandatory
   DESCRIPTION
     "This variable is used as the basis for SNMP naming of
      aal1Ces components.
      These components can be added and deleted."
::= { aal1CesRowStatusEntry 1 }

aal1CesComponentName OBJECT-TYPE
   SYNTAX     DisplayString 
   ACCESS     read-only
   STATUS     mandatory
   DESCRIPTION
     "This variable provides the component's string name for
      use with the ASCII Console Interface"
::= { aal1CesRowStatusEntry 2 }

aal1CesStorageType OBJECT-TYPE
   SYNTAX     StorageType 
   ACCESS     read-only
   STATUS     mandatory
   DESCRIPTION
     "This variable represents the storage type value for the
      aal1Ces tables."
::= { aal1CesRowStatusEntry 4 }

aal1CesIndex OBJECT-TYPE
   SYNTAX     Integer32 (1..16383)
   ACCESS     not-accessible
   STATUS     mandatory
   DESCRIPTION
     "This variable represents the index for the aal1Ces tables."
::= { aal1CesRowStatusEntry 10 }

aal1CesCidDataTable OBJECT-TYPE
   SYNTAX     SEQUENCE OF Aal1CesCidDataEntry
   ACCESS     not-accessible
   STATUS     mandatory
   DESCRIPTION
     "This group contains the attribute for a component's Customer 
      Identifier (CID). Refer to the attribute description for a detailed 
      explanation of CIDs."
::= { aal1Ces 10 }

aal1CesCidDataEntry OBJECT-TYPE
   SYNTAX     Aal1CesCidDataEntry
   ACCESS     not-accessible
   STATUS     mandatory
   DESCRIPTION
     "An entry in the aal1CesCidDataTable."
   INDEX {
      aal1CesIndex }
::= { aal1CesCidDataTable 1 }

Aal1CesCidDataEntry ::= SEQUENCE {
   aal1CesCustomerIdentifier
      Unsigned32 }

aal1CesCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { aal1CesCidDataEntry 1 }

aal1CesProvTable OBJECT-TYPE
   SYNTAX     SEQUENCE OF Aal1CesProvEntry
   ACCESS     not-accessible
   STATUS     mandatory
   DESCRIPTION
     "This group contains basic provisioning data for the AAL1 
      Circuit Emulation Service."
::= { aal1Ces 11 }

aal1CesProvEntry OBJECT-TYPE
   SYNTAX     Aal1CesProvEntry
   ACCESS     not-accessible
   STATUS     mandatory
   DESCRIPTION
     "An entry in the aal1CesProvTable."
   INDEX {
      aal1CesIndex }
::= { aal1CesProvTable 1 }

Aal1CesProvEntry ::= SEQUENCE {
   aal1CesServiceType
      INTEGER,
   aal1CesBufferSize
      Unsigned32,
   aal1CesCellDelayVariationTolerance
      Unsigned32,
   aal1CesCellLossIntegrationPeriod
      Unsigned32,
   aal1CesInterfaceName
      Link,
   aal1CesPartialFill
      Unsigned32,
   aal1CesIdleSuppression
      INTEGER,
   aal1CesIdlePattern
      Hex,
   aal1CesCellLossRecoveryPeriod
      Unsigned32,
   aal1CesDummyDataByte
      Hex }

aal1CesServiceType OBJECT-TYPE
   SYNTAX     INTEGER  {
                 unstructured(0),
                 basicStructured(1),
                 casStructured(2) }
   ACCESS     read-write
   STATUS     mandatory
   DESCRIPTION
     "This attribute specifies the service type for the CES.
      
      In an unstructured service, the entire data stream at the 
      service interface (including any framing bits which may be 
      present) is passed across the network transparently.
      
      The unstructured service uses the Unstructured Data 
      Transfer (UDT) mode of AAL1.
      
      In a structured service, an Nx64kbit/s fraction of the data 
      stream at the service interface is passed across the network. 
      Two modes of structured service are supported: 
      basicStructured and casStructured. In a casStructured 
      service, the Channel Associated Signalling (CAS) bits are 
      carried in a separate data structure from the Nx64 payload; 
      in a basicStructured service they are not.
      
      The structured service uses the Structured Data Transfer 
      (SDT) mode as defined in ITU-T Recommendation 
      I.363.1.
      
      The serviceType attributes at both ends of a connection 
      must be the same."
   DEFVAL     { unstructured }
::= { aal1CesProvEntry 1 }

aal1CesBufferSize OBJECT-TYPE
   SYNTAX     Unsigned32 (94..15651)
   ACCESS     read-write
   STATUS     mandatory
   DESCRIPTION
     "This attribute defines the size of the AAL1 receive segment 
      reassembly buffer in bytes. The value of this attribute will 
      affect the overflow condition during AAL1 processing, that 
      is, increasing the buffer size will reduce the chance of an 
      overflow condition occurring. However, too large a buffer 
      may adversely impact the time needed to process the data 
      in the buffer."
   DEFVAL     { 282 }
::= { aal1CesProvEntry 2 }

aal1CesCellDelayVariationTolerance OBJECT-TYPE
   SYNTAX     Unsigned32 (1..655)
   ACCESS     read-write
   STATUS     mandatory
   DESCRIPTION
     "This attribute defines the maximum cell arrival jitter (in 
      milliseconds) that the AAL1 reassembly process will 
      tolerate in the ATM cell stream without producing errors 
      on the service interface.
      
      This attribute may be set to a small value if the CES 
      connection will produce minimal CDV and a large value if 
      the connection will produce a large CDV.
      
      This attribute, together with the attribute bufferSize, can be 
      configured to optimize the jitter versus absolute delay 
      trade-off in various network configurations."
   DEFVAL     { 1 }
::= { aal1CesProvEntry 3 }

aal1CesCellLossIntegrationPeriod OBJECT-TYPE
   SYNTAX     Unsigned32 (1000..60000)
   ACCESS     read-write
   STATUS     mandatory
   DESCRIPTION
     "This attribute defines the cell loss integration period. This 
      period defines the interval of time (in milliseconds) for 
      which a loss of cells condition must persist before a buffer 
      underflow alarm is raised. A loss of cells condition occurs 
      when the flow of cells to the AAL1 reassembly buffer 
      stops, causing a buffer underflow or starvation condition.
      
      The operational attribute cellLossStatus will be set to loss 
      when the buffer underflow alarm is raised, and noLoss 
      when it is cleared."
   DEFVAL     { 2000 }
::= { aal1CesProvEntry 4 }

aal1CesInterfaceName OBJECT-TYPE
   SYNTAX     Link 
   ACCESS     read-write
   STATUS     mandatory
   DESCRIPTION
     "This attribute identifies the instance of Chan to which an 
      instance of Aal1Ces is linked."
::= { aal1CesProvEntry 5 }

aal1CesPartialFill OBJECT-TYPE
   SYNTAX     Unsigned32 (8..47)
   ACCESS     read-write
   STATUS     mandatory
   DESCRIPTION
     "A significant source of delay in a structured service is the 
      amount of time it takes to collect enough data to fill a cell. 
      This period of time can be reduced by sending cells that 
      are only partially filled with data (idlePattern octets are 
      added to the ATM payload beyond the partial fill level).
      
      This attribute defines the number of payload octets to fill 
      with data. It is applicable to structured services only, and 
      must be set to 47 for unstructured services.
      
      On a given AAL1 Function Processor, the maximum cell 
      rate that can be sustained is dependent upon the combined 
      bandwidths of the provisioned services, and (for structured 
      services) the levels of partialFill. The smaller the 
      partialFill level, the greater the cell rate and hence the 
      fewer the services that can be sustained at that fill level."
   DEFVAL     { 47 }
::= { aal1CesProvEntry 6 }

aal1CesIdleSuppression OBJECT-TYPE
   SYNTAX     INTEGER  {
                 off(0),
                 on(1) }
   ACCESS     read-write
   STATUS     mandatory
   DESCRIPTION
     "This attribute controls the suppression of idle cells. An idle 
      cell is one in which the bytes of the ATM payload (up to 
      the partialFill level) match the idlePattern.
      
      If idleSuppression is off, idle cells are not suppressed.
      
      If idleSuppression is on, at least 75% of cells are 
      suppressed under idle conditions.
      
      The strategy is as follows: the first idle cell after a 
      sequence of non-idle cells is always sent; those that follow 
      are suppressed. Note, however, that at least one cell in 
      eight is always sent (to allow the receive end to regenerate 
      the suppressed cells) and more often than not, two cells are 
      sent (the cell containing the AAL1 pointer, which will 
      almost always fail to match, and the one after that)."
   DEFVAL     { off }
::= { aal1CesProvEntry 7 }

aal1CesIdlePattern OBJECT-TYPE
   SYNTAX     Hex (0..255)
   ACCESS     read-write
   STATUS     mandatory
   DESCRIPTION
     "This attribute specifies the pattern which the bytes of an 
      ATM payload, up to the partialFill level, must match in 
      order for the cell to be classified as idle. Payload bytes 
      beyond the partialFill level are not checked.
      
      The suppression of idle cells is controlled by the attribute 
      idleSuppression. If idleSuppression is on, at least 75% of 
      cells are suppressed under idle conditions."
   DEFVAL     { 126 }
::= { aal1CesProvEntry 8 }

aal1CesCellLossRecoveryPeriod OBJECT-TYPE
   SYNTAX     Unsigned32 (0..60)
   ACCESS     read-write
   STATUS     mandatory
   DESCRIPTION
     "This attribute defines the cell loss recovery period. This 
      period defines the interval of time (in seconds) for which a 
      loss of cells condition must desist before the buffer 
      underflow alarm is cleared.
      
      The operational attribute cellLossStatus will be set to 
      noLoss when the buffer underflow alarm is cleared."
   DEFVAL     { 20 }
::= { aal1CesProvEntry 9 }

aal1CesDummyDataByte OBJECT-TYPE
   SYNTAX     Hex (0..255)
   ACCESS     read-write
   STATUS     mandatory
   DESCRIPTION
     "This attribute defines the pattern which is played out onto 
      the service interface to maintain bit integrity when data is 
      unavailable from the ATM network.
      
      For an unstructured service (serviceType is set to 
      unstructured), dummyDataByte must be set to FF."
   DEFVAL     { 255 }
::= { aal1CesProvEntry 10 }

aal1CesStateTable OBJECT-TYPE
   SYNTAX     SEQUENCE OF Aal1CesStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { aal1Ces 12 }

aal1CesStateEntry OBJECT-TYPE
   SYNTAX     Aal1CesStateEntry
   ACCESS     not-accessible
   STATUS     mandatory
   DESCRIPTION
     "An entry in the aal1CesStateTable."
   INDEX {
      aal1CesIndex }
::= { aal1CesStateTable 1 }

Aal1CesStateEntry ::= SEQUENCE {
   aal1CesAdminState
      INTEGER,
   aal1CesOperationalState
      INTEGER,
   aal1CesUsageState
      INTEGER,
   aal1CesAvailabilityStatus
      OCTET STRING,
   aal1CesProceduralStatus
      OCTET STRING,
   aal1CesControlStatus
      OCTET STRING,
   aal1CesAlarmStatus
      OCTET STRING,
   aal1CesStandbyStatus
      INTEGER,
   aal1CesUnknownStatus
      INTEGER }

aal1CesAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { aal1CesStateEntry 1 }

aal1CesOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { aal1CesStateEntry 2 }

aal1CesUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { aal1CesStateEntry 3 }

aal1CesAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { aal1CesStateEntry 4 }

aal1CesProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { aal1CesStateEntry 5 }

aal1CesControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { aal1CesStateEntry 6 }

aal1CesAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { aal1CesStateEntry 7 }

aal1CesStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { aal1CesStateEntry 8 }

aal1CesUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { aal1CesStateEntry 9 }

aal1CesOperTable OBJECT-TYPE
   SYNTAX     SEQUENCE OF Aal1CesOperEntry
   ACCESS     not-accessible
   STATUS     mandatory
   DESCRIPTION
     "This group contains status information about the AAL1 
      Circuit Emulation Service."
::= { aal1Ces 13 }

aal1CesOperEntry OBJECT-TYPE
   SYNTAX     Aal1CesOperEntry
   ACCESS     not-accessible
   STATUS     mandatory
   DESCRIPTION
     "An entry in the aal1CesOperTable."
   INDEX {
      aal1CesIndex }
::= { aal1CesOperTable 1 }

Aal1CesOperEntry ::= SEQUENCE {
   aal1CesCellLossStatus
      INTEGER,
   aal1CesAal1LayerLossStatus
      INTEGER,
   aal1CesConnectionStatus
      INTEGER }

aal1CesCellLossStatus OBJECT-TYPE
   SYNTAX     INTEGER  {
                 noLoss(0),
                 loss(1) }
   ACCESS     read-only
   STATUS     mandatory
   DESCRIPTION
     "This attribute is set to loss when a buffer underflow alarm 
      is raised (see cellLossIntegrationPeriod), and noLoss 
      when it is clear."
   DEFVAL     { noLoss }
::= { aal1CesOperEntry 1 }

aal1CesAal1LayerLossStatus OBJECT-TYPE
   SYNTAX     INTEGER  {
                 noLoss(0),
                 loss(1) }
   ACCESS     read-only
   STATUS     mandatory
   DESCRIPTION
     "This attribute is set to loss when an AAL1 layer alarm is 
      raised, and noLoss when it is clear."
   DEFVAL     { noLoss }
::= { aal1CesOperEntry 2 }

aal1CesConnectionStatus OBJECT-TYPE
   SYNTAX     INTEGER  {
                 connected(0),
                 channelNotReady(1),
                 atmNotReady(2),
                 atmNotConfigured(3) }
   ACCESS     read-only
   STATUS     mandatory
   DESCRIPTION
     "This attribute indicates whether a service is non-
      operational because of a problem with the service interface 
      side of the service (in which case, it is set to 
      channelNotReady) or because of a problem with the ATM 
      side of the service (in which case, it is set to 
      atmNotConfigured or atmNotReady).
      
      When this attribute is set to channelNotReady, it is an 
      indication that the corresponding Chan component (as 
      defined by the attribute interfaceName) or the Chan 
      component's parent port component (Lp/n Ds1/m or Lp/n 
      E1/m) is locked.
      
      When this attribute is set to atmNotConfigured, it is an 
      indication that no sub-component has been provisioned, 
      and thus no ATM connection has been configured for the 
      service.
      
      When this attribute is set to atmNotReady, it is an 
      indication that the ATM connection with which the service 
      is associated (as defined by a sub-component) has been lost 
      or that it is currently unable to carry CES data.
      
      This attribute is set to connected when a service is 
      operational (that is, the OSI attribute operationalState is 
      enabled.)"
   DEFVAL     { channelNotReady }
::= { aal1CesOperEntry 3 }

aal1CesStatsTable OBJECT-TYPE
   SYNTAX     SEQUENCE OF Aal1CesStatsEntry
   ACCESS     not-accessible
   STATUS     mandatory
   DESCRIPTION
     "This group contains statistical data for an AAL1 Circuit 
      Emulation Service."
::= { aal1Ces 14 }

aal1CesStatsEntry OBJECT-TYPE
   SYNTAX     Aal1CesStatsEntry
   ACCESS     not-accessible
   STATUS     mandatory
   DESCRIPTION
     "An entry in the aal1CesStatsTable."
   INDEX {
      aal1CesIndex }
::= { aal1CesStatsTable 1 }

Aal1CesStatsEntry ::= SEQUENCE {
   aal1CesCellsTransmitted
      PassportCounter64,
   aal1CesCellsReceived
      PassportCounter64,
   aal1CesLostCells
      Counter32,
   aal1CesBufferUnderflows
      Counter32,
   aal1CesBufferOverflows
      Counter32,
   aal1CesReassembledCells
      PassportCounter64,
   aal1CesHeaderErrors
      Counter32,
   aal1CesPointerReframes
      Counter32,
   aal1CesPointerParityErrors
      Counter32,
   aal1CesAal1SequenceErrors
      Counter32,
   aal1CesMisinsertedCells
      Counter32 }

aal1CesCellsTransmitted OBJECT-TYPE
   SYNTAX     PassportCounter64 
   ACCESS     read-only
   STATUS     mandatory
   DESCRIPTION
     "This attribute counts the total number of cells transmitted 
      to the backplane (ingress direction). This includes cells 
      containing CBR data, trunk conditioning cells (structured 
      services), and unframed AIS cells (unstructured services).
      
      The counter wraps when the maximum value is exceeded."
::= { aal1CesStatsEntry 1 }

aal1CesCellsReceived OBJECT-TYPE
   SYNTAX     PassportCounter64 
   ACCESS     read-only
   STATUS     mandatory
   DESCRIPTION
     "This attribute counts the total number of cells received 
      from the backplane (egress direction). This includes CBR 
      user data cells, cells with AAL1 header errors (correctable 
      and non-correctable) and cells with AAL1 sequencing 
      errors. The counter wraps when the maximum value is 
      exceeded."
::= { aal1CesStatsEntry 2 }

aal1CesLostCells OBJECT-TYPE
   SYNTAX     Counter32 
   ACCESS     read-only
   STATUS     mandatory
   DESCRIPTION
     "This attribute counts the number of cells declared as never 
      received by the AAL1 protocol layer. The counter wraps 
      when the maximum value is exceeded."
::= { aal1CesStatsEntry 3 }

aal1CesBufferUnderflows OBJECT-TYPE
   SYNTAX     Counter32 
   ACCESS     read-only
   STATUS     mandatory
   DESCRIPTION
     "This attribute counts the number of times the AAL1 
      reassembly buffer underflows. In the case of a continuous 
      buffer starvation, a single buffer underflow event will be 
      counted. The counter wraps when the maximum value is 
      exceeded."
::= { aal1CesStatsEntry 4 }

aal1CesBufferOverflows OBJECT-TYPE
   SYNTAX     Counter32 
   ACCESS     read-only
   STATUS     mandatory
   DESCRIPTION
     "This attribute counts the number of times the AAL1 
      reassembly buffer overflows. Buffer overflows occur when 
      AAL1 cells arrive at a rate above that which is expected. 
      Occurrences of this condition may be reduced by 
      increasing the value of the attribute bufferSize. The buffer 
      overflow counter wraps when the maximum value is 
      exceeded."
::= { aal1CesStatsEntry 5 }

aal1CesReassembledCells OBJECT-TYPE
   SYNTAX     PassportCounter64 
   ACCESS     read-only
   STATUS     mandatory
   DESCRIPTION
     "This attribute counts the number of received cells whose 
      payload has been played out to the service interface. The 
      counter wraps when the maximum value is exceeded."
::= { aal1CesStatsEntry 6 }

aal1CesHeaderErrors OBJECT-TYPE
   SYNTAX     Counter32 
   ACCESS     read-only
   STATUS     mandatory
   DESCRIPTION
     "This attribute counts the number of cells received with 
      AAL1 header errors. The counter wraps when the 
      maximum value is exceeded."
::= { aal1CesStatsEntry 7 }

aal1CesPointerReframes OBJECT-TYPE
   SYNTAX     Counter32 
   ACCESS     read-only
   STATUS     mandatory
   DESCRIPTION
     "This attribute counts the number of times that the AAL1 
      reassembly unit found an SDT pointer where it was not 
      expected to be, and as a result had to reacquire it. Errors of 
      this kind can occur because of problems at the far end.
      
      This attribute is meaningful for structured services only, 
      and will be 0 for unstructured services.
      
      This counter wraps when the maximum value is exceeded."
::= { aal1CesStatsEntry 8 }

aal1CesPointerParityErrors OBJECT-TYPE
   SYNTAX     Counter32 
   ACCESS     read-only
   STATUS     mandatory
   DESCRIPTION
     "This attribute counts the number of times that the AAL1 
      reassembly unit detects a parity check failure at the point 
      where an SDT pointer is expected. Errors of this kind can 
      occur because of problems at the far end.
      
      This attribute is meaningful for structured services only, 
      and will be 0 for unstructured services.
      
      This counter wraps when the maximum value is exceeded."
::= { aal1CesStatsEntry 9 }

aal1CesAal1SequenceErrors OBJECT-TYPE
   SYNTAX     Counter32 
   ACCESS     read-only
   STATUS     mandatory
   DESCRIPTION
     "This attribute counts the number of times that the sequence 
      number of an incoming AAL1 Type 1 SAR-PDU gets out 
      of synchronisation, as defined by ITU-T Recommendation 
      I.363.1.
      
      This counter wraps when the maximum value is exceeded."
::= { aal1CesStatsEntry 10 }

aal1CesMisinsertedCells OBJECT-TYPE
   SYNTAX     Counter32 
   ACCESS     read-only
   STATUS     mandatory
   DESCRIPTION
     "This attribute counts the number of AAL1 sequence 
      violations which the AAL convergence sublayer interprets 
      as misinserted cells, as defined by ITU-T I.363.1.
      
      This counter wraps when the maximum value is exceeded."
::= { aal1CesStatsEntry 11 }


-- Aal1Ces/n NailedUpAdaptationPoint
-- 
-- A NailedUpAdaptationPoint is a nailed-up point which 
-- straddles the CBR/ATM domains and which is associated 
-- with the adaptation of CBR data to/from ATM cells.
-- 
-- If a NailedUpAdaptationPoint component is provisioned 
-- under an Aal1Ces component, no other components may 
-- be provisioned under the same Aal1Ces component.

aal1CesNap OBJECT IDENTIFIER ::= { aal1Ces 2 }



aal1CesNapRowStatusTable OBJECT-TYPE
   SYNTAX     SEQUENCE OF Aal1CesNapRowStatusEntry
   ACCESS     not-accessible
   STATUS     mandatory
   DESCRIPTION
     "This entry controls the addition and deletion of 
      aal1CesNap components."
::= { aal1CesNap 1 }

aal1CesNapRowStatusEntry OBJECT-TYPE
   SYNTAX     Aal1CesNapRowStatusEntry
   ACCESS     not-accessible
   STATUS     mandatory
   DESCRIPTION
     "A single entry in the table represents a single 
      aal1CesNap component."
   INDEX {
      aal1CesIndex,
      aal1CesNapIndex }
::= { aal1CesNapRowStatusTable 1 }

Aal1CesNapRowStatusEntry ::= SEQUENCE {
   aal1CesNapRowStatus
      RowStatus,
   aal1CesNapComponentName
      DisplayString,
   aal1CesNapStorageType
      StorageType,
   aal1CesNapIndex
      NonReplicated }

aal1CesNapRowStatus OBJECT-TYPE
   SYNTAX     RowStatus 
   ACCESS     read-write
   STATUS     mandatory
   DESCRIPTION
     "This variable is used as the basis for SNMP naming of
      aal1CesNap components.
      These components can be added and deleted."
::= { aal1CesNapRowStatusEntry 1 }

aal1CesNapComponentName OBJECT-TYPE
   SYNTAX     DisplayString 
   ACCESS     read-only
   STATUS     mandatory
   DESCRIPTION
     "This variable provides the component's string name for
      use with the ASCII Console Interface"
::= { aal1CesNapRowStatusEntry 2 }

aal1CesNapStorageType OBJECT-TYPE
   SYNTAX     StorageType 
   ACCESS     read-only
   STATUS     mandatory
   DESCRIPTION
     "This variable represents the storage type value for the
      aal1CesNap tables."
::= { aal1CesNapRowStatusEntry 4 }

aal1CesNapIndex OBJECT-TYPE
   SYNTAX     NonReplicated 
   ACCESS     not-accessible
   STATUS     mandatory
   DESCRIPTION
     "This variable represents the index for the aal1CesNap tables."
::= { aal1CesNapRowStatusEntry 10 }

aal1CesNapProvTable OBJECT-TYPE
   SYNTAX     SEQUENCE OF Aal1CesNapProvEntry
   ACCESS     not-accessible
   STATUS     mandatory
   DESCRIPTION
     "This group contains the provisioning data for the 
      NailedUpAdaptationPoint component."
::= { aal1CesNap 10 }

aal1CesNapProvEntry OBJECT-TYPE
   SYNTAX     Aal1CesNapProvEntry
   ACCESS     not-accessible
   STATUS     mandatory
   DESCRIPTION
     "An entry in the aal1CesNapProvTable."
   INDEX {
      aal1CesIndex,
      aal1CesNapIndex }
::= { aal1CesNapProvTable 1 }

Aal1CesNapProvEntry ::= SEQUENCE {
   aal1CesNapAtmConnection
      Link }

aal1CesNapAtmConnection OBJECT-TYPE
   SYNTAX     Link 
   ACCESS     read-write
   STATUS     mandatory
   DESCRIPTION
     "This attribute specifies the identity of the component to 
      which the NailedUpAdaptationPoint is linked. This will be 
      an AtmIf Vcc NailedUpEndPoint or an AtmIf Vpt Vcc 
      NailedUpEndPoint (the AAL1 cells are transported off the 
      switch via an ATM UNI, where they are routed to the 
      appropriate AAL1 entity at the other end by the ATM 
      bearer service)."
::= { aal1CesNapProvEntry 1 }


-- Aal1Ces/n ActiveEndPoint
-- 
-- The ActiveEndPoint component attempts to set up a 
-- switched virtual circuit automatically between two 
-- Passport CES components.
-- 
-- The ActiveEndPoint component will make connection 
-- setup attempts periodically whenever a connection has not 
-- been established. The component will cease connection 
-- setup attempts after a number of consecutive failed 
-- attempts, as specified by the retryLimit attribute.
-- 
-- The ActiveEndPoint component may also accept an 
-- incoming setup request if a connection is not already 
-- established. To be accepted, an incoming connection setup 
-- request must have originated from remoteAddress. 
-- Additionally, either connection attempts must have been 
-- ceased due to retryLimit consecutive failures, or the 
-- localAddress of the incoming connection setup request 
-- must be smaller than the remoteAddress of the request.
-- 
-- If an ActiveEndPoint component is provisioned under an 
-- Aal1Ces component, no other components may be 
-- provisioned under the same Aal1Ces component.

aal1CesAep OBJECT IDENTIFIER ::= { aal1Ces 3 }



aal1CesAepRowStatusTable OBJECT-TYPE
   SYNTAX     SEQUENCE OF Aal1CesAepRowStatusEntry
   ACCESS     not-accessible
   STATUS     mandatory
   DESCRIPTION
     "This entry controls the addition and deletion of 
      aal1CesAep components."
::= { aal1CesAep 1 }

aal1CesAepRowStatusEntry OBJECT-TYPE
   SYNTAX     Aal1CesAepRowStatusEntry
   ACCESS     not-accessible
   STATUS     mandatory
   DESCRIPTION
     "A single entry in the table represents a single 
      aal1CesAep component."
   INDEX {
      aal1CesIndex,
      aal1CesAepIndex }
::= { aal1CesAepRowStatusTable 1 }

Aal1CesAepRowStatusEntry ::= SEQUENCE {
   aal1CesAepRowStatus
      RowStatus,
   aal1CesAepComponentName
      DisplayString,
   aal1CesAepStorageType
      StorageType,
   aal1CesAepIndex
      NonReplicated }

aal1CesAepRowStatus OBJECT-TYPE
   SYNTAX     RowStatus 
   ACCESS     read-write
   STATUS     mandatory
   DESCRIPTION
     "This variable is used as the basis for SNMP naming of
      aal1CesAep components.
      These components can be added and deleted."
::= { aal1CesAepRowStatusEntry 1 }

aal1CesAepComponentName OBJECT-TYPE
   SYNTAX     DisplayString 
   ACCESS     read-only
   STATUS     mandatory
   DESCRIPTION
     "This variable provides the component's string name for
      use with the ASCII Console Interface"
::= { aal1CesAepRowStatusEntry 2 }

aal1CesAepStorageType OBJECT-TYPE
   SYNTAX     StorageType 
   ACCESS     read-only
   STATUS     mandatory
   DESCRIPTION
     "This variable represents the storage type value for the
      aal1CesAep tables."
::= { aal1CesAepRowStatusEntry 4 }

aal1CesAepIndex OBJECT-TYPE
   SYNTAX     NonReplicated 
   ACCESS     not-accessible
   STATUS     mandatory
   DESCRIPTION
     "This variable represents the index for the aal1CesAep tables."
::= { aal1CesAepRowStatusEntry 10 }

aal1CesAepProvEndPointAddrTable OBJECT-TYPE
   SYNTAX     SEQUENCE OF Aal1CesAepProvEndPointAddrEntry
   ACCESS     not-accessible
   STATUS     mandatory
   DESCRIPTION
     "This group contains NSAP address provisioning data for 
      components using switched virtual circuits."
::= { aal1CesAep 10 }

aal1CesAepProvEndPointAddrEntry OBJECT-TYPE
   SYNTAX     Aal1CesAepProvEndPointAddrEntry
   ACCESS     not-accessible
   STATUS     mandatory
   DESCRIPTION
     "An entry in the aal1CesAepProvEndPointAddrTable."
   INDEX {
      aal1CesIndex,
      aal1CesAepIndex }
::= { aal1CesAepProvEndPointAddrTable 1 }

Aal1CesAepProvEndPointAddrEntry ::= SEQUENCE {
   aal1CesAepExpectedRemoteAddress
      AsciiString,
   aal1CesAepLocalAddress
      AsciiString }

aal1CesAepExpectedRemoteAddress OBJECT-TYPE
   SYNTAX     AsciiString (SIZE (0..40))
   ACCESS     read-write
   STATUS     mandatory
   DESCRIPTION
     "This attribute specifies the expected remote address prefix 
      for an incoming connection setup request.
      
      If expectedRemoteAddress is not empty, only matching 
      connections will be considered for acceptance. If 
      expectedRemoteAddress is 40 characters long, the remote 
      address must match exactly to be accepted. If 
      expectedRemoteAddress is less than 40 characters long, the 
      remote address must begin with expectedRemoteAddress to 
      be accepted.
      
      If expectedRemoteAddress is empty, the component will 
      process connection requests from any remote address."
   DEFVAL     { ''H }  -- ""
::= { aal1CesAepProvEndPointAddrEntry 1 }

aal1CesAepLocalAddress OBJECT-TYPE
   SYNTAX     AsciiString (SIZE (40))
   ACCESS     read-write
   STATUS     mandatory
   DESCRIPTION
     "This attribute specifies the local NSAP address.
      
      If the switch prefix (the nodePrefix attribute of the 
      ModuleData component) has been provisioned, a default 
      value for localAddress based on nodePrefix will be 
      provided.
      
      If ModuleData nodePrefix has not been provisioned and 
      one or more alternate switch prefixes (the 
      alternatePorsPrefixes attribute of the ModuleData 
      component) have been provisioned, a default value for 
      localAddress based on the first provisioned 
      alternatePorsPrefix value will be provided.
      
      If no switch prefixes have been provisioned, localAddress 
      will default to an empty string. To obtain a valid default 
      localAddress in this case, either or both of the ModuleData 
      nodePrefix and ModuleData alternatePorsPrefixes 
      attributes must be provisioned, and this end point 
      component must then be deleted and re-added."
::= { aal1CesAepProvEndPointAddrEntry 2 }

aal1CesAepProvTable OBJECT-TYPE
   SYNTAX     SEQUENCE OF Aal1CesAepProvEntry
   ACCESS     not-accessible
   STATUS     mandatory
   DESCRIPTION
     "This group contains the provisioning data specific to the 
      ActiveEndPoint component."
::= { aal1CesAep 11 }

aal1CesAepProvEntry OBJECT-TYPE
   SYNTAX     Aal1CesAepProvEntry
   ACCESS     not-accessible
   STATUS     mandatory
   DESCRIPTION
     "An entry in the aal1CesAepProvTable."
   INDEX {
      aal1CesIndex,
      aal1CesAepIndex }
::= { aal1CesAepProvTable 1 }

Aal1CesAepProvEntry ::= SEQUENCE {
   aal1CesAepAddressToCall
      AsciiString,
   aal1CesAepRoutingOption
      INTEGER,
   aal1CesAepProfile
      Link,
   aal1CesAepFirstRetryInterval
      Unsigned32,
   aal1CesAepRetryLimit
      Unsigned32 }

aal1CesAepAddressToCall OBJECT-TYPE
   SYNTAX     AsciiString (SIZE (40))
   ACCESS     read-write
   STATUS     mandatory
   DESCRIPTION
     "This attribute specifies the remote NSAP address which 
      this ActiveEndPoint will call."
::= { aal1CesAepProvEntry 1 }

aal1CesAepRoutingOption OBJECT-TYPE
   SYNTAX     INTEGER  {
                 porsOnly(0) }
   ACCESS     read-write
   STATUS     mandatory
   DESCRIPTION
     "routingOption specifies the type of routing to use for 
      establishing the connection:
      
      porsOnly means that only the Path Oriented Routing 
      System may be used in establishing a connection."
   DEFVAL     { porsOnly }
::= { aal1CesAepProvEntry 2 }

aal1CesAepProfile OBJECT-TYPE
   SYNTAX     Link 
   ACCESS     read-write
   STATUS     mandatory
   DESCRIPTION
     "This attribute specifies the PORS routing profile to use for 
      this connection.
      
      If profile is empty, PORS will provide a default profile."
::= { aal1CesAepProvEntry 3 }

aal1CesAepFirstRetryInterval OBJECT-TYPE
   SYNTAX     Unsigned32 (1..3600)
   ACCESS     read-write
   STATUS     mandatory
   DESCRIPTION
     "This attribute defines the time to wait, in seconds, before 
      attempting to establish the connection after the first failed 
      attempt.
      
      The time to wait between subsequent call attempts will 
      generally differ due to a backoff scheme."
   DEFVAL     { 10 }
::= { aal1CesAepProvEntry 4 }

aal1CesAepRetryLimit OBJECT-TYPE
   SYNTAX     Unsigned32 (0..65535)
   ACCESS     read-write
   STATUS     mandatory
   DESCRIPTION
     "retryLimit specifies the maximum number of consecutive 
      unsuccessful connection setup attempts that may be made 
      before further attempts are abandoned.
      
      If this limit is reached, the Restart verb may be used to 
      restart connection attempts.
      
      If retryLimit is 0, there is no limit; attempts will continue 
      indefinitely until a successful connection is established."
   DEFVAL     { 0 }
::= { aal1CesAepProvEntry 5 }

aal1CesAepEpOperTable OBJECT-TYPE
   SYNTAX     SEQUENCE OF Aal1CesAepEpOperEntry
   ACCESS     not-accessible
   STATUS     mandatory
   DESCRIPTION
     "This group contains general operational attributes for 
      components using switched virtual circuits."
::= { aal1CesAep 12 }

aal1CesAepEpOperEntry OBJECT-TYPE
   SYNTAX     Aal1CesAepEpOperEntry
   ACCESS     not-accessible
   STATUS     mandatory
   DESCRIPTION
     "An entry in the aal1CesAepEpOperTable."
   INDEX {
      aal1CesIndex,
      aal1CesAepIndex }
::= { aal1CesAepEpOperTable 1 }

Aal1CesAepEpOperEntry ::= SEQUENCE {
   aal1CesAepRemoteAddress
      AsciiString,
   aal1CesAepLastTearDownCause
      Unsigned32,
   aal1CesAepLastTearDownDiagnostic
      AsciiString }

aal1CesAepRemoteAddress OBJECT-TYPE
   SYNTAX     AsciiString (SIZE (7..40))
   ACCESS     read-only
   STATUS     mandatory
   DESCRIPTION
     "remoteAddress is the address of the remote end point.
      
      If a connection is currently established, remoteAddress 
      will contain the address of the remote end point.
      
      If a connection is not established, remoteAddress will be 
      Unknown."
::= { aal1CesAepEpOperEntry 1 }

aal1CesAepLastTearDownCause OBJECT-TYPE
   SYNTAX     Unsigned32 (0..255)
   ACCESS     read-only
   STATUS     mandatory
   DESCRIPTION
     "lastTearDownCause indicates the cause of the last 
      connection tear down.
      
      The values are as defined in the ATM Forum ATM User-
      Network Interface (UNI) Specification."
::= { aal1CesAepEpOperEntry 2 }

aal1CesAepLastTearDownDiagnostic OBJECT-TYPE
   SYNTAX     AsciiString (SIZE (0..8))
   ACCESS     read-only
   STATUS     mandatory
   DESCRIPTION
     "lastTearDownDiagnostic provides a diagnostic to 
      supplement the lastTearDownCause attribute."
::= { aal1CesAepEpOperEntry 3 }

aal1CesAepOutTable OBJECT-TYPE
   SYNTAX     SEQUENCE OF Aal1CesAepOutEntry
   ACCESS     not-accessible
   STATUS     mandatory
   DESCRIPTION
     "This group contains status information about the AAL1 
      Circuit Emulation Service ActiveEndPoint component."
::= { aal1CesAep 13 }

aal1CesAepOutEntry OBJECT-TYPE
   SYNTAX     Aal1CesAepOutEntry
   ACCESS     not-accessible
   STATUS     mandatory
   DESCRIPTION
     "An entry in the aal1CesAepOutTable."
   INDEX {
      aal1CesIndex,
      aal1CesAepIndex }
::= { aal1CesAepOutTable 1 }

Aal1CesAepOutEntry ::= SEQUENCE {
   aal1CesAepSvcStatus
      INTEGER,
   aal1CesAepLastSetupFailureCause
      Unsigned32,
   aal1CesAepLastSetupFailureDiagnostic
      AsciiString,
   aal1CesAepRetryTimeRemaining
      Counter32,
   aal1CesAepRetryFailures
      Counter32 }

aal1CesAepSvcStatus OBJECT-TYPE
   SYNTAX     INTEGER  {
                 initialising(0),
                 connecting(1),
                 connected(2),
                 idle(3),
                 retriesExhausted(4),
                 failed(5) }
   ACCESS     read-only
   STATUS     mandatory
   DESCRIPTION
     "svcStatus indicates the status of the incoming and outgoing 
      connections.
      
      When this attribute has the value initialising, it indicates 
      that the component is initialising when first created; a 
      connection has not been established, and no incoming 
      setup requests will be processed.
      
      When this attribute has the value connecting, it indicates 
      that a connection has not yet been establised, but that 
      incoming setup requests will be processed.
      
      When this attribute has the value connected, it indicates 
      that a connection has been established.
      
      When this attribute has the value retriesExhausted, it 
      indicates that retryLimit consecutive connection setup 
      attempts have failed, and the connection procedure has 
      been aborted.
      
      When this attribute has the value idle, it indicates that a 
      connection has not been established, and that no incoming 
      setup requests will be processed.
      
      When this attribute has the value failed, it indicates that the 
      connections is in a state other than those described above."
::= { aal1CesAepOutEntry 1 }

aal1CesAepLastSetupFailureCause OBJECT-TYPE
   SYNTAX     Unsigned32 (0..255)
   ACCESS     read-only
   STATUS     mandatory
   DESCRIPTION
     "lastSetupFailureCause indicates the cause of the last 
      connection setup failure.
      
      The values are as defined in the ATM Forum ATM User-
      Network Interface (UNI) Specification."
::= { aal1CesAepOutEntry 2 }

aal1CesAepLastSetupFailureDiagnostic OBJECT-TYPE
   SYNTAX     AsciiString (SIZE (0..8))
   ACCESS     read-only
   STATUS     mandatory
   DESCRIPTION
     "lastSetupFailureDiagnostic provides a diagnostic to 
      supplement the lastSetupFailureCause attribute."
::= { aal1CesAepOutEntry 3 }

aal1CesAepRetryTimeRemaining OBJECT-TYPE
   SYNTAX     Counter32 
   ACCESS     read-only
   STATUS     mandatory
   DESCRIPTION
     "retryTimerValue is the current value of the retry timer for 
      this connection; it indicates the number of seconds before 
      the next connection attempt will be made. retryTimerValue 
      is initialised when a connection attempt fails.
      
      When retryTimerValue reaches 0, an attempt will be made 
      to establish the connection.
      
      When the timer is not running, for example when the 
      connection has been established, retryTimerValue will be 
      0."
::= { aal1CesAepOutEntry 4 }

aal1CesAepRetryFailures OBJECT-TYPE
   SYNTAX     Counter32 
   ACCESS     read-only
   STATUS     mandatory
   DESCRIPTION
     "retryFailures counts the number of consecutive failed 
      connection attempts.
      
      retryFailures is reset to 0 whenever a connection is 
      successfully established, or the connection is restarted 
      using the Restart verb. The counter wraps when the 
      maximum value is exceeded."
::= { aal1CesAepOutEntry 5 }


-- Aal1Ces/n PassiveEndPoint
-- 
-- The PassiveEndPoint component provides a passive end 
-- point for a switched virtual connection between two 
-- applications.
-- 
-- A PassiveEndPoint awaits incoming connection setup 
-- requests. A setup request will only be accepted if a 
-- connection is not already established, and the request 
-- originated from expectedRemoteAddress.
-- 
-- If a PassiveEndPoint component is provisioned under an 
-- Aal1Ces component, no other components may be 
-- provisioned under the same Aal1Ces component.

aal1CesPep OBJECT IDENTIFIER ::= { aal1Ces 4 }



aal1CesPepRowStatusTable OBJECT-TYPE
   SYNTAX     SEQUENCE OF Aal1CesPepRowStatusEntry
   ACCESS     not-accessible
   STATUS     mandatory
   DESCRIPTION
     "This entry controls the addition and deletion of 
      aal1CesPep components."
::= { aal1CesPep 1 }

aal1CesPepRowStatusEntry OBJECT-TYPE
   SYNTAX     Aal1CesPepRowStatusEntry
   ACCESS     not-accessible
   STATUS     mandatory
   DESCRIPTION
     "A single entry in the table represents a single 
      aal1CesPep component."
   INDEX {
      aal1CesIndex,
      aal1CesPepIndex }
::= { aal1CesPepRowStatusTable 1 }

Aal1CesPepRowStatusEntry ::= SEQUENCE {
   aal1CesPepRowStatus
      RowStatus,
   aal1CesPepComponentName
      DisplayString,
   aal1CesPepStorageType
      StorageType,
   aal1CesPepIndex
      NonReplicated }

aal1CesPepRowStatus OBJECT-TYPE
   SYNTAX     RowStatus 
   ACCESS     read-write
   STATUS     mandatory
   DESCRIPTION
     "This variable is used as the basis for SNMP naming of
      aal1CesPep components.
      These components can be added and deleted."
::= { aal1CesPepRowStatusEntry 1 }

aal1CesPepComponentName OBJECT-TYPE
   SYNTAX     DisplayString 
   ACCESS     read-only
   STATUS     mandatory
   DESCRIPTION
     "This variable provides the component's string name for
      use with the ASCII Console Interface"
::= { aal1CesPepRowStatusEntry 2 }

aal1CesPepStorageType OBJECT-TYPE
   SYNTAX     StorageType 
   ACCESS     read-only
   STATUS     mandatory
   DESCRIPTION
     "This variable represents the storage type value for the
      aal1CesPep tables."
::= { aal1CesPepRowStatusEntry 4 }

aal1CesPepIndex OBJECT-TYPE
   SYNTAX     NonReplicated 
   ACCESS     not-accessible
   STATUS     mandatory
   DESCRIPTION
     "This variable represents the index for the aal1CesPep tables."
::= { aal1CesPepRowStatusEntry 10 }

aal1CesPepProvEndPointAddrTable OBJECT-TYPE
   SYNTAX     SEQUENCE OF Aal1CesPepProvEndPointAddrEntry
   ACCESS     not-accessible
   STATUS     mandatory
   DESCRIPTION
     "This group contains NSAP address provisioning data for 
      components using switched virtual circuits."
::= { aal1CesPep 10 }

aal1CesPepProvEndPointAddrEntry OBJECT-TYPE
   SYNTAX     Aal1CesPepProvEndPointAddrEntry
   ACCESS     not-accessible
   STATUS     mandatory
   DESCRIPTION
     "An entry in the aal1CesPepProvEndPointAddrTable."
   INDEX {
      aal1CesIndex,
      aal1CesPepIndex }
::= { aal1CesPepProvEndPointAddrTable 1 }

Aal1CesPepProvEndPointAddrEntry ::= SEQUENCE {
   aal1CesPepExpectedRemoteAddress
      AsciiString,
   aal1CesPepLocalAddress
      AsciiString }

aal1CesPepExpectedRemoteAddress OBJECT-TYPE
   SYNTAX     AsciiString (SIZE (0..40))
   ACCESS     read-write
   STATUS     mandatory
   DESCRIPTION
     "This attribute specifies the expected remote address prefix 
      for an incoming connection setup request.
      
      If expectedRemoteAddress is not empty, only matching 
      connections will be considered for acceptance. If 
      expectedRemoteAddress is 40 characters long, the remote 
      address must match exactly to be accepted. If 
      expectedRemoteAddress is less than 40 characters long, the 
      remote address must begin with expectedRemoteAddress to 
      be accepted.
      
      If expectedRemoteAddress is empty, the component will 
      process connection requests from any remote address."
   DEFVAL     { ''H }  -- ""
::= { aal1CesPepProvEndPointAddrEntry 1 }

aal1CesPepLocalAddress OBJECT-TYPE
   SYNTAX     AsciiString (SIZE (40))
   ACCESS     read-write
   STATUS     mandatory
   DESCRIPTION
     "This attribute specifies the local NSAP address.
      
      If the switch prefix (the nodePrefix attribute of the 
      ModuleData component) has been provisioned, a default 
      value for localAddress based on nodePrefix will be 
      provided.
      
      If ModuleData nodePrefix has not been provisioned and 
      one or more alternate switch prefixes (the 
      alternatePorsPrefixes attribute of the ModuleData 
      component) have been provisioned, a default value for 
      localAddress based on the first provisioned 
      alternatePorsPrefix value will be provided.
      
      If no switch prefixes have been provisioned, localAddress 
      will default to an empty string. To obtain a valid default 
      localAddress in this case, either or both of the ModuleData 
      nodePrefix and ModuleData alternatePorsPrefixes 
      attributes must be provisioned, and this end point 
      component must then be deleted and re-added."
::= { aal1CesPepProvEndPointAddrEntry 2 }

aal1CesPepEpOperTable OBJECT-TYPE
   SYNTAX     SEQUENCE OF Aal1CesPepEpOperEntry
   ACCESS     not-accessible
   STATUS     mandatory
   DESCRIPTION
     "This group contains general operational attributes for 
      components using switched virtual circuits."
::= { aal1CesPep 11 }

aal1CesPepEpOperEntry OBJECT-TYPE
   SYNTAX     Aal1CesPepEpOperEntry
   ACCESS     not-accessible
   STATUS     mandatory
   DESCRIPTION
     "An entry in the aal1CesPepEpOperTable."
   INDEX {
      aal1CesIndex,
      aal1CesPepIndex }
::= { aal1CesPepEpOperTable 1 }

Aal1CesPepEpOperEntry ::= SEQUENCE {
   aal1CesPepRemoteAddress
      AsciiString,
   aal1CesPepLastTearDownCause
      Unsigned32,
   aal1CesPepLastTearDownDiagnostic
      AsciiString }

aal1CesPepRemoteAddress OBJECT-TYPE
   SYNTAX     AsciiString (SIZE (7..40))
   ACCESS     read-only
   STATUS     mandatory
   DESCRIPTION
     "remoteAddress is the address of the remote end point.
      
      If a connection is currently established, remoteAddress 
      will contain the address of the remote end point.
      
      If a connection is not established, remoteAddress will be 
      Unknown."
::= { aal1CesPepEpOperEntry 1 }

aal1CesPepLastTearDownCause OBJECT-TYPE
   SYNTAX     Unsigned32 (0..255)
   ACCESS     read-only
   STATUS     mandatory
   DESCRIPTION
     "lastTearDownCause indicates the cause of the last 
      connection tear down.
      
      The values are as defined in the ATM Forum ATM User-
      Network Interface (UNI) Specification."
::= { aal1CesPepEpOperEntry 2 }

aal1CesPepLastTearDownDiagnostic OBJECT-TYPE
   SYNTAX     AsciiString (SIZE (0..8))
   ACCESS     read-only
   STATUS     mandatory
   DESCRIPTION
     "lastTearDownDiagnostic provides a diagnostic to 
      supplement the lastTearDownCause attribute."
::= { aal1CesPepEpOperEntry 3 }

aal1CesPepPassiveOperTable OBJECT-TYPE
   SYNTAX     SEQUENCE OF Aal1CesPepPassiveOperEntry
   ACCESS     not-accessible
   STATUS     mandatory
   DESCRIPTION
     "This group contains status information about the AAL1 
      Circuit Emulation Service PassiveEndPoint component."
::= { aal1CesPep 12 }

aal1CesPepPassiveOperEntry OBJECT-TYPE
   SYNTAX     Aal1CesPepPassiveOperEntry
   ACCESS     not-accessible
   STATUS     mandatory
   DESCRIPTION
     "An entry in the aal1CesPepPassiveOperTable."
   INDEX {
      aal1CesIndex,
      aal1CesPepIndex }
::= { aal1CesPepPassiveOperTable 1 }

Aal1CesPepPassiveOperEntry ::= SEQUENCE {
   aal1CesPepSvcStatus
      INTEGER }

aal1CesPepSvcStatus OBJECT-TYPE
   SYNTAX     INTEGER  {
                 initialising(0),
                 connecting(1),
                 connected(2),
                 idle(3),
                 failed(5) }
   ACCESS     read-only
   STATUS     mandatory
   DESCRIPTION
     "svcStatus indicates the status of the incoming connection.
      
      When this attribute has the value initialising, it indicates 
      that the component is initialising when first created; a 
      connection has not been established, and no incoming 
      setup requests will be processed.
      
      When this attribute has the value connecting, it indicates 
      that a connection has not yet been establised, but that 
      incoming setup requests will be processed.
      
      When this attribute has the value connected, it indicates 
      that a connection has been established.
      
      When this attribute has the value idle, it indicates that a 
      connection has not been established, and that no incoming 
      setup requests will be processed.
      
      When this attribute has the value failed, it indicates that the 
      connections is in a state other than those described above."
::= { aal1CesPepPassiveOperEntry 1 }


-- ...Lc
-- This component contains all of the operation attributes for a Path 
-- Oriented Logical Connection.

aal1CesLCo OBJECT IDENTIFIER ::= { aal1Ces 5 }



aal1CesLCoRowStatusTable OBJECT-TYPE
   SYNTAX     SEQUENCE OF Aal1CesLCoRowStatusEntry
   ACCESS     not-accessible
   STATUS     mandatory
   DESCRIPTION
     "This entry controls the addition and deletion of 
      aal1CesLCo components."
::= { aal1CesLCo 1 }

aal1CesLCoRowStatusEntry OBJECT-TYPE
   SYNTAX     Aal1CesLCoRowStatusEntry
   ACCESS     not-accessible
   STATUS     mandatory
   DESCRIPTION
     "A single entry in the table represents a single 
      aal1CesLCo component."
   INDEX {
      aal1CesIndex,
      aal1CesLCoIndex }
::= { aal1CesLCoRowStatusTable 1 }

Aal1CesLCoRowStatusEntry ::= SEQUENCE {
   aal1CesLCoRowStatus
      RowStatus,
   aal1CesLCoComponentName
      DisplayString,
   aal1CesLCoStorageType
      StorageType,
   aal1CesLCoIndex
      NonReplicated }

aal1CesLCoRowStatus OBJECT-TYPE
   SYNTAX     RowStatus 
   ACCESS     read-only
   STATUS     mandatory
   DESCRIPTION
     "This variable is used as the basis for SNMP naming of
      aal1CesLCo components.
      These components cannot be added nor deleted."
::= { aal1CesLCoRowStatusEntry 1 }

aal1CesLCoComponentName OBJECT-TYPE
   SYNTAX     DisplayString 
   ACCESS     read-only
   STATUS     mandatory
   DESCRIPTION
     "This variable provides the component's string name for
      use with the ASCII Console Interface"
::= { aal1CesLCoRowStatusEntry 2 }

aal1CesLCoStorageType OBJECT-TYPE
   SYNTAX     StorageType 
   ACCESS     read-only
   STATUS     mandatory
   DESCRIPTION
     "This variable represents the storage type value for the
      aal1CesLCo tables."
::= { aal1CesLCoRowStatusEntry 4 }

aal1CesLCoIndex OBJECT-TYPE
   SYNTAX     NonReplicated 
   ACCESS     not-accessible
   STATUS     mandatory
   DESCRIPTION
     "This variable represents the index for the aal1CesLCo tables."
::= { aal1CesLCoRowStatusEntry 10 }

aal1CesLCoPathDataTable OBJECT-TYPE
   SYNTAX     SEQUENCE OF Aal1CesLCoPathDataEntry
   ACCESS     not-accessible
   STATUS     mandatory
   DESCRIPTION
     "This group contains all operational attributes for the path oriented 
      LCo."
::= { aal1CesLCo 10 }

aal1CesLCoPathDataEntry OBJECT-TYPE
   SYNTAX     Aal1CesLCoPathDataEntry
   ACCESS     not-accessible
   STATUS     mandatory
   DESCRIPTION
     "An entry in the aal1CesLCoPathDataTable."
   INDEX {
      aal1CesIndex,
      aal1CesLCoIndex }
::= { aal1CesLCoPathDataTable 1 }

Aal1CesLCoPathDataEntry ::= SEQUENCE {
   aal1CesLCoState
      INTEGER,
   aal1CesLCoOverrideRemoteName
      AsciiString,
   aal1CesLCoEnd
      INTEGER,
   aal1CesLCoCostMetric
      Unsigned32,
   aal1CesLCoDelayMetric
      Unsigned32,
   aal1CesLCoRoundTripDelay
      Unsigned32,
   aal1CesLCoSetupPriority
      Unsigned32,
   aal1CesLCoHoldingPriority
      Unsigned32,
   aal1CesLCoRequiredTxBandwidth
      Gauge32,
   aal1CesLCoRequiredRxBandwidth
      Gauge32,
   aal1CesLCoRequiredTrafficType
      INTEGER,
   aal1CesLCoPermittedTrunkTypes
      OCTET STRING,
   aal1CesLCoRequiredSecurity
      Unsigned32,
   aal1CesLCoRequiredCustomerParameter
      Unsigned32,
   aal1CesLCoEmissionPriority
      Unsigned32,
   aal1CesLCoDiscardPriority
      Unsigned32,
   aal1CesLCoPathType
      INTEGER,
   aal1CesLCoRetryCount
      Unsigned32,
   aal1CesLCoPathFailureCount
      Unsigned32,
   aal1CesLCoReasonForNoRoute
      INTEGER,
   aal1CesLCoLastTearDownReason
      INTEGER,
   aal1CesLCoPathFailureAction
      INTEGER,
   aal1CesLCoBumpPreference
      INTEGER,
   aal1CesLCoOptimization
      INTEGER,
   aal1CesLCoPathUpDateTime
      EnterpriseDateAndTime }

aal1CesLCoState OBJECT-TYPE
   SYNTAX     INTEGER  {
                 pathDown(0),
                 selectingRoute(1),
                 connecting(2),
                 pathUp(3),
                 pathDownRetrying(4) }
   ACCESS     read-only
   STATUS     mandatory
   DESCRIPTION
     "This attribute reflects the current state of the connection. The 
      pathDown state indicates a connection that has no remote end 
      provisioned or the application has not yet signalled for a path. The 
      selectingRoute state occurs when a request has been sent to route 
      selector and it has not yet responded. The connectingState occurs 
      while a path is being established. The pathUp state is the normal 
      operational state of a path. The pathDownRetrying state indicates a 
      path that attempted route selection but received no route and is now 
      waiting to retry route selection again."
::= { aal1CesLCoPathDataEntry 1 }

aal1CesLCoOverrideRemoteName OBJECT-TYPE
   SYNTAX     AsciiString (SIZE (0..40))
   ACCESS     read-write
   STATUS     mandatory
   DESCRIPTION
     "If set and the current PLC remoteName is blank this remoteName 
      will override the blank PLC remoteName. Usually you would set 
      this attribute and then lock/unlock the service component which 
      will result in this new overrideRemoteName being used as if it had 
      been provisioned into the PLC remoteName. The advantage of this 
      attribute is that the connection's remoteName can be changed 
      immediately without having to 'activate prov' but the disadvantage 
      is that the overrideRemoteName is not permanent and if the card or 
      switch is reset the override will be lost."
::= { aal1CesLCoPathDataEntry 2 }

aal1CesLCoEnd OBJECT-TYPE
   SYNTAX     INTEGER  {
                 calling(0),
                 called(1) }
   ACCESS     read-only
   STATUS     mandatory
   DESCRIPTION
     "This attribute identifies whether this is the calling or called end of 
      the path."
::= { aal1CesLCoPathDataEntry 3 }

aal1CesLCoCostMetric OBJECT-TYPE
   SYNTAX     Unsigned32 (0..65535)
   ACCESS     read-only
   STATUS     mandatory
   DESCRIPTION
     "This attribute gives the route's total cost metric. It is calculated as 
      the sum of the cost metric of all trunks in the path at the time the 
      connection was established. The cost metric of a trunk is defined by 
      the trunkCost attribute of the Trunk component. The costMetric for 
      an LCo that is originated and terminated on the same module is 0."
::= { aal1CesLCoPathDataEntry 4 }

aal1CesLCoDelayMetric OBJECT-TYPE
   SYNTAX     Unsigned32 (0..100000)
   ACCESS     read-only
   STATUS     mandatory
   DESCRIPTION
     "This attribute gives the total delay of the route as the one way delay 
      for a 512 byte packet. It is calculated as the sum of the delays of all 
      trunks in the path stored in topology at the time the connection was 
      established. The delay for an LCo that is originated and terminated 
      on the same module is 0."
::= { aal1CesLCoPathDataEntry 5 }

aal1CesLCoRoundTripDelay OBJECT-TYPE
   SYNTAX     Unsigned32 (0..200000)
   ACCESS     read-only
   STATUS     mandatory
   DESCRIPTION
     "This attribute contains the time taken for a packet (cell) of 44 bytes 
      to be transmitted to the remote LCo and return to this LCo. The 
      number reported is given in milliseconds to the nearest millisecond. 
      A value of one millisecond is reported if the time is less than 1 
      millisecond even though the delay may be less than 1 Millisecond 
      when the LCo is originated and terminated on the same module."
::= { aal1CesLCoPathDataEntry 6 }

aal1CesLCoSetupPriority OBJECT-TYPE
   SYNTAX     Unsigned32 (0..4)
   ACCESS     read-only
   STATUS     mandatory
   DESCRIPTION
     "This attribute gives the priority at which the current path is 
      established. Zero is the highest priority and four is the lowest. The 
      holdingPriority, a complementary attribute of this component, 
      indicates the priority a path maintains once it is established."
::= { aal1CesLCoPathDataEntry 7 }

aal1CesLCoHoldingPriority OBJECT-TYPE
   SYNTAX     Unsigned32 (0..4)
   ACCESS     read-only
   STATUS     mandatory
   DESCRIPTION
     "This attribute gives the priority at which a path holds its current 
      path once the path is established. Zero is the highest priority and 
      four is the lowest. The setupPriority, a complementary attribute, 
      indicates the priority of a path at establishment time."
::= { aal1CesLCoPathDataEntry 8 }

aal1CesLCoRequiredTxBandwidth OBJECT-TYPE
   SYNTAX     Gauge32 (0..4294967295)
   ACCESS     read-only
   STATUS     mandatory
   DESCRIPTION
     "This attribute gives the actual bandwidth (in bits per second) 
      reserved by this path on each of the trunks of its route. This attribute 
      represents the bandwidth for traffic outgoing to the remote end 
      point. The originating end of the connection determines this value."
::= { aal1CesLCoPathDataEntry 9 }

aal1CesLCoRequiredRxBandwidth OBJECT-TYPE
   SYNTAX     Gauge32 (0..4294967295)
   ACCESS     read-only
   STATUS     mandatory
   DESCRIPTION
     "This attribute gives the actual bandwidth (in bits per second) 
      reserved by this path on each of trunks of its route. This attribute 
      represents the bandwidth for traffic incoming from the remote end 
      point. The originating end of the connection determines this value"
::= { aal1CesLCoPathDataEntry 10 }

aal1CesLCoRequiredTrafficType OBJECT-TYPE
   SYNTAX     INTEGER  {
                 voice(0),
                 data(1),
                 video(2),
                 trafficType1(3),
                 trafficType2(4),
                 trafficType3(5),
                 trafficType4(6),
                 trafficType5(7) }
   ACCESS     read-only
   STATUS     mandatory
   DESCRIPTION
     "This operational attribute indicates the type of traffic transmitted 
      over the path. There are eight possible traffic types, and the path can 
      transmit only one of them. The originating end of the connection 
      determines the type. These are arbitrary designations for traffic 
      type. The voice, data and video traffic types are defined, and five 
      other arbitrary traffic types can be defined by the network 
      administration. This attribute is used in the route selection process 
      to restrict the route to trunks that support this traffic type. The 
      supportedTrafficType trunk attribute lists all the types of traffic 
      allowed on the trunk. For example, if requiredTrafficType is 
      specified as trafficType1 then only trunks that include trafficType1 
      in supportedTrafficType, will be candidates for this connection."
::= { aal1CesLCoPathDataEntry 11 }

aal1CesLCoPermittedTrunkTypes OBJECT-TYPE
   SYNTAX     OCTET STRING (SIZE (1))
   ACCESS     read-only
   STATUS     mandatory
   DESCRIPTION
     "This operational attribute lists up to eight types of trunk that can be 
      used on the route. The originating end of the connection determines 
      the types. The terrestrial and satellite trunk types have been 
      defined, leaving six remaining arbitrary types that can be defined by 
      the network administration. The trunk's type is indicated in the 
      trunkType attribute of the Trunk component. When selecting a 
      route, PORS only chooses trunks whose trunkType are in the 
      permittedTrunkTypes for the path.

      Description of bits:
      terrestrial(0)
      satellite(1)
      trunkType1(2)
      trunkType2(3)
      trunkType3(4)
      trunkType4(5)
      trunkType5(6)
      trunkType6(7)"
::= { aal1CesLCoPathDataEntry 12 }

aal1CesLCoRequiredSecurity OBJECT-TYPE
   SYNTAX     Unsigned32 (0..7)
   ACCESS     read-only
   STATUS     mandatory
   DESCRIPTION
     "This attribute indicates the required minimum level of security of 
      the trunks on the route. Zero represents the most secure and seven 
      represents the least secure. The trunk's security is indicated by the 
      trunkSecurity attribute of the Trunk component, and has values 
      identical in range and meaning to the requiredSecurity attribute. 
      PORS ensures that any route selected does not contain a trunk 
      whose trunkSecurity attribute is numerically greater than the 
      requiredSecurity."
::= { aal1CesLCoPathDataEntry 13 }

aal1CesLCoRequiredCustomerParameter OBJECT-TYPE
   SYNTAX     Unsigned32 (0..7)
   ACCESS     read-only
   STATUS     mandatory
   DESCRIPTION
     "This attribute indicates the allowed customer defined parameter of 
      the trunks on the route.The originating end of the connection 
      determines the customer defined parameter. Its value, a number 
      from zero to seven, is chosen by a network administration to have a 
      meaning specific to their network, thus allowing them to customize 
      the use of their trunks. A complementary trunk attribute, 
      customerParameter, also has a value from zero to seven. The route 
      selection process does not consider trunks whose 
      customerParameter is greater than the requiredCustomerParameter 
      of the path."
::= { aal1CesLCoPathDataEntry 14 }

aal1CesLCoEmissionPriority OBJECT-TYPE
   SYNTAX     Unsigned32 (0..2)
   ACCESS     read-only
   STATUS     mandatory
   DESCRIPTION
     "This attribute indicates the urgency with which packets on the path 
      are emitted by the trunks on the route. The originating end of the 
      connection selects the emissionPriority. EmissionPriority of zero 
      indicates the highest emission priority, while two indicates the 
      lowest emission priority. Packets with a higher emissionPriority (or 
      numerically less) are serviced and sent out before the packets of 
      lower emissionPriority (or numerically higher)."
::= { aal1CesLCoPathDataEntry 15 }

aal1CesLCoDiscardPriority OBJECT-TYPE
   SYNTAX     Unsigned32 (1..3)
   ACCESS     read-only
   STATUS     mandatory
   DESCRIPTION
     "This attribute indicates the importance of the packets on the 
      path.The originating end of the connection sets discardPriority. One 
      is used for paths carrying the most important traffic, and three is 
      used for paths carrying the least important traffic. Packets with 
      lower discardPriority(numerically lower) are discarded after 
      packets with a higher discardPriority(numerically higher)."
::= { aal1CesLCoPathDataEntry 16 }

aal1CesLCoPathType OBJECT-TYPE
   SYNTAX     INTEGER  {
                 normal(0),
                 manual(1),
                 forced(2) }
   ACCESS     read-only
   STATUS     mandatory
   DESCRIPTION
     "This attribute indicates whether the path for this PLC was 
      determined automatically or by static provisioning. Normal 
      pathTypes are selected automatically by Route Selector.The other 
      pathTypes are both manual pathTypes where the operator must 
      specify, through provisioning, a static route termed the manualPath. 
      A manual pathType connection is nearly identical to a normal path 
      type connection with the exception that the route is pre-provisioned. 
      For a manual pathType, bandwidth reservations are respected along 
      the path exactly as in a normal path. The last type, the forced 
      pathType, is also a manual path but regardless of the bandwidth 
      available the route is granted provided the trunks are operational 
      and there are sufficient Logical Channels (LChs).
      
      The forced pathType could result in over committing the reserved 
      bandwidth allowed on a trunk. A better way to achieve the effects of 
      a forced pathType is to use a manual pathType with setupPriority = 
      0 and holdingPriority = 0. In this manner the path will reserve 
      correct bandwidth and it will bump other paths if required while not 
      being bumped itself."
::= { aal1CesLCoPathDataEntry 17 }

aal1CesLCoRetryCount OBJECT-TYPE
   SYNTAX     Unsigned32 (0..255)
   ACCESS     read-only
   STATUS     mandatory
   DESCRIPTION
     "This attribute is the count of the number of times the path chosen 
      during route selection could not be instantiated. This count should 
      be three or below if the network is performing adequately. A high 
      value indicates that the route selection is often performed using an 
      out-of-date view of available network bandwidth and/or topology.
      This attribute will only increase at the calling end of the connection.
      This attribute is reset each time a path reconnects and stops 
      counting when it reaches its maximum value."
::= { aal1CesLCoPathDataEntry 18 }

aal1CesLCoPathFailureCount OBJECT-TYPE
   SYNTAX     Unsigned32 (0..65535)
   ACCESS     read-only
   STATUS     mandatory
   DESCRIPTION
     "This attribute is the count of the number of times the path has 
      successfully connected. It is set to zero the first time the path is up. 
      If a path fails anytime after connecting this count will be 
      incremented when the path is up again. Failed route requests do not 
      count in this statistic. See retryCount above. This attribute stops 
      counting at its maximum value."
::= { aal1CesLCoPathDataEntry 19 }

aal1CesLCoReasonForNoRoute OBJECT-TYPE
   SYNTAX     INTEGER  {
                 none(0),
                 destinationNameTooLong(1),
                 destinationNotSpecified(2),
                 unknownDestinationName(3),
                 incorrectDestination(4),
                 incorrectDestinationEndPoint(5),
                 unknownSource(6),
                 unknownDestination(7),
                 sameNode(8),
                 routeCostTooMuch(9),
                 routesDelayTooLong(10),
                 attributesNotMet(11),
                 anError(12),
                 attributeProfileProblem(13),
                 manualPathIndexProblem(14) }
   ACCESS     read-only
   STATUS     mandatory
   DESCRIPTION
     "This attribute is the route selection's reasonForNoRoute and 
      provides a brief reason for which a route was not selected. The 
      reasons are essentially self-explanatory. Perhaps two reasons for no 
      route require some explanation. The reason 
      unknownRemoteNodeName is issued when the remote node name 
      is not in the topological database. The reason plcAttributesNotMet 
      is issued when there is no network connectivity at a level specified 
      by the PLC attributes. This reason is also issued when there is no 
      physical connectivity between two end nodes."
   DEFVAL     { none }
::= { aal1CesLCoPathDataEntry 20 }

aal1CesLCoLastTearDownReason OBJECT-TYPE
   SYNTAX     INTEGER  {
                 none(0),
                 normalShutDown(1),
                 insufficientTxLcOrBandwidth(2),
                 insufficientRxLcOrBandwidth(3),
                 trunkFailure(4),
                 trunkCardFailure(5),
                 operatorForced(6),
                 lostLcnClash(7),
                 networkCongestion(8),
                 trunkNotFound(9),
                 farEndNotFound(10),
                 wrongModuleReached(11),
                 farEndBusy(12),
                 callLoopedBack(13),
                 unknownReason(14),
                 farEndNotReady(15),
                 remoteNameMismatch(16),
                 serviceTypeMismatch(17),
                 reconnectFromFarEnd(18),
                 bumped(19),
                 accessCardFailure(20),
                 optimized(21),
                 overrideRemoteName(22),
                 trunkOrFarEndDidNotSupportMode(23) }
   ACCESS     read-only
   STATUS     mandatory
   DESCRIPTION
     "This attribute reflects the last tear down reason for a connection 
      (LCo). In many cases this displays the reason for a momentary 
      service interruption. This attribute applies to the last path failure 
      only. If a path is no longer up, this may give an indication to the 
      reason that the path has failed. In many cases an alarm will also be 
      generated with more specific information. The following is a brief 
      description of the reasons:
      none - This path has no information for the teardown this is typical 
      of a path provisioned with no remoteName that has not been up.
      normalShutDown - This path has gone down due to normal call 
      termination.
      insufficientTxLcOrBandwidth - At present there is either no 
      available bandwidth or logical channel numbers available on one or 
      more of the trunks for this path in the transmit direction.
      insufficientRxLcOrBandwidth - At present there is either no 
      available bandwidth or logical channel numbers available on one or 
      more of the trunks for this path in the receive direction.
      trunkFailure- A trunk on the path has failed or has gone down due 
      to a provisioning change of a critical attribute.
      trunkCardFailure- A trunk FP card has failed along the path.
      accessCardFailure- The FP on which the peer access service was 
      running has failed.
      operatorForced- The path has terminated due to the operator 
      locking a trunk along the path.
      lostLcnClash- The path has terminated because the PA's at both 
      ends of an intermediate trunk have allocated the same LC to 
      different calls. When this happens both calls must go down and then 
      try to come up again a fraction of a second later (effectively 
      ensuring that they will now be assigned different LC's). It is normal 
      to get the odd clash especially when the PA's usedLC is 
      approaching the PA's maxLC.
      networkCongestion - The path has failed due to control information 
      being lost and not recoverable.
      trunkNotFound - Occurs on a manual path usually. Check for 
      trunks not up or names provisioned incorrectly.
      farEndNotFound - The far end is not provisioned or is not up. 
      Check remote Name.
      wrongModuleReached - This may occur on a manual path. Check 
      provisioning for correct trunk and service names. For a normal 
      path, the network Topology may be changing check remoteName.
      farEndBusy - The far end has been reached but it is busy. Check 
      remoteName and remote end provisioning.
      callLoopedBack - This LCo is provisioned to call itself. Re-
      provision since this is invalid.
      unknownReason - The failure was not resolved.
      farEndNotReady - The remote end was reached but the connection 
      was refused due to the remote end not being enabled.
      remoteNameMismatch - The remote end has alarmed and rejected 
      this setup due to remoteName provisioning.
      serviceTypeMismatch - The remote Service Type does not match 
      this service type. Check provisioning.
      reconnectFromFarEnd - The remote end re-established this 
      connection. Check the remote end lastTearDownReason to 
      determine the real reason.
      bumped - Another call bumped this path from a trunk to get 
      bandwidth (or an LC) which it required to come up. This other path 
      had a higher setupPriority than this path's holdingPriority hence it 
      was allowed to steal the bandwidth (or LC) from this path.
      optimized - This call has been rerouted due to the optimization 
      feature. The call is still active this just indicates why the path 
      changed.
      trunkOrFarEndDidNotSupportMode - This call was unable to 
      complete because a mode required by the service was not supported 
      by one of the trunks the route went through or by the far end service 
      it connected to. Currently the only mode that this applies to is the 
      map/mux mode on TRUNK PA ATM component. Map mode was 
      required by the application (CES/FrAtm etc.) but was not available 
      on the TRUNK PA ATM component through which the call was 
      routed or the far end CES/FrAtm component did not specify the 
      same mode."
   DEFVAL     { none }
::= { aal1CesLCoPathDataEntry 21 }

aal1CesLCoPathFailureAction OBJECT-TYPE
   SYNTAX     INTEGER  {
                 disconnectConnection(0),
                 reRoutePath(1) }
   ACCESS     read-only
   STATUS     mandatory
   DESCRIPTION
     "This attribute displays whether the application is set to tolerate 
      momentary interruption of a path while a new path is selected. If 
      disconnectConnection is displayed, the application is informed as 
      soon as possible about a failure by disconnection. If the attribute 
      displays reRoutePath, the path may attempt an immediate reroute, 
      provided the failure is a recoverable failure. If rerouting fails the 
      application is informed of the failure. 
      With this option set to reRoutePath the LCo may wait up to 30 
      seconds before informing the service of complete disconnection in 
      order to allow both ends to attempt to reconnect. Note that if PLC 
      components are different at both ends only the calling end is 
      allowed to reconnect.
      
      All pathTypes respect this attribute. Also on a manualPath with 
      both ends provisioned with independent paths (at least with respect 
      to the failure) this option will have the desired effect that the path is 
      rerouted without complete disconnection at both ends"
::= { aal1CesLCoPathDataEntry 22 }

aal1CesLCoBumpPreference OBJECT-TYPE
   SYNTAX     INTEGER  {
                 bumpWhenNecessary(0),
                 bumpToObtainBestRoute(1) }
   ACCESS     read-only
   STATUS     mandatory
   DESCRIPTION
     "This attribute specifies when bumping will occur during route 
      selection process. Bumping may occur when necessary or always. It 
      will be necessary for a connection to bump if there is not enough 
      resources for the connection to be established and these resources 
      are occupied by a connection whose setupPriority is lower 
      (numerically higher) than the connection's setupPriority. A 
      connection may also always bump in order to obtain the best route."
::= { aal1CesLCoPathDataEntry 23 }

aal1CesLCoOptimization OBJECT-TYPE
   SYNTAX     INTEGER  {
                 disabled(0),
                 enabled(1) }
   ACCESS     read-only
   STATUS     mandatory
   DESCRIPTION
     "This attribute is used to specify whether this connection should 
      attempt to optimize its path when requested by the routing PORS 
      component. Every path is as optimal as it can be when it is 
      established, but as network traffic patterns and configurations 
      change this path may no longer be as optimal as it could be. The 
      PORS connection manager on a module requests circuits to 
      optimize at the optimization interval."
::= { aal1CesLCoPathDataEntry 24 }

aal1CesLCoPathUpDateTime OBJECT-TYPE
   SYNTAX     EnterpriseDateAndTime (SIZE (0 | 19))
   ACCESS     read-only
   STATUS     mandatory
   DESCRIPTION
     "This is the time stamp when the current path was established or 
      reestablished."
::= { aal1CesLCoPathDataEntry 25 }

aal1CesLCoStatsTable OBJECT-TYPE
   SYNTAX     SEQUENCE OF Aal1CesLCoStatsEntry
   ACCESS     not-accessible
   STATUS     mandatory
   DESCRIPTION
     "This group contains the operational statistics attributes for the path 
      oriented LCo."
::= { aal1CesLCo 11 }

aal1CesLCoStatsEntry OBJECT-TYPE
   SYNTAX     Aal1CesLCoStatsEntry
   ACCESS     not-accessible
   STATUS     mandatory
   DESCRIPTION
     "An entry in the aal1CesLCoStatsTable."
   INDEX {
      aal1CesIndex,
      aal1CesLCoIndex }
::= { aal1CesLCoStatsTable 1 }

Aal1CesLCoStatsEntry ::= SEQUENCE {
   aal1CesLCoPktsToNetwork
      PassportCounter64,
   aal1CesLCoBytesToNetwork
      PassportCounter64,
   aal1CesLCoPktsFromNetwork
      PassportCounter64,
   aal1CesLCoBytesFromNetwork
      PassportCounter64 }

aal1CesLCoPktsToNetwork OBJECT-TYPE
   SYNTAX     PassportCounter64 
   ACCESS     read-only
   STATUS     mandatory
   DESCRIPTION
     "This attribute counts the number of packets transmitted to the 
      network over this Logical Connection."
::= { aal1CesLCoStatsEntry 1 }

aal1CesLCoBytesToNetwork OBJECT-TYPE
   SYNTAX     PassportCounter64 
   ACCESS     read-only
   STATUS     mandatory
   DESCRIPTION
     "This attribute counts the number of bytes sent to the network over 
      this Logical Connection."
::= { aal1CesLCoStatsEntry 2 }

aal1CesLCoPktsFromNetwork OBJECT-TYPE
   SYNTAX     PassportCounter64 
   ACCESS     read-only
   STATUS     mandatory
   DESCRIPTION
     "This attribute counts the number of packets received from the 
      remote LCo via the network."
::= { aal1CesLCoStatsEntry 3 }

aal1CesLCoBytesFromNetwork OBJECT-TYPE
   SYNTAX     PassportCounter64 
   ACCESS     read-only
   STATUS     mandatory
   DESCRIPTION
     "This attribute counts the number of bytes received from the remote 
      LCo via the network."
::= { aal1CesLCoStatsEntry 4 }

aal1CesLCoPathTable OBJECT-TYPE
   SYNTAX     SEQUENCE OF Aal1CesLCoPathEntry
   ACCESS     not-accessible
   STATUS     mandatory
   DESCRIPTION
     "This attribute contains the trunk component names over which the 
      path has been instantiated and the remote end point name 
      terminating the path."
::= { aal1CesLCo 264 }

aal1CesLCoPathEntry OBJECT-TYPE
   SYNTAX     Aal1CesLCoPathEntry
   ACCESS     not-accessible
   STATUS     mandatory
   DESCRIPTION
     "An entry in the aal1CesLCoPathTable."
   INDEX {
      aal1CesIndex,
      aal1CesLCoIndex,
      aal1CesLCoPathValue }
::= { aal1CesLCoPathTable 1 }

Aal1CesLCoPathEntry ::= SEQUENCE {
   aal1CesLCoPathValue
      AsciiString }

aal1CesLCoPathValue OBJECT-TYPE
   SYNTAX     AsciiString (SIZE (0..40))
   ACCESS     read-only
   STATUS     mandatory
   DESCRIPTION
     "This variable represents both the value and the index for the
      aal1CesLCoPathTable."
::= { aal1CesLCoPathEntry 1 }




-- 
-- Version and Compliance statements
-- 



-- Object-Group Statement:
-- A list of all current accessible leaf objects.

-- OBJECTS { aal1CesLCoOverrideRemoteName,
--           aal1CesLCoRowStatus,
--           aal1CesBufferSize,
--           aal1CesDummyDataByte,
--           aal1CesOperationalState,
--           aal1CesIdleSuppression,
--           aal1CesPepLastTearDownCause,
--           aal1CesServiceType,
--           aal1CesLCoEmissionPriority,
--           aal1CesBufferOverflows,
--           aal1CesAepProfile,
--           aal1CesNapAtmConnection,
--           aal1CesLCoState,
--           aal1CesPepRemoteAddress,
--           aal1CesCellLossStatus,
--           aal1CesAepComponentName,
--           aal1CesLCoPktsToNetwork,
--           aal1CesCellDelayVariationTolerance,
--           aal1CesLCoLastTearDownReason,
--           aal1CesAepLastSetupFailureDiagnostic,
--           aal1CesLCoCostMetric,
--           aal1CesLCoRequiredCustomerParameter,
--           aal1CesAepRetryTimeRemaining,
--           aal1CesLCoDiscardPriority,
--           aal1CesAal1LayerLossStatus,
--           aal1CesPepStorageType,
--           aal1CesAal1SequenceErrors,
--           aal1CesAepExpectedRemoteAddress,
--           aal1CesAvailabilityStatus,
--           aal1CesLCoBytesToNetwork,
--           aal1CesLCoRetryCount,
--           aal1CesLCoDelayMetric,
--           aal1CesAepSvcStatus,
--           aal1CesLCoBumpPreference,
--           aal1CesAlarmStatus,
--           aal1CesNapStorageType,
--           aal1CesAepAddressToCall,
--           aal1CesLCoRequiredTxBandwidth,
--           aal1CesCellsReceived,
--           aal1CesLCoSetupPriority,
--           aal1CesLCoPathFailureCount,
--           aal1CesUnknownStatus,
--           aal1CesStandbyStatus,
--           aal1CesLCoRequiredSecurity,
--           aal1CesBufferUnderflows,
--           aal1CesAepRemoteAddress,
--           aal1CesUsageState,
--           aal1CesAepRoutingOption,
--           aal1CesIdlePattern,
--           aal1CesLCoRoundTripDelay,
--           aal1CesHeaderErrors,
--           aal1CesAepRetryLimit,
--           aal1CesLCoHoldingPriority,
--           aal1CesLostCells,
--           aal1CesReassembledCells,
--           aal1CesLCoPermittedTrunkTypes,
--           aal1CesPointerReframes,
--           aal1CesLCoReasonForNoRoute,
--           aal1CesCellLossRecoveryPeriod,
--           aal1CesAepFirstRetryInterval,
--           aal1CesInterfaceName,
--           aal1CesCellsTransmitted,
--           aal1CesLCoPathFailureAction,
--           aal1CesLCoEnd,
--           aal1CesPepLocalAddress,
--           aal1CesNapRowStatus,
--           aal1CesAepRetryFailures,
--           aal1CesControlStatus,
--           aal1CesAdminState,
--           aal1CesPartialFill,
--           aal1CesLCoRequiredRxBandwidth,
--           aal1CesAepStorageType,
--           aal1CesPointerParityErrors,
--           aal1CesLCoPktsFromNetwork,
--           aal1CesRowStatus,
--           aal1CesPepRowStatus,
--           aal1CesAepLastTearDownDiagnostic,
--           aal1CesPepSvcStatus,
--           aal1CesProceduralStatus,
--           aal1CesMisinsertedCells,
--           aal1CesLCoStorageType,
--           aal1CesAepLastTearDownCause,
--           aal1CesNapComponentName,
--           aal1CesLCoPathUpDateTime,
--           aal1CesLCoRequiredTrafficType,
--           aal1CesPepLastTearDownDiagnostic,
--           aal1CesAepLocalAddress,
--           aal1CesPepExpectedRemoteAddress,
--           aal1CesConnectionStatus,
--           aal1CesCustomerIdentifier,
--           aal1CesLCoComponentName,
--           aal1CesAepLastSetupFailureCause,
--           aal1CesLCoBytesFromNetwork,
--           aal1CesLCoOptimization,
--           aal1CesComponentName,
--           aal1CesPepComponentName,
--           aal1CesCellLossIntegrationPeriod,
--           aal1CesLCoPathType,
--           aal1CesAepRowStatus,
--           aal1CesLCoPathValue,
--           aal1CesStorageType }
-- STATUS  mandatory
-- DESCRIPTION
--   "A list of all current accessible leaf objects."

circuitEmulationServiceGroup OBJECT IDENTIFIER ::= { circuitEmulationServiceMIB 1 }
circuitEmulationServiceGroupBD OBJECT IDENTIFIER ::= { circuitEmulationServiceGroup 4 }
circuitEmulationServiceGroupBD00 OBJECT IDENTIFIER ::= { circuitEmulationServiceGroupBD 1 }
circuitEmulationServiceGroupBD00A OBJECT IDENTIFIER ::= { circuitEmulationServiceGroupBD00 2 }



-- Agent-Capabilities Statement:

-- PRODUCT-RELEASE "Passport Release 7.0 CircuitEmulationService."
-- STATUS          mandatory
-- DESCRIPTION     "CircuitEmulationService MIB: MIB Version BD00A,
--                  Software Version BG00S4C."
-- SUPPORTS        Nortel-Magellan-Passport-CircuitEmulationServiceMIB
--    INCLUDES     { circuitEmulationServiceGroupBD00A }

circuitEmulationServiceCapabilities OBJECT IDENTIFIER ::= { circuitEmulationServiceMIB 3 }
circuitEmulationServiceCapabilitiesBD OBJECT IDENTIFIER ::= { circuitEmulationServiceCapabilities 4 }
circuitEmulationServiceCapabilitiesBD00 OBJECT IDENTIFIER ::= { circuitEmulationServiceCapabilitiesBD 1 }
circuitEmulationServiceCapabilitiesBD00A OBJECT IDENTIFIER ::= { circuitEmulationServiceCapabilitiesBD00 2 }





END
