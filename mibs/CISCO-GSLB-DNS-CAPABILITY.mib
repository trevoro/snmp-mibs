-- *****************************************************************
-- CISCO-GSLB-DNS-CAPABILITY.my:
-- CISCO-GSLB-DNS-MIB AGENT-CAPABILITIES
--   
-- Feb 2007, Pawan N
--   
-- Copyright (c) 2006-2007 by Cisco Systems Inc.
-- All rights reserved.
-- ****************************************************************

CISCO-GSLB-DNS-CAPABILITY DEFINITIONS ::= BEGIN

IMPORTS
    MODULE-IDENTITY
        FROM SNMPv2-SMI
    AGENT-CAPABILITIES
        FROM SNMPv2-CONF
    ciscoAgentCapability
        FROM CISCO-SMI;


ciscoGslbDnsCapability MODULE-IDENTITY
    LAST-UPDATED    "200702230000Z"
    ORGANIZATION    "Cisco Systems, Inc."
    CONTACT-INFO
            "Cisco Systems
            Customer Service

            Postal:  170 W Tasman Drive
            San Jose, CA  95134
            USA

            Tel:  +1 800 553-NETS

            E-mail:  cs-slb@cisco.com"
    DESCRIPTION
        "The capabilities description
        of CISCO-GSLB-DNS-MIB."
    REVISION        "200702230000Z"
    DESCRIPTION
        "Initial version of this MIB module."
    ::= { ciscoAgentCapability 535 }



ciscoGslbDnsCapabilityV02R00 AGENT-CAPABILITIES
    PRODUCT-RELEASE "GSS 2.0"
    STATUS          current
    DESCRIPTION
        "GSS 2.0 Cisco GSLB DNS MIB capabilities"

    SUPPORTS        CISCO-GSLB-DNS-MIB
    INCLUDES        {
                        ciscoGslbDnsNotifObjectsGroup,
                        ciscoGslbDnsNotifGroup
                    }
    ::= { ciscoGslbDnsCapability 1 }

END
