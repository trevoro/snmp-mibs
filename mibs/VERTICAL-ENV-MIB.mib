VERTICAL-ENV-MIB DEFINITIONS ::= BEGIN

IMPORTS
             Gauge, enterprises
                     FROM RFC1155-SMI
             DisplayString
                     FROM RFC1213-MIB
             OBJECT-TYPE
                     FROM RFC-1212
             TRAP-TYPE
                     FROM RFC-1215;
             

vertical OBJECT IDENTIFIER ::= { enterprises 2338 }  


     --  This MIB module uses the extended OBJECT-TYPE macro 
	 --  as defined in RFC 1212.
  
     --  This is the MIB module for Vertical Networks IO Box
     --  environment.Presently, this includes cooling fans 
     --  and Power supply units.  
	 --  This MIB is found in the private.enterprise branch 
	 --  of the MIB tree.

     --  Author  : Raju Viswambharan
     --  Version : 1.0
     --  Date    : 19 October, 1998
     --  Comments : created
 

     -- This MIB is structured into two groups:
	
     --	The Fan Table: Which contains status information about
     --                       the Instant Office cooling fans
     --	The Power Supply Table: Which contains status 
     --                         information about the Instant 
	 --							Office power supply units
	 --	The Trap Info Group: Which contains more information
     --                      about the last Fan, Power Supply 
	 --					     and Fault Monitor Trap.

	 environment    OBJECT IDENTIFIER ::= {vertical 11}
								   
     -- The Fan Table  - The Instant Office fan table
		
       iOFanTable OBJECT-TYPE
              SYNTAX  SEQUENCE OF IOFanEntry
              ACCESS  not-accessible
              STATUS  current
              DESCRIPTION
               "Table of status information about all 
			    Instant Office cooling fans"
       ::= { environment 1 }

       iOFanEntry OBJECT-TYPE
             SYNTAX  IOFanEntry
             ACCESS  not-accessible
             STATUS  mandatory
             DESCRIPTION
              "An entry in the Fan Table."
             INDEX {fanIndex}
             ::= {iOFanTable 1}
     
       IOFanEntry ::=
            SEQUENCE {
			  fanIndex
                 INTEGER,
              fanOperStatus
                 INTEGER
            }


	  fanIndex OBJECT-TYPE
              SYNTAX  INTEGER
              ACCESS  read-only
              STATUS  mandatory
              DESCRIPTION
                 "The index of the cooling fan within the system"
              ::= { iOFanEntry 1}

       fanOperStatus OBJECT-TYPE
              SYNTAX  INTEGER {
					running				(1), 
					stopped				(2),
					unknown				(3) 
			  }    
              ACCESS  read-only
              STATUS  mandatory
              DESCRIPTION
                 "The operational status of this fan.
				  The following are valid values:
					running	=1,(the normal	operational state),	stopped	=2, unknown	=3"
              ::= { iOFanEntry 2}


     -- The PowerSupply Table  - The Instant Office Power 
	 --                          Supply Table
		
       iOPSTable OBJECT-TYPE
              SYNTAX  SEQUENCE OF IOPSEntry
              ACCESS  not-accessible
              STATUS  current
              DESCRIPTION
               "Table of status information about all
			    Instant Office power supplies"
       ::= { environment 2 }

       iOPSEntry OBJECT-TYPE
             SYNTAX  IOPSEntry
             ACCESS  not-accessible
             STATUS  mandatory
             DESCRIPTION
              "An entry in the Power Supply Table."
             INDEX {psIndex}
             ::= {iOPSTable 1}
     
       IOPSEntry ::=
            SEQUENCE {
			  psIndex
                 INTEGER,
              psOperStatus
                 INTEGER
            }


	  psIndex OBJECT-TYPE
              SYNTAX  INTEGER
              ACCESS  read-only
              STATUS  mandatory
              DESCRIPTION
                 "The index of the power supply unit within the system"
              ::= { iOPSEntry 1}

       psOperStatus OBJECT-TYPE
              SYNTAX  INTEGER {
					on					(1), 
					off					(2),
					unknown				(3) 
			  }    
              ACCESS  read-only
              STATUS  mandatory
              DESCRIPTION
                 "The operational status of this power supply.
				  The following are valid
				  values:
					on=1, off=2, unknown=3 "
              ::= { iOPSEntry 2}


	-- Fault Monitor Group - contains information about the 
	--                          Fault Monitor Status

	iOFaultMonitorGroup OBJECT IDENTIFIER ::= { environment 3 }
	
	

	iOFaultMonitorStatus OBJECT-TYPE
		SYNTAX  INTEGER {
					rAMFull					(1), 
					notResponding			(2),
					ok						(3),
					modemFailed				(4) 
			  }    
              ACCESS  read-only
              STATUS  mandatory
              DESCRIPTION
                 "The operational status of the Fault 
				  Monitor. The following are valid 
				  values:
					RAMFull					=1, 
					NotResponding			=2, 
					Ok						=3,
					ModemFailed				=4 "
              ::= { iOFaultMonitorGroup 1}


	-- Trap Information Group - contains information about 
	--                 the last Fan and Power Supply Traps

	iOTrapInfoGroup OBJECT IDENTIFIER ::= { environment 4 }
	
	

	iOLastFanTrap OBJECT-TYPE
		SYNTAX      DisplayString (SIZE (0..255))
		ACCESS  read-only
		STATUS      mandatory
		DESCRIPTION
            "This object describes,in more detail,the last Fan
			 Trap event that occured. Since traps for all fans
			 are combined into one Trap, this string describes
			 each fan status just after the trap condition."
			::= { iOTrapInfoGroup 1 }



	iOLastPowerSupplyTrap OBJECT-TYPE
		SYNTAX      DisplayString (SIZE (0..255))
        ACCESS  read-only
        STATUS      mandatory
        DESCRIPTION
            "This object describes,in more detail,the last 
			 Power Supply Trap event that occured. Since 
			 traps for all power supplies are combined into
			 one Trap, this string describes each power 
			 supply status just after the trap condition."
			::= { iOTrapInfoGroup 2 }

	iOLastFaultMonitorTrap OBJECT-TYPE
		SYNTAX      DisplayString (SIZE (0..255))
        ACCESS  read-only
        STATUS      mandatory
        DESCRIPTION
            "This object describes,in more detail,the last
			 Fault Monitor Trap event that occured. Since
			 traps for all Fault Monitor events are combined
			 into one Trap,this string describes the Fault
			 Monitor event (RAM full, NotResponding or 
			 Modem Failed) that caused this trap."
			::= { iOTrapInfoGroup 3 }



-- TRAP Definitions - 

iOFanStatus TRAP-TYPE
	ENTERPRISE  vertical
	VARIABLES {iOLastFanTrap }
	DESCRIPTION
        " This notification is sent when one (or more) 
		  cooling fans changes state (i.e. it goes from
		  an ON state to OFF state or vice-versa. Even
		  if more than one fan changes state, only one 
		  trap is sent. Information about the new state
		  of all the fans is sent in the Trap Data
		  (iOLastFanTrap)"
	::= 47

iOPowerSupplyStatus TRAP-TYPE
	ENTERPRISE  vertical
	VARIABLES {iOLastPowerSupplyTrap }
	DESCRIPTION
        " This notification is sent when one (or more)
		  power supply units changs state (i.e it goes
		  from an ON state to an OFF state, or vice 
		  versa). Even if more than one power supply 
		  changes state, only one trap is sent. Information
		  about the new state of all the power supplies 
		  is sent in the Trap Data (IOLastPowerSupplyTrap)."
	::= 48

iOFaultMonitorStatusTrap TRAP-TYPE
	ENTERPRISE  vertical
	VARIABLES {iOLastFaultMonitorTrap }
	DESCRIPTION
        " This notification is sent when or more of
		  the following Fault Monitor Events occur:
		  RAM full, Fault Monitor NotResponding or 
		  Modem Failed. Information about these 
		  events is contained in the Trap data
		  (IOLatFaultmonitorTrap)."
	::= 49


END
