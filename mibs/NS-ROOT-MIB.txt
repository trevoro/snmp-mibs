NS-ROOT-MIB DEFINITIONS ::= BEGIN

IMPORTS
    Counter32, Counter64, Gauge32, Integer32, IpAddress, NOTIFICATION-TYPE, 
    OBJECT-TYPE, TimeTicks, enterprises, MODULE-IDENTITY, OBJECT-IDENTITY
        FROM SNMPv2-SMI;


netScaler MODULE-IDENTITY
    LAST-UPDATED "200406240000Z"
    ORGANIZATION
        "Netscaler, Inc."
    CONTACT-INFO
        " Netscaler Technical Assistance Center

         Postal: 180 Baytech Dr.
                 San Jose, CA 95134
                 USA

         Tel: +1-866-NETSCALER

         E-mail: support@netscaler.com"
    DESCRIPTION
        "The enterprise specific MIB for Netscaler."
    ::= { enterprises 5951 }


EntityState ::=
    INTEGER { down(1), unknown(2), busy(3), outOfService(4), 
                    transitionToOutOfService(5), up(7) }

EntityProtocolType ::=
    INTEGER { http(0), ftp(1), tcp(2), udp(3), sslBridge(4), monitor(5), 
                    monitorUdp(6), nntp(7), httpserver(8), httpclient(9), 
                    rpcserver(10), rpcclient(11), nat(12), 
                    any(13), ssl(14), dns(15), adns(16), snmp(17), 
                    ha(18), monitorPing(19), sslOtherTcp(20), aaa(21),
                    secureMonitor(22), sslvpnUpd(23), rip(24), dnsClient(25),
                    rpcServer(26), rpcClient(27), serviceUnknown(28) }

HAMode ::=
    INTEGER { standalone(0), primary(1), secondary(2), unknown(3) }

FeatureStatus ::=
    INTEGER { notLicensed(0), licensedButDisabled(1), 
                    licensedAndEnabled(2) }

ModeStatus ::=
    INTEGER { disabled(0), enabled(1) }

SiteType ::=
    INTEGER  { localSite(1),remoteSite(2) }

MepStatus ::=
    INTEGER  { mepActive(1),mepInactive(2),mepDown(3) }

MetricExchange ::=
    INTEGER { disabled(1) ,enabled(2) }

--netScaler OBJECT IDENTIFIER
--    ::= { enterprises 5951 }

nsRoot OBJECT IDENTIFIER
    ::= { netScaler 1 }

netScalerEvents OBJECT IDENTIFIER
    ::= { nsRoot 1 }

wsSystem OBJECT IDENTIFIER
    ::= { nsRoot 2 }

sysStatistics OBJECT IDENTIFIER
    ::= { wsSystem 1 }

totalClientConnections OBJECT-TYPE
    SYNTAX      Counter32
    MAX-ACCESS  read-only
    STATUS      current
    DESCRIPTION 
        "The Total Client Connections made from system start."
    ::= { sysStatistics 1 }

curClientConnections OBJECT-TYPE
    SYNTAX      Counter32
    MAX-ACCESS  read-only
    STATUS      current
    DESCRIPTION 
        "The Current Client Connections."
    ::= { sysStatistics 2 }

totalServerConnections OBJECT-TYPE
    SYNTAX      Counter32
    MAX-ACCESS  read-only
    STATUS      current
    DESCRIPTION 
        "The Total Server Connections made from system start."
    ::= { sysStatistics 3 }

curServerConnections OBJECT-TYPE
    SYNTAX      Counter32
    MAX-ACCESS  read-only
    STATUS      current
    DESCRIPTION 
        "The Current Server Connections."
    ::= { sysStatistics 4 }

clientConnRefused OBJECT-TYPE
    SYNTAX      Counter32
    MAX-ACCESS  read-only
    STATUS      current
    DESCRIPTION 
        "Client connections added the SurgeQ, and blocked from initiating a server connection to control op/s"
    ::= { sysStatistics 5 }

reuseHit OBJECT-TYPE
    SYNTAX      Counter32
    MAX-ACCESS  read-only
    STATUS      current
    DESCRIPTION 
        "Total no of client transactions used the server connection in the reuse-pool"
    ::= { sysStatistics 6 }

reuseMiss OBJECT-TYPE
    SYNTAX      Counter32
    MAX-ACCESS  read-only
    STATUS      current
    DESCRIPTION 
        "The total new Connections made, when server connection
         unavailable in reuse pool."
    ::= { sysStatistics 7 }

totClientDontReuse OBJECT-TYPE
    SYNTAX      Counter32
    MAX-ACCESS  read-only
    STATUS      current
    DESCRIPTION 
        "The total client connection with Dont Reuse flag set."
    ::= { sysStatistics 8 }

totServerDontReuse OBJECT-TYPE
    SYNTAX      Counter32
    MAX-ACCESS  read-only
    STATUS      current
    DESCRIPTION 
        "The total server connection with Dont Reuse set."
    ::= { sysStatistics 9 }

curPhysicalServers OBJECT-TYPE
    SYNTAX      Counter32
    MAX-ACCESS  read-only
    STATUS      current
    DESCRIPTION 
        "The number of physical servers that WS has open connections with."
    ::= { sysStatistics 10 }

totPhysicalServers OBJECT-TYPE
    SYNTAX      Counter32
    MAX-ACCESS  read-only
    STATUS      current
    DESCRIPTION 
        "The total number of physical servers that WS opened connections 
         to from the last reboot."
    ::= { sysStatistics 11 }

cookiePacketSeqReject OBJECT-TYPE
    SYNTAX      Counter32
    MAX-ACCESS  read-only
    STATUS      current
    DESCRIPTION 
        "The number of tcp connections rejected because of syn cookie sequence number mismatch."
    ::= { sysStatistics 12 }

cookieSignatureReject OBJECT-TYPE
    SYNTAX      Counter32
    MAX-ACCESS  read-only
    STATUS      current
    DESCRIPTION 
        "The number of tcp connections rejected because of syn cookie mismatch."
    ::= { sysStatistics 13 }

cpuUsage OBJECT-TYPE
    SYNTAX      Counter32
    MAX-ACCESS  read-only
    STATUS      current
    DESCRIPTION 
        "The CPU Utilization."
    ::= { sysStatistics 14 }

unackSyn OBJECT-TYPE
    SYNTAX      Counter32
    MAX-ACCESS  read-only
    STATUS      current
    DESCRIPTION 
        "The number of un-acknowledged SYNs NS has received so far."
    ::= { sysStatistics 15 }

curClientEstablishedConn OBJECT-TYPE
    SYNTAX      Counter32
    MAX-ACCESS  read-only
    STATUS      current
    DESCRIPTION 
        "The number of currently established client connections."
    ::= { sysStatistics 16 }

curServerEstablishedConn OBJECT-TYPE
    SYNTAX      Counter32
    MAX-ACCESS  read-only
    STATUS      current
    DESCRIPTION 
        "The number of currently established server connections."
    ::= { sysStatistics 17 }

wsHttpGroup OBJECT IDENTIFIER
	::= { sysStatistics 18 }

totalRequests OBJECT-TYPE
    SYNTAX      Counter32
    MAX-ACCESS  read-only
    STATUS      obsolete
    DESCRIPTION 
        "The total HTTP Requests."
    ::= { wsHttpGroup 1 }

totalGets OBJECT-TYPE
    SYNTAX      Counter32
    MAX-ACCESS  read-only
    STATUS      obsolete
    DESCRIPTION 
        "The total HTTP GETs."
    ::= { wsHttpGroup 2 }

totalRequests1-0 OBJECT-TYPE
    SYNTAX      Counter32
    MAX-ACCESS  read-only
    STATUS      obsolete
    DESCRIPTION 
        "The total HTTP 1.0 Requests."
    ::= { wsHttpGroup 3 }

totalPosts OBJECT-TYPE
    SYNTAX      Counter32
    MAX-ACCESS  read-only
    STATUS      obsolete
    DESCRIPTION 
        "The total HTTP Posts."
    ::= { wsHttpGroup 4 }

totalResponses OBJECT-TYPE
    SYNTAX      Counter32
    MAX-ACCESS  read-only
    STATUS      obsolete
    DESCRIPTION 
        "The total HTTP Responses."
    ::= { wsHttpGroup 5 }

totalResponses1-0 OBJECT-TYPE
    SYNTAX      Counter32
    MAX-ACCESS  read-only
    STATUS      obsolete
    DESCRIPTION 
        "The total HTTP 1.0 Responses."
    ::= { wsHttpGroup 6 }

totalContentLenResponses OBJECT-TYPE
    SYNTAX      Counter32
    MAX-ACCESS  read-only
    STATUS      obsolete
    DESCRIPTION 
        "The total HTTP Responses with Content Length."
    ::= { wsHttpGroup 7 }

totalChunkedResponses OBJECT-TYPE
    SYNTAX      Counter32
    MAX-ACCESS  read-only
    STATUS      obsolete
    DESCRIPTION 
        "The total HTTP Chunked Responses."
    ::= { wsHttpGroup 8 }

totalMultiPartResponses OBJECT-TYPE
    SYNTAX      Counter32
    MAX-ACCESS  read-only
    STATUS      obsolete
    DESCRIPTION 
        "The total HTTP Multi-part Responses."
    ::= { wsHttpGroup 9 }

totalIncompleteHeaders OBJECT-TYPE
    SYNTAX      Counter32
    MAX-ACCESS  read-only
    STATUS      obsolete
    DESCRIPTION 
        "The total HTTP Incomplete headers."
    ::= { wsHttpGroup 10 }

totalIncompleteRequests OBJECT-TYPE
    SYNTAX      Counter32
    MAX-ACCESS  read-only
    STATUS      obsolete
    DESCRIPTION 
        "The total Incomplete Requests."
    ::= { wsHttpGroup 11 }

totalIncompleteResponses OBJECT-TYPE
    SYNTAX      Counter32
    MAX-ACCESS  read-only
    STATUS      obsolete
    DESCRIPTION 
        "The total Incomplete Responses."
    ::= { wsHttpGroup 12 }

totalPipeLinedRequests OBJECT-TYPE
    SYNTAX      Counter32
    MAX-ACCESS  read-only
    STATUS      obsolete
    DESCRIPTION 
        "The total pipe-lined Requests."
    ::= { wsHttpGroup 13 }

serverBusyErrs OBJECT-TYPE
    SYNTAX      Counter32
    MAX-ACCESS  read-only
    STATUS      obsolete
    DESCRIPTION 
        "The total HTTP Server Busy Errors."
    ::= { wsHttpGroup 14 }

wsIfStatsTable OBJECT-TYPE
    SYNTAX      SEQUENCE OF WsIfStatsEntry
    MAX-ACCESS  not-accessible
    STATUS      current
    DESCRIPTION 
        "The Raw bandwidth usage of all the interfaces."
    ::= { sysStatistics 19 }

wsIfStatsEntry OBJECT-TYPE
    SYNTAX      WsIfStatsEntry
    MAX-ACCESS  not-accessible
    STATUS      current
    DESCRIPTION 
        "The Raw bandwidth usage of all the interfaces."
    INDEX       { index }
    ::= { wsIfStatsTable 1 }

WsIfStatsEntry ::= SEQUENCE {
    index                       Integer32,
    wsIfName                    OCTET STRING,
    wsIfMedia                   OCTET STRING,
    rxRawBandwidthUsage         Counter32,
    rxAveragePacketRate         Counter32,
    rxCurrentPacketRate         Counter32,
    rxAveragePacketsSize        Counter32,
    rxFrameErrors               Counter32,
    rxCrcErrors                 Counter32,
    rxAlignmentErrors           Counter32,
    txRawBandwidthUsage         Counter32,
    txAveragePacketRate         Counter32,
    txCurrentPacketRate         Counter32,
    txAveragePacketsSize        Counter32,
    txExcessCollisions          Counter32,
    txLateCollisions            Counter32,
    txCollisions                Counter32,
    txMultiCollisionsErrors     Counter32,
    txCarrierErrors             Counter32
}

index OBJECT-TYPE
    SYNTAX      Integer32
    MAX-ACCESS  read-only
    STATUS      current
    DESCRIPTION 
        "The distinguishing Id for each physical interface."
    ::= { wsIfStatsEntry 1 }

wsIfName OBJECT-TYPE
    SYNTAX      OCTET STRING
    MAX-ACCESS  read-only
    STATUS      current
    DESCRIPTION 
        "The name of the Interface"
    ::= { wsIfStatsEntry 2 }

wsIfMedia OBJECT-TYPE
    SYNTAX      OCTET STRING
    MAX-ACCESS  read-only
    STATUS      current
    DESCRIPTION 
        "The media type of the Interface"
    ::= { wsIfStatsEntry 3 }

rxRawBandwidthUsage OBJECT-TYPE
    SYNTAX      Counter32
    MAX-ACCESS  read-only
    STATUS      current
    DESCRIPTION 
        "The received raw bandwidth on interface in bitsps
         since the last time this variable was 
         retrieved using SNMP."
    ::= { wsIfStatsEntry 4 }

rxAveragePacketRate OBJECT-TYPE
    SYNTAX      Counter32
    MAX-ACCESS  read-only
    STATUS      current
    DESCRIPTION 
        "The average number of packets received on the 
         interface since the system start."
    ::= { wsIfStatsEntry 5 }

rxCurrentPacketRate OBJECT-TYPE
    SYNTAX      Counter32
    MAX-ACCESS  read-only
    STATUS      current
    DESCRIPTION 
        "The packet rate on the interface since the last
         time the variable was retrieved with using SNMP."
    ::= { wsIfStatsEntry 6 }

rxAveragePacketsSize OBJECT-TYPE
    SYNTAX      Counter32
    MAX-ACCESS  read-only
    STATUS      current
    DESCRIPTION 
        "The average size of the packet received on the 
         interface since the system start."
    ::= { wsIfStatsEntry 7 }

rxFrameErrors OBJECT-TYPE
    SYNTAX      Counter32
    MAX-ACCESS  read-only
    STATUS      current
    DESCRIPTION 
        "A Counter for the number of frame errors received
         on the interface."
    ::= { wsIfStatsEntry 8 }

rxCrcErrors OBJECT-TYPE
    SYNTAX      Counter32
    MAX-ACCESS  read-only
    STATUS      current
    DESCRIPTION 
        "A Counter for the number of Crc errors received on
         the interface."
    ::= { wsIfStatsEntry 9 }

rxAlignmentErrors OBJECT-TYPE
    SYNTAX      Counter32
    MAX-ACCESS  read-only
    STATUS      current
    DESCRIPTION 
        "A Counter to indicate the number of Alignment errors
         received on the interface."
    ::= { wsIfStatsEntry 10 }

txRawBandwidthUsage OBJECT-TYPE
    SYNTAX      Counter32
    MAX-ACCESS  read-only
    STATUS      current
    DESCRIPTION 
        "The transmit raw bandwidth on interface in bitsps
         from the last time this variable was retrieved."
    ::= { wsIfStatsEntry 11 }

txAveragePacketRate OBJECT-TYPE
    SYNTAX      Counter32
    MAX-ACCESS  read-only
    STATUS      current
    DESCRIPTION 
        "The average number of packets transmitted on the 
         the interface since the system start."
    ::= { wsIfStatsEntry 12 }

txCurrentPacketRate OBJECT-TYPE
    SYNTAX      Counter32
    MAX-ACCESS  read-only
    STATUS      current
    DESCRIPTION 
        "The packet rate on the interface since the last
         time this variable was retrieved using SNMP."
    ::= { wsIfStatsEntry 13 }

txAveragePacketsSize OBJECT-TYPE
    SYNTAX      Counter32
    MAX-ACCESS  read-only
    STATUS      current
    DESCRIPTION 
        "The average size of the packet received on the 
         interface since the system start."
    ::= { wsIfStatsEntry 14 }

txExcessCollisions OBJECT-TYPE
    SYNTAX      Counter32
    MAX-ACCESS  read-only
    STATUS      current
    DESCRIPTION 
        "A Counter to indicate excess collisions detected in
         transmission on the interface."
    ::= { wsIfStatsEntry 15 }

txLateCollisions OBJECT-TYPE
    SYNTAX      Counter32
    MAX-ACCESS  read-only
    STATUS      current
    DESCRIPTION 
        "A Counter to indicate late collisions detected in
         transmission on the interface."
    ::= { wsIfStatsEntry 16 }

txCollisions OBJECT-TYPE
    SYNTAX      Counter32
    MAX-ACCESS  read-only
    STATUS      current
    DESCRIPTION 
        "A Counter to indicate total collision Errors detected 
         in transmission on the interface."
    ::= { wsIfStatsEntry 17 }

txMultiCollisionsErrors OBJECT-TYPE
    SYNTAX      Counter32
    MAX-ACCESS  read-only
    STATUS      current
    DESCRIPTION 
        "A Counter to indicate Multi collision Errors detected 
         in transmission on the interface."
    ::= { wsIfStatsEntry 18 }

txCarrierErrors OBJECT-TYPE
    SYNTAX      Counter32
    MAX-ACCESS  read-only
    STATUS      current
    DESCRIPTION 
        "A Counter to indicate Carrier Errors detected in 
         transmission on the interface."
    ::= { wsIfStatsEntry 19 }

wsudpgroup OBJECT IDENTIFIER
    ::= { sysStatistics 20 }

totudpsessions OBJECT-TYPE
    SYNTAX      Counter32
    MAX-ACCESS  read-only
    STATUS      obsolete
    DESCRIPTION 
        "Total number of udp sessions since the start of the system"
    ::= { wsudpgroup 1 }

currudpsessions OBJECT-TYPE
    SYNTAX      Counter32
    MAX-ACCESS  read-only
    STATUS      obsolete
    DESCRIPTION 
        "Total number of current udp sessions "
    ::= { wsudpgroup 2 }

sysConfig OBJECT IDENTIFIER
    ::= { wsSystem 2 }

wsIpAddress OBJECT-TYPE
    SYNTAX      IpAddress
    MAX-ACCESS  read-only
    STATUS      current
    DESCRIPTION 
        "The primary IP address of the netscaler."
    ::= { sysConfig 1 }

wsNetmask OBJECT-TYPE
    SYNTAX      IpAddress
    MAX-ACCESS  read-only
    STATUS      current
    DESCRIPTION 
        "The netmask for the IP address of the netscaler."
    ::= { sysConfig 2 }

wsMappedIpAddress OBJECT-TYPE
    SYNTAX      IpAddress
    MAX-ACCESS  read-only
    STATUS      obsolete
    DESCRIPTION 
        "The Mapped IP address of the netscaler."
    ::= { sysConfig 3 }

wsLastMappedIpAddress OBJECT-TYPE
    SYNTAX      IpAddress
    MAX-ACCESS  read-only
    STATUS      obsolete
    DESCRIPTION 
        "The last Mapped IP address of the netscaler."
    ::= { sysConfig 4 }

wsMappedIpAddressRange OBJECT-TYPE
    SYNTAX      Integer32
    MAX-ACCESS  read-only
    STATUS      obsolete
    DESCRIPTION 
        "The range of mapped IP addresses on the netscaler."
    ::= { sysConfig 5 }

wsFailOver OBJECT-TYPE
    SYNTAX      INTEGER { enabled(1), disabled(2) }
    MAX-ACCESS  read-only
    STATUS      current
    DESCRIPTION 
        "Is Fail Over enabled on the netscaler."
    ::= { sysConfig 6 }

wsPriority OBJECT-TYPE
    SYNTAX      Integer32
    MAX-ACCESS  read-only
    STATUS      obsolete
    DESCRIPTION 
        "The priority of the netscaler."
    ::= { sysConfig 7 }

wsMaxClientList OBJECT-TYPE
    SYNTAX      Integer32
    MAX-ACCESS  read-only
    STATUS      current
    DESCRIPTION 
        "The Maximum number of server connections that NS can open to the server."
    ::= { sysConfig 8 }

wsClientIp OBJECT-TYPE
    SYNTAX      INTEGER { enabled(1), disabled(2) }
    MAX-ACCESS  read-only
    STATUS      current
    DESCRIPTION 
        "Enable Client IP in the HTTP Request to the Server."
    ::= { sysConfig 9 }

wsFailoverTime OBJECT-TYPE
    SYNTAX      Integer32
    MAX-ACCESS  read-only
    STATUS      obsolete
    DESCRIPTION 
        "The time in seconds after which the secondary takes over as 
         primary, if there is no response from primary."
    ::= { sysConfig 10 }

wsMaxRequestsPerConn OBJECT-TYPE
    SYNTAX      Integer32
    MAX-ACCESS  read-only
    STATUS      current
    DESCRIPTION 
        "The Maximum number of requests per connection on a server-connection."
    ::= { sysConfig 11 }

wsSmoothConnection OBJECT-TYPE
    SYNTAX      INTEGER { enabled(1), disabled(2) }
    MAX-ACCESS  read-only
    STATUS      current
    DESCRIPTION 
        "Smooth Connection Feature on the netscaler."
    ::= { sysConfig 12 }

loadBalancing OBJECT IDENTIFIER
    ::= { nsRoot 3 }

lbStatisticsTable OBJECT-TYPE
    SYNTAX      SEQUENCE OF LbStatisticsEntry
    MAX-ACCESS  not-accessible
    STATUS      current
    DESCRIPTION 
        "The Virtual Service Information for each of the entities."
    ::= { loadBalancing 1 }

lbStatisticsEntry OBJECT-TYPE
    SYNTAX      LbStatisticsEntry
    MAX-ACCESS  not-accessible
    STATUS      current
    DESCRIPTION 
        "The Virtual Service Information for each of the entities."
    INDEX       { vsId, psId }
    ::= { lbStatisticsTable 1 }

LbStatisticsEntry ::= SEQUENCE {
    vsId            Integer32,
    psId            Integer32,
    vsIpAddress     IpAddress,
    vsPort          Integer32,
    psIpAddress     IpAddress,
    psPort          Integer32,
    protocolType    INTEGER,
    lbMethod		INTEGER,
    serviceHits     Integer32,
    latency         Integer32,
    connections		Integer32

}

vsId OBJECT-TYPE
    SYNTAX      Integer32
    MAX-ACCESS  read-only
    STATUS      current
    DESCRIPTION 
        "The distinguishing Id for each Virtual Service inside
         a NetScaler."
    ::= { lbStatisticsEntry 1 }

psId OBJECT-TYPE
    SYNTAX      Integer32
    MAX-ACCESS  read-only
    STATUS      current
    DESCRIPTION 
        "The distinguishing Id for each Physical Service inside
         a NetScaler."
    ::= { lbStatisticsEntry 2 }

vsIpAddress OBJECT-TYPE
    SYNTAX      IpAddress
    MAX-ACCESS  read-only
    STATUS      current
    DESCRIPTION 
        "The IP address in the Virtual Service."
    ::= { lbStatisticsEntry 3 }

vsPort OBJECT-TYPE
    SYNTAX      Integer32
    MAX-ACCESS  read-only
    STATUS      current
    DESCRIPTION 
        "The port in the Virtual Service."
    ::= { lbStatisticsEntry 4 }

psIpAddress OBJECT-TYPE
    SYNTAX      IpAddress
    MAX-ACCESS  read-only
    STATUS      current
    DESCRIPTION 
        "The IP address in the Physical Service."
    ::= { lbStatisticsEntry 5 }

psPort OBJECT-TYPE
    SYNTAX      Integer32
    MAX-ACCESS  read-only
    STATUS      current
    DESCRIPTION 
        "The port in the Physical Service."
    ::= { lbStatisticsEntry 6 }

protocolType OBJECT-TYPE
    SYNTAX      INTEGER { http(0), ftp(1), tcp(2), udp(3), sslBridge(4), 
                    monitor(5), monitorUdp(6), nntp(7), httpserver(8), 
                    httpclient(9), rpcserver(10), rpcclient(11), ssf(12), 
                    nat(13), any(14), ssl(15), dns(16), adns(17), 
                    snmp(18), ha(19), monitorPing(20), 
                    serviceUnknown(21) }
    MAX-ACCESS  read-only
    STATUS      current
    DESCRIPTION 
        "The protocol type in the Virtual Service."
    ::= { lbStatisticsEntry 7 }

lbMethod OBJECT-TYPE
	SYNTAX INTEGER	{
		weightedRoundRobin(1), leastConnections(2), leastResponse(3),
		asynchronousMAC(4), urlHashed(5), domainHashed(6),
		destinationIPHashed(7), sourceIPHashed(8), leastBandwidth(9),
		leastPackets(10) }
		MAX-ACCESS read-only
		STATUS current
		DESCRIPTION
			"The Policy used for Load Balancing"
		::= { lbStatisticsEntry 8 }

serviceHits OBJECT-TYPE
    SYNTAX      Integer32
    MAX-ACCESS  read-only
    STATUS      current
    DESCRIPTION 
        "The total hits on the physical service."
    ::= { lbStatisticsEntry 9 }

latency OBJECT-TYPE
    SYNTAX      Integer32
    MAX-ACCESS  read-only
    STATUS      current
    DESCRIPTION 
        "The latency in responding to gets from the 
         physical server."
    ::= { lbStatisticsEntry 10 }

connections OBJECT-TYPE
	SYNTAX Integer32
	MAX-ACCESS read-only
	STATUS current
	DESCRIPTION
		"The number of active connections on the 
		 physical Server."
	::= { lbStatisticsEntry 11 }


lbConfig OBJECT IDENTIFIER
    ::= { loadBalancing 2 }

virServiceTable OBJECT-TYPE
    SYNTAX      SEQUENCE OF VirServiceEntry
    MAX-ACCESS  not-accessible
    STATUS      current
    DESCRIPTION 
        "The table that has all the configuration information 
         for each virtual service."
    ::= { lbConfig 1 }

virServiceEntry OBJECT-TYPE
    SYNTAX      VirServiceEntry
    MAX-ACCESS  not-accessible
    STATUS      current
    DESCRIPTION 
        "The Virtual Service Information for each of the entities."
    INDEX       { vserId }
    ::= { virServiceTable 1 }

VirServiceEntry ::= SEQUENCE {
    vserId                Integer32,
    ipAddress           IpAddress,
    port                Integer32,
    vsProtocolType        INTEGER,
    name                OCTET STRING,
    vsLbMethod			INTEGER,
    persistanceType		INTEGER,
    persistanceTimeout  Integer32,
    state				INTEGER
}

vserId OBJECT-TYPE
    SYNTAX      Integer32
    MAX-ACCESS  read-only
    STATUS      current
    DESCRIPTION 
        "The distinguishing Id for each Virtual Service inside
         a NetScaler."
    ::= { virServiceEntry 1 }

ipAddress OBJECT-TYPE
    SYNTAX      IpAddress
    MAX-ACCESS  read-only
    STATUS      current
    DESCRIPTION 
        "The IP address in the Virtual Service."
    ::= { virServiceEntry 2 }

port OBJECT-TYPE
    SYNTAX      Integer32
    MAX-ACCESS  read-only
    STATUS      current
    DESCRIPTION 
        "The port in the Virtual Service."
    ::= { virServiceEntry 3 }

vsProtocolType OBJECT-TYPE
    SYNTAX      INTEGER { http(0), ftp(1), tcp(2), udp(3), sslBridge(4), 
                    monitor(5), monitorUdp(6), nntp(7), httpserver(8), 
                    httpclient(9), rpcserver(10), rpcclient(11), ssf(12), 
                    nat(13), any(14), ssl(15), dns(16), adns(17), 
                    snmp(18), ha(19), monitorPing(20), 
                    serviceUnknown(21) }
    MAX-ACCESS  read-only
    STATUS      current
    DESCRIPTION 
        "The protocol type in the Virtual Service."
    ::= { virServiceEntry 4 }

name OBJECT-TYPE
    SYNTAX      OCTET STRING
    MAX-ACCESS  read-only
    STATUS      current
    DESCRIPTION 
        "The name of the Virtual Service"
    ::= { virServiceEntry 5 }

vsLbMethod OBJECT-TYPE
	SYNTAX INTEGER	{
		weightedRoundRobin(1), leastConnections(2), leastResponse(3),
		asynchronousMAC(4), urlHashed(5), domainHashed(6),
		destinationIPHashed(7), sourceIPHashed(8), leastBandwidth(9),
		leastPackets(10)
	}
	MAX-ACCESS read-only
	STATUS current
	DESCRIPTION
		"The Policy used for Load Balancing"
	::= { virServiceEntry 6 }

persistanceType OBJECT-TYPE
	SYNTAX INTEGER	{
		sourceIp(1), cookieInsert(2), cookieDelete(3), cookieRead(4),
		cookieHash(5), sessionId(6), server(7)
	}
	MAX-ACCESS read-only
	STATUS current
	DESCRIPTION
		"The type of persistence used"
	::= {virServiceEntry 7}

persistanceTimeout OBJECT-TYPE
    SYNTAX      Integer32
    MAX-ACCESS  read-only
    STATUS      current
    DESCRIPTION 
        "The timeout set for persistence "
    ::= { virServiceEntry 8 }

state OBJECT-TYPE
	SYNTAX INTEGER	{
		up(0), down(1), unknown(2),
		busy(3), outOfService(4), transitionToOutOfService(5)
	}		
	MAX-ACCESS read-only
	STATUS current
	DESCRIPTION
		"The State of the virtual Service"
	::= {virServiceEntry 9}


phyServiceTable OBJECT-TYPE
    SYNTAX      SEQUENCE OF PhyServiceEntry
    MAX-ACCESS  not-accessible
    STATUS      current
    DESCRIPTION 
        "The table that has all the configuration information 
         for each physical service."
    ::= { lbConfig 2 }

phyServiceEntry OBJECT-TYPE
    SYNTAX      PhyServiceEntry
    MAX-ACCESS  not-accessible
    STATUS      current
    DESCRIPTION 
        "The Physical Service Information for each of the entities."
    INDEX       { pserId }
    ::= { phyServiceTable 1 }

PhyServiceEntry ::= SEQUENCE {
    pserId            Integer32,
    pserIpAddress     IpAddress,
    pserPort          Integer32,
    psProtocolType    INTEGER,
    psName            OCTET STRING,
    psState			INTEGER,
    weight          Integer32,
    psVsIpAddress     IpAddress,
    psVsPort          Integer32
}

pserId OBJECT-TYPE
    SYNTAX      Integer32
    MAX-ACCESS  read-only
    STATUS      current
    DESCRIPTION 
        "The distinguishing Id for each Physical Service inside
         a NetScaler."
    ::= { phyServiceEntry 1 }

pserIpAddress OBJECT-TYPE
    SYNTAX      IpAddress
    MAX-ACCESS  read-only
    STATUS      current
    DESCRIPTION 
        "The IP address in the Physical Service."
    ::= { phyServiceEntry 2 }

pserPort OBJECT-TYPE
    SYNTAX      Integer32
    MAX-ACCESS  read-only
    STATUS      current
    DESCRIPTION 
        "The port in the Physical Service."
    ::= { phyServiceEntry 3 }

psProtocolType OBJECT-TYPE
    SYNTAX      INTEGER { http(0), ftp(1), tcp(2), udp(3), sslBridge(4), 
                    monitor(5), monitorUdp(6), nntp(7), httpserver(8), 
                    httpclient(9), rpcserver(10), rpcclient(11), ssf(12), 
                    nat(13), any(14), ssl(15), dns(16), adns(17), 
                    snmp(18), ha(19), monitorPing(20), 
                    serviceUnknown(21) }
    MAX-ACCESS  read-only
    STATUS      current
    DESCRIPTION 
        "The protocol type in the Physical Service."
    ::= { phyServiceEntry 4 }

psName OBJECT-TYPE
    SYNTAX      OCTET STRING
    MAX-ACCESS  read-only
    STATUS      current
    DESCRIPTION 
        "The name of the Physical Service"
    ::= { phyServiceEntry 5 }
 
psState OBJECT-TYPE
	SYNTAX INTEGER	{down(0), up(1) }
	MAX-ACCESS read-only
	STATUS current
	DESCRIPTION
		"The state of the Physical Service."
	::= {phyServiceEntry 6}

weight OBJECT-TYPE
    SYNTAX      Integer32
    MAX-ACCESS  read-only
    STATUS      current
    DESCRIPTION 
        "The weight assigned to the Physical Service."
    ::= { phyServiceEntry 7 }

psVsIpAddress OBJECT-TYPE
    SYNTAX      IpAddress
    MAX-ACCESS  read-only
    STATUS      current
    DESCRIPTION 
        "The IP address in the Virtual Service to which this
         physical service is bound."
    ::= { phyServiceEntry 8 }

psVsPort OBJECT-TYPE
    SYNTAX      Integer32
    MAX-ACCESS  read-only
    STATUS      current
    DESCRIPTION 
        "The port in the Virtual Service."
    ::= { phyServiceEntry 9 }

sureConnect OBJECT IDENTIFIER
    ::= { nsRoot 4 }

scStatistics OBJECT IDENTIFIER
    ::= { sureConnect 1 }

scperServiceStatisticsTable OBJECT-TYPE
    SYNTAX      SEQUENCE OF ScperServiceStatisticsEntry
    MAX-ACCESS  not-accessible
    STATUS      current
    DESCRIPTION 
        "The Internet On Hold Statistics for each of the entities."
    ::= { scStatistics 1 }

scperServiceStatisticsEntry OBJECT-TYPE
    SYNTAX      ScperServiceStatisticsEntry
    MAX-ACCESS  not-accessible
    STATUS      current
    DESCRIPTION 
        "The Internet On Hold Statistics for each of the entities."
    INDEX       { devno }
    ::= { scperServiceStatisticsTable 1 }

ScperServiceStatisticsEntry ::= SEQUENCE {
    devno           Integer32,
    phyIpAddress    IpAddress,
    phyPort         Integer32,
    scProtocolType    INTEGER,
    currentDelay    Integer32,
    avgTxTime       Integer32,
    surgeCount      Integer32,
    iohCount        Integer32
}

devno OBJECT-TYPE
    SYNTAX      Integer32
    MAX-ACCESS  read-only
    STATUS      current
    DESCRIPTION 
        "The distinguishing Id for each physical Service inside
         a NetScaler."
    ::= { scperServiceStatisticsEntry 1 }

phyIpAddress OBJECT-TYPE
    SYNTAX      IpAddress
    MAX-ACCESS  read-only
    STATUS      current
    DESCRIPTION 
        "The IP address in the Physical Service."
    ::= { scperServiceStatisticsEntry 2 }

phyPort OBJECT-TYPE
    SYNTAX      Integer32
    MAX-ACCESS  read-only
    STATUS      current
    DESCRIPTION 
        "The port in the Physical Service."
    ::= { scperServiceStatisticsEntry 3 }

scProtocolType OBJECT-TYPE
    SYNTAX      INTEGER { http(0), ftp(1), tcp(2), udp(3), sslBridge(4), 
                    monitor(5), monitorUdp(6), nntp(7), httpserver(8), 
                    httpclient(9), rpcserver(10), rpcclient(11), ssf(12), 
                    nat(13), any(14), ssl(15), dns(16), adns(17), 
                    snmp(18), ha(19), monitorPing(20), 
                    serviceUnknown(21) }
    MAX-ACCESS  read-only
    STATUS      current
    DESCRIPTION 
        "The protocol type in the Physical Service."
    ::= { scperServiceStatisticsEntry 4 }

currentDelay OBJECT-TYPE
    SYNTAX      Integer32
    MAX-ACCESS  read-only
    STATUS      current
    DESCRIPTION 
        "The current Delay on the physical Service."
    ::= { scperServiceStatisticsEntry 5 }

avgTxTime OBJECT-TYPE
    SYNTAX      Integer32
    MAX-ACCESS  read-only
    STATUS      current
    DESCRIPTION 
        "The average transaction time."
    ::= { scperServiceStatisticsEntry 6 }

surgeCount OBJECT-TYPE
    SYNTAX      Integer32
    MAX-ACCESS  read-only
    STATUS      current
    DESCRIPTION 
        "The count of number of times the surge occurred."
    ::= { scperServiceStatisticsEntry 7 }

iohCount OBJECT-TYPE
    SYNTAX      Integer32
    MAX-ACCESS  read-only
    STATUS      current
    DESCRIPTION 
        "The number of client requests, after having put on hold
         couldnt still access the physical server."
    ::= { scperServiceStatisticsEntry 8 }

scperPolicyStatisticsTable OBJECT-TYPE
    SYNTAX      SEQUENCE OF ScperPolicyStatisticsEntry
    MAX-ACCESS  not-accessible
    STATUS      current
    DESCRIPTION 
        "The Internet On Hold Statistics for each of the entities."
    ::= { scStatistics 2 }

scperPolicyStatisticsEntry OBJECT-TYPE
    SYNTAX      ScperPolicyStatisticsEntry
    MAX-ACCESS  not-accessible
    STATUS      current
    DESCRIPTION 
        "The Internet On Hold Statistics for each of the entities."
    INDEX       { policydevno }
    ::= { scperPolicyStatisticsTable 1 }

ScperPolicyStatisticsEntry ::= SEQUENCE {
    policydevno             Integer32,
    primaryserviceIp        IpAddress,
    primaryserviceport      Integer32,
    destserviceIp           IpAddress,
    destserviceport         Integer32,
    transactiontime         Integer32,
    totaltransaction        Integer32,
    totalopenconnection     Integer32
}

policydevno OBJECT-TYPE
    SYNTAX      Integer32
    MAX-ACCESS  read-only
    STATUS      current
    DESCRIPTION 
        "The distinguishing Id for each physical Service inside
         a NetScaler."
    ::= { scperPolicyStatisticsEntry 1 }

primaryserviceIp OBJECT-TYPE
    SYNTAX      IpAddress
    MAX-ACCESS  read-only
    STATUS      current
    DESCRIPTION 
        " ip address of primary service"
    ::= { scperPolicyStatisticsEntry 2 }

primaryserviceport OBJECT-TYPE
    SYNTAX      Integer32
    MAX-ACCESS  read-only
    STATUS      current
    DESCRIPTION 
        " port number of primary service"
    ::= { scperPolicyStatisticsEntry 3 }

destserviceIp OBJECT-TYPE
    SYNTAX      IpAddress
    MAX-ACCESS  read-only
    STATUS      current
    DESCRIPTION 
        " ip address of destination physical service"
    ::= { scperPolicyStatisticsEntry 4 }

destserviceport OBJECT-TYPE
    SYNTAX      Integer32
    MAX-ACCESS  read-only
    STATUS      current
    DESCRIPTION 
        " port number of destination physical service"
    ::= { scperPolicyStatisticsEntry 5 }

transactiontime OBJECT-TYPE
    SYNTAX      Integer32
    MAX-ACCESS  read-only
    STATUS      current
    DESCRIPTION 
        " transaction time"
    ::= { scperPolicyStatisticsEntry 6 }

totaltransaction OBJECT-TYPE
    SYNTAX      Integer32
    MAX-ACCESS  read-only
    STATUS      current
    DESCRIPTION 
        " total number of transactions "
    ::= { scperPolicyStatisticsEntry 7 }

totalopenconnection OBJECT-TYPE
    SYNTAX      Integer32
    MAX-ACCESS  read-only
    STATUS      current
    DESCRIPTION 
        " total number of open connections for this policy "
    ::= { scperPolicyStatisticsEntry 8 }

scGlobalStats OBJECT IDENTIFIER
    ::= { scStatistics 3 }

scUrlHits OBJECT-TYPE
    SYNTAX      Integer32
    MAX-ACCESS  read-only
    STATUS      current
    DESCRIPTION 
        "this Counter gives the  number of times we matched an
         incoming request with a Configured sureconnect  policy "
    ::= { scGlobalStats 1 }

popUps OBJECT-TYPE
	SYNTAX Integer32
	MAX-ACCESS read-only
	STATUS current
	DESCRIPTION
		"this Counter gives the number of times  we served the
		in-memory java script which throws up the pop up window"
	::= { scGlobalStats 2 }

altContUrls OBJECT-TYPE
	SYNTAX Integer32
	MAX-ACCESS read-only
	STATUS current
	DESCRIPTION
		"this Counter gives the total  number of requests which
		came with the onhold cookie. So, this gives the number requests
 		which  are required to load the alternate content in the pop up
 		window."

	::= { scGlobalStats 3 }

sessReqs OBJECT-TYPE
	SYNTAX Integer32
	MAX-ACCESS read-only
	STATUS	current
	DESCRIPTION
		"this Counter gives the number requests which came in a
		SureConnect session. "
	::= {scGlobalStats 4 }

postReqs OBJECT-TYPE
	SYNTAX Integer32
	MAX-ACCESS read-only
	STATUS current
	DESCRIPTION
		"this Counter gives the number of times a post request
		triggered  SureConnect"
	::= { scGlobalStats 5 }

thresholdFail OBJECT-TYPE
	SYNTAX Integer32
	MAX-ACCESS read-only
	STATUS current
	DESCRIPTION
		" this Counter gives the number of times we did not serve the
		in-memory response because  the  thresholds conditions had failed "
	::= { scGlobalStats 6}

faultyCookies OBJECT-TYPE
	SYNTAX Integer32
	MAX-ACCESS read-only
	STATUS current
	DESCRIPTION
		"this Counter gives the number of times we encountered
		corrupted SureConnect Cookies"
	::= { scGlobalStats 7}

unSupBrow OBJECT-TYPE
	SYNTAX Integer32
	MAX-ACCESS read-only
	STATUS current
	DESCRIPTION
		"this Counter gives the number of times requests came from
		unsupported browsers. For a list of  browsers supported by
		SureConnect, please check the Functional Spec."
	::= { scGlobalStats 8}

resetStats OBJECT-TYPE
	SYNTAX Integer32
	MAX-ACCESS read-only
	STATUS current
	DESCRIPTION
		"This gives the number of times delay stats were reset.
		Delay stats are reset when there is no traffic to the configured
		url for more than 10 minutes"
	::= { scGlobalStats 9}		

scConfig OBJECT IDENTIFIER
    ::= { sureConnect 2 }

scPolicyconfigTable OBJECT-TYPE
    SYNTAX      SEQUENCE OF ScPolicyconfigEntry
    MAX-ACCESS  not-accessible
    STATUS      current
    DESCRIPTION 
        "The Internet On Hold Statistics for each of the entities."
    ::= { scConfig 1 }

scPolicyconfigEntry OBJECT-TYPE
    SYNTAX      ScPolicyconfigEntry
    MAX-ACCESS  not-accessible
    STATUS      current
    DESCRIPTION 
        "The Internet On Hold Statistics for each of the entities."
    INDEX       { policyIndex }
    ::= { scPolicyconfigTable 1 }

ScPolicyconfigEntry ::= SEQUENCE {
    policyIndex                     Integer32,
    policyName                      OCTET STRING,
    scPolicyUrl                     OCTET STRING,
    delayThreshold                  INTEGER,
    maxConnections                  INTEGER,
    actionType						INTEGER,
    alternatecontentServicename     OCTET STRING,
    ruleName                        OCTET STRING,
    alternatecontentPath            OCTET STRING
}

policyIndex OBJECT-TYPE
    SYNTAX      Integer32
    MAX-ACCESS  read-only
    STATUS      current
    DESCRIPTION 
        "The distinguishing Id for each On Hold Policy inside
         a NetScaler."
    ::= { scPolicyconfigEntry 1 }

policyName OBJECT-TYPE
    SYNTAX      OCTET STRING
    MAX-ACCESS  read-only
    STATUS      current
    DESCRIPTION 
        "The name of the Physical Service"
    ::= { scPolicyconfigEntry 2 }

scPolicyUrl OBJECT-TYPE
    SYNTAX      OCTET STRING
    MAX-ACCESS  read-only
    STATUS      current
    DESCRIPTION 
        "The URL in the IOH Policy"
    ::= { scPolicyconfigEntry 3 }

delayThreshold OBJECT-TYPE
    SYNTAX      INTEGER { notconfigured(-1) }
    MAX-ACCESS  read-only
    STATUS      current
    DESCRIPTION 
        "The delay threshold."
    ::= { scPolicyconfigEntry 4 }

maxConnections OBJECT-TYPE
    SYNTAX      INTEGER { notconfigured(-1) }
    MAX-ACCESS  read-only
    STATUS      current
    DESCRIPTION 
        "The max connections."
    ::= { scPolicyconfigEntry 5 }

actionType OBJECT-TYPE
	SYNTAX INTEGER { ns (0), acs (1), noAction(4) }
	MAX-ACCESS read-only
	STATUS current
	DESCRIPTION
		"The type of action that NetScaler takes when initiating on-hold."
	::= { scPolicyconfigEntry 6}
		
alternatecontentServicename OBJECT-TYPE
    SYNTAX      OCTET STRING
    MAX-ACCESS  read-only
    STATUS      current
    DESCRIPTION 
        "The alternate service name for the content "
    ::= { scPolicyconfigEntry 7 }

ruleName OBJECT-TYPE
    SYNTAX      OCTET STRING
    MAX-ACCESS  read-only
    STATUS      current
    DESCRIPTION 
        " Rule Name "
    ::= { scPolicyconfigEntry 8 }

alternatecontentPath OBJECT-TYPE
    SYNTAX      OCTET STRING
    MAX-ACCESS  read-only
    STATUS      current
    DESCRIPTION 
        "The alternate path for the content "
    ::= { scPolicyconfigEntry 9 }

contentSwitching OBJECT IDENTIFIER
    ::= { nsRoot 5 }

cswStatisticsTable OBJECT-TYPE
    SYNTAX      SEQUENCE OF CswStatisticsEntry
    MAX-ACCESS  not-accessible
    STATUS      current
    DESCRIPTION 
        "The Content Switching Statistics for each of the entities."
    ::= { contentSwitching 1 }

cswStatisticsEntry OBJECT-TYPE
    SYNTAX      CswStatisticsEntry
    MAX-ACCESS  not-accessible
    STATUS      current
    DESCRIPTION 
        "The Content Switching Statistics for each of the entities."
    INDEX       { cswIndex }
    ::= { cswStatisticsTable 1 }

CswStatisticsEntry ::= SEQUENCE {
    cswIndex           Integer32,
    cswVsIpAddress     IpAddress,
    cswVsPort          Integer32,
    cswProtocolType    INTEGER,
    virServiceName  OCTET STRING,
    vsHits          Integer32,
    vsMiss          Integer32
}

cswIndex OBJECT-TYPE
    SYNTAX      Integer32
    MAX-ACCESS  read-only
    STATUS      current
    DESCRIPTION 
        "The distinguishing Id for each virtual Service inside
         a NetScaler."
    ::= { cswStatisticsEntry 1 }

cswVsIpAddress OBJECT-TYPE
    SYNTAX      IpAddress
    MAX-ACCESS  read-only
    STATUS      current
    DESCRIPTION 
        "The IP address in the Virtual Service."
    ::= { cswStatisticsEntry 2 }

cswVsPort OBJECT-TYPE
    SYNTAX      Integer32
    MAX-ACCESS  read-only
    STATUS      current
    DESCRIPTION 
        "The port in the Virtual Service."
    ::= { cswStatisticsEntry 3 }

cswProtocolType OBJECT-TYPE
    SYNTAX      INTEGER { http(0), ftp(1), tcp(2), udp(3), sslBridge(4), 
                    monitor(5), monitorUdp(6), nntp(7), httpserver(8), 
                    httpclient(9), rpcserver(10), rpcclient(11), ssf(12), 
                    nat(13), any(14), ssl(15), dns(16), adns(17), 
                    snmp(18), ha(19), monitorPing(20), 
                    serviceUnknown(21) }
    MAX-ACCESS  read-only
    STATUS      current
    DESCRIPTION 
        "The protocol type of the Virtual Server."
    ::= { cswStatisticsEntry 4 }

virServiceName OBJECT-TYPE
    SYNTAX      OCTET STRING
    MAX-ACCESS  read-only
    STATUS      current
    DESCRIPTION 
        "The name of the CSW Virtual server "
    ::= { cswStatisticsEntry 5 }

vsHits OBJECT-TYPE
    SYNTAX      Integer32
    MAX-ACCESS  read-only
    STATUS      current
    DESCRIPTION 
        "The total hits on all the policies bound to this virtual server."
    ::= { cswStatisticsEntry 6 }

vsMiss OBJECT-TYPE
    SYNTAX      Integer32
    MAX-ACCESS  read-only
    STATUS      current
    DESCRIPTION 
        "The total Miss on all the policies bound to this virtual server."
    ::= { cswStatisticsEntry 7 }

cswConfigTable OBJECT-TYPE
    SYNTAX      SEQUENCE OF CswConfigEntry
    MAX-ACCESS  not-accessible
    STATUS      current
    DESCRIPTION 
        "The CSW configuration information for each of the entities."
    ::= { contentSwitching 2 }

cswConfigEntry OBJECT-TYPE
    SYNTAX      CswConfigEntry
    MAX-ACCESS  not-accessible
    STATUS      current
    DESCRIPTION 
        "The CSW configuration information for each of the entities."
    INDEX       { cswVsId, policyId }
    ::= { cswConfigTable 1 }

CswConfigEntry ::= SEQUENCE {
    cswVsId            Integer32,
    policyId        Integer32,
    vServerName     OCTET STRING,
    policyname      OCTET STRING,
    policyvalue     OCTET STRING,
    policyHits      Integer32,
    domain          OCTET STRING
}

cswVsId OBJECT-TYPE
    SYNTAX      Integer32
    MAX-ACCESS  read-only
    STATUS      current
    DESCRIPTION 
        "The distinguishing Id for each CSW Vserver inside
         a NetScaler."
    ::= { cswConfigEntry 1 }

policyId OBJECT-TYPE
    SYNTAX      Integer32
    MAX-ACCESS  read-only
    STATUS      current
    DESCRIPTION 
        "The distinguishing Id for each CSW Policy inside
         a NetScaler."
    ::= { cswConfigEntry 2 }

vServerName OBJECT-TYPE
    SYNTAX      OCTET STRING
    MAX-ACCESS  read-only
    STATUS      current
    DESCRIPTION 
        "The name of the CSW Virtual Server"
    ::= { cswConfigEntry 3 }

policyname OBJECT-TYPE
    SYNTAX      OCTET STRING
    MAX-ACCESS  read-only
    STATUS      current
    DESCRIPTION 
        "The name of the policy binding to a Virtual Server"
    ::= { cswConfigEntry 4 }

policyvalue OBJECT-TYPE
    SYNTAX      OCTET STRING
    MAX-ACCESS  read-only
    STATUS      current
    DESCRIPTION 
        "The value of the policy"
    ::= { cswConfigEntry 5 }

policyHits OBJECT-TYPE
    SYNTAX      Integer32
    MAX-ACCESS  read-only
    STATUS      current
    DESCRIPTION 
        "The hits on the Policy in the Virtual Service."
    ::= { cswConfigEntry 6 }

domain OBJECT-TYPE
    SYNTAX      OCTET STRING
    MAX-ACCESS  read-only
    STATUS      current
    DESCRIPTION 
        "The domain hosted by the CSW vserver"
    ::= { cswConfigEntry 7 }

cacheRedirection OBJECT IDENTIFIER
    ::= { nsRoot 6 }

crStatisticsTable OBJECT-TYPE
    SYNTAX      SEQUENCE OF CrStatisticsEntry
    MAX-ACCESS  not-accessible
    STATUS      current
    DESCRIPTION 
        "The Cache Redirection Statistics for each of the entities."
    ::= { cacheRedirection 1 }

crStatisticsEntry OBJECT-TYPE
    SYNTAX      CrStatisticsEntry
    MAX-ACCESS  not-accessible
    STATUS      current
    DESCRIPTION 
        "The Cache Redirection Statistics for each of the entities."
    INDEX       { crVsIndex }
    ::= { crStatisticsTable 1 }

CrStatisticsEntry ::= SEQUENCE {
    crVsIndex           Integer32,
    crVsIpAddress     IpAddress,
    crVsPort          Integer32,
    crProtocolType    INTEGER,
    crVirServiceName  OCTET STRING,
    crVsHits          Integer32,
    crVsMiss          Integer32
}

crVsIndex OBJECT-TYPE
    SYNTAX      Integer32
    MAX-ACCESS  read-only
    STATUS      current
    DESCRIPTION 
        "The distinguishing Id for each virtual Service inside
         a NetScaler."
    ::= { crStatisticsEntry 1 }

crVsIpAddress OBJECT-TYPE
    SYNTAX      IpAddress
    MAX-ACCESS  read-only
    STATUS      current
    DESCRIPTION 
        "The IP address in the Virtual Service."
    ::= { crStatisticsEntry 2 }

crVsPort OBJECT-TYPE
    SYNTAX      Integer32
    MAX-ACCESS  read-only
    STATUS      current
    DESCRIPTION 
        "The port in the Virtual Service."
    ::= { crStatisticsEntry 3 }

crProtocolType OBJECT-TYPE
    SYNTAX      INTEGER { http(0), ftp(1), tcp(2), udp(3), sslBridge(4), 
                    monitor(5), monitorUdp(6), nntp(7), httpserver(8), 
                    httpclient(9), rpcserver(10), rpcclient(11), ssf(12), 
                    nat(13), any(14), ssl(15), dns(16), adns(17), 
                    snmp(18), ha(19), monitorPing(20), 
                    serviceUnknown(21) }
    MAX-ACCESS  read-only
    STATUS      current
    DESCRIPTION 
        "The protocol type in the Physical Service."
    ::= { crStatisticsEntry 4 }

crVirServiceName OBJECT-TYPE
    SYNTAX      OCTET STRING
    MAX-ACCESS  read-only
    STATUS      current
    DESCRIPTION 
        "The name of the CSW Virtual server "
    ::= { crStatisticsEntry 5 }

crVsHits OBJECT-TYPE
    SYNTAX      Integer32
    MAX-ACCESS  read-only
    STATUS      current
    DESCRIPTION 
        "The total hits on the policies."
    ::= { crStatisticsEntry 6 }

crVsMiss OBJECT-TYPE
    SYNTAX      Integer32
    MAX-ACCESS  read-only
    STATUS      current
    DESCRIPTION 
        "The total Miss on the policy."
    ::= { crStatisticsEntry 7 }

crConfig OBJECT IDENTIFIER
    ::= { cacheRedirection 2 }

crPolBindConfigTable OBJECT-TYPE
    SYNTAX      SEQUENCE OF CrPolBindConfigEntry
    MAX-ACCESS  not-accessible
    STATUS      current
    DESCRIPTION 
        "The CR policy binding configuration information for each of the entry."
    ::= { crConfig 1 }

crPolBindConfigEntry OBJECT-TYPE
    SYNTAX      CrPolBindConfigEntry
    MAX-ACCESS  not-accessible
    STATUS      current
    DESCRIPTION 
        "The CR policy binding configuration information for each of the entry."
    INDEX       { bindId }
    ::= { crPolBindConfigTable 1 }

CrPolBindConfigEntry ::= SEQUENCE {
    bindId          Integer32,
    crbVServerName     OCTET STRING,
    crbPolicyname      OCTET STRING,
    crbPolicyvalue     OCTET STRING,
    crbPolicyHits      Integer32
}

bindId OBJECT-TYPE
    SYNTAX      Integer32
    MAX-ACCESS  read-only
    STATUS      current
    DESCRIPTION 
        "The unique binding Id for each CR Policy inside
         a NetScaler."
    ::= { crPolBindConfigEntry 1 }

crbVServerName OBJECT-TYPE
    SYNTAX      OCTET STRING
    MAX-ACCESS  read-only
    STATUS      current
    DESCRIPTION 
        "The name of the CR Virtual Server"
    ::= { crPolBindConfigEntry 2 }

crbPolicyname OBJECT-TYPE
    SYNTAX      OCTET STRING
    MAX-ACCESS  read-only
    STATUS      current
    DESCRIPTION 
        "The name of the policy binding to a Virtual Server"
    ::= { crPolBindConfigEntry 3 }

crbPolicyvalue OBJECT-TYPE
    SYNTAX      OCTET STRING
    MAX-ACCESS  read-only
    STATUS      current
    DESCRIPTION 
        "The value of the policy"
    ::= { crPolBindConfigEntry 4 }

crbPolicyHits OBJECT-TYPE
    SYNTAX      Integer32
    MAX-ACCESS  read-only
    STATUS      current
    DESCRIPTION 
        "The hits on the Policy in the Virtual Service."
    ::= { crPolBindConfigEntry 5 }

crMapBindConfigTable OBJECT-TYPE
    SYNTAX      SEQUENCE OF CrMapBindConfigEntry
    MAX-ACCESS  not-accessible
    STATUS      current
    DESCRIPTION 
        "The CR map policy binding configuration information for each of the entry."
    ::= { crConfig 2 }

crMapBindConfigEntry OBJECT-TYPE
    SYNTAX      CrMapBindConfigEntry
    MAX-ACCESS  not-accessible
    STATUS      current
    DESCRIPTION 
        "The CR map policy binding configuration information for each of the entry."
    INDEX       { mapbindId }
    ::= { crMapBindConfigTable 1 }

CrMapBindConfigEntry ::= SEQUENCE {
    mapbindId       Integer32,
    mapName         OCTET STRING,
    mapHits         Integer32,
    vserverName     OCTET STRING
}

mapbindId OBJECT-TYPE
    SYNTAX      Integer32
    MAX-ACCESS  read-only
    STATUS      current
    DESCRIPTION 
        "The unique binding Id for each CR Map Policy inside
         a NetScaler."
    ::= { crMapBindConfigEntry 1 }

mapName OBJECT-TYPE
    SYNTAX      OCTET STRING
    MAX-ACCESS  read-only
    STATUS      current
    DESCRIPTION 
        "The name of the map policy bound to CR Virtual Server"
    ::= { crMapBindConfigEntry 2 }

mapHits OBJECT-TYPE
    SYNTAX      Integer32
    MAX-ACCESS  read-only
    STATUS      current
    DESCRIPTION 
        "The hits on the Map Policy in the Virtual Service"
    ::= { crMapBindConfigEntry 3 }

vserverName OBJECT-TYPE
    SYNTAX      OCTET STRING
    MAX-ACCESS  read-only
    STATUS      current
    DESCRIPTION 
        "The name of the CR vserver"
    ::= { crMapBindConfigEntry 4 }

crMapConfigTable OBJECT-TYPE
    SYNTAX      SEQUENCE OF CrMapConfigEntry
    MAX-ACCESS  not-accessible
    STATUS      current
    DESCRIPTION 
        "The CR map configuration information for each of the entry."
    ::= { crConfig 3 }

crMapConfigEntry OBJECT-TYPE
    SYNTAX      CrMapConfigEntry
    MAX-ACCESS  not-accessible
    STATUS      current
    DESCRIPTION 
        "The CR map configuration information for each of the entry."
    INDEX       { crmIndex }
    ::= { crMapConfigTable 1 }

CrMapConfigEntry ::= SEQUENCE {
    crmIndex       Integer32,
    crmMapName     OCTET STRING,
    srcDomain   OCTET STRING,
    dstDomain   OCTET STRING,
    srcUrl      OCTET STRING,
    dstUrl      OCTET STRING
}

crmIndex OBJECT-TYPE
    SYNTAX      Integer32
    MAX-ACCESS  read-only
    STATUS      current
    DESCRIPTION 
        "The unique Id for each CR Map inside
         a NetScaler."
    ::= { crMapConfigEntry 1 }

crmMapName OBJECT-TYPE
    SYNTAX      OCTET STRING
    MAX-ACCESS  read-only
    STATUS      current
    DESCRIPTION 
        "The name of the map policy"
    ::= { crMapConfigEntry 2 }

srcDomain OBJECT-TYPE
    SYNTAX      OCTET STRING
    MAX-ACCESS  read-only
    STATUS      current
    DESCRIPTION 
        "The name of the source domain hosted by the map"
    ::= { crMapConfigEntry 3 }

dstDomain OBJECT-TYPE
    SYNTAX      OCTET STRING
    MAX-ACCESS  read-only
    STATUS      current
    DESCRIPTION 
        "The name of the destination domain after the mapping is applied"
    ::= { crMapConfigEntry 4 }

srcUrl OBJECT-TYPE
    SYNTAX      OCTET STRING
    MAX-ACCESS  read-only
    STATUS      current
    DESCRIPTION 
        "The Url to be modified under the given source domain"
    ::= { crMapConfigEntry 5 }

dstUrl OBJECT-TYPE
    SYNTAX      OCTET STRING
    MAX-ACCESS  read-only
    STATUS      current
    DESCRIPTION 
        "The Url after mapping"
    ::= { crMapConfigEntry 6 }

compression OBJECT IDENTIFIER
    ::= { nsRoot 7 }

compressionStats OBJECT IDENTIFIER
    ::= { compression 1 }

cmpTotRequests OBJECT-TYPE
    SYNTAX      Counter32
    MAX-ACCESS  read-only
    STATUS      obsolete
    DESCRIPTION 
        " Number of compression requests done"
    ::= { compressionStats 1 }

cmpTotTxbytes OBJECT-TYPE
    SYNTAX      Counter32
    MAX-ACCESS  read-only
    STATUS      obsolete
    DESCRIPTION 
        " Number of compressed bytes transmitted"
    ::= { compressionStats 2 }

cmpTotRxbytes OBJECT-TYPE
    SYNTAX      Counter32
    MAX-ACCESS  read-only
    STATUS      obsolete
    DESCRIPTION 
        " Number of compressible bytes received"
    ::= { compressionStats 3 }

cmpTotTxpkts OBJECT-TYPE
    SYNTAX      Counter32
    MAX-ACCESS  read-only
    STATUS      obsolete
    DESCRIPTION 
        " Number of compressed packets transmitted"
    ::= { compressionStats 4 }

cmpTotRxpkts OBJECT-TYPE
    SYNTAX      Counter32
    MAX-ACCESS  read-only
    STATUS      obsolete
    DESCRIPTION 
        " Number of compressible packets received"
    ::= { compressionStats 5 }

compressionRatio OBJECT-TYPE
    SYNTAX      OCTET STRING
    MAX-ACCESS  read-only
    STATUS      obsolete
    DESCRIPTION 
        " ratio of compressible data received vs compressed data transmitted"
    ::= { compressionStats 6 }

totalDataCompressionRatio OBJECT-TYPE
    SYNTAX      OCTET STRING
    MAX-ACCESS  read-only
    STATUS      obsolete
    DESCRIPTION 
        " ratio of total data received to total data transmitted"
    ::= { compressionStats 7 }

vlan OBJECT IDENTIFIER
    ::= { nsRoot 8 }

vlanstatsTable OBJECT-TYPE
    SYNTAX      SEQUENCE OF VlanstatsEntry
    MAX-ACCESS  not-accessible
    STATUS      obsolete
    DESCRIPTION 
        "The Vlan Statistics for each of the entities."
    ::= { vlan 1 }

vlanstatsEntry OBJECT-TYPE
    SYNTAX      VlanstatsEntry
    MAX-ACCESS  not-accessible
    STATUS      obsolete
    DESCRIPTION 
        "The Vlan Statistics for each of the entities."
    INDEX       { vlansDevno }
    ::= { vlanstatsTable 1 }

VlanstatsEntry ::= SEQUENCE {
    vlansDevno                   Integer32,
    totalrxpkts             Counter32,
    totaltxpkts             Counter32,
    totalrxbytes            Counter32,
    totaltxbytes            Counter32,
    totaldroppedpkts        Counter32,
    totalbroadcastpackets   Counter32
}

vlansDevno OBJECT-TYPE
    SYNTAX      Integer32
    MAX-ACCESS  read-only
    STATUS      obsolete
    DESCRIPTION 
        "The distinguishing Id for each vlan inside
         netscaler"
    ::= { vlanstatsEntry 1 }

totalrxpkts OBJECT-TYPE
    SYNTAX      Counter32
    MAX-ACCESS  read-only
    STATUS      obsolete
    DESCRIPTION 
        "Total Number of packets received in this vlan "
    ::= { vlanstatsEntry 2 }

totaltxpkts OBJECT-TYPE
    SYNTAX      Counter32
    MAX-ACCESS  read-only
    STATUS      obsolete
    DESCRIPTION 
        "Total Number of packets transmitted in this vlan"
    ::= { vlanstatsEntry 3 }

totalrxbytes OBJECT-TYPE
    SYNTAX      Counter32
    MAX-ACCESS  read-only
    STATUS      obsolete
    DESCRIPTION 
        "Total Number of bytes received in this vlan "
    ::= { vlanstatsEntry 4 }

totaltxbytes OBJECT-TYPE
    SYNTAX      Counter32
    MAX-ACCESS  read-only
    STATUS      obsolete
    DESCRIPTION 
        "Total Number of bytes transmitted in this vlan"
    ::= { vlanstatsEntry 5 }

totaldroppedpkts OBJECT-TYPE
    SYNTAX      Counter32
    MAX-ACCESS  read-only
    STATUS      obsolete
    DESCRIPTION 
        "Total Number of dropped packets in this vlan"
    ::= { vlanstatsEntry 6 }

totalbroadcastpackets OBJECT-TYPE
    SYNTAX      Counter32
    MAX-ACCESS  read-only
    STATUS      obsolete
    DESCRIPTION 
        "Total Number of broadcasted packets in this vlan"
    ::= { vlanstatsEntry 7 }

vlanconfigTable OBJECT-TYPE
    SYNTAX      SEQUENCE OF VlanconfigEntry
    MAX-ACCESS  not-accessible
    STATUS      current
    DESCRIPTION 
        "The Vlan config Statistics for each of the entities."
    ::= { vlan 2 }

vlanconfigEntry OBJECT-TYPE
    SYNTAX      VlanconfigEntry
    MAX-ACCESS  not-accessible
    STATUS      current
    DESCRIPTION 
        "The Vlan config Statistics for each of the entities."
    INDEX       { vlancDevno }
    ::= { vlanconfigTable 1 }

VlanconfigEntry ::= SEQUENCE {
    vlancDevno       Integer32,
    tagId       Integer32,
    interfaces  OCTET STRING,
    ipaddress   IpAddress,
    netmask     IpAddress,
    tagging     OCTET STRING
}

vlancDevno OBJECT-TYPE
    SYNTAX      Integer32
    MAX-ACCESS  read-only
    STATUS      current
    DESCRIPTION 
        "The distinguishing Id for each vlan inside
         netscaler"
    ::= { vlanconfigEntry 1 }

tagId OBJECT-TYPE
    SYNTAX      Integer32
    MAX-ACCESS  read-only
    STATUS      current
    DESCRIPTION 
        "The unique tag Id for each vlan inside
         NetScaler"
    ::= { vlanconfigEntry 2 }

interfaces OBJECT-TYPE
    SYNTAX      OCTET STRING
    MAX-ACCESS  read-only
    STATUS      current
    DESCRIPTION 
        "The port number associated to each vlan inside
         netscaler"
    ::= { vlanconfigEntry 3 }

ipaddress OBJECT-TYPE
    SYNTAX      IpAddress
    MAX-ACCESS  read-only
    STATUS      current
    DESCRIPTION 
        "The ipaddress for each vlan inside
         netscaler"
    ::= { vlanconfigEntry 4 }

netmask OBJECT-TYPE
    SYNTAX      IpAddress
    MAX-ACCESS  read-only
    STATUS      current
    DESCRIPTION 
        "The netmask corresponding to ipaddress for each vlan inside
         netscaler"
    ::= { vlanconfigEntry 5 }

tagging OBJECT-TYPE
    SYNTAX      OCTET STRING
    MAX-ACCESS  read-only
    STATUS      current
    DESCRIPTION 
        "Tagged member interfaces of this vlan"
    ::= { vlanconfigEntry 6 }

domainNameService OBJECT IDENTIFIER
    ::= { nsRoot 9 }

dnsServer OBJECT IDENTIFIER
    ::= { domainNameService 1 }

dnsServerStatistics OBJECT IDENTIFIER
    ::= { dnsServer 1 }

totQueries OBJECT-TYPE
    SYNTAX      Counter32
    MAX-ACCESS  read-only
    STATUS      current
    DESCRIPTION 
        "this Counter gives the  number of times NetScaler as a 
         name server received a query for any kind of DNS Record. "
    ::= { dnsServerStatistics 1 }

totAnswers OBJECT-TYPE
    SYNTAX      Counter32
    MAX-ACCESS  read-only
    STATUS      current
    DESCRIPTION 
        "this Counter gives the  number of times NetScaler as a 
         name server received a query for a name server Record. "
    ::= { dnsServerStatistics 2 }

totAuthAns OBJECT-TYPE
    SYNTAX      Counter32
    MAX-ACCESS  read-only
    STATUS      current
    DESCRIPTION 
        "Number of queries which were authoritatively answered."
    ::= { dnsServerStatistics 3 }

totAuthNoNames OBJECT-TYPE
    SYNTAX      Counter32
    MAX-ACCESS  read-only
    STATUS      current
    DESCRIPTION 
        "Number of queries for which `authoritative no such name'
         responses were made."
    ::= { dnsServerStatistics 4 }

totAuthNoDataResps OBJECT-TYPE
    SYNTAX      Counter32
    MAX-ACCESS  read-only
    STATUS      current
    DESCRIPTION 
        "Number of queries for which `authoritative no such data'
         (empty answer) responses were made."
    ::= { dnsServerStatistics 5 }

totNonAuthDatas OBJECT-TYPE
    SYNTAX      Counter32
    MAX-ACCESS  read-only
    STATUS      current
    DESCRIPTION 
        "Number of queries which were non-authoritatively
         answered (cached data)."
    ::= { dnsServerStatistics 6 }

totNonAuthNoDatas OBJECT-TYPE
    SYNTAX      Counter32
    MAX-ACCESS  read-only
    STATUS      current
    DESCRIPTION 
        "Number of queries which were non-authoritatively
         answered with no data (empty answer)."
    ::= { dnsServerStatistics 7 }

totReqRefusals OBJECT-TYPE
    SYNTAX      Counter32
    MAX-ACCESS  read-only
    STATUS      current
    DESCRIPTION 
        "Number of DNS requests refused by the server."
    ::= { dnsServerStatistics 8 }

totReqUnparses OBJECT-TYPE
    SYNTAX      Counter32
    MAX-ACCESS  read-only
    STATUS      current
    DESCRIPTION 
        "Number of requests received which were unparseable."
    ::= { dnsServerStatistics 9 }

totOtherErrors OBJECT-TYPE
    SYNTAX      Counter32
    MAX-ACCESS  read-only
    STATUS      current
    DESCRIPTION 
        "Number of requests which were aborted for other (local)
         server errors."
    ::= { dnsServerStatistics 10 }

aRecQueries OBJECT-TYPE
    SYNTAX      Counter32
    MAX-ACCESS  read-only
    STATUS      current
    DESCRIPTION 
        "this Counter gives the  number of times NetScaler as a 
         name server received a query for an Address Record. "
    ::= { dnsServerStatistics 11 }

nsRecQueries OBJECT-TYPE
    SYNTAX      Counter32
    MAX-ACCESS  read-only
    STATUS      current
    DESCRIPTION 
        "this Counter gives the  number of times NetScaler as a 
         name server received a query for a name server Record. "
    ::= { dnsServerStatistics 12 }

mxRecQueries OBJECT-TYPE
    SYNTAX      Counter32
    MAX-ACCESS  read-only
    STATUS      current
    DESCRIPTION 
        "this Counter gives the  number of times NetScaler as a 
         name server received a query for an mail exchanger Record. "
    ::= { dnsServerStatistics 13 }

soaRecQueries OBJECT-TYPE
    SYNTAX      Counter32
    MAX-ACCESS  read-only
    STATUS      current
    DESCRIPTION 
        "this Counter gives the  number of times NetScaler as a 
         name server received a query for an SOA Record. "
    ::= { dnsServerStatistics 14 }

cnameRecQueries OBJECT-TYPE
    SYNTAX      Counter32
    MAX-ACCESS  read-only
    STATUS      current
    DESCRIPTION 
        "this Counter gives the  number of times NetScaler as a 
         name server received a query for an CNAME Record. "
    ::= { dnsServerStatistics 15 }

totUnsupportedQueries OBJECT-TYPE
    SYNTAX      Counter32
    MAX-ACCESS  read-only
    STATUS      current
    DESCRIPTION 
        "this Counter gives the  number of times NetScaler as a 
         name server received a query for an unsupported Record type. "
    ::= { dnsServerStatistics 16 }

dnsServerConfig OBJECT IDENTIFIER
    ::= { dnsServer 2 }

dnsServerRecursion OBJECT-TYPE
    SYNTAX      INTEGER { available(1), restricted(2), unavailable(3) }
    MAX-ACCESS  read-only
    STATUS      current
    DESCRIPTION 
        "This represents the recursion services offered by this
         name server.  The values that can be read are:
         
         available(1) - performs recursion on requests from
         clients.
         
         restricted(2) - recursion is performed on requests only
         from certain clients, for example; clients on an access
         control list.
         
         unavailable(3) - recursion is not available."
    ::= { dnsServerConfig 1 }

dnsServerZoneTable OBJECT-TYPE
    SYNTAX      SEQUENCE OF DnsServerZoneEntry
    MAX-ACCESS  not-accessible
    STATUS      current
    DESCRIPTION 
        "The table that has the configuration information 
         for each zone for which NetScaler is authoritative."
    ::= { dnsServerConfig 2 }

dnsServerZoneEntry OBJECT-TYPE
    SYNTAX      DnsServerZoneEntry
    MAX-ACCESS  not-accessible
    STATUS      current
    DESCRIPTION 
        "The Zone information for each domain as an entry."
    INDEX       { zoneIndex }
    ::= { dnsServerZoneTable 1 }

DnsServerZoneEntry ::= SEQUENCE {
    zoneIndex   Integer32,
    zoneName    OCTET STRING
}

zoneIndex OBJECT-TYPE
    SYNTAX      Integer32
    MAX-ACCESS  read-only
    STATUS      current
    DESCRIPTION 
        "The distinguishing Id for each zone on NetScaler."
    ::= { dnsServerZoneEntry 1 }

zoneName OBJECT-TYPE
    SYNTAX      OCTET STRING
    MAX-ACCESS  read-only
    STATUS      current
    DESCRIPTION 
        "The domain name."
    ::= { dnsServerZoneEntry 2 }

globalServerLB OBJECT IDENTIFIER
    ::= { nsRoot 10 }

gslbStatistics OBJECT IDENTIFIER
    ::= { globalServerLB 1 }

gslbDomainStatsTable OBJECT-TYPE
    SYNTAX      SEQUENCE OF GslbDomainStatsEntry
    MAX-ACCESS  not-accessible
    STATUS      obsolete
    DESCRIPTION 
        "The table that has statistics for each gslb domain 
         on netscaler.OBSOLETE"
    ::= { gslbStatistics 1 }

gslbDomainStatsEntry OBJECT-TYPE
    SYNTAX      GslbDomainStatsEntry
    MAX-ACCESS  not-accessible
    STATUS      obsolete
    DESCRIPTION 
        "The gslb statistics table entry. OBSOLETE"
    INDEX       { gslbDomainIndex }
    ::= { gslbDomainStatsTable 1 }

GslbDomainStatsEntry ::= SEQUENCE {
    gslbDomainIndex     Integer32,
    domainName          OCTET STRING,
    gslbDomainQueries   Counter32
}

gslbDomainIndex OBJECT-TYPE
    SYNTAX      Integer32
    MAX-ACCESS  read-only
    STATUS      obsolete
    DESCRIPTION 
        "The distinguishing Id for each gslb Domain on NetScaler. OBSOLETE"
    ::= { gslbDomainStatsEntry 1 }

domainName OBJECT-TYPE
    SYNTAX      OCTET STRING
    MAX-ACCESS  read-only
    STATUS      obsolete
    DESCRIPTION 
        "The domain name that has gslb feature enabled. OBSOLETE"
    ::= { gslbDomainStatsEntry 2 }

gslbDomainQueries OBJECT-TYPE
    SYNTAX      Counter32
    MAX-ACCESS  read-only
    STATUS      obsolete
    DESCRIPTION 
        "number of times a dns query against this gslb domain
         was received by the netscaler. OBSOLETE"
    ::= { gslbDomainStatsEntry 3 }

gslbConfig OBJECT IDENTIFIER
    ::= { globalServerLB 2 }

gslbDomainConfigTable OBJECT-TYPE
    SYNTAX      SEQUENCE OF GslbDomainConfigEntry
    MAX-ACCESS  not-accessible
    STATUS      obsolete
    DESCRIPTION 
        "The table that has configuration for each gslb domain 
         on netscaler.OBSOLETE"
    ::= { gslbConfig 1 }

gslbDomainConfigEntry OBJECT-TYPE
    SYNTAX      GslbDomainConfigEntry
    MAX-ACCESS  not-accessible
    STATUS      obsolete
    DESCRIPTION 
        "The gslb statistics table entry. OBSOLETE"
    INDEX       { gslbcDomainIndex }
    ::= { gslbDomainConfigTable 1 }

GslbDomainConfigEntry ::= SEQUENCE {
    gslbcDomainIndex     Integer32,
    gslbcDomainName          OCTET STRING,
    gslbVipName         OCTET STRING,
    reOrderInterval     TimeTicks
}

gslbcDomainIndex OBJECT-TYPE
    SYNTAX      Integer32
    MAX-ACCESS  read-only
    STATUS      obsolete
    DESCRIPTION 
        "The distinguishing Id for each gslb Domain on NetScaler.OBSOLETE"
    ::= { gslbDomainConfigEntry 1 }

gslbcDomainName OBJECT-TYPE
    SYNTAX      OCTET STRING
    MAX-ACCESS  read-only
    STATUS      obsolete
    DESCRIPTION 
        "The domain name that has gslb feature enabled.OBSOLETE"
    ::= { gslbDomainConfigEntry 2 }

gslbVipName OBJECT-TYPE
    SYNTAX      OCTET STRING
    MAX-ACCESS  read-only
    STATUS      obsolete
    DESCRIPTION 
        "The LB VIP thats bound to the gslb domain name. All the 
         IP addresses for the gslb domain are bound to this VIP.
         The characteristics for this VIP should be found in the 
         LoadBalancing Group Mib. OBSOLETE"
    ::= { gslbDomainConfigEntry 3 }

reOrderInterval OBJECT-TYPE
    SYNTAX      TimeTicks
    MAX-ACCESS  read-only
    STATUS      obsolete
    DESCRIPTION 
        "The interval in which metrics are exchanged among the 
         NetScalers and a decision made about which is the best
         IP address at that point for the gslb domain name. OBSOLETE"
    ::= { gslbDomainConfigEntry 4 }

pq OBJECT IDENTIFIER
    ::= { nsRoot 11 }

pqstatistics OBJECT IDENTIFIER
    ::= { pq 1 }

pqStatsperLBVipTable OBJECT-TYPE
    SYNTAX      SEQUENCE OF PqStatsperLBVipEntry
    MAX-ACCESS  not-accessible
    STATUS      current
    DESCRIPTION 
        "The table that has statistics for each LB Vip 
         on netscaler."
    ::= { pqstatistics 1 }

pqStatsperLBVipEntry OBJECT-TYPE
    SYNTAX      PqStatsperLBVipEntry
    MAX-ACCESS  not-accessible
    STATUS      current
    DESCRIPTION 
        "The PQ statistics per Load Balancing VIP entry."
    INDEX       { pqDevno }
    ::= { pqStatsperLBVipTable 1 }

PqStatsperLBVipEntry ::= SEQUENCE {
    pqDevno                       Integer32,
    totclienttransactiontime    Counter32,
    totclienttransaction        Counter32,
    dropped                     Counter32,
    qdepth                      Counter32
}

pqDevno OBJECT-TYPE
    SYNTAX      Integer32
    MAX-ACCESS  read-only
    STATUS      current
    DESCRIPTION 
        "The distinguishing id for the LoadBalancing Vserver"
    ::= { pqStatsperLBVipEntry 1 }

totclienttransactiontime OBJECT-TYPE
    SYNTAX      Counter32
    MAX-ACCESS  read-only
    STATUS      current
    DESCRIPTION 
        "Total client transaction time "
    ::= { pqStatsperLBVipEntry 2 }

totclienttransaction OBJECT-TYPE
    SYNTAX      Counter32
    MAX-ACCESS  read-only
    STATUS      current
    DESCRIPTION 
        "Total number of client transaction "
    ::= { pqStatsperLBVipEntry 3 }

dropped OBJECT-TYPE
    SYNTAX      Counter32
    MAX-ACCESS  read-only
    STATUS      current
    DESCRIPTION 
        "Number of dropped transactions "
    ::= { pqStatsperLBVipEntry 4 }

qdepth OBJECT-TYPE
    SYNTAX      Counter32
    MAX-ACCESS  read-only
    STATUS      current
    DESCRIPTION 
        "Number of waiting clients "
    ::= { pqStatsperLBVipEntry 5 }

pqStatsperpqpolicyandperLBVipTable OBJECT-TYPE
    SYNTAX      SEQUENCE OF PqStatsperpqpolicyandperLBVipEntry
    MAX-ACCESS  not-accessible
    STATUS      current
    DESCRIPTION 
        "The table that has statistics for each LB Vip 
         on netscaler."
    ::= { pqstatistics 2 }

pqStatsperpqpolicyandperLBVipEntry OBJECT-TYPE
    SYNTAX      PqStatsperpqpolicyandperLBVipEntry
    MAX-ACCESS  not-accessible
    STATUS      current
    DESCRIPTION 
        "The PQ statistics per Load Balancing VIP entry."
    INDEX       { pqvsdevno, pqpoldevno }
    ::= { pqStatsperpqpolicyandperLBVipTable 1 }

PqStatsperpqpolicyandperLBVipEntry ::= SEQUENCE {
    pqvsdevno                     Integer32,
    pqpoldevno                  Integer32,
    pqtotclienttransactiontime    Counter32,
    pqtotclienttransaction        Counter32,
    pqDropped                     Counter32,
    pqQdepth                      Counter32
}

pqvsdevno OBJECT-TYPE
    SYNTAX      Integer32
    MAX-ACCESS  read-only
    STATUS      current
    DESCRIPTION 
        "The distinguishing id for the LoadBalancing Vservice"
    ::= { pqStatsperpqpolicyandperLBVipEntry 1 }

pqpoldevno OBJECT-TYPE
    SYNTAX      Integer32
    MAX-ACCESS  read-only
    STATUS      current
    DESCRIPTION 
        "The distinguishing id for the PQ policy"
    ::= { pqStatsperpqpolicyandperLBVipEntry 2 }

pqtotclienttransactiontime OBJECT-TYPE
    SYNTAX      Counter32
    MAX-ACCESS  read-only
    STATUS      current
    DESCRIPTION 
        "Total client transaction time "
    ::= { pqStatsperpqpolicyandperLBVipEntry 3 }

pqtotclienttransaction OBJECT-TYPE
    SYNTAX      Counter32
    MAX-ACCESS  read-only
    STATUS      current
    DESCRIPTION 
        "Total number of client transaction "
    ::= { pqStatsperpqpolicyandperLBVipEntry 4 }

pqDropped OBJECT-TYPE
    SYNTAX      Counter32
    MAX-ACCESS  read-only
    STATUS      current
    DESCRIPTION 
        "Number of dropped transactions "
    ::= { pqStatsperpqpolicyandperLBVipEntry 5 }

pqQdepth OBJECT-TYPE
    SYNTAX      Counter32
    MAX-ACCESS  read-only
    STATUS      current
    DESCRIPTION 
        "Number of waiting clients "
    ::= { pqStatsperpqpolicyandperLBVipEntry 6 }

pqconfig OBJECT IDENTIFIER
    ::= { pq 2 }

pqpolicyconfigTable OBJECT-TYPE
    SYNTAX      SEQUENCE OF PqpolicyconfigEntry
    MAX-ACCESS  not-accessible
    STATUS      current
    DESCRIPTION 
        "The table that has configuration statistics for each PQ
         policy on netscaler."
    ::= { pqconfig 1 }

pqpolicyconfigEntry OBJECT-TYPE
    SYNTAX      PqpolicyconfigEntry
    MAX-ACCESS  not-accessible
    STATUS      current
    DESCRIPTION 
        "The PQ config statistics per policy."
    INDEX       { pqPolDevno }
    ::= { pqpolicyconfigTable 1 }

PqpolicyconfigEntry ::= SEQUENCE {
    pqPolDevno               Integer32,
    pqpolicyname        OCTET STRING,
    rulename            OCTET STRING,
    qdepthThreshval     Integer32,
    polqdepthThreshval  Integer32,
    priority            Integer32,
    pqPolWeight              Integer32
}

pqPolDevno OBJECT-TYPE
    SYNTAX      Integer32
    MAX-ACCESS  read-only
    STATUS      current
    DESCRIPTION 
        "The distinguishing id for the policy"
    ::= { pqpolicyconfigEntry 1 }

pqpolicyname OBJECT-TYPE
    SYNTAX      OCTET STRING
    MAX-ACCESS  read-only
    STATUS      current
    DESCRIPTION 
        "The name for PQ policy"
    ::= { pqpolicyconfigEntry 2 }

rulename OBJECT-TYPE
    SYNTAX      OCTET STRING
    MAX-ACCESS  read-only
    STATUS      current
    DESCRIPTION 
        "The rule name"
    ::= { pqpolicyconfigEntry 3 }

qdepthThreshval OBJECT-TYPE
    SYNTAX      Integer32
    MAX-ACCESS  read-only
    STATUS      current
    DESCRIPTION 
        "The threshold value for qdepth"
    ::= { pqpolicyconfigEntry 4 }

polqdepthThreshval OBJECT-TYPE
    SYNTAX      Integer32
    MAX-ACCESS  read-only
    STATUS      current
    DESCRIPTION 
        "The threshold value for policyqdepth"
    ::= { pqpolicyconfigEntry 5 }

priority OBJECT-TYPE
    SYNTAX      Integer32
    MAX-ACCESS  read-only
    STATUS      current
    DESCRIPTION 
        "The priority for this pq policy"
    ::= { pqpolicyconfigEntry 6 }

pqPolWeight OBJECT-TYPE
    SYNTAX      Integer32
    MAX-ACCESS  read-only
    STATUS      current
    DESCRIPTION 
        "The weight for the priority"
    ::= { pqpolicyconfigEntry 7 }

dos OBJECT IDENTIFIER
    ::= { nsRoot 12 }

dosstatistics OBJECT IDENTIFIER
    ::= { dos 1 }

dosservicestatsTable OBJECT-TYPE
    SYNTAX      SEQUENCE OF DosservicestatsEntry
    MAX-ACCESS  not-accessible
    STATUS      current
    DESCRIPTION 
        "The table that has statistics for each LB Vip."
    ::= { dosstatistics 1 }

dosservicestatsEntry OBJECT-TYPE
    SYNTAX      DosservicestatsEntry
    MAX-ACCESS  not-accessible
    STATUS      current
    DESCRIPTION 
        "The DOS service statistics per Load Balancing VIP entry."
    INDEX       { dosDevno }
    ::= { dosservicestatsTable 1 }

DosservicestatsEntry ::= SEQUENCE {
    dosDevno               Integer32,
    surgecnt            Counter32,
    dosqdepth           Counter32,
    totaljstransaction  Counter32
}

dosDevno OBJECT-TYPE
    SYNTAX      Integer32
    MAX-ACCESS  read-only
    STATUS      current
    DESCRIPTION 
        "The distinguishing id for the LoadBalancing Vserver"
    ::= { dosservicestatsEntry 1 }

surgecnt OBJECT-TYPE
    SYNTAX      Counter32
    MAX-ACCESS  read-only
    STATUS      current
    DESCRIPTION 
        "The qdepth on this service"
    ::= { dosservicestatsEntry 2 }

dosqdepth OBJECT-TYPE
    SYNTAX      Counter32
    MAX-ACCESS  read-only
    STATUS      current
    DESCRIPTION 
        "The number of genuine clients on this service"
    ::= { dosservicestatsEntry 3 }

totaljstransaction OBJECT-TYPE
    SYNTAX      Counter32
    MAX-ACCESS  read-only
    STATUS      current
    DESCRIPTION 
        "The total number of javascripts sent to genuine clients "
    ::= { dosservicestatsEntry 4 }

dosconfig OBJECT IDENTIFIER
    ::= { dos 2 }

dospolicyconfigTable OBJECT-TYPE
    SYNTAX      SEQUENCE OF DospolicyconfigEntry
    MAX-ACCESS  not-accessible
    STATUS      current
    DESCRIPTION 
        "The table that has statistics for each policy 
         on netscaler."
    ::= { dosconfig 1 }

dospolicyconfigEntry OBJECT-TYPE
    SYNTAX      DospolicyconfigEntry
    MAX-ACCESS  not-accessible
    STATUS      current
    DESCRIPTION 
        "The entry for DOS policy configuration"
    INDEX       { dosPolDevno }
    ::= { dospolicyconfigTable 1 }

DospolicyconfigEntry ::= SEQUENCE {
    dosPolDevno           Integer32,
    dospolicyname   OCTET STRING,
    thresholdvalue  Integer32
}

dosPolDevno OBJECT-TYPE
    SYNTAX      Integer32
    MAX-ACCESS  read-only
    STATUS      current
    DESCRIPTION 
        "The distinguishing id for the configured DOS policies"
    ::= { dospolicyconfigEntry 1 }

dospolicyname OBJECT-TYPE
    SYNTAX      OCTET STRING
    MAX-ACCESS  read-only
    STATUS      current
    DESCRIPTION 
        "The name of the DOS policy"
    ::= { dospolicyconfigEntry 2 }

thresholdvalue OBJECT-TYPE
    SYNTAX      Integer32
    MAX-ACCESS  read-only
    STATUS      current
    DESCRIPTION 
        "The value of qdepth at which DOS protection gets triggered"
    ::= { dospolicyconfigEntry 3 }

ssloffloading OBJECT IDENTIFIER
    ::= { nsRoot 13 }

sslstatistics OBJECT IDENTIFIER
    ::= { ssloffloading 1 }

sslglobalstats OBJECT IDENTIFIER
    ::= { sslstatistics 1 }

currSPS OBJECT-TYPE
    SYNTAX      Counter32
    MAX-ACCESS  read-only
    STATUS      obsolete
    DESCRIPTION 
        "SSL session/second between client and NetScaler"
    ::= { sslglobalstats 1 }

sslV2TxCount OBJECT-TYPE
	SYNTAX Counter32
	MAX-ACCESS read-only
	STATUS obsolete
	DESCRIPTION
		"Total number of SSL v2 Transactions"
	::= { sslglobalstats 2 }

sslV3TxCount OBJECT-TYPE
	SYNTAX Counter32
	MAX-ACCESS read-only
	STATUS obsolete
	DESCRIPTION
		"Total number of SSL v3 Transactions"
	::= { sslglobalstats 3 }

tlsV1TxCount OBJECT-TYPE
	SYNTAX Counter32
	MAX-ACCESS read-only
	STATUS obsolete
	DESCRIPTION
		"Total number of TLS v1 Transactions"
	::= { sslglobalstats 4 }

keyExRSA512 OBJECT-TYPE
	SYNTAX Counter32
	MAX-ACCESS read-only
	STATUS obsolete
	DESCRIPTION
		"Total number of 512 bit RSA key exchange"
	::= { sslglobalstats 5 }
		
keyExRSA1024 OBJECT-TYPE
	SYNTAX Counter32
	MAX-ACCESS read-only
	STATUS obsolete
	DESCRIPTION
		"Total number of 1024 bit RSA key exchange"
	::= { sslglobalstats 6 }

keyExDH512 OBJECT-TYPE
	SYNTAX Counter32
	MAX-ACCESS read-only
	STATUS obsolete
	DESCRIPTION
		"Total number of 512 bit DH key exchange"
	::= { sslglobalstats 7 }

keyExDH1024 OBJECT-TYPE
	SYNTAX Counter32
	MAX-ACCESS read-only
	STATUS obsolete
	DESCRIPTION
		"Total number of 1024 bit DH key exchange"
	::= { sslglobalstats 8 }

authRSA OBJECT-TYPE
	SYNTAX Counter32
	MAX-ACCESS read-only
	STATUS obsolete
	DESCRIPTION
		"Total number of RSA authentication"
	::= { sslglobalstats 9 }
		
authDH OBJECT-TYPE
	SYNTAX Counter32
	MAX-ACCESS read-only
	STATUS obsolete
	DESCRIPTION
		"Total number of DH authentication"
	::= { sslglobalstats 10 }

authDS OBJECT-TYPE
	SYNTAX Counter32
	MAX-ACCESS read-only
	STATUS obsolete
	DESCRIPTION
		"Total number of DS authentication"
	::= { sslglobalstats 11 }

cipher40BitRC4 OBJECT-TYPE
	SYNTAX Counter32
	MAX-ACCESS read-only
	STATUS obsolete
	DESCRIPTION
			"Total number of RC4-40 cipher used"
	::= { sslglobalstats 12 }

cipher56BitRC4 OBJECT-TYPE
	SYNTAX Counter32
	MAX-ACCESS read-only
	STATUS obsolete
	DESCRIPTION
		"Total number of RC4-56 cipher used"
	::= { sslglobalstats 13 }

cipher64BitRC4 OBJECT-TYPE
	SYNTAX Counter32
	MAX-ACCESS read-only
	STATUS obsolete
	DESCRIPTION
		"Total number of RC4-64 cipher used"
	::= { sslglobalstats 14 }

cipher128BitRC4 OBJECT-TYPE
	SYNTAX Counter32
	MAX-ACCESS read-only
	STATUS obsolete
	DESCRIPTION
		"Total number of RC4-128 cipher used"
	::= { sslglobalstats 15 }


cipher40BitDES OBJECT-TYPE
	SYNTAX Counter32
	MAX-ACCESS read-only
	STATUS obsolete
	DESCRIPTION
		"Total number of DES-40 cipher used"
	::= { sslglobalstats 16 }

cipher56BitDES OBJECT-TYPE
	SYNTAX Counter32
	MAX-ACCESS read-only
	STATUS obsolete
	DESCRIPTION
		"Total number of DES-56 cipher used"
	::= { sslglobalstats 17 }


cipher168Bit3DES OBJECT-TYPE
	SYNTAX Counter32
	MAX-ACCESS read-only
	STATUS obsolete
	DESCRIPTION
		"Total number of 3DES-168 cipher used"
	::= { sslglobalstats 18 }


cipher40BitRC2 OBJECT-TYPE
	SYNTAX Counter32
	MAX-ACCESS read-only
	STATUS obsolete
	DESCRIPTION
		"Total number of RC2-40 cipher used"
	::= { sslglobalstats 19 }

cipher56BitRC2 OBJECT-TYPE
	SYNTAX Counter32
	MAX-ACCESS read-only
	STATUS obsolete
	DESCRIPTION
		"Total number of RC2-56 cipher used"
	::= { sslglobalstats 20 }


cipher128BitRC2 OBJECT-TYPE
	SYNTAX Counter32
	MAX-ACCESS read-only
	STATUS obsolete
	DESCRIPTION
		"Total number of RC2-128 cipher used"
	::= { sslglobalstats 21 }

cipher128BitIDEA OBJECT-TYPE
	SYNTAX Counter32
	MAX-ACCESS read-only
	STATUS obsolete
	DESCRIPTION
		"Total number of IDEA-128 cipher used"
	::= { sslglobalstats 22 }

hashMD5 OBJECT-TYPE
	SYNTAX Counter32
	MAX-ACCESS read-only
	STATUS obsolete
	DESCRIPTION
		"Total number of HASH-MD5 hash used"
	::= { sslglobalstats 23 }

hashSHA OBJECT-TYPE
	SYNTAX Counter32
	MAX-ACCESS read-only
	STATUS obsolete
	DESCRIPTION
		"Total number of HASH_SHA hash used"
	::= { sslglobalstats 24 }

sslConfig OBJECT IDENTIFIER
    ::= { ssloffloading 2 }

certKeyTable OBJECT-TYPE
    SYNTAX      SEQUENCE OF CertKeyEntry
    MAX-ACCESS  not-accessible
    STATUS      current
    DESCRIPTION 
        "The table that has all the configuration information for 
         each certificate key pair."
    ::= { sslConfig 1 }

certKeyEntry OBJECT-TYPE
    SYNTAX      CertKeyEntry
    MAX-ACCESS  not-accessible
    STATUS      current
    DESCRIPTION 
        "The certificate key pair information for each entry."
    INDEX       { certKeyId }
    ::= { certKeyTable 1 }

CertKeyEntry ::= SEQUENCE {
    certKeyId       Integer32,
    certKeyName     OCTET STRING,
    certPath        OCTET STRING,
    keyPath         OCTET STRING,
    inputFormat     INTEGER
}

certKeyId OBJECT-TYPE
    SYNTAX      Integer32
    MAX-ACCESS  read-only
    STATUS      current
    DESCRIPTION 
        "The Distinguish ID for each certificate key pair in NetScaler."
    ::= { certKeyEntry 1 }

certKeyName OBJECT-TYPE
    SYNTAX      OCTET STRING
    MAX-ACCESS  read-only
    STATUS      current
    DESCRIPTION 
        "The certificate key pair Name."
    ::= { certKeyEntry 2 }

certPath OBJECT-TYPE
    SYNTAX      OCTET STRING
    MAX-ACCESS  read-only
    STATUS      current
    DESCRIPTION 
        "The certificate path."
    ::= { certKeyEntry 3 }

keyPath OBJECT-TYPE
    SYNTAX      OCTET STRING
    MAX-ACCESS  read-only
    STATUS      current
    DESCRIPTION 
        "The private key path."
    ::= { certKeyEntry 4 }

inputFormat OBJECT-TYPE
    SYNTAX      INTEGER { der(1), pem(3) }
    MAX-ACCESS  read-only
    STATUS      current
    DESCRIPTION 
        "The input format of the certificate key pair."
    ::= { certKeyEntry 5 }

crlTable OBJECT-TYPE
    SYNTAX      SEQUENCE OF CrlEntry
    MAX-ACCESS  not-accessible
    STATUS      current
    DESCRIPTION 
        "The table that has all the configuration 
         information for each CRL in NetScaler."
    ::= { sslConfig 2 }

crlEntry OBJECT-TYPE
    SYNTAX      CrlEntry
    MAX-ACCESS  not-accessible
    STATUS      current
    DESCRIPTION 
        "The CRL information for each entry."
    INDEX       { crlId }
    ::= { crlTable 1 }

CrlEntry ::= SEQUENCE {
	crlId	Integer32,
	crlName	OCTET STRING,
	crlPath	OCTET STRING,
    crlInputFormat     INTEGER
}
  
crlId  OBJECT-TYPE
	SYNTAX Integer32
    MAX-ACCESS  read-only
	STATUS current
	DESCRIPTION		
		"The Distinguish ID for each CRL in NetScaler."
	::= { crlEntry 1 }


crlName OBJECT-TYPE
  	SYNTAX OCTET STRING
	MAX-ACCESS read-only
	STATUS current
	DESCRIPTION	
		"The name of CRL."
	::= { crlEntry 2 }


crlPath OBJECT-TYPE
  	SYNTAX OCTET STRING
	MAX-ACCESS read-only
	STATUS current
	DESCRIPTION	
		"The CRL path."
	::= { crlEntry 3 }

  
crlInputFormat OBJECT-TYPE
    SYNTAX      INTEGER { der(1), pem(3) }
    MAX-ACCESS  read-only
    STATUS      current
    DESCRIPTION 
        "The input format of CRL."
    ::= { crlEntry 4 }
                
cipherGroupTable OBJECT-TYPE
    SYNTAX      SEQUENCE OF CipherGroupEntry
    MAX-ACCESS  not-accessible
    STATUS      current
    DESCRIPTION 
        "The table that has all the configuration information
         for each cipher group in NetScaler."
    ::= { sslConfig 3 }

cipherGroupEntry OBJECT-TYPE
    SYNTAX      CipherGroupEntry
    MAX-ACCESS  not-accessible
    STATUS      current
    DESCRIPTION 
        "The Cipher group information for each entry."
    INDEX       { cipherGroupId, cipherId }
    ::= { cipherGroupTable 1 }

CipherGroupEntry ::= SEQUENCE {
    cipherGroupId       Integer32,
    cipherId            Integer32,
    cipherGroupName     OCTET STRING,
    cipherName          OCTET STRING,
    cipherDesc          OCTET STRING
}

cipherGroupId OBJECT-TYPE
    SYNTAX      Integer32
    MAX-ACCESS  read-only
    STATUS      current
    DESCRIPTION 
        "The Distinguish ID for each Cipher group in NetScaler."
    ::= { cipherGroupEntry 1 }

cipherId OBJECT-TYPE
    SYNTAX      Integer32
    MAX-ACCESS  read-only
    STATUS      current
    DESCRIPTION 
        "The Distinguish ID for each Cipher in NetScaler."
    ::= { cipherGroupEntry 2 }

cipherGroupName OBJECT-TYPE
    SYNTAX      OCTET STRING
    MAX-ACCESS  read-only
    STATUS      current
    DESCRIPTION 
        "The Cipher group name."
    ::= { cipherGroupEntry 3 }

cipherName OBJECT-TYPE
    SYNTAX      OCTET STRING
    MAX-ACCESS  read-only
    STATUS      current
    DESCRIPTION 
        "The Cipher name."
    ::= { cipherGroupEntry 4 }

cipherDesc OBJECT-TYPE
    SYNTAX      OCTET STRING
    MAX-ACCESS  read-only
    STATUS      current
    DESCRIPTION 
        "The Cipher description."
    ::= { cipherGroupEntry 5 }

advanceSSLConfigTable OBJECT-TYPE
    SYNTAX      SEQUENCE OF AdvanceSSLConfigEntry
    MAX-ACCESS  not-accessible
    STATUS      current
    DESCRIPTION 
        "The table that has all the advance SSL configuration
         information for each  virtual/physical service in NetScaler."
    ::= { sslConfig 4 }

advanceSSLConfigEntry OBJECT-TYPE
    SYNTAX      AdvanceSSLConfigEntry
    MAX-ACCESS  not-accessible
    STATUS      current
    DESCRIPTION 
        "The advance SSL configuration for each entry."
    INDEX       { sslConfigId }
    ::= { advanceSSLConfigTable 1 }

AdvanceSSLConfigEntry ::= SEQUENCE {
	sslConfigId	Integer32,
	serviceName	OCTET STRING,
	dh	INTEGER,
	dhCount	Integer32,
	dhFile	OCTET STRING,
    eRSA            INTEGER,
    eRSACount       Integer32,
    certHeader      INTEGER,
    certHeaderTag   OCTET STRING,
    sessHeader      INTEGER,
    sessHeaderTag   OCTET STRING,
    sslv2           INTEGER,
    sslv3           INTEGER,
    tlsv1           INTEGER,
    owaSupport      INTEGER,
    sslRedirect     INTEGER,
    clearTextPort   Integer32,
    serviceType     INTEGER
}
 
sslConfigId	OBJECT-TYPE
	SYNTAX Integer32
	MAX-ACCESS  read-only
	STATUS current   
	DESCRIPTION	
		"The Distinguish ID for each SSL virtual/physical service in NetScaler."
	::= { advanceSSLConfigEntry 1 }

serviceName	OBJECT-TYPE
  	SYNTAX OCTET STRING
	MAX-ACCESS read-only
	STATUS current
	DESCRIPTION	
		"The service name."
	::= { advanceSSLConfigEntry 2 }

dh OBJECT-TYPE
	SYNTAX INTEGER {disabled(1),enabled(2)}
	MAX-ACCESS  read-only
	STATUS current
	DESCRIPTION	
		"Whether DH is enabled/disabled."
	::= { advanceSSLConfigEntry 3 }

dhCount OBJECT-TYPE
	SYNTAX Integer32
	MAX-ACCESS read-only
	STATUS current
	DESCRIPTION	
		"The DH refresh count to re-generate public/private key."
	::= { advanceSSLConfigEntry 4 }

dhFile OBJECT-TYPE
  	SYNTAX OCTET STRING
	MAX-ACCESS read-only
	STATUS current
	DESCRIPTION	
		"The DH file path name."
	::= { advanceSSLConfigEntry 5 }

eRSA OBJECT-TYPE
    SYNTAX      INTEGER { disabled(1), enabled(2) }
    MAX-ACCESS  read-only
    STATUS      current
    DESCRIPTION 
        "The ephimeral RSA support for service."
    ::= { advanceSSLConfigEntry 6 }

eRSACount OBJECT-TYPE
    SYNTAX      Integer32
    MAX-ACCESS  read-only
    STATUS      current
    DESCRIPTION 
        "The eRSA refresh count to re-generate RSA temporary key."
    ::= { advanceSSLConfigEntry 7 }

certHeader OBJECT-TYPE
    SYNTAX      INTEGER { disabled(1), enabled(2) }
    MAX-ACCESS  read-only
    STATUS      current
    DESCRIPTION 
        "The certificate insertion in HTTP request."
    ::= { advanceSSLConfigEntry 8 }

certHeaderTag OBJECT-TYPE
    SYNTAX      OCTET STRING
    MAX-ACCESS  read-only
    STATUS      current
    DESCRIPTION 
        "The certificate tag name in HTTP request."
    ::= { advanceSSLConfigEntry 9 }

sessHeader OBJECT-TYPE
    SYNTAX      INTEGER { disabled(1), enabled(2) }
    MAX-ACCESS  read-only
    STATUS      current
    DESCRIPTION 
        "The session id insertion in HTTP request."
    ::= { advanceSSLConfigEntry 10 }

sessHeaderTag OBJECT-TYPE
    SYNTAX      OCTET STRING
    MAX-ACCESS  read-only
    STATUS      current
    DESCRIPTION 
        "The session id tag name in HTTP request."
    ::= { advanceSSLConfigEntry 11 }

sslv2 OBJECT-TYPE
    SYNTAX      INTEGER { disabled(1), enabled(2) }
    MAX-ACCESS  read-only
    STATUS      current
    DESCRIPTION 
        "The support for SSLv2 protocol for service."
    ::= { advanceSSLConfigEntry 12 }

sslv3 OBJECT-TYPE
    SYNTAX      INTEGER { disabled(1), enabled(2) }
    MAX-ACCESS  read-only
    STATUS      current
    DESCRIPTION 
        "The support for SSLv3 protocol for service."
    ::= { advanceSSLConfigEntry 13 }

tlsv1 OBJECT-TYPE
    SYNTAX      INTEGER { disabled(1), enabled(2) }
    MAX-ACCESS  read-only
    STATUS      current
    DESCRIPTION 
        "The support for TLSv1 protocol for service."
    ::= { advanceSSLConfigEntry 14 }

owaSupport OBJECT-TYPE
    SYNTAX      INTEGER { disabled(1), enabled(2) }
    MAX-ACCESS  read-only
    STATUS      current
    DESCRIPTION 
        "The support for outlook web access for service."
    ::= { advanceSSLConfigEntry 15 }

sslRedirect OBJECT-TYPE
    SYNTAX      INTEGER { disabled(1), enabled(2) }
    MAX-ACCESS  read-only
    STATUS      current
    DESCRIPTION 
        "The support for ssl redirect for service."
    ::= { advanceSSLConfigEntry 16 }

clearTextPort OBJECT-TYPE
    SYNTAX      Integer32
    MAX-ACCESS  read-only
    STATUS      current
    DESCRIPTION 
        "The clear text port on the backend webserver."
    ::= { advanceSSLConfigEntry 17 }

serviceType OBJECT-TYPE
    SYNTAX      INTEGER { virtualserver(0), physicalservice(1) }
    MAX-ACCESS  read-only
    STATUS      current
    DESCRIPTION 
        "The type of the service virtual/ real."
    ::= { advanceSSLConfigEntry 18 }

certBindingConfigTable OBJECT-TYPE
    SYNTAX      SEQUENCE OF CertBindingConfigEntry
    MAX-ACCESS  not-accessible
    STATUS      current
    DESCRIPTION 
        "The table that has all the certificate configuration 
         for each  service in NetScaler."
    ::= { sslConfig 5 }

certBindingConfigEntry OBJECT-TYPE
    SYNTAX      CertBindingConfigEntry
    MAX-ACCESS  not-accessible
    STATUS      current
    DESCRIPTION 
        "The certificate bindings for each entry."
    INDEX       { certBindId, certKeyID, certType }
    ::= { certBindingConfigTable 1 }

CertBindingConfigEntry ::= SEQUENCE {
	certBindId				Integer32,
    certKeyID       Integer32,
    certType		INTEGER,
    certBindServiceName		OCTET STRING,
    certBindKeyName     OCTET STRING,
    certBindServiceType     INTEGER
}

certBindId	OBJECT-TYPE
	SYNTAX Integer32
	MAX-ACCESS read-only
	STATUS current
	DESCRIPTION	
		"The Distinguish ID for each SSL virtual/real service in NetScaler."
	::= { certBindingConfigEntry 1 }

certKeyID OBJECT-TYPE
    SYNTAX      Integer32
    MAX-ACCESS  read-only
    STATUS      current
    DESCRIPTION 
        "The Distinguish ID for each certificate key pair in NetScaler."
    ::= { certBindingConfigEntry 2 }
 
certType OBJECT-TYPE
	SYNTAX INTEGER { serverCertificate(1), caCertificate (2) }
	MAX-ACCESS  read-only
	STATUS current
	DESCRIPTION	
		"Whether certificate key pair is CA or not."
	::= { certBindingConfigEntry 3 }

certBindServiceName     OBJECT-TYPE
	SYNTAX OCTET STRING	
    MAX-ACCESS  read-only
	STATUS current
	DESCRIPTION	
		"The service name."
	::= { certBindingConfigEntry 4 }

certBindKeyName OBJECT-TYPE
    SYNTAX      OCTET STRING
    MAX-ACCESS  read-only
    STATUS      current
    DESCRIPTION 
        "The certificate key pair name."
    ::= { certBindingConfigEntry 5 }

certBindServiceType OBJECT-TYPE
    SYNTAX      INTEGER { virtualserver(0), physicalservice(1) }
    MAX-ACCESS  read-only
    STATUS      current
    DESCRIPTION 
        "The type of the service virtual/ real."
    ::= { certBindingConfigEntry 6 }

cipherBindingConfigTable OBJECT-TYPE
    SYNTAX      SEQUENCE OF CipherBindingConfigEntry
    MAX-ACCESS  not-accessible
    STATUS      current
    DESCRIPTION 
        "The table that has all the cipher configuration for
         each  service in NetScaler."
    ::= { sslConfig 6 }

cipherBindingConfigEntry OBJECT-TYPE
    SYNTAX      CipherBindingConfigEntry
    MAX-ACCESS  not-accessible
    STATUS      current
    DESCRIPTION 
        "The cipher bindings for each entry."
    INDEX       { cipherBindId, cipherID }
    ::= { cipherBindingConfigTable 1 }

CipherBindingConfigEntry ::= SEQUENCE {
    cipherBindId              Integer32,
    cipherID        Integer32,
    cipherBindServiceName		OCTET STRING,
    cipherbName      OCTET STRING,
    cipherbDesc      OCTET STRING,
    cipherBindServiceType     INTEGER
}

cipherBindId OBJECT-TYPE
    SYNTAX      Integer32
    MAX-ACCESS  read-only
    STATUS      current
    DESCRIPTION 
        "The distinguishing ID for each SSL virtual/real service in NetScaler."
    ::= { cipherBindingConfigEntry 1 }

cipherID OBJECT-TYPE
    SYNTAX      Integer32
    MAX-ACCESS  read-only
    STATUS      current
    DESCRIPTION 
        "The distinguishing ID for each cipher in NetScaler."
    ::= { cipherBindingConfigEntry 2 }

cipherBindServiceName	OBJECT-TYPE
	SYNTAX OCTET STRING	
	MAX-ACCESS read-only
	STATUS current
	DESCRIPTION	
		"The name of the physical or virtual service."
	::= { cipherBindingConfigEntry 3 }

cipherbName OBJECT-TYPE
    SYNTAX      OCTET STRING
    MAX-ACCESS  read-only
    STATUS      current
    DESCRIPTION 
        "The cipher name."
    ::= { cipherBindingConfigEntry 4 }

cipherbDesc OBJECT-TYPE
    SYNTAX      OCTET STRING
    MAX-ACCESS  read-only
    STATUS      current
    DESCRIPTION 
        "The cipher description."
    ::= { cipherBindingConfigEntry 5 }

cipherBindServiceType OBJECT-TYPE
    SYNTAX      INTEGER { virtualserver(0), physicalservice(1) }
    MAX-ACCESS  read-only
    STATUS      current
    DESCRIPTION 
        "The type of the service virtual/ real."
    ::= { cipherBindingConfigEntry 6 }

cpe OBJECT IDENTIFIER
    ::= { nsRoot 14 }

cpestatistics OBJECT IDENTIFIER
    ::= { cpe 1 }

cpestatspolicyTable OBJECT-TYPE
    SYNTAX      SEQUENCE OF CpestatspolicyEntry
    MAX-ACCESS  not-accessible
    STATUS      obsolete
    DESCRIPTION 
        "The table that has all the policy stats for
         each  virtual service in NetScaler."
    ::= { cpestatistics 1 }

cpestatspolicyEntry OBJECT-TYPE
    SYNTAX      CpestatspolicyEntry
    MAX-ACCESS  not-accessible
    STATUS      obsolete
    DESCRIPTION 
        "The policy items for each entry."
    INDEX       { cpesDevno }
    ::= { cpestatspolicyTable 1 }

CpestatspolicyEntry ::= SEQUENCE {
    cpesDevno       Integer32,
    cpesPolicyname  OCTET STRING,
    cpesPolicyhits  Counter32
}

cpesDevno OBJECT-TYPE
    SYNTAX      Integer32
    MAX-ACCESS  read-only
    STATUS      obsolete
    DESCRIPTION 
        " The unique identifier for the policy"
    ::= { cpestatspolicyEntry 1 }

cpesPolicyname OBJECT-TYPE
    SYNTAX      OCTET STRING
    MAX-ACCESS  read-only
    STATUS      obsolete
    DESCRIPTION 
        " The name of the policy "
    ::= { cpestatspolicyEntry 2 }

cpesPolicyhits OBJECT-TYPE
    SYNTAX      Counter32
    MAX-ACCESS  read-only
    STATUS      obsolete
    DESCRIPTION 
        "Number of times that the policy condition has been met by NetScaler"
    ::= { cpestatspolicyEntry 3 }

cpestatsactionTable OBJECT-TYPE
    SYNTAX      SEQUENCE OF CpestatsactionEntry
    MAX-ACCESS  not-accessible
    STATUS      obsolete
    DESCRIPTION 
        "The table that has all the action stats for
         each  virtual service in NetScaler."
    ::= { cpestatistics 2 }

cpestatsactionEntry OBJECT-TYPE
    SYNTAX      CpestatsactionEntry
    MAX-ACCESS  not-accessible
    STATUS      obsolete
    DESCRIPTION 
        "The action items for each entry."
    INDEX       { cpeaDevno }
    ::= { cpestatsactionTable 1 }

CpestatsactionEntry ::= SEQUENCE {
    cpeaDevno       Integer32,
    actionname  OCTET STRING,
    actionhits  Counter32
}

cpeaDevno OBJECT-TYPE
    SYNTAX      Integer32
    MAX-ACCESS  read-only
    STATUS      obsolete
    DESCRIPTION 
        " The unique identifier for the action"
    ::= { cpestatsactionEntry 1 }

actionname OBJECT-TYPE
    SYNTAX      OCTET STRING
    MAX-ACCESS  read-only
    STATUS      obsolete
    DESCRIPTION 
        " The name of the action "
    ::= { cpestatsactionEntry 2 }

actionhits OBJECT-TYPE
    SYNTAX      Counter32
    MAX-ACCESS  read-only
    STATUS      obsolete
    DESCRIPTION 
        "Number of times that the action has been made by NetScaler"
    ::= { cpestatsactionEntry 3 }

cpeconfig OBJECT IDENTIFIER
    ::= { cpe 2 }

cpeconfigpolicyTable OBJECT-TYPE
    SYNTAX      SEQUENCE OF CpeconfigpolicyEntry
    MAX-ACCESS  not-accessible
    STATUS      obsolete
    DESCRIPTION 
        "The table that has all the policy stats for
         each  virtual service in NetScaler."
    ::= { cpeconfig 1 }

cpeconfigpolicyEntry OBJECT-TYPE
    SYNTAX      CpeconfigpolicyEntry
    MAX-ACCESS  not-accessible
    STATUS      obsolete
    DESCRIPTION 
        "The policy items for each entry."
    INDEX       { cpecDevno }
    ::= { cpeconfigpolicyTable 1 }

CpeconfigpolicyEntry ::= SEQUENCE {
    cpecDevno       Integer32,
    cpecPolicyname  OCTET STRING,
    reqrule     OCTET STRING,
    reqaction   OCTET STRING
}

cpecDevno OBJECT-TYPE
    SYNTAX      Integer32
    MAX-ACCESS  read-only
    STATUS      obsolete
    DESCRIPTION 
        " The unique identifier for the policy"
    ::= { cpeconfigpolicyEntry 1 }

cpecPolicyname OBJECT-TYPE
    SYNTAX      OCTET STRING
    MAX-ACCESS  read-only
    STATUS      obsolete
    DESCRIPTION 
        " The name of the policy "
    ::= { cpeconfigpolicyEntry 2 }

reqrule OBJECT-TYPE
    SYNTAX      OCTET STRING
    MAX-ACCESS  read-only
    STATUS      obsolete
    DESCRIPTION 
        "user defined request rule for the policy from client to NetScaler"
    ::= { cpeconfigpolicyEntry 3 }

reqaction OBJECT-TYPE
    SYNTAX      OCTET STRING
    MAX-ACCESS  read-only
    STATUS      obsolete
    DESCRIPTION 
        "user defined request action for the policy from client to NetScaler"
    ::= { cpeconfigpolicyEntry 4 }

cpeconfigactionTable OBJECT-TYPE
    SYNTAX      SEQUENCE OF CpeconfigactionEntry
    MAX-ACCESS  not-accessible
    STATUS      obsolete
    DESCRIPTION 
        "The table that has all the action configurations for
         each  virtual service in NetScaler."
    ::= { cpeconfig 2 }

cpeconfigactionEntry OBJECT-TYPE
    SYNTAX      CpeconfigactionEntry
    MAX-ACCESS  not-accessible
    STATUS      obsolete
    DESCRIPTION 
        "The action items for each entry."
    INDEX       { cpecaDevno }
    ::= { cpeconfigactionTable 1 }

CpeconfigactionEntry ::= SEQUENCE {
    cpecaDevno       Integer32,
    cpecaActionname  OCTET STRING,
    directive   INTEGER,
    qualifier   INTEGER,
    value       OCTET STRING,
    page        OCTET STRING,
    server      OCTET STRING
}

cpecaDevno OBJECT-TYPE
    SYNTAX      Integer32
    MAX-ACCESS  read-only
    STATUS      obsolete
    DESCRIPTION 
        " The unique identifier for the action"
    ::= { cpeconfigactionEntry 1 }

cpecaActionname OBJECT-TYPE
    SYNTAX      OCTET STRING
    MAX-ACCESS  read-only
    STATUS      obsolete
    DESCRIPTION 
        " The name of the action "
    ::= { cpeconfigactionEntry 2 }

directive OBJECT-TYPE
    SYNTAX      INTEGER { unknown(0), reset(1), drop(2), httpec(3), 
                    cmp(4), add(5), mod(6), del(7), cor(8), forward(9), 
                    noComparison(10), last(11) }
    MAX-ACCESS  read-only
    STATUS      obsolete
    DESCRIPTION 
        " The name of the directive associated with this action "
    ::= { cpeconfigactionEntry 3 }

qualifier OBJECT-TYPE
    SYNTAX      INTEGER { unknown(0), http(1), header(2), query(3) }
    MAX-ACCESS  read-only
    STATUS      obsolete
    DESCRIPTION 
        " The name of the qualifier associated with this action "
    ::= { cpeconfigactionEntry 4 }

value OBJECT-TYPE
    SYNTAX      OCTET STRING
    MAX-ACCESS  read-only
    STATUS      obsolete
    DESCRIPTION 
        " The value associated with this action . The value depends on 
         the directive . If the directive is RESPONSE , then the 
         value returned is status. Similarly , if the directive is
         either ADD or MOD or DEL , then the value returned is header.
         If the directive is RST or CMP, then NULL is returned"
    ::= { cpeconfigactionEntry 5 }

page OBJECT-TYPE
    SYNTAX      OCTET STRING
    MAX-ACCESS  read-only
    STATUS      obsolete
    DESCRIPTION 
        " The value of this depends on the value of directive. If value of
         directive is  RESPONSE  , then the page is returned, and if directive
         is MOD , then the header is returned , 
         otherwise NULL is returned"
    ::= { cpeconfigactionEntry 6 }

server OBJECT-TYPE
    SYNTAX      OCTET STRING
    MAX-ACCESS  read-only
    STATUS      obsolete
    DESCRIPTION 
        " The server name associated with this action based on the directive.
         If the directive is FORWARD , then the server returns the name of the
          service , otherwise returns empty string"
    ::= { cpeconfigactionEntry 7 }

cpeExprConfigStatsTable OBJECT-TYPE
    SYNTAX      SEQUENCE OF CpeExprConfigStatsEntry
    MAX-ACCESS  not-accessible
    STATUS      current
    DESCRIPTION 
        "This table contains configuration information for each of 
         the expressions on the Netscaler   "
    ::= { cpe 3 }

cpeExprConfigStatsEntry OBJECT-TYPE
    SYNTAX      CpeExprConfigStatsEntry
    MAX-ACCESS  not-accessible
    STATUS      current
    DESCRIPTION 
        "This table contains configuration information for each of 
         the expressions on the Netscaler   "
    INDEX       { cpeeIndex }
    ::= { cpeExprConfigStatsTable 1 }

CpeExprConfigStatsEntry ::= SEQUENCE {
    cpeeIndex       Integer32,
    exprName    OCTET STRING,
    cpeeQualifier   INTEGER,
    operator    INTEGER,
    hdrName     OCTET STRING,
    cpeeValue       OCTET STRING,
    length      Integer32,
    offset      Integer32,
    cpeeNetmask     Integer32
}

cpeeIndex OBJECT-TYPE
    SYNTAX      Integer32
    MAX-ACCESS  read-only
    STATUS      current
    DESCRIPTION 
        "The distinguishing Id for expression."
    ::= { cpeExprConfigStatsEntry 1 }

exprName OBJECT-TYPE
    SYNTAX      OCTET STRING
    MAX-ACCESS  read-only
    STATUS      current
    DESCRIPTION 
        "The name of the expression."
    ::= { cpeExprConfigStatsEntry 2 }

cpeeQualifier OBJECT-TYPE
    SYNTAX      INTEGER { unknownQualifier(-1), method(0), 
                    urlPrefix(1), urlSuffix(2), urlTokens(3), 
                    version(4), header(5), urlQuery(6), url(7), 
                    urllen(8), urlquerylen(9), domain(10), sourceIp(11), 
                    sourcePort(12), destinationIp(13), 
                    destinationPort(14), compoundExpression(15), 
                    evaluatePredefined(16) }
    MAX-ACCESS  read-only
    STATUS      obsolete
    DESCRIPTION 
        "The qualifier of the expression."
    ::= { cpeExprConfigStatsEntry 3 }

operator OBJECT-TYPE
    SYNTAX      INTEGER { and(0), or(1), not(2), equal(3), notEqual(4), 
                    greaterThan(5), lessThan(6), 
                    greaterThanOrEqualTo(7), 
                    lessThanOrEqualTo(8), exists(9), notExists(10), 
                    contains(11), notContains(12), contents(13) }
    MAX-ACCESS  read-only
    STATUS      obsolete
    DESCRIPTION 
        "The operator in the expression."
    ::= { cpeExprConfigStatsEntry 4 }

hdrName OBJECT-TYPE
    SYNTAX      OCTET STRING
    MAX-ACCESS  read-only
    STATUS      obsolete
    DESCRIPTION 
        "The http header in the expression when the 
         value of qualifier is HEADER , otherwise empty string"
    ::= { cpeExprConfigStatsEntry 5 }

cpeeValue OBJECT-TYPE
    SYNTAX      OCTET STRING
    MAX-ACCESS  read-only
    STATUS      current
    DESCRIPTION 
        "The value of the expression."
    ::= { cpeExprConfigStatsEntry 6 }

length OBJECT-TYPE
    SYNTAX      Integer32
    MAX-ACCESS  read-only
    STATUS      obsolete
    DESCRIPTION 
        "The length , which is an optional value , used in 
         the expression . This has value only when the qualifier is
         CONTAINS or CONTENTS"
    ::= { cpeExprConfigStatsEntry 7 }

offset OBJECT-TYPE
    SYNTAX      Integer32
    MAX-ACCESS  read-only
    STATUS      obsolete
    DESCRIPTION 
        "The offset , which is an optional value , used in 
         the expression . This has value only when the qualifier is
         CONTAINS or CONTENTS"
    ::= { cpeExprConfigStatsEntry 8 }

cpeeNetmask OBJECT-TYPE
    SYNTAX      Integer32
    MAX-ACCESS  read-only
    STATUS      obsolete
    DESCRIPTION 
        "The netmask , which is an optional value , used in 
         the expression . This has value only when the qualifier is
         SOURCEIP"
    ::= { cpeExprConfigStatsEntry 9 }

nsProducts OBJECT IDENTIFIER
    ::= { netScaler 4 }

rs9000 OBJECT IDENTIFIER
    ::= { nsProducts 1 }

nsSysGroup OBJECT IDENTIFIER
    ::= { rs9000 1 }

sysBuildVersion OBJECT-TYPE
    SYNTAX      OCTET STRING
    MAX-ACCESS  read-only
    STATUS      current
    DESCRIPTION 
        "This shows the version of the kernel build running on
         the netscaler "
    ::= { nsSysGroup 1 }

sysIpAddress OBJECT-TYPE
    SYNTAX      IpAddress
    MAX-ACCESS  read-only
    STATUS      current
    DESCRIPTION 
        "This shows the configured ipaddress of the NetScaler "
    ::= { nsSysGroup 2 }

sysNetmask OBJECT-TYPE
    SYNTAX      IpAddress
    MAX-ACCESS  read-only
    STATUS      current
    DESCRIPTION 
        "This shows the configured netmask of the NetScaler"
    ::= { nsSysGroup 3 }

sysMappedIpAddress OBJECT-TYPE
    SYNTAX      IpAddress
    MAX-ACCESS  read-only
    STATUS      obsolete
    DESCRIPTION 
        "This shows the configured mapped ipaddress on
         NetScaler "
    ::= { nsSysGroup 4 }

sysMappedIpAddressRange OBJECT-TYPE
    SYNTAX      Integer32
    MAX-ACCESS  read-only
    STATUS      obsolete
    DESCRIPTION 
        "This represents the configured NetScaler's ipaddress "
    ::= { nsSysGroup 5 }

sysHighAvailabilityMode OBJECT-TYPE
    SYNTAX      HAMode
    MAX-ACCESS  read-only
    STATUS      current
    DESCRIPTION 
        "This shows whether NetScaler is in standalone mode
         or whether it is primary or secondary in case of
         failover  mode "
    ::= { nsSysGroup 6 }

sysGateway OBJECT-TYPE
    SYNTAX      IpAddress
    MAX-ACCESS  read-only
    STATUS      current
    DESCRIPTION 
        "This represents the default gateway configured on
         the NetScaler"
    ::= { nsSysGroup 7 }

sysCurMappedIpCount OBJECT-TYPE
    SYNTAX	Gauge32
    MAX-ACCESS	read-only
    STATUS	current
    DESCRIPTION
    	"This represents the number of Mapped IPs currently configured on the NetScaler system"
    ::= { nsSysGroup 8 }

nsFeatureInfo OBJECT IDENTIFIER
    ::= { nsSysGroup 20 }

featureWebLogging OBJECT-TYPE
    SYNTAX      FeatureStatus
    MAX-ACCESS  read-only
    STATUS      current
    DESCRIPTION 
        "This represents whether webLogging feature is enabled
         or disabled on NetScaler."
    ::= { nsFeatureInfo 1 }

featureSurgeProtection OBJECT-TYPE
    SYNTAX      FeatureStatus
    MAX-ACCESS  read-only
    STATUS      current
    DESCRIPTION 
        "This represents whether surgeProtection feature is
         enabled or disabled on NetScaler."
    ::= { nsFeatureInfo 2 }

featureLoadBalancing OBJECT-TYPE
    SYNTAX      FeatureStatus
    MAX-ACCESS  read-only
    STATUS      current
    DESCRIPTION 
        "This represents whether loadBalancing feature is
         enabled or disabled on NetScaler."
    ::= { nsFeatureInfo 3 }

featureContentSwitching OBJECT-TYPE
    SYNTAX      FeatureStatus
    MAX-ACCESS  read-only
    STATUS      current
    DESCRIPTION 
        "This represents whether contentSwitching feature is
         enabled or disabled on NetScaler."
    ::= { nsFeatureInfo 4 }

featureCacheRedirection OBJECT-TYPE
    SYNTAX      FeatureStatus
    MAX-ACCESS  read-only
    STATUS      current
    DESCRIPTION 
        "This represents whether cacheRedirection feature is
         enabled or disabled on NetScaler."
    ::= { nsFeatureInfo 5 }

featureSureConnect OBJECT-TYPE
    SYNTAX      FeatureStatus
    MAX-ACCESS  read-only
    STATUS      current
    DESCRIPTION 
        "This represents whether sureConnect feature is
         enabled or disabled on NetScaler."
    ::= { nsFeatureInfo 6 }

featureCompression OBJECT-TYPE
    SYNTAX      FeatureStatus
    MAX-ACCESS  read-only
    STATUS      current
    DESCRIPTION 
        "This represents whether compressionControl feature is
         enabled or disabled on NetScaler."
    ::= { nsFeatureInfo 7 }

featurePriorityQueuing OBJECT-TYPE
    SYNTAX      FeatureStatus
    MAX-ACCESS  read-only
    STATUS      current
    DESCRIPTION 
        "This represents whether priorityQueuing feature is
         enabled or disabled on NetScaler."
    ::= { nsFeatureInfo 8 }

featureSslOffloading OBJECT-TYPE
    SYNTAX      FeatureStatus
    MAX-ACCESS  read-only
    STATUS      current
    DESCRIPTION 
        "This represents whether sslOffloading feature is
         enabled or disabled on NetScaler."
    ::= { nsFeatureInfo 9 }

featureGslb OBJECT-TYPE
    SYNTAX      FeatureStatus
    MAX-ACCESS  read-only
    STATUS      current
    DESCRIPTION 
        "This represents whether gslb feature is
         enabled or disabled on NetScaler."
    ::= { nsFeatureInfo 10 }

featureHttpDosProtection OBJECT-TYPE
    SYNTAX      FeatureStatus
    MAX-ACCESS  read-only
    STATUS      current
    DESCRIPTION 
        "This represents whether httpDosProtection feature is
         enabled or disabled on NetScaler."
    ::= { nsFeatureInfo 11 }

featureDynamicRouting OBJECT-TYPE
    SYNTAX      FeatureStatus
    MAX-ACCESS  read-only
    STATUS      current
    DESCRIPTION 
        "This represents whether Dynamic Routing feature is
         enabled or disabled on NetScaler."
    ::= { nsFeatureInfo 12 }

featureContentFiltering OBJECT-TYPE
    SYNTAX      FeatureStatus
    MAX-ACCESS  read-only
    STATUS      current
    DESCRIPTION 
        "This represents whether ContentFiltering feature is
         enabled or disabled on NetScaler."
    ::= { nsFeatureInfo 13 }

featureInternalCaching OBJECT-TYPE
    SYNTAX      FeatureStatus
    MAX-ACCESS  read-only
    STATUS      current
    DESCRIPTION 
        "This represents whether InternalCaching feature is
         enabled or disabled on NetScaler."
    ::= { nsFeatureInfo 14 }

featureSSLVPN OBJECT-TYPE
    SYNTAX      FeatureStatus
    MAX-ACCESS  read-only
    STATUS      current
    DESCRIPTION 
        "This represents whether SSL VPN feature is
         enabled or disabled on NetScaler."
    ::= { nsFeatureInfo 15 }

featureOSPF OBJECT-TYPE
    SYNTAX      FeatureStatus
    MAX-ACCESS  read-only
    STATUS      current
    DESCRIPTION 
        "This represents whether OSPF  feature is
         enabled or disabled on NetScaler."
    ::= { nsFeatureInfo 16 }

featureRIP OBJECT-TYPE
    SYNTAX      FeatureStatus
    MAX-ACCESS  read-only
    STATUS      current
    DESCRIPTION 
        "This represents whether RIP feature is
         enabled or disabled on NetScaler."
    ::= { nsFeatureInfo 17 }

nsModeInfo OBJECT IDENTIFIER
    ::= { nsSysGroup 21 }

modeFastRamp OBJECT-TYPE
    SYNTAX      ModeStatus
    MAX-ACCESS  read-only
    STATUS      current
    DESCRIPTION 
        "This represents whether fastRamp feature is
         enabled or disabled on NetScaler."
    ::= { nsModeInfo 1 }

l2Mode OBJECT-TYPE
    SYNTAX      ModeStatus
    MAX-ACCESS  read-only
    STATUS      current
    DESCRIPTION 
        "This represents whether l2Mode feature is
         enabled or disabled on NetScaler."
    ::= { nsModeInfo 2 }

modeUseSrcIp OBJECT-TYPE
    SYNTAX      ModeStatus
    MAX-ACCESS  read-only
    STATUS      current
    DESCRIPTION 
        "This represents whether useSrcIp feature is
         enabled or disabled on NetScaler."
    ::= { nsModeInfo 3 }

modeClientKeepAlive OBJECT-TYPE
    SYNTAX      ModeStatus
    MAX-ACCESS  read-only
    STATUS      current
    DESCRIPTION 
        "This represents whether clientKeepAlive feature is
         enabled or disabled on NetScaler."
    ::= { nsModeInfo 4 }

modeTcpBuffering OBJECT-TYPE
    SYNTAX      ModeStatus
    MAX-ACCESS  read-only
    STATUS      current
    DESCRIPTION 
        "This represents whether tcpBuffering feature is
         enabled or disabled on NetScaler."
    ::= { nsModeInfo 5 }

modeMacBasedForwarding OBJECT-TYPE
    SYNTAX      ModeStatus
    MAX-ACCESS  read-only
    STATUS      current
    DESCRIPTION 
        "This represents whether macBasedForwarding feature is
         enabled or disabled on NetScaler."
    ::= { nsModeInfo 6 }

modeUseSubnetIp OBJECT-TYPE
    SYNTAX      ModeStatus
    MAX-ACCESS  read-only
    STATUS      current
    DESCRIPTION 
        "This represents whether Use Subnet IP feature is
         enabled or disabled on NetScaler."
    ::= { nsModeInfo 7 }

modeEdgeConfiguration OBJECT-TYPE
    SYNTAX      ModeStatus
    MAX-ACCESS  read-only
    STATUS      current
    DESCRIPTION 
        "This represents whether Edge Configuration feature is
         enabled or disabled on NetScaler."
    ::= { nsModeInfo 8 }

l3mode OBJECT-TYPE
    SYNTAX      ModeStatus
    MAX-ACCESS  read-only
    STATUS      current
    DESCRIPTION 
        "This represents whether l3 mode (ip forwarding) feature is
         enabled or disabled on NetScaler."
    ::= { nsModeInfo 9 }

modePathMTUDiscovery OBJECT-TYPE
    SYNTAX      ModeStatus
    MAX-ACCESS  read-only
    STATUS      current
    DESCRIPTION 
        "This represents whether path MTU discovery feature is
         enabled or disabled on NetScaler."
    ::= { nsModeInfo 10 }

modeStaticRouteAdv OBJECT-TYPE
    SYNTAX      ModeStatus
    MAX-ACCESS  read-only
    STATUS      current
    DESCRIPTION 
        "This represents whether static route advertisement feature is
         enabled or disabled on NetScaler."
    ::= { nsModeInfo 11 }

modeDirectRouteAdv OBJECT-TYPE
    SYNTAX      ModeStatus
    MAX-ACCESS  read-only
    STATUS      current
    DESCRIPTION 
        "This represents whether direct route advertisement feature is
         enabled or disabled on NetScaler."
    ::= { nsModeInfo 12 }

nsFiltersGroup OBJECT IDENTIFIER
    ::= { nsSysGroup 22 }

aclStatsGroup OBJECT IDENTIFIER
    ::= { nsFiltersGroup 1 }

aclTotPktsBridgedLow OBJECT-TYPE
    SYNTAX      Counter32
    MAX-ACCESS  read-only
    STATUS      obsolete
    DESCRIPTION 
        "Total packets that matched the acl for bridge and
         got bridged by NetScaler. low32 bits of 64bit counter"
    ::= { aclStatsGroup 1 }

aclTotPktsBridgedHigh OBJECT-TYPE
    SYNTAX      Counter32
    MAX-ACCESS  read-only
    STATUS      obsolete
    DESCRIPTION 
        "Total packets that matched the acl for bridge and
         got bridged by NetScaler. high32 bits of 64bit counter"
    ::= { aclStatsGroup 2 }

aclTotPktsDeniedLow OBJECT-TYPE
    SYNTAX      Counter32
    MAX-ACCESS  read-only
    STATUS      obsolete
    DESCRIPTION 
        "Total packets that matched the acl for deny and
         got dropped by NetScaler. low32 bits of 64bit counter"
    ::= { aclStatsGroup 3 }

aclTotPktsDeniedHigh OBJECT-TYPE
    SYNTAX      Counter32
    MAX-ACCESS  read-only
    STATUS      obsolete
    DESCRIPTION 
        "Total packets that matched the acl for deny and
         got dropped by NetScaler. high32 bits of 64bit counter"
    ::= { aclStatsGroup 4 }

aclTotPktsAllowedLow OBJECT-TYPE
    SYNTAX      Counter32
    MAX-ACCESS  read-only
    STATUS      obsolete
    DESCRIPTION 
        "Total packets that matched the acl for allow and
         got routed by NetScaler on doing routelookups.
         	 low32 bits of 64bit counter."
    ::= { aclStatsGroup 5 }

aclTotPktsAllowedHigh OBJECT-TYPE
    SYNTAX      Counter32
    MAX-ACCESS  read-only
    STATUS      obsolete
    DESCRIPTION 
        "Total packets that matched the acl for allow and
         got routed by NetScaler on doing routelookups.
         	 high32 bits of 64bit counter."
    ::= { aclStatsGroup 6 }

aclTotPktsReusedLow OBJECT-TYPE
    SYNTAX      Counter32
    MAX-ACCESS  read-only
    STATUS      obsolete
    DESCRIPTION 
        "..."
    ::= { aclStatsGroup 7 }

aclTotPktsReusedHigh OBJECT-TYPE
    SYNTAX      Counter32
    MAX-ACCESS  read-only
    STATUS      obsolete
    DESCRIPTION 
        "..."
    ::= { aclStatsGroup 8 }

aclTotPktsBridged OBJECT-TYPE
    SYNTAX      Counter64
    MAX-ACCESS  read-only
    STATUS      current
    DESCRIPTION 
        "Total packets that matched the acl for bridge and
         got bridged by NetScaler."
    ::= { aclStatsGroup 9 }

aclTotPktsDenied OBJECT-TYPE
    SYNTAX      Counter64
    MAX-ACCESS  read-only
    STATUS      current
    DESCRIPTION 
        "Total packets that matched the acl for deny and
         got dropped by NetScaler."
    ::= { aclStatsGroup 10 }

aclTotPktsAllowed OBJECT-TYPE
    SYNTAX      Counter64
    MAX-ACCESS  read-only
    STATUS      current
    DESCRIPTION 
        "Total packets that matched the acl for allow and
         got routed by NetScaler on doing routelookups."
    ::= { aclStatsGroup 11 }

contentFiltersTable OBJECT-TYPE
    SYNTAX      SEQUENCE OF ContentFiltersEntry
    MAX-ACCESS  not-accessible
    STATUS      current
    DESCRIPTION 
        "The table that has the information 
         about content filter."
    ::= { nsFiltersGroup 2 }

contentFiltersEntry OBJECT-TYPE
    SYNTAX      ContentFiltersEntry
    MAX-ACCESS  not-accessible
    STATUS      current
    DESCRIPTION 
        "This represents the information 
         for each entry of content filter."
    INDEX       { contentFilterName }
    ::= { contentFiltersTable 1 }

ContentFiltersEntry ::= SEQUENCE {
    contentFilterName       OCTET STRING,
    contentFilterHitsLow    Counter32,
    contentFilterHitsHigh   Counter32,
    contentFilterHits		Counter64
}

contentFilterName OBJECT-TYPE
    SYNTAX      OCTET STRING
    MAX-ACCESS  read-only
    STATUS      current
    DESCRIPTION 
        "The name of the content filter "
    ::= { contentFiltersEntry 1 }

contentFilterHitsLow OBJECT-TYPE
    SYNTAX      Counter32
    MAX-ACCESS  read-only
    STATUS      obsolete
    DESCRIPTION 
        "The number of times that the content filter has been hit.
         low32 bits of 64bit counter."
    ::= { contentFiltersEntry 2 }

contentFilterHitsHigh OBJECT-TYPE
    SYNTAX      Counter32
    MAX-ACCESS  read-only
    STATUS      obsolete
    DESCRIPTION 
        "The number of times that the content filter has been hit.
         high32 bits of 64bit counter."
    ::= { contentFiltersEntry 3 }

contentFilterHits OBJECT-TYPE
    SYNTAX      Counter64
    MAX-ACCESS  read-only
    STATUS      current
    DESCRIPTION 
        "The number of times that the content filter has been hit."
    ::= { contentFiltersEntry 4 }

nsHighAvailabilityGroup OBJECT IDENTIFIER
    ::= { nsSysGroup 23 }

haPeerId OBJECT-TYPE
    SYNTAX      Integer32
    MAX-ACCESS  read-only
    STATUS      current
    DESCRIPTION 
        "The unique identifier to represent the failover peer
         NetScaler"
    ::= { nsHighAvailabilityGroup 1 }

haPeerIpAddress OBJECT-TYPE
    SYNTAX      IpAddress
    MAX-ACCESS  read-only
    STATUS      current
    DESCRIPTION 
        "This represents the ipaddress of the failover peer
         NetScaler"
    ::= { nsHighAvailabilityGroup 2 }

haPeerState OBJECT-TYPE
    SYNTAX      HAMode
    MAX-ACCESS  read-only
    STATUS      current
    DESCRIPTION 
        "This represents the state of the failover peer
         NetScaler whether Primary or Secondary"
    ::= { nsHighAvailabilityGroup 3 }

haTotStateTransitions OBJECT-TYPE
    SYNTAX      Counter32
    MAX-ACCESS  read-only
    STATUS      current
    DESCRIPTION 
        "This represents the total number of state changes that 
         the NetScaler has made from primary to secondary and vice-versa"
    ::= { nsHighAvailabilityGroup 4 }

haTimeofLastStateTransition OBJECT-TYPE
    SYNTAX      TimeTicks
    MAX-ACCESS  read-only
    STATUS      current
    DESCRIPTION 
        "This represents the time since the NetScaler underwent
         a state change from primary to secondary or vice-versa"
    ::= { nsHighAvailabilityGroup 5 }

vlanTable OBJECT-TYPE
    SYNTAX      SEQUENCE OF VlanEntry
    MAX-ACCESS  not-accessible
    STATUS      current
    DESCRIPTION 
        "The vlan related statistics Table."
    ::= { nsSysGroup 24 }

vlanEntry OBJECT-TYPE
    SYNTAX      VlanEntry
    MAX-ACCESS  not-accessible
    STATUS      current
    DESCRIPTION 
        "Each entry contains one IpAddress to 
         physical address equivalence."
    INDEX       { vlanId }
    ::= { vlanTable 1 }

VlanEntry ::= SEQUENCE {
    vlanId                      Integer32,
    vlanMemberInterfaces        OCTET STRING,
    vlanTaggedInterfaces        OCTET STRING,
    vlanTotRxPktsLow            Counter32,
    vlanTotRxPktsHigh           Counter32,
    vlanTotRxBytesLow           Counter32,
    vlanTotRxBytesHigh          Counter32,
    vlanTotTxPktsLow            Counter32,
    vlanTotTxPktsHigh           Counter32,
    vlanTotTxBytesLow           Counter32,
    vlanTotTxBytesHigh          Counter32,
    vlanTotDroppedPktsLow       Counter32,
    vlanTotDroppedPktsHigh      Counter32,
    vlanTotBroadcastPktsLow     Counter32,
    vlanTotBroadcastPktsHigh    Counter32,
    vlanTotRxPkts	            Counter64,
    vlanTotRxBytes				Counter64,
    vlanTotTxPkts				Counter64,
    vlanTotTxBytes				Counter64,
    vlanTotDroppedPkts			Counter64,
    vlanTotBroadcastPkts		Counter64
    
}

vlanId OBJECT-TYPE
    SYNTAX      Integer32
    MAX-ACCESS  read-only
    STATUS      current
    DESCRIPTION 
        "This represents the unique id of the vlan"
    ::= { vlanEntry 1 }

vlanMemberInterfaces OBJECT-TYPE
    SYNTAX      OCTET STRING
    MAX-ACCESS  read-only
    STATUS      current
    DESCRIPTION 
        "This represents the list of interfaces on the 
         NetScaler that are members of the vlan "
    ::= { vlanEntry 2 }

vlanTaggedInterfaces OBJECT-TYPE
    SYNTAX      OCTET STRING
    MAX-ACCESS  read-only
    STATUS      current
    DESCRIPTION 
        "This represents the list of interfaces on the 
         NetScaler that are members of the vlan that 
         carry tagged packets"
    ::= { vlanEntry 3 }

vlanTotRxPktsLow OBJECT-TYPE
    SYNTAX      Counter32
    MAX-ACCESS  read-only
    STATUS      obsolete
    DESCRIPTION 
        "This represents the total number of packets 
         received on the vlan. low32 bits of 64bit counter."
    ::= { vlanEntry 4 }

vlanTotRxPktsHigh OBJECT-TYPE
    SYNTAX      Counter32
    MAX-ACCESS  read-only
    STATUS      obsolete
    DESCRIPTION 
        "This represents the total number of packets 
         received on the vlan. high32 bits of 64bit counter."
    ::= { vlanEntry 5 }

vlanTotRxBytesLow OBJECT-TYPE
    SYNTAX      Counter32
    MAX-ACCESS  read-only
    STATUS      obsolete
    DESCRIPTION 
        "This represents the total number of bytes received 
         on the vlan. low32 bits of 64bit counter."
    ::= { vlanEntry 6 }

vlanTotRxBytesHigh OBJECT-TYPE
    SYNTAX      Counter32
    MAX-ACCESS  read-only
    STATUS      obsolete
    DESCRIPTION 
        "This represents the total number of bytes received 
         on the vlan. high32 bits of 64bit counter."
    ::= { vlanEntry 7 }

vlanTotTxPktsLow OBJECT-TYPE
    SYNTAX      Counter32
    MAX-ACCESS  read-only
    STATUS      obsolete
    DESCRIPTION 
        "This represents the total number of packets transmitted  
         on the vlan. low32 bits of 64bit counter."
    ::= { vlanEntry 8 }

vlanTotTxPktsHigh OBJECT-TYPE
    SYNTAX      Counter32
    MAX-ACCESS  read-only
    STATUS      obsolete
    DESCRIPTION 
        "This represents the total number of packets transmitted  
         on the vlan. high32 bits of 64bit counter."
    ::= { vlanEntry 9 }

vlanTotTxBytesLow OBJECT-TYPE
    SYNTAX      Counter32
    MAX-ACCESS  read-only
    STATUS      obsolete
    DESCRIPTION 
        "This represents the total number of bytes transmitted  
         on the vlan. low32 bits of 64bit counter."
    ::= { vlanEntry 10 }

vlanTotTxBytesHigh OBJECT-TYPE
    SYNTAX      Counter32
    MAX-ACCESS  read-only
    STATUS      obsolete
    DESCRIPTION 
        "This represents the total number of bytes transmitted  
         on the vlan. high32 bits of 64bit counter."
    ::= { vlanEntry 11 }

vlanTotDroppedPktsLow OBJECT-TYPE
    SYNTAX      Counter32
    MAX-ACCESS  read-only
    STATUS      obsolete
    DESCRIPTION 
        "This represents the total number of packets  
         dropped in the vlan. low32 bits of 64bit counter."
    ::= { vlanEntry 12 }

vlanTotDroppedPktsHigh OBJECT-TYPE
    SYNTAX      Counter32
    MAX-ACCESS  read-only
    STATUS      obsolete
    DESCRIPTION 
        "This represents the total number of packets dropped 
         in the vlan. high32 bits of 64bit counter."
    ::= { vlanEntry 13 }

vlanTotBroadcastPktsLow OBJECT-TYPE
    SYNTAX      Counter32
    MAX-ACCESS  read-only
    STATUS      obsolete
    DESCRIPTION 
        "This represents the total number of broadcast packets 
         sent and received on the vlan. low32 bits of 64bit counter."
    ::= { vlanEntry 14 }

vlanTotBroadcastPktsHigh OBJECT-TYPE
    SYNTAX      Counter32
    MAX-ACCESS  read-only
    STATUS      obsolete
    DESCRIPTION 
        "This represents the total number of broadcast packets 
         sent and received on the vlan. high32 bits of 64bit counter."
    ::= { vlanEntry 15 }

vlanTotRxPkts OBJECT-TYPE
    SYNTAX      Counter64
    MAX-ACCESS  read-only
    STATUS      current
    DESCRIPTION 
        "This represents the total number of packets 
         received on the vlan."
    ::= { vlanEntry 16 }

vlanTotRxBytes OBJECT-TYPE
    SYNTAX      Counter64
    MAX-ACCESS  read-only
    STATUS      current
    DESCRIPTION 
        "This represents the total number of bytes received 
         on the vlan."
    ::= { vlanEntry 17 }

vlanTotTxPkts OBJECT-TYPE
    SYNTAX      Counter64
    MAX-ACCESS  read-only
    STATUS      current
    DESCRIPTION 
        "This represents the total number of packets transmitted  
         on the vlan."
    ::= { vlanEntry 18 }

vlanTotTxBytes OBJECT-TYPE
    SYNTAX      Counter64
    MAX-ACCESS  read-only
    STATUS      current
    DESCRIPTION 
        "This represents the total number of bytes transmitted  
         on the vlan."
    ::= { vlanEntry 19 }

vlanTotDroppedPkts OBJECT-TYPE
    SYNTAX      Counter64
    MAX-ACCESS  read-only
    STATUS      current
    DESCRIPTION 
        "This represents the total number of packets  
         dropped in the vlan."
    ::= { vlanEntry 20 }

vlanTotBroadcastPkts OBJECT-TYPE
    SYNTAX      Counter64
    MAX-ACCESS  read-only
    STATUS      current
    DESCRIPTION 
        "This represents the total number of broadcast packets 
         sent and received on the vlan."
    ::= { vlanEntry 21 }

nsResourceGroup OBJECT IDENTIFIER
    ::= { nsSysGroup 41 }

resCpuUsage OBJECT-TYPE
    SYNTAX      Gauge32
    MAX-ACCESS  read-only
    STATUS      current
    DESCRIPTION 
        "This represents the percentage of CPU utilization on NetScaler"
    ::= { nsResourceGroup 1 }

resMemUsage OBJECT-TYPE
    SYNTAX      Gauge32
    MAX-ACCESS  read-only
    STATUS      current
    DESCRIPTION 
        "This represents the percentage of memory utilization on NetScaler"
    ::= { nsResourceGroup 2 }

nsIpStatsGroup OBJECT IDENTIFIER
    ::= { nsSysGroup 43 }

ipTotRxPktsLow OBJECT-TYPE
    SYNTAX      Counter32
    MAX-ACCESS  read-only
    STATUS      obsolete
    DESCRIPTION 
        "This represents the lower 32bits of the Counter which 
         contains total number of ip packets received by the netscaler"
    ::= { nsIpStatsGroup 1 }

ipTotRxPktsHigh OBJECT-TYPE
    SYNTAX      Counter32
    MAX-ACCESS  read-only
    STATUS      obsolete
    DESCRIPTION 
        "This represents the higher 32 bits of the Counter which 
         contains total number of ip packets received by the netscaler"
    ::= { nsIpStatsGroup 2 }

ipTotRxBytesLow OBJECT-TYPE
    SYNTAX      Counter32
    MAX-ACCESS  read-only
    STATUS      obsolete
    DESCRIPTION 
        "This represents the lower 32bits of the Counter which 
         contains total number of ip bytes received by the netscaler"
    ::= { nsIpStatsGroup 3 }

ipTotRxBytesHigh OBJECT-TYPE
    SYNTAX      Counter32
    MAX-ACCESS  read-only
    STATUS      obsolete
    DESCRIPTION 
        "This represents the higher 32 bits of the Counter which 
         contains total number of ip bytes received by the netscaler"
    ::= { nsIpStatsGroup 4 }

ipTotRxMbitsLow OBJECT-TYPE
    SYNTAX      Counter32
    MAX-ACCESS  read-only
    STATUS      obsolete
    DESCRIPTION 
        "This represents the lower 32bits of the Counter which 
         contains total number of ip bits received by the netscaler 
         in Megabits"
    ::= { nsIpStatsGroup 5 }

ipTotRxMbitsHigh OBJECT-TYPE
    SYNTAX      Counter32
    MAX-ACCESS  read-only
    STATUS      obsolete
    DESCRIPTION 
        "This represents the higher 32 bits of the Counter which 
         contains total number of  ip bits received by the netscaler 
         in Megabits"
    ::= { nsIpStatsGroup 6 }

ipTotTxPktsLow OBJECT-TYPE
    SYNTAX      Counter32
    MAX-ACCESS  read-only
    STATUS      obsolete
    DESCRIPTION 
        "This represents the lower 32bits of the Counter which 
         contains total number of ip packets transmitted by the netscaler"
    ::= { nsIpStatsGroup 7 }

ipTotTxPktsHigh OBJECT-TYPE
    SYNTAX      Counter32
    MAX-ACCESS  read-only
    STATUS      obsolete
    DESCRIPTION 
        "This represents the higher 32 bits of the Counter which 
         contains total number of ip packets transmitted by the netscaler"
    ::= { nsIpStatsGroup 8 }

ipTotTxBytesLow OBJECT-TYPE
    SYNTAX      Counter32
    MAX-ACCESS  read-only
    STATUS      obsolete
    DESCRIPTION 
        "This represents the lower 32bits of the Counter which 
         contains total number of ip bytes transmitted by the netscaler"
    ::= { nsIpStatsGroup 9 }

ipTotTxBytesHigh OBJECT-TYPE
    SYNTAX      Counter32
    MAX-ACCESS  read-only
    STATUS      obsolete
    DESCRIPTION 
        "This represents the higher 32 bits of the Counter which 
         contains total number of ip bytes transmitted by the netscaler"
    ::= { nsIpStatsGroup 10 }

ipTotTxMbitsLow OBJECT-TYPE
    SYNTAX      Counter32
    MAX-ACCESS  read-only
    STATUS      obsolete
    DESCRIPTION 
        "This represents the lower 32bits of the Counter which 
         contains total number of ip bits transmitted by the netscaler in Megabits"
    ::= { nsIpStatsGroup 11 }

ipTotTxMbitsHigh OBJECT-TYPE
    SYNTAX      Counter32
    MAX-ACCESS  read-only
    STATUS      obsolete
    DESCRIPTION 
        "This represents the higher 32 bits of the Counter which 
         contains total number of  ip bits transmitted by the netscaler in Megabits"
    ::= { nsIpStatsGroup 12 }

ipTotFragmentsLow OBJECT-TYPE
    SYNTAX      Counter32
    MAX-ACCESS  read-only
    STATUS      obsolete
    DESCRIPTION 
        "This represents the lower 32bits of the Counter which 
         contains total number of ip fragments received"
    ::= { nsIpStatsGroup 13 }

ipTotFragmentsHigh OBJECT-TYPE
    SYNTAX      Counter32
    MAX-ACCESS  read-only
    STATUS      obsolete
    DESCRIPTION 
        "This represents the higher 32 bits of the Counter which 
         contains total number of  ip fragments received"
    ::= { nsIpStatsGroup 14 }

ipTotBadlensLow OBJECT-TYPE
    SYNTAX      Counter32
    MAX-ACCESS  read-only
    STATUS      obsolete
    DESCRIPTION 
        "This represents the lower 32bits of the Counter which 
        contains total number of ip packets received with 
        length > 1514 "
    ::= { nsIpStatsGroup 15 }

ipTotBadlensHigh OBJECT-TYPE
    SYNTAX      Counter32
    MAX-ACCESS  read-only
    STATUS      obsolete
    DESCRIPTION 
        "This represents the higher 32 bits of the Counter which 
        contains total number of ip packets received with 
        length > 1514"
    ::= { nsIpStatsGroup 16 }

ipTotBadMacAddrsLow OBJECT-TYPE
    SYNTAX      Counter32
    MAX-ACCESS  read-only
    STATUS      obsolete
    DESCRIPTION 
        "This represents the lower 32bits of the Counter which 
        contains total number of transmitted ip packets with 
        bad MAC addresses"
    ::= { nsIpStatsGroup 17 }

ipTotBadMacAddrsHigh OBJECT-TYPE
    SYNTAX      Counter32
    MAX-ACCESS  read-only
    STATUS      obsolete
    DESCRIPTION 
        "This represents the higher 32bits of the Counter which
         contains total number of transmitted ip packets with 
         bad MAC addresseses"
    ::= { nsIpStatsGroup 18 }           

ipTotMaxClientsLow OBJECT-TYPE
    SYNTAX      Counter32
    MAX-ACCESS  read-only
    STATUS      obsolete
    DESCRIPTION 
        "This represents the lower 32bits of the Counter which 
        contains total number of times one tries to open a new
        connection to a service having maximum number of allowed 
        open client connections"
    ::= { nsIpStatsGroup 19 }

ipTotMaxClientsHigh OBJECT-TYPE
    SYNTAX      Counter32
    MAX-ACCESS  read-only
    STATUS      obsolete
    DESCRIPTION 
        "This represents the higher 32bits of the Counter which 
        contains total number of times one tries to open a new 
        connection to a service having maximum number of allowed 
        open client connections"
    ::= { nsIpStatsGroup 20 }

ipTotUnknownSvcsLow OBJECT-TYPE
    SYNTAX      Counter32
    MAX-ACCESS  read-only
    STATUS      obsolete
    DESCRIPTION 
        "This represents the lower 32bits of the Counter which 
        contains total number of packets received for a NetScaler
        owned IP, but an un-configured port/service"
    ::= { nsIpStatsGroup 21 }

ipTotUnknownSvcsHigh OBJECT-TYPE
    SYNTAX      Counter32
    MAX-ACCESS  read-only
    STATUS      obsolete
    DESCRIPTION 
        "This represents the higher 32bits of the Counter which 
        contains total number of packets received for a NetScaler
        owned IP, but an un-configured port/service"
    ::= { nsIpStatsGroup 22 }

ipTotLandattacksLow OBJECT-TYPE
    SYNTAX      Counter32
    MAX-ACCESS  read-only
    STATUS      obsolete
    DESCRIPTION 
        "This represents the lower 32bits of the Counter which 
        contains total number of land attacks packets received 
        by NetScaler"
    ::= { nsIpStatsGroup 23 }

ipTotLandattacksHigh OBJECT-TYPE
    SYNTAX      Counter32
    MAX-ACCESS  read-only
    STATUS      obsolete
    DESCRIPTION 
        "This represents the higher 32bits of the Counter which 
        contains total number of land attacks packets received 
        by NetScaler"
    ::= { nsIpStatsGroup 24 }
    
ipTotRxPkts OBJECT-TYPE
    SYNTAX      Counter64
    MAX-ACCESS  read-only
    STATUS      current
    DESCRIPTION 
        "This represents the Counter which 
         contains total number of ip packets received by the netscaler"
    ::= { nsIpStatsGroup 25 }

ipTotRxBytes OBJECT-TYPE
    SYNTAX      Counter64
    MAX-ACCESS  read-only
    STATUS      current
    DESCRIPTION 
        "This represents the Counter which 
         contains total number of ip bytes received by the netscaler"
    ::= { nsIpStatsGroup 26 }

ipTotRxMbits OBJECT-TYPE
    SYNTAX      Counter64
    MAX-ACCESS  read-only
    STATUS      current
    DESCRIPTION 
        "This represents the Counter which 
         contains total number of ip bits received by the netscaler 
         in Megabits"
    ::= { nsIpStatsGroup 27 }

ipTotTxPkts OBJECT-TYPE
    SYNTAX      Counter64
    MAX-ACCESS  read-only
    STATUS      current
    DESCRIPTION 
        "This represents the Counter which 
         contains total number of ip packets transmitted by the netscaler"
    ::= { nsIpStatsGroup 28 }

ipTotTxBytes OBJECT-TYPE
    SYNTAX      Counter64
    MAX-ACCESS  read-only
    STATUS      current
    DESCRIPTION 
        "This represents the Counter which 
         contains total number of ip bytes transmitted by the netscaler"
    ::= { nsIpStatsGroup 29 }

ipTotTxMbits OBJECT-TYPE
    SYNTAX      Counter64
    MAX-ACCESS  read-only
    STATUS      current
    DESCRIPTION 
        "This represents the Counter which 
         contains total number of ip bits transmitted by the netscaler in Megabits"
    ::= { nsIpStatsGroup 30 }

ipTotFragments OBJECT-TYPE
    SYNTAX      Counter64
    MAX-ACCESS  read-only
    STATUS      current
    DESCRIPTION 
        "This represents the Counter which 
         contains total number of ip fragments received"
    ::= { nsIpStatsGroup 31 }

ipTotBadlens OBJECT-TYPE
    SYNTAX      Counter64
    MAX-ACCESS  read-only
    STATUS      current
    DESCRIPTION 
        "The total number of ip packets received with length > 1514"
    ::= { nsIpStatsGroup 32 }

ipTotBadMacAddrs OBJECT-TYPE
    SYNTAX      Counter64
    MAX-ACCESS  read-only
    STATUS      current
    DESCRIPTION 
        "The total number of transmitted ip packets with bad MAC addresseses"
    ::= { nsIpStatsGroup 33 }

ipTotMaxClients OBJECT-TYPE
    SYNTAX      Counter64
    MAX-ACCESS  read-only
    STATUS      current
    DESCRIPTION 
        "The total number of times one tries to open a new connection to a service having maximum number of allowed open client connections"
    ::= { nsIpStatsGroup 34 }

ipTotUnknownSvcs OBJECT-TYPE
    SYNTAX      Counter64
    MAX-ACCESS  read-only
    STATUS      current
    DESCRIPTION 
        "The total number of packets received for a NetScaler owned IP, but an un-configured port/service"
    ::= { nsIpStatsGroup 35 }

ipTotLandattacks OBJECT-TYPE
    SYNTAX      Counter64
    MAX-ACCESS  read-only
    STATUS      current
    DESCRIPTION 
        "The total number of land attack packets received by NetScaler."
    ::= { nsIpStatsGroup 36 }

nsIcmpStatsGroup OBJECT IDENTIFIER
    ::= { nsSysGroup 44 }

icmpTotRxPktsLow OBJECT-TYPE
    SYNTAX      Counter32
    MAX-ACCESS  read-only
    STATUS      obsolete
    DESCRIPTION 
        "This represents the lower 32bits of the Counter which 
         contains total number of icmp packets received by NetScaler "
    ::= { nsIcmpStatsGroup 1 }

icmpTotRxPktsHigh OBJECT-TYPE
    SYNTAX      Counter32
    MAX-ACCESS  read-only
    STATUS      obsolete
    DESCRIPTION 
        "This represents the higher 32 bits of the Counter 
         which contains total number of  icmp packets received by NetScaler"
    ::= { nsIcmpStatsGroup 2 }

icmpTotRxBytesLow OBJECT-TYPE
    SYNTAX      Counter32
    MAX-ACCESS  read-only
    STATUS      obsolete
    DESCRIPTION 
        "This represents the lower 32bits of the Counter 
         which contains total number of icmp bytes received by NetScaler "
    ::= { nsIcmpStatsGroup 3 }

icmpTotRxBytesHigh OBJECT-TYPE
    SYNTAX      Counter32
    MAX-ACCESS  read-only
    STATUS      obsolete
    DESCRIPTION 
        "This represents the higher 32 bits of the Counter which 
         contains total number of  icmp bytes received by NetScaler"
    ::= { nsIcmpStatsGroup 4 }

icmpTotTxPktsLow OBJECT-TYPE
    SYNTAX      Counter32
    MAX-ACCESS  read-only
    STATUS      obsolete
    DESCRIPTION 
        "This represents the lower 32bits of the Counter which 
         contains total number of icmp packets transmitted by NetScaler "
    ::= { nsIcmpStatsGroup 5 }

icmpTotTxPktsHigh OBJECT-TYPE
    SYNTAX      Counter32
    MAX-ACCESS  read-only
    STATUS      obsolete
    DESCRIPTION 
        "This represents the higher 32 bits of the Counter which 
         contains total number of  icmp packets transmitted by NetScaler"
    ::= { nsIcmpStatsGroup 6 }

icmpTotTxBytesLow OBJECT-TYPE
    SYNTAX      Counter32
    MAX-ACCESS  read-only
    STATUS      obsolete
    DESCRIPTION 
        "This represents the lower 32bits of the Counter which 
         contains total number of icmp bytes transmitted by NetScaler "
    ::= { nsIcmpStatsGroup 7 }

icmpTotTxBytesHigh OBJECT-TYPE
    SYNTAX      Counter32
    MAX-ACCESS  read-only
    STATUS      obsolete
    DESCRIPTION 
        "This represents the higher 32 bits of the Counter which 
         contains total number of  icmp bytes transmitted by NetScaler"
    ::= { nsIcmpStatsGroup 8 }

icmpTotRxEchoReplyLow OBJECT-TYPE
    SYNTAX      Counter32
    MAX-ACCESS  read-only
    STATUS      obsolete
    DESCRIPTION 
        "This represents the lower 32 bits of the Counter which 
         contains total number of  icmp Echo Replies received by NetScaler"
    ::= { nsIcmpStatsGroup 9 }

icmpTotRxEchoReplyHigh OBJECT-TYPE
    SYNTAX      Counter32
    MAX-ACCESS  read-only
    STATUS      obsolete
    DESCRIPTION 
        "This represents the higher 32 bits of the Counter which 
         contains total number of  icmp Echo Replies received by NetScaler"
    ::= { nsIcmpStatsGroup 10 }

icmpTotTxEchoReplyLow OBJECT-TYPE
    SYNTAX      Counter32
    MAX-ACCESS  read-only
    STATUS      obsolete
    DESCRIPTION 
        "This represents the lower 32 bits of the Counter which 
         contains total number of  icmp Echo Replies transmitted by NetScaler"
    ::= { nsIcmpStatsGroup 11 }

icmpTotTxEchoReplyHigh OBJECT-TYPE
    SYNTAX      Counter32
    MAX-ACCESS  read-only
    STATUS      obsolete
    DESCRIPTION 
        "This represents the higher 32 bits of the Counter which 
         contains total number of  icmp Echo Replies transmitted by NetScaler"
    ::= { nsIcmpStatsGroup 12 }

icmpTotRxEchoLow OBJECT-TYPE
    SYNTAX      Counter32
    MAX-ACCESS  read-only
    STATUS      obsolete
    DESCRIPTION 
        "This represents the lower 32 bits of the Counter which 
         contains total number of  icmp Echo  received by NetScaler"
    ::= { nsIcmpStatsGroup 13 }

icmpTotRxEchoHigh OBJECT-TYPE
    SYNTAX      Counter32
    MAX-ACCESS  read-only
    STATUS      obsolete
    DESCRIPTION 
        "This represents the higher 32 bits of the Counter which 
         contains total number of  icmp Echo  received by NetScaler"
    ::= { nsIcmpStatsGroup 14 }

icmpTotPktsDroppedLow OBJECT-TYPE
    SYNTAX      Counter32
    MAX-ACCESS  read-only
    STATUS      obsolete
    DESCRIPTION 
        "This represents the lower 32bits of the Counter which 
         contains total number of icmp packets dropped by NetScaler "
    ::= { nsIcmpStatsGroup 15 }

icmpTotPktsDroppedHigh OBJECT-TYPE
    SYNTAX      Counter32
    MAX-ACCESS  read-only
    STATUS      obsolete
    DESCRIPTION 
        "This represents the higher 32 bits of the Counter which 
         contains total number of  icmp packets dropped by NetScaler"
    ::= { nsIcmpStatsGroup 16 }

icmpCurRateThreshold OBJECT-TYPE
    SYNTAX      Integer32
    MAX-ACCESS  read-only
    STATUS      current
    DESCRIPTION 
        "This contains the value set for 10ms rate threshold for icmp packets. 
         This implies that within 10ms range , NetScaler can allow 
         (receive or pass through ) the set number of icmp packets "
    ::= { nsIcmpStatsGroup 17 }

icmpCurRateThresholdInterval OBJECT-TYPE
    SYNTAX      Integer32
    MAX-ACCESS  read-only
    STATUS      obsolete
    DESCRIPTION 
        "This represents the higher 32 bits of the Counter which 
         contains total number ..."
    ::= { nsIcmpStatsGroup 18 }

icmpCurRateCounter OBJECT-TYPE
    SYNTAX      Counter32
    MAX-ACCESS  read-only
    STATUS      obsolete
    DESCRIPTION 
        "This represents the lower 32bits of the Counter which 
         contains total number of icmp ... "
    ::= { nsIcmpStatsGroup 19 }

icmpTotThresholdExceedsLow OBJECT-TYPE
    SYNTAX      Counter32
    MAX-ACCESS  read-only
    STATUS      obsolete
    DESCRIPTION 
        "This represents the lower 32bits of the Counter which 
         contains total number of time icmp rate threshold was exceeded"
    ::= { nsIcmpStatsGroup 20 }

icmpTotThresholdExceedsHigh OBJECT-TYPE
    SYNTAX      Counter32
    MAX-ACCESS  read-only
    STATUS      obsolete
    DESCRIPTION 
        "This represents the higher 32 bits of the Counter which 
         contains total number of time icmp rate threshold was exceeded"
    ::= { nsIcmpStatsGroup 21 }
 
icmpTotRxPkts OBJECT-TYPE
    SYNTAX      Counter64
    MAX-ACCESS  read-only
    STATUS      current
    DESCRIPTION 
        "This represents the Counter which 
         contains total number of icmp packets received by NetScaler "
    ::= { nsIcmpStatsGroup 22 }

icmpTotRxBytes OBJECT-TYPE
    SYNTAX      Counter64
    MAX-ACCESS  read-only
    STATUS      current
    DESCRIPTION 
        "This represents the Counter 
         which contains total number of icmp bytes received by NetScaler "
    ::= { nsIcmpStatsGroup 23 }

icmpTotTxPkts OBJECT-TYPE
    SYNTAX      Counter64
    MAX-ACCESS  read-only
    STATUS      current
    DESCRIPTION 
        "This represents the Counter which 
         contains total number of icmp packets transmitted by NetScaler "
    ::= { nsIcmpStatsGroup 24 }

icmpTotTxBytes OBJECT-TYPE
    SYNTAX      Counter64
    MAX-ACCESS  read-only
    STATUS      current
    DESCRIPTION 
        "This represents the Counter which 
         contains total number of icmp bytes transmitted by NetScaler "
    ::= { nsIcmpStatsGroup 25 }

icmpTotRxEchoReply OBJECT-TYPE
    SYNTAX      Counter64
    MAX-ACCESS  read-only
    STATUS      current
    DESCRIPTION 
        "This represents the Counter which 
         contains total number of  icmp Echo Replies received by NetScaler"
    ::= { nsIcmpStatsGroup 26 }

icmpTotTxEchoReply OBJECT-TYPE
    SYNTAX      Counter64
    MAX-ACCESS  read-only
    STATUS      current
    DESCRIPTION 
        "This represents the Counter which 
         contains total number of  icmp Echo Replies transmitted by NetScaler"
    ::= { nsIcmpStatsGroup 27 }

icmpTotRxEcho OBJECT-TYPE
    SYNTAX      Counter64
    MAX-ACCESS  read-only
    STATUS      current
    DESCRIPTION 
        "This represents the Counter which 
         contains total number of  icmp Echo  received by NetScaler"
    ::= { nsIcmpStatsGroup 28 }

icmpTotPktsDropped OBJECT-TYPE
    SYNTAX      Counter64
    MAX-ACCESS  read-only
    STATUS      current
    DESCRIPTION 
        "This represents the Counter which 
         contains total number of icmp packets dropped by NetScaler "
    ::= { nsIcmpStatsGroup 29 }

icmpTotThresholdExceeds OBJECT-TYPE
    SYNTAX      Counter64
    MAX-ACCESS  read-only
    STATUS      current
    DESCRIPTION 
        "This represents the Counter which 
         contains total number of time icmp rate threshold was exceeded"
    ::= { nsIcmpStatsGroup 30 }

nsUdpStatsGroup OBJECT IDENTIFIER
    ::= { nsSysGroup 45 }

udpTotUnknownSvcPktsLow OBJECT-TYPE
    SYNTAX      Counter32
    MAX-ACCESS  read-only
    STATUS      obsolete
    DESCRIPTION 
        "This represents the lower 32bits of the Counter which contains number of UDP packets received for a NetScaler owned IP, but an un-configured port/service"
    ::= { nsUdpStatsGroup 1 }

udpTotUnknownSvcPktsHigh OBJECT-TYPE
    SYNTAX      Counter32
    MAX-ACCESS  read-only
    STATUS      obsolete
    DESCRIPTION 
        "This represents the higher 32bits of the Counter which contains number of UDP packets received for a NetScaler owned IP, but an un-configured port/service"
    ::= { nsUdpStatsGroup 2 }

udpTotRxPktsLow OBJECT-TYPE
    SYNTAX      Counter32
    MAX-ACCESS  read-only
    STATUS      obsolete
    DESCRIPTION 
        "This represents the lower 32bits of the Counter which 
         contains total number of UDP packets received by NetScaler "
    ::= { nsUdpStatsGroup 3 }

udpTotRxPktsHigh OBJECT-TYPE
    SYNTAX      Counter32
    MAX-ACCESS  read-only
    STATUS      obsolete
    DESCRIPTION 
        "This represents the higher 32 bits of the Counter which 
         contains total number of  UDP packets received by NetScaler"
    ::= { nsUdpStatsGroup 4 }

udpTotRxBytesLow OBJECT-TYPE
    SYNTAX      Counter32
    MAX-ACCESS  read-only
    STATUS      obsolete
    DESCRIPTION 
        "This represents the lower 32bits of the Counter which 
         contains total number of UDP bytes received by NetScaler "
    ::= { nsUdpStatsGroup 5 }

udpTotRxBytesHigh OBJECT-TYPE
    SYNTAX      Counter32
    MAX-ACCESS  read-only
    STATUS      obsolete
    DESCRIPTION 
        "This represents the higher 32 bits of the Counter which 
         contains total number of  UDP bytes received by NetScaler"
    ::= { nsUdpStatsGroup 6 }

udpTotTxPktsLow OBJECT-TYPE
    SYNTAX      Counter32
    MAX-ACCESS  read-only
    STATUS      obsolete
    DESCRIPTION 
        "This represents the lower 32bits of the Counter which 
         contains total number of UDP packets transmitted by NetScaler "
    ::= { nsUdpStatsGroup 7 }

udpTotTxPktsHigh OBJECT-TYPE
    SYNTAX      Counter32
    MAX-ACCESS  read-only
    STATUS      obsolete
    DESCRIPTION 
        "This represents the higher 32 bits of the Counter which 
         contains total number of  UDP packets transmitted by NetScaler"
    ::= { nsUdpStatsGroup 8 }

udpTotTxBytesLow OBJECT-TYPE
    SYNTAX      Counter32
    MAX-ACCESS  read-only
    STATUS      obsolete
    DESCRIPTION 
        "This represents the lower 32bits of the Counter which 
         contains total number of UDP bytes transmitted by NetScaler "
    ::= { nsUdpStatsGroup 9 }

udpTotTxBytesHigh OBJECT-TYPE
    SYNTAX      Counter32
    MAX-ACCESS  read-only
    STATUS      obsolete
    DESCRIPTION 
        "This represents the higher 32 bits of the Counter which 
         contains total number of  UDP bytes transmitted by NetScaler"
    ::= { nsUdpStatsGroup 10 }

udpRateThreshold OBJECT-TYPE
    SYNTAX      Counter32
    MAX-ACCESS  read-only
    STATUS      current
    DESCRIPTION 
        "This represents the lower 32bits of the Counter which contains 
         udp rate threshold value. The UDP packets received beyond 
         threshold will be dropped "
    ::= { nsUdpStatsGroup 11 }

udpRateInterval OBJECT-TYPE
    SYNTAX      Counter32
    MAX-ACCESS  read-only
    STATUS      obsolete
    DESCRIPTION 
        "This represents the lower 32bits of the Counter which contains 
         udp rate threshold value . The UDP packets received beyond 
         threshold will be dropped "
    ::= { nsUdpStatsGroup 12 }

udpCurRateCounter OBJECT-TYPE
    SYNTAX      Counter32
    MAX-ACCESS  read-only
    STATUS      obsolete
    DESCRIPTION 
        "This represents the lower 32bits of the Counter which contains 
         udp rate threshold value . The UDP packets received 
         beyond threshold will be dropped "
    ::= { nsUdpStatsGroup 13 }

udpCurRateThresholdExceedsLow OBJECT-TYPE
    SYNTAX      Counter32
    MAX-ACCESS  read-only
    STATUS      obsolete
    DESCRIPTION 
        "This represents the lower 32bits of the Counter which contains 
         udp rate threshold value . The UDP packets received beyond 
         threshold will be dropped "
    ::= { nsUdpStatsGroup 14 }

udpCurRateThresholdExceedsHigh OBJECT-TYPE
    SYNTAX      Counter32
    MAX-ACCESS  read-only
    STATUS      obsolete
    DESCRIPTION 
        "This represents the higher 32bits of the Counter which contains 
         udp rate threshold value . The UDP packets received 
         beyond threshold will be dropped "
    ::= { nsUdpStatsGroup 15 }

udpTotUnknownSvcPkts OBJECT-TYPE
    SYNTAX      Counter64
    MAX-ACCESS  read-only
    STATUS      current
    DESCRIPTION 
        "Total number of UDP packets received for a NetScaler owned IP, but an un-configured port/service"
    ::= { nsUdpStatsGroup 16 }

udpTotRxPkts OBJECT-TYPE
    SYNTAX      Counter64
    MAX-ACCESS  read-only
    STATUS      current
    DESCRIPTION 
        "This represents the Counter which 
         contains total number of UDP packets received by NetScaler "
    ::= { nsUdpStatsGroup 17 }

udpTotRxBytes OBJECT-TYPE
    SYNTAX      Counter64
    MAX-ACCESS  read-only
    STATUS      current
    DESCRIPTION 
        "This represents the Counter which 
         contains total number of UDP bytes received by NetScaler "
    ::= { nsUdpStatsGroup 18 }

udpTotTxPkts OBJECT-TYPE
    SYNTAX      Counter64
    MAX-ACCESS  read-only
    STATUS      current
    DESCRIPTION 
        "This represents the Counter which 
         contains total number of UDP packets transmitted by NetScaler "
    ::= { nsUdpStatsGroup 19 }

udpTotTxBytes OBJECT-TYPE
    SYNTAX      Counter64
    MAX-ACCESS  read-only
    STATUS      current
    DESCRIPTION 
        "This represents the Counter which 
         contains total number of UDP bytes transmitted by NetScaler "
    ::= { nsUdpStatsGroup 20 }

udpCurRateThresholdExceeds OBJECT-TYPE
    SYNTAX      Counter64
    MAX-ACCESS  read-only
    STATUS      current
    DESCRIPTION 
        "This represents the Counter which contains 
         udp rate threshold value . The UDP packets received beyond 
         threshold will be dropped "
    ::= { nsUdpStatsGroup 21 }

nsTcpStatsGroup OBJECT IDENTIFIER
    ::= { nsSysGroup 46 }

tcpCurServerConn OBJECT-TYPE
    SYNTAX      Gauge32
    MAX-ACCESS  read-only
    STATUS      current
    DESCRIPTION 
        "This represents the total number of current server 
         connections on NetScaler"
    ::= { nsTcpStatsGroup 1 }

tcpCurClientConn OBJECT-TYPE
    SYNTAX      Gauge32
    MAX-ACCESS  read-only
    STATUS      current
    DESCRIPTION 
        "This represents the total number of current client 
         connections on NetScaler"
    ::= { nsTcpStatsGroup 2 }

tcpCurPendingConn OBJECT-TYPE
    SYNTAX      Gauge32
    MAX-ACCESS  read-only
    STATUS      current
    DESCRIPTION 
        "This represents total number of pending 
         connections on NetScaler"
    ::= { nsTcpStatsGroup 3 }

tcpCurResetCount OBJECT-TYPE
    SYNTAX      Counter32
    MAX-ACCESS  read-only
    STATUS      obsolete
    DESCRIPTION 
        "This represents total number of resets sent 
         by NetScaler. Obsolete."
    ::= { nsTcpStatsGroup 4 }

tcpMaxServerConnections OBJECT-TYPE
    SYNTAX      Integer32
    MAX-ACCESS  read-only
    STATUS      current
    DESCRIPTION 
        "This represents the maximum server connection 
         limit on NetScaler"
    ::= { nsTcpStatsGroup 5 }

tcpMaxReqsperConn OBJECT-TYPE
    SYNTAX      Integer32
    MAX-ACCESS  read-only
    STATUS      current
    DESCRIPTION 
        "This represents the maximum number of requests 
         handled by NetScaler per connection"
    ::= { nsTcpStatsGroup 6 }

tcpMaxPerSrvrReusePool OBJECT-TYPE
    SYNTAX      Integer32
    MAX-ACCESS  read-only
    STATUS      obsolete
    DESCRIPTION 
        "This represents the time the last reset got 
         sent by NetScaler"
    ::= { nsTcpStatsGroup 7 }

nsSslStatsGroup OBJECT IDENTIFIER
    ::= { nsSysGroup 47 }

sslCardStatus OBJECT-TYPE
    SYNTAX      Integer32
    MAX-ACCESS  read-only
    STATUS      current
    DESCRIPTION 
        "Status of the SSL CARD"
    ::= { nsSslStatsGroup 1 }

sslEngineStatus OBJECT-TYPE
    SYNTAX      Integer32
    MAX-ACCESS  read-only
    STATUS      current
    DESCRIPTION 
        "Status of the SSL Engine"
    ::= { nsSslStatsGroup 2 }

sslSessionsPerSec OBJECT-TYPE
    SYNTAX      Integer32
    MAX-ACCESS  read-only
    STATUS      current
    DESCRIPTION 
        "SSL sessions/second between client and NetScaler"
    ::= { nsSslStatsGroup 3 }

sslTotTransactionsLow OBJECT-TYPE
    SYNTAX      Counter32
    MAX-ACCESS  read-only
    STATUS      obsolete
    DESCRIPTION 
        " Total number of SSL Transactions.
         low32 bits of 64bit counter."
    ::= { nsSslStatsGroup 11 }

sslTotTransactionsHigh OBJECT-TYPE
    SYNTAX      Counter32
    MAX-ACCESS  read-only
    STATUS      obsolete
    DESCRIPTION 
        " Total number of SSL Transactions.
         high32 bits of 64bit counter."
    ::= { nsSslStatsGroup 12 }

sslTotSSLv2TransactionsLow OBJECT-TYPE
    SYNTAX      Counter32
    MAX-ACCESS  read-only
    STATUS      obsolete
    DESCRIPTION 
        " Total number of SSLv2 Transactions.
         low32 bits of 64bit counter."
    ::= { nsSslStatsGroup 13 }

sslTotSSLv2TransactionsHigh OBJECT-TYPE
    SYNTAX      Counter32
    MAX-ACCESS  read-only
    STATUS      obsolete
    DESCRIPTION 
        " Total number of SSLv2 Transactions.
         high32 bits of 64bit counter."
    ::= { nsSslStatsGroup 14 }

sslTotSSLv3TransactionsLow OBJECT-TYPE
    SYNTAX      Counter32
    MAX-ACCESS  read-only
    STATUS      obsolete
    DESCRIPTION 
        " Total number of SSLv3 Transactions.
         low32 bits of 64bit counter."
    ::= { nsSslStatsGroup 15 }

sslTotSSLv3TransactionsHigh OBJECT-TYPE
    SYNTAX      Counter32
    MAX-ACCESS  read-only
    STATUS      obsolete
    DESCRIPTION 
        " Total number of SSLv3 Transactions.
         high32 bits of 64bit counter."
    ::= { nsSslStatsGroup 16 }

sslTotTLSv1TransactionsLow OBJECT-TYPE
    SYNTAX      Counter32
    MAX-ACCESS  read-only
    STATUS      obsolete
    DESCRIPTION 
        " Total number of TLSv1 Transactions.
         low32 bits of 64bit counter."
    ::= { nsSslStatsGroup 17 }

sslTotTLSv1TransactionsHigh OBJECT-TYPE
    SYNTAX      Counter32
    MAX-ACCESS  read-only
    STATUS      obsolete
    DESCRIPTION 
        " Total number of TLSv1 Transactions.
         high32 bits of 64bit counter."
    ::= { nsSslStatsGroup 18 }

sslTotSessionsLow OBJECT-TYPE
    SYNTAX      Counter32
    MAX-ACCESS  read-only
    STATUS      obsolete
    DESCRIPTION 
        " Total number of SSL Sessions.
         low32 bits of 64bit counter."
    ::= { nsSslStatsGroup 19 }

sslTotSessionsHigh OBJECT-TYPE
    SYNTAX      Counter32
    MAX-ACCESS  read-only
    STATUS      obsolete
    DESCRIPTION 
        " Total number of SSL Sessions.
         high32 bits of 64bit counter."
    ::= { nsSslStatsGroup 20 }

sslTotSSLv2SessionsLow OBJECT-TYPE
    SYNTAX      Counter32
    MAX-ACCESS  read-only
    STATUS      obsolete
    DESCRIPTION 
        " Total number of SSLv2 Sessions.
         low32 bits of 64bit counter."
    ::= { nsSslStatsGroup 21 }

sslTotSSLv2SessionsHigh OBJECT-TYPE
    SYNTAX      Counter32
    MAX-ACCESS  read-only
    STATUS      obsolete
    DESCRIPTION 
        " Total number of SSLv2 Sessions.
         high32 bits of 64bit counter."
    ::= { nsSslStatsGroup 22 }

sslTotSSLv3SessionsLow OBJECT-TYPE
    SYNTAX      Counter32
    MAX-ACCESS  read-only
    STATUS      obsolete
    DESCRIPTION 
        " Total number of SSLv3 Sessions.
         low32 bits of 64bit counter."
    ::= { nsSslStatsGroup 23 }

sslTotSSLv3SessionsHigh OBJECT-TYPE
    SYNTAX      Counter32
    MAX-ACCESS  read-only
    STATUS      obsolete
    DESCRIPTION 
        " Total number of SSLv3 Sessions.
         high32 bits of 64bit counter."
    ::= { nsSslStatsGroup 24 }

sslTotTLSv1SessionsLow OBJECT-TYPE
    SYNTAX      Counter32
    MAX-ACCESS  read-only
    STATUS      obsolete
    DESCRIPTION 
        " Total number of TLSv1 Sessions.
         low32 bits of 64bit counter."
    ::= { nsSslStatsGroup 25 }

sslTotTLSv1SessionsHigh OBJECT-TYPE
    SYNTAX      Counter32
    MAX-ACCESS  read-only
    STATUS      obsolete
    DESCRIPTION 
        " Total number of TLSv1 Sessions.
         high32 bits of 64bit counter."
    ::= { nsSslStatsGroup 26 }

sslTotExpiredSessionsLow OBJECT-TYPE
    SYNTAX      Counter32
    MAX-ACCESS  read-only
    STATUS      obsolete
    DESCRIPTION 
        " Total number of Expired SSL Sessions.
         low32 bits of 64bit counter."
    ::= { nsSslStatsGroup 27 }

sslTotExpiredSessionsHigh OBJECT-TYPE
    SYNTAX      Counter32
    MAX-ACCESS  read-only
    STATUS      obsolete
    DESCRIPTION 
        " Total number of Expired SSL Sessions.
         high32 bits of 64bit counter."
    ::= { nsSslStatsGroup 28 }

sslTotNewSessionsLow OBJECT-TYPE
    SYNTAX      Counter32
    MAX-ACCESS  read-only
    STATUS      obsolete
    DESCRIPTION 
        " Total number of New SSL Sessions.
         low32 bits of 64bit counter."
    ::= { nsSslStatsGroup 29 }

sslTotNewSessionsHigh OBJECT-TYPE
    SYNTAX      Counter32
    MAX-ACCESS  read-only
    STATUS      obsolete
    DESCRIPTION 
        " Total number of New SSL Sessions.
         high32 bits of 64bit counter."
    ::= { nsSslStatsGroup 30 }

sslTotSessionHitsLow OBJECT-TYPE
    SYNTAX      Counter32
    MAX-ACCESS  read-only
    STATUS      obsolete
    DESCRIPTION 
        " Total number of SSL Session Resue hits.
         low32 bits of 64bit counter."
    ::= { nsSslStatsGroup 31 }

sslTotSessionHitsHigh OBJECT-TYPE
    SYNTAX      Counter32
    MAX-ACCESS  read-only
    STATUS      obsolete
    DESCRIPTION 
        " Total number of SSL Session Reuse hits.
         high32 bits of 64bit counter."
    ::= { nsSslStatsGroup 32 }

sslTotSessionMissLow OBJECT-TYPE
    SYNTAX      Counter32
    MAX-ACCESS  read-only
    STATUS      obsolete
    DESCRIPTION 
        " Total number of SSL Session Reuse miss.
         low32 bits of 64bit counter."
    ::= { nsSslStatsGroup 33 }

sslTotSessionMissHigh OBJECT-TYPE
    SYNTAX      Counter32
    MAX-ACCESS  read-only
    STATUS      obsolete
    DESCRIPTION 
        " Total number of SSL Session Reuse miss.
         high32 bits of 64bit counter."
    ::= { nsSslStatsGroup 34 }

sslTotRenegSessionsLow OBJECT-TYPE
    SYNTAX      Counter32
    MAX-ACCESS  read-only
    STATUS      obsolete
    DESCRIPTION 
        " Total number of SSL Session Renegotiation done.
         low32 bits of 64bit counter."
    ::= { nsSslStatsGroup 35 }

sslTotRenegSessionsHigh OBJECT-TYPE
    SYNTAX      Counter32
    MAX-ACCESS  read-only
    STATUS      obsolete
    DESCRIPTION 
        " Total number of SSL Session Renegotiation done.
         high32 bits of 64bit counter."
    ::= { nsSslStatsGroup 36 }

sslTotSSLv3RenegSessionsLow OBJECT-TYPE
    SYNTAX      Counter32
    MAX-ACCESS  read-only
    STATUS      obsolete
    DESCRIPTION 
        " Total number of SSL Session Renegotiation done on SSLv3.
         low32 bits of 64bit counter."
    ::= { nsSslStatsGroup 37 }

sslTotSSLv3RenegSessionsHigh OBJECT-TYPE
    SYNTAX      Counter32
    MAX-ACCESS  read-only
    STATUS      obsolete
    DESCRIPTION 
        " Total number of SSL Session Renegotiation done on SSLv3.
         high32 bits of 64bit counter."
    ::= { nsSslStatsGroup 38 }

sslTotTLSv1RenegSessionsLow OBJECT-TYPE
    SYNTAX      Counter32
    MAX-ACCESS  read-only
    STATUS      obsolete
    DESCRIPTION 
        " Total number of SSL Session Renegotiation done on TLSv1.
         low32 bits of 64bit counter."
    ::= { nsSslStatsGroup 39 }

sslTotTLSv1RenegSessionsHigh OBJECT-TYPE
    SYNTAX      Counter32
    MAX-ACCESS  read-only
    STATUS      obsolete
    DESCRIPTION 
        " Total number of SSL Session Renegotiation done on TLSv1.
         high32 bits of 64bit counter."
    ::= { nsSslStatsGroup 40 }

sslTotSSLv2HandshakesLow OBJECT-TYPE
    SYNTAX      Counter32
    MAX-ACCESS  read-only
    STATUS      obsolete
    DESCRIPTION 
        " Total number of SSL Handshake on SSLv2.
         low32 bits of 64bit counter."
    ::= { nsSslStatsGroup 41 }

sslTotSSLv2HandshakesHigh OBJECT-TYPE
    SYNTAX      Counter32
    MAX-ACCESS  read-only
    STATUS      obsolete
    DESCRIPTION 
        " Total number of SSL Handshake on SSLv2.
         high32 bits of 64bit counter."
    ::= { nsSslStatsGroup 42 }

sslTotSSLv3HandshakesLow OBJECT-TYPE
    SYNTAX      Counter32
    MAX-ACCESS  read-only
    STATUS      obsolete
    DESCRIPTION 
        " Total number of SSL Handshake on SSLv3.
         low32 bits of 64bit counter."
    ::= { nsSslStatsGroup 43 }

sslTotSSLv3HandshakesHigh OBJECT-TYPE
    SYNTAX      Counter32
    MAX-ACCESS  read-only
    STATUS      obsolete
    DESCRIPTION 
        " Total number of SSL Handshake on SSLv3.
         high32 bits of 64bit counter."
    ::= { nsSslStatsGroup 44 }

sslTotTLSv1HandshakesLow OBJECT-TYPE
    SYNTAX      Counter32
    MAX-ACCESS  read-only
    STATUS      obsolete
    DESCRIPTION 
        " Total number of SSL Handshake on TLSv1.
         low32 bits of 64bit counter."
    ::= { nsSslStatsGroup 45 }

sslTotTLSv1HandshakesHigh OBJECT-TYPE
    SYNTAX      Counter32
    MAX-ACCESS  read-only
    STATUS      obsolete
    DESCRIPTION 
        " Total number of SSL Handshake on TLSv1.
         hig32 bits of 64bit counter."
    ::= { nsSslStatsGroup 46 }

sslTotSSLv2ClientAuthenticationsLow OBJECT-TYPE
    SYNTAX      Counter32
    MAX-ACCESS  read-only
    STATUS      obsolete
    DESCRIPTION 
        " Total number of times client authentication done on SSLv2.
         low32 bits of 64bit counter."
    ::= { nsSslStatsGroup 47 }

sslTotSSLv2ClientAuthenticationsHigh OBJECT-TYPE
    SYNTAX      Counter32
    MAX-ACCESS  read-only
    STATUS      obsolete
    DESCRIPTION 
        " Total number of times client authentication done on SSLv2.
         high32 bits of 64bit counter."
    ::= { nsSslStatsGroup 48 }

sslTotSSLv3ClientAuthenticationsLow OBJECT-TYPE
    SYNTAX      Counter32
    MAX-ACCESS  read-only
    STATUS      obsolete
    DESCRIPTION 
        " Total number of times client authentication done on SSLv3.
         low32 bits of 64bit counter."
    ::= { nsSslStatsGroup 49 }

sslTotSSLv3ClientAuthenticationsHigh OBJECT-TYPE
    SYNTAX      Counter32
    MAX-ACCESS  read-only
    STATUS      obsolete
    DESCRIPTION 
        " Total number of times client authentication done on SSLv3.
         high32 bits of 64bit counter."
    ::= { nsSslStatsGroup 50 }

sslTotTLSv1ClientAuthenticationsLow OBJECT-TYPE
    SYNTAX      Counter32
    MAX-ACCESS  read-only
    STATUS      obsolete
    DESCRIPTION 
        " Total number of times client authentication done on TLSv1.
         low32 bits of 64bit counter."
    ::= { nsSslStatsGroup 51 }

sslTotTLSv1ClientAuthenticationsHigh OBJECT-TYPE
    SYNTAX      Counter32
    MAX-ACCESS  read-only
    STATUS      obsolete
    DESCRIPTION 
        " Total number of times client authentication done on TLSv1.
         high32 bits of 64bit counter."
    ::= { nsSslStatsGroup 52 }

sslTotRSA512keyExchangesLow OBJECT-TYPE
    SYNTAX      Counter32
    MAX-ACCESS  read-only
    STATUS      obsolete
    DESCRIPTION 
        " Total number of times RSA 512 Key Exchange used.
         low32 bits of 64bit counter."
    ::= { nsSslStatsGroup 53 }

sslTotRSA512keyExchangesHigh OBJECT-TYPE
    SYNTAX      Counter32
    MAX-ACCESS  read-only
    STATUS      obsolete
    DESCRIPTION 
        " Total number of times RSA 512 Key Exchange used.
         high32 bits of 64bit counter."
    ::= { nsSslStatsGroup 54 }

sslTotRSA1024keyExchangesLow OBJECT-TYPE
    SYNTAX      Counter32
    MAX-ACCESS  read-only
    STATUS      obsolete
    DESCRIPTION 
        " Total number of times RSA 1024 Key Exchange used.
         low32 bits of 64bit counter."
    ::= { nsSslStatsGroup 55 }

sslTotRSA1024keyExchangesHigh OBJECT-TYPE
    SYNTAX      Counter32
    MAX-ACCESS  read-only
    STATUS      obsolete
    DESCRIPTION 
        " Total number of times RSA 1024 Key Exchange used.
         high32 bits of 64bit counter."
    ::= { nsSslStatsGroup 56 }

sslTotRSA2048keyExchangesLow OBJECT-TYPE
    SYNTAX      Counter32
    MAX-ACCESS  read-only
    STATUS      obsolete
    DESCRIPTION 
        " Total number of times RSA 2048 Key Exchange used.
         low32 bits of 64bit counter."
    ::= { nsSslStatsGroup 57 }

sslTotRSA2048keyExchangesHigh OBJECT-TYPE
    SYNTAX      Counter32
    MAX-ACCESS  read-only
    STATUS      obsolete
    DESCRIPTION 
        " Total number of times RSA 2048 Key Exchange used.
         high32 bits of 64bit counter."
    ::= { nsSslStatsGroup 58 }

sslTotDH512keyExchangesLow OBJECT-TYPE
    SYNTAX      Counter32
    MAX-ACCESS  read-only
    STATUS      obsolete
    DESCRIPTION 
        " Total number of times DH 512 Key Exchange used.
         low32 bits of 64bit counter."
    ::= { nsSslStatsGroup 59 }

sslTotDH512keyExchangesHigh OBJECT-TYPE
    SYNTAX      Counter32
    MAX-ACCESS  read-only
    STATUS      obsolete
    DESCRIPTION 
        " Total number of times DH 512 Key Exchange used.
         high32 bits of 64bit counter."
    ::= { nsSslStatsGroup 60 }

sslTotDH1024keyExchangesLow OBJECT-TYPE
    SYNTAX      Counter32
    MAX-ACCESS  read-only
    STATUS      obsolete
    DESCRIPTION 
        " Total number of times DH 1024 Key Exchange used.
         low32 bits of 64bit counter."
    ::= { nsSslStatsGroup 61 }

sslTotDH1024keyExchangesHigh OBJECT-TYPE
    SYNTAX      Counter32
    MAX-ACCESS  read-only
    STATUS      obsolete
    DESCRIPTION 
        " Total number of times DH 1024 Key Exchange used.
         high32 bits of 64bit counter."
    ::= { nsSslStatsGroup 62 }

sslTotDH2048keyExchangesLow OBJECT-TYPE
    SYNTAX      Counter32
    MAX-ACCESS  read-only
    STATUS      obsolete
    DESCRIPTION 
        " Total number of times DH 2048 Key Exchange used.
         low32 bits of 64bit counter."
    ::= { nsSslStatsGroup 63 }

sslTotDH2048keyExchangesHigh OBJECT-TYPE
    SYNTAX      Counter32
    MAX-ACCESS  read-only
    STATUS      obsolete
    DESCRIPTION 
        " Total number of times DH 2048 Key Exchange used.
         high32 bits of 64bit counter."
    ::= { nsSslStatsGroup 64 }

sslTotRSAAuthorizationsLow OBJECT-TYPE
    SYNTAX      Counter32
    MAX-ACCESS  read-only
    STATUS      obsolete
    DESCRIPTION 
        " Total number of times RSA authorization used.
         low32 bits of 64bit counter."
    ::= { nsSslStatsGroup 65 }

sslTotRSAAuthorizationsHigh OBJECT-TYPE
    SYNTAX      Counter32
    MAX-ACCESS  read-only
    STATUS      obsolete
    DESCRIPTION 
        " Total number of times RSA authorization used.
         high32 bits of 64bit counter."
    ::= { nsSslStatsGroup 66 }

sslTotDHAuthorizationsLow OBJECT-TYPE
    SYNTAX      Counter32
    MAX-ACCESS  read-only
    STATUS      obsolete
    DESCRIPTION 
        " Total number of times DH authorization used.
         low32 bits of 64bit counter."
    ::= { nsSslStatsGroup 67 }

sslTotDHAuthorizationsHigh OBJECT-TYPE
    SYNTAX      Counter32
    MAX-ACCESS  read-only
    STATUS      obsolete
    DESCRIPTION 
        " Total number of times DH authorization used.
         high32 bits of 64bit counter."
    ::= { nsSslStatsGroup 68 }

sslTotDSSAuthorizationsLow OBJECT-TYPE
    SYNTAX      Counter32
    MAX-ACCESS  read-only
    STATUS      obsolete
    DESCRIPTION 
        " Total number of times DSS authorization used.
         low32 bits of 64bit counter."
    ::= { nsSslStatsGroup 69 }

sslTotDSSAuthorizationsHigh OBJECT-TYPE
    SYNTAX      Counter32
    MAX-ACCESS  read-only
    STATUS      obsolete
    DESCRIPTION 
        " Total number of times DSS authorization used.
         high32 bits of 64bit counter."
    ::= { nsSslStatsGroup 70 }

sslTotNULLAuthorizationsLow OBJECT-TYPE
    SYNTAX      Counter32
    MAX-ACCESS  read-only
    STATUS      obsolete
    DESCRIPTION 
        " Total number of times NULL authorization used.
         low32 bits of 64bit counter."
    ::= { nsSslStatsGroup 71 }

sslTotNULLAuthorizationsHigh OBJECT-TYPE
    SYNTAX      Counter32
    MAX-ACCESS  read-only
    STATUS      obsolete
    DESCRIPTION 
        " Total number of times NULL authorization used.
         high32 bits of 64bit counter."
    ::= { nsSslStatsGroup 72 }

sslTot40BitRC4CiphersLow OBJECT-TYPE
    SYNTAX      Counter32
    MAX-ACCESS  read-only
    STATUS      obsolete
    DESCRIPTION 
        " Total number of times RC4 40bit cipher used.
         low32 bits of 64bit counter."
    ::= { nsSslStatsGroup 73 }

sslTot40BitRC4CiphersHigh OBJECT-TYPE
    SYNTAX      Counter32
    MAX-ACCESS  read-only
    STATUS      obsolete
    DESCRIPTION 
        " Total number of times RC4 40bit cipher used.
         high32 bits of 64bit counter."
    ::= { nsSslStatsGroup 74 }

sslTot56BitRC4CiphersLow OBJECT-TYPE
    SYNTAX      Counter32
    MAX-ACCESS  read-only
    STATUS      obsolete
    DESCRIPTION 
        " Total number of times RC4 56bit cipher used.
         low32 bits of 64bit counter."
    ::= { nsSslStatsGroup 75 }

sslTot56BitRC4CiphersHigh OBJECT-TYPE
    SYNTAX      Counter32
    MAX-ACCESS  read-only
    STATUS      obsolete
    DESCRIPTION 
        " Total number of times RC4 56bit cipher used.
         high32 bits of 64bit counter."
    ::= { nsSslStatsGroup 76 }

sslTot64BitRC4CiphersLow OBJECT-TYPE
    SYNTAX      Counter32
    MAX-ACCESS  read-only
    STATUS      obsolete
    DESCRIPTION 
        " Total number of times RC4 64bit cipher used.
         low32 bits of 64bit counter."
    ::= { nsSslStatsGroup 77 }

sslTot64BitRC4CiphersHigh OBJECT-TYPE
    SYNTAX      Counter32
    MAX-ACCESS  read-only
    STATUS      obsolete
    DESCRIPTION 
        " Total number of times RC4 64bit cipher used.
         high32 bits of 64bit counter."
    ::= { nsSslStatsGroup 78 }

sslTot128BitRC4CiphersLow OBJECT-TYPE
    SYNTAX      Counter32
    MAX-ACCESS  read-only
    STATUS      obsolete
    DESCRIPTION 
        " Total number of times RC4 128bit cipher used.
         low32 bits of 64bit counter."
    ::= { nsSslStatsGroup 79 }

sslTot128BitRC4CiphersHigh OBJECT-TYPE
    SYNTAX      Counter32
    MAX-ACCESS  read-only
    STATUS      obsolete
    DESCRIPTION 
        " Total number of times RC4 128bit cipher used.
         high32 bits of 64bit counter."
    ::= { nsSslStatsGroup 80 }

sslTot40BitDESCiphersLow OBJECT-TYPE
    SYNTAX      Counter32
    MAX-ACCESS  read-only
    STATUS      obsolete
    DESCRIPTION 
        " Total number of times DES 40bit cipher used.
         low32 bits of 64bit counter."
    ::= { nsSslStatsGroup 81 }

sslTot40BitDESCiphersHigh OBJECT-TYPE
    SYNTAX      Counter32
    MAX-ACCESS  read-only
    STATUS      obsolete
    DESCRIPTION 
        " Total number of times DES 40bit cipher used.
         high32 bits of 64bit counter."
    ::= { nsSslStatsGroup 82 }

sslTot56BitDESCiphersLow OBJECT-TYPE
    SYNTAX      Counter32
    MAX-ACCESS  read-only
    STATUS      obsolete
    DESCRIPTION 
        " Total number of times DES 56bit cipher used.
         low32 bits of 64bit counter."
    ::= { nsSslStatsGroup 83 }

sslTot56BitDESCiphersHigh OBJECT-TYPE
    SYNTAX      Counter32
    MAX-ACCESS  read-only
    STATUS      obsolete
    DESCRIPTION 
        " Total number of times DES 56bit cipher used.
         high32 bits of 64bit counter."
    ::= { nsSslStatsGroup 84 }

sslTot168Bit3DESCiphersLow OBJECT-TYPE
    SYNTAX      Counter32
    MAX-ACCESS  read-only
    STATUS      obsolete
    DESCRIPTION 
        " Total number of times  3DES 168bit cipher used.
         low32 bits of 64bit counter."
    ::= { nsSslStatsGroup 85 }

sslTot168Bit3DESCiphersHigh OBJECT-TYPE
    SYNTAX      Counter32
    MAX-ACCESS  read-only
    STATUS      obsolete
    DESCRIPTION 
        " Total number of times 3DES 168bit cipher used.
         high32 bits of 64bit counter."
    ::= { nsSslStatsGroup 86 }

sslTot40BitRC2CiphersLow OBJECT-TYPE
    SYNTAX      Counter32
    MAX-ACCESS  read-only
    STATUS      obsolete
    DESCRIPTION 
        " Total number of times RC2 40bit cipher used.
         low32 bits of 64bit counter."
    ::= { nsSslStatsGroup 87 }

sslTot40BitRC2CiphersHigh OBJECT-TYPE
    SYNTAX      Counter32
    MAX-ACCESS  read-only
    STATUS      obsolete
    DESCRIPTION 
        " Total number of times RC2 40bit cipher used.
         high32 bits of 64bit counter."
    ::= { nsSslStatsGroup 88 }

sslTot56BitRC2CiphersLow OBJECT-TYPE
    SYNTAX      Counter32
    MAX-ACCESS  read-only
    STATUS      obsolete
    DESCRIPTION 
        " Total number of times RC2 56bit cipher used.
         low32 bits of 64bit counter."
    ::= { nsSslStatsGroup 89 }

sslTot56BitRC2CiphersHigh OBJECT-TYPE
    SYNTAX      Counter32
    MAX-ACCESS  read-only
    STATUS      obsolete
    DESCRIPTION 
        " Total number of times RC2 56bit cipher used.
         high32 bits of 64bit counter."
    ::= { nsSslStatsGroup 90 }

sslTot128BitRC2CiphersLow OBJECT-TYPE
    SYNTAX      Counter32
    MAX-ACCESS  read-only
    STATUS      obsolete
    DESCRIPTION 
        " Total number of times RC2 128bit cipher used.
         low32 bits of 64bit counter."
    ::= { nsSslStatsGroup 91 }

sslTot128BitRC2CiphersHigh OBJECT-TYPE
    SYNTAX      Counter32
    MAX-ACCESS  read-only
    STATUS      obsolete
    DESCRIPTION 
        " Total number of times RC2 128bit cipher used.
         high32 bits of 64bit counter."
    ::= { nsSslStatsGroup 92 }

sslTot128BitIDEACiphersLow OBJECT-TYPE
    SYNTAX      Counter32
    MAX-ACCESS  read-only
    STATUS      obsolete
    DESCRIPTION 
        " Total number of times IDEA 128bit cipher used.
         low32 bits of 64bit counter."
    ::= { nsSslStatsGroup 93 }

sslTot128BitIDEACiphersHigh OBJECT-TYPE
    SYNTAX      Counter32
    MAX-ACCESS  read-only
    STATUS      obsolete
    DESCRIPTION 
        " Total number of times IDEA 128bit cipher used.
         high32 bits of 64bit counter."
    ::= { nsSslStatsGroup 94 }

sslTotNULLCiphersLow OBJECT-TYPE
    SYNTAX      Counter32
    MAX-ACCESS  read-only
    STATUS      obsolete
    DESCRIPTION 
        " Total number of times NULL cipher used.
         low32 bits of 64bit counter."
    ::= { nsSslStatsGroup 95 }

sslTotNULLCiphersHigh OBJECT-TYPE
    SYNTAX      Counter32
    MAX-ACCESS  read-only
    STATUS      obsolete
    DESCRIPTION 
        " Total number of times NULL cipher used.
         high32 bits of 64bit counter."
    ::= { nsSslStatsGroup 96 }

sslTotMD5MacLow OBJECT-TYPE
    SYNTAX      Counter32
    MAX-ACCESS  read-only
    STATUS      obsolete
    DESCRIPTION 
        " Total number of times MD5 MAC used.
         low32 bits of 64bit counter."
    ::= { nsSslStatsGroup 97 }

sslTotMD5MacHigh OBJECT-TYPE
    SYNTAX      Counter32
    MAX-ACCESS  read-only
    STATUS      obsolete
    DESCRIPTION 
        " Total number of times MD5 MAC used.
         high32 bits of 64bit counter."
    ::= { nsSslStatsGroup 98 }

sslTotSHAMacLow OBJECT-TYPE
    SYNTAX      Counter32
    MAX-ACCESS  read-only
    STATUS      obsolete
    DESCRIPTION 
        " Total number of times SHA MAC used.
         low32 bits of 64bit counter."
    ::= { nsSslStatsGroup 99 }

sslTotSHAMacHigh OBJECT-TYPE
    SYNTAX      Counter32
    MAX-ACCESS  read-only
    STATUS      obsolete
    DESCRIPTION 
        " Total number of times SHA MAC used.
         high32 bits of 64bit counter."
    ::= { nsSslStatsGroup 100 }

sslTotOffloadBulkDESLow OBJECT-TYPE
    SYNTAX      Counter32
    MAX-ACCESS  read-only
    STATUS      obsolete
    DESCRIPTION 
        " Total number of DES encryption offloaded to card.
         low32 bits of 64bit counter."
    ::= { nsSslStatsGroup 101 }

sslTotOffloadBulkDESHigh OBJECT-TYPE
    SYNTAX      Counter32
    MAX-ACCESS  read-only
    STATUS      obsolete
    DESCRIPTION 
        " Total number of DES encryption offloaded to card.
         high32 bits of 64bit counter."
    ::= { nsSslStatsGroup 102 }

sslTotOffloadRSAKeyExchangesLow OBJECT-TYPE
    SYNTAX      Counter32
    MAX-ACCESS  read-only
    STATUS      obsolete
    DESCRIPTION 
        " Total number of RSAKey Exchange offloaded to card.
         low32 bits of 64bit counter."
    ::= { nsSslStatsGroup 103 }

sslTotOffloadRSAKeyExchangesHigh OBJECT-TYPE
    SYNTAX      Counter32
    MAX-ACCESS  read-only
    STATUS      obsolete
    DESCRIPTION 
        " Total number of RSAKey Exchange offloaded to card.
         high32 bits of 64bit counter."
    ::= { nsSslStatsGroup 104 }

sslTotOffloadDHKeyExchangesLow OBJECT-TYPE
    SYNTAX      Counter32
    MAX-ACCESS  read-only
    STATUS      obsolete
    DESCRIPTION 
        " Total number of DHKey Exchange offloaded to card.
         low32 bits of 64bit counter."
    ::= { nsSslStatsGroup 105 }

sslTotOffloadDHKeyExchangesHigh OBJECT-TYPE
    SYNTAX      Counter32
    MAX-ACCESS  read-only
    STATUS      obsolete
    DESCRIPTION 
        " Total number of DHKey Exchange offloaded to card.
         high32 bits of 64bit counter."
    ::= { nsSslStatsGroup 106 }

sslTotOffloadSignRSALow OBJECT-TYPE
    SYNTAX      Counter32
    MAX-ACCESS  read-only
    STATUS      obsolete
    DESCRIPTION 
        " Total number of RSA sign offloaded to card.
         low32 bits of 64bit counter."
    ::= { nsSslStatsGroup 107 }

sslTotOffloadSignRSAHigh OBJECT-TYPE
    SYNTAX      Counter32
    MAX-ACCESS  read-only
    STATUS      obsolete
    DESCRIPTION 
        " Total number of RSA sign offloaded to card.
         high32 bits of 64bit counter."
    ::= { nsSslStatsGroup 108 }

sslBeTotSessionsLow OBJECT-TYPE
    SYNTAX      Counter32
    MAX-ACCESS  read-only
    STATUS      obsolete
    DESCRIPTION 
        " SSL Backend Encryption: Total number of SSL Sessions.
         low32 bits of 64bit counter."
    ::= { nsSslStatsGroup 120 }

sslBeTotSessionsHigh OBJECT-TYPE
    SYNTAX      Counter32
    MAX-ACCESS  read-only
    STATUS      obsolete
    DESCRIPTION 
        " SSL Backend Encryption: Total number of SSL Sessions.
         high32 bits of 64bit counter."
    ::= { nsSslStatsGroup 121 }

sslBeTotSSLv3SessionsLow OBJECT-TYPE
    SYNTAX      Counter32
    MAX-ACCESS  read-only
    STATUS      obsolete
    DESCRIPTION 
        " SSL Backend Encryption: Total number of SSLv3 Sessions.
         low32 bits of 64bit counter."
    ::= { nsSslStatsGroup 122 }

sslBeTotSSLv3SessionsHigh OBJECT-TYPE
    SYNTAX      Counter32
    MAX-ACCESS  read-only
    STATUS      obsolete
    DESCRIPTION 
        " SSL Backend Encryption: Total number of SSLv3 Sessions.
         high32 bits of 64bit counter."
    ::= { nsSslStatsGroup 123 }

sslBeTotTLSv1SessionsLow OBJECT-TYPE
    SYNTAX      Counter32
    MAX-ACCESS  read-only
    STATUS      obsolete
    DESCRIPTION 
        " SSL Backend Encryption: Total number of TLSv1 Sessions.
         low32 bits of 64bit counter."
    ::= { nsSslStatsGroup 124 }

sslBeTotTLSv1SessionsHigh OBJECT-TYPE
    SYNTAX      Counter32
    MAX-ACCESS  read-only
    STATUS      obsolete
    DESCRIPTION 
        " SSL Backend Encryption: Total number of TLSv1 Sessions.
         high32 bits of 64bit counter."
    ::= { nsSslStatsGroup 125 }

sslBeExpiredSessionsLow OBJECT-TYPE
    SYNTAX      Counter32
    MAX-ACCESS  read-only
    STATUS      obsolete
    DESCRIPTION 
        " SSL Backend Encryption: Total number of SSL Sessions Expired.
         low32 bits of 64bit counter."
    ::= { nsSslStatsGroup 126 }

sslBeTotExpiredSessionsHigh OBJECT-TYPE
    SYNTAX      Counter32
    MAX-ACCESS  read-only
    STATUS      obsolete
    DESCRIPTION 
        " SSL Backend Encryption: Total number of SSL Sessions Expired.
         high32 bits of 64bit counter."
    ::= { nsSslStatsGroup 127 }

sslBeTotSessionMultiplexAttemptsLow OBJECT-TYPE
    SYNTAX      Counter32
    MAX-ACCESS  read-only
    STATUS      obsolete
    DESCRIPTION 
        " SSL Backend Encryption: Total number of SSL Session Multiplexing 
         attempts. low32 bits of 64bit counter."
    ::= { nsSslStatsGroup 128 }

sslBeTotSessionMultiplexAttemptsHigh OBJECT-TYPE
    SYNTAX      Counter32
    MAX-ACCESS  read-only
    STATUS      obsolete
    DESCRIPTION 
        " SSL Backend Encryption: Total number of SSL Session Multiplexing 
         attempts. high32 bits of 64bit counter."
    ::= { nsSslStatsGroup 129 }

sslBeTotSessionMultiplexAttemptSuccessLow OBJECT-TYPE
    SYNTAX      Counter32
    MAX-ACCESS  read-only
    STATUS      obsolete
    DESCRIPTION 
        " SSL Backend Encryption: Total number of SSL Session Multiplexing 
         attempt Successful. low32 bits of 64bit counter."
    ::= { nsSslStatsGroup 130 }

sslBeTotSessionMultiplexAttemptSuccessHigh OBJECT-TYPE
    SYNTAX      Counter32
    MAX-ACCESS  read-only
    STATUS      obsolete
    DESCRIPTION 
        " SSL Backend Encryption: Total number of SSL Session Multiplexing 
         attempt Successful. high32 bits of 64bit counter."
    ::= { nsSslStatsGroup 131 }

sslBeTotSessionMultiplexAttemptFailsLow OBJECT-TYPE
    SYNTAX      Counter32
    MAX-ACCESS  read-only
    STATUS      obsolete
    DESCRIPTION 
        " SSL Backend Encryption: Total number of SSL Session Multiplexing 
         attempt Failure. low32 bits of 64bit counter."
    ::= { nsSslStatsGroup 132 }

sslBeTotSessionMultiplexAttemptFailsHigh OBJECT-TYPE
    SYNTAX      Counter32
    MAX-ACCESS  read-only
    STATUS      obsolete
    DESCRIPTION 
        " SSL Backend Encryption: Total number of SSL Session Multiplexing 
         attempt Failure. high32 bits of 64bit counter."
    ::= { nsSslStatsGroup 133 }

sslBeMaxMultiplexedSessionsLow OBJECT-TYPE
    SYNTAX      Counter32
    MAX-ACCESS  read-only
    STATUS      obsolete
    DESCRIPTION 
        " SSL Backend Encryption: Total number of SSL Session Multiplexing.
         low32 bits of 64bit counter."
    ::= { nsSslStatsGroup 134 }

sslBeMaxMultiplexedSessionsHigh OBJECT-TYPE
    SYNTAX      Counter32
    MAX-ACCESS  read-only
    STATUS      obsolete
    DESCRIPTION 
        " SSL Backend Encryption: Total number of SSL Session Multiplexing.
         high32 bits of 64bit counter."
    ::= { nsSslStatsGroup 135 }

sslBeSessionsReplacedLow OBJECT-TYPE
    SYNTAX      Counter32
    MAX-ACCESS  read-only
    STATUS      obsolete
    DESCRIPTION 
        "..."
    ::= { nsSslStatsGroup 136 }

sslBeSessionsReplacedHigh OBJECT-TYPE
    SYNTAX      Counter32
    MAX-ACCESS  read-only
    STATUS      obsolete
    DESCRIPTION 
        "..."
    ::= { nsSslStatsGroup 137 }

sslBeTotSSLv3HandshakesLow OBJECT-TYPE
    SYNTAX      Counter32
    MAX-ACCESS  read-only
    STATUS      obsolete
    DESCRIPTION 
        " SSL Backend Encryption: Total number of SSLv3 Handshake.
         low32 bits of 64bit counter."
    ::= { nsSslStatsGroup 138 }

sslBeTotSSLv3HandshakesHigh OBJECT-TYPE
    SYNTAX      Counter32
    MAX-ACCESS  read-only
    STATUS      obsolete
    DESCRIPTION 
        " SSL Backend Encryption: Total number of SSLv3 Handshake.
         high32 bits of 64bit counter."
    ::= { nsSslStatsGroup 139 }

sslBeTotTLSv1HandshakesLow OBJECT-TYPE
    SYNTAX      Counter32
    MAX-ACCESS  read-only
    STATUS      obsolete
    DESCRIPTION 
        " SSL Backend Encryption: Total number of TLSv1 Handshake.
         low32 bits of 64bit counter."
    ::= { nsSslStatsGroup 140 }

sslBeTotTLSv1HandshakesHigh OBJECT-TYPE
    SYNTAX      Counter32
    MAX-ACCESS  read-only
    STATUS      obsolete
    DESCRIPTION 
        " SSL Backend Encryption: Total number of TLSv1 Handshake.
         high32 bits of 64bit counter."
    ::= { nsSslStatsGroup 141 }

sslBeTotSSLv3ClientAuthenticationsLow OBJECT-TYPE
    SYNTAX      Counter32
    MAX-ACCESS  read-only
    STATUS      obsolete
    DESCRIPTION 
        " SSL Backend Encryption: Total number of SSLv3 Client Authentication.
         low32 bits of 64bit counter."
    ::= { nsSslStatsGroup 142 }

sslBeTotSSLv3ClientAuthenticationsHigh OBJECT-TYPE
    SYNTAX      Counter32
    MAX-ACCESS  read-only
    STATUS      obsolete
    DESCRIPTION 
        " SSL Backend Encryption: Total number of SSLv3 Client Authentication.
         high32 bits of 64bit counter."
    ::= { nsSslStatsGroup 143 }

sslBeTotTLSv1ClientAuthenticationsLow OBJECT-TYPE
    SYNTAX      Counter32
    MAX-ACCESS  read-only
    STATUS      obsolete
    DESCRIPTION 
        " SSL Backend Encryption: Total number of TLSv1 Client Authentication.
         low32 bits of 64bit counter."
    ::= { nsSslStatsGroup 144 }

sslBeTotTLSv1ClientAuthenticationsHigh OBJECT-TYPE
    SYNTAX      Counter32
    MAX-ACCESS  read-only
    STATUS      obsolete
    DESCRIPTION 
        " SSL Backend Encryption: Total number of TLSv1 Client Authentication.
         high32 bits of 64bit counter."
    ::= { nsSslStatsGroup 145 }

sslBeTotRSA512keyExchangesLow OBJECT-TYPE
    SYNTAX      Counter32
    MAX-ACCESS  read-only
    STATUS      obsolete
    DESCRIPTION 
        " SSL Backend Encryption: Total number of RSA 512bit Key Exchange.
         low32 bits of 64bit counter."
    ::= { nsSslStatsGroup 146 }

sslBeTotRSA512keyExchangesHigh OBJECT-TYPE
    SYNTAX      Counter32
    MAX-ACCESS  read-only
    STATUS      obsolete
    DESCRIPTION 
        " SSL Backend Encryption: Total number of RSA 512bit Key Exchange.
         high32 bits of 64bit counter."
    ::= { nsSslStatsGroup 147 }

sslBeTotRSA1024keyExchangesLow OBJECT-TYPE
    SYNTAX      Counter32
    MAX-ACCESS  read-only
    STATUS      obsolete
    DESCRIPTION 
        " SSL Backend Encryption: Total number of RSA 1024bit Key Exchange.
         low32 bits of 64bit counter."
    ::= { nsSslStatsGroup 148 }

sslBeTotRSA1024keyExchangesHigh OBJECT-TYPE
    SYNTAX      Counter32
    MAX-ACCESS  read-only
    STATUS      obsolete
    DESCRIPTION 
        " SSL Backend Encryption: Total number of RSA 1024bit Key Exchange.
         high32 bits of 64bit counter."
    ::= { nsSslStatsGroup 149 }

sslBeTotRSA2048keyExchangesLow OBJECT-TYPE
    SYNTAX      Counter32
    MAX-ACCESS  read-only
    STATUS      obsolete
    DESCRIPTION 
        " SSL Backend Encryption: Total number of RSA 2048bit Key Exchange.
         low32 bits of 64bit counter."
    ::= { nsSslStatsGroup 150 }

sslBeTotRSA2048keyExchangesHigh OBJECT-TYPE
    SYNTAX      Counter32
    MAX-ACCESS  read-only
    STATUS      obsolete
    DESCRIPTION 
        " SSL Backend Encryption: Total number of RSA 2048bit Key Exchange.
         high32 bits of 64bit counter."
    ::= { nsSslStatsGroup 151 }

sslBeTotDH512keyExchangesLow OBJECT-TYPE
    SYNTAX      Counter32
    MAX-ACCESS  read-only
    STATUS      obsolete
    DESCRIPTION 
        " SSL Backend Encryption: Total number of DH 512bit Key Exchange.
         low32 bits of 64bit counter."
    ::= { nsSslStatsGroup 152 }

sslBeTotDH512keyExchangesHigh OBJECT-TYPE
    SYNTAX      Counter32
    MAX-ACCESS  read-only
    STATUS      obsolete
    DESCRIPTION 
        " SSL Backend Encryption: Total number of DH 512bit Key Exchange.
         high32 bits of 64bit counter."
    ::= { nsSslStatsGroup 153 }

sslBeTotDH1024keyExchangesLow OBJECT-TYPE
    SYNTAX      Counter32
    MAX-ACCESS  read-only
    STATUS      obsolete
    DESCRIPTION 
        " SSL Backend Encryption: Total number of DH 1024bit Key Exchange.
         low32 bits of 64bit counter."
    ::= { nsSslStatsGroup 154 }

sslBeTotDH1024keyExchangesHigh OBJECT-TYPE
    SYNTAX      Counter32
    MAX-ACCESS  read-only
    STATUS      obsolete
    DESCRIPTION 
        " SSL Backend Encryption: Total number of DH 1024bit Key Exchange.
         high32 bits of 64bit counter."
    ::= { nsSslStatsGroup 155 }

sslBeTotDH2048keyExchangesLow OBJECT-TYPE
    SYNTAX      Counter32
    MAX-ACCESS  read-only
    STATUS      obsolete
    DESCRIPTION 
        " SSL Backend Encryption: Total number of DH 2048bit Key Exchange.
         low32 bits of 64bit counter."
    ::= { nsSslStatsGroup 156 }

sslBeTotDH2048keyExchangesHigh OBJECT-TYPE
    SYNTAX      Counter32
    MAX-ACCESS  read-only
    STATUS      obsolete
    DESCRIPTION 
        " SSL Backend Encryption: Total number of DH 2048bit Key Exchange.
         high32 bits of 64bit counter."
    ::= { nsSslStatsGroup 157 }

sslBeTotRSAAuthorizationsLow OBJECT-TYPE
    SYNTAX      Counter32
    MAX-ACCESS  read-only
    STATUS      obsolete
    DESCRIPTION 
        " SSL Backend Encryption: Total number of times RSA Authorization used.
         low32 bits of 64bit counter."
    ::= { nsSslStatsGroup 158 }

sslBeTotRSAAuthorizationsHigh OBJECT-TYPE
    SYNTAX      Counter32
    MAX-ACCESS  read-only
    STATUS      obsolete
    DESCRIPTION 
        " SSL Backend Encryption: Total number of times RSA Authorization used.
         high32 bits of 64bit counter."
    ::= { nsSslStatsGroup 159 }

sslBeTotDHAuthorizationsLow OBJECT-TYPE
    SYNTAX      Counter32
    MAX-ACCESS  read-only
    STATUS      obsolete
    DESCRIPTION 
        " SSL Backend Encryption: Total number of times DH Authorization used.
         low32 bits of 64bit counter."
    ::= { nsSslStatsGroup 160 }

sslBeTotDHAuthorizationsHigh OBJECT-TYPE
    SYNTAX      Counter32
    MAX-ACCESS  read-only
    STATUS      obsolete
    DESCRIPTION 
        " SSL Backend Encryption: Total number of times DH Authorization used.
         high32 bits of 64bit counter."
    ::= { nsSslStatsGroup 161 }

sslBeTotDSSAuthorizationsLow OBJECT-TYPE
    SYNTAX      Counter32
    MAX-ACCESS  read-only
    STATUS      obsolete
    DESCRIPTION 
        " SSL Backend Encryption: Total number of times DSS Authorization used.
         low32 bits of 64bit counter."
    ::= { nsSslStatsGroup 162 }

sslBeTotDSSAuthorizationsHigh OBJECT-TYPE
    SYNTAX      Counter32
    MAX-ACCESS  read-only
    STATUS      obsolete
    DESCRIPTION 
        " SSL Backend Encryption: Total number of times DSS Authorization used.
         high32 bits of 64bit counter."
    ::= { nsSslStatsGroup 163 }

sslBeTotNULLAuthorizationsLow OBJECT-TYPE
    SYNTAX      Counter32
    MAX-ACCESS  read-only
    STATUS      obsolete
    DESCRIPTION 
        " SSL Backend Encryption: Total number of times NULL Authorization used.
         low32 bits of 64bit counter."
    ::= { nsSslStatsGroup 164 }

sslBeTotNULLAuthorizationsHigh OBJECT-TYPE
    SYNTAX      Counter32
    MAX-ACCESS  read-only
    STATUS      obsolete
    DESCRIPTION 
        " SSL Backend Encryption: Total number of times NULL Authorization used.
         high32 bits of 64bit counter."
    ::= { nsSslStatsGroup 165 }

sslBeTot40BitRC4CiphersLow OBJECT-TYPE
    SYNTAX      Counter32
    MAX-ACCESS  read-only
    STATUS      obsolete
    DESCRIPTION 
        " SSL Backend Encryption:  Total number of times 40bit RC4 cipher used.
         low32 bits of 64bit counter."
    ::= { nsSslStatsGroup 166 }

sslBeTot40BitRC4CiphersHigh OBJECT-TYPE
    SYNTAX      Counter32
    MAX-ACCESS  read-only
    STATUS      obsolete
    DESCRIPTION 
        " SSL Backend Encryption: Total number of times 40bit RC4 cipher used.
         high32 bits of 64bit counter."
    ::= { nsSslStatsGroup 167 }

sslBeTot56BitRC4CiphersLow OBJECT-TYPE
    SYNTAX      Counter32
    MAX-ACCESS  read-only
    STATUS      obsolete
    DESCRIPTION 
        " SSL Backend Encryption: Total number of times 56bit RC4 cipher used.
         low32 bits of 64bit counter."
    ::= { nsSslStatsGroup 168 }

sslBeTot56BitRC4CiphersHigh OBJECT-TYPE
    SYNTAX      Counter32
    MAX-ACCESS  read-only
    STATUS      obsolete
    DESCRIPTION 
        " SSL Backend Encryption: Total number of times 56bit RC4 cipher used.
         high32 bits of 64bit counter."
    ::= { nsSslStatsGroup 169 }

sslBeTot64BitRC4CiphersLow OBJECT-TYPE
    SYNTAX      Counter32
    MAX-ACCESS  read-only
    STATUS      obsolete
    DESCRIPTION 
        " SSL Backend Encryption: Total number of times 64bit RC4 cipher used.
         low32 bits of 64bit counter."
    ::= { nsSslStatsGroup 170 }

sslBeTot64BitRC4CiphersHigh OBJECT-TYPE
    SYNTAX      Counter32
    MAX-ACCESS  read-only
    STATUS      obsolete
    DESCRIPTION 
        " SSL Backend Encryption: Total number of times 64bit RC4 cipher used.
         high32 bits of 64bit counter."
    ::= { nsSslStatsGroup 171 }

sslBeTot128BitRC4CiphersLow OBJECT-TYPE
    SYNTAX      Counter32
    MAX-ACCESS  read-only
    STATUS      obsolete
    DESCRIPTION 
        " SSL Backend Encryption: Total number of times 128bit RC4 cipher used.
         low32 bits of 64bit counter."
    ::= { nsSslStatsGroup 172 }

sslBeTot128BitRC4CiphersHigh OBJECT-TYPE
    SYNTAX      Counter32
    MAX-ACCESS  read-only
    STATUS      obsolete
    DESCRIPTION 
        " SSL Backend Encryption: Total number of times 128bit RC4 cipher used.
         high32 bits of 64bit counter."
    ::= { nsSslStatsGroup 173 }

sslBeTot40BitDESCiphersLow OBJECT-TYPE
    SYNTAX      Counter32
    MAX-ACCESS  read-only
    STATUS      obsolete
    DESCRIPTION 
        " SSL Backend Encryption: Total number of times 40bit DES cipher used.
         low32 bits of 64bit counter."
    ::= { nsSslStatsGroup 174 }

sslBeTot40BitDESCiphersHigh OBJECT-TYPE
    SYNTAX      Counter32
    MAX-ACCESS  read-only
    STATUS      obsolete
    DESCRIPTION 
        " SSL Backend Encryption: Total number of times 40bit DES cipher used.
         high32 bits of 64bit counter."
    ::= { nsSslStatsGroup 175 }

sslBeTot56BitDESCiphersLow OBJECT-TYPE
    SYNTAX      Counter32
    MAX-ACCESS  read-only
    STATUS      obsolete
    DESCRIPTION 
        " SSL Backend Encryption: Total number of times 56bit DES cipher used.
         low32 bits of 64bit counter."
    ::= { nsSslStatsGroup 176 }

sslBeTot56BitDESCiphersHigh OBJECT-TYPE
    SYNTAX      Counter32
    MAX-ACCESS  read-only
    STATUS      obsolete
    DESCRIPTION 
        " SSL Backend Encryption: Total number of times 56bit DES cipher used.
         high32 bits of 64bit counter."
    ::= { nsSslStatsGroup 177 }

sslBeTot168Bit3DESCiphersLow OBJECT-TYPE
    SYNTAX      Counter32
    MAX-ACCESS  read-only
    STATUS      obsolete
    DESCRIPTION 
        " SSL Backend Encryption: Total number of times 168bit 3DES cipher used.
         low32 bits of 64bit counter."
    ::= { nsSslStatsGroup 178 }

sslBeTot168Bit3DESCiphersHigh OBJECT-TYPE
    SYNTAX      Counter32
    MAX-ACCESS  read-only
    STATUS      obsolete
    DESCRIPTION 
        " SSL Backend Encryption: Total number of times 168bit 3DES cipher used.
         high32 bits of 64bit counter."
    ::= { nsSslStatsGroup 179 }

sslBeTot40BitRC2CiphersLow OBJECT-TYPE
    SYNTAX      Counter32
    MAX-ACCESS  read-only
    STATUS      obsolete
    DESCRIPTION 
        " SSL Backend Encryption: Total number of times 40bit RC2 cipher used.
         low32 bits of 64bit counter."
    ::= { nsSslStatsGroup 180 }

sslBeTot40BitRC2CiphersHigh OBJECT-TYPE
    SYNTAX      Counter32
    MAX-ACCESS  read-only
    STATUS      obsolete
    DESCRIPTION 
        " SSL Backend Encryption: Total number of times 40bit RC2 cipher used.
         high32 bits of 64bit counter."
    ::= { nsSslStatsGroup 181 }

sslBeTot56BitRC2CiphersLow OBJECT-TYPE
    SYNTAX      Counter32
    MAX-ACCESS  read-only
    STATUS      obsolete
    DESCRIPTION 
        " SSL Backend Encryption: Total number of times 56bit RC2 cipher used.
         low32 bits of 64bit counter."
    ::= { nsSslStatsGroup 182 }

sslBeTot56BitRC2CiphersHigh OBJECT-TYPE
    SYNTAX      Counter32
    MAX-ACCESS  read-only
    STATUS      obsolete
    DESCRIPTION 
        " SSL Backend Encryption: Total number of times 56bit RC2 cipher used.
         high32 bits of 64bit counter."
    ::= { nsSslStatsGroup 183 }

sslBeTot128BitRC2CiphersLow OBJECT-TYPE
    SYNTAX      Counter32
    MAX-ACCESS  read-only
    STATUS      obsolete
    DESCRIPTION 
        " SSL Backend Encryption: Total number of times 128bit RC2 cipher used.
         low32 bits of 64bit counter."
    ::= { nsSslStatsGroup 184 }

sslBeTot128BitRC2CiphersHigh OBJECT-TYPE
    SYNTAX      Counter32
    MAX-ACCESS  read-only
    STATUS      obsolete
    DESCRIPTION 
        " SSL Backend Encryption: Total number of times 128bit RC2 cipher used.
         high32 bits of 64bit counter."
    ::= { nsSslStatsGroup 185 }

sslBeTot128BitIDEACiphersLow OBJECT-TYPE
    SYNTAX      Counter32
    MAX-ACCESS  read-only
    STATUS      obsolete
    DESCRIPTION 
        " SSL Backend Encryption: Total number of times 128bit IDEA cipher used.
         low32 bits of 64bit counter."
    ::= { nsSslStatsGroup 186 }

sslBeTot128BitIDEACiphersHigh OBJECT-TYPE
    SYNTAX      Counter32
    MAX-ACCESS  read-only
    STATUS      obsolete
    DESCRIPTION 
        " SSL Backend Encryption: Total number of times 128bit IDEA cipher used.
         high32 bits of 64bit counter."
    ::= { nsSslStatsGroup 187 }

sslBeTotNULLCiphersLow OBJECT-TYPE
    SYNTAX      Counter32
    MAX-ACCESS  read-only
    STATUS      obsolete
    DESCRIPTION 
        " SSL Backend Encryption: Total number of times NULL cipher used.
         low32 bits of 64bit counter."
    ::= { nsSslStatsGroup 188 }

sslBeTotNULLCiphersHigh OBJECT-TYPE
    SYNTAX      Counter32
    MAX-ACCESS  read-only
    STATUS      obsolete
    DESCRIPTION 
        " SSL Backend Encryption: Total number of times NULL cipher used.
         high32 bits of 64bit counter."
    ::= { nsSslStatsGroup 189 }

sslBeTotMD5MacLow OBJECT-TYPE
    SYNTAX      Counter32
    MAX-ACCESS  read-only
    STATUS      obsolete
    DESCRIPTION 
        " SSL Backend Encryption: Total number of times MD5 MAC used.
         low32 bits of 64bit counter."
    ::= { nsSslStatsGroup 190 }

sslBeTotMD5MacHigh OBJECT-TYPE
    SYNTAX      Counter32
    MAX-ACCESS  read-only
    STATUS      obsolete
    DESCRIPTION 
        " SSL Backend Encryption: Total number of times MD5 MAC used.
         high32 bits of 64bit counter."
    ::= { nsSslStatsGroup 191 }

sslBeTotSHAMacLow OBJECT-TYPE
    SYNTAX      Counter32
    MAX-ACCESS  read-only
    STATUS      obsolete
    DESCRIPTION 
        " SSL Backend Encryption: Total number of times SHA MAC used.				  
         low32 bits of 64bit counter."
    ::= { nsSslStatsGroup 192 }

sslBeTotSHAMacHigh OBJECT-TYPE
    SYNTAX      Counter32
    MAX-ACCESS  read-only
    STATUS      obsolete
    DESCRIPTION 
        " SSL Backend Encryption: Total number of times SHA MAC used.
         high32 bits of 64bit counter."
    ::= { nsSslStatsGroup 193 }
                               
sslTotTransactions OBJECT-TYPE
    SYNTAX      Counter64
    MAX-ACCESS  read-only
    STATUS      current
    DESCRIPTION 
        " Total number of SSL Transactions.
         "
    ::= { nsSslStatsGroup 200 }

sslTotSSLv2Transactions OBJECT-TYPE
    SYNTAX      Counter64
    MAX-ACCESS  read-only
    STATUS      current
    DESCRIPTION 
        " Total number of SSLv2 Transactions.
         "
    ::= { nsSslStatsGroup 201 }

sslTotSSLv3Transactions OBJECT-TYPE
    SYNTAX      Counter64
    MAX-ACCESS  read-only
    STATUS      current
    DESCRIPTION 
        " Total number of SSLv3 Transactions.
         "
    ::= { nsSslStatsGroup 202 }

sslTotTLSv1Transactions OBJECT-TYPE
    SYNTAX      Counter64
    MAX-ACCESS  read-only
    STATUS      current
    DESCRIPTION 
        " Total number of TLSv1 Transactions.
         "
    ::= { nsSslStatsGroup 203 }

sslTotSessions OBJECT-TYPE
    SYNTAX      Counter64
    MAX-ACCESS  read-only
    STATUS      current
    DESCRIPTION 
        " Total number of SSL Sessions.
         "
    ::= { nsSslStatsGroup 204 }

sslTotSSLv2Sessions OBJECT-TYPE
    SYNTAX      Counter64
    MAX-ACCESS  read-only
    STATUS      current
    DESCRIPTION 
        " Total number of SSLv2 Sessions.
         "
    ::= { nsSslStatsGroup 205 }

sslTotSSLv3Sessions OBJECT-TYPE
    SYNTAX      Counter64
    MAX-ACCESS  read-only
    STATUS      current
    DESCRIPTION 
        " Total number of SSLv3 Sessions.
         "
    ::= { nsSslStatsGroup 206 }

sslTotTLSv1Sessions OBJECT-TYPE
    SYNTAX      Counter64
    MAX-ACCESS  read-only
    STATUS      current
    DESCRIPTION 
        " Total number of TLSv1 Sessions.
         "
    ::= { nsSslStatsGroup 207 }

sslTotExpiredSessions OBJECT-TYPE
    SYNTAX      Counter64
    MAX-ACCESS  read-only
    STATUS      current
    DESCRIPTION 
        " Total number of Expired SSL Sessions.
         "
    ::= { nsSslStatsGroup 208 }

sslTotNewSessions OBJECT-TYPE
    SYNTAX      Counter64
    MAX-ACCESS  read-only
    STATUS      current
    DESCRIPTION 
        " Total number of New SSL Sessions.
         "
    ::= { nsSslStatsGroup 209 }

sslTotSessionHits OBJECT-TYPE
    SYNTAX      Counter64
    MAX-ACCESS  read-only
    STATUS      current
    DESCRIPTION 
        " Total number of SSL Session Resue hits.
         "
    ::= { nsSslStatsGroup 210 }

sslTotSessionMiss OBJECT-TYPE
    SYNTAX      Counter64
    MAX-ACCESS  read-only
    STATUS      current
    DESCRIPTION 
        " Total number of SSL Session Reuse miss.
         "
    ::= { nsSslStatsGroup 211 }

sslTotRenegSessions OBJECT-TYPE
    SYNTAX      Counter64
    MAX-ACCESS  read-only
    STATUS      current
    DESCRIPTION 
        " Total number of SSL Session Renegotiation done.
         "
    ::= { nsSslStatsGroup 212 }

sslTotSSLv3RenegSessions OBJECT-TYPE
    SYNTAX      Counter64
    MAX-ACCESS  read-only
    STATUS      current
    DESCRIPTION 
        " Total number of SSL Session Renegotiation done on SSLv3.
         "
    ::= { nsSslStatsGroup 213 }

sslTotTLSv1RenegSessions OBJECT-TYPE
    SYNTAX      Counter64
    MAX-ACCESS  read-only
    STATUS      current
    DESCRIPTION 
        " Total number of SSL Session Renegotiation done on TLSv1.
         "
    ::= { nsSslStatsGroup 214 }

sslTotSSLv2Handshakes OBJECT-TYPE
    SYNTAX      Counter64
    MAX-ACCESS  read-only
    STATUS      current
    DESCRIPTION 
        " Total number of SSL Handshake on SSLv2.
         "
    ::= { nsSslStatsGroup 215 }

sslTotSSLv3Handshakes OBJECT-TYPE
    SYNTAX      Counter64
    MAX-ACCESS  read-only
    STATUS      current
    DESCRIPTION 
        " Total number of SSL Handshake on SSLv3.
         "
    ::= { nsSslStatsGroup 216 }

sslTotTLSv1Handshakes OBJECT-TYPE
    SYNTAX      Counter64
    MAX-ACCESS  read-only
    STATUS      current
    DESCRIPTION 
        " Total number of SSL Handshake on TLSv1.
         "
    ::= { nsSslStatsGroup 217 }

sslTotSSLv2ClientAuthentications OBJECT-TYPE
    SYNTAX      Counter64
    MAX-ACCESS  read-only
    STATUS      current
    DESCRIPTION 
        " Total number of times client authentication done on SSLv2.
         "
    ::= { nsSslStatsGroup 218 }

sslTotSSLv3ClientAuthentications OBJECT-TYPE
    SYNTAX      Counter64
    MAX-ACCESS  read-only
    STATUS      current
    DESCRIPTION 
        " Total number of times client authentication done on SSLv3.
         "
    ::= { nsSslStatsGroup 219 }

sslTotTLSv1ClientAuthentications OBJECT-TYPE
    SYNTAX      Counter64
    MAX-ACCESS  read-only
    STATUS      current
    DESCRIPTION 
        " Total number of times client authentication done on TLSv1.
         "
    ::= { nsSslStatsGroup 220 }

sslTotRSA512keyExchanges OBJECT-TYPE
    SYNTAX      Counter64
    MAX-ACCESS  read-only
    STATUS      current
    DESCRIPTION 
        " Total number of times RSA 512 Key Exchange used.
         "
    ::= { nsSslStatsGroup 221 }

sslTotRSA1024keyExchanges OBJECT-TYPE
    SYNTAX      Counter64
    MAX-ACCESS  read-only
    STATUS      current
    DESCRIPTION 
        " Total number of times RSA 1024 Key Exchange used.
         "
    ::= { nsSslStatsGroup 222 }

sslTotRSA2048keyExchanges OBJECT-TYPE
    SYNTAX      Counter64
    MAX-ACCESS  read-only
    STATUS      current
    DESCRIPTION 
        " Total number of times RSA 2048 Key Exchange used.
         "
    ::= { nsSslStatsGroup 223 }

sslTotDH512keyExchanges OBJECT-TYPE
    SYNTAX      Counter64
    MAX-ACCESS  read-only
    STATUS      current
    DESCRIPTION 
        " Total number of times DH 512 Key Exchange used.
         "
    ::= { nsSslStatsGroup 224 }

sslTotDH1024keyExchanges OBJECT-TYPE
    SYNTAX      Counter64
    MAX-ACCESS  read-only
    STATUS      current
    DESCRIPTION 
        " Total number of times DH 1024 Key Exchange used.
         "
    ::= { nsSslStatsGroup 225 }

sslTotDH2048keyExchanges OBJECT-TYPE
    SYNTAX      Counter64
    MAX-ACCESS  read-only
    STATUS      current
    DESCRIPTION 
        " Total number of times DH 2048 Key Exchange used.
         "
    ::= { nsSslStatsGroup 226 }

sslTotRSAAuthorizations OBJECT-TYPE
    SYNTAX      Counter64
    MAX-ACCESS  read-only
    STATUS      current
    DESCRIPTION 
        " Total number of times RSA authorization used.
         "
    ::= { nsSslStatsGroup 227 }

sslTotDHAuthorizations OBJECT-TYPE
    SYNTAX      Counter64
    MAX-ACCESS  read-only
    STATUS      current
    DESCRIPTION 
        " Total number of times DH authorization used.
         "
    ::= { nsSslStatsGroup 228 }

sslTotDSSAuthorizations OBJECT-TYPE
    SYNTAX      Counter64
    MAX-ACCESS  read-only
    STATUS      current
    DESCRIPTION 
        " Total number of times DSS authorization used.
         "
    ::= { nsSslStatsGroup 229 }

sslTotNULLAuthorizations OBJECT-TYPE
    SYNTAX      Counter64
    MAX-ACCESS  read-only
    STATUS      current
    DESCRIPTION 
        " Total number of times NULL authorization used.
         "
    ::= { nsSslStatsGroup 230 }

sslTot40BitRC4Ciphers OBJECT-TYPE
    SYNTAX      Counter64
    MAX-ACCESS  read-only
    STATUS      current
    DESCRIPTION 
        " Total number of times RC4 40bit cipher used.
         "
    ::= { nsSslStatsGroup 231 }

sslTot56BitRC4Ciphers OBJECT-TYPE
    SYNTAX      Counter64
    MAX-ACCESS  read-only
    STATUS      current
    DESCRIPTION 
        " Total number of times RC4 56bit cipher used.
         "
    ::= { nsSslStatsGroup 232 }

sslTot64BitRC4Ciphers OBJECT-TYPE
    SYNTAX      Counter64
    MAX-ACCESS  read-only
    STATUS      current
    DESCRIPTION 
        " Total number of times RC4 64bit cipher used.
         "
    ::= { nsSslStatsGroup 233 }

sslTot128BitRC4Ciphers OBJECT-TYPE
    SYNTAX      Counter64
    MAX-ACCESS  read-only
    STATUS      current
    DESCRIPTION 
        " Total number of times RC4 128bit cipher used.
         "
    ::= { nsSslStatsGroup 234 }

sslTot40BitDESCiphers OBJECT-TYPE
    SYNTAX      Counter64
    MAX-ACCESS  read-only
    STATUS      current
    DESCRIPTION 
        " Total number of times DES 40bit cipher used.
         "
    ::= { nsSslStatsGroup 235 }

sslTot56BitDESCiphers OBJECT-TYPE
    SYNTAX      Counter64
    MAX-ACCESS  read-only
    STATUS      current
    DESCRIPTION 
        " Total number of times DES 56bit cipher used.
         "
    ::= { nsSslStatsGroup 236 }

sslTot168Bit3DESCiphers OBJECT-TYPE
    SYNTAX      Counter64
    MAX-ACCESS  read-only
    STATUS      current
    DESCRIPTION 
        " Total number of times  3DES 168bit cipher used.
         "
    ::= { nsSslStatsGroup 237 }

sslTot40BitRC2Ciphers OBJECT-TYPE
    SYNTAX      Counter64
    MAX-ACCESS  read-only
    STATUS      current
    DESCRIPTION 
        " Total number of times RC2 40bit cipher used.
         "
    ::= { nsSslStatsGroup 238 }

sslTot56BitRC2Ciphers OBJECT-TYPE
    SYNTAX      Counter64
    MAX-ACCESS  read-only
    STATUS      current
    DESCRIPTION 
        " Total number of times RC2 56bit cipher used.
         "
    ::= { nsSslStatsGroup 239 }

sslTot128BitRC2Ciphers OBJECT-TYPE
    SYNTAX      Counter64
    MAX-ACCESS  read-only
    STATUS      current
    DESCRIPTION 
        " Total number of times RC2 128bit cipher used.
         "
    ::= { nsSslStatsGroup 240 }

sslTot128BitIDEACiphers OBJECT-TYPE
    SYNTAX      Counter64
    MAX-ACCESS  read-only
    STATUS      current
    DESCRIPTION 
        " Total number of times IDEA 128bit cipher used.
         "
    ::= { nsSslStatsGroup 241 }

sslTotNULLCiphers OBJECT-TYPE
    SYNTAX      Counter64
    MAX-ACCESS  read-only
    STATUS      current
    DESCRIPTION 
        " Total number of times NULL cipher used.
         "
    ::= { nsSslStatsGroup 242 }

sslTotMD5Mac OBJECT-TYPE
    SYNTAX      Counter64
    MAX-ACCESS  read-only
    STATUS      current
    DESCRIPTION 
        " Total number of times MD5 MAC used.
         "
    ::= { nsSslStatsGroup 243 }

sslTotSHAMac OBJECT-TYPE
    SYNTAX      Counter64
    MAX-ACCESS  read-only
    STATUS      current
    DESCRIPTION 
        " Total number of times SHA MAC used.
         "
    ::= { nsSslStatsGroup 244 }

sslTotOffloadBulkDES OBJECT-TYPE
    SYNTAX      Counter64
    MAX-ACCESS  read-only
    STATUS      current
    DESCRIPTION 
        " Total number of DES encryption offloaded to card.
         "
    ::= { nsSslStatsGroup 245 }

sslTotOffloadRSAKeyExchanges OBJECT-TYPE
    SYNTAX      Counter64
    MAX-ACCESS  read-only
    STATUS      current
    DESCRIPTION 
        " Total number of RSAKey Exchange offloaded to card.
         "
    ::= { nsSslStatsGroup 246 }

sslTotOffloadDHKeyExchanges OBJECT-TYPE
    SYNTAX      Counter64
    MAX-ACCESS  read-only
    STATUS      current
    DESCRIPTION 
        " Total number of DHKey Exchange offloaded to card.
         "
    ::= { nsSslStatsGroup 247 }

sslTotOffloadSignRSA OBJECT-TYPE
    SYNTAX      Counter64
    MAX-ACCESS  read-only
    STATUS      current
    DESCRIPTION 
        " Total number of RSA sign offloaded to card.
         "
    ::= { nsSslStatsGroup 248 }

sslBeTotSessions OBJECT-TYPE
    SYNTAX      Counter64
    MAX-ACCESS  read-only
    STATUS      current
    DESCRIPTION 
        " SSL Backend Encryption: Total number of SSL Sessions.
         "
    ::= { nsSslStatsGroup 260 }

sslBeTotSSLv3Sessions OBJECT-TYPE
    SYNTAX      Counter64
    MAX-ACCESS  read-only
    STATUS      current
    DESCRIPTION 
        " SSL Backend Encryption: Total number of SSLv3 Sessions.
         "
    ::= { nsSslStatsGroup 261 }

sslBeTotTLSv1Sessions OBJECT-TYPE
    SYNTAX      Counter64
    MAX-ACCESS  read-only
    STATUS      current
    DESCRIPTION 
        " SSL Backend Encryption: Total number of TLSv1 Sessions.
         "
    ::= { nsSslStatsGroup 262 }

sslBeExpiredSessions OBJECT-TYPE
    SYNTAX      Counter64
    MAX-ACCESS  read-only
    STATUS      current
    DESCRIPTION 
        " SSL Backend Encryption: Total number of SSL Sessions Expired.
         "
    ::= { nsSslStatsGroup 263 }

sslBeTotSessionMultiplexAttempts OBJECT-TYPE
    SYNTAX      Counter64
    MAX-ACCESS  read-only
    STATUS      current
    DESCRIPTION 
        " SSL Backend Encryption: Total number of SSL Session Multiplexing 
         attempts. "
    ::= { nsSslStatsGroup 264 }

sslBeTotSessionMultiplexAttemptSuccess OBJECT-TYPE
    SYNTAX      Counter64
    MAX-ACCESS  read-only
    STATUS      current
    DESCRIPTION 
        " SSL Backend Encryption: Total number of SSL Session Multiplexing 
         attempt Successful. "
    ::= { nsSslStatsGroup 265 }

sslBeTotSessionMultiplexAttemptFails OBJECT-TYPE
    SYNTAX      Counter64
    MAX-ACCESS  read-only
    STATUS      current
    DESCRIPTION 
        " SSL Backend Encryption: Total number of SSL Session Multiplexing 
         attempt Failure. "
    ::= { nsSslStatsGroup 266 }

sslBeMaxMultiplexedSessions OBJECT-TYPE
    SYNTAX      Counter64
    MAX-ACCESS  read-only
    STATUS      current
    DESCRIPTION 
        " SSL Backend Encryption: Total number of SSL Session Multiplexing.
         "
    ::= { nsSslStatsGroup 267 }

sslBeTotSSLv3Handshakes OBJECT-TYPE
    SYNTAX      Counter64
    MAX-ACCESS  read-only
    STATUS      current
    DESCRIPTION 
        " SSL Backend Encryption: Total number of SSLv3 Handshake.
         "
    ::= { nsSslStatsGroup 268 }

sslBeTotTLSv1Handshakes OBJECT-TYPE
    SYNTAX      Counter64
    MAX-ACCESS  read-only
    STATUS      current
    DESCRIPTION 
        " SSL Backend Encryption: Total number of TLSv1 Handshake.
         "
    ::= { nsSslStatsGroup 269 }

sslBeTotSSLv3ClientAuthentications OBJECT-TYPE
    SYNTAX      Counter64
    MAX-ACCESS  read-only
    STATUS      current
    DESCRIPTION 
        " SSL Backend Encryption: Total number of SSLv3 Client Authentication.
         "
    ::= { nsSslStatsGroup 270 }

sslBeTotTLSv1ClientAuthentications OBJECT-TYPE
    SYNTAX      Counter64
    MAX-ACCESS  read-only
    STATUS      current
    DESCRIPTION 
        " SSL Backend Encryption: Total number of TLSv1 Client Authentication.
         "
    ::= { nsSslStatsGroup 271 }

sslBeTotRSA512keyExchanges OBJECT-TYPE
    SYNTAX      Counter64
    MAX-ACCESS  read-only
    STATUS      current
    DESCRIPTION 
        " SSL Backend Encryption: Total number of RSA 512bit Key Exchange.
         "
    ::= { nsSslStatsGroup 272 }

sslBeTotRSA1024keyExchanges OBJECT-TYPE
    SYNTAX      Counter64
    MAX-ACCESS  read-only
    STATUS      current
    DESCRIPTION 
        " SSL Backend Encryption: Total number of RSA 1024bit Key Exchange.
         "
    ::= { nsSslStatsGroup 273 }

sslBeTotRSA2048keyExchanges OBJECT-TYPE
    SYNTAX      Counter64
    MAX-ACCESS  read-only
    STATUS      current
    DESCRIPTION 
        " SSL Backend Encryption: Total number of RSA 2048bit Key Exchange.
         "
    ::= { nsSslStatsGroup 274 }

sslBeTotDH512keyExchanges OBJECT-TYPE
    SYNTAX      Counter64
    MAX-ACCESS  read-only
    STATUS      current
    DESCRIPTION 
        " SSL Backend Encryption: Total number of DH 512bit Key Exchange.
         "
    ::= { nsSslStatsGroup 275 }

sslBeTotDH1024keyExchanges OBJECT-TYPE
    SYNTAX      Counter64
    MAX-ACCESS  read-only
    STATUS      current
    DESCRIPTION 
        " SSL Backend Encryption: Total number of DH 1024bit Key Exchange.
         "
    ::= { nsSslStatsGroup 276 }

sslBeTotDH2048keyExchanges OBJECT-TYPE
    SYNTAX      Counter64
    MAX-ACCESS  read-only
    STATUS      current
    DESCRIPTION 
        " SSL Backend Encryption: Total number of DH 2048bit Key Exchange.
         "
    ::= { nsSslStatsGroup 277 }

sslBeTotRSAAuthorizations OBJECT-TYPE
    SYNTAX      Counter64
    MAX-ACCESS  read-only
    STATUS      current
    DESCRIPTION 
        " SSL Backend Encryption: Total number of times RSA Authorization used.
         "
    ::= { nsSslStatsGroup 278 }

sslBeTotDHAuthorizations OBJECT-TYPE
    SYNTAX      Counter64
    MAX-ACCESS  read-only
    STATUS      current
    DESCRIPTION 
        " SSL Backend Encryption: Total number of times DH Authorization used.
         "
    ::= { nsSslStatsGroup 279 }

sslBeTotDSSAuthorizations OBJECT-TYPE
    SYNTAX      Counter64
    MAX-ACCESS  read-only
    STATUS      current
    DESCRIPTION 
        " SSL Backend Encryption: Total number of times DSS Authorization used.
         "
    ::= { nsSslStatsGroup 280 }

sslBeTotNULLAuthorizations OBJECT-TYPE
    SYNTAX      Counter64
    MAX-ACCESS  read-only
    STATUS      current
    DESCRIPTION 
        " SSL Backend Encryption: Total number of times NULL Authorization used.
         "
    ::= { nsSslStatsGroup 281 }

sslBeTot40BitRC4Ciphers OBJECT-TYPE
    SYNTAX      Counter64
    MAX-ACCESS  read-only
    STATUS      current
    DESCRIPTION 
        " SSL Backend Encryption:  Total number of times 40bit RC4 cipher used.
         "
    ::= { nsSslStatsGroup 282 }

sslBeTot56BitRC4Ciphers OBJECT-TYPE
    SYNTAX      Counter64
    MAX-ACCESS  read-only
    STATUS      current
    DESCRIPTION 
        " SSL Backend Encryption: Total number of times 56bit RC4 cipher used.
         "
    ::= { nsSslStatsGroup 283 }

sslBeTot64BitRC4Ciphers OBJECT-TYPE
    SYNTAX      Counter64
    MAX-ACCESS  read-only
    STATUS      current
    DESCRIPTION 
        " SSL Backend Encryption: Total number of times 64bit RC4 cipher used.
         "
    ::= { nsSslStatsGroup 284 }

sslBeTot128BitRC4Ciphers OBJECT-TYPE
    SYNTAX      Counter64
    MAX-ACCESS  read-only
    STATUS      current
    DESCRIPTION 
        " SSL Backend Encryption: Total number of times 128bit RC4 cipher used.
         "
    ::= { nsSslStatsGroup 285 }

sslBeTot40BitDESCiphers OBJECT-TYPE
    SYNTAX      Counter64
    MAX-ACCESS  read-only
    STATUS      current
    DESCRIPTION 
        " SSL Backend Encryption: Total number of times 40bit DES cipher used.
         "
    ::= { nsSslStatsGroup 286 }

sslBeTot56BitDESCiphers OBJECT-TYPE
    SYNTAX      Counter64
    MAX-ACCESS  read-only
    STATUS      current
    DESCRIPTION 
        " SSL Backend Encryption: Total number of times 56bit DES cipher used.
         "
    ::= { nsSslStatsGroup 287 }

sslBeTot168Bit3DESCiphers OBJECT-TYPE
    SYNTAX      Counter64
    MAX-ACCESS  read-only
    STATUS      current
    DESCRIPTION 
        " SSL Backend Encryption: Total number of times 168bit 3DES cipher used.
         "
    ::= { nsSslStatsGroup 288 }

sslBeTot40BitRC2Ciphers OBJECT-TYPE
    SYNTAX      Counter64
    MAX-ACCESS  read-only
    STATUS      current
    DESCRIPTION 
        " SSL Backend Encryption: Total number of times 40bit RC2 cipher used.
         "
    ::= { nsSslStatsGroup 289 }

sslBeTot56BitRC2Ciphers OBJECT-TYPE
    SYNTAX      Counter64
    MAX-ACCESS  read-only
    STATUS      current
    DESCRIPTION 
        " SSL Backend Encryption: Total number of times 56bit RC2 cipher used.
         "
    ::= { nsSslStatsGroup 290 }

sslBeTot128BitRC2Ciphers OBJECT-TYPE
    SYNTAX      Counter64
    MAX-ACCESS  read-only
    STATUS      current
    DESCRIPTION 
        " SSL Backend Encryption: Total number of times 128bit RC2 cipher used.
         "
    ::= { nsSslStatsGroup 291 }

sslBeTot128BitIDEACiphers OBJECT-TYPE
    SYNTAX      Counter64
    MAX-ACCESS  read-only
    STATUS      current
    DESCRIPTION 
        " SSL Backend Encryption: Total number of times 128bit IDEA cipher used.
         "
    ::= { nsSslStatsGroup 292 }

sslBeTotNULLCiphers OBJECT-TYPE
    SYNTAX      Counter64
    MAX-ACCESS  read-only
    STATUS      current
    DESCRIPTION 
        " SSL Backend Encryption: Total number of times NULL cipher used.
         "
    ::= { nsSslStatsGroup 293 }

sslBeTotMD5Mac OBJECT-TYPE
    SYNTAX      Counter64
    MAX-ACCESS  read-only
    STATUS      current
    DESCRIPTION 
        " SSL Backend Encryption: Total number of times MD5 MAC used.
         "
    ::= { nsSslStatsGroup 294 }

sslBeTotSHAMac OBJECT-TYPE
    SYNTAX      Counter64
    MAX-ACCESS  read-only
    STATUS      current
    DESCRIPTION 
        " SSL Backend Encryption: Total number of times SHA MAC used.				  
         "
    ::= { nsSslStatsGroup 295 }

sslCurSessions  OBJECT-TYPE
        SYNTAX  Counter32
        MAX-ACCESS  read-only
        STATUS  current
        DESCRIPTION
                "Number of active SSL sessions"
        ::= { nsSslStatsGroup 296 }

nsHttpStatsGroup OBJECT IDENTIFIER
    ::= { nsSysGroup 48 }

httpTotGetsLow OBJECT-TYPE
    SYNTAX      Counter32
    MAX-ACCESS  read-only
    STATUS      obsolete
    DESCRIPTION 
        "Number of HTTP GET requests received, low32 bit counter"
    ::= { nsHttpStatsGroup 1 }

httpTotGetsHigh OBJECT-TYPE
    SYNTAX      Counter32
    MAX-ACCESS  read-only
    STATUS      obsolete
    DESCRIPTION 
        "Number of HTTP GET requests received, high32 bit counter"
    ::= { nsHttpStatsGroup 2 }

httpTotPostsLow OBJECT-TYPE
    SYNTAX      Counter32
    MAX-ACCESS  read-only
    STATUS      obsolete
    DESCRIPTION 
        "Number of HTTP POST requests received, low32bit counter"
    ::= { nsHttpStatsGroup 3 }

httpTotPostsHigh OBJECT-TYPE
    SYNTAX      Counter32
    MAX-ACCESS  read-only
    STATUS      obsolete
    DESCRIPTION 
        "Number of HTTP POST requests received, high32bit counter"
    ::= { nsHttpStatsGroup 4 }

httpTotOthersLow OBJECT-TYPE
    SYNTAX      Counter32
    MAX-ACCESS  read-only
    STATUS      obsolete
    DESCRIPTION 
        "Number of non GET-POST HTTP methods received, low32 bit counter"
    ::= { nsHttpStatsGroup 5 }

httpTotOthersHigh OBJECT-TYPE
    SYNTAX      Counter32
    MAX-ACCESS  read-only
    STATUS      obsolete
    DESCRIPTION 
        "Number of non GET-POST HTTP methods received, high32 bit counter "
    ::= { nsHttpStatsGroup 6 }

httpTotRxRequestBytesLow OBJECT-TYPE
    SYNTAX      Counter32
    MAX-ACCESS  read-only
    STATUS      obsolete
    DESCRIPTION 
        "Data received in request including headers(in bytes), low32 bit counter"
    ::= { nsHttpStatsGroup 7 }

httpTotRxRequestBytesHigh OBJECT-TYPE
    SYNTAX      Counter32
    MAX-ACCESS  read-only
    STATUS      obsolete
    DESCRIPTION 
        "Data received in request including headers(in bytes), high32 bit counter"
    ::= { nsHttpStatsGroup 8 }

httpTotRxResponseBytesLow OBJECT-TYPE
    SYNTAX      Counter32
    MAX-ACCESS  read-only
    STATUS      obsolete
    DESCRIPTION 
        "Data received in the response including headers(in bytes), low32 bit counter"
    ::= { nsHttpStatsGroup 9 }

httpTotRxResponseBytesHigh OBJECT-TYPE
    SYNTAX      Counter32
    MAX-ACCESS  read-only
    STATUS      obsolete
    DESCRIPTION 
        "Data received in the response including headers(in bytes), high32 bit counter"
    ::= { nsHttpStatsGroup 10 }

httpTotTxRequestBytesLow OBJECT-TYPE
    SYNTAX      Counter32
    MAX-ACCESS  read-only
    STATUS      obsolete
    DESCRIPTION 
        "Data transmitted in request including headers(in bytes), low32 bit counter"
    ::= { nsHttpStatsGroup 11 }

httpTotTxRequestBytesHigh OBJECT-TYPE
    SYNTAX      Counter32
    MAX-ACCESS  read-only
    STATUS      obsolete
    DESCRIPTION 
        "Data transmitted in request including headers(in bytes), high32 bit counter"
    ::= { nsHttpStatsGroup 12 }

httpTotTxResponseBytesLow OBJECT-TYPE
    SYNTAX      Counter32
    MAX-ACCESS  read-only
    STATUS      obsolete
    DESCRIPTION 
        "Data transmitted in response including headers(in bytes), low32 bit counter"
    ::= { nsHttpStatsGroup 13 }

httpTotTxResponseBytesHigh OBJECT-TYPE
    SYNTAX      Counter32
    MAX-ACCESS  read-only
    STATUS      obsolete
    DESCRIPTION 
        "Data transmitted in response including headers(in bytes), high32 bit counter"
    ::= { nsHttpStatsGroup 14 }

httpTotHTTP10reqLow OBJECT-TYPE
    SYNTAX      Counter32
    MAX-ACCESS  read-only
    STATUS      obsolete
    DESCRIPTION 
        "No of HTTP/1.0 Request received from the client, low32 bit counter"
    ::= { nsHttpStatsGroup 15 }

httpTotHTTP10reqHigh OBJECT-TYPE
    SYNTAX      Counter32
    MAX-ACCESS  read-only
    STATUS      obsolete
    DESCRIPTION 
        "No of HTTP/1.0 Request received from the client, high32 bit counter"
    ::= { nsHttpStatsGroup 16 }

httpTotResponsesLow OBJECT-TYPE
    SYNTAX      Counter32
    MAX-ACCESS  read-only
    STATUS      obsolete
    DESCRIPTION 
        "No of HTTP Response received from the servers, low32 bit counter"
    ::= { nsHttpStatsGroup 17 }

httpTotResponsesHigh OBJECT-TYPE
    SYNTAX      Counter32
    MAX-ACCESS  read-only
    STATUS      obsolete
    DESCRIPTION 
        "No of HTTP Response received from the servers, high32 bit counter"
    ::= { nsHttpStatsGroup 18 }

httpTot10ResponsesLow OBJECT-TYPE
    SYNTAX      Counter32
    MAX-ACCESS  read-only
    STATUS      obsolete
    DESCRIPTION 
        "No of HTTP/1.0 Responses received from the servers, low32 bit counter"
    ::= { nsHttpStatsGroup 19 }

httpTot10ResponsesHigh OBJECT-TYPE
    SYNTAX      Counter32
    MAX-ACCESS  read-only
    STATUS      obsolete
    DESCRIPTION 
        "No of HTTP/1.0 Responses received from the servers, high32 bit counter"
    ::= { nsHttpStatsGroup 20 }

httpTotClenResponsesLow OBJECT-TYPE
    SYNTAX      Counter32
    MAX-ACCESS  read-only
    STATUS      obsolete
    DESCRIPTION 
        "No. of HTTP request/responses received with the Content-Length headers, low32 bit counter"
    ::= { nsHttpStatsGroup 21 }

httpTotClenResponsesHigh OBJECT-TYPE
    SYNTAX      Counter32
    MAX-ACCESS  read-only
    STATUS      obsolete
    DESCRIPTION 
        "No. of HTTP request/responses received with the Content-Length headers, high32 bit counter"
    ::= { nsHttpStatsGroup 22 }

httpTotChunkedResponsesLow OBJECT-TYPE
    SYNTAX      Counter32
    MAX-ACCESS  read-only
    STATUS      obsolete
    DESCRIPTION 
        "No. of HTTP request/responses received with the Chunked Encoding, low32 bit counter"
    ::= { nsHttpStatsGroup 23 }

httpTotChunkedResponsesHigh OBJECT-TYPE
    SYNTAX      Counter32
    MAX-ACCESS  read-only
    STATUS      obsolete
    DESCRIPTION 
        "No. of HTTP request/responses received with the Chunked Encoding, high32 bit counter"
    ::= { nsHttpStatsGroup 24 }

httpErrIncompleteRequestsLow OBJECT-TYPE
    SYNTAX      Counter32
    MAX-ACCESS  read-only
    STATUS      obsolete
    DESCRIPTION 
        "No. of Incomplete request Header received, low32 bit counter"
    ::= { nsHttpStatsGroup 25 }

httpErrIncompleteRequestsHigh OBJECT-TYPE
    SYNTAX      Counter32
    MAX-ACCESS  read-only
    STATUS      obsolete
    DESCRIPTION 
        "No. of Incomplete request Header received, high32 bit counter"
    ::= { nsHttpStatsGroup 26 }

httpErrIncompleteResponsesLow OBJECT-TYPE
    SYNTAX      Counter32
    MAX-ACCESS  read-only
    STATUS      obsolete
    DESCRIPTION 
        "No. of Incomplete response Header received, low32 bit counter"
    ::= { nsHttpStatsGroup 27 }

httpErrIncompleteResponsesHigh OBJECT-TYPE
    SYNTAX      Counter32
    MAX-ACCESS  read-only
    STATUS      obsolete
    DESCRIPTION 
        "No. of Incomplete response Header received, high32 bit counter"
    ::= { nsHttpStatsGroup 28 }

httpErrPipelinedRequestsLow OBJECT-TYPE
    SYNTAX      Counter32
    MAX-ACCESS  read-only
    STATUS      obsolete
    DESCRIPTION 
        "No. of HTTP/1.1 Pipeline request received, low32 bit counter"
    ::= { nsHttpStatsGroup 29 }

httpErrPipelinedRequestsHigh OBJECT-TYPE
    SYNTAX      Counter32
    MAX-ACCESS  read-only
    STATUS      obsolete
    DESCRIPTION 
        "No. of HTTP/1.1 Pipeline request received, high32 bit counter"
    ::= { nsHttpStatsGroup 30 }

httpErrIncompleteHeadersLow OBJECT-TYPE
    SYNTAX      Counter32
    MAX-ACCESS  read-only
    STATUS      obsolete
    DESCRIPTION 
        "Number of times completion of the HTTP incomplete header reassembly failed, low32 bit counter"
    ::= { nsHttpStatsGroup 31 }

httpErrIncompleteHeadersHigh OBJECT-TYPE
    SYNTAX      Counter32
    MAX-ACCESS  read-only
    STATUS      obsolete
    DESCRIPTION 
        "Number of times completion of the HTTP incomplete header reassembly failed, high32 bit counter "
    ::= { nsHttpStatsGroup 32 }

httpErrServerBusyLow OBJECT-TYPE
    SYNTAX      Counter32
    MAX-ACCESS  read-only
    STATUS      obsolete
    DESCRIPTION 
        "Number of times 500 Server BUSY error response is received from the server, low32 bit counter"
    ::= { nsHttpStatsGroup 33 }

httpErrServerBusyHigh OBJECT-TYPE
    SYNTAX      Counter32
    MAX-ACCESS  read-only
    STATUS      obsolete
    DESCRIPTION 
        "Number of times 500 Server BUSY error response is received from the server, high32 bit counter "
    ::= { nsHttpStatsGroup 34 }

httpTotChunkedReqLow OBJECT-TYPE
    SYNTAX      Counter32
    MAX-ACCESS  read-only
    STATUS      obsolete
    DESCRIPTION 
        "Number of Chunked Request received, low32 bit counter"
    ::= { nsHttpStatsGroup 35 }

httpTotChunkedReqHigh OBJECT-TYPE
    SYNTAX      Counter32
    MAX-ACCESS  read-only
    STATUS      obsolete
    DESCRIPTION 
        "Number of Chunked Request received, high32 bit counter"
    ::= { nsHttpStatsGroup 36 }

httpTotClenReqLow OBJECT-TYPE
    SYNTAX      Counter32
    MAX-ACCESS  read-only
    STATUS      obsolete
    DESCRIPTION 
        "Number of Content Length Requests received, low32 bit counter"
    ::= { nsHttpStatsGroup 37 }

httpTotClenReqHigh OBJECT-TYPE
    SYNTAX      Counter32
    MAX-ACCESS  read-only
    STATUS      obsolete
    DESCRIPTION 
        "Number of Content Length Requests received, high32 bit counter"
    ::= { nsHttpStatsGroup 38 }

httpErrLargeContentLow OBJECT-TYPE
    SYNTAX      Counter32
    MAX-ACCESS  read-only
    STATUS      obsolete
    DESCRIPTION 
        "No. large/invalid request/response received, low32 bit counter"
    ::= { nsHttpStatsGroup 39 }

httpErrLargeContentHigh OBJECT-TYPE
    SYNTAX      Counter32
    MAX-ACCESS  read-only
    STATUS      obsolete
    DESCRIPTION 
        "No. large/invalid request/response received, high32 bit counter"
    ::= { nsHttpStatsGroup 40 }

httpErrLargeCtlenLow OBJECT-TYPE
    SYNTAX      Counter32
    MAX-ACCESS  read-only
    STATUS      obsolete
    DESCRIPTION 
        "Number of Content Length Requests received, low32 bit counter"
    ::= { nsHttpStatsGroup 41 }

httpErrLargeCtlenHigh OBJECT-TYPE
    SYNTAX      Counter32
    MAX-ACCESS  read-only
    STATUS      obsolete
    DESCRIPTION 
        "Number of Content Length Requests received, high32 bit counter"
    ::= { nsHttpStatsGroup 42 }

httpErrLargeChunkLow OBJECT-TYPE
    SYNTAX      Counter32
    MAX-ACCESS  read-only
    STATUS      obsolete
    DESCRIPTION 
        "No. of large/invalid chunk request/response received, low32 bit counter"
    ::= { nsHttpStatsGroup 43 }

httpErrLargeChunkHigh OBJECT-TYPE
    SYNTAX      Counter32
    MAX-ACCESS  read-only
    STATUS      obsolete
    DESCRIPTION 
        "No. of large/invalid chunk request/response received, high32 bit counter "
    ::= { nsHttpStatsGroup 44 }
 
httpTotGets OBJECT-TYPE
    SYNTAX      Counter64
    MAX-ACCESS  read-only
    STATUS      current
    DESCRIPTION 
        "Number of HTTP GET requests received"
    ::= { nsHttpStatsGroup 45 }

httpTotPosts OBJECT-TYPE
    SYNTAX      Counter64
    MAX-ACCESS  read-only
    STATUS      current
    DESCRIPTION 
        "Number of HTTP POST requests received"
    ::= { nsHttpStatsGroup 46 }

httpTotOthers OBJECT-TYPE
    SYNTAX      Counter64
    MAX-ACCESS  read-only
    STATUS      current
    DESCRIPTION 
        "Number of non GET-POST HTTP methods received"
    ::= { nsHttpStatsGroup 47 }

httpTotRxRequestBytes OBJECT-TYPE
    SYNTAX      Counter64
    MAX-ACCESS  read-only
    STATUS      current
    DESCRIPTION 
        "Data received in request including headers(in bytes)"
    ::= { nsHttpStatsGroup 48 }

httpTotRxResponseBytes OBJECT-TYPE
    SYNTAX      Counter64
    MAX-ACCESS  read-only
    STATUS      current
    DESCRIPTION 
        "Data received in the response including headers(in bytes)"
    ::= { nsHttpStatsGroup 49 }

httpTotTxRequestBytes OBJECT-TYPE
    SYNTAX      Counter64
    MAX-ACCESS  read-only
    STATUS      current
    DESCRIPTION 
        "Data transmitted in request including headers(in bytes)"
    ::= { nsHttpStatsGroup 50 }

httpTotTxResponseBytes OBJECT-TYPE
    SYNTAX      Counter64
    MAX-ACCESS  read-only
    STATUS      current
    DESCRIPTION 
        "Data transmitted in response including headers(in bytes)"
    ::= { nsHttpStatsGroup 51 }

httpTotHTTP10req OBJECT-TYPE
    SYNTAX      Counter64
    MAX-ACCESS  read-only
    STATUS      current
    DESCRIPTION 
        "No of HTTP/1.0 Request received from the client"
    ::= { nsHttpStatsGroup 52 }

httpTotResponses OBJECT-TYPE
    SYNTAX      Counter64
    MAX-ACCESS  read-only
    STATUS      current
    DESCRIPTION 
        "No of HTTP Response received from the servers"
    ::= { nsHttpStatsGroup 53 }

httpTot10Responses OBJECT-TYPE
    SYNTAX      Counter64
    MAX-ACCESS  read-only
    STATUS      current
    DESCRIPTION 
        "No of HTTP/1.0 Responses received from the servers"
    ::= { nsHttpStatsGroup 54 }

httpTotClenResponses OBJECT-TYPE
    SYNTAX      Counter64
    MAX-ACCESS  read-only
    STATUS      current
    DESCRIPTION 
        "No. of HTTP request/responses received with the Content-Length headers"
    ::= { nsHttpStatsGroup 55 }

httpTotChunkedResponses OBJECT-TYPE
    SYNTAX      Counter64
    MAX-ACCESS  read-only
    STATUS      current
    DESCRIPTION 
        "No. of HTTP request/responses received with the Chunked Encoding"
    ::= { nsHttpStatsGroup 56 }

httpErrIncompleteRequests OBJECT-TYPE
    SYNTAX      Counter64
    MAX-ACCESS  read-only
    STATUS      current
    DESCRIPTION 
        "No. of Incomplete request Header received"
    ::= { nsHttpStatsGroup 57 }

httpErrIncompleteResponses OBJECT-TYPE
    SYNTAX      Counter64
    MAX-ACCESS  read-only
    STATUS      current
    DESCRIPTION 
        "No. of Incomplete response Header received"
    ::= { nsHttpStatsGroup 58 }

httpErrPipelinedRequests OBJECT-TYPE
    SYNTAX      Counter64
    MAX-ACCESS  read-only
    STATUS      current
    DESCRIPTION 
        "No. of HTTP/1.1 Pipeline request received"
    ::= { nsHttpStatsGroup 59 }

httpErrIncompleteHeaders OBJECT-TYPE
    SYNTAX      Counter64
    MAX-ACCESS  read-only
    STATUS      current
    DESCRIPTION 
        "Number of times completion of the HTTP incomplete header reassembly failed"
    ::= { nsHttpStatsGroup 60 }

httpErrServerBusy OBJECT-TYPE
    SYNTAX      Counter64
    MAX-ACCESS  read-only
    STATUS      current
    DESCRIPTION 
        "Number of times 500 Server BUSY error response is received from the server"
    ::= { nsHttpStatsGroup 61 }

httpTotChunkedReq OBJECT-TYPE
    SYNTAX      Counter64
    MAX-ACCESS  read-only
    STATUS      current
    DESCRIPTION 
        "Number of Chunked Request received"
    ::= { nsHttpStatsGroup 62 }

httpTotClenReq OBJECT-TYPE
    SYNTAX      Counter64
    MAX-ACCESS  read-only
    STATUS      current
    DESCRIPTION 
        "Number of Content Length Requests received"
    ::= { nsHttpStatsGroup 63 }

httpErrLargeContent OBJECT-TYPE
    SYNTAX      Counter64
    MAX-ACCESS  read-only
    STATUS      current
    DESCRIPTION 
        "No. large/invalid request/response received"
    ::= { nsHttpStatsGroup 64 }

httpErrLargeCtlen OBJECT-TYPE
    SYNTAX      Counter64
    MAX-ACCESS  read-only
    STATUS      current
    DESCRIPTION 
        "Number of Content Length Requests received"
    ::= { nsHttpStatsGroup 65 }

httpErrLargeChunk OBJECT-TYPE
    SYNTAX      Counter64
    MAX-ACCESS  read-only
    STATUS      current
    DESCRIPTION 
        "No. of large/invalid chunk request/response received"
    ::= { nsHttpStatsGroup 66 }

nsCacheStatsGroup OBJECT IDENTIFIER
    ::= { nsSysGroup 49 }

-- CACHE_GENERATED

	cacheMaxMemoryKB OBJECT-TYPE
		SYNTAX Counter32
		MAX-ACCESS read-only
		STATUS current
		DESCRIPTION "Maximum size of Cache storage in kilobytes"
	::= { nsCacheStatsGroup 1}

	cacheUtilizedMemoryKB OBJECT-TYPE
		SYNTAX Counter32
		MAX-ACCESS read-only
		STATUS current
		DESCRIPTION "Current size of Cache storage in kilobytes"
	::= { nsCacheStatsGroup 2}

	cacheNumCached OBJECT-TYPE
		SYNTAX Counter32
		MAX-ACCESS read-only
		STATUS current
		DESCRIPTION "Number of objects in the cache. This includes (1) objects fully download (2) objects being downloaded (3) objects expired but not yet removed (4) objects flushed but not yet removed"
	::= { nsCacheStatsGroup 3}

	cacheErrMemAllocLow OBJECT-TYPE
		SYNTAX Counter32
		MAX-ACCESS read-only
		STATUS obsolete
		DESCRIPTION "Total number of times the cache failed to allocate memory to store transactions"
	::= { nsCacheStatsGroup 4}

	cacheErrMemAllocHigh OBJECT-TYPE
		SYNTAX Counter32
		MAX-ACCESS read-only
		STATUS obsolete
		DESCRIPTION "Total number of times the cache failed to allocate memory to store transactions"
	::= { nsCacheStatsGroup 5}

	cacheTotRequestsLow OBJECT-TYPE
		SYNTAX Counter32
		MAX-ACCESS read-only
		STATUS obsolete
		DESCRIPTION "Total number of requets"
	::= { nsCacheStatsGroup 6}

	cacheTotRequestsHigh OBJECT-TYPE
		SYNTAX Counter32
		MAX-ACCESS read-only
		STATUS obsolete
		DESCRIPTION "Total number of requets"
	::= { nsCacheStatsGroup 7}

	cacheTotHitsLow OBJECT-TYPE
		SYNTAX Counter32
		MAX-ACCESS read-only
		STATUS obsolete
		DESCRIPTION "Total number of hits"
	::= { nsCacheStatsGroup 8}

	cacheTotHitsHigh OBJECT-TYPE
		SYNTAX Counter32
		MAX-ACCESS read-only
		STATUS obsolete
		DESCRIPTION "Total number of hits"
	::= { nsCacheStatsGroup 9}

	cacheTotMissesLow OBJECT-TYPE
		SYNTAX Counter32
		MAX-ACCESS read-only
		STATUS obsolete
		DESCRIPTION "Total number of misses"
	::= { nsCacheStatsGroup 10}

	cacheTotMissesHigh OBJECT-TYPE
		SYNTAX Counter32
		MAX-ACCESS read-only
		STATUS obsolete
		DESCRIPTION "Total number of misses"
	::= { nsCacheStatsGroup 11}

	cachePercentHit OBJECT-TYPE
		SYNTAX Counter32
		MAX-ACCESS read-only
		STATUS current
		DESCRIPTION "Cache hit ratio expressed as percentage"
	::= { nsCacheStatsGroup 12}

	cacheRecentPercentHit OBJECT-TYPE
		SYNTAX Counter32
		MAX-ACCESS read-only
		STATUS current
		DESCRIPTION "Recently recorded cache hit ratio expressed as percentage"
	::= { nsCacheStatsGroup 13}

	cacheCurHits OBJECT-TYPE
		SYNTAX Gauge32
		MAX-ACCESS read-only
		STATUS current
		DESCRIPTION "This number should be close to the number of hits being served currently."
	::= { nsCacheStatsGroup 14}

	cacheCurMisses OBJECT-TYPE
		SYNTAX Gauge32
		MAX-ACCESS read-only
		STATUS current
		DESCRIPTION "Number of clients that are being served by the origin via the cache. This number should be close to the number of requests being served at present and that had experienced a store-able miss. It does not include those requests that had experienced a non-store-able miss."
	::= { nsCacheStatsGroup 15}

	cacheTot304HitsLow OBJECT-TYPE
		SYNTAX Counter32
		MAX-ACCESS read-only
		STATUS obsolete
		DESCRIPTION "Total number of 304 Not Modified responses served from the cache."
	::= { nsCacheStatsGroup 16}

	cacheTot304HitsHigh OBJECT-TYPE
		SYNTAX Counter32
		MAX-ACCESS read-only
		STATUS obsolete
		DESCRIPTION "Total number of 304 Not Modified responses served from the cache."
	::= { nsCacheStatsGroup 17}

	cacheTotNon304HitsLow OBJECT-TYPE
		SYNTAX Counter32
		MAX-ACCESS read-only
		STATUS obsolete
		DESCRIPTION "Total number of full responses served from the cache."
	::= { nsCacheStatsGroup 18}

	cacheTotNon304HitsHigh OBJECT-TYPE
		SYNTAX Counter32
		MAX-ACCESS read-only
		STATUS obsolete
		DESCRIPTION "Total number of full responses served from the cache."
	::= { nsCacheStatsGroup 19}

	cachePercent304Hits OBJECT-TYPE
		SYNTAX Counter32
		MAX-ACCESS read-only
		STATUS current
		DESCRIPTION "Ratio of 304 hits to total hits expressed as percentage"
	::= { nsCacheStatsGroup 20}

	cacheRecentPercent304Hits OBJECT-TYPE
		SYNTAX Counter32
		MAX-ACCESS read-only
		STATUS current
		DESCRIPTION "Recently recorded ratio of 304 hits to all hits expressed as percentage"
	::= { nsCacheStatsGroup 21}

	cacheTotStoreAbleMissesLow OBJECT-TYPE
		SYNTAX Counter32
		MAX-ACCESS read-only
		STATUS obsolete
		DESCRIPTION "Total number of store-able misses"
	::= { nsCacheStatsGroup 22}

	cacheTotStoreAbleMissesHigh OBJECT-TYPE
		SYNTAX Counter32
		MAX-ACCESS read-only
		STATUS obsolete
		DESCRIPTION "Total number of store-able misses"
	::= { nsCacheStatsGroup 23}

	cacheTotNonStoreAbleMissesLow OBJECT-TYPE
		SYNTAX Counter32
		MAX-ACCESS read-only
		STATUS obsolete
		DESCRIPTION "Total number of non-store-able misses"
	::= { nsCacheStatsGroup 24}

	cacheTotNonStoreAbleMissesHigh OBJECT-TYPE
		SYNTAX Counter32
		MAX-ACCESS read-only
		STATUS obsolete
		DESCRIPTION "Total number of non-store-able misses"
	::= { nsCacheStatsGroup 25}

	cachePercentStoreAbleMiss OBJECT-TYPE
		SYNTAX Counter32
		MAX-ACCESS read-only
		STATUS current
		DESCRIPTION "Ratio of store-able misses to all misses expressed as percentage"
	::= { nsCacheStatsGroup 26}

	cacheRecentPercentStoreAbleMiss OBJECT-TYPE
		SYNTAX Counter32
		MAX-ACCESS read-only
		STATUS current
		DESCRIPTION "Recently recorded ratio of store-able misses to all misses expressed as percentage"
	::= { nsCacheStatsGroup 27}

	cacheTotRevalidationMissLow OBJECT-TYPE
		SYNTAX Counter32
		MAX-ACCESS read-only
		STATUS obsolete
		DESCRIPTION "Number of times cache generated a conditional request to the origin"
	::= { nsCacheStatsGroup 28}

	cacheTotRevalidationMissHigh OBJECT-TYPE
		SYNTAX Counter32
		MAX-ACCESS read-only
		STATUS obsolete
		DESCRIPTION "Number of times cache generated a conditional request to the origin"
	::= { nsCacheStatsGroup 29}

	cacheTotFullToConditionalRequestLow OBJECT-TYPE
		SYNTAX Counter32
		MAX-ACCESS read-only
		STATUS obsolete
		DESCRIPTION "Number of times cache converted a full request from the client to a conditional request to the origin"
	::= { nsCacheStatsGroup 30}

	cacheTotFullToConditionalRequestHigh OBJECT-TYPE
		SYNTAX Counter32
		MAX-ACCESS read-only
		STATUS obsolete
		DESCRIPTION "Number of times cache converted a full request from the client to a conditional request to the origin"
	::= { nsCacheStatsGroup 31}

	cacheTotSuccessfulRevalidationLow OBJECT-TYPE
		SYNTAX Counter32
		MAX-ACCESS read-only
		STATUS obsolete
		DESCRIPTION "Total number of times stored content was successfully revalidated by a 304 Not Modified response from the origin"
	::= { nsCacheStatsGroup 32}

	cacheTotSuccessfulRevalidationHigh OBJECT-TYPE
		SYNTAX Counter32
		MAX-ACCESS read-only
		STATUS obsolete
		DESCRIPTION "Total number of times stored content was successfully revalidated by a 304 Not Modified response from the origin"
	::= { nsCacheStatsGroup 33}

	cachePercentSuccessfulRevalidation OBJECT-TYPE
		SYNTAX Counter32
		MAX-ACCESS read-only
		STATUS current
		DESCRIPTION "Percentage of times stored content was successfully revalidated by a 304 response rather than by a full response"
	::= { nsCacheStatsGroup 34}

	cacheRecentPercentSuccessfulRevalidation OBJECT-TYPE
		SYNTAX Counter32
		MAX-ACCESS read-only
		STATUS current
		DESCRIPTION "Recently recorded percentage of times stored content was successfully revalidated by a 304 response rather than by a full response"
	::= { nsCacheStatsGroup 35}

	cacheBytesServedLow OBJECT-TYPE
		SYNTAX Counter32
		MAX-ACCESS read-only
		STATUS obsolete
		DESCRIPTION "Total number of bytes served from the cache"
	::= { nsCacheStatsGroup 36}

	cacheBytesServedHigh OBJECT-TYPE
		SYNTAX Counter32
		MAX-ACCESS read-only
		STATUS obsolete
		DESCRIPTION "Total number of bytes served from the cache"
	::= { nsCacheStatsGroup 37}

	cacheCompressedBytesServedLow OBJECT-TYPE
		SYNTAX Counter32
		MAX-ACCESS read-only
		STATUS obsolete
		DESCRIPTION "Total number of compressed bytes served from the cache"
	::= { nsCacheStatsGroup 38}

	cacheCompressedBytesServedHigh OBJECT-TYPE
		SYNTAX Counter32
		MAX-ACCESS read-only
		STATUS obsolete
		DESCRIPTION "Total number of compressed bytes served from the cache"
	::= { nsCacheStatsGroup 39}

	cachePercentByteHit OBJECT-TYPE
		SYNTAX Counter32
		MAX-ACCESS read-only
		STATUS current
		DESCRIPTION "Cache byte hit ratio expressed as percentage. Here we define byte hit ratio as ((number of bytes served from the cache)/(total number of bytes served to the client)). This is the standard definition of Byte Hit Ratio. If compression is turned ON in NS then this ratio doesn't mean much. This might under or over estimate the origin-to-cache bandwidth saving (depending upon whether bytes served by CMP in NetScaler are more or less than compressed bytes served from the cache). If CMP is turned OFF in NS then this ratio is same as cachePercentOriginBandwidthSaved."
	::= { nsCacheStatsGroup 40}

	cacheRecentPercentByteHit OBJECT-TYPE
		SYNTAX Counter32
		MAX-ACCESS read-only
		STATUS current
		DESCRIPTION "Recently recorded cache byte hit ratio expressed as percentage. Here we define byte hit ratio as ((number of bytes served from the cache)/(total number of bytes served to the client)). This is the standard definition of Byte Hit Ratio. If compression is turned ON in NS then this ratio doesn't mean much. This might under or over estimate the origin-to-cache bandwidth saving (depending upon whether bytes served by CMP in NetScaler are more or less than compressed bytes served from the cache). If CMP is turned OFF in NS then this ratio is same as cacheRecentPercentOriginBandwidthSaved."
	::= { nsCacheStatsGroup 41}

	cachePercentOriginBandwidthSaved OBJECT-TYPE
		SYNTAX Counter32
		MAX-ACCESS read-only
		STATUS current
		DESCRIPTION "Percentage of bandwidth saved at the origin is given by ((number of extra bytes that would have been served by the origin if the cache were absent)/(extra bytes that would have been served by the origin + number of bytes served by the origin). With this definition we are able to show benefits of integrated compression. The assumption here is that all the compression has been done in NetScaler, otherwise the b/w saving might get over estimated."
	::= { nsCacheStatsGroup 42}

	cacheRecentPercentOriginBandwidthSaved OBJECT-TYPE
		SYNTAX Counter32
		MAX-ACCESS read-only
		STATUS current
		DESCRIPTION "Recently Recorded Cache byte hit ratio expressed as percentage. Here we define byte hit ratio as ((number of extra bytes that would have been served by the origin)/(total number of bytes served to the client)). With this definition we are able to show benefits of integrated compression. The byte hit ratio can be greater than 1 because of integrated cmp. The assumption here is that all the compression has been done in NetScaler."
	::= { nsCacheStatsGroup 43}

	cacheErrMemAlloc OBJECT-TYPE
		SYNTAX Counter64
		MAX-ACCESS read-only
		STATUS current
		DESCRIPTION "Total number of times the cache failed to allocate memory to store transactions"
	::= { nsCacheStatsGroup 44}

	cacheTotRequests OBJECT-TYPE
		SYNTAX Counter64
		MAX-ACCESS read-only
		STATUS current
		DESCRIPTION "Total number of requets"
	::= { nsCacheStatsGroup 45}

	cacheTotHits OBJECT-TYPE
		SYNTAX Counter64
		MAX-ACCESS read-only
		STATUS current
		DESCRIPTION "Total number of hits"
	::= { nsCacheStatsGroup 46}

	cacheTotMisses OBJECT-TYPE
		SYNTAX Counter64
		MAX-ACCESS read-only
		STATUS current
		DESCRIPTION "Total number of misses"
	::= { nsCacheStatsGroup 47}

	cacheTot304Hits OBJECT-TYPE
		SYNTAX Counter64
		MAX-ACCESS read-only
		STATUS current
		DESCRIPTION "Total number of 304 Not Modified responses served from the cache."
	::= { nsCacheStatsGroup 48}

	cacheTotNon304Hits OBJECT-TYPE
		SYNTAX Counter64
		MAX-ACCESS read-only
		STATUS current
		DESCRIPTION "Total number of full responses served from the cache."
	::= { nsCacheStatsGroup 49}

	cacheTotStoreAbleMisses OBJECT-TYPE
		SYNTAX Counter64
		MAX-ACCESS read-only
		STATUS current
		DESCRIPTION "Total number of store-able misses"
	::= { nsCacheStatsGroup 50}

	cacheTotNonStoreAbleMisses OBJECT-TYPE
		SYNTAX Counter64
		MAX-ACCESS read-only
		STATUS current
		DESCRIPTION "Total number of non-store-able misses"
	::= { nsCacheStatsGroup 51}

	cacheTotRevalidationMiss OBJECT-TYPE
		SYNTAX Counter64
		MAX-ACCESS read-only
		STATUS current
		DESCRIPTION "Number of times cache generated a conditional request to the origin"
	::= { nsCacheStatsGroup 52}

	cacheTotFullToConditionalRequest OBJECT-TYPE
		SYNTAX Counter64
		MAX-ACCESS read-only
		STATUS current
		DESCRIPTION "Number of times cache converted a full request from the client to a conditional request to the origin"
	::= { nsCacheStatsGroup 53}

	cacheTotSuccessfulRevalidation OBJECT-TYPE
		SYNTAX Counter64
		MAX-ACCESS read-only
		STATUS current
		DESCRIPTION "Total number of times stored content was successfully revalidated by a 304 Not Modified response from the origin"
	::= { nsCacheStatsGroup 54}

	cacheTotResponseBytes OBJECT-TYPE
		SYNTAX Counter64
		MAX-ACCESS read-only
		STATUS current
		DESCRIPTION "Total number of HTTP response bytes served by NetScaler"
	::= { nsCacheStatsGroup 55}

	cacheBytesServed OBJECT-TYPE
		SYNTAX Counter64
		MAX-ACCESS read-only
		STATUS current
		DESCRIPTION "Total number of bytes served from the cache"
	::= { nsCacheStatsGroup 56}

	cacheCompressedBytesServed OBJECT-TYPE
		SYNTAX Counter64
		MAX-ACCESS read-only
		STATUS current
		DESCRIPTION "Total number of compressed bytes served from the cache"
	::= { nsCacheStatsGroup 57}

	cacheTotPetRequests OBJECT-TYPE
		SYNTAX Counter64
		MAX-ACCESS read-only
		STATUS current
		DESCRIPTION "Total number of PET requests"
	::= { nsCacheStatsGroup 58}

	cacheTotPetHits OBJECT-TYPE
		SYNTAX Counter64
		MAX-ACCESS read-only
		STATUS current
		DESCRIPTION "Total number of PET hits"
	::= { nsCacheStatsGroup 59}

	cachePercentPetHits OBJECT-TYPE
		SYNTAX Counter32
		MAX-ACCESS read-only
		STATUS current
		DESCRIPTION "Ratio of successful PET revalidations expressed as percentage"
	::= { nsCacheStatsGroup 60}

	cacheTotParameterizedRequests OBJECT-TYPE
		SYNTAX Counter64
		MAX-ACCESS read-only
		STATUS current
		DESCRIPTION "Total number of parameterized requests"
	::= { nsCacheStatsGroup 61}

	cacheTotParameterizedHits OBJECT-TYPE
		SYNTAX Counter64
		MAX-ACCESS read-only
		STATUS current
		DESCRIPTION "Total number of hits for parameterized requests"
	::= { nsCacheStatsGroup 62}

	cacheTotParameterizedNon304Hits OBJECT-TYPE
		SYNTAX Counter64
		MAX-ACCESS read-only
		STATUS current
		DESCRIPTION "Total number of full responses served from cache for parameterized requests"
	::= { nsCacheStatsGroup 63}

	cacheTotParameterized304Hits OBJECT-TYPE
		SYNTAX Counter64
		MAX-ACCESS read-only
		STATUS current
		DESCRIPTION "Total number of 304 responses served from cache for parameterized requests"
	::= { nsCacheStatsGroup 64}

	cachePercentParameterized304Hits OBJECT-TYPE
		SYNTAX Counter32
		MAX-ACCESS read-only
		STATUS current
		DESCRIPTION "Ratio of parameterized 304 hits to all parameterized hits expressed as a percentage"
	::= { nsCacheStatsGroup 65}

	cacheRecentPercentParameterizedHits OBJECT-TYPE
		SYNTAX Counter32
		MAX-ACCESS read-only
		STATUS current
		DESCRIPTION "Recently recorded ratio of parameterized 304 hits to all parameterized hits expressed as a percentage"
	::= { nsCacheStatsGroup 66}

	cacheTotInvalidationRequests OBJECT-TYPE
		SYNTAX Counter64
		MAX-ACCESS read-only
		STATUS current
		DESCRIPTION "Total number of invalidation requests"
	::= { nsCacheStatsGroup 67}

	cacheTotNonParameterizedInvalidationRequests OBJECT-TYPE
		SYNTAX Counter64
		MAX-ACCESS read-only
		STATUS current
		DESCRIPTION "Total number of requests which performed full invalidation"
	::= { nsCacheStatsGroup 68}

	cacheTotParameterizedInvalidationRequests OBJECT-TYPE
		SYNTAX Counter64
		MAX-ACCESS read-only
		STATUS current
		DESCRIPTION "Total number of requests which performed parameterized invalidation"
	::= { nsCacheStatsGroup 69}

-- CACHE_GENERATED_ENDS

nsCompressionStatsGroup OBJECT IDENTIFIER
    ::= { nsSysGroup 50 }
    
compTotalRequests	OBJECT-TYPE
    SYNTAX      Counter32
    MAX-ACCESS  read-only
    STATUS      current
    DESCRIPTION 
        " Number of compression requests done"
	::= { nsCompressionStatsGroup 1 }
	
compTotalTxBytes	OBJECT-TYPE
    SYNTAX      Counter32
    MAX-ACCESS  read-only
    STATUS      current
    DESCRIPTION 
        " Number of compressed bytes transmitted"
	::= { nsCompressionStatsGroup 2 }
	
compTotalRxBytes	OBJECT-TYPE  
    SYNTAX      Counter32
    MAX-ACCESS  read-only
    STATUS      current
    DESCRIPTION 
        " Number of compressible bytes received"
	::= { nsCompressionStatsGroup 3 }

compTotalTxPackets	OBJECT-TYPE  
    SYNTAX      Counter32
    MAX-ACCESS  read-only
    STATUS      current
    DESCRIPTION 
        " Number of compressed packets transmitted"
	::= { nsCompressionStatsGroup 4 }
	
compTotalRxPackets	OBJECT-TYPE  
	SYNTAX      Counter32
    MAX-ACCESS  read-only
    STATUS      current
    DESCRIPTION 
        " Number of compressible packets received"
    ::= { nsCompressionStatsGroup 5 }
    
compRatio	OBJECT-TYPE          
    SYNTAX      OCTET STRING
    MAX-ACCESS  read-only
    STATUS      current
    DESCRIPTION 
        " ratio of compressible data received vs compressed data transmitted"
	::= { nsCompressionStatsGroup 6 }

compTotalDataCompressionRatio	OBJECT-TYPE
    SYNTAX      OCTET STRING
    MAX-ACCESS  read-only
    STATUS      current
    DESCRIPTION 
        " ratio of total data received to total data transmitted"
	::= { nsCompressionStatsGroup 7 }

nsGslbGroup  OBJECT IDENTIFIER
    ::=   { nsSysGroup   51  }

gslbGlobalStats  OBJECT IDENTIFIER
    ::=   { nsGslbGroup   1  }

customEntries   OBJECT-TYPE
    SYNTAX Counter32
    MAX-ACCESS read-only
    STATUS current
    DESCRIPTION "This is the number of custom locations"
    ::= {  gslbGlobalStats  1  }

staticEntries   OBJECT-TYPE
    SYNTAX Counter32
    MAX-ACCESS read-only
    STATUS current
    DESCRIPTION "This is the number of static locations"
    ::= {  gslbGlobalStats  2  }

gslbGlobalInfo  OBJECT IDENTIFIER
    ::=   { nsGslbGroup   2  }

gslbSitesTable  OBJECT-TYPE
    SYNTAX  SEQUENCE OF GslbSitesEntry
    MAX-ACCESS not-accessible
    STATUS current
    DESCRIPTION "This table contains gslb sites information"
    ::= { gslbGlobalInfo  1 }

 gslbSitesEntry  OBJECT-TYPE
    SYNTAX GslbSitesEntry
    MAX-ACCESS not-accessible
    STATUS current
    DESCRIPTION "..."
    INDEX { siteName  }
    ::= { gslbSitesTable   1  }

GslbSitesEntry  ::= SEQUENCE   {
    siteName   OCTET STRING ,
    siteIp   IpAddress ,
    siteType   SiteType ,
    siteMetricExchange MetricExchange ,
    siteMepStatus   MepStatus ,
    sitePublicIp   IpAddress
    }

siteName   OBJECT-TYPE
    SYNTAX OCTET STRING
    MAX-ACCESS read-only
    STATUS current
    DESCRIPTION "This is the name of the gslb site"
    ::= {  gslbSitesEntry  1  }

siteIp   OBJECT-TYPE
    SYNTAX IpAddress
    MAX-ACCESS read-only
    STATUS current
    DESCRIPTION "This is the IP address of the site"
    ::= {  gslbSitesEntry  2  }

siteType   OBJECT-TYPE
    SYNTAX SiteType
    MAX-ACCESS read-only
    STATUS current
    DESCRIPTION "This indicates whether the Gslb site is local or remote."
    ::= {  gslbSitesEntry  3  }

siteMetricExchange   OBJECT-TYPE
    SYNTAX MetricExchange
    MAX-ACCESS read-only
    STATUS current
    DESCRIPTION "This indicates whether metric exchange is enabled or disabled at this site."
    ::= {  gslbSitesEntry  4  }

siteMepStatus   OBJECT-TYPE
    SYNTAX MepStatus
    MAX-ACCESS read-only
    STATUS current
    DESCRIPTION "This indicates the status of the Metric Exchange Policy at the site. "
    ::= {  gslbSitesEntry  5  }

sitePublicIp   OBJECT-TYPE
    SYNTAX IpAddress
    MAX-ACCESS read-only
    STATUS current
    DESCRIPTION "This is the public IP address of the site"
    ::= {  gslbSitesEntry  6  }

gslbPoliciesTable  OBJECT-TYPE
    SYNTAX  SEQUENCE OF GslbPoliciesEntry
    MAX-ACCESS not-accessible
    STATUS current
    DESCRIPTION "This table contains the policy information"
    ::= { gslbGlobalInfo  2 }

 gslbPoliciesEntry  OBJECT-TYPE
    SYNTAX GslbPoliciesEntry
    MAX-ACCESS not-accessible
    STATUS  current
    DESCRIPTION "..."
    INDEX { gslbPolicyName  }
    ::= { gslbPoliciesTable   1  }

GslbPoliciesEntry  ::= SEQUENCE   {
    gslbPolicyName   OCTET STRING ,
    totalHits   Counter32
    }

gslbPolicyName   OBJECT-TYPE
    SYNTAX OCTET STRING
    MAX-ACCESS read-only
    STATUS current
    DESCRIPTION "This is the policy name"
    ::= {  gslbPoliciesEntry  1  }

totalHits   OBJECT-TYPE
    SYNTAX Counter32
    MAX-ACCESS read-only
    STATUS current
    DESCRIPTION "This is the total hits for the policy"
    ::= {  gslbPoliciesEntry  2  }

nsPolicyEngineGroup OBJECT IDENTIFIER
    ::=   { nsSysGroup 52 }

nsPolicyStatsTable  OBJECT-TYPE
    SYNTAX  SEQUENCE OF NsPolicyStatsEntry
    MAX-ACCESS not-accessible
    STATUS current
    DESCRIPTION "This table contains the statistics for all policies"
    ::= { nsPolicyEngineGroup 1 }

nsPolicyStatsEntry  OBJECT-TYPE
    SYNTAX NsPolicyStatsEntry
    MAX-ACCESS not-accessible
    STATUS  current
    DESCRIPTION "..."
    INDEX { pengPolicyName  }
    ::= { nsPolicyStatsTable 1 }

NsPolicyStatsEntry ::= SEQUENCE   {
    pengPolicyName      OCTET STRING,
    pengPolicyHits      Counter32,
    pengBytesIn         Counter32,
    pengBytesOut        Counter32
    }

pengPolicyName  OBJECT-TYPE
    SYNTAX      OCTET STRING
    MAX-ACCESS  read-only
    STATUS      current
    DESCRIPTION "Name of the Policy"
    ::= { nsPolicyStatsEntry 1 }

pengPolicyHits  OBJECT-TYPE
    SYNTAX      Counter32
    MAX-ACCESS  read-only
    STATUS      current
    DESCRIPTION "Total hits"
    ::= { nsPolicyStatsEntry 2 }

pengBytesIn     OBJECT-TYPE
    SYNTAX      Counter32
    MAX-ACCESS  read-only
    STATUS      current
    DESCRIPTION "Total uncompressed bytes in (compression only)"
    ::= { nsPolicyStatsEntry 3 }

pengBytesOut    OBJECT-TYPE
    SYNTAX      Counter32
    MAX-ACCESS  read-only
    STATUS      current
    DESCRIPTION "Total compressed bytes out (compression only)"
    ::= { nsPolicyStatsEntry 4 }

nsSvcGroup OBJECT IDENTIFIER
    ::= { rs9000 2 }

serviceTable OBJECT-TYPE
    SYNTAX      SEQUENCE OF ServiceEntry
    MAX-ACCESS  not-accessible
    STATUS      current
    DESCRIPTION 
        "The netscaler services table"
    ::= { nsSvcGroup 1 }

serviceEntry OBJECT-TYPE
    SYNTAX      ServiceEntry
    MAX-ACCESS  not-accessible
    STATUS      current
    DESCRIPTION 
        "the sevice entry"
    INDEX       { svcServiceName }
    ::= { serviceTable 1 }

ServiceEntry ::= SEQUENCE {
    svcServiceName                 OCTET STRING,
    serviceIpAddress            IpAddress,
    servicePort                 Integer32,
    svcServiceType                 EntityProtocolType,
    serviceState                EntityState,
    svcMaxReqPerConn            Integer32,
    svcAvgTransactionTime       TimeTicks,
    svcEstablishedConn          Counter32,
    svcActiveConn               Counter32,
    svcSurgeCount               Counter32,
    svcTotalRequestsLow         Counter32,
    svcTotalRequestsHigh        Counter32,
    svcTotalRequestBytesLow     Counter32,
    svcTotalRequestBytesHigh    Counter32,
    svcTotalResponsesLow        Counter32,
    svcTotalResponsesHigh       Counter32,
    svcTotalResponseBytesLow    Counter32,
    svcTotalResponseBytesHigh   Counter32,
    svcTotalPktsRecvdLow        Counter32,
    svcTotalPktsRecvdHigh       Counter32,
    svcTotalPktsSentLow         Counter32,
    svcTotalPktsSentHigh        Counter32,
    svcTotalSynsRecvdLow        Counter32,
    svcTotalSynsRecvdHigh       Counter32,
    svcTotalRequests	        Counter64,
    svcTotalRequestBytes	Counter64,
    svcTotalResponses		Counter64,
    svcTotalResponseBytes	Counter64,
    svcTotalPktsRecvd		Counter64,
    svcTotalPktsSent		Counter64,
    svcTotalSynsRecvd		Counter64,
    svcGslbSiteName			OCTET STRING
}

svcServiceName OBJECT-TYPE
    SYNTAX      OCTET STRING
    MAX-ACCESS  read-only
    STATUS      current
    DESCRIPTION 
        "the name of the service."
    ::= { serviceEntry 1 }

serviceIpAddress OBJECT-TYPE
    SYNTAX      IpAddress
    MAX-ACCESS  read-only
    STATUS      current
    DESCRIPTION 
        "the ip address at which the service is running."
    ::= { serviceEntry 2 }

servicePort OBJECT-TYPE
    SYNTAX      Integer32
    MAX-ACCESS  read-only
    STATUS      current
    DESCRIPTION 
        "the port at which the service is running."
    ::= { serviceEntry 3 }

svcServiceType OBJECT-TYPE
    SYNTAX      EntityProtocolType
    MAX-ACCESS  read-only
    STATUS      current
    DESCRIPTION 
        "the protocol type of the service"
    ::= { serviceEntry 4 }

serviceState OBJECT-TYPE
    SYNTAX      EntityState
    MAX-ACCESS  read-only
    STATUS      current
    DESCRIPTION 
        "the state of the service"
    ::= { serviceEntry 5 }

svcMaxReqPerConn OBJECT-TYPE
    SYNTAX      Integer32
    MAX-ACCESS  read-only
    STATUS      current
    DESCRIPTION 
        "the maximum requests per connection allowed on this
         service."
    ::= { serviceEntry 6 }

svcAvgTransactionTime OBJECT-TYPE
    SYNTAX      TimeTicks
    MAX-ACCESS  read-only
    STATUS      current
    DESCRIPTION 
        "average transaction time between netscaler and the
         service behind it."
    ::= { serviceEntry 7 }

svcEstablishedConn OBJECT-TYPE
    SYNTAX      Counter32
    MAX-ACCESS  read-only
    STATUS      current
    DESCRIPTION 
        "number of established connection"
    ::= { serviceEntry 8 }

svcActiveConn OBJECT-TYPE
    SYNTAX      Counter32
    MAX-ACCESS  read-only
    STATUS      current
    DESCRIPTION 
        " The number of established connections that are currently active."
    ::= { serviceEntry 9 }

svcSurgeCount OBJECT-TYPE
    SYNTAX      Counter32
    MAX-ACCESS  read-only
    STATUS      current
    DESCRIPTION 
        "the number requests in the surge queue"
    ::= { serviceEntry 10 }

svcTotalRequestsLow OBJECT-TYPE
    SYNTAX      Counter32
    MAX-ACCESS  read-only
    STATUS      obsolete
    DESCRIPTION 
        "The total number of requests. low32 bits of 64bit counter."
    ::= { serviceEntry 11 }

svcTotalRequestsHigh OBJECT-TYPE
    SYNTAX      Counter32
    MAX-ACCESS  read-only
    STATUS      obsolete
    DESCRIPTION 
        " The total number of requests. high32 bits of 64bit counter."
    ::= { serviceEntry 12 }

svcTotalRequestBytesLow OBJECT-TYPE
    SYNTAX      Counter32
    MAX-ACCESS  read-only
    STATUS      obsolete
    DESCRIPTION 
        " The total number of request bytes. low32 bits of 64bit counter."
    ::= { serviceEntry 13 }

svcTotalRequestBytesHigh OBJECT-TYPE
    SYNTAX      Counter32
    MAX-ACCESS  read-only
    STATUS      obsolete
    DESCRIPTION 
        " The total number of request bytes. high32 bits of 64bit counter."
    ::= { serviceEntry 14 }

svcTotalResponsesLow OBJECT-TYPE
    SYNTAX      Counter32
    MAX-ACCESS  read-only
    STATUS      obsolete
    DESCRIPTION 
        " The total number of responses. low32 bits of 64bit counter."
    ::= { serviceEntry 15 }

svcTotalResponsesHigh OBJECT-TYPE
    SYNTAX      Counter32
    MAX-ACCESS  read-only
    STATUS      obsolete
    DESCRIPTION 
        " The total number of responses. high32 bits of 64bit counter."
    ::= { serviceEntry 16 }

svcTotalResponseBytesLow OBJECT-TYPE
    SYNTAX      Counter32
    MAX-ACCESS  read-only
    STATUS      obsolete
    DESCRIPTION 
        " The total response bytes. low32 bits of 64bit counter."
    ::= { serviceEntry 17 }

svcTotalResponseBytesHigh OBJECT-TYPE
    SYNTAX      Counter32
    MAX-ACCESS  read-only
    STATUS      obsolete
    DESCRIPTION 
        " The total response bytes. high32 bits of 64bit counter."
    ::= { serviceEntry 18 }

svcTotalPktsRecvdLow OBJECT-TYPE
    SYNTAX      Counter32
    MAX-ACCESS  read-only
    STATUS      obsolete
    DESCRIPTION 
        " The total packets received. low32 bits of 64bit counter."
    ::= { serviceEntry 19 }

svcTotalPktsRecvdHigh OBJECT-TYPE
    SYNTAX      Counter32
    MAX-ACCESS  read-only
    STATUS      obsolete
    DESCRIPTION 
        " The total packets received. high32 bits of 64bit counter."
    ::= { serviceEntry 20 }

svcTotalPktsSentLow OBJECT-TYPE
    SYNTAX      Counter32
    MAX-ACCESS  read-only
    STATUS      obsolete
    DESCRIPTION 
        " The total packets sent. low32 bits of 64bit counter."
    ::= { serviceEntry 21 }

svcTotalPktsSentHigh OBJECT-TYPE
    SYNTAX      Counter32
    MAX-ACCESS  read-only
    STATUS      obsolete
    DESCRIPTION 
        " The total packets sent. high32 bits of 64bit counter."
    ::= { serviceEntry 22 }

svcTotalSynsRecvdLow OBJECT-TYPE
    SYNTAX      Counter32
    MAX-ACCESS  read-only
    STATUS      obsolete
    DESCRIPTION 
        " The total number of syns received from clients on this service. 
         low32 bits of 64bit counter."
    ::= { serviceEntry 23 }

svcTotalSynsRecvdHigh OBJECT-TYPE
    SYNTAX      Counter32
    MAX-ACCESS  read-only
    STATUS      obsolete
    DESCRIPTION 
        " The total number of syns received from clients on this service.
         high32 bits of 64bit counter."
    ::= { serviceEntry 24 }

svcTotalRequests OBJECT-TYPE
    SYNTAX      Counter64
    MAX-ACCESS  read-only
    STATUS      current
    DESCRIPTION 
        "The total number of requests. "
    ::= { serviceEntry 30 }

svcTotalRequestBytes OBJECT-TYPE
    SYNTAX      Counter64
    MAX-ACCESS  read-only
    STATUS      current
    DESCRIPTION 
        " The total number of request bytes. "
    ::= { serviceEntry 31 }

svcTotalResponses OBJECT-TYPE
    SYNTAX      Counter64
    MAX-ACCESS  read-only
    STATUS      current
    DESCRIPTION 
        " The total number of responses. "
    ::= { serviceEntry 32 }

svcTotalResponseBytes OBJECT-TYPE
    SYNTAX      Counter64
    MAX-ACCESS  read-only
    STATUS      current
    DESCRIPTION 
        " The total response bytes. "
    ::= { serviceEntry 33 }

svcTotalPktsRecvd OBJECT-TYPE
    SYNTAX      Counter64
    MAX-ACCESS  read-only
    STATUS      current
    DESCRIPTION 
        " The total packets received. "
    ::= { serviceEntry 34 }

svcTotalPktsSent OBJECT-TYPE
    SYNTAX      Counter64
    MAX-ACCESS  read-only
    STATUS      current
    DESCRIPTION 
        " The total packets sent. "
    ::= { serviceEntry 35 }

svcTotalSynsRecvd OBJECT-TYPE
    SYNTAX      Counter64
    MAX-ACCESS  read-only
    STATUS      current
    DESCRIPTION 
        " The total number of syns received from clients on this service. 
         "
    ::= { serviceEntry 36 }

svcGslbSiteName   OBJECT-TYPE
    SYNTAX OCTET STRING
    MAX-ACCESS read-only
    STATUS current
    DESCRIPTION "The name of the gslb site on which this service is defined."
    ::= {  serviceEntry  37  }

serverTable OBJECT-TYPE
    SYNTAX SEQUENCE OF ServerEntry
    ACCESS not-accessible
    STATUS current
    DESCRIPTION
        "The servers table"
    ::= { nsSvcGroup 2}

serverEntry OBJECT-TYPE
    SYNTAX ServerEntry
    ACCESS not-accessible
    STATUS current
    DESCRIPTION
        "The server entry"
    INDEX { serverName }
    ::= { serverTable 1 }

ServerEntry ::=
    SEQUENCE {
        serverName      OCTET STRING,
        serverIpAddress IpAddress,
        serverState     EntityState,
        serverDelay     Integer32
    }

serverName OBJECT-TYPE
    SYNTAX OCTET STRING
    ACCESS read-only
    STATUS current
    DESCRIPTION
        "the name of the server."
    ::= { serverEntry 1  }

serverIpAddress  OBJECT-TYPE
    SYNTAX IpAddress
    ACCESS read-only
    STATUS current
    DESCRIPTION
        "the ip address of the server."
    ::= { serverEntry 2 }

serverState     OBJECT-TYPE
    SYNTAX EntityState
    ACCESS read-write
    STATUS current
    DESCRIPTION
        "the state of the server."
    ::= {serverEntry 3 }

serverDelay     OBJECT-TYPE
    SYNTAX Integer32
    ACCESS write-only
    STATUS current
    DESCRIPTION
        "Specifies time in seconds after which all services in this server are brought down"
    ::= { serverEntry 4 }

nsVserverGroup OBJECT IDENTIFIER
    ::= { rs9000 3 }

vserverTable OBJECT-TYPE
    SYNTAX      SEQUENCE OF VserverEntry
    MAX-ACCESS  not-accessible
    STATUS      current
    DESCRIPTION 
        "The vservers table"
    ::= { nsVserverGroup 1 }

vserverEntry OBJECT-TYPE
    SYNTAX      VserverEntry
    MAX-ACCESS  not-accessible
    STATUS      current
    DESCRIPTION 
        "the vserver entry"
    INDEX       { vsvrVserverName }
    ::= { vserverTable 1 }

VserverEntry ::= SEQUENCE {
    vsvrVserverName                 OCTET STRING,
    vserverIpAddress            IpAddress,
    vserverPort                 Integer32,
    vserverType                 EntityProtocolType,
    vserverState                EntityState,
    vsvrMaxReqPerConn           Counter32,
    vsvrCurClntConnections      Gauge32,
    vsvrCurSrvrConnections      Gauge32,
    vsvrAvgTransactionTime      TimeTicks,
    vsvrSurgeCount              Counter32,
    vsvrTotalRequestsLow        Counter32,
    vsvrTotalRequestsHigh       Counter32,
    vsvrTotalRequestBytesLow    Counter32,
    vsvrTotalRequestBytesHigh   Counter32,
    vsvrTotalResponsesLow       Counter32,
    vsvrTotalResponsesHigh      Counter32,
    vsvrTotalResponseBytesLow   Counter32,
    vsvrTotalResponseBytesHigh  Counter32,
    vsvrTotalPktsRecvdLow       Counter32,
    vsvrTotalPktsRecvdHigh      Counter32,
    vsvrTotalPktsSentLow        Counter32,
    vsvrTotalPktsSentHigh       Counter32,
    vsvrTotalSynsRecvdLow       Counter32,
    vsvrTotalSynsRecvdHigh      Counter32,
    vsvrTotalRequests	        Counter64,
    vsvrTotalRequestBytes	Counter64,
    vsvrTotalResponses       	Counter64,
    vsvrTotalResponseBytes   	Counter64,
    vsvrTotalPktsRecvd     	Counter64,
    vsvrTotalPktsSent        	Counter64,
    vsvrTotalSynsRecvd       	Counter64
}

vsvrVserverName OBJECT-TYPE
    SYNTAX      OCTET STRING
    MAX-ACCESS  read-only
    STATUS      current
    DESCRIPTION 
        "the name of the vserver"
    ::= { vserverEntry 1 }

vserverIpAddress OBJECT-TYPE
    SYNTAX      IpAddress
    MAX-ACCESS  read-only
    STATUS      current
    DESCRIPTION 
        "the ip address of the vserver"
    ::= { vserverEntry 2 }

vserverPort OBJECT-TYPE
    SYNTAX      Integer32
    MAX-ACCESS  read-only
    STATUS      current
    DESCRIPTION 
        "the port of the vserver"
    ::= { vserverEntry 3 }

vserverType OBJECT-TYPE
    SYNTAX      EntityProtocolType
    MAX-ACCESS  read-only
    STATUS      current
    DESCRIPTION 
        "the protocol type of the vserver"
    ::= { vserverEntry 4 }

vserverState OBJECT-TYPE
    SYNTAX      EntityState
    MAX-ACCESS  read-only
    STATUS      current
    DESCRIPTION 
        "the state of the vserver"
    ::= { vserverEntry 5 }

vsvrMaxReqPerConn OBJECT-TYPE
    SYNTAX      Counter32
    MAX-ACCESS  read-only
    STATUS      current
    DESCRIPTION 
        "OBSOLETE
         The maximum requests per connection permitted"
    ::= { vserverEntry 6 }

vsvrCurClntConnections OBJECT-TYPE
    SYNTAX      Gauge32
    MAX-ACCESS  read-only
    STATUS      current
    DESCRIPTION 
        "The number of current client connections to the vserver"
    ::= { vserverEntry 7 }

vsvrCurSrvrConnections OBJECT-TYPE
    SYNTAX      Gauge32
    MAX-ACCESS  read-only
    STATUS      current
    DESCRIPTION 
        "The number of current connections to the real servers behind
         the vserver."
    ::= { vserverEntry 8 }

vsvrAvgTransactionTime OBJECT-TYPE
    SYNTAX      TimeTicks
    MAX-ACCESS  read-only
    STATUS      obsolete
    DESCRIPTION 
        "OBSOLETE 
         the average transaction time."
    ::= { vserverEntry 9 }

vsvrSurgeCount OBJECT-TYPE
    SYNTAX      Counter32
    MAX-ACCESS  read-only
    STATUS      obsolete
    DESCRIPTION 
        "OBSOLETE 
         the number of requests in the surge queue"
    ::= { vserverEntry 10 }

vsvrTotalRequestsLow OBJECT-TYPE
    SYNTAX      Counter32
    MAX-ACCESS  read-only
    STATUS      obsolete
    DESCRIPTION 
        "The total number of requests. low32 bits of 64bit counter."
    ::= { vserverEntry 11 }

vsvrTotalRequestsHigh OBJECT-TYPE
    SYNTAX      Counter32
    MAX-ACCESS  read-only
    STATUS      obsolete
    DESCRIPTION 
        "The total number of requests. high32 bits of 64bit counter."
    ::= { vserverEntry 12 }

vsvrTotalRequestBytesLow OBJECT-TYPE
    SYNTAX      Counter32
    MAX-ACCESS  read-only
    STATUS      obsolete
    DESCRIPTION 
        "The total number of request bytes. low32 bits of 64bit counter."
    ::= { vserverEntry 13 }

vsvrTotalRequestBytesHigh OBJECT-TYPE
    SYNTAX      Counter32
    MAX-ACCESS  read-only
    STATUS      obsolete
    DESCRIPTION 
        "The total number of request bytes. high32 bits of 64bit counter."
    ::= { vserverEntry 14 }

vsvrTotalResponsesLow OBJECT-TYPE
    SYNTAX      Counter32
    MAX-ACCESS  read-only
    STATUS      obsolete
    DESCRIPTION 
        "The total number of responses. low32 bits of 64bit counter."
    ::= { vserverEntry 15 }

vsvrTotalResponsesHigh OBJECT-TYPE
    SYNTAX      Counter32
    MAX-ACCESS  read-only
    STATUS      obsolete
    DESCRIPTION 
        "The total number of responses. high32 bits of 64bit counter."
    ::= { vserverEntry 16 }

vsvrTotalResponseBytesLow OBJECT-TYPE
    SYNTAX      Counter32
    MAX-ACCESS  read-only
    STATUS      obsolete
    DESCRIPTION 
        "The total number of response bytes. low32 bits of 64bit counter."
    ::= { vserverEntry 17 }

vsvrTotalResponseBytesHigh OBJECT-TYPE
    SYNTAX      Counter32
    MAX-ACCESS  read-only
    STATUS      obsolete
    DESCRIPTION 
        "The total number of response bytes. high32 bits of 64bit counter."
    ::= { vserverEntry 18 }

vsvrTotalPktsRecvdLow OBJECT-TYPE
    SYNTAX      Counter32
    MAX-ACCESS  read-only
    STATUS      obsolete
    DESCRIPTION 
        "The total number of packets received. low32 bits of 64bit counter."
    ::= { vserverEntry 19 }

vsvrTotalPktsRecvdHigh OBJECT-TYPE
    SYNTAX      Counter32
    MAX-ACCESS  read-only
    STATUS      obsolete
    DESCRIPTION 
        "The total number of packets received. high32 bits of 64bit counter."
    ::= { vserverEntry 20 }

vsvrTotalPktsSentLow OBJECT-TYPE
    SYNTAX      Counter32
    MAX-ACCESS  read-only
    STATUS      obsolete
    DESCRIPTION 
        "The total number of packets sent. low32 bits of 64bit counter."
    ::= { vserverEntry 21 }

vsvrTotalPktsSentHigh OBJECT-TYPE
    SYNTAX      Counter32
    MAX-ACCESS  read-only
    STATUS      obsolete
    DESCRIPTION 
        "The total number of packets sent. high32 bits of 64bit counter."
    ::= { vserverEntry 22 }

vsvrTotalSynsRecvdLow OBJECT-TYPE
    SYNTAX      Counter32
    MAX-ACCESS  read-only
    STATUS      obsolete
    DESCRIPTION 
        "The total number of Syns received from clients on this vserver. 
         low32 bits of 64bit counter."
    ::= { vserverEntry 23 }

vsvrTotalSynsRecvdHigh OBJECT-TYPE
    SYNTAX      Counter32
    MAX-ACCESS  read-only
    STATUS      obsolete
    DESCRIPTION 
        "The total number of Syns received from clients on this vserver. 
         high32 bits of 64bit counter."
    ::= { vserverEntry 24 }

vsvrTotalRequests OBJECT-TYPE
    SYNTAX      Counter64
    MAX-ACCESS  read-only
    STATUS      current
    DESCRIPTION 
        "The total number of requests. "
    ::= { vserverEntry 30 }

vsvrTotalRequestBytes OBJECT-TYPE
    SYNTAX      Counter64
    MAX-ACCESS  read-only
    STATUS      current
    DESCRIPTION 
        "The total number of request bytes. "
    ::= { vserverEntry 31 }

vsvrTotalResponses OBJECT-TYPE
    SYNTAX      Counter64
    MAX-ACCESS  read-only
    STATUS      current
    DESCRIPTION 
        "The total number of responses. "
    ::= { vserverEntry 32 }

vsvrTotalResponseBytes OBJECT-TYPE
    SYNTAX      Counter64
    MAX-ACCESS  read-only
    STATUS      current
    DESCRIPTION 
        "The total number of response bytes. "
    ::= { vserverEntry 33 }

vsvrTotalPktsRecvd OBJECT-TYPE
    SYNTAX      Counter64
    MAX-ACCESS  read-only
    STATUS      current
    DESCRIPTION 
        "The total number of packets received. "
    ::= { vserverEntry 34 }

vsvrTotalPktsSent OBJECT-TYPE
    SYNTAX      Counter64
    MAX-ACCESS  read-only
    STATUS      current
    DESCRIPTION 
        "The total number of packets sent. "
    ::= { vserverEntry 35 }

vsvrTotalSynsRecvd OBJECT-TYPE
    SYNTAX      Counter64
    MAX-ACCESS  read-only
    STATUS      current
    DESCRIPTION 
        "The total number of Syns received from clients on this vserver. 
         "
    ::= { vserverEntry 36 }

vserverServiceTable OBJECT-TYPE
    SYNTAX      SEQUENCE OF VserverServiceEntry
    MAX-ACCESS  not-accessible
    STATUS      current
    DESCRIPTION 
        "the vserver service relationship table"
    ::= { nsVserverGroup 2 }

vserverServiceEntry OBJECT-TYPE
    SYNTAX      VserverServiceEntry
    MAX-ACCESS  not-accessible
    STATUS      current
    DESCRIPTION 
        "the vserver service relationship entry"
    INDEX       { vsvrVserverName, svcServiceName }
    ::= { vserverServiceTable 1 }

VserverServiceEntry ::= SEQUENCE {
    serviceHitsLow              Counter32,
    serviceHitsHigh             Counter32,
    servicePersistentHitsLow    Counter32,
    servicePersistentHitsHigh   Counter32,
    vsvrServiceHits          	Counter64,
    servicePersistentHits    	Counter64,
    serviceWeight		Integer32
}

serviceHitsLow OBJECT-TYPE
    SYNTAX      Counter32
    MAX-ACCESS  read-only
    STATUS      obsolete
    DESCRIPTION 
        "This represents the number of times that the service 
         has been provided. low32 bits of 64bit counter."
    ::= { vserverServiceEntry 1 }

serviceHitsHigh OBJECT-TYPE
    SYNTAX      Counter32
    MAX-ACCESS  read-only
    STATUS      obsolete
    DESCRIPTION 
        "This represents the number of times that the service 
         has been provided. high32 bits of 64bit counter."
    ::= { vserverServiceEntry 2 }

servicePersistentHitsLow OBJECT-TYPE
    SYNTAX      Counter32
    MAX-ACCESS  read-only
    STATUS      obsolete
    DESCRIPTION 
        " The total number of persistent hits. low32 bits of 64bit counter."
    ::= { vserverServiceEntry 3 }

servicePersistentHitsHigh OBJECT-TYPE
    SYNTAX      Counter32
    MAX-ACCESS  read-only
    STATUS      obsolete
    DESCRIPTION 
        " The total number of persistent hits. high32 bits of 64bit counter."
    ::= { vserverServiceEntry 4 }

vsvrServiceHits OBJECT-TYPE
    SYNTAX      Counter64
    MAX-ACCESS  read-only
    STATUS      current
    DESCRIPTION 
        "This represents the number of times that the service 
         has been provided. "
    ::= { vserverServiceEntry 5 }

servicePersistentHits OBJECT-TYPE
    SYNTAX      Counter64
    MAX-ACCESS  read-only
    STATUS      current
    DESCRIPTION 
        " The total number of persistent hits. "
    ::= { vserverServiceEntry 6 }

serviceWeight OBJECT-TYPE
    SYNTAX Integer32
    ACCESS read-write
    STATUS current
    DESCRIPTION
        " The weight of the service tied to the vserver."
    ::= { vserverServiceEntry 7 }

vserverCspolicyTable OBJECT-TYPE
    SYNTAX      SEQUENCE OF VserverCspolicyEntry
    MAX-ACCESS  not-accessible
    STATUS      current
    DESCRIPTION 
        "the vserver content switching policy relationship table"
    ::= { nsVserverGroup 3 }

vserverCspolicyEntry OBJECT-TYPE
    SYNTAX      VserverCspolicyEntry
    MAX-ACCESS  not-accessible
    STATUS      current
    DESCRIPTION 
        "the vserver content switching policy relationship entry"
    INDEX       { vsvrVserverName, cspolicyName }
    ::= { vserverCspolicyTable 1 }

VserverCspolicyEntry ::= SEQUENCE {
    cspolicyName                OCTET STRING,
    cspolicyDestVserverName     OCTET STRING,
    cspolicyHitsLow             Counter32,
    cspolicyHitsHigh            Counter32,
    cspolicyHits	        Counter64
}

cspolicyName OBJECT-TYPE
    SYNTAX      OCTET STRING
    MAX-ACCESS  read-only
    STATUS      current
    DESCRIPTION 
        "This represents the name of the policy bound to 
         content switching vserver "
    ::= { vserverCspolicyEntry 1 }

cspolicyDestVserverName OBJECT-TYPE
    SYNTAX      OCTET STRING
    MAX-ACCESS  read-only
    STATUS      current
    DESCRIPTION 
        "This represents the name of the destination vserver to 
         which the request has to be directed to if the content 
         switching policy evaluates to true."
    ::= { vserverCspolicyEntry 2 }

cspolicyHitsLow OBJECT-TYPE
    SYNTAX      Counter32
    MAX-ACCESS  read-only
    STATUS      obsolete
    DESCRIPTION 
        "This represents the number of hits on this policy.
         low32 bits of the 64 bit counter."
    ::= { vserverCspolicyEntry 3 }

cspolicyHitsHigh OBJECT-TYPE
    SYNTAX      Counter32
    MAX-ACCESS  read-only
    STATUS      obsolete
    DESCRIPTION 
        "This represents the number of hits on this policy.
         low32 bits of the 64 bit counter."
    ::= { vserverCspolicyEntry 4 }

cspolicyHits OBJECT-TYPE
    SYNTAX      Counter64
    MAX-ACCESS  read-only
    STATUS      current
    DESCRIPTION 
        "This represents the number of hits on this policy."
    ::= { vserverCspolicyEntry 5 }

vserverCrpolicyTable OBJECT-TYPE
    SYNTAX      SEQUENCE OF VserverCrpolicyEntry
    MAX-ACCESS  not-accessible
    STATUS      current
    DESCRIPTION 
        "the vserver cache redirection policy relationship table"
    ::= { nsVserverGroup 4 }

vserverCrpolicyEntry OBJECT-TYPE
    SYNTAX      VserverCrpolicyEntry
    MAX-ACCESS  not-accessible
    STATUS      current
    DESCRIPTION 
        "the vserver cache redirection policy relationship entry"
    INDEX       { vsvrVserverName, crpolicyName }
    ::= { vserverCrpolicyTable 1 }

VserverCrpolicyEntry ::= SEQUENCE {
    crpolicyName        OCTET STRING,
    crpolicyHitsLow     Counter32,
    crpolicyHitsHigh    Counter32,
    crpolicyHits	Counter64
}

crpolicyName OBJECT-TYPE
    SYNTAX      OCTET STRING
    MAX-ACCESS  read-only
    STATUS      current
    DESCRIPTION 
        "This represents the name of the policy bound 
         to cache-redirection vserver "
    ::= { vserverCrpolicyEntry 1 }

crpolicyHitsLow OBJECT-TYPE
    SYNTAX      Counter32
    MAX-ACCESS  read-only
    STATUS      obsolete
    DESCRIPTION 
        "This represents the hits on the cr policy. low32 bits of the
         64 bit counter"
    ::= { vserverCrpolicyEntry 2 }

crpolicyHitsHigh OBJECT-TYPE
    SYNTAX      Counter32
    MAX-ACCESS  read-only
    STATUS      obsolete
    DESCRIPTION 
        "This represents the hits on the cr policy. high32 bits of the
         64 bit counter"
    ::= { vserverCrpolicyEntry 3 }

crpolicyHits OBJECT-TYPE
    SYNTAX      Counter64
    MAX-ACCESS  read-only
    STATUS      current
    DESCRIPTION 
        "This represents the hits on the cr policy. "
    ::= { vserverCrpolicyEntry 4 }
  
netScalerEventsV2 OBJECT-IDENTITY
	STATUS		current
	DESCRIPTION	
		"The events for NetScaler"
	::= { netScalerEvents 0 }
	
changeToPrimary NOTIFICATION-TYPE
    STATUS      current
    DESCRIPTION 
        "This trap indicates that the netscaler is now operating
         in the primary mode."
    ::= { netScalerEventsV2 1 }

changeToSecondary NOTIFICATION-TYPE
    STATUS      current
    DESCRIPTION 
        "This trap indicates that the netscaler is now operating
         in the Secondary mode."
    ::= { netScalerEventsV2 2 }

cpuUtilization NOTIFICATION-TYPE
    STATUS      current
    DESCRIPTION 
        "This trap indicates that the CPU utilization has exceeded the high threshold"
    ::= { netScalerEventsV2 3 }

linkUp NOTIFICATION-TYPE
    STATUS      obsolete
    DESCRIPTION 
        "The link of the netscaler is up. OBSOLETE"
    ::= { netScalerEventsV2 4 }

linkDown NOTIFICATION-TYPE
    STATUS      obsolete
    DESCRIPTION 
        "The link of the netscaler is down. OBSOLETE"
    ::= { netScalerEventsV2 5 }

discoverFailure NOTIFICATION-TYPE
    STATUS      obsolete
    DESCRIPTION 
        "This indicates the netscaler failed to discover its 
         peer. OBSOLETE"
    ::= { netScalerEventsV2 6 }

memUtilization NOTIFICATION-TYPE
    STATUS      obsolete
    DESCRIPTION 
        "This indicates the utilization of netscaler memory. 
         OBSOLETE"
    ::= { netScalerEventsV2 7 }

entitydown NOTIFICATION-TYPE
    STATUS      current
    DESCRIPTION 
        "This trap is sent when the state of interface, vserver 
         or physical	service changed to DOWN"
    ::= { netScalerEventsV2 8 }

entityup NOTIFICATION-TYPE
    STATUS      current
    DESCRIPTION 
        "This trap is sent when the state of interface, vserver 
         or physical	service changed to UP"
    ::= { netScalerEventsV2 9 }

synflood NOTIFICATION-TYPE
    STATUS      current
    DESCRIPTION 
        "This trap is sent when the rate at which unacknowledged
         SYNs are received cross a threshold value"
    ::= { netScalerEventsV2 10 }

cpuUtilizationNormal NOTIFICATION-TYPE
    STATUS      current
    DESCRIPTION 
        "This trap indicates that the CPU utilization has come back to normal"
    ::= { netScalerEventsV2 11 }

synfloodNormal NOTIFICATION-TYPE
    STATUS      current
    DESCRIPTION 
        "This trap is sent when the rate at which unacknowledged
         SYNs are received returns to normal"
    ::= { netScalerEventsV2 12 }

memoryUtilization NOTIFICATION-TYPE
    STATUS      current
    DESCRIPTION	
	"This trap is sent when the memory utilization of the system exceeds the threshold value"
    ::= { netScalerEventsV2 13 }

memoryUtilizationNormal NOTIFICATION-TYPE
    STATUS      current
    DESCRIPTION
    	"This trap is sent when the memory utilization of the system returns to normal"
    ::= { netScalerEventsV2 14 }

vServerRequestRate NOTIFICATION-TYPE
	STATUS      current
	DESCRIPTION
		"This trap is sent when the request rate on a vServer exceeds a threshold value"
	::= { netScalerEventsV2 15 }

vServerRequestRateNormal NOTIFICATION-TYPE
	STATUS      current
	DESCRIPTION
		"This trap is sent when the request rate on a vServer returns to normal"
	::= { netScalerEventsV2 16 }

serviceRequestRate NOTIFICATION-TYPE
	STATUS      current
	DESCRIPTION
		"This trap is sent when the request rate on a service exceeds a threshold value"
	::= { netScalerEventsV2 17 }

serviceRequestRateNormal NOTIFICATION-TYPE
	STATUS      current
	DESCRIPTION
		"This trap is sent when the request rate on a service returns to normal"
	::= { netScalerEventsV2 18 }

entityRxRate NOTIFICATION-TYPE
	STATUS      current
	DESCRIPTION	
		"This trap is sent when the request bytes/s of a vServer / Service exceeds a threshold value"
	::= { netScalerEventsV2 19 }

entityRxRateNormal NOTIFICATION-TYPE
	STATUS      current
	DESCRIPTION	
		"This trap is sent when the request bytes/s of a vServer / Service returns to normal"
	::= { netScalerEventsV2 20 }

entityTxRate NOTIFICATION-TYPE
	STATUS      current
	DESCRIPTION	
		"This trap is sent when the response bytes/s of a vServer / Service exceeds a threshold value"
	::= { netScalerEventsV2 21  }

entityTxRateNormal NOTIFICATION-TYPE
	STATUS      current
	DESCRIPTION	
		"This trap is sent when the response bytes/s of a vServer / Service returns to normal"
	::= { netScalerEventsV2 22 }

entitySynflood NOTIFICATION-TYPE
	STATUS      current
	DESCRIPTION
		"This trap is sent when the number of unacknowledged syns for a vServer / Service exceeds a threshold value"
	::= { netScalerEventsV2 23 }

entitySynfloodNormal NOTIFICATION-TYPE
	STATUS      current
	DESCRIPTION
		"This trap is sent when the number of unacknowledged syns for a vServer / Service returns to normal"
	::= { netScalerEventsV2 24 }

netScalerConfigChange NOTIFICATION-TYPE
	STATUS      current
	DESCRIPTION
		"This trap is sent when the configuration on the NetScaler is changed."
	::= { netScalerEventsV2 25 }

maxClients NOTIFICATION-TYPE
	STATUS      current
	DESCRIPTION
		"This trap is sent when the number of clients hits the maxClients value for a service"
	::= { netScalerEventsV2 26 }

maxClientsNormal NOTIFICATION-TYPE
	STATUS      current
	DESCRIPTION
		"This trap is sent when the number of clients falls below maxClients value for a service"
	::= { netScalerEventsV2 27 }

END -- end of module NS-ROOT-MIB.
