-- *****************************************************************************
-- Unisphere-Data-DS3-MIB
--
-- Unisphere Networks Inc. Enterprise MIB
-- DS3 MIB
--
-- Copyright (c) 1998, 1999 Redstone Communications, Incorporated.
-- Copyright (c) 1999, 2002 Unisphere Networks, Incorporated.
-- All Rights Reserved.
-- *****************************************************************************

Unisphere-Data-DS3-MIB DEFINITIONS ::= BEGIN

IMPORTS
    MODULE-IDENTITY, OBJECT-TYPE, Integer32
        FROM SNMPv2-SMI
    MODULE-COMPLIANCE, OBJECT-GROUP
        FROM SNMPv2-CONF
    ifIndex, InterfaceIndexOrZero
        FROM IF-MIB
    TruthValue, RowStatus, DisplayString
        FROM SNMPv2-TC
    UsdNextIfIndex
        FROM Unisphere-Data-TC
    usDataMibs
        FROM Unisphere-Data-MIBs
    PerfCurrentCount, PerfIntervalCount, PerfTotalCount
        FROM PerfHist-TC-MIB
    dsx3FarEndCurrentEntry, dsx3FarEndIntervalEntry, dsx3FarEndTotalEntry
        FROM RFC1407-MIB;

usdDs3MIB  MODULE-IDENTITY
    LAST-UPDATED "200204041407Z"  -- 04-Apr-02 09:07 AM EST
    ORGANIZATION "Unisphere Networks, Inc."
    CONTACT-INFO
        "       Unisphere Networks, Inc.
        Postal: 10 Technology Park Drive
                Westford, MA  01886
                USA
        Tel:    +1 978 589 5800
        E-mail: mib@UnisphereNetworks.com"
    DESCRIPTION
        "The DS3 MIB for the Unisphere Networks Inc. enterprise."
    -- Revision History
    REVISION    "200204041407Z"  -- 04-Apr-02 09:07 AM EST  - RX 4.0
    DESCRIPTION
        "Added invalid seconds objects to the far end statistics tables and more
        configuration objects."
    REVISION    "200202222121Z"  -- 22-Feb-02 04:21 PM EST  - RX 3.3
    DESCRIPTION
        "Modified the valid range for usdDsx3Ds3Channel"
    REVISION    "200104271949Z"  -- 27-Apr-01 03:49 PM EDT  - RX 3.0
    DESCRIPTION
        "Added dynamic DS3 interface support."
    REVISION    "200102050000Z"  -- 05-Feb-01               - RX 2.6
    DESCRIPTION
        "Added following objects:
             usdDsx3Ds3DsuMode
             usdDsx3Ds3BandwidthLimit
             usdDsx3Ds3DsuScrambleMode"
    REVISION      "9907270000Z"  -- 27-Jul-99               - RX 1.1
    DESCRIPTION
        "Added usdDsx3LineType and usdDsx3CellScramblerConfig."
    REVISION      "9811130000Z"  -- 13-Nov-98               - RX 1.0
    DESCRIPTION
        "Initial version of this MIB module."
    ::= { usDataMibs 4 }


-- +++++++++++++++++++++++++++++++++++++++++++++++++++++++++++++++++++++++++++++
-- Textual conventions
-- +++++++++++++++++++++++++++++++++++++++++++++++++++++++++++++++++++++++++++++
-- No textual conventions are defined in this MIB


-- +++++++++++++++++++++++++++++++++++++++++++++++++++++++++++++++++++++++++++++
-- Managed objects
-- +++++++++++++++++++++++++++++++++++++++++++++++++++++++++++++++++++++++++++++
usdDs3Objects     OBJECT IDENTIFIER ::= { usdDs3MIB 1 }

--
-- This MIB contains managed objects for DS3/E3 interfaces.
-- Management objects are provided to supplement those
-- found in RFC1407 DS3/E3 MIB.
--

-- /////////////////////////////////////////////////////////////////////////////
--
-- DS3 Interfaces
--
-- /////////////////////////////////////////////////////////////////////////////
--
-- The DS3 Configuration Table
--
usdDsx3ConfigTable  OBJECT-TYPE
    SYNTAX      SEQUENCE OF UsdDsx3ConfigEntry
    MAX-ACCESS  not-accessible
    STATUS      current
    DESCRIPTION
        "This table contains entries for DS3/E3 interfaces present in the
        system."
    ::= { usdDs3Objects 1 }

usdDsx3ConfigEntry  OBJECT-TYPE
    SYNTAX      UsdDsx3ConfigEntry
    MAX-ACCESS  not-accessible
    STATUS      current
    DESCRIPTION
        "Each entry describes the characteristics of an DS3/E3 interface."
    INDEX     { ifIndex }
    ::= { usdDsx3ConfigTable 1 }

UsdDsx3ConfigEntry ::= SEQUENCE {
    usdDsx3LineLength           Integer32,
    usdDsx3LineType             INTEGER,
    usdDsx3CellScramblerConfig  INTEGER,
    usdDsx3Channelization       TruthValue,
    usdDsx3InterfaceType        INTEGER,
    usdDsx3Application          INTEGER,
    usdDsx3Ds3Channel           INTEGER,
    usdDsx3LowerIfIndex         InterfaceIndexOrZero,
    usdDsx3RowStatus            RowStatus,
    usdDsx3Ds3DsuMode           INTEGER,
    usdDsx3Ds3BandwidthLimit    INTEGER,
    usdDsx3Ds3DsuScrambleMode   INTEGER,
    usdDsx3MdlCarrier           INTEGER,
    usdDsx3MdlTransmit          INTEGER,
    usdDsx3MdlEic               DisplayString,
    usdDsx3MdlLic               DisplayString,
    usdDsx3MdlFic               DisplayString,
    usdDsx3MdlUnit              DisplayString,
    usdDsx3MdlPfi               DisplayString,
    usdDsx3MdlPort              DisplayString,
    usdDsx3MdlGenerator         DisplayString }

usdDsx3LineLength  OBJECT-TYPE
    SYNTAX      Integer32 (0..64000)
    UNITS       "meters"
    MAX-ACCESS  read-create
    STATUS      current
    DESCRIPTION
        "The length of the DS3/E3 line in meters.  This objects provides
        information for line build out circuitry.  This object is only useful if
        the interface has configurable line build out circuitry."
    ::= { usdDsx3ConfigEntry 1 }

usdDsx3LineType  OBJECT-TYPE
    SYNTAX      INTEGER {
                    usdDsx3other(1),
                    usdDsx3M23(2),
                    usdDsx3SYNTRAN(3),
                    usdDsx3CbitParity(4),
                    usdDsx3ClearChannel(5),
                    usdE3G832(6),
                    usdE3Framed(7),
                    usdE3Plcp(8),
                    usdDsx3M23Plcp(18),
                    usdDsx3CbitParityPlcp(20) }
    MAX-ACCESS  read-create
    STATUS      current
    DESCRIPTION
        "This variable indicates the variety of DS3 C-bit or E3 application
        implementing this interface.  The type of interface affects the
        interpretation of the usage and error statistics.  The rate of DS3 is
        44.736 Mbps and E3 is 34.368 Mbps.  The dsx3ClearChannel value means
        that the C-bits are not used except for sending/receiving AIS.  Note
        that this object represents the actual line type when the corresponding
        value of dsx3LineType is dsx3other(1).

        The values, in sequence, describe:
             TITLE:              SPECIFICATION:
             dsx3M23             ANSI T1.107-1988
             dsx3SYNTRAN         ANSI T1.107-1988
             dsx3CbitParity      ANSI T1.107a-1989
             dsx3ClearChannel    ANSI T1.102-1987
             e3G832              ITU-T G.832
             e3Framed            ITU-T G.751
             e3Plcp              ETSI T/NA(91)18.
             dsx3M23Plcp         ATM Forum af-phy-0054.000
             dsx3CbitParityPlcp  ATM Forum af-phy-0054.000 "
    ::= { usdDsx3ConfigEntry 2 }

usdDsx3CellScramblerConfig  OBJECT-TYPE
    SYNTAX      INTEGER {
                    scramblerOn(1),
                    scramblerOff(2),
                    notSupported(3) }
    MAX-ACCESS  read-create
    STATUS      current
    DESCRIPTION
        "This variable indicates the state of the ATM cell scrambler for
        interfaces which support ATM over DS3 or E3.  For interfaces which do
        not support ATM, this object returns the value notSupported(3)."
    ::= { usdDsx3ConfigEntry 3 }

usdDsx3Channelization  OBJECT-TYPE
    SYNTAX      TruthValue
    MAX-ACCESS  read-create
    STATUS      current
    DESCRIPTION
        "The channelization setting for this DS3 interface; true(1) indicates
        channelization, false(2) indicates no channelization."
    ::= { usdDsx3ConfigEntry 4 }

usdDsx3InterfaceType  OBJECT-TYPE
    SYNTAX      INTEGER {
                    ds3T3(0),
                    ds3E3(1) }
    MAX-ACCESS  read-create
    STATUS      current
    DESCRIPTION
        "The DS3 interface type setting."
    ::= { usdDsx3ConfigEntry 5 }

usdDsx3Application  OBJECT-TYPE
    SYNTAX      INTEGER {
                    ds3FrameOverDs3(0),
                    ds3AtmOverDs3(1) }
    MAX-ACCESS  read-create
    STATUS      current
    DESCRIPTION
        "The interface application setting."
    ::= { usdDsx3ConfigEntry 6 }

usdDsx3Ds3Channel  OBJECT-TYPE
    SYNTAX      INTEGER (1..28)
    MAX-ACCESS  read-create
    STATUS      current
    DESCRIPTION
        "The DS3 channel setting.  The range of channel settings depends on the
        line rate of the underlying interface."
    ::= { usdDsx3ConfigEntry 7 }

usdDsx3LowerIfIndex  OBJECT-TYPE
    SYNTAX      InterfaceIndexOrZero
    MAX-ACCESS  read-create
    STATUS      current
    DESCRIPTION
        "The ifIndex of the interface over which this DS3 interface is to be
        layered.  A value of zero indicates no layering.  An implementation may
        choose to require that a nonzero value be configured at entry creation."
    ::= { usdDsx3ConfigEntry 8 }

usdDsx3RowStatus  OBJECT-TYPE
    SYNTAX      RowStatus
    MAX-ACCESS  read-create
    STATUS      current
    DESCRIPTION
        "Controls creation/deletion of entries in this table according to the
        RowStatus textual convention, constrained to support setting the
        following values only:
            createAndGo
            destroy

        To create an entry in this table, the following entry objects MUST be
        explicitly configured:
            usdDsx3RowStatus
            usdDsx3LowerIfIndex

        In addition, when creating an entry the following conditions must hold:

            A value for ifIndex must have been determined previously, by reading
            usdDsx3NextIfIndex.

            The interface identified by usdDsx3LowerIfIndex must exist.

        A corresponding entry in ifTable/ifXTable/usdIfTable is created/destroyed
        as a result of creating/destroying an entry in this table."
    ::= { usdDsx3ConfigEntry 9 }

usdDsx3Ds3DsuMode  OBJECT-TYPE
    SYNTAX      INTEGER {
                    ds3DsuModeNone(0),
                    ds3DsuLarsCom(2),
                    ds3DsuDigitalLink(4) }
    MAX-ACCESS  read-create
    STATUS      current
    DESCRIPTION
        "The DSU configuration setting for this entry."
    DEFVAL    { ds3DsuModeNone }
    ::= { usdDsx3ConfigEntry 10 }

usdDsx3Ds3BandwidthLimit  OBJECT-TYPE
    SYNTAX      INTEGER (0..44210)
    MAX-ACCESS  read-create
    STATUS      current
    DESCRIPTION
        "The DSU bandwidth configuration for this entry."
    DEFVAL {0}
    ::= { usdDsx3ConfigEntry 11 }

usdDsx3Ds3DsuScrambleMode  OBJECT-TYPE
    SYNTAX      INTEGER {
                    ds3DsuScrambleDisabled(0),
                    ds3DsuScrambleEnable(1) }
    MAX-ACCESS  read-create
    STATUS      current
    DESCRIPTION
        "The DSU scramble mode setting for this entry."
    DEFVAL    { ds3DsuScrambleDisabled }
    ::= { usdDsx3ConfigEntry 12 }

usdDsx3MdlCarrier  OBJECT-TYPE
    SYNTAX  INTEGER {
                disabled(0),
                enabled(1) }
    MAX-ACCESS  read-create
    STATUS      current
    DESCRIPTION
         "Specifies the interface is used in carrier environment."
    DEFVAL    { disabled }
    ::= { usdDsx3ConfigEntry 13 }

usdDsx3MdlTransmit  OBJECT-TYPE
    SYNTAX      INTEGER {
                    path(1),
                    idlesignal(2),
                    testsignal(4),
                    none(8) }
    MAX-ACCESS  read-create
    STATUS      current
    DESCRIPTION
         "Specifies transmission enabling."
    DEFVAL    { none }
    ::= { usdDsx3ConfigEntry 14 }

usdDsx3MdlEic  OBJECT-TYPE
    SYNTAX      DisplayString (SIZE(0..10))
    MAX-ACCESS  read-create
    STATUS      current
    DESCRIPTION
        "This is the equipment identification code."
    DEFVAL    { "" }
    ::= { usdDsx3ConfigEntry 15 }

usdDsx3MdlLic  OBJECT-TYPE
    SYNTAX      DisplayString (SIZE(0..11))
    MAX-ACCESS  read-create
    STATUS      current
    DESCRIPTION
        "This is the location identification code."
    DEFVAL    { "" }
    ::= { usdDsx3ConfigEntry 16 }

usdDsx3MdlFic  OBJECT-TYPE
    SYNTAX      DisplayString (SIZE(0..10))
    MAX-ACCESS  read-create
    STATUS      current
    DESCRIPTION
        "This is the frame identification code."
    DEFVAL    { "" }
    ::= { usdDsx3ConfigEntry 17 }

usdDsx3MdlUnit  OBJECT-TYPE
    SYNTAX      DisplayString (SIZE(0..6))
    MAX-ACCESS  read-create
    STATUS      current
    DESCRIPTION
        "This is the unit identification code."
    ::= { usdDsx3ConfigEntry 18 }

usdDsx3MdlPfi  OBJECT-TYPE
    SYNTAX      DisplayString (SIZE(0..38))
    MAX-ACCESS  read-create
    STATUS      current
    DESCRIPTION
        "This is the facility identification code to send in the MDL path
        message."
    DEFVAL    { "" }
    ::= { usdDsx3ConfigEntry 19 }

usdDsx3MdlPort  OBJECT-TYPE
    SYNTAX      DisplayString (SIZE(0..38))
    MAX-ACCESS  read-create
    STATUS      current
    DESCRIPTION
        "This is the equipment port number to send in the MDL idle signal
        message."
    ::= { usdDsx3ConfigEntry 20 }

usdDsx3MdlGenerator  OBJECT-TYPE
    SYNTAX      DisplayString (SIZE(0..38))
    MAX-ACCESS  read-create
    STATUS      current
    DESCRIPTION
        "This is the generator number to send in the MDL test signal message."
    ::= { usdDsx3ConfigEntry 21 }


usdDs3NextIfIndex  OBJECT-TYPE
    SYNTAX      UsdNextIfIndex
    MAX-ACCESS  read-only
    STATUS      current
    DESCRIPTION
        "Coordinate ifIndex value allocation for entries in usdDsx3ConfigTable.

        A GET of this object returns the next available ifIndex value to be used
        to create an entry in the associated interface table; or zero, if no
        valid ifIndex value is available.  This object also returns a value of
        zero when it is the lexicographic successor of a varbind presented in an
        SNMP GETNEXT or GETBULK request, for which circumstance it is assumed
        that ifIndex allocation is unintended.

        Successive GETs will typically return different values, thus avoiding
        collisions among cooperating management clients seeking to create table
        entries simultaneously."
    ::= { usdDs3Objects 2 }


--
-- The DS3 Far End Table
--
-- the DS3 Far End Current
-- The DS3 Far End current table contains statistics being
-- collected for the current 15 minute interval.
--
usdDsx3FarEndCurrentTable  OBJECT-TYPE
    SYNTAX      SEQUENCE OF UsdDsx3FarEndCurrentEntry
    MAX-ACCESS  not-accessible
    STATUS      current
    DESCRIPTION
        "This table contains entries for DS3/E3 interfaces present in the
        system."
    ::= { usdDs3Objects 3 }

usdDsx3FarEndCurrentEntry  OBJECT-TYPE
    SYNTAX      UsdDsx3FarEndCurrentEntry
    MAX-ACCESS  not-accessible
    STATUS      current
    DESCRIPTION
        "Each entry describes the characteristics of an DS3/E3 interface."
    AUGMENTS  { dsx3FarEndCurrentEntry }
    ::= { usdDsx3FarEndCurrentTable 1 }

UsdDsx3FarEndCurrentEntry ::= SEQUENCE {
    usdDsx3FarEndCurrentInvalidSeconds
        PerfCurrentCount
    }

usdDsx3FarEndCurrentInvalidSeconds  OBJECT-TYPE
    SYNTAX      PerfCurrentCount
    MAX-ACCESS  read-only
    STATUS      current
    DESCRIPTION
        "The counter associated with the number of Invalid Seconds encountered
        by a DS3/E3 interface in the current 15 minute interval."
    ::= { usdDsx3FarEndCurrentEntry 1 }

--
-- the DS3 Far End Interval
-- The DS3 Far End Interval Table contains statistics collected by each DS3
-- Interface over the previous 24 hours of operation.  The past 24 hours are
-- broken into 96 completed 15 minute intervals.
--
usdDsx3FarEndIntervalTable  OBJECT-TYPE
    SYNTAX      SEQUENCE OF UsdDsx3FarEndIntervalEntry
    MAX-ACCESS  not-accessible
    STATUS      current
    DESCRIPTION
        "This table contains entries for DS3/E3 interfaces present in the
        system."
    ::= { usdDs3Objects 4 }

usdDsx3FarEndIntervalEntry  OBJECT-TYPE
    SYNTAX      UsdDsx3FarEndIntervalEntry
    MAX-ACCESS  not-accessible
    STATUS      current
    DESCRIPTION
        "Each entry describes the characteristics of an DS3/E3 interface."
    AUGMENTS  { dsx3FarEndIntervalEntry }
    ::= { usdDsx3FarEndIntervalTable 1 }

UsdDsx3FarEndIntervalEntry ::= SEQUENCE {
    usdDsx3FarEndIntervalInvalidSeconds PerfIntervalCount }

usdDsx3FarEndIntervalInvalidSeconds  OBJECT-TYPE
    SYNTAX      PerfIntervalCount
    MAX-ACCESS  read-only
    STATUS      current
    DESCRIPTION
        "The counter associated with the number of Invalid Seconds encountered
        by a DS3/E3 interface in one of the previous 96 individual 15 minute
        intervals."
    ::= { usdDsx3FarEndIntervalEntry 1 }


--
-- the DS3 Far End Total
-- The DS3 Far End Total Table contains the cumulative sum of the
-- statistics for the 24 hour period preceding the current interval.
--
usdDsx3FarEndTotalTable  OBJECT-TYPE
    SYNTAX      SEQUENCE OF UsdDsx3FarEndTotalEntry
    MAX-ACCESS  not-accessible
    STATUS      current
    DESCRIPTION
        "This table contains entries for DS3/E3 interfaces present in the
        system."
    ::= { usdDs3Objects 5 }

usdDsx3FarEndTotalEntry  OBJECT-TYPE
    SYNTAX      UsdDsx3FarEndTotalEntry
    MAX-ACCESS  not-accessible
    STATUS      current
    DESCRIPTION
        "Each entry describes the characteristics of an DS3/E3 interface."
    AUGMENTS  { dsx3FarEndTotalEntry }
    ::= { usdDsx3FarEndTotalTable 1 }

UsdDsx3FarEndTotalEntry ::= SEQUENCE {
    usdDsx3FarEndTotalInvalidSeconds    PerfTotalCount }

usdDsx3FarEndTotalInvalidSeconds  OBJECT-TYPE
    SYNTAX      PerfTotalCount
    MAX-ACCESS  read-only
    STATUS      current
    DESCRIPTION
        "The counter associated with the number of Invalid Seconds encountered
        by a DS3/E3 interface in the previous 24 hour interval."
    ::= { usdDsx3FarEndTotalEntry 1 }


-- +++++++++++++++++++++++++++++++++++++++++++++++++++++++++++++++++++++++++++++
-- Notification control objects
-- +++++++++++++++++++++++++++++++++++++++++++++++++++++++++++++++++++++++++++++
-- No notifications are defined in this MIB.  Placeholder follows.
-- usdDs3TrapControl      OBJECT IDENTIFIER ::= { usdDs3MIB 2 }

-- +++++++++++++++++++++++++++++++++++++++++++++++++++++++++++++++++++++++++++++
-- Notifications
-- +++++++++++++++++++++++++++++++++++++++++++++++++++++++++++++++++++++++++++++
-- No notifications are defined in this MIB.  Placeholders follow.
-- The following two OBJECT IDENTIFIERS are used to define SNMPv2
-- Notifications that are easily translated into SNMPv1 Traps.
-- usdDs3Traps            OBJECT IDENTIFIER ::= { usdDs3MIB 3 }
-- usdDs3TrapPrefix       OBJECT IDENTIFIER ::= { usdDs3Traps 0 }


-- +++++++++++++++++++++++++++++++++++++++++++++++++++++++++++++++++++++++++++++
-- Conformance information
-- +++++++++++++++++++++++++++++++++++++++++++++++++++++++++++++++++++++++++++++
usdDs3Conformance OBJECT IDENTIFIER ::= { usdDs3MIB 4 }
usdDs3Compliances OBJECT IDENTIFIER ::= { usdDs3Conformance 1 }
usdDs3Groups      OBJECT IDENTIFIER ::= { usdDs3Conformance 2 }

--
-- compliance statements
--
usdDs3Compliance  MODULE-COMPLIANCE
    STATUS      obsolete
    DESCRIPTION
        "Obsolete compliance statement for entities which implement the
        Unisphere DS3/E3 MIB.  This statement became obsolete when support was
        added for line type and cell scrambler objects."
    MODULE   -- this module
        MANDATORY-GROUPS {
            usdDs3Group }
    ::= { usdDs3Compliances 1 }                                        -- RX 1.0

usdDs3Compliance2  MODULE-COMPLIANCE
    STATUS      obsolete
    DESCRIPTION
        "Obsolete compliance statement for entities which implement the
        Unisphere DS3/E3 MIB.  This statement became obsolete when support was
        added for DSU objects."
    MODULE   -- this module
        MANDATORY-GROUPS {
            usdDs3Group2 }
    ::= { usdDs3Compliances 2 }                                        -- RX 1.1

usdDs3Compliance3  MODULE-COMPLIANCE
    STATUS      obsolete
    DESCRIPTION
        "Obsolete compliance statement for entities which implement the
        Unisphere DS3/E3 MIB.  This statement became obsolete when support was
        added for dynamic DS3 interface objects."
    MODULE   -- this module
        MANDATORY-GROUPS {
            usdDs3Group3 }
    ::= { usdDs3Compliances 3 }                                        -- RX 2.6

usdDs3Compliance4  MODULE-COMPLIANCE
    STATUS      obsolete
    DESCRIPTION
        "Obsolete compliance statement for entities which implement the
        Unisphere DS3/E3 MIB.  This statement became obsolete when far end
        invalid seconds objects and more configuration objects were added."
    MODULE   -- this module
        MANDATORY-GROUPS {
            usdDs3Group4 }
    ::= { usdDs3Compliances 4 }                                        -- RX 3.0

usdDs3Compliance5  MODULE-COMPLIANCE
    STATUS      current
    DESCRIPTION
        "The compliance statement for entities which implement the Unisphere
        DS3/E3 MIB."
    MODULE   -- this module
        MANDATORY-GROUPS {
            usdDs3Group5,
            usdDs3FarEndGroup }
    ::= { usdDs3Compliances 5 }                                        -- RX 4.0

-- units of conformance

usdDs3Group  OBJECT-GROUP
    OBJECTS {
        usdDsx3LineLength }
    STATUS      obsolete
    DESCRIPTION
        "Obsolete collection of objects providing management of DS3/E3
        interfaces in a Unisphere product.  This group became obsolete when
        support was added for line type and cell scrambler objects."
    ::= { usdDs3Groups 1 }

usdDs3Group2  OBJECT-GROUP
    OBJECTS {
        usdDsx3LineLength,
        usdDsx3LineType,
        usdDsx3CellScramblerConfig }
    STATUS      obsolete
    DESCRIPTION
        "Obsolete collection of objects providing management of DS3/E3
        interfaces in a Unisphere product.  This group became obsolete when
        support was added for DSU configuration objects."
    ::= { usdDs3Groups 2 }

usdDs3Group3  OBJECT-GROUP
    OBJECTS {
        usdDsx3LineLength,
        usdDsx3LineType,
        usdDsx3CellScramblerConfig,
        usdDsx3Ds3DsuMode,
        usdDsx3Ds3BandwidthLimit,
        usdDsx3Ds3DsuScrambleMode }
    STATUS      obsolete
    DESCRIPTION
        "Obsolete collection of objects providing management of DS3/E3
        interfaces in a Unisphere product.  This group became obsolete when
        support was added for dynamic DS3 interface objects."
    ::= { usdDs3Groups 3 }

usdDs3Group4  OBJECT-GROUP
    OBJECTS {
        usdDsx3LineLength,
        usdDsx3LineType,
        usdDsx3CellScramblerConfig,
        usdDsx3Channelization,
        usdDsx3InterfaceType,
        usdDsx3Application,
        usdDsx3Ds3Channel,
        usdDsx3LowerIfIndex,
        usdDsx3RowStatus,
        usdDsx3Ds3DsuMode,
        usdDsx3Ds3BandwidthLimit,
        usdDsx3Ds3DsuScrambleMode,

        usdDs3NextIfIndex }
    STATUS      obsolete
    DESCRIPTION
        "Obsolete collection of objects providing management of DS3/E3
        interfaces in a Unisphere product.  This group became obsolete when more
        configuration objects were added."
    ::= { usdDs3Groups 4 }

usdDs3Group5  OBJECT-GROUP
    OBJECTS {
        usdDsx3LineLength,
        usdDsx3LineType,
        usdDsx3CellScramblerConfig,
        usdDsx3Channelization,
        usdDsx3InterfaceType,
        usdDsx3Application,
        usdDsx3Ds3Channel,
        usdDsx3LowerIfIndex,
        usdDsx3RowStatus,
        usdDsx3Ds3DsuMode,
        usdDsx3Ds3BandwidthLimit,
        usdDsx3Ds3DsuScrambleMode,
        usdDsx3MdlCarrier,
        usdDsx3MdlTransmit,
        usdDsx3MdlEic,
        usdDsx3MdlLic,
        usdDsx3MdlFic,
        usdDsx3MdlUnit,
        usdDsx3MdlPfi,
        usdDsx3MdlPort,
        usdDsx3MdlGenerator,

        usdDs3NextIfIndex }
    STATUS      current
    DESCRIPTION
        "A collection of objects providing management of DS3/E3 interfaces in a
        Unisphere product."
    ::= { usdDs3Groups 5 }

usdDs3FarEndGroup  OBJECT-GROUP
    OBJECTS {
        usdDsx3FarEndCurrentInvalidSeconds,
        usdDsx3FarEndIntervalInvalidSeconds,
        usdDsx3FarEndTotalInvalidSeconds }
    STATUS      current
    DESCRIPTION
        "A collection of objects providing remote statistics information
        applicable to DS3 interfaces in a Unisphere product."
    ::= { usdDs3Groups 6 }

END
