-- 
-- Copyright 1999 by Fore Systems, Inc. 
-- Converted to SMIv2 rfc 2578,2579,2580 - STD 58
--
--
--
-- Copyright (c) 1993-1998 FORE Systems, Inc., as an unpublished work.
-- This notice does not imply unrestricted or public access to these
-- materials which are a trade secret of FORE Systems, Inc. or its
-- subsidiaries or affiliates (together referred to as "FORE"), and
-- which may not be reproduced, used, sold or transferred to any third
-- party without FORE's prior written consent.
--
-- All rights reserved.
--
-- U.S. Government Restricted Rights.  If you are licensing the
-- Software on behalf of the U.S. Government ("Government"), the
-- following provisions apply to you.  If the Software is supplied to
-- the Department of Defense ("DoD"), it is classified as "Commercial
-- Computer Software" under paragraph 252.227-7014 of the DoD Supplement
-- to the Federal Acquisition Regulations ("DFARS") (or any successor
-- regulations) and the Government is acquiring only the license
-- rights granted herein (the license rights customarily provided to
-- non-Government users).  If the Software is supplied to any unit
-- or agency of the Government other than DoD, it is classified as
-- "Restricted Computer Software" and the Government's rights in the
-- Software are defined in paragraph 52.227-19 of the Federal Acquisition
-- Regulations ("FAR") (or any successor regulations) or, in the cases
-- of NASA, in paragraph 18.52.227-86 of the NASA Supplement to the FAR
-- (or any successor regulations).
--

Fore-Lane-MIB DEFINITIONS ::= BEGIN

IMPORTS
	OBJECT-TYPE,
	MODULE-IDENTITY,
	Integer32,
	TimeTicks				FROM SNMPv2-SMI
	DisplayString, MacAddress		FROM SNMPv2-TC
	EntryStatus, systems,
	NsapAddr, AtmAddress 			FROM Fore-Common-MIB;

foreLaneModule MODULE-IDENTITY
          LAST-UPDATED         "9911050000Z"
          ORGANIZATION         "FORE"
          CONTACT-INFO         
               "      Postal:   FORE Systems Inc.
                                 1000 FORE Drive
                                 Warrendale, PA 15086-7502
                       Tel:      +1 724 742 6900
                       Email:    nm_mibs@fore.com
                       Web:      http://www.fore.com"
          DESCRIPTION
           "Fore Systems LAN-Emulation MIB"
    ::= { systems 4 }


---------------------------------------------------------------
-- MIB Types Definitions

LecConfigType ::= INTEGER {
		wellknown(1),
		manual(2)
	}

LaneDataFrameFormat ::= INTEGER {
		unspecified(1),
		aflane8023(2),	-- ethernet
		aflane8025(3)	-- token-ring
	}

LaneDataFrameSize ::= INTEGER {
		unspecified(1),
		max1516(2),
		max4544(3),
		max9234(4),
		max18190(5),
		max1580(6)
	}

---------------------------------------------------------------

laneLecGroup    OBJECT IDENTIFIER ::= { foreLaneModule 1 }
lecConfGroup	OBJECT IDENTIFIER ::= { laneLecGroup 1 }
lecStatGroup	OBJECT IDENTIFIER ::= { laneLecGroup 2 }
lecArpGroup	OBJECT IDENTIFIER ::= { laneLecGroup 3 }

laneLesGroup	OBJECT IDENTIFIER ::= { foreLaneModule 2 }
lesConfGroup	OBJECT IDENTIFIER ::= { laneLesGroup 1 }
lesStatGroup	OBJECT IDENTIFIER ::= { laneLesGroup 2 }

laneBusGroup	OBJECT IDENTIFIER ::= { foreLaneModule 3 }
busConfGroup	OBJECT IDENTIFIER ::= { laneBusGroup 1 }
busStatGroup	OBJECT IDENTIFIER ::= { laneBusGroup 2 }

laneLecsGroup	OBJECT IDENTIFIER ::= { foreLaneModule 4 }
lecsConfGroup	OBJECT IDENTIFIER ::= { laneLecsGroup 1 }
lecsStatGroup	OBJECT IDENTIFIER ::= { laneLecsGroup 2 }

laneMibExtGroup	OBJECT IDENTIFIER ::= { foreLaneModule 5 }

---------------------------------------------------------------
-- LEC Groups
--
-- The LEC MIB allows the management station to configure the LEC on a host or
-- a switch.  In order to configure the LEC, the address of the LECS is
-- required.  lecDefaultLecsConfigType and lecDefaultLecsAtmAddress allow
-- for setting the default LECS address.
--

lecDefaultLecsConfigType OBJECT-TYPE
	SYNTAX  LecConfigType
	MAX-ACCESS  read-write
	STATUS  current
	DESCRIPTION
		"Default configuration type of the LECS, see
		lecConfLecsConfigType (which overrides this variable)
		for more information on config type"
	::= { lecConfGroup 1 }

lecDefaultLecsAtmAddress OBJECT-TYPE
	SYNTAX  AtmAddress
	MAX-ACCESS  read-write
	STATUS  current
	DESCRIPTION
		"Default LECS Atm Address to use for each LEC, can be
		overridden by lecConfLecsAtmAddress"
	::= { lecConfGroup 2 }


lecConfTable OBJECT-TYPE
	SYNTAX	SEQUENCE OF LecConfEntry
	MAX-ACCESS	not-accessible
	STATUS  current
	DESCRIPTION
		"A table of LECs and their parameters."
	::= { lecConfGroup 10 }

lecConfEntry OBJECT-TYPE
	SYNTAX  LecConfEntry
	MAX-ACCESS	not-accessible
	STATUS  current
	DESCRIPTION
		"A table entry contaning LEC parameters."
	INDEX   { lecConfIndex }
	::= { lecConfTable 1 }

LecConfEntry ::=
	SEQUENCE {
		lecConfIndex			Integer32,
		lecConfAtmAddress		AtmAddress,
		lecConfAdminStatus		INTEGER,
		lecConfOperStatus		INTEGER,
		lecConfElanName			DisplayString,
		lecConfMacAddress		MacAddress,
		lecConfLecsConfigType		LecConfigType,
		lecConfLecsAtmAddress		AtmAddress,
		lecConfLesAtmAddress		AtmAddress,
		lecConfEntryStatus		EntryStatus,
		lecConfIfName			DisplayString
	}


lecConfIndex OBJECT-TYPE
	SYNTAX	Integer32 (1..255)
	MAX-ACCESS	read-only
	STATUS	current
	DESCRIPTION
		"The index to the lecConfTable"
	::= { lecConfEntry 1 }

lecConfAtmAddress OBJECT-TYPE
	SYNTAX	AtmAddress
	MAX-ACCESS	read-create
	STATUS	current
	DESCRIPTION
		"The ATM address of this LEC"
	::= { lecConfEntry 2 }

lecConfAdminStatus OBJECT-TYPE
	SYNTAX	INTEGER {
			up(1),
			down(2)
		}
	MAX-ACCESS	read-create
	STATUS	current
	DESCRIPTION
		"The desired state for this LEC, the default value for
		this variable is up(1)"
	::= { lecConfEntry 3 }

lecConfOperStatus OBJECT-TYPE
	SYNTAX	INTEGER {
			up(1),
			down(2),
			joining(3)
		}
	MAX-ACCESS	read-only
	STATUS	current
	DESCRIPTION
		"The actual status of this LEC"
	::= { lecConfEntry 4 }

lecConfElanName OBJECT-TYPE
	SYNTAX	DisplayString
	MAX-ACCESS	read-create
	STATUS	current
	DESCRIPTION
		"Name of the emulated lan to join"
	::= { lecConfEntry 5 }

lecConfMacAddress OBJECT-TYPE
	SYNTAX	MacAddress
	MAX-ACCESS	read-only
	STATUS	current
	DESCRIPTION
		"MAC address assigned to this LEC"
	::= { lecConfEntry 6 }

lecConfLecsConfigType OBJECT-TYPE
	SYNTAX	LecConfigType
	MAX-ACCESS	read-create
	STATUS	current
	DESCRIPTION
		"One of: wellknown(1), manual(2).
		 The default configuration type of the LEC is based on
		 the default value set in the lecDefaultConfigType variable.
		 wellknown(1) means that the LEC will try to find LECS in the
		 manner specified in the spec (ILMI, WellKnown, PVC).
		 manual(2) means that the LEC will use the address specified
		 in the lecConfLecsAtmAddress variable."
	::= { lecConfEntry 7 }

lecConfLecsAtmAddress OBJECT-TYPE
	SYNTAX	AtmAddress
	MAX-ACCESS	read-create
	STATUS	current
	DESCRIPTION
		"The ATM address of LECS.  The default ATM address of the
		LECS server is based on the default value set in the
		lecDefaultLecsAtmAddress variable.  When the
		lecConfLecsConfigType is set to manual(2), this variable will
		be set to the Wellknown LECS address."
	::= { lecConfEntry 8 }

lecConfLesAtmAddress OBJECT-TYPE
	SYNTAX	AtmAddress
	MAX-ACCESS	read-create
	STATUS	current
	DESCRIPTION
		"The ATM address of LES to join.  If The lecConfLecsConfigType
		is set to manual(2) and this variable is set to address of an
		LES, this address will be used as the address of the LES
		to join."
	::= { lecConfEntry 9 }

lecConfEntryStatus OBJECT-TYPE
	SYNTAX	EntryStatus
	MAX-ACCESS	read-create
	STATUS	current
	DESCRIPTION
		"The status of this table entry, one of: valid(1),
		createRequest(2), underCreation(3), invalid(4)"
	::= { lecConfEntry 10 }

lecConfIfName OBJECT-TYPE
	SYNTAX	DisplayString
	MAX-ACCESS	read-only
	STATUS	current
	DESCRIPTION
		"Name of the interface associated with this LEC."
	::= { lecConfEntry 11 }

-- The following variables allow for manipulating the LEC's ARP cache

elarpFlush OBJECT-TYPE
	SYNTAX  INTEGER {
		enable(1),
		disable(2)
	}
	MAX-ACCESS  read-write
	STATUS  current
	DESCRIPTION
		"This variable causes the LEC ARP cache to be flushed
		when it is set to enable(1)."
	::= { lecArpGroup 1 }


lecArpTable OBJECT-TYPE
	SYNTAX	SEQUENCE OF LecArpEntry
	MAX-ACCESS	not-accessible
	STATUS  current
	DESCRIPTION
		"A table of LEC ARP entries."
	::= { lecArpGroup 10 }

lecArpEntry OBJECT-TYPE
	SYNTAX  LecArpEntry
	MAX-ACCESS	not-accessible
	STATUS  current
	DESCRIPTION
		"A table entry contaning LEC ARP parameters."
	INDEX   { lecArpMacAddress }
	::= { lecArpTable 1 }

LecArpEntry ::=
	SEQUENCE {
		lecArpMacAddress		MacAddress,
		lecArpAtmAddress		AtmAddress,
		lecArpFlags			INTEGER,
		lecArpConnVPI			Integer32,
		lecArpConnVCI			Integer32,
		lecArpFlush			INTEGER,
		lecArpElanName			DisplayString
	}

lecArpMacAddress OBJECT-TYPE
	SYNTAX	MacAddress
	MAX-ACCESS	read-only
	STATUS	current
	DESCRIPTION
		"MAC address of this ARP entry."
	::= { lecArpEntry 1 }

lecArpAtmAddress OBJECT-TYPE
	SYNTAX	AtmAddress
	MAX-ACCESS	read-only
	STATUS	current
	DESCRIPTION
		"The ATM address associated with this ARP entry."
	::= { lecArpEntry 2 }

lecArpFlags OBJECT-TYPE
	SYNTAX	INTEGER {
		incomplete(1),
		loopback(2),
		pending(3),
		valid(4)
	}
	MAX-ACCESS	read-only
	STATUS	current
	DESCRIPTION
		"The flags associated with this ARP entry."
	::= { lecArpEntry 3 }

lecArpConnVPI OBJECT-TYPE
	SYNTAX	Integer32
	MAX-ACCESS	read-only
	STATUS	current
	DESCRIPTION
		"The VPI associated with this connection."
	::= { lecArpEntry 4 }

lecArpConnVCI OBJECT-TYPE
	SYNTAX	Integer32
	MAX-ACCESS	read-only
	STATUS	current
	DESCRIPTION
		"The VCI associated with this connection."
	::= { lecArpEntry 5 }

lecArpFlush OBJECT-TYPE
	SYNTAX	INTEGER {
		enable(1),
		disable(2)
	}
	MAX-ACCESS	read-write
	STATUS	current
	DESCRIPTION
		"When set to enable(1), will flush this entry from
		ARP cache."
	::= { lecArpEntry 6 }

lecArpElanName OBJECT-TYPE
	SYNTAX	DisplayString
	MAX-ACCESS	read-only
	STATUS	current
	DESCRIPTION
		"Name of the emulated lan associated with this arp entry."
	::= { lecArpEntry 7 }

---------------------------------------------------------------
-- LES Groups
--
-- The LES table allows for setting up a LES service on a host or a switch.
-- Since multiple LESes may be started on the host or the switch, this table
-- is indexed by the lesConfIndex variable.
--

lesConfTable OBJECT-TYPE
	SYNTAX	SEQUENCE OF LesConfEntry
	MAX-ACCESS	not-accessible
	STATUS  current
	DESCRIPTION
		"A table of LESes and their parameters."
	::= { lesConfGroup 1 }

lesConfEntry OBJECT-TYPE
	SYNTAX  LesConfEntry
	MAX-ACCESS	not-accessible
	STATUS  current
	DESCRIPTION
		"A table entry contaning LES parameters."
	INDEX   { lesConfIndex }
	::= { lesConfTable 1 }

LesConfEntry ::=
	SEQUENCE {
		lesConfIndex			Integer32,
		lesConfAtmAddress		AtmAddress,
		lesConfAdminStatus		INTEGER,
		lesConfOperStatus		INTEGER,
		lesConfElanName			DisplayString,
		lesConfBusAtmAddress		AtmAddress,
		lesConfBusMaster		INTEGER,
		lesConfEntryStatus		EntryStatus,
		lesConfLanType			LaneDataFrameFormat,
		lesConfMaxFrameSize		LaneDataFrameSize,
		lesConfSecureServer		INTEGER,
		lesConfLECSAtmAddress		AtmAddress,
		lesConfAnycastAtmAddress	AtmAddress,
		lesConfRegisterTLVs		INTEGER,
		lesConfElanId			Integer32,
		lesConfTokenRingNumber		Integer32,
		lesConfForwardArp		INTEGER
	}

lesConfIndex OBJECT-TYPE
	SYNTAX	Integer32 (1..255)
	MAX-ACCESS	read-only
	STATUS	current
	DESCRIPTION
		"Index into the LesConfTable"
	::= { lesConfEntry 1 }

lesConfAtmAddress OBJECT-TYPE
	SYNTAX	AtmAddress
	MAX-ACCESS	read-create
	STATUS	current
	DESCRIPTION
		"The Atm address of this LES"
	::= { lesConfEntry 2 }

lesConfAdminStatus OBJECT-TYPE
	SYNTAX	INTEGER {
			up(1),
			down(2)
		}
	MAX-ACCESS	read-create
	STATUS	current
	DESCRIPTION
		"The desired state for this LES"
	::= { lesConfEntry 3 }

lesConfOperStatus OBJECT-TYPE
	SYNTAX	INTEGER {
			up(1),
			down(2)
		}
	MAX-ACCESS	read-only
	STATUS	current
	DESCRIPTION
		"The actual status of this LES"
	::= { lesConfEntry 4 }

lesConfElanName OBJECT-TYPE
	SYNTAX	DisplayString
	MAX-ACCESS	read-create
	STATUS	current
	DESCRIPTION
		"A name for this LES (not-required)"
	::= { lesConfEntry 5 }

lesConfBusAtmAddress OBJECT-TYPE
	SYNTAX	AtmAddress
	MAX-ACCESS	read-create
	STATUS	current
	DESCRIPTION
		"The ATM address of the BUS associated with this LES"
	::= { lesConfEntry 6 }

lesConfBusMaster OBJECT-TYPE
	SYNTAX	INTEGER {
		enable(1),
		disable(2)
	}
	MAX-ACCESS	read-create
	STATUS	deprecated
	DESCRIPTION
		"The configuration of the BUS associated with this LES.
		When this variable is set to enable(1), the LES will
		attempt to start the BUS on the current host."
	::= { lesConfEntry 7 }

lesConfEntryStatus OBJECT-TYPE
	SYNTAX	EntryStatus
	MAX-ACCESS	read-create
	STATUS	current
	DESCRIPTION
		"The status of this table entry, one of: valid(1),
		createRequest(2), underCreation(3), invalid(4)"
	::= { lesConfEntry 8 }

lesConfLanType OBJECT-TYPE
	SYNTAX  LaneDataFrameFormat
	MAX-ACCESS  read-create
	STATUS  current
	DESCRIPTION
		"The LAN type of this LES, one of: unspecified(1),
		aflane8023(2), aflane8025(3).  When unspecified,
		the LES may attempt to discover the LAN type from
		the LECS, or simply choose a default value."
	::= { lesConfEntry 9 }

lesConfMaxFrameSize OBJECT-TYPE
	SYNTAX  LaneDataFrameSize
	MAX-ACCESS  read-create
	STATUS  current
	DESCRIPTION
		"The Maximum Frame Size of this LES, one of:
		unspecified(1), max1516(2), max4544(3), max9234(4),
		max18190(5), max1580(6).  When unspecified, the LES may
		attempt to discover the Maximum Frame Size from the LECS,
		or simply choose a value commensurate with the LAN type."
	::= { lesConfEntry 10 }

lesConfSecureServer OBJECT-TYPE
	SYNTAX	INTEGER {
		enable(1),
		disable(2)
	}
	MAX-ACCESS	read-create
	STATUS	current
	DESCRIPTION
		"The configuration of a secure LES or insecure LES."
	::= { lesConfEntry 11 }

lesConfLECSAtmAddress OBJECT-TYPE
	SYNTAX  AtmAddress
	MAX-ACCESS  read-create
	STATUS  current
	DESCRIPTION
		"The LECS atm address used when running with
		 lesConfSecureServer enabled."
	::= { lesConfEntry 12 }

lesConfAnycastAtmAddress OBJECT-TYPE
	SYNTAX  AtmAddress
	MAX-ACCESS  read-create
	STATUS  current
	DESCRIPTION
		"The Anycast atm address used by clients to connect to
		 one of the Les Servers"
	::= { lesConfEntry 13 }

lesConfRegisterTLVs OBJECT-TYPE
	SYNTAX INTEGER {
		enable(1),
		disable(2)
	}
	MAX-ACCESS read-create
	STATUS current
	DESCRIPTION
		"The configuration of a server to forward (or not)
		 registration TLVs."
	DEFVAL { enable }
	::= { lesConfEntry 14 }

lesConfElanId OBJECT-TYPE
	SYNTAX	Integer32
	MAX-ACCESS  read-create
	STATUS  current
	DESCRIPTION
		"The configuration of a numeric (non-zero) ELAN identifier."
	::= { lesConfEntry 15 }

lesConfTokenRingNumber OBJECT-TYPE
	SYNTAX Integer32 (0..4095)
	MAX-ACCESS read-create
	STATUS current
	DESCRIPTION
		"12-bit hexadecimal ring (segment) number for a token ring
		 ELAN."
	::= { lesConfEntry 16 }

lesConfForwardArp OBJECT-TYPE
	SYNTAX INTEGER {
		enable(1),
		disable(2)
	}
	MAX-ACCESS read-create
	STATUS current
	DESCRIPTION
		"The configuration of the LES to flood all LE-ARP requests  
		 to all clients, both proxy and non-proxy."
	DEFVAL { disable }
	::= { lesConfEntry 17 }	

lesLnniConfTable OBJECT-TYPE
	SYNTAX	SEQUENCE OF LesLnniConfEntry
	MAX-ACCESS	not-accessible
	STATUS  current
	DESCRIPTION
		"A table of entries to LNNI information about LESs."
	::= { lesConfGroup 2 }

lesLnniConfEntry OBJECT-TYPE
	SYNTAX  LesLnniConfEntry
	MAX-ACCESS	not-accessible
	STATUS  current
	DESCRIPTION
		"A table entry contaning LNNI parameters to LESes.
		 LESes are identified by their lesConfIndex parameter."
	INDEX   { lesConfIndex, lesLnniConfAtmAddress }
	::= { lesLnniConfTable 1 }

LesLnniConfEntry ::=
	SEQUENCE {
		lesLnniConfAtmAddress		NsapAddr,
		lesLnniConfEntryStatus		EntryStatus
	}

lesLnniConfAtmAddress OBJECT-TYPE
	SYNTAX	NsapAddr
	MAX-ACCESS	read-only
	STATUS	current
	DESCRIPTION
		"The Atm address of a partner LES."
	::= { lesLnniConfEntry 1 }

lesLnniConfEntryStatus OBJECT-TYPE
	SYNTAX	EntryStatus
	MAX-ACCESS	read-write
	STATUS	current
	DESCRIPTION
		"The status of this table entry, one of: valid(1),
		createRequest(2), underCreation(3), invalid(4)"
	::= { lesLnniConfEntry 2 }

---
--- LES-LEQ Table
---

lesLeqGroup	OBJECT IDENTIFIER ::= { lesConfGroup 3 }

lesLeqConfLesId OBJECT-TYPE
	SYNTAX	Integer32
	MAX-ACCESS	read-write
	STATUS	current
	DESCRIPTION
		"The value of the lesConfIndex for the LES
		on which the leq command will be run when the
		lesLeqTableReload variable is set to go."
	::= { lesLeqGroup 1 }

lesLeqTableReload OBJECT-TYPE
	SYNTAX	INTEGER {
			idle(1),
			go(2),
			inProgress(3),
			succeeded(4),
			failed(5)
		}
	MAX-ACCESS	read-write
	STATUS	current
	DESCRIPTION
		"The current status of lesLeqTable update for the LES
		whose index is specified in lesLeqConfLesId.
		Is idle when the before it is set.  To update the
		lesLeqTable content corresponding to this LES set this
		to go.  A manager may restart the table update process by
		setting this entry to go when it is in the succeeded
		or failed states.  This variable may be read-only in
		in inProgress state or may allow sets to idle."
	::= { lesLeqGroup 2 }

lesLeqStatLesId OBJECT-TYPE
	SYNTAX	Integer32
	MAX-ACCESS	read-only
	STATUS	current
	DESCRIPTION
		"The value of the lesConfIndex for the LES
		on which the leq command was most recently run
		and the lesLeqTable was populated for."
	::= { lesLeqGroup 3 }

lesLeqLastTime OBJECT-TYPE
	SYNTAX	TimeTicks
	MAX-ACCESS	read-only
	STATUS	current
	DESCRIPTION
		"The value of sysUptime the time the last
		request to fill in the lesLeqTable was finished."
	::= { lesLeqGroup 4 }

lesLeqTable OBJECT-TYPE
	SYNTAX	SEQUENCE OF LesLeqEntry
	MAX-ACCESS	not-accessible
	STATUS	current
	DESCRIPTION
		"This table contains all LAN Emulation clients
		serviced by a LES specified in lesLeqLesId.

		This table is generated from the output of the
		leq command. Details of the leq command can be
		found else where."
	::= { lesLeqGroup 5 }

lesLeqEntry OBJECT-TYPE
	SYNTAX	LesLeqEntry
	MAX-ACCESS	not-accessible
	STATUS	current
	DESCRIPTION
		"Each entry represents a LANE client."
	INDEX	{ lesLeqIndex }
	::= { lesLeqTable 1 }

LesLeqEntry ::=
	SEQUENCE {
		lesLeqIndex     Integer32,
		lesLeqNsap      NsapAddr,
		lesLeqName      DisplayString
	}

lesLeqIndex OBJECT-TYPE
	SYNTAX	Integer32
	MAX-ACCESS	read-only
	STATUS	current
	DESCRIPTION
		"An integer which is the index of the LANE client and
		uniquely identifies a LEC in this table."
	::= { lesLeqEntry 1 }

lesLeqNsap OBJECT-TYPE
	SYNTAX	NsapAddr
	MAX-ACCESS	read-only
	STATUS	current
	DESCRIPTION
		"The NSAP address of the LANE client. This is the
		primary NSAP address of the LEC used in joining
		phase"
	::= { lesLeqEntry 2 }

lesLeqName OBJECT-TYPE
	SYNTAX	DisplayString
	MAX-ACCESS	read-only
	STATUS	current
	DESCRIPTION
		"This is the comment field sent by the LEC to the
		LES during joining phase. This comment will contain
		the hostname of the machine where the LEC was started"
	::= { lesLeqEntry 3 }

---------------------------------------------------------------
-- BUS Groups
--
-- The BUS table may be used to setup BUS service on a host or a switch.  This
-- table is indexed by the busConfIndex variable.
--

busConfTable OBJECT-TYPE
	SYNTAX	SEQUENCE OF BusConfEntry
	MAX-ACCESS	not-accessible
	STATUS  deprecated
	DESCRIPTION
		"A table of BUSes and their parameters."
	::= { busConfGroup 1 }

busConfEntry OBJECT-TYPE
	SYNTAX  BusConfEntry
	MAX-ACCESS	not-accessible
	STATUS  deprecated
	DESCRIPTION
		"A table entry contaning BUS parameters."
	INDEX   { busConfIndex }
	::= { busConfTable 1 }

BusConfEntry ::=
	SEQUENCE {
		busConfIndex			Integer32,
		busConfAtmAddress		AtmAddress,
		busConfAdminStatus		INTEGER,
		busConfOperStatus		INTEGER,
		busConfName			DisplayString,
		busConfEntryStatus		EntryStatus,
		busConfLanType			LaneDataFrameFormat,
		busConfMaxFrameSize		LaneDataFrameSize
	}

busConfIndex OBJECT-TYPE
	SYNTAX  Integer32 (1..255)
	MAX-ACCESS  read-only
	STATUS  deprecated
	DESCRIPTION
		"Index into the BusConfTable"
	::= { busConfEntry 1 }

busConfAtmAddress OBJECT-TYPE
	SYNTAX  AtmAddress
	MAX-ACCESS  read-create
	STATUS  deprecated
	DESCRIPTION
		"The Atm address of this BUS"
	::= { busConfEntry 2 }

busConfAdminStatus OBJECT-TYPE
	SYNTAX  INTEGER {
			up(1),
			down(2)
		}
	MAX-ACCESS  read-create
	STATUS  deprecated
	DESCRIPTION
		"The desired state for this BUS"
	::= { busConfEntry 3 }

busConfOperStatus OBJECT-TYPE
	SYNTAX  INTEGER {
			up(1),
			down(2)
		}
	MAX-ACCESS  read-only
	STATUS  deprecated
	DESCRIPTION
		"The actual status of this BUS"
	::= { busConfEntry 4 }

busConfName OBJECT-TYPE
	SYNTAX  DisplayString
	MAX-ACCESS  read-create
	STATUS  deprecated
	DESCRIPTION
		"A name for this BUS (not-required)"
	::= { busConfEntry 5 }

busConfEntryStatus OBJECT-TYPE
	SYNTAX  EntryStatus
	MAX-ACCESS  read-create
	STATUS  deprecated
	DESCRIPTION
		"The status of this table entry, one of: valid(1),
		createRequest(2), underCreation(3), invalid(4)"
	::= { busConfEntry 6 }

busConfLanType OBJECT-TYPE
	SYNTAX  LaneDataFrameFormat
	MAX-ACCESS  read-create
	STATUS  deprecated
	DESCRIPTION
		"The LAN type of this BUS, one of: unspecified(1),
		aflane8023(2), aflane8025(3).  When unspecified,
		the BUS may attempt to discover the LAN type from
		signaling IEs, or simply choose a default value."
	::= { busConfEntry 7 }

busConfMaxFrameSize OBJECT-TYPE
	SYNTAX  LaneDataFrameSize
	MAX-ACCESS  read-create
	STATUS  deprecated
	DESCRIPTION
		"The Maximum Frame Size of this BUS, one of:
		unspecified(1), max1516(2), max4544(3), max9234(4),
		max18190(5), max1580(6).  When unspecified, the BUS may
		attempt to discover the Maximum Frame Size from signaling
		IEs, or simply handle the maximum."
	::= { busConfEntry 8 }

---------------------------------------------------------------
-- LECS Group
--
-- The LECS table may be used to setup LECS service on a host or a switch.
-- The LECS configuration table is indexed by lecsConfIndex variable.
--

lecsConfTable OBJECT-TYPE
	SYNTAX	SEQUENCE OF LecsConfEntry
	MAX-ACCESS	not-accessible
	STATUS  current
	DESCRIPTION
		"A table of LECSes and their parameters."
	::= { lecsConfGroup 1 }

lecsConfEntry OBJECT-TYPE
	SYNTAX  LecsConfEntry
	MAX-ACCESS	not-accessible
	STATUS  current
	DESCRIPTION
		"A table entry contaning LECS parameters."
	INDEX   { lecsConfIndex }
	::= { lecsConfTable 1 }

LecsConfEntry ::=
	SEQUENCE {
		lecsConfIndex			Integer32,
		lecsConfAtmAddress		AtmAddress,
		lecsConfAdminStatus		INTEGER,
		lecsConfOperStatus		INTEGER,
		lecsConfDatabase		DisplayString,
		lecsConfEntryStatus		EntryStatus,
		lecsConfDefaultLesFlag		INTEGER,
		lecsConfDefaultLesAtmAddress	AtmAddress,
		lecsConfWellKnownAddressFlag	INTEGER,
		lecsConfWellKnownAddress	AtmAddress
	}

lecsConfIndex OBJECT-TYPE
	SYNTAX	Integer32 (1..255)
	MAX-ACCESS	read-only
	STATUS	current
	DESCRIPTION
		"The index into the LecsConfTable"
	::= { lecsConfEntry 1 }

lecsConfAtmAddress OBJECT-TYPE
	SYNTAX	AtmAddress
	MAX-ACCESS	read-create
	STATUS	current
	DESCRIPTION
		"The ATM address of this LECS"
	::= { lecsConfEntry 2 }

lecsConfAdminStatus OBJECT-TYPE
	SYNTAX	INTEGER {
			up(1),
			down(2)
		}
	MAX-ACCESS	read-create
	STATUS	current
	DESCRIPTION
		"The desired state for LECS"
	::= { lecsConfEntry 3 }

lecsConfOperStatus OBJECT-TYPE
	SYNTAX	INTEGER {
			up(1),
			down(2)
		}
	MAX-ACCESS	read-only
	STATUS	current
	DESCRIPTION
		"The actual status of LECS"
	::= { lecsConfEntry 4 }

lecsConfDatabase OBJECT-TYPE
	SYNTAX	DisplayString
	MAX-ACCESS	read-create
	STATUS	current
	DESCRIPTION
		"The full path to the location and name of the
		LECS database."
	::= { lecsConfEntry 5 }

lecsConfEntryStatus OBJECT-TYPE
	SYNTAX	EntryStatus
	MAX-ACCESS	read-create
	STATUS	current
	DESCRIPTION
		"The status of this table entry, one of: valid(1),
		createRequest(2), underCreation(3), invalid(4)"
	::= { lecsConfEntry 6 }

lecsConfDefaultLesFlag OBJECT-TYPE
	SYNTAX	INTEGER {
			enable(1),
			disable(2)
		}
	MAX-ACCESS	read-create
	STATUS	current
	DESCRIPTION
		"The option to use the default LES ATM-address if the
		 configuration file is inaccessible, one of: enable(1),
		 disable(2)"
	::= { lecsConfEntry 7 }

lecsConfDefaultLesAtmAddress OBJECT-TYPE
	SYNTAX  AtmAddress
	MAX-ACCESS  read-create
	STATUS  current
	DESCRIPTION
		"The ATM address of the default LES"
	::= { lecsConfEntry 8 }

lecsConfWellKnownAddressFlag OBJECT-TYPE
	SYNTAX	INTEGER {
			none(1),
			atm-forum(2),
			other(3)
		}
	MAX-ACCESS	read-create
	STATUS	current
	DESCRIPTION
		"The option to disable the LECS well-known address,
		 one of: none(1), atm-forum(2), other(3)"
	::= { lecsConfEntry 9 }

lecsConfWellKnownAddress OBJECT-TYPE
	SYNTAX  AtmAddress
	MAX-ACCESS  read-create
	STATUS  current
	DESCRIPTION
		"The well-known address for the LECS"
	::= { lecsConfEntry 10 }

---------------------------------------------------------------
-- LANE MIB EXT Group
--
-- The extLecConfigTable is an extension to the ATM Forum LEC
-- MIB (af-lane-0044.0000)
--

-- extLecConfigTable OBJECT-TYPE
-- 	SYNTAX       SEQUENCE OF ExtLecConfigEntry
-- 	MAX-ACCESS   not-accessible
-- 	STATUS       current
-- 	DESCRIPTION
-- 		"This table contains FORE System's extension to
-- 		 the lecConfigTable of the ATM Forum LEC MIB."
-- 	::= { laneMibExtGroup 1 }
-- 
-- extLecConfigEntry OBJECT-TYPE
-- 	SYNTAX       ExtLecConfigEntry
-- 	MAX-ACCESS   not-accessible
-- 	STATUS       current
-- 	DESCRIPTION
-- 		"Each table entry contains configuration information
-- 		about one LAN Emulation Client."
-- 	AUGMENTS  { lecConfigEntry }
-- 	::= { extLecConfigTable 1 }
-- 
-- ExtLecConfigEntry ::=
-- 	SEQUENCE {
-- 		extLecConfigPrimaryAtmAddress	AtmLaneAddress,
-- 	}
-- 
-- extLecConfigPrimaryAtmAddress OBJECT-TYPE
-- 	SYNTAX      AtmLaneAddress
-- 	MAX-ACCESS  read-write
-- 	STATUS      current
-- 	DESCRIPTION
-- 		"C1 LE Client's ATM Addresses.
-- 
-- 		 The primary ATM address which this LAN Emulation
-- 		 Client will use the next time it returns to the
-- 		 Initial State.If this value is not set, the system
-- 		 will choose an unused ATM address.
-- 
-- 		 This address is used to establish the Control Direct
-- 		 and Multicast Send VCCs, and may also be used to set
-- 		 up Data Direct VCCs.
-- 
-- 		 A client may have additional ATM addresses for use
-- 		 with Data Direct VCCs.  These addresses are readable
-- 		 via the lecAtmAddressTable."
-- 
-- 	REFERENCE
-- 		"ATM Forum LAN Emulation Over ATM Specification, V1.0,
-- 		 Section 5.1.1"
-- 	DEFVAL   { "" }
-- 	::= { extLecConfigEntry 1 }

END
