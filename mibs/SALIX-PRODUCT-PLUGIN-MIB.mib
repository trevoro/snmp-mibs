SALIX-PRODUCT-PLUGIN-MIB DEFINITIONS ::= BEGIN

IMPORTS

   MODULE-IDENTITY, OBJECT-TYPE, IpAddress    FROM SNMPv2-SMI

   MODULE-COMPLIANCE, OBJECT-GROUP            FROM SNMPv2-CONF
   

         TEXTUAL-CONVENTION, DisplayString,
         RowStatus, TruthValue               FROM SNMPv2-TC
         
--   atmfM4AlarmSevProfileEntry,
         atmfM4PlugInUnitEntry, 
         atmfM4CellProtoHistIndex            FROM ATM-FORUM-M4-MIB   
         
         entPhysicalIndex, PhysicalIndex     FROM ENTITY-MIB     

         platform1                          FROM SALIX-MIB;

salixProductPlugInMIB MODULE-IDENTITY
     LAST-UPDATED "9810130000Z"
     ORGANIZATION "SALIX Technologies"
     CONTACT-INFO "904 Wind River Lane
                   Suite 101
                   Gaithersburg, MD  20878
                   (301)-417-0017"
     DESCRIPTION  "The MIB describing SALIX specific extensions
                   to the M4-MIB"
     ::= { platform1 5 }

   salixProductPlugInMIBObjects OBJECT IDENTIFIER ::= { salixProductPlugInMIB 1 }
   salixProductPlugInMIBTraps   OBJECT IDENTIFIER ::= { salixProductPlugInMIB 2 }
   salixProductPlugInMIBCompliance OBJECT IDENTIFIER ::= { salixProductPlugInMIB 3 }
   salixProductPlugInMIBTrapPrefix OBJECT IDENTIFIER ::= { salixProductPlugInMIBTraps 0 }

  SalixPlugInUnitType ::= TEXTUAL-CONVENTION
       STATUS     current
       DESCRIPTION
            "HNE hardware plug-in unit types:
             unknown(0)                - Unknown plug-in unit type
             mpu(1)                    - Management Processor Unit
             dpu(2)                    - Data Processor Unit
             smu(3)                    - Sync Module Unit
             liu(4)                    - Line Interface Unit
             hsf(5)                    - Hybrid Switch Fabric Unit
             powerSupply(6)            - Power supply
             fan(7)                    - Fan Unit
             hardDrive(8)              - Hard drive
             xcoder(9)                 - Transcoder
             ds3Liu(10)                - Ds3 LIU
             softwarePacketLiu(11)     - Software Packet LIU
             packetLiu(12)"

       SYNTAX     INTEGER { unknown(0),
                            mpu(1),
                            dpu(2),
                            smu(3),
                            liu(4),
                            hsf(5),
                            powerSupply(6),
                            fan(7),
                            hardDrive(8),
                            xcoder(9),
                            ds3Liu(10),
                            softwarePacketLiu(11),
                            packetLiu(12) }
                            
                            
                            
-- HNE Plug-in Unit Object

  salixPlugInUnit OBJECT IDENTIFIER ::= { salixProductPlugInMIBObjects 1 }

  -- Management Processor Unit (MPU) Plug-in Unit Table

--  salixPlugInUnitMpuTable OBJECT-TYPE
--       SYNTAX     SEQUENCE OF    SalixPlugInUnitMpuEntry
--       MAX-ACCESS not-accessible
--       STATUS     current
--       DESCRIPTION
--            "The HNE Management Processor Unit (MPU) plug-in unit table."
--       ::= { salixPlugInUnit 1 }
--
--  salixPlugInUnitMpuEntry OBJECT-TYPE
--       SYNTAX     SalixPlugInUnitMpuEntry
--       MAX-ACCESS not-accessible
--       STATUS     current
--       DESCRIPTION
--            "An entry in the HNE MPU plug-in unit table. An entry contains
--             HNE specific plug-in information for a Management Processor
--             Unit."
--       INDEX { entPhysicalIndex }
--       ::= { salixPlugInUnitMpuTable 1 }
--

  -- Data Processor Unit (DPU) Plug-in Unit Table

  salixPlugInUnitDpuTable OBJECT-TYPE
       SYNTAX     SEQUENCE OF    SalixPlugInUnitDpuEntry
       MAX-ACCESS not-accessible
       STATUS     current
       DESCRIPTION
            "The HNE Data Processor Unit (DPU) plug-in unit table."
       ::= { salixPlugInUnit 1 }

  salixPlugInUnitDpuEntry OBJECT-TYPE
       SYNTAX     SalixPlugInUnitDpuEntry
       MAX-ACCESS not-accessible
       STATUS     current
       DESCRIPTION
            "An entry in the HNE DPU plug-in unit table. An entry contains
             HNE specific plug-in information for a Data Processor
             Unit.  This table parallels the salixAtmfM4PlugInUnitTable.
             However, only valid LIU indices of the salixAtmfM4PlugInUnitTable
             will contain information pertinent to a DPU."

       INDEX { entPhysicalIndex }
       ::= { salixPlugInUnitDpuTable 1 }

  SalixPlugInUnitDpuEntry ::= SEQUENCE {
            salixDpuProcessorType        INTEGER
       }

  salixDpuProcessorType OBJECT-TYPE
       SYNTAX     INTEGER { mipsR4700 (1) }
       MAX-ACCESS read-only
       STATUS     current
       DESCRIPTION
            "The type of processor installed on the Data Processor Unit.

             mipsR4700(1) - MIPS R4700 RISC processor."
       ::= { salixPlugInUnitDpuEntry 1 }

  -- Line Interface Unit (LIU) Plug-in Unit Table

  salixPlugInUnitLiuTable OBJECT-TYPE
       SYNTAX     SEQUENCE OF    SalixPlugInUnitLiuEntry
       MAX-ACCESS not-accessible
       STATUS     current
       DESCRIPTION
            "The HNE Line Interface Unit (LIU) plug-in unit table."
       ::= { salixPlugInUnit 2 }

  salixPlugInUnitLiuEntry OBJECT-TYPE
       SYNTAX     SalixPlugInUnitLiuEntry
       MAX-ACCESS not-accessible
       STATUS     current
       DESCRIPTION
            "An entry in the HNE LIU plug-in unit table. An entry contains
             HNE specific plug-in information for an LIU.  This table
             is indexed the same as the salixAtmfM4PlugInUnitTable.  However,
             only valid LIU indices of the salixAtmfM4PlugInUnitTable will
             contain information pertinent to an LIU."
       INDEX { entPhysicalIndex }
       ::= { salixPlugInUnitLiuTable 1 }

  SalixPlugInUnitLiuEntry ::= SEQUENCE {
            salixLiuOrderwireEnabled    TruthValue,
            salixLiuOrderwireSonetLine  INTEGER,
            salixLiuOrderwireSonetLayer INTEGER
       }

  salixLiuOrderwireEnabled OBJECT-TYPE
       SYNTAX     TruthValue
       MAX-ACCESS read-write
       STATUS     current
       DESCRIPTION
            "Indication of whether the orderwire is enabled.

             true(1)  - the orderwire is enabled
             false(2) - the orderwire is not-enabled"
       DEFVAL { false }
       ::= { salixPlugInUnitLiuEntry 1 }

  salixLiuOrderwireSonetLine OBJECT-TYPE
       SYNTAX     INTEGER (1..4)
       MAX-ACCESS read-write
       STATUS     current
       DESCRIPTION
            "Identifies which of the SONET lines on the plug-in unit to take
             the orderwire from for drop to the handset."
       DEFVAL { 1 }
       ::= { salixPlugInUnitLiuEntry 2 }

  salixLiuOrderwireSonetLayer OBJECT-TYPE
       SYNTAX     INTEGER { section(1), line(2) }
       MAX-ACCESS read-write
       STATUS     current
       DESCRIPTION
            "Identifies which of the two orderwire signals in the selected
             SONET line should be routed to the handset on the plug-in unit."
       DEFVAL { section }
       ::= { salixPlugInUnitLiuEntry 3 }

  -- Sync Module Plug-in Unit Table

--  salixPlugInUnitSyncTable          OBJECT IDENTIFIER ::=  { salixPlugInUnit 3 }

  salixPlugInUnitSyncTable OBJECT-TYPE
       SYNTAX     SEQUENCE OF    SalixPlugInUnitSyncEntry
       MAX-ACCESS not-accessible
       STATUS     current
       DESCRIPTION
            "The HNE Sync module plug-in unit table."
       ::= { salixPlugInUnit 3 }

  salixPlugInUnitSyncEntry OBJECT-TYPE
       SYNTAX     SalixPlugInUnitSyncEntry
       MAX-ACCESS not-accessible
       STATUS     current
       DESCRIPTION
            "An entry in the HNE Sync module plug-in unit table. An entry
             contains HNE specific plug-in information for a Sync module.
             This table is indexed the same as the salixAtmfM4PlugInUnitTable.
             However, only valid Sync module indices of the
             salixAtmfM4PlugInUnitTable will contain information pertinent
             to a Sync module."
       INDEX { entPhysicalIndex }
       ::= { salixPlugInUnitSyncTable 1 }

  SalixPlugInUnitSyncEntry ::= SEQUENCE {
            salixSyncSlotIdentifier    INTEGER
       }

  salixSyncSlotIdentifier OBJECT-TYPE
       SYNTAX     INTEGER { primary(1), secondary(2) }
       MAX-ACCESS read-only
       STATUS     current
       DESCRIPTION
            "Indicates whether the Sync module is installed in the primary
             or secondary plug-in unit slot."
       ::= { salixPlugInUnitSyncEntry 1 }

  -- Hybrid Switch Fabric (HSF) Plug-in Unit Table

-- Removed from build one
--  salixPlugInUnitHsfTable OBJECT-TYPE
--       SYNTAX     SEQUENCE OF    SalixPlugInUnitHsfEntry
--       MAX-ACCESS not-accessible
--       STATUS     current
--       DESCRIPTION
--            "The Hybrid Switch Fabric (HSF) plug-in unit table."
--      ::= { salixPlugInUnit 3 }
--
-- salixPlugInUnitHsfEntry OBJECT-TYPE
--       SYNTAX     SalixPlugInUnitHsfEntry
--       MAX-ACCESS not-accessible
--       STATUS     current
--       DESCRIPTION
--            "An entry in the HNE HSF plug-in unit table. An entry contains
--             HNE Hybrid Switch Fabric specific plug-in information.
--             Unit."
--       INDEX { entPhysicalIndex }
--       ::= { salixPlugInUnitHsfTable 1 }
--
--  SalixPlugInUnitHsfEntry ::= SEQUENCE {
--            salixHsfState                INTEGER
--       }
--
--  salixHsfState     OBJECT-TYPE
--       SYNTAX     INTEGER { working(1), protect(2), failed(3) }
--       MAX-ACCESS read-only
--       STATUS     current
--       DESCRIPTION
--            "The status of the HSF plug-in unit:
--
--             working(1) - The plug-in unit is working and active
--             protect(2) - The plug-in unit is on standby
--             failed(3)  - The plug-in unit has failed"
--       ::= { salixPlugInUnitHsfEntry 1 }


   -- Packet Line Interface Unit (pktliu) Plug-in Unit Table
--
--  salixPlugInUnitPacketLiuTable OBJECT-TYPE
--       SYNTAX     SEQUENCE OF    SalixPlugInUnitPacketLiuEntry
--       MAX-ACCESS not-accessible
--     STATUS     current
--       DESCRIPTION
--            "The HNE Packet Line Interface Unit (pktliu) plug-in unit table."
--       ::= { salixPlugInUnit 5 }
--
--  salixPlugInUnitPacketPacketLiuEntry OBJECT-TYPE
--       SYNTAX     SalixPlugInUnitPacketLiuEntry
--       MAX-ACCESS not-accessible
--       STATUS     current
--       DESCRIPTION
--            "An entry in the HNE Packet LIU plug-in unit table. An entry contains
--             HNE specific plug-in information for a Packet LIU.  This table
--             is indexed the same as the salixAtmfM4PlugInUnitTable.  However,
--             only valid Packet LIU indices of the salixAtmfM4PlugInUnitTable will
--             contain information pertinent to an LIU."
--       INDEX { entPhysicalIndex }
--       ::= { salixPlugInUnitPacketLiuTable 1 }
--
--  SalixPlugInUnitPacketLiuEntry ::= SEQUENCE {
--
--       }       


  -- Transcoder (XCDR) Plug-in Unit Table

  salixPlugInUnitXcdrTable OBJECT-TYPE
       SYNTAX     SEQUENCE OF    SalixPlugInUnitXcdrEntry
       MAX-ACCESS not-accessible
       STATUS     current
       DESCRIPTION
            "The Transcoder (xcoder) plug-in unit table."
       ::= { salixPlugInUnit 6 }

  salixPlugInUnitXcdrEntry OBJECT-TYPE
       SYNTAX     SalixPlugInUnitXcdrEntry
       MAX-ACCESS not-accessible
       STATUS     current
       DESCRIPTION
            "An entry in the XCDR table.  On entry exists for each
            Transcoder in the system.  Each entry contains information
            and configuration about the Transcoder"
       INDEX { entPhysicalIndex }
       ::= { salixPlugInUnitXcdrTable 1 }

  SalixPlugInUnitXcdrEntry ::= SEQUENCE {
      salixPlugInUnitXcdrPercentWorkingDsp                INTEGER,
      salixPlugInUnitXcdrType                             INTEGER
       }
       
   salixPlugInUnitXcdrPercentWorkingDsp OBJECT-TYPE
      SYNTAX      INTEGER(0..100)
      MAX-ACCESS  read-only
      STATUS      current
      DESCRIPTION
         "Represents the percentage of the Dsp's on the Transcoder that are 
          currently working.  The exact Dsp's that have failed can be found
          in the itxDspConfigTable from the SALIX-ITX-MIB"
   ::= { salixPlugInUnitXcdrEntry 1 }
   
   salixPlugInUnitXcdrType OBJECT-TYPE
      SYNTAX      INTEGER { voipServer(1), 
                            toneAndAnnouncementServer(2),
                            universalServer(3) }
      MAX-ACCESS  read-write
      STATUS      current
      DESCRIPTION
         "This object describes the Type of Transcoder described by the entry.
          
          voipServer(1) - A Transcoder that is limited to VOIP calls
          toneAndAnnouncementServer(2) - A Transcoder that is limited to announcements and tones
          universalServer(3) - A Transcoder that can do both Annoucements and VOIP calls"
      DEFVAL { universalServer }
   ::= { salixPlugInUnitXcdrEntry 2 }

  -- DS3 Line Interface Unit (LIU) Plug-in Unit Table

  salixPlugInUnitDs3LiuTable OBJECT-TYPE
       SYNTAX     SEQUENCE OF    SalixPlugInUnitDs3LiuEntry
       MAX-ACCESS not-accessible
       STATUS     current
       DESCRIPTION
            "The DS3 Line Interface Unit (DS3LIU) plug-in unit table."
       ::= { salixPlugInUnit 7 }

  salixPlugInUnitDs3LiuEntry OBJECT-TYPE
       SYNTAX     SalixPlugInUnitDs3LiuEntry
       MAX-ACCESS not-accessible
       STATUS     current
       DESCRIPTION
            "An entry in the SALIX Ds3Liu Plugin Unit Table.  One entry 
             exists for each DS3LIU in the system, and contains information 
             specific to DS3LIUs."
       INDEX { entPhysicalIndex }
       ::= { salixPlugInUnitDs3LiuTable 1 }

  SalixPlugInUnitDs3LiuEntry ::= SEQUENCE {
            salixDs3LiuGroupNumber    INTEGER
       }

  salixDs3LiuGroupNumber OBJECT-TYPE
       SYNTAX     INTEGER(0..4)
       MAX-ACCESS read-write
       STATUS     current
       DESCRIPTION
            "The group that the DS3LIU corresponding to this entry belongs
            to.  Valid groups are numbered from 1 to 4.  A value of 0 
            indicates that the DS3LIU does not belong in a group."
       DEFVAL { 0 }
       ::= { salixPlugInUnitDs3LiuEntry 1 }
     

-- Conformance Statements

salixPPIGroups      OBJECT IDENTIFIER  ::= { salixProductPlugInMIBCompliance 1 }
salixPPICompliances OBJECT IDENTIFIER  ::= { salixProductPlugInMIBCompliance 2 }

   salixPPIGroup OBJECT-GROUP
      OBJECTS {
         salixDpuProcessorType,
         salixLiuOrderwireEnabled,
         salixLiuOrderwireSonetLine,
         salixLiuOrderwireSonetLayer
      }
      STATUS         current
      DESCRIPTION    "Salix M4 Plug-In Objects Group"
      ::= { salixProductPlugInMIBCompliance 1}

-- Compliance Statements

salixPPICompliance MODULE-COMPLIANCE
     STATUS       current
     DESCRIPTION
                  "The basic implementation requirements for the SALIX-M4-MIB."
     MODULE       -- This module
     MANDATORY-GROUPS { salixPPIGroup }
     ::= { salixProductPlugInMIBCompliance 2 }

END
