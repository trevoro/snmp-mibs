PANDATEL-AGENT-MIB DEFINITIONS ::= BEGIN

 -- This is private mib Agent Group
 -- for all snmp-manageable entities by PANDATEL.

 -- The agent's universal description resides in group 10000.
 -- This is because the agent information shall be supported
 -- by all manageable devices independent of their particular
 -- network technology or management access conditions.

 -- Ver.1.04  Sep.13.1999

        IMPORTS
                enterprises, Counter, IpAddress, Gauge, TimeTicks
                        FROM RFC1155-SMI
                DisplayString, PhysAddress
                        FROM RFC1213-MIB
                OBJECT-TYPE
                        FROM RFC-1212;

 -- ********************* THE MAIN STRUCTURE ********************

pandatel        OBJECT IDENTIFIER ::= { enterprises 760 }

mibs            OBJECT IDENTIFIER ::= { pandatel 1 }

agent           OBJECT IDENTIFIER ::= { mibs 10000 }

-- *********************** THE SNMP AGENT **********************

agentGroup      OBJECT IDENTIFIER ::= { agent 1 }

agentNetAddress  OBJECT-TYPE
        SYNTAX  IpAddress
        ACCESS  read-write
        STATUS  mandatory
        DESCRIPTION
                "The administrative network address of this unit's
                 agent, e.g. the IP address."
        ::= { agentGroup 1 }

agentSubnetMask OBJECT-TYPE
        SYNTAX  IpAddress
        ACCESS  read-write
        STATUS  mandatory
        DESCRIPTION
                "The administrative SubNet mask of this unit's agent."
        ::= { agentGroup 2 }

agentPhysAddress OBJECT-TYPE
        SYNTAX  PhysAddress
        ACCESS  read-only
        STATUS  mandatory
        DESCRIPTION
                "The physical address of this unit's agent."
        ::= { agentGroup 3 }

agentMgmtAccessMode OBJECT-TYPE
        SYNTAX  INTEGER {
                other(1),       -- not yet defined
                inband(2),      -- inband mgmt, e.g. some lan devices
                outband(3),     -- outband mgmt, e.g. some transparent
                                --   point-to-point devices
                proxy(4)        -- mgmt only via a proxy agent
        }
        ACCESS  read-only
        STATUS  mandatory
        DESCRIPTION
                "The mode this unit's agent can be reached."
        ::= { agentGroup 4 }

agentHardwareRevision OBJECT-TYPE
        SYNTAX  DisplayString
        ACCESS  read-only
        STATUS  mandatory
        DESCRIPTION
                "The hardware revision of this unit's agent.
                 This is intended to be of the type like 1.00a,
                 but can also contain any textual description."
        ::= { agentGroup 5 }

agentSoftwareRevision OBJECT-TYPE
        SYNTAX  DisplayString
        ACCESS  read-only
        STATUS  mandatory
        DESCRIPTION
                "The software revision of this unit's agent.
                 This is intended to be of the type like 1.00a,
                 but can also contain any textual description."
        ::= { agentGroup 6 }

agentTrapReceiverTable OBJECT-TYPE
        SYNTAX  SEQUENCE OF AgentTrapReceiverTableEntry
        ACCESS  not-accessible
        STATUS  mandatory
        DESCRIPTION
                "This entity's Trap Receiver Table."
        ::= { agentGroup 7 }

agentSecurityTable OBJECT-TYPE
        SYNTAX  SEQUENCE OF AgentSecurityTableEntry
        ACCESS  not-accessible
        STATUS  mandatory
        DESCRIPTION
                "This entity's Security Table."
        ::= { agentGroup 8 }

agTrapReceiverTableEntry OBJECT-TYPE
        SYNTAX  AgentTrapReceiverTableEntry
        ACCESS  not-accessible
        STATUS  mandatory
        DESCRIPTION
                "One entry in this entity's Trap Receiver Table,
                 consisting of the trap receiver's IP address
                 and the community string to be used with it."
        INDEX   { agTrapReceiverNetAddress }
        ::= { agentTrapReceiverTable 1 }

AgentTrapReceiverTableEntry ::= SEQUENCE {
        agTrapReceiverNetAddress
                IpAddress,
        agTrapReceiverTrapCommunity
                DisplayString,
        agTrapReceiverType
                INTEGER
        }

agTrapReceiverNetAddress  OBJECT-TYPE
        SYNTAX  IpAddress
        ACCESS  read-write
        STATUS  mandatory
        DESCRIPTION
                "The network address of this trap receiver, e.g.
                 the IP Address."
        ::= { agTrapReceiverTableEntry 1 }

agTrapReceiverTrapCommunity  OBJECT-TYPE
        SYNTAX  DisplayString
        ACCESS  read-write
        STATUS  mandatory
        DESCRIPTION
                "The community string used for traps to this receiver."
        ::= { agTrapReceiverTableEntry 2 }

agTrapReceiverType   OBJECT-TYPE
        SYNTAX  INTEGER {
                valid (1),    -- a valid address
                invalid (2)   -- an invalid address
                }
        ACCESS  read-write
        STATUS  mandatory
        DESCRIPTION
                "All entries return the value 1 (valid) for this
                 object.
                 Setting this object to the value 2 (invalid) deletes
                 the entry from the trap receiver table."
        ::= { agTrapReceiverTableEntry 3 }

agSecTableEntry OBJECT-TYPE
        SYNTAX  AgentSecurityTableEntry
        ACCESS  not-accessible
        STATUS  mandatory
        DESCRIPTION
                "One entry in this entity's security table,
                 consisting of the security level and the
                 community string to be used with it."
        INDEX   { agSecSecurityLevel }
        ::= { agentSecurityTable 1 }

AgentSecurityTableEntry ::= SEQUENCE {
        agSecSecurityLevel
                INTEGER,
        agSecCommunity
                DisplayString
        }

agSecSecurityLevel  OBJECT-TYPE
        SYNTAX  INTEGER {
                read-only-sysgroup (1),
                read-all-mgmt-objs (2),
                standard-mgmt-access (3),
                administrator-access (4),
                high-security-access (5)
        }
        ACCESS  read-only
        STATUS  mandatory
        DESCRIPTION
                "The security level that is indicated by using the
                 security community string."
        ::= { agSecTableEntry 1 }

agSecCommunity  OBJECT-TYPE
        SYNTAX  DisplayString
        ACCESS  read-write
        STATUS  mandatory
        DESCRIPTION
                "The community string used for identification of
                 the desired security level."
        ::= { agSecTableEntry 2 }

agentMgmtSecurity  OBJECT IDENTIFIER ::= { agentGroup 9 }

agentAuthRestrictMode OBJECT-TYPE
        SYNTAX  INTEGER {
                other         (1),
                notRestricted (2),
                restricted    (3)
        }
        ACCESS  read-write
        STATUS  mandatory
        DESCRIPTION
                "Restricting management authorization means that only
                 snmp requests from members of the trap receiver table
                 will be accepted.
                 Requests from other sources will instead cause an
                 authentication trap, if enabled.
                 When not restricted, snmp requests from any manager
                 who uses a valid community will be accepted, although
                 traps will be sent only to those destinations that
                 are included in the trap receiver table."
        ::= { agentMgmtSecurity 1 }

END
