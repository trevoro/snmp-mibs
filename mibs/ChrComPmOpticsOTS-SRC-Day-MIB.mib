ChrComPmOpticsOTS-SRC-Day-MIB

--FORCE-INCLUDE	<mib.h>
--FORCE-INCLUDE	<snmpdefs.h>
--FORCE-INCLUDE	"mibhand.h"

	DEFINITIONS  ::=  BEGIN

IMPORTS
	OBJECT-TYPE, Counter32			FROM  SNMPv2-SMI
	Integer32, Unsigned32			FROM  SNMPv2-SMI
	chrComPmOptics				FROM  Chromatis-MIB
	chrComIfifIndex					FROM  ChrComIfifTable-MIB
	TruthValue				FROM  ChrTyp-MIB
	Gauge32				FROM  SNMPv2-SMI;

-- chrComPmOpticsOTS-SRC-Day Table

chrComPmOpticsOTS-SRC-DayTable		OBJECT-TYPE
	SYNTAX		SEQUENCE OF ChrComPmOpticsOTS-SRC-DayEntry
	MAX-ACCESS	not-accessible
	STATUS		current
	DESCRIPTION
	""
	::= { chrComPmOptics 6}

chrComPmOpticsOTS-SRC-DayEntry		OBJECT-TYPE
	SYNTAX		ChrComPmOpticsOTS-SRC-DayEntry
	MAX-ACCESS	not-accessible
	STATUS		current
	DESCRIPTION
	""
	INDEX  {  chrComIfifIndex, chrComPmOpticsDayNumber }

--DEFAULT  get-function-async  MNIL_GetRoutine
--DEFAULT  set-function-async  MNIL_SetRoutine
--DEFAULT  next-function-async MNIL_NextRoutine
--DEFAULT  test-function-async MNIL_TestRoutine
--DEFAULT  cookie "OTS-SRC-Day"
	::= { chrComPmOpticsOTS-SRC-DayTable  1 }

ChrComPmOpticsOTS-SRC-DayEntry  ::=
	SEQUENCE  {
	chrComPmOpticsDayNumber		Unsigned32	(1..2),
	chrComPmOpticsSuspectedIntrvl		TruthValue,
	chrComPmOpticsElapsedTime		Unsigned32	(0..4294967295),
	chrComPmOpticsSuppressedIntrvls	Gauge32			(0..4294967295),
	chrComPmOpticsORS			Gauge32			(0..4294967295),
	chrComPmOpticsSES			Gauge32			(0..4294967295),
	chrComPmOpticsUAS			Gauge32			(0..4294967295),
	chrComPmOpticsMean			Integer32	(0..2147483647),
	chrComPmOpticsMax			Integer32	(0..2147483647),
	chrComPmOpticsMin			Integer32	(0..2147483647),
	chrComPmOpticsSD			Integer32	(0..2147483647),
	chrComPmOpticsThresholdProfIndex	Unsigned32	(0..4294967295),
	chrComPmOpticsResetCountersAction	TruthValue
}

chrComPmOpticsDayNumber 	OBJECT-TYPE
	SYNTAX		Unsigned32	(1..2)
	MAX-ACCESS 	read-only
	STATUS 		current
	DESCRIPTION
	""
	::= { chrComPmOpticsOTS-SRC-DayEntry  1 }

chrComPmOpticsSuspectedIntrvl 	OBJECT-TYPE
	SYNTAX		TruthValue
	MAX-ACCESS 	read-only
	STATUS 		current
	DESCRIPTION
	"a flag marking the validity of the entry data"
	::= { chrComPmOpticsOTS-SRC-DayEntry  2 }

chrComPmOpticsElapsedTime 	OBJECT-TYPE
	SYNTAX		Unsigned32	(0..4294967295)
	MAX-ACCESS 	read-only
	STATUS 		current
	DESCRIPTION
	"measurment duration, in 0.01 seconds"
	::= { chrComPmOpticsOTS-SRC-DayEntry  3 }

chrComPmOpticsSuppressedIntrvls 	OBJECT-TYPE
	SYNTAX		Gauge32			(0..4294967295)
	MAX-ACCESS 	read-only
	STATUS 		current
	DESCRIPTION
	"invalid for first version. indicates how many all-zero periods have passed."
	::= { chrComPmOpticsOTS-SRC-DayEntry  4 }

chrComPmOpticsORS 	OBJECT-TYPE
	SYNTAX		Gauge32			(0..4294967295)
	MAX-ACCESS 	read-only
	STATUS 		current
	DESCRIPTION
	""
	::= { chrComPmOpticsOTS-SRC-DayEntry  5 }

chrComPmOpticsSES 	OBJECT-TYPE
	SYNTAX		Gauge32			(0..4294967295)
	MAX-ACCESS 	read-only
	STATUS 		current
	DESCRIPTION
	""
	::= { chrComPmOpticsOTS-SRC-DayEntry  6 }

chrComPmOpticsUAS 	OBJECT-TYPE
	SYNTAX		Gauge32			(0..4294967295)
	MAX-ACCESS 	read-only
	STATUS 		current
	DESCRIPTION
	""
	::= { chrComPmOpticsOTS-SRC-DayEntry  7 }

chrComPmOpticsMean 	OBJECT-TYPE
	SYNTAX		Integer32	(0..2147483647)
	MAX-ACCESS 	read-only
	STATUS 		current
	DESCRIPTION
	""
	::= { chrComPmOpticsOTS-SRC-DayEntry  8 }

chrComPmOpticsMax 	OBJECT-TYPE
	SYNTAX		Integer32	(0..2147483647)
	MAX-ACCESS 	read-only
	STATUS 		current
	DESCRIPTION
	""
	::= { chrComPmOpticsOTS-SRC-DayEntry  9 }

chrComPmOpticsMin 	OBJECT-TYPE
	SYNTAX		Integer32	(0..2147483647)
	MAX-ACCESS 	read-only
	STATUS 		current
	DESCRIPTION
	""
	::= { chrComPmOpticsOTS-SRC-DayEntry  10 }

chrComPmOpticsSD 	OBJECT-TYPE
	SYNTAX		Integer32	(0..2147483647)
	MAX-ACCESS 	read-only
	STATUS 		current
	DESCRIPTION
	""
	::= { chrComPmOpticsOTS-SRC-DayEntry  11 }

chrComPmOpticsThresholdProfIndex 	OBJECT-TYPE
	SYNTAX		Unsigned32	(0..4294967295)
	MAX-ACCESS 	read-write
	STATUS 		current
	DESCRIPTION
	""
	::= { chrComPmOpticsOTS-SRC-DayEntry  12 }

chrComPmOpticsResetCountersAction 	OBJECT-TYPE
	SYNTAX		TruthValue
	MAX-ACCESS 	read-write
	STATUS 		current
	DESCRIPTION
	""
	::= { chrComPmOpticsOTS-SRC-DayEntry  13 }


END
