-- ZyXEL Communications Corporation
-- Private Enterprise MIB definition 
  
-- This file describes the ZyXEL Communications Corporation Enterprise MIB.
-- It contains ZyXEL products OIDs, and common managed objects.

-- $Log: ZYXEL-VLAN-COUNTER-MIB.mib $ 
-- Revision 1.3  2012/09/19 08:21:06  Kevin 
-- if it's leaf node, revise the vender name from zyxel to zy 
-- Revision 1.2  2012/07/05 06:25:03  Kevin 
-- 1. upgrade from SNMP to SNMPv2  
-- 2. clean warning 
-- Revision 1.1  2012/05/31 10:46:48  Kevin 
-- Initial revision 

ZYXEL-VLAN-COUNTER-MIB DEFINITIONS ::= BEGIN

    IMPORTS
	enterprises		FROM RFC1155-SMI                                
	
	OBJECT-TYPE, Unsigned32, Counter64
		FROM SNMPv2-SMI			-- RFC2578	
	RowStatus, DateAndTime, TruthValue, StorageType, MacAddress
		FROM SNMPv2-TC			-- RFC2579
	DisplayString                                          
	  	FROM RFC1213-MIB
	EnabledStatus
		FROM  P-BRIDGE-MIB
	PortList
		FROM  Q-BRIDGE-MIB
	dot1dBasePort
       	FROM BRIDGE-MIB
	InterfaceIndexOrZero			-- RFC2863
		FROM IF-MIB
	SnmpAdminString
		FROM SNMP-FRAMEWORK-MIB		-- RFC2571
	InetAddressType, InetAddress
		FROM INET-ADDRESS-MIB		-- RFC2851
	OperationResponseStatus
		FROM DISMAN-PING-MIB
    Counter, TimeTicks
        FROM RFC1155-SMI
    BridgeId, Timeout
        FROM BRIDGE-MIB  
    dot1agCfmMdIndex 
		FROM IEEE8021-CFM-MIB
	dot1agCfmMaIndex
		FROM IEEE8021-CFM-MIB	
	dot1agCfmMepIdentifier
		FROM IEEE8021-CFM-MIB   	
    IpAddress
        FROM SNMPv2-SMI
    ifIndex
    	FROM IF-MIB					-- RFC2863
    NOTIFICATION-TYPE
        FROM SNMPv2-SMI
    sysObjectID 
        FROM RFC1213-MIB 
	ospfIfIpAddress, ospfAddressLessIf, ospfAreaId, ospfNbrIpAddr, ospfNbrAddressLessIndex,
	ospfLsdbAreaId, ospfLsdbType, ospfLsdbLsid, ospfLsdbRouterId, ospfVirtIfAreaId, ospfVirtIfNeighbor
		FROM OSPF-MIB
	esMgmt			
		FROM ZYXEL-ES-SMI;

	zyxelVlanCounter MODULE-IDENTITY
		LAST-UPDATED	"201207010000Z"    
		ORGANIZATION "Enterprise Solution ZyXEL"     
		CONTACT-INFO
			""	   
		DESCRIPTION
			"The subtree for VLAN counter"
		::= { esMgmt 87 }	

	zyxelVlanCounterSetup		OBJECT IDENTIFIER ::= { zyxelVlanCounter 1  }
	zyxelVlanCounterStatus     	OBJECT IDENTIFIER ::= { zyxelVlanCounter 2 }
		
-- *******************************************************************
-- *
-- * zyxelVlanCounterSetup
-- *
-- ******************************************************************* 
    			
-- zyxelVlanCounterTable
		zyxelVlanCounterTable OBJECT-TYPE
	    SYNTAX      SEQUENCE OF ZyxelVlanCounterEntry
        MAX-ACCESS  not-accessible
	    STATUS      current
	    DESCRIPTION
	            "Defines the Vlan Counter Table for providing, via SNMP,
           the capability of performing vlan counting operations at
          a remote host and having their results of these operations are
          stored in the table."       
        ::= { zyxelVlanCounterSetup 1 }

    	zyxelVlanCounterEntry OBJECT-TYPE
        SYNTAX      ZyxelVlanCounterEntry
        MAX-ACCESS  not-accessible
        STATUS      current
        DESCRIPTION
            "Defines an entry in the zyxelVlanCounterTable."
        INDEX {
                zyVlanCounterVid             
        }
    	::= { zyxelVlanCounterTable 1 }

   		ZyxelVlanCounterEntry ::=
        SEQUENCE {
			zyVlanCounterVid	   	INTEGER,
            zyVlanCounterTimeout    Unsigned32,
            zyVlanCounterPorts      PortList,     
            zyVlanCounterRowStatus  RowStatus
       
   		}  
		
    	zyVlanCounterVid OBJECT-TYPE
        SYNTAX  INTEGER   
        MAX-ACCESS  not-accessible
        STATUS      current
        DESCRIPTION
            "VLAN ID where the VLAN counter applies."
        ::= { zyxelVlanCounterEntry 1 }		
   		
    	zyVlanCounterTimeout OBJECT-TYPE
        SYNTAX  Unsigned32   
        MAX-ACCESS  read-write
        STATUS      current
        DESCRIPTION
			"Specifies the time-out value, in seconds, for a VLAN counter operation."
        ::= { zyxelVlanCounterEntry 2 }

    	zyVlanCounterPorts OBJECT-TYPE
        SYNTAX      PortList
        MAX-ACCESS  read-write
        STATUS      current
        DESCRIPTION
			"Specify the port for a VLAN counter operation."        
        ::= { zyxelVlanCounterEntry 3 }

		zyVlanCounterRowStatus OBJECT-TYPE
    	SYNTAX		RowStatus
    	MAX-ACCESS	read-create
    	STATUS		current
    	DESCRIPTION
    		"This object allows to create and delete a VLAN counter entry." 
        ::= { zyxelVlanCounterEntry 4 }

-- *******************************************************************
-- *
-- * zyxelVlanCounterStatus
-- *
-- ******************************************************************* 
      
-- zyxelVlanCounterInfoTable
       	zyxelVlanCounterInfoTable OBJECT-TYPE
	    SYNTAX      SEQUENCE OF ZyxelVlanCounterInfoEntry
        MAX-ACCESS  not-accessible
	    STATUS      current
	    DESCRIPTION
	            "The table that show incoming packet statistics on individual VLAN"       
        ::= { zyxelVlanCounterStatus 1 }

    	zyxelVlanCounterInfoEntry OBJECT-TYPE
        SYNTAX      ZyxelVlanCounterInfoEntry
        MAX-ACCESS  not-accessible
        STATUS      current
        DESCRIPTION
            "Incoming packet statistics information for a particular VLAN."
        INDEX {
                zyVlanCounterInfoVid             
        }
    	::= { zyxelVlanCounterInfoTable 1 }

   		ZyxelVlanCounterInfoEntry ::=
        SEQUENCE {
			zyVlanCounterInfoVid						INTEGER,
            zyVlanCounterInfoHCOctets                   Counter64,
            zyVlanCounterInfoHCPackets                  Counter64,
            zyVlanCounterInfoHCMulticastPackets         Counter64,
            zyVlanCounterInfoHCBroadcastPackets         Counter64,
            zyVlanCounterInfoHCTaggedPackets            Counter64,
            zyVlanCounterInfoHCPackets64Octets	       	Counter64,
            zyVlanCounterInfoHCPackets65to127Octets     Counter64,
            zyVlanCounterInfoHCPackets128to255Octets    Counter64,
            zyVlanCounterInfoHCPackets256to511Octets    Counter64,
            zyVlanCounterInfoHCPackets512to1023Octets   Counter64,
            zyVlanCounterInfoHCPackets1024to1518Octets  Counter64,
            zyVlanCounterInfoHCOversizePackets          Counter64
   		}   	

		zyVlanCounterInfoVid OBJECT-TYPE
		SYNTAX		INTEGER
        MAX-ACCESS  not-accessible
        STATUS      current
        DESCRIPTION
            "VLAN ID where the VLAN counter applies."
        ::= { zyxelVlanCounterInfoEntry 1 }		
		
    	zyVlanCounterInfoHCOctets OBJECT-TYPE
        SYNTAX      Counter64 
        UNITS       "Octets"
        MAX-ACCESS  read-only
        STATUS      current
        DESCRIPTION
            "Average receive Octets"
        ::= { zyxelVlanCounterInfoEntry 2 } 

    	zyVlanCounterInfoHCPackets OBJECT-TYPE
        SYNTAX      Counter64
        MAX-ACCESS  read-only
        STATUS      current
        DESCRIPTION
            "Total received number of good packets flowing trhough this VLAN."    
        ::= { zyxelVlanCounterInfoEntry 3 }

    	zyVlanCounterInfoHCMulticastPackets OBJECT-TYPE
        SYNTAX      Counter64
        MAX-ACCESS  read-only
        STATUS      current
        DESCRIPTION
            "Total received number of  good multicast packets flowing through this VLAN."    
        ::= { zyxelVlanCounterInfoEntry 4 }

    	zyVlanCounterInfoHCBroadcastPackets OBJECT-TYPE
        SYNTAX      Counter64  
        MAX-ACCESS  read-only
        STATUS      current
        DESCRIPTION        
             "Total received number of  good broadcast packets flowing through this VLAN."    
        ::= { zyxelVlanCounterInfoEntry 5 }

    	zyVlanCounterInfoHCTaggedPackets OBJECT-TYPE
        SYNTAX      Counter64  
        MAX-ACCESS  read-only
        STATUS      current
        DESCRIPTION        
             "Total received number of  VLAN-tagged packets flowing through this VLAN."    
        ::= { zyxelVlanCounterInfoEntry 6 }

    	zyVlanCounterInfoHCPackets64Octets OBJECT-TYPE
        SYNTAX      Counter64     
        MAX-ACCESS  read-only
        STATUS      current
        DESCRIPTION
            "Total received number of packets that were 64 octets in length."    
        ::= { zyxelVlanCounterInfoEntry 7 }

    	zyVlanCounterInfoHCPackets65to127Octets OBJECT-TYPE
        SYNTAX      Counter64             
        MAX-ACCESS  read-only
        STATUS      current
        DESCRIPTION    
            "Total received number of packets that were between 65 and 127 octets in length."     
        ::= { zyxelVlanCounterInfoEntry 8 }

    	zyVlanCounterInfoHCPackets128to255Octets OBJECT-TYPE
        SYNTAX      Counter64
        MAX-ACCESS  read-only
        STATUS      current
        DESCRIPTION
            "Total received number of packets that were between 128 and 255 octets in length."
        ::= { zyxelVlanCounterInfoEntry 9 }

    	zyVlanCounterInfoHCPackets256to511Octets  OBJECT-TYPE
        SYNTAX      Counter64    
        MAX-ACCESS  read-only
        STATUS      current
        DESCRIPTION
            "Total received number of packets that were between 256 and 511 octets in length."           
        ::= { zyxelVlanCounterInfoEntry 10 }

    	zyVlanCounterInfoHCPackets512to1023Octets OBJECT-TYPE
        SYNTAX      Counter64
        MAX-ACCESS  read-only
        STATUS      current
        DESCRIPTION        
            "Total received number of packets that were between 512 and 1023 octets in length "    
        ::= { zyxelVlanCounterInfoEntry 11 }

    	zyVlanCounterInfoHCPackets1024to1518Octets OBJECT-TYPE
        SYNTAX      Counter64
        MAX-ACCESS  read-only
        STATUS      current
        DESCRIPTION
            "Total received number of packets that were between 1024 and 1518 octets in length "         
        ::= { zyxelVlanCounterInfoEntry 12 }

    	zyVlanCounterInfoHCOversizePackets OBJECT-TYPE
        SYNTAX     Counter64
        MAX-ACCESS  read-only
        STATUS      current
        DESCRIPTION
            "Total received number of packets that were between 1519 octets and the maximun frame size. 
            The maximun frame size varies depending on your switch model"     
        ::= { zyxelVlanCounterInfoEntry 13 }

 
END
