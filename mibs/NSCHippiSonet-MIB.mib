-- Network Systems Corporation Enterprise MIB for Hippi/Sonet Management
-- Thu Sep 16 1993
-- J. Miller

-- This MIB is to be used in conjunction with the NSC standard MIB to
-- define Sonet specific information.

               NSCHippiSonet-MIB DEFINITIONS ::= BEGIN
 
               IMPORTS
                       OBJECT-TYPE FROM RFC1155-SMI
							  DisplayString, PhysAddress
                           FROM RFC1213-MIB
                       nscHippiSonet
                           FROM NSC-MIB;

               -- For ease of lookup, the following are actually defined
               -- in the NSC MIB but are supplied here as comments.
               -- The content of this MIB definition is to define the
               -- objects under the nscHippiSonet node.

               -- nsc		OBJECT IDENTIFIER ::= { enterprises 10 }
               -- nscMib	OBJECT IDENTIFIER ::= { nsc 2 }
               -- nscProducts	OBJECT IDENTIFIER ::= { nscMib 1 }
               --   nscDevices	OBJECT IDENTIFIER ::= { nscProducts 1 }
               --     nscObj	OBJECT IDENTIFIER ::= { nscDevices 1 }
               --   nscHippiSonet OBJECT IDENTIFIER ::= { nscProducts 5 }

               nscHippiSonetEngineStatus OBJECT-TYPE
                   SYNTAX   DisplayString
                   ACCESS   read-only
                   STATUS   mandatory
                   DESCRIPTION
                       "String describing the current state of the engine."
               ::= { nscHippiSonet 1 }

               -- The MIB currently contains information that is roughly
               -- translated from the procedures used to diagnose the
               -- machine.  As such, items exist for checking register
               -- status, monitor status, and A/D status.

               nscHippiSonetRegisters OBJECT IDENTIFIER ::= { nscHippiSonet 2 }
               nscHippiSonetMonitor   OBJECT IDENTIFIER ::= { nscHippiSonet 3 }
               nscHippiSonetAtoD      OBJECT IDENTIFIER ::= { nscHippiSonet 4 }

               nscHippiSonetSourceIField OBJECT-TYPE
                   SYNTAX   DisplayString
                   ACCESS   read-only
                   STATUS   mandatory
                   DESCRIPTION
                       "Hippi source I-Field register."
               ::= { nscHippiSonet 5 }

               nscHippiSonetProfile   OBJECT IDENTIFIER ::= { nscHippiSonet 6 }

               -- The sonet registers object contains objects for the Framer,
               -- Unframer, and Mega FIFO.  Rather then returning a cryptic
               -- hex digit, and ascii version of the decoded register is
               -- returned as a string.

               -- Sonet Unframer registers

               nscHippiSonetUnframer OBJECT IDENTIFIER ::=
                                                   { nscHippiSonetRegisters 1 }

               nscHippiSonetUnframerStatus OBJECT-TYPE
                   SYNTAX   DisplayString
                   ACCESS   read-only
                   STATUS   mandatory
                   DESCRIPTION
                       "Unframer status register."
               ::= { nscHippiSonetUnframer 1 }

               nscHippiSonetUnframerOHdma OBJECT-TYPE
                   SYNTAX   DisplayString
                   ACCESS   read-only
                   STATUS   mandatory
                   DESCRIPTION
                       "Unframer overhead DMA register."
               ::= { nscHippiSonetUnframer 2 }


               -- Sonet Framer registers

               nscHippiSonetFramer OBJECT IDENTIFIER ::=
                                                   { nscHippiSonetRegisters 2 }

               nscHippiSonetFramerStatus OBJECT-TYPE
                   SYNTAX   DisplayString
                   ACCESS   read-only
                   STATUS   mandatory
                   DESCRIPTION
                       "Framer status register."
               ::= { nscHippiSonetFramer 1 }

               nscHippiSonetFramerAdaptID OBJECT-TYPE
                   SYNTAX   DisplayString
                   ACCESS   read-only
                   STATUS   mandatory
                   DESCRIPTION
                       "Adaptor ID (HDA) and enable status."
               ::= { nscHippiSonetFramer 2 }

               nscHippiSonetFramerInput OBJECT-TYPE
                   SYNTAX   DisplayString
                   ACCESS   read-only
                   STATUS   mandatory
                   DESCRIPTION
                       "Framer input register."
               ::= { nscHippiSonetFramer 3 }

               nscHippiSonetFramerData OBJECT-TYPE
                   SYNTAX   DisplayString
                   ACCESS   read-only
                   STATUS   mandatory
                   DESCRIPTION
                       "Framer data register."
               ::= { nscHippiSonetFramer 4 }

               nscHippiSonetFramerIField OBJECT-TYPE
                   SYNTAX   DisplayString
                   ACCESS   read-only
                   STATUS   mandatory
                   DESCRIPTION
                       "Framer I-Field register."
               ::= { nscHippiSonetFramer 5 }


               -- Sonet Mega FIFO registers

               nscHippiSonetMegaFifo OBJECT IDENTIFIER ::=
                                                   { nscHippiSonetRegisters 3 }

               nscHippiSonetMFcontrol OBJECT-TYPE
                   SYNTAX   DisplayString
                   ACCESS   read-only
                   STATUS   mandatory
                   DESCRIPTION
                       "Mega FIFO control register."
               ::= { nscHippiSonetMegaFifo 1 }

               nscHippiSonetMFstatus OBJECT-TYPE
                   SYNTAX   DisplayString
                   ACCESS   read-only
                   STATUS   mandatory
                   DESCRIPTION
                       "Mega FIFO status register."
               ::= { nscHippiSonetMegaFifo 2 }

               nscHippiSonetMFtimeout OBJECT-TYPE
                   SYNTAX   DisplayString
                   ACCESS   read-only
                   STATUS   mandatory
                   DESCRIPTION
                       "Mega FIFO timeout register."
               ::= { nscHippiSonetMegaFifo 3 }

               nscHippiSonetMFConnectStatus OBJECT-TYPE
                   SYNTAX   DisplayString
                   ACCESS   read-only
                   STATUS   mandatory
                   DESCRIPTION
                       "Mega FIFO connection status register."
               ::= { nscHippiSonetMegaFifo 4 }

               -- The monitor counts a number of items.  These are
               -- stored in a global structure and are returned via
               -- the following object.  Even though the counters are
               -- 64 bits, only the lower 32 are returned.

               nscHippiSonetMonClock OBJECT-TYPE
                   SYNTAX   INTEGER
                   ACCESS   read-only
                   STATUS   mandatory
                   DESCRIPTION
                       "500 Khz clock value (for time stamps)."
               ::= { nscHippiSonetMonitor 1 }

               nscHippiSonetMonMFFlowControl OBJECT-TYPE
                   SYNTAX   INTEGER
                   ACCESS   read-only
                   STATUS   mandatory
                   DESCRIPTION
                       "Mega FIFO flow control duration."
               ::= { nscHippiSonetMonitor 2 }

               nscHippiSonetMonDLFlowControl OBJECT-TYPE
                   SYNTAX   INTEGER
                   ACCESS   read-only
                   STATUS   mandatory
                   DESCRIPTION
                       "Down line flow control duration"
               ::= { nscHippiSonetMonitor 3 }

               nscHippiSonetMonBIPErrors OBJECT-TYPE
                   SYNTAX   INTEGER
                   ACCESS   read-only
                   STATUS   mandatory
                   DESCRIPTION
                       "Received path BIP Errors."
               ::= { nscHippiSonetMonitor 4 }

               nscHippiSonetMonSrcBusy OBJECT-TYPE
                   SYNTAX   INTEGER
                   ACCESS   read-only
                   STATUS   mandatory
                   DESCRIPTION
                       "Duration in 500Khz that the source was busy."
               ::= { nscHippiSonetMonitor 5 }

               nscHippiSonetMonSrcSOC OBJECT-TYPE
                   SYNTAX   INTEGER
                   ACCESS   read-only
                   STATUS   mandatory
                   DESCRIPTION
                       "Number of source start of connections"
               ::= { nscHippiSonetMonitor 6 }

               nscHippiSonetMonSrcEOC OBJECT-TYPE
                   SYNTAX   INTEGER
                   ACCESS   read-only
                   STATUS   mandatory
                   DESCRIPTION
                       "Number of source end of connections"
               ::= { nscHippiSonetMonitor 7 }

               nscHippiSonetMonDstConnectDuration OBJECT-TYPE
                   SYNTAX   INTEGER
                   ACCESS   read-only
                   STATUS   mandatory
                   DESCRIPTION
                       "Number 500Khz cycles destination has been connected"
               ::= { nscHippiSonetMonitor 8 }

               nscHippiSonetMonSrcConnectDuration OBJECT-TYPE
                   SYNTAX   INTEGER
                   ACCESS   read-only
                   STATUS   mandatory
                   DESCRIPTION
                       "Number 500Khz cycles source has been connected"
               ::= { nscHippiSonetMonitor 9 }

               nscHippiSonetMonDstConnectReject OBJECT-TYPE
                   SYNTAX   INTEGER
                   ACCESS   read-only
                   STATUS   mandatory
                   DESCRIPTION
                       "Number of Destination connect rejects."
               ::= { nscHippiSonetMonitor 10 }

               nscHippiSonetMonSrcConnectFail OBJECT-TYPE
                   SYNTAX   INTEGER
                   ACCESS   read-only
                   STATUS   mandatory
                   DESCRIPTION
                       "Number of source connect failures."
               ::= { nscHippiSonetMonitor 11 }

               nscHippiSonetMonLOF OBJECT-TYPE
                   SYNTAX   INTEGER
                   ACCESS   read-only
                   STATUS   mandatory
                   DESCRIPTION
                       "Number of receive sonet Loss of Frame events"
               ::= { nscHippiSonetMonitor 12 }

               nscHippiSonetMonLOS OBJECT-TYPE
                   SYNTAX   INTEGER
                   ACCESS   read-only
                   STATUS   mandatory
                   DESCRIPTION
                       "Number of receive sonet Loss of Signal events"
               ::= { nscHippiSonetMonitor 13 }

               nscHippiSonetMonDstBursts OBJECT-TYPE
                   SYNTAX   INTEGER
                   ACCESS   read-only
                   STATUS   mandatory
                   DESCRIPTION
                       "Number of Destination bursts"
               ::= { nscHippiSonetMonitor 14 }

               nscHippiSonetMonDstPackets OBJECT-TYPE
                   SYNTAX   INTEGER
                   ACCESS   read-only
                   STATUS   mandatory
                   DESCRIPTION
                       "Number of Destination packets"
               ::= { nscHippiSonetMonitor 15 }

               nscHippiSonetMonDstSync OBJECT-TYPE
                   SYNTAX   INTEGER
                   ACCESS   read-only
                   STATUS   mandatory
                   DESCRIPTION
                       "Number of Destination sync errors"
               ::= { nscHippiSonetMonitor 16 }

               nscHippiSonetMonDstLLRC OBJECT-TYPE
                   SYNTAX   INTEGER
                   ACCESS   read-only
                   STATUS   mandatory
                   DESCRIPTION
                       "Number of Destination LLRC errors"
               ::= { nscHippiSonetMonitor 17 }

               nscHippiSonetMonDstPE OBJECT-TYPE
                   SYNTAX   INTEGER
                   ACCESS   read-only
                   STATUS   mandatory
                   DESCRIPTION
                       "Number of Destination Parity Errors"
               ::= { nscHippiSonetMonitor 18 }

               nscHippiSonetMonDstConnect OBJECT-TYPE
                   SYNTAX   INTEGER
                   ACCESS   read-only
                   STATUS   mandatory
                   DESCRIPTION
                       "Number of Destination connects"
               ::= { nscHippiSonetMonitor 19 }

               nscHippiSonetMonSrcConnect OBJECT-TYPE
                   SYNTAX   INTEGER
                   ACCESS   read-only
                   STATUS   mandatory
                   DESCRIPTION
                       "Number of source connects"
               ::= { nscHippiSonetMonitor 20 }

               nscHippiSonetMonSrcPackets OBJECT-TYPE
                   SYNTAX   INTEGER
                   ACCESS   read-only
                   STATUS   mandatory
                   DESCRIPTION
                       "Number of source packets"
               ::= { nscHippiSonetMonitor 21 }

               nscHippiSonetMonSrcBursts OBJECT-TYPE
                   SYNTAX   INTEGER
                   ACCESS   read-only
                   STATUS   mandatory
                   DESCRIPTION
                       "Number of source bursts"
               ::= { nscHippiSonetMonitor 22 }

               nscHippiSonetMonSrcForceErrors OBJECT-TYPE
                   SYNTAX   INTEGER
                   ACCESS   read-only
                   STATUS   mandatory
                   DESCRIPTION
                       "Number of Source Bad-data Force Errors"
               ::= { nscHippiSonetMonitor 23 }

               nscHippiSonetMonSrcCRC OBJECT-TYPE
                   SYNTAX   INTEGER
                   ACCESS   read-only
                   STATUS   mandatory
                   DESCRIPTION
                       "Number of Source CRC errors"
               ::= { nscHippiSonetMonitor 24 }

               nscHippiSonetMonDstWords OBJECT-TYPE
                   SYNTAX   INTEGER
                   ACCESS   read-only
                   STATUS   mandatory
                   DESCRIPTION
                       "Number of Destination burst words / 32 (Kbits)"
               ::= { nscHippiSonetMonitor 25 }

               nscHippiSonetMonSrcWords OBJECT-TYPE
                   SYNTAX   INTEGER
                   ACCESS   read-only
                   STATUS   mandatory
                   DESCRIPTION
                       "Number of Destination burst words / 32 (Kbits)"
               ::= { nscHippiSonetMonitor 26 }

               -- There is an AtoD task that continually samples the
               -- AtoD converter and stores the result in a global
               -- structure.  This routine accesses that structure
               -- to return information about its values.

               nscHippiSonetADRecvOpticalPower OBJECT-TYPE
                   SYNTAX   INTEGER
                   ACCESS   read-only
                   STATUS   mandatory
                   DESCRIPTION
                       "Receive optical power in dbm's"
               ::= { nscHippiSonetAtoD 1 }

               nscHippiSonetADLaserBias OBJECT-TYPE
                   SYNTAX   INTEGER
                   ACCESS   read-only
                   STATUS   mandatory
                   DESCRIPTION
                       "Laser bias voltage (in milli-volts)"
               ::= { nscHippiSonetAtoD 2 }

               nscHippiSonetADLaserBackface OBJECT-TYPE
                   SYNTAX   INTEGER
                   ACCESS   read-only
                   STATUS   mandatory
                   DESCRIPTION
                       "Laser backface voltage (in milli-volts)"
               ::= { nscHippiSonetAtoD 3 }

               nscHippiSonetADInternalTemp OBJECT-TYPE
                   SYNTAX   INTEGER
                   ACCESS   read-only
                   STATUS   mandatory
                   DESCRIPTION
                       "Internal temperature (degrees F)"
               ::= { nscHippiSonetAtoD 4 }

               nscHippiSonetADExhaustTemp OBJECT-TYPE
                   SYNTAX   INTEGER
                   ACCESS   read-only
                   STATUS   mandatory
                   DESCRIPTION
                       "Exhaust temperature (degrees F)"
               ::= { nscHippiSonetAtoD 5 }

               -- The NV Ram contains various profiled parameters
               -- that are used by the machine during boot.  The
               -- parameters identify baseline information regarding
               -- sensors as well as operational parameters for boot
               -- output and clock settings.

               nscHippiSonetOpticalRcvOffset OBJECT-TYPE
                   SYNTAX   DisplayString
                   ACCESS   read-only
                   STATUS   mandatory
                   DESCRIPTION
                       "String representation of the floating value for
                       the offset of the optical receive light formula."
               ::= { nscHippiSonetProfile 1 }

               nscHippiSonetOpticalRcvSlope OBJECT-TYPE
                   SYNTAX   DisplayString
                   ACCESS   read-only
                   STATUS   mandatory
                   DESCRIPTION
                       "String representation of the floating value for
                       the slope of the optical receive light formula."
               ::= { nscHippiSonetProfile 2 }

               nscHippiSonetBiasCurrent OBJECT-TYPE
                   SYNTAX   INTEGER
                   ACCESS   read-only
                   STATUS   mandatory
                   DESCRIPTION
                       "Integer representation of the floating value for
                       the baseline current of the transmit laser in
                       milliamps.  This value is used by the machine to
                       determine the life of the laser."
               ::= { nscHippiSonetProfile 3 }

               nscHippiSonetBiasTemp OBJECT-TYPE
                   SYNTAX   INTEGER
                   ACCESS   read-only
                   STATUS   mandatory
                   DESCRIPTION
                       "Temperature in celcius at which the profiled
                       bias current was taken.  This value is used with
                       the bias current to determine the life of the laser."
               ::= { nscHippiSonetProfile 4 }

               nscHippiSonetBackfaceVoltage OBJECT-TYPE
                   SYNTAX   DisplayString
                   ACCESS   read-only
                   STATUS   mandatory
                   DESCRIPTION
                       "String representation of the floting value of the
                       Voltage in millivolts that was measured at the
                       backface of the laser when it was new.  This value
                       is used with the current backface voltage as an
                       additional method of determining if the transmit
                       laser has become defective."
               ::= { nscHippiSonetProfile 5 }

               nscHippiSonetIField OBJECT-TYPE
                   SYNTAX   INTEGER
                   ACCESS   read-write
                   STATUS   mandatory
                   DESCRIPTION
                       "The I-Field address that is used by the hippi
                       interface."
               ::= { nscHippiSonetProfile 6 }

               nscHippiSonetBootPort OBJECT-TYPE
                   SYNTAX   INTEGER (0..1)
                   ACCESS   read-write
                   STATUS   mandatory
                   DESCRIPTION
                       "Which rs232 port the boot information should be sent
                       to.  Ports 1 & 2 are the only valid ports with 1 being
                       located on the back of the machine and 2 on the front."
               ::= { nscHippiSonetProfile 7 }

               nscHippiSonetPortSpeed OBJECT-TYPE
                   SYNTAX   INTEGER
                   ACCESS   read-write
                   STATUS   mandatory
                   DESCRIPTION
                       "The baud rate to set the rs232 ports to at boot time."
               ::= { nscHippiSonetProfile 8 }

               nscHippiSonetThreshold OBJECT-TYPE
                   SYNTAX   INTEGER (0..7)
                   ACCESS   read-write
                   STATUS   mandatory
                   DESCRIPTION
                       "Threshold of the mega-fifo at which flow control will
                       be activated.  The value represents 8ths of the fifo
                       with 7 representing the fifo must be full before flow
                       control is activated and 0 indicating that flow control
                       will happen as soon as the mega-fifo starts to fill.
                       This value may need to be adjusted to deal with time
                       delays over vary long sonet links in that you want flow
                       control to propagate back to the transmitting sonet box
                       before it puts enough information on the line to
                       overflow this machine."
               ::= { nscHippiSonetProfile 9 }

               nscHippiTimeout OBJECT-TYPE
                   SYNTAX   INTEGER (1..'7fff'h)
                   ACCESS   read-write
                   STATUS   mandatory
                   DESCRIPTION
                       "Timeout value to use when trying to connect from our
                       hippi source.  This timer is started when the source
                       raises connect.  If the destination fails to respond
                       before the timer goes off, the connect will be aborted.
                       The timer is represented as the number of 500 KHz
                       clock ticks."
               ::= { nscHippiSonetProfile 10 }

               nscHippiSonetDipSwitch OBJECT-TYPE
                   SYNTAX   INTEGER
                   ACCESS   read-write
                   STATUS   mandatory
                   DESCRIPTION
                       "This is a software switch that functions much like
                       a hardware dip switch.  At the moment, the only use
                       of this switch is to define whether the unit will
                       act as the master clock for the sonet line.  The
                       bit values are defined as follows:

                          x x x x x x 1   -   assert master clock
                          x x x x x 1 x   -   not assigned
                          x x x x 1 x x   -   not assigned
                          x x x 1 x x x   -   not assigned
                          x x 1 x x x x   -   not assigned
                          x 1 x x x x x   -   not assigned
                          1 x x x x x x   -   not assigned"
               ::= { nscHippiSonetProfile 11 }

             END
