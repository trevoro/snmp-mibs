-- |**********************************************************************|
 -- | Copyright 1998 - Sonoma Systems, Inc. Marina del Rey, CA 90292       |
 -- |    Unpublished software - All rights reserved.                       |
 -- |                                                                      |
 -- | The information in this software is subject to change without notice |
 -- | and should not be construed as a commitment by Sonoma Systems, Inc.  |
 -- |                                                                      |
 -- | Sonoma Systems, Inc. assumes no responsibility for the use or        |
 -- | reliability of its software on equipment which is not supplied by    |
 -- | Sonoma Systems, Inc.                                                 |
 -- |                                                                      |
 -- | This software is furnished under a license and may be copied only    |
 -- | under the terms of that license and with the inclusion of this       |
 -- | notice. This software, or any other copies thereof, may not be       |
 -- | provided or otherwise made available to any other person except to   |
 -- | one who agrees to these license terms. Title to and ownership of the |
 -- | software shall at all times remain with Sonoma Systems, Inc.         |
 -- |**********************************************************************|
 --
 -- Sonoma Systems Inc.,
 -- 4640 Admiralty Way, Suite #600,
 -- Marina Del Rey,
 -- California 90292-6695.
 --
 -- Web : www.sonoma-systems.com
 -- Phone:  310.827.8000
 --
 -- NAME        : ds3mib.def
 --
 -- DESCRIPTION : This is the ATM MIB for the Sonoma DS3 interface.
 --
 -- ARCHIVE : $Archive:   M:\pvcs\pvcsproj\sonoma3\src\mib\ds3mib.dev  $
 -- REVISION: $Revision:   1.5  $
 -- AUTHOR  : $Author:   TMANCOUR  $
 -- DATE    : $Date:   Feb 08 1999 14:07:28  $


SONOMASYSTEMS-SONOMA-ATM-DS3-MIB DEFINITIONS ::= BEGIN

      IMPORTS
        Counter
        FROM RFC1155-SMI
        OBJECT-TYPE
        FROM RFC-1212
        sonomaATM
        FROM SONOMASYSTEMS-SONOMA-MIB;


    --  This MIB module uses the extended OBJECT-TYPE macro as
    --  defined in [14];
    --
    -- Hierarchy for these groups
    -- enterprises OBJECT IDENTIFIER ::= { private 4 }
    -- sonomaSystems OBJECT IDENTIFIER ::= {  enterprises 2926 }
    -- sonomaSeries OBJECT IDENTIFIER ::= { sonomaSystems 25 }
    -- sonomaATM OBJECT IDENTIFIER ::= { sonomaSeries 7 }
    sonomaDS3ATMAdapterGroup OBJECT IDENTIFIER ::= { sonomaATM 2 }
        

      --   Sonoma DS3 ATM Adapter Specific Group MIB groups
      atmDs3ConfGroup    OBJECT IDENTIFIER ::= { sonomaDS3ATMAdapterGroup 1 }
      atmDs3StatsGroup   OBJECT IDENTIFIER ::= { sonomaDS3ATMAdapterGroup 2 }

    -- Sonoma DS3 ATM Adapter Specific Group MIB groups

    -- This group contains all informat specificly for
    -- Sonoma Systems DS3 adapter. It includes the configuration and
    -- some statistics information

    --  atmDS3ConfGroup

    atmDs3ConfPhyTable  OBJECT-TYPE
        SYNTAX  SEQUENCE OF AtmDs3ConfPhyEntry
        ACCESS  not-accessible
        STATUS  mandatory
        DESCRIPTION
            "A table of physical layer configuration for the DS3
         interface"
        ::= { atmDs3ConfGroup 1 }

    atmDs3ConfPhyEntry  OBJECT-TYPE
        SYNTAX  AtmDs3ConfPhyEntry
        ACCESS  not-accessible
        STATUS  mandatory
        DESCRIPTION
          "A entry in the table, containing information about the
           physical layer of a DS3 interface"
        INDEX  { atmDs3ConfPhysIndex }
        ::= { atmDs3ConfPhyTable 1 }
    
    AtmDs3ConfPhyEntry ::= SEQUENCE {
      atmDs3ConfPhysIndex     INTEGER,
      atmDs3ConfFraming       INTEGER,
      atmDs3ConfInsGFCBits    INTEGER,
      atmDs3ConfSerBipolarIO  INTEGER,
      atmDs3ConfScramblePld   INTEGER,
      atmDs3ConfOverheadPLCP  INTEGER,
      atmDs3ConfGenerateFEBE  INTEGER,
      atmDs3ConfGenerateFEAC  INTEGER,
      atmDs3ConfLoopback      INTEGER,
      atmDs3ConfCableLength   INTEGER,
      atmDs3ConfInternalEqualizer   INTEGER,
      atmDs3ConfFillerCells   INTEGER,
      atmDs3ConfGenerateClock INTEGER
    }

    atmDs3ConfPhysIndex   OBJECT-TYPE
        SYNTAX  INTEGER
        ACCESS  read-only
        STATUS  mandatory
        DESCRIPTION
            "The physical interface index."
        ::= { atmDs3ConfPhyEntry 1 }   

    atmDs3ConfFraming OBJECT-TYPE
        SYNTAX  INTEGER { 
		framingDS3(1), 
		framingE3(2)
		}
        ACCESS  read-only
        STATUS  mandatory
        DESCRIPTION
            "DS3 or E3 framing selection."
        ::= { atmDs3ConfPhyEntry 2 }

    atmDs3ConfInsGFCBits   OBJECT-TYPE
	SYNTAX  INTEGER { 
		enabled (1), 
		disabled (2) 
		}
        ACCESS  read-write
        STATUS  mandatory
        DESCRIPTION
            "Enable/disable the insertion of GFC bits."
	    DEFVAL { disabled }
        ::= { atmDs3ConfPhyEntry 3 }

    atmDs3ConfSerBipolarIO OBJECT-TYPE
        SYNTAX  INTEGER { 
		enabled (1), 
		disabled (2) 
		}
        ACCESS  read-write
        STATUS  mandatory
        DESCRIPTION
            "Enable/disable bipolar serial I/O."
	    DEFVAL { enabled }
        ::= { atmDs3ConfPhyEntry 4 }

    atmDs3ConfScramblePld OBJECT-TYPE
        SYNTAX  INTEGER { 
		enabled (1), 
		disabled (2) 
		}
        ACCESS  read-write
        STATUS  mandatory
        DESCRIPTION
            "Enable/disable payload scrambling."
	    DEFVAL { enabled }
        ::= { atmDs3ConfPhyEntry 5 }

    atmDs3ConfOverheadPLCP    OBJECT-TYPE
        SYNTAX  INTEGER { 
		enabled (1), 
		disabled (2) 
		}
        ACCESS  read-write
        STATUS  mandatory
        DESCRIPTION
            "Enable/disable PLCP processing."
	    DEFVAL { enabled }
        ::= { atmDs3ConfPhyEntry 6 }

    atmDs3ConfGenerateFEBE    OBJECT-TYPE
        SYNTAX  INTEGER { 
		enabled (1), 
		disabled (2) 
		}
        ACCESS  read-write
        STATUS  mandatory
        DESCRIPTION
            "Enable/disable FEBE generation when F, M, or CP bit
             errors received."
	    DEFVAL { enabled }
        ::= { atmDs3ConfPhyEntry 7 }

    atmDs3ConfGenerateFEAC    OBJECT-TYPE
        SYNTAX  INTEGER { 
		enabled (1), 
		disabled (2) 
		}
        ACCESS  read-write
        STATUS  mandatory
        DESCRIPTION
            "Enable/disable FEAC generation and detection."
	    DEFVAL { disabled }
        ::= { atmDs3ConfPhyEntry 8 }

    atmDs3ConfLoopback     OBJECT-TYPE
        SYNTAX  INTEGER { 
		disabled(1), 
		internal(2), 
		external(3)
		}
        ACCESS  read-write
        STATUS  mandatory
        DESCRIPTION
            "Enable/disable internal loopback."
	    DEFVAL { disabled }
        ::= { atmDs3ConfPhyEntry 9 }

    atmDs3ConfCableLength OBJECT-TYPE
        SYNTAX  INTEGER { 
		notGreaterThan225Feet(1), 
		greaterThan225Feet(2) 
		}
        ACCESS  read-write
        STATUS  mandatory
        DESCRIPTION
            "Configure for the length of the cable."
	    DEFVAL { notGreaterThan225Feet }
        ::= { atmDs3ConfPhyEntry 10 }

    atmDs3ConfInternalEqualizer OBJECT-TYPE
        SYNTAX  INTEGER { 
		use(1), 
		bypass(2)
		}
        ACCESS  read-write
        STATUS  mandatory
        DESCRIPTION
            "Configure to use or bypass the internal equalizer."
	    DEFVAL { use }
        ::= { atmDs3ConfPhyEntry 11 }

    atmDs3ConfFillerCells OBJECT-TYPE
        SYNTAX  INTEGER {
                        unassigned(1), 
                        idle(2) 
                        }
        ACCESS  read-write
        STATUS  mandatory
        DESCRIPTION
            "This parameter indicates the type of filler cells to send
             when there are no data cells."
          DEFVAL { unassigned }
        ::= { atmDs3ConfPhyEntry 12 }

    atmDs3ConfGenerateClock OBJECT-TYPE
        SYNTAX  INTEGER { 
		enabled (1), 
		disabled (2) 
		}
        ACCESS  read-write
        STATUS  mandatory
        DESCRIPTION
            "Enable/disable clock generation."
	    DEFVAL { disabled }
        ::= { atmDs3ConfPhyEntry 13 }

    --  atmDS3StatsGroup

    atmDs3PhyStatsTable  OBJECT-TYPE
        SYNTAX  SEQUENCE OF AtmDs3PhyStatsEntry
        ACCESS  not-accessible
        STATUS  mandatory
        DESCRIPTION
            "A table of physical layer statistics information for the DS3
         interface"
        ::= { atmDs3StatsGroup 1 }

    atmDs3PhyStatsEntry  OBJECT-TYPE
        SYNTAX  AtmDs3PhyStatsEntry
        ACCESS  not-accessible
        STATUS  mandatory
        DESCRIPTION
          "A entry in the table, containing information about the
           physical layer of a DS3 interface"
        INDEX  { atmDs3PhyStatsPhysIndex }
        ::= { atmDs3PhyStatsTable 1 }
    
    AtmDs3PhyStatsEntry ::= SEQUENCE {
      atmDs3PhyStatsPhysIndex   INTEGER,
      atmDs3StatsNoSignals      Counter,
      atmDs3StatsNoDs3Frames    Counter,
      atmDs3StatsAisDetects     Counter,
      atmDs3StatsAlarms         Counter,
      atmDs3StatsFrameErrs      Counter,
      atmDs3StatsParityErrs     Counter,
      atmDs3StatsCpErrs         Counter,
      atmDs3StatsFeBlockErrs    Counter,
      atmDs3StatsBpvErrs        Counter,
      atmDs3StatsRemoteAlarms   Counter,
      atmDs3StatsOutOfCell      INTEGER,
      atmDs3StatsFifoOverflow   INTEGER,
      atmDs3StatsRemoteAlarmInd INTEGER,
      atmDs3StatsSignalLoss     INTEGER,
      atmDs3StatsFrameLoss      INTEGER,
      atmDs3StatsSyncLoss       INTEGER,
      atmDs3StatsPlcpAlarmState INTEGER,
      atmDs3StatsAisState       INTEGER,
      atmDs3StatsClearCounters  INTEGER
    }

    atmDs3PhyStatsPhysIndex  OBJECT-TYPE
        SYNTAX  INTEGER
        ACCESS  read-only
        STATUS  mandatory
        DESCRIPTION
            "The physical interface index."
        ::= { atmDs3PhyStatsEntry 1 }  

    atmDs3StatsAlarms  OBJECT-TYPE
        SYNTAX  Counter
        ACCESS  read-only
        STATUS  mandatory
        DESCRIPTION
            "Test the PLCP alarm counter"
        ::= { atmDs3PhyStatsEntry 2 }

    atmDs3StatsNoSignals  OBJECT-TYPE
        SYNTAX  Counter
        ACCESS  read-only
        STATUS  mandatory
        DESCRIPTION
            "No signal error counter."
        ::= { atmDs3PhyStatsEntry 3 }

    atmDs3StatsNoDs3Frames  OBJECT-TYPE
        SYNTAX  Counter
        ACCESS  read-only
        STATUS  mandatory
        DESCRIPTION
            "No DS-3 frame error counter."
        ::= { atmDs3PhyStatsEntry 4 }

    atmDs3StatsAisDetects  OBJECT-TYPE
        SYNTAX  Counter
        ACCESS  read-only
        STATUS  mandatory
        DESCRIPTION
            "AIS detect counter."
        ::= { atmDs3PhyStatsEntry 5 }

    atmDs3StatsFrameErrs  OBJECT-TYPE
        SYNTAX  Counter
        ACCESS  read-only
        STATUS  mandatory
        DESCRIPTION
            "Frame error counter."
        ::= { atmDs3PhyStatsEntry 6 }

    atmDs3StatsParityErrs  OBJECT-TYPE
        SYNTAX  Counter
        ACCESS  read-only
        STATUS  mandatory
        DESCRIPTION
            "Parity error counter."
        ::= { atmDs3PhyStatsEntry 7 }

    atmDs3StatsCpErrs  OBJECT-TYPE
        SYNTAX  Counter
        ACCESS  read-only
        STATUS  mandatory
        DESCRIPTION
            "CP error counter."
        ::= { atmDs3PhyStatsEntry 8 }

    atmDs3StatsFeBlockErrs  OBJECT-TYPE
        SYNTAX  Counter
        ACCESS  read-only
        STATUS  mandatory
        DESCRIPTION
            "Far End Block error counter."
        ::= { atmDs3PhyStatsEntry 9 }

    atmDs3StatsBpvErrs  OBJECT-TYPE
        SYNTAX  Counter
        ACCESS  read-only
        STATUS  mandatory
        DESCRIPTION
            "Bipolar Violation error counter."
        ::= { atmDs3PhyStatsEntry 10 }

    atmDs3StatsRemoteAlarms  OBJECT-TYPE
        SYNTAX  Counter
        ACCESS  read-only
        STATUS  mandatory
        DESCRIPTION
            "Bipolar Violation error counter."
        ::= { atmDs3PhyStatsEntry 11 }

    atmDs3StatsSignalLoss  OBJECT-TYPE
        SYNTAX  INTEGER { 
		true (1), 
		false (2)
		}
        ACCESS  read-only
        STATUS  mandatory
        DESCRIPTION
            "Signal loss indication."
        ::= { atmDs3PhyStatsEntry 12 }

    atmDs3StatsOutOfCell  OBJECT-TYPE
        SYNTAX  INTEGER { 
		true (1), 
		false (2)
		}
        ACCESS  read-only
        STATUS  mandatory
        DESCRIPTION
            "ATM out-of-cell delineation."
        ::= { atmDs3PhyStatsEntry 13 }

    atmDs3StatsFifoOverflow  OBJECT-TYPE
        SYNTAX  INTEGER { 
		true (1), 
		false (2)
		}
        ACCESS  read-only
        STATUS  mandatory
        DESCRIPTION
            "ATM FIFO overflow."
        ::= { atmDs3PhyStatsEntry 14 }

    atmDs3StatsRemoteAlarmInd  OBJECT-TYPE
        SYNTAX  INTEGER { 
		true (1), 
		false (2)
		}
        ACCESS  read-only
        STATUS  mandatory
        DESCRIPTION
            "Remote alarm indication."
        ::= { atmDs3PhyStatsEntry 15 }

    atmDs3StatsFrameLoss  OBJECT-TYPE
        SYNTAX  INTEGER { 
		true (1), 
		false (2)
		}
        ACCESS  read-only
        STATUS  mandatory
        DESCRIPTION
            "Frame loss indication."
        ::= { atmDs3PhyStatsEntry 16 }

    atmDs3StatsSyncLoss  OBJECT-TYPE
        SYNTAX  INTEGER { 
		true (1), 
		false (2)
		}
        ACCESS  read-only
        STATUS  mandatory
        DESCRIPTION
            "Synchronization loss counter."
        ::= { atmDs3PhyStatsEntry 17 }

    atmDs3StatsPlcpAlarmState   OBJECT-TYPE
        SYNTAX  INTEGER { 
		true (1), 
		false (2)
		}
        ACCESS  read-only
        STATUS  mandatory
        DESCRIPTION
            "Test the PLCP alarm state."
        ::= { atmDs3PhyStatsEntry 18 }

    atmDs3StatsAisState OBJECT-TYPE
        SYNTAX  INTEGER { 
		true (1), 
		false (2)
		}
        ACCESS  read-only
        STATUS  mandatory
        DESCRIPTION
            "AIS detect LED state."
        ::= { atmDs3PhyStatsEntry 19 }

    atmDs3StatsClearCounters  OBJECT-TYPE
        SYNTAX  INTEGER { 
		true (1), 
		false (2)
		}
        ACCESS  read-write
        STATUS  mandatory
        DESCRIPTION
            "Clear all counters in this group ONLY."
	    DEFVAL { false }
        ::= { atmDs3PhyStatsEntry 20 }

END
