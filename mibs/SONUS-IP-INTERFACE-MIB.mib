--
-- This SMIv2 module has been generated by smidump 0.2-cvs. Do not edit.
--

SONUS-IP-INTERFACE-MIB DEFINITIONS ::= BEGIN

IMPORTS
    IANAifType
        FROM IANAifType-MIB
    Integer32, IpAddress, MODULE-IDENTITY, NOTIFICATION-TYPE, 
    OBJECT-TYPE
        FROM SNMPv2-SMI
    RowStatus
        FROM SNMPv2-TC
    sonusEventClass, sonusEventDescription, sonusEventLevel, 
    sonusShelfIndex, sonusSlotIndex
        FROM SONUS-COMMON-MIB
    sonusPacketMIBs
        FROM SONUS-SMI
    SonusName
        FROM SONUS-TC;

sonusIpInterfaceMIB MODULE-IDENTITY
    LAST-UPDATED    "200107310000Z"
    ORGANIZATION    
            "Sonus Networks, Inc."
    CONTACT-INFO    
            "   Customer Support    
             Sonus Networks, Inc,
             5 carlisle Road
             Westford, MA 01886
             USA
             
             Tel: 978-692-8999
             Fax: 978-392-9118
             E-mail: cs.snmp@sonusnet.com"
    DESCRIPTION     
            "The MIB Module for IP Interface Management."
    ::= { sonusPacketMIBs 1 }


sonusIpInterfaceMIBObjects OBJECT IDENTIFIER
    ::= { sonusIpInterfaceMIB 1 }

sonusNrsConfigObjects OBJECT IDENTIFIER
    ::= { sonusIpInterfaceMIBObjects 1 }

sonusNrsVirtExtRouterEnable OBJECT-TYPE
    SYNTAX          INTEGER { disabled(1), enabled(2) }
    MAX-ACCESS      read-write
    STATUS          current
    DESCRIPTION     
            "The Virtual External Router administrative status.
             The value 'enabled' denotes that Gateway IP addresses
             will be advertised with one associated with each
             active PNS link and that learned routes will not be
             readvertised (to prevent routes through us).  The
             value 'disabled' denotes that routing will operate
             as usual."
    DEFVAL          { disabled }
    ::= { sonusNrsConfigObjects 1 }

sonusNif OBJECT IDENTIFIER
    ::= { sonusIpInterfaceMIBObjects 3 }

sonusNifNextIndex OBJECT-TYPE
    SYNTAX          Integer32
    MAX-ACCESS      read-only
    STATUS          current
    DESCRIPTION     
            "The next valid index to use when creating an entry in
             the sonusNifTable."
    ::= { sonusNif 1 }

sonusNifTable OBJECT-TYPE
    SYNTAX          SEQUENCE OF SonusNifEntry
    MAX-ACCESS      not-accessible
    STATUS          current
    DESCRIPTION     
            "The collection of Interface information for the
             specified instance."
    ::= { sonusNif 2 }

sonusNifEntry OBJECT-TYPE
    SYNTAX          SonusNifEntry
    MAX-ACCESS      not-accessible
    STATUS          current
    DESCRIPTION     
            "The collection of Interface information for the
             specified instance."
    INDEX           { sonusNifIndex }
    ::= { sonusNifTable 1 }

SonusNifEntry ::=
    SEQUENCE {
        sonusNifIndex                   Integer32,
        sonusNifName                    SonusName,
        sonusNifType                    IANAifType,
        sonusNifIpAddress               IpAddress,
        sonusNifIpMask                  IpAddress,
        sonusNifMtu                     Integer32,
        sonusNifShelf                   Integer32,
        sonusNifSlot                    Integer32,
        sonusNifPort                    Integer32,
        sonusNifCircuit                 Integer32,
        sonusNifNextHopAddr             IpAddress,
        sonusNifMode                    INTEGER,
        sonusNifAction                  INTEGER,
        sonusNifTimeout                 Integer32,
        sonusNifState                   INTEGER,
        sonusNifOutOfServiceReason      INTEGER,
        sonusNifClass                   INTEGER,
        sonusNifRowStatus               RowStatus,
        sonusNifBwDeviation             Integer32,
        sonusNifBwContingency           Integer32
    }

sonusNifIndex OBJECT-TYPE
    SYNTAX          Integer32
    MAX-ACCESS      read-only
    STATUS          current
    DESCRIPTION     
            "The ifIndex assigned to this NIF when it was created.
             This will not change until the NIF is deleted."
    ::= { sonusNifEntry 1 }

sonusNifName OBJECT-TYPE
    SYNTAX          SonusName
    MAX-ACCESS      read-write
    STATUS          current
    DESCRIPTION     
            "The administrative name of the NIF."
    ::= { sonusNifEntry 2 }

sonusNifType OBJECT-TYPE
    SYNTAX          IANAifType
    MAX-ACCESS      read-write
    STATUS          current
    DESCRIPTION     
            "The type of interface, distinguished according to the
             physical/link protocol(s) immediately 'below' the network
             layer in the protocol stack.
             
             Values are from the IANAifType TC."
    DEFVAL          { 6 }
    ::= { sonusNifEntry 3 }

sonusNifIpAddress OBJECT-TYPE
    SYNTAX          IpAddress
    MAX-ACCESS      read-write
    STATUS          current
    DESCRIPTION     
            "The IP Address of the Interface"
    ::= { sonusNifEntry 4 }

sonusNifIpMask OBJECT-TYPE
    SYNTAX          IpAddress
    MAX-ACCESS      read-write
    STATUS          current
    DESCRIPTION     
            "The IP subnet mask of this Interface."
    ::= { sonusNifEntry 5 }

sonusNifMtu OBJECT-TYPE
    SYNTAX          Integer32 (576..1500)
    MAX-ACCESS      read-only
    STATUS          current
    DESCRIPTION     
            "The size of the largest datagram that can be sent/received
             on the interface, specified in octets."
    ::= { sonusNifEntry 6 }

sonusNifShelf OBJECT-TYPE
    SYNTAX          Integer32 (1..6)
    MAX-ACCESS      read-write
    STATUS          current
    DESCRIPTION     
            "A 32-bit integer identifying the shelf of the
             Interface"
    ::= { sonusNifEntry 7 }

sonusNifSlot OBJECT-TYPE
    SYNTAX          Integer32 (1..16)
    MAX-ACCESS      read-write
    STATUS          current
    DESCRIPTION     
            "A 32-bit integer identifying the slot of the
             Interface"
    ::= { sonusNifEntry 8 }

sonusNifPort OBJECT-TYPE
    SYNTAX          Integer32 (1..4)
    MAX-ACCESS      read-write
    STATUS          current
    DESCRIPTION     
            "A 32-bit integer identifying the port of the
             Interface."
    ::= { sonusNifEntry 9 }

sonusNifCircuit OBJECT-TYPE
    SYNTAX          Integer32
    MAX-ACCESS      read-only
    STATUS          current
    DESCRIPTION     
            "A 32-bit integer identifying the circuit of the
             Interface.  For current hardware this must be 1."
    DEFVAL          { 1 }
    ::= { sonusNifEntry 10 }

sonusNifNextHopAddr OBJECT-TYPE
    SYNTAX          IpAddress
    MAX-ACCESS      read-write
    STATUS          current
    DESCRIPTION     
            "The next hop address to use for all traffic out this NIF."
    ::= { sonusNifEntry 11 }

sonusNifMode OBJECT-TYPE
    SYNTAX          INTEGER { outOfService(1), inService(2) }
    MAX-ACCESS      read-write
    STATUS          current
    DESCRIPTION     
            "The operation mode for NIF."
    DEFVAL          { inService }
    ::= { sonusNifEntry 12 }

sonusNifAction OBJECT-TYPE
    SYNTAX          INTEGER { dryUp(1), force(2) }
    MAX-ACCESS      read-write
    STATUS          current
    DESCRIPTION     
            "The dryup option for NIF."
    DEFVAL          { dryUp }
    ::= { sonusNifEntry 13 }

sonusNifTimeout OBJECT-TYPE
    SYNTAX          Integer32 (1..1440)
    MAX-ACCESS      read-write
    STATUS          current
    DESCRIPTION     
            "The dryup timeout in minute. The default is one hour "
    DEFVAL          { 60 }
    ::= { sonusNifEntry 14 }

sonusNifState OBJECT-TYPE
    SYNTAX          INTEGER { disabled(1), enabled(2) }
    MAX-ACCESS      read-write
    STATUS          current
    DESCRIPTION     
            "Administrative state of the interface.
             
             Changes may only be made while disabled and will only
             take effect when enabled next."
    ::= { sonusNifEntry 15 }

sonusNifOutOfServiceReason OBJECT-TYPE
    SYNTAX          INTEGER { notApplicable(1), admin(2), gateway(3), 
                        portDown(4), serverDown(5), vcsDown(6), noVc(7), 
                        srvrAbsent(8), linkDown(9) }
    MAX-ACCESS      read-only
    STATUS          current
    DESCRIPTION     
            "The reason of NIF being out of service. The NIF could be out of service due to one 
             of the following reasons: operator initiated command, gateway not responding to 
             arp request, port failure/outOfService, or server failure/outOfService. The 
             		 notApplicable is set when the NIF is inService or dryUp state"
    ::= { sonusNifEntry 16 }

sonusNifClass OBJECT-TYPE
    SYNTAX          INTEGER { general(1), reserved(2) }
    MAX-ACCESS      read-write
    STATUS          current
    DESCRIPTION     
            "This object indicates whether a NIF is reserved or general(not reserved). The resources
             of a general NIF are used by marlin common IP calls whereas the resources of a reserved 
             NIF are used only by MGCP IP calls"
    DEFVAL          { general }
    ::= { sonusNifEntry 17 }

sonusNifRowStatus OBJECT-TYPE
    SYNTAX          RowStatus
    MAX-ACCESS      read-write
    STATUS          current
    DESCRIPTION     
            ""
    ::= { sonusNifEntry 18 }

sonusNifBwDeviation OBJECT-TYPE
    SYNTAX          Integer32 (0..100)
    MAX-ACCESS      read-write
    STATUS          current
    DESCRIPTION     
            "The deviation between actual and expected NIF bandwidth in percentage of the 
             overall NIF bandwidth. If actual bandwidth is greater than the expected 
             bandwdith plus deviation amount, a trap will be set and the trap will be 
             only cleared when the actual bandwidth dropped below the expected bandwidth.
             If the actual bandwidth is lower than the expected badniwdth minus 2 times
             of deviation amount, a different trap will be set and the trap will be
             cleared when the actual bandwdith reaches the expected bandwidth. "
    DEFVAL          { 0 }
    ::= { sonusNifEntry 19 }

sonusNifBwContingency OBJECT-TYPE
    SYNTAX          Integer32 (0..100)
    MAX-ACCESS      read-write
    STATUS          current
    DESCRIPTION     
            "The percentage of the overall NIF bandwidth is reserved for contigency. If actual 
             bandwidth is greater than the expected bandwdith and less than the overall NIF
             bandwidth minus contingency amount, calls will still be accepted. "
    DEFVAL          { 0 }
    ::= { sonusNifEntry 20 }

sonusNifAdmnTable OBJECT-TYPE
    SYNTAX          SEQUENCE OF SonusNifAdmnEntry
    MAX-ACCESS      not-accessible
    STATUS          current
    DESCRIPTION     
            "The collection of Interface information for the
             specified instance."
    ::= { sonusIpInterfaceMIBObjects 6 }

sonusNifAdmnEntry OBJECT-TYPE
    SYNTAX          SonusNifAdmnEntry
    MAX-ACCESS      not-accessible
    STATUS          current
    DESCRIPTION     
            "The collection of Interface information for the specified instance."
    INDEX           { sonusNifAdmnShelf, sonusNifAdmnSlot, 
                      sonusNifAdmnPort, sonusNifAdmnIndex }
    ::= { sonusNifAdmnTable 1 }

SonusNifAdmnEntry ::=
    SEQUENCE {
        sonusNifAdmnShelf               Integer32,
        sonusNifAdmnSlot                Integer32,
        sonusNifAdmnPort                Integer32,
        sonusNifAdmnIndex               Integer32
    }

sonusNifAdmnShelf OBJECT-TYPE
    SYNTAX          Integer32
    MAX-ACCESS      read-only
    STATUS          current
    DESCRIPTION     
            "A 32-bit integer identifying the shelf of the Interface"
    ::= { sonusNifAdmnEntry 1 }

sonusNifAdmnSlot OBJECT-TYPE
    SYNTAX          Integer32
    MAX-ACCESS      read-only
    STATUS          current
    DESCRIPTION     
            "A 32-bit integer identifying the slot of the Interface"
    ::= { sonusNifAdmnEntry 2 }

sonusNifAdmnPort OBJECT-TYPE
    SYNTAX          Integer32
    MAX-ACCESS      read-only
    STATUS          current
    DESCRIPTION     
            "A 32-bit integer identifying the port of the Interface."
    ::= { sonusNifAdmnEntry 3 }

sonusNifAdmnIndex OBJECT-TYPE
    SYNTAX          Integer32
    MAX-ACCESS      read-only
    STATUS          current
    DESCRIPTION     
            "The ifIndex assigned to this NIF when it was created.
             This will not change until the NIF is deleted."
    ::= { sonusNifAdmnEntry 4 }

sonusNrsMgmtIfTable OBJECT-TYPE
    SYNTAX          SEQUENCE OF SonusNrsMgmtIfEntry
    MAX-ACCESS      not-accessible
    STATUS          current
    DESCRIPTION     
            "The collection of Management Interface information for the
             specified instance."
    ::= { sonusIpInterfaceMIBObjects 7 }

sonusNrsMgmtIfEntry OBJECT-TYPE
    SYNTAX          SonusNrsMgmtIfEntry
    MAX-ACCESS      not-accessible
    STATUS          current
    DESCRIPTION     
            "The collection of Management Interface information for the
             specified instance."
    INDEX           { sonusNrsMgmtIfShelf, sonusNrsMgmtIfSlot, 
                      sonusNrsMgmtIfPort, sonusNrsMgmtIfCircuit }
    ::= { sonusNrsMgmtIfTable 1 }

SonusNrsMgmtIfEntry ::=
    SEQUENCE {
        sonusNrsMgmtIfIndex             Integer32,
        sonusNrsMgmtIfShelf             Integer32,
        sonusNrsMgmtIfSlot              Integer32,
        sonusNrsMgmtIfPort              Integer32,
        sonusNrsMgmtIfCircuit           Integer32,
        sonusNrsMgmtIfType              IANAifType,
        sonusNrsMgmtIfIpAddress         IpAddress,
        sonusNrsMgmtIfIpMask            IpAddress,
        sonusNrsMgmtIfMtu               Integer32,
        sonusNrsMgmtIfGatewayAddress    IpAddress,
        sonusNrsMgmtIfMode              INTEGER,
        sonusNrsMgmtIfAdminStatus       INTEGER,
        sonusNrsMgmtIfOperStatus        INTEGER,
        sonusNrsMgmtIfLogicMgmtIpAddress IpAddress
    }

sonusNrsMgmtIfIndex OBJECT-TYPE
    SYNTAX          Integer32
    MAX-ACCESS      read-only
    STATUS          current
    DESCRIPTION     
            "The ifIndex assigned to this management NIF when it was created.
             This will not change until the NIF is deleted."
    ::= { sonusNrsMgmtIfEntry 1 }

sonusNrsMgmtIfShelf OBJECT-TYPE
    SYNTAX          Integer32
    MAX-ACCESS      read-write
    STATUS          current
    DESCRIPTION     
            "A 32-bit integer identifying the shelf of the Management
             Interface"
    ::= { sonusNrsMgmtIfEntry 2 }

sonusNrsMgmtIfSlot OBJECT-TYPE
    SYNTAX          Integer32
    MAX-ACCESS      read-write
    STATUS          current
    DESCRIPTION     
            "A 32-bit integer identifying the slot of the Management
             Interface"
    ::= { sonusNrsMgmtIfEntry 3 }

sonusNrsMgmtIfPort OBJECT-TYPE
    SYNTAX          Integer32
    MAX-ACCESS      read-write
    STATUS          current
    DESCRIPTION     
            "A 32-bit integer identifying the port of the Management
             Interface.  For current hardware this must be 1 or 2."
    ::= { sonusNrsMgmtIfEntry 4 }

sonusNrsMgmtIfCircuit OBJECT-TYPE
    SYNTAX          Integer32
    MAX-ACCESS      read-only
    STATUS          current
    DESCRIPTION     
            "A 32-bit integer identifying the circuit of the Management
             Interface.  For current hardware this must be 1."
    ::= { sonusNrsMgmtIfEntry 5 }

sonusNrsMgmtIfType OBJECT-TYPE
    SYNTAX          IANAifType
    MAX-ACCESS      read-only
    STATUS          current
    DESCRIPTION     
            "The type of interface, distinguished according to the
             physical/link protocol(s) immediately 'below' the network
             layer in the protocol stack.
             
             Values are from RFC1213 for the ifType object.
             
             Current hardware supports only the ethernet-csmacd (6)
             type."
    ::= { sonusNrsMgmtIfEntry 6 }

sonusNrsMgmtIfIpAddress OBJECT-TYPE
    SYNTAX          IpAddress
    MAX-ACCESS      read-write
    STATUS          current
    DESCRIPTION     
            "The IP Address of the Management Interface"
    ::= { sonusNrsMgmtIfEntry 7 }

sonusNrsMgmtIfIpMask OBJECT-TYPE
    SYNTAX          IpAddress
    MAX-ACCESS      read-write
    STATUS          current
    DESCRIPTION     
            "The IP subnet mask of this Management Interface."
    ::= { sonusNrsMgmtIfEntry 8 }

sonusNrsMgmtIfMtu OBJECT-TYPE
    SYNTAX          Integer32
    MAX-ACCESS      read-write
    STATUS          current
    DESCRIPTION     
            "The size of the largest datagram that can be sent/received
             on the interface, specified in octets."
    ::= { sonusNrsMgmtIfEntry 9 }

sonusNrsMgmtIfGatewayAddress OBJECT-TYPE
    SYNTAX          IpAddress
    MAX-ACCESS      read-write
    STATUS          current
    DESCRIPTION     
            "The IP address of the default gateway for this Management
             Interface."
    ::= { sonusNrsMgmtIfEntry 10 }

sonusNrsMgmtIfMode OBJECT-TYPE
    SYNTAX          INTEGER { standby(1), active(2) }
    MAX-ACCESS      read-write
    STATUS          current
    DESCRIPTION     
            "The requested mode of the interface."
    DEFVAL          { active }
    ::= { sonusNrsMgmtIfEntry 11 }

sonusNrsMgmtIfAdminStatus OBJECT-TYPE
    SYNTAX          INTEGER { disabled(1), enabled(2) }
    MAX-ACCESS      read-write
    STATUS          current
    DESCRIPTION     
            "The requested status of the interface."
    ::= { sonusNrsMgmtIfEntry 12 }

sonusNrsMgmtIfOperStatus OBJECT-TYPE
    SYNTAX          INTEGER { outOfService(1), inService(2), 
                        outOfServiceDisabled(3), outOfServiceLinkDown(4) }
    MAX-ACCESS      read-only
    STATUS          current
    DESCRIPTION     
            "The actual status of the management interface.  A link will
             be InService if the sonusNrsMgmtIfAdminStatus is enabled and
             the physical link is up.  It will be OutOfService if the admin
             status is enabled but the physical link is down.  It will be
             OutOfServiceDisabled if the physical link is up but the admin
             status is disabled.  It will be OutOfServiceLinkDown if the
             physical link is down and the admin status is disabled."
    ::= { sonusNrsMgmtIfEntry 13 }

sonusNrsMgmtIfLogicMgmtIpAddress OBJECT-TYPE
    SYNTAX          IpAddress
    MAX-ACCESS      read-only
    STATUS          current
    DESCRIPTION     
            "The logical Mgmt IP address assigned to the mgmt interface if
             this mgmt interface is active and in service."
    ::= { sonusNrsMgmtIfEntry 14 }

sonusNrsLogicMgmtIfAdmnTable OBJECT-TYPE
    SYNTAX          SEQUENCE OF SonusNrsLogicMgmtIfAdmnEntry
    MAX-ACCESS      not-accessible
    STATUS          current
    DESCRIPTION     
            "The collection of logical IP addresses for the node"
    ::= { sonusIpInterfaceMIBObjects 8 }

sonusNrsLogicMgmtIfAdmnEntry OBJECT-TYPE
    SYNTAX          SonusNrsLogicMgmtIfAdmnEntry
    MAX-ACCESS      not-accessible
    STATUS          current
    DESCRIPTION     
            "The collection of logical IP addresses for the node"
    INDEX           { sonusNrsLogicMgmtIfAdmnShelf }
    ::= { sonusNrsLogicMgmtIfAdmnTable 1 }

SonusNrsLogicMgmtIfAdmnEntry ::=
    SEQUENCE {
        sonusNrsLogicMgmtIfAdmnShelf    Integer32,
        sonusNrsLogicMgmtIfAdmnIpAddress IpAddress,
        sonusNrsLogicMgmtIfAdmnIpAddressB IpAddress
    }

sonusNrsLogicMgmtIfAdmnShelf OBJECT-TYPE
    SYNTAX          Integer32 (1..6)
    MAX-ACCESS      read-write
    STATUS          current
    DESCRIPTION     
            "A 32-bit integer identifying the shelf of the logical ip address assigned to"
    ::= { sonusNrsLogicMgmtIfAdmnEntry 1 }

sonusNrsLogicMgmtIfAdmnIpAddress OBJECT-TYPE
    SYNTAX          IpAddress
    MAX-ACCESS      read-write
    STATUS          current
    DESCRIPTION     
            "The Logical IP address of the shelf"
    ::= { sonusNrsLogicMgmtIfAdmnEntry 2 }

sonusNrsLogicMgmtIfAdmnIpAddressB OBJECT-TYPE
    SYNTAX          IpAddress
    MAX-ACCESS      read-write
    STATUS          current
    DESCRIPTION     
            "The second logical IP address for the shelf if the MNS ports are on the
             different subnet."
    ::= { sonusNrsLogicMgmtIfAdmnEntry 3 }

sonusNrsLinkFailureParamAdmnTable OBJECT-TYPE
    SYNTAX          SEQUENCE OF SonusNrsLinkFailureParamAdmnEntry
    MAX-ACCESS      not-accessible
    STATUS          current
    DESCRIPTION     
            "The table of user configured parameters for link failure detection"
    ::= { sonusIpInterfaceMIBObjects 9 }

sonusNrsLinkFailureParamAdmnEntry OBJECT-TYPE
    SYNTAX          SonusNrsLinkFailureParamAdmnEntry
    MAX-ACCESS      not-accessible
    STATUS          current
    DESCRIPTION     
            "One set of parameters configured for a server"
    INDEX           { sonusNrsLinkFailureParamAdmnShelf, 
                      sonusNrsLinkFailureParamAdmnSlot }
    ::= { sonusNrsLinkFailureParamAdmnTable 1 }

SonusNrsLinkFailureParamAdmnEntry ::=
    SEQUENCE {
        sonusNrsLinkFailureParamAdmnShelf Integer32,
        sonusNrsLinkFailureParamAdmnSlot Integer32,
        sonusNrsLinkFailureParamAdmnThreshold     Integer32,
        sonusNrsLinkFailureParamAdmnRetries   Integer32,
        sonusNrsLinkFailureParamAdmnVerifyTimer       Integer32,
        sonusNrsLinkFailureParamAdmnReattemptTimer          Integer32,
        sonusNrsLinkFailureParamAdmnState INTEGER
    }

sonusNrsLinkFailureParamAdmnShelf OBJECT-TYPE
    SYNTAX          Integer32 (1..6)
    MAX-ACCESS      read-write
    STATUS          current
    DESCRIPTION     
            "The shelf index of the server"
    ::= { sonusNrsLinkFailureParamAdmnEntry 1 }

sonusNrsLinkFailureParamAdmnSlot OBJECT-TYPE
    SYNTAX          Integer32 (1..16)
    MAX-ACCESS      read-write
    STATUS          current
    DESCRIPTION     
            "The slot index of the server"
    ::= { sonusNrsLinkFailureParamAdmnEntry 2 }

sonusNrsLinkFailureParamAdmnThreshold OBJECT-TYPE
    SYNTAX          Integer32 (0..100)
    MAX-ACCESS      read-write
    STATUS          current
    DESCRIPTION     
            "The number of failed port accepted before failing over the server.
             0 Threshold means the link/port failure will not trigger failover."
    ::= { sonusNrsLinkFailureParamAdmnEntry 3 }

sonusNrsLinkFailureParamAdmnRetries OBJECT-TYPE
    SYNTAX          Integer32 (0..10)
    MAX-ACCESS      read-write
    STATUS          current
    DESCRIPTION     
            "The number of retries before declare the link failure"
    DEFVAL          { 2 }
    ::= { sonusNrsLinkFailureParamAdmnEntry 4 }

sonusNrsLinkFailureParamAdmnVerifyTimer OBJECT-TYPE
    SYNTAX          Integer32 (0..60000)
    MAX-ACCESS      read-write
    STATUS          current
    DESCRIPTION     
            "The verify timer in ms unit defined when link is up"
    DEFVAL          { 500 }
    ::= { sonusNrsLinkFailureParamAdmnEntry 5 }

sonusNrsLinkFailureParamAdmnReattemptTimer OBJECT-TYPE
    SYNTAX          Integer32 (0..60000)
    MAX-ACCESS      read-write
    STATUS          current
    DESCRIPTION     
            "The re-attempt timer in ms unit defined between retires"
    DEFVAL          { 250 }
    ::= { sonusNrsLinkFailureParamAdmnEntry 6 }

sonusNrsLinkFailureParamAdmnState OBJECT-TYPE
    SYNTAX          INTEGER { disabled(1), enabled(2) }
    MAX-ACCESS      read-write
    STATUS          current
    DESCRIPTION     
            "The administrative state of turning on/off link failure detection."
    DEFVAL          { disabled }
    ::= { sonusNrsLinkFailureParamAdmnEntry 7 }

sonusNrsLinkFailureStatTable OBJECT-TYPE
    SYNTAX          SEQUENCE OF SonusNrsLinkFailureStatEntry
    MAX-ACCESS      not-accessible
    STATUS          current
    DESCRIPTION     
            "statistics for link failure detection"
    ::= { sonusIpInterfaceMIBObjects 10 }

sonusNrsLinkFailureStatEntry OBJECT-TYPE
    SYNTAX          SonusNrsLinkFailureStatEntry
    MAX-ACCESS      not-accessible
    STATUS          current
    DESCRIPTION     
            ""
    INDEX           { sonusNrsLinkFailureStatShelf, 
                      sonusNrsLinkFailureStatSlot }
    ::= { sonusNrsLinkFailureStatTable 1 }

SonusNrsLinkFailureStatEntry ::=
    SEQUENCE {
        sonusNrsLinkFailureStatShelf    Integer32,
        sonusNrsLinkFailureStatSlot     Integer32,
        sonusNrsLinkFailureStatFailures Integer32,
        sonusNrsLinkFailureStatRedundFailures     Integer32
    }

sonusNrsLinkFailureStatShelf OBJECT-TYPE
    SYNTAX          Integer32
    MAX-ACCESS      read-only
    STATUS          current
    DESCRIPTION     
            "shelf index for target server"
    ::= { sonusNrsLinkFailureStatEntry 1 }

sonusNrsLinkFailureStatSlot OBJECT-TYPE
    SYNTAX          Integer32
    MAX-ACCESS      read-only
    STATUS          current
    DESCRIPTION     
            "slot index for target server"
    ::= { sonusNrsLinkFailureStatEntry 2 }

sonusNrsLinkFailureStatFailures OBJECT-TYPE
    SYNTAX          Integer32
    MAX-ACCESS      read-only
    STATUS          current
    DESCRIPTION     
            "number of failures detected on this server"
    ::= { sonusNrsLinkFailureStatEntry 3 }

sonusNrsLinkFailureStatRedundFailures OBJECT-TYPE
    SYNTAX          Integer32
    MAX-ACCESS      read-only
    STATUS          current
    DESCRIPTION     
            "number of failures detected on the redundant server"
    ::= { sonusNrsLinkFailureStatEntry 4 }

sonusNrsPerDestLinkFailureStatTable OBJECT-TYPE
    SYNTAX          SEQUENCE OF SonusNrsPerDestLinkFailureStatEntry
    MAX-ACCESS      not-accessible
    STATUS          current
    DESCRIPTION     
            "statistics for link failure detected per destination"
    ::= { sonusIpInterfaceMIBObjects 11 }

sonusNrsPerDestLinkFailureStatEntry OBJECT-TYPE
    SYNTAX          SonusNrsPerDestLinkFailureStatEntry
    MAX-ACCESS      not-accessible
    STATUS          current
    DESCRIPTION     
            ""
    INDEX           { sonusNrsPerDestLinkFailureStatIfIndex, 
                      sonusNrsPerDestLinkFailureStatIpAddress }
    ::= { sonusNrsPerDestLinkFailureStatTable 1 }

SonusNrsPerDestLinkFailureStatEntry ::=
    SEQUENCE {
        sonusNrsPerDestLinkFailureStatIfIndex     Integer32,
        sonusNrsPerDestLinkFailureStatIpAddress       IpAddress,
        sonusNrsPerDestLinkFailureStatMinTime     Integer32,
        sonusNrsPerDestLinkFailureStatMaxTime     Integer32,
        sonusNrsPerDestLinkFailureStatAverageTime         Integer32,
        sonusNrsPerDestLinkFailureStatSumTime     Integer32,
        sonusNrsPerDestLinkFailureStat1Failure      Integer32,
        sonusNrsPerDestLinkFailureStat2Failure      Integer32,
        sonusNrsPerDestLinkFailureStatFailures      Integer32,
        sonusNrsPerDestLinkFailureStatReplies     Integer32,
        sonusNrsPerDestLinkFailureStatDupeReplies         Integer32,
        sonusNrsPerDestLinkFailureStatLateReplies         Integer32
    }

sonusNrsPerDestLinkFailureStatIfIndex OBJECT-TYPE
    SYNTAX          Integer32
    MAX-ACCESS      read-only
    STATUS          current
    DESCRIPTION     
            "The ifindex"
    ::= { sonusNrsPerDestLinkFailureStatEntry 1 }

sonusNrsPerDestLinkFailureStatIpAddress OBJECT-TYPE
    SYNTAX          IpAddress
    MAX-ACCESS      read-only
    STATUS          current
    DESCRIPTION     
            "The destination IP address."
    ::= { sonusNrsPerDestLinkFailureStatEntry 2 }

sonusNrsPerDestLinkFailureStatMinTime OBJECT-TYPE
    SYNTAX          Integer32
    MAX-ACCESS      read-only
    STATUS          current
    DESCRIPTION     
            "The minimum time used for get reply for a echo request packet."
    ::= { sonusNrsPerDestLinkFailureStatEntry 3 }

sonusNrsPerDestLinkFailureStatMaxTime OBJECT-TYPE
    SYNTAX          Integer32
    MAX-ACCESS      read-only
    STATUS          current
    DESCRIPTION     
            "The maximum time used for get reply for a echo request packet."
    ::= { sonusNrsPerDestLinkFailureStatEntry 4 }

sonusNrsPerDestLinkFailureStatAverageTime OBJECT-TYPE
    SYNTAX          Integer32
    MAX-ACCESS      read-only
    STATUS          current
    DESCRIPTION     
            "The average time used for get reply for a echo request packet."
    ::= { sonusNrsPerDestLinkFailureStatEntry 5 }

sonusNrsPerDestLinkFailureStatSumTime OBJECT-TYPE
    SYNTAX          Integer32
    MAX-ACCESS      read-only
    STATUS          current
    DESCRIPTION     
            "The summary of time"
    ::= { sonusNrsPerDestLinkFailureStatEntry 6 }

sonusNrsPerDestLinkFailureStat1Failure OBJECT-TYPE
    SYNTAX          Integer32
    MAX-ACCESS      read-only
    STATUS          current
    DESCRIPTION     
            "The number of single failures for this destination."
    ::= { sonusNrsPerDestLinkFailureStatEntry 7 }

sonusNrsPerDestLinkFailureStat2Failure OBJECT-TYPE
    SYNTAX          Integer32
    MAX-ACCESS      read-only
    STATUS          current
    DESCRIPTION     
            "The number of double failures for this destination."
    ::= { sonusNrsPerDestLinkFailureStatEntry 8 }

sonusNrsPerDestLinkFailureStatFailures OBJECT-TYPE
    SYNTAX          Integer32
    MAX-ACCESS      read-only
    STATUS          current
    DESCRIPTION     
            "The number of >2 failures for this destination."
    ::= { sonusNrsPerDestLinkFailureStatEntry 9 }

sonusNrsPerDestLinkFailureStatReplies OBJECT-TYPE
    SYNTAX          Integer32
    MAX-ACCESS      read-only
    STATUS          current
    DESCRIPTION     
            "The number of replies"
    ::= { sonusNrsPerDestLinkFailureStatEntry 10 }

sonusNrsPerDestLinkFailureStatDupeReplies OBJECT-TYPE
    SYNTAX          Integer32
    MAX-ACCESS      read-only
    STATUS          current
    DESCRIPTION     
            "The number of dupe replies"
    ::= { sonusNrsPerDestLinkFailureStatEntry 11 }

sonusNrsPerDestLinkFailureStatLateReplies OBJECT-TYPE
    SYNTAX          Integer32
    MAX-ACCESS      read-only
    STATUS          current
    DESCRIPTION     
            "The number of late replies."
    ::= { sonusNrsPerDestLinkFailureStatEntry 12 }

sonusSrvrEthernetSwitchIpTable OBJECT-TYPE
    SYNTAX          SEQUENCE OF SonusSrvrEthernetSwitchIpEntry
    MAX-ACCESS      not-accessible
    STATUS          current
    DESCRIPTION     
            "The table of ethernet switch IP address for servers"
    ::= { sonusIpInterfaceMIBObjects 12 }

sonusSrvrEthernetSwitchIpEntry OBJECT-TYPE
    SYNTAX          SonusSrvrEthernetSwitchIpEntry
    MAX-ACCESS      not-accessible
    STATUS          current
    DESCRIPTION     
            "ethernet switch IP address for a server"
    INDEX           { sonusSrvrEthernetSwitchIpShelf, 
                      sonusSrvrEthernetSwitchIpSlot, 
                      sonusSrvrEthernetSwitchIpPort }
    ::= { sonusSrvrEthernetSwitchIpTable 1 }

SonusSrvrEthernetSwitchIpEntry ::=
    SEQUENCE {
        sonusSrvrEthernetSwitchIpShelf  Integer32,
        sonusSrvrEthernetSwitchIpSlot   Integer32,
        sonusSrvrEthernetSwitchIpIpAddress  IpAddress,
        sonusSrvrEthernetSwitchIpPort   Integer32
    }

sonusSrvrEthernetSwitchIpShelf OBJECT-TYPE
    SYNTAX          Integer32 (1..6)
    MAX-ACCESS      read-write
    STATUS          current
    DESCRIPTION     
            "The shelf index of the server"
    ::= { sonusSrvrEthernetSwitchIpEntry 1 }

sonusSrvrEthernetSwitchIpSlot OBJECT-TYPE
    SYNTAX          Integer32 (1..16)
    MAX-ACCESS      read-write
    STATUS          current
    DESCRIPTION     
            "The slot index of the server"
    ::= { sonusSrvrEthernetSwitchIpEntry 2 }

sonusSrvrEthernetSwitchIpIpAddress OBJECT-TYPE
    SYNTAX          IpAddress
    MAX-ACCESS      read-write
    STATUS          current
    DESCRIPTION     
            "The ethernet switch IP address for this server."
    ::= { sonusSrvrEthernetSwitchIpEntry 3 }

sonusSrvrEthernetSwitchIpPort OBJECT-TYPE
    SYNTAX          Integer32 (0..65535)
    MAX-ACCESS      read-write
    STATUS          current
    DESCRIPTION     
            "The port index of the server"
    ::= { sonusSrvrEthernetSwitchIpEntry 4 }

sonusNrsSocketAccessAdmnTable OBJECT-TYPE
    SYNTAX          SEQUENCE OF SonusNrsSocketAccessAdmnEntry
    MAX-ACCESS      not-accessible
    STATUS          current
    DESCRIPTION     
            "The table of socket access definitions"
    ::= { sonusIpInterfaceMIBObjects 13 }

sonusNrsSocketAccessAdmnEntry OBJECT-TYPE
    SYNTAX          SonusNrsSocketAccessAdmnEntry
    MAX-ACCESS      not-accessible
    STATUS          current
    DESCRIPTION     
            "socket access definition for a server"
    INDEX           { sonusNrsSocketAccessProtocol, 
                      sonusNrsSocketAccessPort, 
                      sonusNrsSocketAccessIfIndex }
    ::= { sonusNrsSocketAccessAdmnTable 1 }

SonusNrsSocketAccessAdmnEntry ::=
    SEQUENCE {
        sonusNrsSocketAccessProtocol    INTEGER,
        sonusNrsSocketAccessPort        Integer32,
        sonusNrsSocketAccessIfIndex     Integer32,
        sonusNrsSocketAccessPermission  INTEGER,
        sonusNrsSocketAccessRowStatus   RowStatus
    }

sonusNrsSocketAccessProtocol OBJECT-TYPE
    SYNTAX          INTEGER { tcp(6), udp(17) }
    MAX-ACCESS      read-write
    STATUS          current
    DESCRIPTION     
            "The protocol definition"
    DEFVAL          { tcp }
    ::= { sonusNrsSocketAccessAdmnEntry 1 }

sonusNrsSocketAccessPort OBJECT-TYPE
    SYNTAX          Integer32 (1..65535)
    MAX-ACCESS      read-only
    STATUS          current
    DESCRIPTION     
            "The port number, value between 1-65535"
    ::= { sonusNrsSocketAccessAdmnEntry 2 }

sonusNrsSocketAccessIfIndex OBJECT-TYPE
    SYNTAX          Integer32 (1..65535)
    MAX-ACCESS      read-write
    STATUS          current
    DESCRIPTION     
            "A non-zero unsigned long ifindex assigned to the port where defines the access permition."
    ::= { sonusNrsSocketAccessAdmnEntry 3 }

sonusNrsSocketAccessPermission OBJECT-TYPE
    SYNTAX          INTEGER { deny(1), permit(2) }
    MAX-ACCESS      read-write
    STATUS          current
    DESCRIPTION     
            "The access permission"
    DEFVAL          { permit }
    ::= { sonusNrsSocketAccessAdmnEntry 4 }

sonusNrsSocketAccessRowStatus OBJECT-TYPE
    SYNTAX          RowStatus
    MAX-ACCESS      read-write
    STATUS          current
    DESCRIPTION     
            ""
    ::= { sonusNrsSocketAccessAdmnEntry 5 }

sonusNrsDebugIfTable OBJECT-TYPE
    SYNTAX          SEQUENCE OF SonusNrsDebugIfEntry
    MAX-ACCESS      not-accessible
    STATUS          current
    DESCRIPTION     
            "The collection of Debug Interface information for the
             specified instance."
    ::= { sonusIpInterfaceMIBObjects 99 }

sonusNrsDebugIfEntry OBJECT-TYPE
    SYNTAX          SonusNrsDebugIfEntry
    MAX-ACCESS      not-accessible
    STATUS          current
    DESCRIPTION     
            "The collection of Debug Interface information for the
             specified instance."
    INDEX           { sonusNrsDebugIfShelf, sonusNrsDebugIfSlot }
    ::= { sonusNrsDebugIfTable 1 }

SonusNrsDebugIfEntry ::=
    SEQUENCE {
        sonusNrsDebugIfIndex            Integer32,
        sonusNrsDebugIfShelf            Integer32,
        sonusNrsDebugIfSlot             Integer32,
        sonusNrsDebugIfPort             Integer32,
        sonusNrsDebugIfCircuit          Integer32,
        sonusNrsDebugIfType             IANAifType,
        sonusNrsDebugIfIpAddress        IpAddress,
        sonusNrsDebugIfIpMask           IpAddress,
        sonusNrsDebugIfMtu              Integer32,
        sonusNrsDebugIfGatewayAddress   IpAddress,
        sonusNrsDebugIfAdminStatus      INTEGER,
        sonusNrsDebugIfOperStatus       INTEGER
    }

sonusNrsDebugIfIndex OBJECT-TYPE
    SYNTAX          Integer32
    MAX-ACCESS      read-only
    STATUS          current
    DESCRIPTION     
            "The ifIndex assigned to this debug NIF when it was created.
             This will not change until the NIF is deleted."
    ::= { sonusNrsDebugIfEntry 1 }

sonusNrsDebugIfShelf OBJECT-TYPE
    SYNTAX          Integer32
    MAX-ACCESS      read-write
    STATUS          current
    DESCRIPTION     
            "A 32-bit integer identifying the shelf of the Debug
             Interface"
    ::= { sonusNrsDebugIfEntry 2 }

sonusNrsDebugIfSlot OBJECT-TYPE
    SYNTAX          Integer32
    MAX-ACCESS      read-write
    STATUS          current
    DESCRIPTION     
            "A 32-bit integer identifying the slot of the Debug
             Interface"
    ::= { sonusNrsDebugIfEntry 3 }

sonusNrsDebugIfPort OBJECT-TYPE
    SYNTAX          Integer32
    MAX-ACCESS      read-write
    STATUS          current
    DESCRIPTION     
            "A 32-bit integer identifying the port of the Debug
             Interface.  For current hardware this must be 1."
    ::= { sonusNrsDebugIfEntry 4 }

sonusNrsDebugIfCircuit OBJECT-TYPE
    SYNTAX          Integer32
    MAX-ACCESS      read-write
    STATUS          current
    DESCRIPTION     
            "A 32-bit integer identifying the circuit of the Debug
             Interface.  For current hardware this must be 1."
    ::= { sonusNrsDebugIfEntry 5 }

sonusNrsDebugIfType OBJECT-TYPE
    SYNTAX          IANAifType
    MAX-ACCESS      read-write
    STATUS          current
    DESCRIPTION     
            "The type of interface, distinguished according to the
             physical/link protocol(s) immediately 'below' the network
             layer in the protocol stack.
             
             Values are from RFC1213 for the ifType object.
             
             Current hardware supports only the ethernet-csmacd (6)
             type."
    ::= { sonusNrsDebugIfEntry 6 }

sonusNrsDebugIfIpAddress OBJECT-TYPE
    SYNTAX          IpAddress
    MAX-ACCESS      read-write
    STATUS          current
    DESCRIPTION     
            "The IP Address of the Debug Interface"
    ::= { sonusNrsDebugIfEntry 7 }

sonusNrsDebugIfIpMask OBJECT-TYPE
    SYNTAX          IpAddress
    MAX-ACCESS      read-write
    STATUS          current
    DESCRIPTION     
            "The IP subnet mask of this Debug Interface."
    ::= { sonusNrsDebugIfEntry 8 }

sonusNrsDebugIfMtu OBJECT-TYPE
    SYNTAX          Integer32
    MAX-ACCESS      read-write
    STATUS          current
    DESCRIPTION     
            "The size of the largest datagram that can be sent/received
             on the interface, specified in octets."
    ::= { sonusNrsDebugIfEntry 9 }

sonusNrsDebugIfGatewayAddress OBJECT-TYPE
    SYNTAX          IpAddress
    MAX-ACCESS      read-write
    STATUS          current
    DESCRIPTION     
            "The IP address of the default gateway for this Debug
             Interface."
    ::= { sonusNrsDebugIfEntry 10 }

sonusNrsDebugIfAdminStatus OBJECT-TYPE
    SYNTAX          INTEGER { disabled(1), enabled(2) }
    MAX-ACCESS      read-write
    STATUS          current
    DESCRIPTION     
            "The requested status of the interface."
    ::= { sonusNrsDebugIfEntry 11 }

sonusNrsDebugIfOperStatus OBJECT-TYPE
    SYNTAX          INTEGER { outOfService(1), inService(2), 
                        outOfServiceDisabled(3), outOfServiceLinkDown(4) }
    MAX-ACCESS      read-only
    STATUS          current
    DESCRIPTION     
            "The actual status of the debug interface.  A link will
             be InService if the sonusNrsDebugIfAdminStatus is enabled and
             the physical link is up.  It will be OutOfService if the admin
             status is enabled but the physical link is down.  It will be
             OutOfServiceDisabled if the physical link is up but the admin
             status is disabled.  It will be OutOfServiceLinkDown if the
             physical link is down and the admin status is disabled."
    ::= { sonusNrsDebugIfEntry 12 }

sonusIpInterfaceMIBNotifications OBJECT IDENTIFIER
    ::= { sonusIpInterfaceMIB 2 }

sonusIpInterfaceMIBNotificationsPrefix OBJECT IDENTIFIER
    ::= { sonusIpInterfaceMIBNotifications 0 }

sonusIpInterfaceMIBNotificationsObjects OBJECT IDENTIFIER
    ::= { sonusIpInterfaceMIBNotifications 1 }

sonusNrsNifInServiceNotification NOTIFICATION-TYPE
    OBJECTS         { sonusNifShelf, sonusNifSlot, sonusNifPort, 
                      sonusNifIndex, sonusNifName, sonusEventDescription, 
                      sonusEventClass, sonusEventLevel }
    STATUS          current
    DESCRIPTION     
            "This trap indicates that a NIF is available to support
             call processing."
    ::= { sonusIpInterfaceMIBNotificationsPrefix 1 }

sonusNrsNifOutOfServiceNotification NOTIFICATION-TYPE
    OBJECTS         { sonusNifShelf, sonusNifSlot, sonusNifPort, 
                      sonusNifIndex, sonusNifName, 
                      sonusNifOutOfServiceReason, sonusEventDescription, 
                      sonusEventClass, sonusEventLevel }
    STATUS          current
    DESCRIPTION     
            "This trap indicates that a NIF is no longer available to
             support call processing."
    ::= { sonusIpInterfaceMIBNotificationsPrefix 2 }

sonusNrsNifEnabledNotification NOTIFICATION-TYPE
    OBJECTS         { sonusNifShelf, sonusNifSlot, sonusNifPort, 
                      sonusNifIndex, sonusNifName, sonusEventDescription, 
                      sonusEventClass, sonusEventLevel }
    STATUS          current
    DESCRIPTION     
            "This trap indicates that a NIF's configuration is enabled."
    ::= { sonusIpInterfaceMIBNotificationsPrefix 3 }

sonusNrsNifDisabledNotification NOTIFICATION-TYPE
    OBJECTS         { sonusNifShelf, sonusNifSlot, sonusNifPort, 
                      sonusNifIndex, sonusNifName, sonusEventDescription, 
                      sonusEventClass, sonusEventLevel }
    STATUS          current
    DESCRIPTION     
            "This trap indicates that a NIF's configuration is disabled."
    ::= { sonusIpInterfaceMIBNotificationsPrefix 4 }

sonusNrsNifDeletedNotification NOTIFICATION-TYPE
    OBJECTS         { sonusNifShelf, sonusNifSlot, sonusNifPort, 
                      sonusNifIndex, sonusNifName, sonusEventDescription, 
                      sonusEventClass, sonusEventLevel }
    STATUS          current
    DESCRIPTION     
            "This trap indicates that a NIF's configuration is deleted."
    ::= { sonusIpInterfaceMIBNotificationsPrefix 5 }

sonusNrsNifHighWatermarkNotification NOTIFICATION-TYPE
    OBJECTS         { sonusNifShelf, sonusNifSlot, sonusNifPort, 
                      sonusNifIndex, sonusNifName, sonusEventDescription, 
                      sonusEventClass, sonusEventLevel }
    STATUS          current
    DESCRIPTION     
            "This trap indicates that a NIF's high watermark has been reached 
             the first time since the NIF's low watermark has beend reached."
    ::= { sonusIpInterfaceMIBNotificationsPrefix 6 }

sonusNrsNifLowWatermarkNotification NOTIFICATION-TYPE
    OBJECTS         { sonusNifShelf, sonusNifSlot, sonusNifPort, 
                      sonusNifIndex, sonusNifName, sonusEventDescription, 
                      sonusEventClass, sonusEventLevel }
    STATUS          current
    DESCRIPTION     
            "This trap indicates that a NIF's low watermark has been reached
             the first time since the NIF's high watermark has been reached."
    ::= { sonusIpInterfaceMIBNotificationsPrefix 7 }

sonusNrsNifBwHighDeviationNotification NOTIFICATION-TYPE
    OBJECTS         { sonusNifShelf, sonusNifSlot, sonusNifPort, 
                      sonusNifIndex, sonusNifName, sonusEventDescription, 
                      sonusEventClass, sonusEventLevel }
    STATUS          current
    DESCRIPTION     
            "This trap indicates that a NIF's actual bandwidth is greater than the 
             expected bandwidth plus deviation amount. This trap will be re-armed
             when the actual bandwdith dropped below the expected level. "
    ::= { sonusIpInterfaceMIBNotificationsPrefix 8 }

sonusNrsNifBwLowDeviationNotification NOTIFICATION-TYPE
    OBJECTS         { sonusNifShelf, sonusNifSlot, sonusNifPort, 
                      sonusNifIndex, sonusNifName, sonusEventDescription, 
                      sonusEventClass, sonusEventLevel }
    STATUS          current
    DESCRIPTION     
            "This trap indicates that a NIF's actual bandwidth is lower than the
             expected bandwidth minus 2 times the deviation amount.This trap will 
             be re-armed when the actual bandwdith reached the expected level."
    ::= { sonusIpInterfaceMIBNotificationsPrefix 9 }

sonusNrsLinkDownNotification NOTIFICATION-TYPE
    OBJECTS         { sonusShelfIndex, sonusSlotIndex, 
                      sonusEventDescription, sonusEventClass, 
                      sonusEventLevel }
    STATUS          current
    DESCRIPTION     
            "This trap indicates that a link down event has been detected on a server"
    ::= { sonusIpInterfaceMIBNotificationsPrefix 10 }

sonusNrsLinkUpNotification NOTIFICATION-TYPE
    OBJECTS         { sonusShelfIndex, sonusSlotIndex, 
                      sonusEventDescription, sonusEventClass, 
                      sonusEventLevel }
    STATUS          current
    DESCRIPTION     
            "This trap indicates that a link up event has event detected on a server"
    ::= { sonusIpInterfaceMIBNotificationsPrefix 11 }

sonusNrsNifCreatedNotification NOTIFICATION-TYPE
    OBJECTS         { sonusNifShelf, sonusNifSlot, sonusNifPort, 
                      sonusNifIndex, sonusNifName, sonusEventDescription, 
                      sonusEventClass, sonusEventLevel }
    STATUS          current
    DESCRIPTION     
            "This trap indicates that a NIF's configuration is created."
    ::= { sonusIpInterfaceMIBNotificationsPrefix 12 }

END -- end of module SONUS-IP-INTERFACE-MIB.
