-- $Header:   K:/WanSuite/archives/include/pvcs/ipad.mib,v   1.39   Jun 21 2000 14:41:36   bobr  $

IPAD-MIB DEFINITIONS ::= BEGIN

IMPORTS enterprises, IpAddress, TimeTicks              FROM RFC1155-SMI
        OBJECT-TYPE                                    FROM RFC-1212
        DisplayString                                  FROM RFC1213-MIB
        TRAP-TYPE                                      FROM RFC-1215;

verilink    OBJECT IDENTIFIER ::= { enterprises 321 }
hbu         OBJECT IDENTIFIER ::= { verilink 100 }
ipad        OBJECT IDENTIFIER ::= { hbu 1 }

-- IPAD sections

ipadFrPort      OBJECT IDENTIFIER ::= { ipad 1 }
ipadService     OBJECT IDENTIFIER ::= { ipad 2 }
ipadChannel     OBJECT IDENTIFIER ::= { ipad 3 }
ipadDLCI        OBJECT IDENTIFIER ::= { ipad 4 }
ipadEndpoint    OBJECT IDENTIFIER ::= { ipad 5 }
ipadUser        OBJECT IDENTIFIER ::= { ipad 6 }
ipadPPP         OBJECT IDENTIFIER ::= { ipad 7 }
ipadModem       OBJECT IDENTIFIER ::= { ipad 8 }
ipadSvcAware    OBJECT IDENTIFIER ::= { ipad 9 }
ipadPktSwitch   OBJECT IDENTIFIER ::= { ipad 10 }
ipadTrapDest    OBJECT IDENTIFIER ::= { ipad 11 }
ipadMisc        OBJECT IDENTIFIER ::= { ipad 12 }
ipadRouter      OBJECT IDENTIFIER ::= { ipad 13 }
ipadSoftKey     OBJECT IDENTIFIER ::= { ipad 14 }

-- ipadFrPort section
-- contains the frame relay port table

ipadFrPortTable    OBJECT-TYPE
    SYNTAX    SEQUENCE OF IpadFrPortTableEntry
    ACCESS    not-accessible
    STATUS    optional
    DESCRIPTION
        "Table of frame relay port parameters."
    ::= { ipadFrPort 1 }

ipadFrPortTableEntry    OBJECT-TYPE
    SYNTAX  IpadFrPortTableEntry
    ACCESS  not-accessible
    STATUS  mandatory
    DESCRIPTION
        "An entry in the ipad frame relay port table."
    INDEX   { ipadFrPortService }
    ::= { ipadFrPortTable 1 }

IpadFrPortTableEntry ::=
    SEQUENCE
    {
    ipadFrPortService            INTEGER,
    ipadFrPortActive             INTEGER,
    ipadFrPortLMIType            INTEGER,
    ipadFrPortLMIMode            INTEGER,
    ipadFrPortRxInvAlmThreshold  INTEGER,
    ipadFrPortRxInvAlmAlarm      INTEGER,
    ipadFrPortTxAlmThreshold     INTEGER,
    ipadFrPortTxAlmAlarm         INTEGER,
    ipadFrPortRxAlmThreshold     INTEGER,
    ipadFrPortRxAlmAlarm         INTEGER
    }

ipadFrPortService    OBJECT-TYPE
    SYNTAX  INTEGER
    ACCESS  read-only
    STATUS  mandatory
    DESCRIPTION
        "Index into the ipad frame relay port table;
        an entry in the ipad service table."
    ::= { ipadFrPortTableEntry 1 }

ipadFrPortActive    OBJECT-TYPE
    SYNTAX  INTEGER
        {
        other(1),
        no(2),
        yes(3)
        }
    ACCESS  read-only
    STATUS  mandatory
    DESCRIPTION
        "Specifies if the port is active."
    ::= { ipadFrPortTableEntry 2 }

ipadFrPortLMIType    OBJECT-TYPE
    SYNTAX  INTEGER
        {
        other(1),
        ccitt(2),
        ansi(3),
        lmi(4),
        none(5)
        }
    ACCESS  read-only
    STATUS  mandatory
    DESCRIPTION
        "Specifies the link management information 
        type used on this port."
    ::= { ipadFrPortTableEntry 3 }

ipadFrPortLMIMode    OBJECT-TYPE
    SYNTAX  INTEGER
        {
        other(1),
        sourcing(2),
        monitoring(3)
        }
    ACCESS  read-only
    STATUS  mandatory
    DESCRIPTION
        "Specifies the link management information 
        mode used on this port."
    ::= { ipadFrPortTableEntry 4 }

ipadFrPortRxInvAlmThreshold  OBJECT-TYPE
    SYNTAX  INTEGER
    ACCESS  read-write
    STATUS  mandatory
    DESCRIPTION     
        "Sets the rx invalid frames alarm threshold.  
        Setting this field to 0 disables the alarm."
    ::= { ipadFrPortTableEntry 5 }

ipadFrPortRxInvAlmAlarm    OBJECT-TYPE
    SYNTAX  INTEGER
        {
        other(1),
        noAlarm(2),
        thresholdExceeded(3)
        }
    ACCESS  read-only
    STATUS  mandatory
    DESCRIPTION
        "Reports if the invalid frames threshold has 
        been exceeded."
    ::= { ipadFrPortTableEntry 6 }

ipadFrPortTxAlmThreshold     OBJECT-TYPE
    SYNTAX  INTEGER
    ACCESS  read-write
    STATUS  mandatory
    DESCRIPTION     
        "Sets the tx throughput alarm threshold (in octets/second).  
        Setting this field to 0 disables the alarm."
    ::= { ipadFrPortTableEntry 7 }

ipadFrPortTxAlmAlarm    OBJECT-TYPE
    SYNTAX  INTEGER
        {
        other(1),
        noAlarm(2),
        thresholdExceeded(3)
        }
    ACCESS  read-only
    STATUS  mandatory
    DESCRIPTION
        "Reports if the tx throughput threshold has 
        been exceeded."
    ::= { ipadFrPortTableEntry 8 }

ipadFrPortRxAlmThreshold      OBJECT-TYPE
    SYNTAX  INTEGER
    ACCESS  read-write
    STATUS  mandatory
    DESCRIPTION     
        "Sets the rx throughput alarm threshold (in octets/second).  
        Setting this field to 0 disables the alarm."
    ::= { ipadFrPortTableEntry 9 }

ipadFrPortRxAlmAlarm        OBJECT-TYPE
    SYNTAX  INTEGER
        {
        other(1),
        noAlarm(2),
        thresholdExceeded(3)
        }
    ACCESS  read-only
    STATUS  mandatory
    DESCRIPTION
        "Reports if the rx throughput threshold has 
        been exceeded."
    ::= { ipadFrPortTableEntry 10 }

-- ipadService section
-- contains the service table

ipadServiceTable    OBJECT-TYPE
    SYNTAX  SEQUENCE OF IpadServiceTableEntry
    ACCESS  not-accessible
    STATUS  optional
    DESCRIPTION
        "The ipad service table."
    ::= { ipadService 1 }

ipadServiceTableEntry    OBJECT-TYPE
    SYNTAX  IpadServiceTableEntry
    ACCESS  not-accessible
    STATUS  mandatory
    DESCRIPTION
        "An entry in the ipad service table."
    INDEX    { ipadServiceIndex }
    ::= { ipadServiceTable 1 }

IpadServiceTableEntry ::=
    SEQUENCE
    {
    ipadServiceIndex        INTEGER,
    ipadServiceifIndex      INTEGER,
    ipadServiceType         INTEGER,
    ipadServicePair         INTEGER
    }

ipadServiceIndex    OBJECT-TYPE
    SYNTAX  INTEGER
    ACCESS  read-only
    STATUS  mandatory
    DESCRIPTION
        "The index for the ipad service table."
    ::= { ipadServiceTableEntry 1 }

ipadServiceifIndex    OBJECT-TYPE
    SYNTAX  INTEGER
        {
        disabled(0),
        supervisor(1),
        network1(2),
        network2(3),
        user1(4),
        user2(5),
        ethernet(6)
        }
    ACCESS  read-write
    STATUS  mandatory
    DESCRIPTION
        "The MIB-II ifIndex for this service."
    ::= { ipadServiceTableEntry 2 }

ipadServiceType        OBJECT-TYPE
    SYNTAX  INTEGER
        {
        other(1),
        tdm(2),
        ppp(3),
        pppMonitor(4),
        frameRelay(5),
        frameRelayMonitor(6),
        ip(7),
        serial(8),
        tty(9)
        }
    ACCESS  read-write
    STATUS  mandatory
    DESCRIPTION
        "The type of this service."
    ::= { ipadServiceTableEntry 3 }

ipadServicePair        OBJECT-TYPE
    SYNTAX  INTEGER
    ACCESS  read-write
    STATUS  mandatory
    DESCRIPTION
        "An entry in this table, which establishes a service pairing."
    ::= { ipadServiceTableEntry 4 }

ipadServiceAddService OBJECT-TYPE
    SYNTAX  INTEGER
        {
        addService(1)
        }
    ACCESS  read-write
    STATUS  mandatory
    DESCRIPTION
        "Adds a row to the Service Table."
    ::= { ipadService 2 }

ipadServiceDeleteService OBJECT-TYPE
    SYNTAX  INTEGER
    ACCESS  read-write
    STATUS  mandatory
    DESCRIPTION
        "Identifies a Service to be deleted; an index into the Service Table."
    ::= { ipadService 3 }

-- ipadChannel section
-- contains the channel table

ipadChannelTable    OBJECT-TYPE
    SYNTAX  SEQUENCE OF IpadChannelTableEntry
    ACCESS  not-accessible
    STATUS  optional
    DESCRIPTION
        "The ipad channel table."
    ::= { ipadChannel 1 }

ipadChannelTableEntry    OBJECT-TYPE
    SYNTAX  IpadChannelTableEntry
    ACCESS  not-accessible
    STATUS  mandatory
    DESCRIPTION
        "An entry in the ipad channel table."
    INDEX    { ipadChannelifIndex, ipadChannelIndex }
    ::= { ipadChannelTable 1 }

IpadChannelTableEntry ::=
    SEQUENCE
    {
    ipadChannelifIndex      INTEGER,
    ipadChannelIndex        INTEGER,
    ipadChannelService      INTEGER,
    ipadChannelPair         INTEGER,
    ipadChannelRate         INTEGER
    }

ipadChannelifIndex    OBJECT-TYPE
    SYNTAX  INTEGER
        {
        supervisor(1),
        network1(2),
        network2(3),
        user1(4),
        user2(5),
        ethernet(6)
        }
    ACCESS  read-only
    STATUS  mandatory
    DESCRIPTION
        "Primary index into ipad channel table, MIB-II ifIndex."
    ::= { ipadChannelTableEntry 1 }

ipadChannelIndex    OBJECT-TYPE
    SYNTAX  INTEGER
    ACCESS  read-only
    STATUS  mandatory
    DESCRIPTION
        "Channel index for the physical interface."
    ::= { ipadChannelTableEntry 2 }

ipadChannelService    OBJECT-TYPE
    SYNTAX  INTEGER
    ACCESS  read-write
    STATUS  mandatory
    DESCRIPTION
        "Index into service table for this channel."
    ::= { ipadChannelTableEntry 3 }

ipadChannelPair        OBJECT-TYPE
    SYNTAX  INTEGER
    ACCESS  read-write
    STATUS  mandatory
    DESCRIPTION    
        "Pair for this channel; an entry in the channel 
        table.  Use service pair in service table to 
        determine which service contains this channel."
    ::= { ipadChannelTableEntry 4 }

ipadChannelRate        OBJECT-TYPE
    SYNTAX  INTEGER
    {
    other(1),
    rate56(2),
    rate64(3)
    }
    ACCESS  read-write
    STATUS  mandatory
    DESCRIPTION    
        "Rate for this channel."
    ::= { ipadChannelTableEntry 5 }

-- ipadDLCI section
-- contains the DLCI table

ipadDLCITable    OBJECT-TYPE
    SYNTAX  SEQUENCE OF IpadDLCITableEntry
    ACCESS  not-accessible
    STATUS  optional
    DESCRIPTION
        "The ipad DLCI table."
    ::= { ipadDLCI 1 }

ipadDLCITableEntry    OBJECT-TYPE
    SYNTAX  IpadDLCITableEntry
    ACCESS  not-accessible
    STATUS  mandatory
    DESCRIPTION
        "An entry in the ipad DLCI table."
    INDEX    { ipadDLCIservice,ipadDLCInumber }
    ::= { ipadDLCITable 1 }

IpadDLCITableEntry ::=
    SEQUENCE
    {
    ipadDLCIservice           INTEGER,
    ipadDLCInumber            INTEGER,
    ipadDLCIactive            INTEGER,
    ipadDLCIcongestion        INTEGER,
    ipadDLCIremote            INTEGER,
    ipadDLCIremoteUnit        DisplayString,
    ipadDLCIremoteEquipActive INTEGER,
    ipadDLCIencapsulation     INTEGER,
    ipadDLCIproprietary       INTEGER,
    ipadDLCIpropOffset        INTEGER,
    ipadDLCIinBand            INTEGER,
    ipadDLCICIR               INTEGER,
    ipadDLCIBe                INTEGER,
    ipadDLCIminBC             INTEGER,
    ipadDLCIrxMon             INTEGER,
    ipadDLCIdEctrl            INTEGER,
    ipadDLCIenableDelay       INTEGER,
    ipadDLCItxExCIRThreshold  INTEGER,
    ipadDLCItxExCIRAlarm      INTEGER,
    ipadDLCItxExBeThreshold   INTEGER,
    ipadDLCItxExBeAlarm       INTEGER,
    ipadDLCIrxCongThreshold   INTEGER,
    ipadDLCIrxCongAlarm       INTEGER,
    ipadDLCIrxBECNinCIR       INTEGER,
    ipadDLCIUASThreshold      INTEGER,
    ipadDLCIUASAlarm          INTEGER
    }

ipadDLCIservice    OBJECT-TYPE
    SYNTAX  INTEGER
    ACCESS  read-only
    STATUS  mandatory
    DESCRIPTION
        "An index into the ipad service table."
    ::= { ipadDLCITableEntry 1 }

ipadDLCInumber    OBJECT-TYPE
    SYNTAX  INTEGER
    ACCESS  read-only
    STATUS  mandatory
    DESCRIPTION
        "The DLCI number for this entry."
    ::= { ipadDLCITableEntry 2 }

ipadDLCIactive    OBJECT-TYPE
    SYNTAX  INTEGER
        {
        other(1),
        no(2),
        yes(3),
        pending(4)
        }
    ACCESS  read-only
    STATUS  mandatory
    DESCRIPTION
        "Specifies if the DLCI is active."
    ::= { ipadDLCITableEntry 3 }

ipadDLCIcongestion    OBJECT-TYPE
    SYNTAX  INTEGER
    {
    other(1),
    no(2),
    yes(3)
    }
    ACCESS  read-only
    STATUS  mandatory
    DESCRIPTION
        "Specifies if the dlci is receiving frames 
        with FECN or BECN bit set."
    ::= { ipadDLCITableEntry 4 }

ipadDLCIremote    OBJECT-TYPE
    SYNTAX  INTEGER
    ACCESS  read-only
    STATUS  mandatory
    DESCRIPTION
        "Remote DLCI number."
    ::= { ipadDLCITableEntry 5 }

ipadDLCIremoteUnit    OBJECT-TYPE
    SYNTAX  DisplayString( SIZE(0..11))
    ACCESS  read-only
    STATUS  mandatory
    DESCRIPTION
        "Name of the remote DLCI."
    ::= { ipadDLCITableEntry 6 }

ipadDLCIremoteEquipActive    OBJECT-TYPE
    SYNTAX  INTEGER
    {
    other(1),
    inactive(2),
    active(3),
    sosAlarm(4)
    }
    ACCESS  read-only
    STATUS  mandatory
    DESCRIPTION
        "Reports if the equipment attached to the
        remote unit is active."
    ::= { ipadDLCITableEntry 7 }

ipadDLCIencapsulation    OBJECT-TYPE
    SYNTAX  INTEGER
    {
    other(1),
    rfc1490(2),
    proprietary(3)
    }
    ACCESS  read-write
    STATUS  mandatory
    DESCRIPTION
        "Type of protocol encapsulation used on this DLCI."
    ::= { ipadDLCITableEntry 8 }

ipadDLCIproprietary    OBJECT-TYPE
    SYNTAX  INTEGER
    {
    other(1),
    ip(2),
    ipx(3),
    ethertype(4),
    none(5)
    }
    ACCESS  read-write
    STATUS  mandatory
    DESCRIPTION
        "When the encapsulation is proprietary, the traffic type must be
        configured to gather protocol specific statistics."
    ::= { ipadDLCITableEntry 9 }

ipadDLCIpropOffset    OBJECT-TYPE
    SYNTAX  INTEGER
    ACCESS  read-write
    STATUS  mandatory
    DESCRIPTION
        "When the encapsulation is proprietary, this is the number of bytes
        after the frame relay header to look for the specified protocol
        decode."
    ::= { ipadDLCITableEntry 10 }

ipadDLCIinBand    OBJECT-TYPE
    SYNTAX  INTEGER
    {
    other(1),
    no(2),
    yes(3)
    }
    ACCESS  read-write
    STATUS  mandatory
    DESCRIPTION
        "Determines if frames on this DLCI will be parsed to look
        for management frames destined for the unit itself."
    ::= { ipadDLCITableEntry 11 }

ipadDLCICIR    OBJECT-TYPE
    SYNTAX  INTEGER
    ACCESS  read-write
    STATUS  mandatory
    DESCRIPTION
        "Default committed information rate in bits per second."
    ::= { ipadDLCITableEntry 12 }

ipadDLCIBe    OBJECT-TYPE
    SYNTAX  INTEGER
    ACCESS  read-write
    STATUS  mandatory
    DESCRIPTION
        "Default excess burst rate in bits per second."
    ::= { ipadDLCITableEntry 13 }

ipadDLCIminBC    OBJECT-TYPE
    SYNTAX  INTEGER
    ACCESS  read-write
    STATUS  mandatory
    DESCRIPTION
        "If the corresponding interface is configured to enable
        congestion management, the minimum transfer rate at which
        the unit will throttle back offering data to the network."
    ::= { ipadDLCITableEntry 14 }

ipadDLCIrxMon    OBJECT-TYPE
    SYNTAX  INTEGER
    {
    other(1),
    no(2),
    yes(3)
    }
    ACCESS  read-write
    STATUS  mandatory
    DESCRIPTION
        "Determines if the SLA parameters will be monitored for received
        frames."
    ::= { ipadDLCITableEntry 15 }

ipadDLCIdEctrl    OBJECT-TYPE
    SYNTAX  INTEGER
    {
    other(1),
    no(2),
    yes(3)
    }
    ACCESS  read-write
    STATUS  mandatory
    DESCRIPTION
        "Determines if the Rx monitor will set the DE bit on all frames
        received in excess of the CIR before they are switched to their
        destination port."
    ::= { ipadDLCITableEntry 16 }

ipadDLCIenableDelay    OBJECT-TYPE
    SYNTAX  INTEGER
    {
    other(1),
    disable(2),
    enable(3)
    }
    ACCESS  read-write
    STATUS  mandatory
    DESCRIPTION
        "Enable or disable delay."
    ::= { ipadDLCITableEntry 17 }

ipadDLCItxExCIRThreshold    OBJECT-TYPE
    SYNTAX  INTEGER
    ACCESS  read-write
    STATUS  mandatory
    DESCRIPTION     
        "Sets the Tx over CIR alarm threshold.  This threshold 
        is the number of octets per second in excess of CIR.  Setting 
        this field to 0 disables the alarm."
    ::= { ipadDLCITableEntry 18 }

ipadDLCItxExCIRAlarm    OBJECT-TYPE
    SYNTAX  INTEGER
    {
    other(1),
    noAlarm(2),
    thresholdExceeded(3)
    }
    ACCESS  read-only
    STATUS  mandatory
    DESCRIPTION
        "Reports if the Tx over CIR threshold has been exceeded."
    ::= { ipadDLCITableEntry 19 }

ipadDLCItxExBeThreshold    OBJECT-TYPE
    SYNTAX  INTEGER
    ACCESS  read-write
    STATUS  mandatory
    DESCRIPTION     
        "Sets the Tx over Be alarm threshold.  This threshold is the 
        number of octets per second in excess of Be.  Setting this 
		field to 0 disables the alarm."
    ::= { ipadDLCITableEntry 20 }

ipadDLCItxExBeAlarm    OBJECT-TYPE
    SYNTAX  INTEGER
    {
    other(1),
    noAlarm(2),
    thresholdExceeded(3)
    }
    ACCESS  read-only
    STATUS  mandatory
    DESCRIPTION
        "Reports if the Tx over Be threshold has been exceeded."
    ::= { ipadDLCITableEntry 21 }

ipadDLCIrxCongThreshold    OBJECT-TYPE
    SYNTAX  INTEGER
    ACCESS  read-write
    STATUS  mandatory
    DESCRIPTION     
        "Sets the Rx congestion alarm threshold.  This threshold 
        is the number of frames received with BECN/FECN.  Setting 
        this field to 0 disables the alarm."
    ::= { ipadDLCITableEntry 22 }

ipadDLCIrxCongAlarm    OBJECT-TYPE
    SYNTAX  INTEGER
    {
    other(1),
    noAlarm(2),
    thresholdExceeded(3)
    }
    ACCESS  read-only
    STATUS  mandatory
    DESCRIPTION
        "Reports if the Rx congestion threshold has been exceeded."
    ::= { ipadDLCITableEntry 23 }

ipadDLCIrxBECNinCIR    OBJECT-TYPE
    SYNTAX  INTEGER
    {
    other(1),
    noAlarm(2),
    alarmCondition(3)
    }
    ACCESS  read-only
    STATUS  mandatory
    DESCRIPTION
        "Reports if BECN has been received within CIR."
    ::= { ipadDLCITableEntry 24 }

ipadDLCIUASThreshold    OBJECT-TYPE
    SYNTAX  INTEGER
    ACCESS  read-write
    STATUS  mandatory
    DESCRIPTION     
        "Sets the UAS (unavailable seconds) alarm threshold.  This
        threshold is the number of seconds passed that the DLCI is
        unavailable.  Setting this field to 0 disables the alarm."
    ::= { ipadDLCITableEntry 25 }

ipadDLCIUASAlarm    OBJECT-TYPE
    SYNTAX  INTEGER
    {
    other(1),
    noAlarm(2),
    thresholdExceeded(3)
    }
    ACCESS  read-only
    STATUS  mandatory
    DESCRIPTION
        "Reports if the UAS threshold has been exceeded."
    ::= { ipadDLCITableEntry 26 }

ipadDLCILastChange OBJECT-TYPE
    SYNTAX  TimeTicks
    ACCESS  read-only
    STATUS  mandatory
    DESCRIPTION
        "Time of the last change in the DLCI table."
    ::= { ipadDLCI 2 }
    
-- ipadEndpoint section
-- endpoint table

ipadEndpointTable    OBJECT-TYPE
    SYNTAX  SEQUENCE OF IpadEndpointTableEntry
    ACCESS  not-accessible
    STATUS  optional
    DESCRIPTION
        "The ipad endpoint table."
    ::= { ipadEndpoint 1 }

ipadEndpointTableEntry    OBJECT-TYPE
    SYNTAX    IpadEndpointTableEntry
    ACCESS  not-accessible
    STATUS  mandatory
    DESCRIPTION
        "An entry in the ipad endpoint table."
    INDEX   { ipadEndpointIndex }
    ::= { ipadEndpointTable 1 }

IpadEndpointTableEntry ::=
    SEQUENCE
    {
    ipadEndpointIndex        INTEGER,
    ipadEndpointName         DisplayString,
    ipadEndpointService      INTEGER,
    ipadEndpointDLCInumber   INTEGER,
    ipadEndpointType         INTEGER,
    ipadEndpointForward      INTEGER,
    ipadEndpointBackup       INTEGER,
    ipadEndpointRefSLP       INTEGER,
    ipadEndpointRemoteIpAddr IpAddress,
    ipadEndpointRemoteIpMask IpAddress
    }

ipadEndpointIndex    OBJECT-TYPE
    SYNTAX  INTEGER
    ACCESS  read-only
    STATUS  mandatory
    DESCRIPTION
        "The index into the ipad endpoint table."
    ::= { ipadEndpointTableEntry 1 }

ipadEndpointName    OBJECT-TYPE
    SYNTAX  DisplayString ( SIZE(0..11) )
    ACCESS  read-write
    STATUS  mandatory
    DESCRIPTION
        "The name for the endpoint."
    ::= { ipadEndpointTableEntry 2 }

ipadEndpointService    OBJECT-TYPE
    SYNTAX  INTEGER
    ACCESS  read-write
    STATUS  mandatory
    DESCRIPTION
        "An index into the ipad service table."
    ::= { ipadEndpointTableEntry 3 }

ipadEndpointDLCInumber    OBJECT-TYPE
    SYNTAX  INTEGER
    ACCESS  read-write
    STATUS  mandatory
    DESCRIPTION
        "Data link connection identifier for this endpoint;
            The DLCI number for this entry."
    ::= { ipadEndpointTableEntry 4 }

ipadEndpointType    OBJECT-TYPE
    SYNTAX  INTEGER
    {
    other(1),
    local(2),
    switched(3),
    ipRoute(4)
    }
    ACCESS  read-write
    STATUS  mandatory
    DESCRIPTION
        "Endpoint type."
    ::= { ipadEndpointTableEntry 5 }

ipadEndpointForward    OBJECT-TYPE
    SYNTAX  INTEGER
    ACCESS  read-write
    STATUS  mandatory
    DESCRIPTION
        "Index into the endpoint names table.  This is the endpoint
        on which data should be forwarded for switched endpoints." 
    ::= { ipadEndpointTableEntry 6 }

ipadEndpointBackup    OBJECT-TYPE
    SYNTAX  INTEGER
    ACCESS  read-write
    STATUS  mandatory
    DESCRIPTION
        "Index into the endpoint table.  This is the endpoint
        on which data should be forwarded in the case where the
        endpoint becomes inactive."
    ::= { ipadEndpointTableEntry 7 }

ipadEndpointRefSLP    OBJECT-TYPE
    SYNTAX  INTEGER
    ACCESS  read-write
    STATUS  mandatory
    DESCRIPTION
        "Index into the endpoint table.  The service level parameters
        can be copied from another configured endpoint."
    ::= { ipadEndpointTableEntry 8 }

ipadEndpointRemoteIpAddr    OBJECT-TYPE
    SYNTAX  IpAddress
    ACCESS  read-write
    STATUS  mandatory
    DESCRIPTION
        "IP address for remote."
    ::= { ipadEndpointTableEntry 9 }

ipadEndpointRemoteIpMask    OBJECT-TYPE
    SYNTAX  IpAddress
    ACCESS  read-write
    STATUS  mandatory
    DESCRIPTION
        "IP address mask for remote."
    ::= { ipadEndpointTableEntry 10 }

ipadEndpointAddEndpoint OBJECT-TYPE
    SYNTAX  DisplayString( SIZE(0..11) )
    ACCESS  read-write
    STATUS  mandatory
    DESCRIPTION
        "Identifies an Endpoint to be added."
    ::= { ipadEndpoint 2 }

ipadEndpointDeleteEndpoint OBJECT-TYPE
    SYNTAX  DisplayString( SIZE(0..11) )
    ACCESS  read-write
    STATUS  mandatory
    DESCRIPTION
        "Identifies an Endpoint to be deleted."
    ::= { ipadEndpoint 3 }

ipadEndpointLastChange OBJECT-TYPE
    SYNTAX  TimeTicks
    ACCESS  read-only
    STATUS  mandatory
    DESCRIPTION
        "Time of the last change in the Endpoint table."
    ::= { ipadEndpoint 4 }

-- ipadUser section
-- contains the User table

ipadUserTable    OBJECT-TYPE
    SYNTAX  SEQUENCE OF IpadUserTableEntry
    ACCESS  not-accessible
    STATUS  optional
    DESCRIPTION
        "Table of user selected parameters."
    ::= { ipadUser 1 }

ipadUserTableEntry    OBJECT-TYPE
    SYNTAX  IpadUserTableEntry
    ACCESS  not-accessible
    STATUS  mandatory
    DESCRIPTION
        "An entry in the ipad user table."
    INDEX   { ipadUserIndex }
    ::= { ipadUserTable 1 }

IpadUserTableEntry ::=
    SEQUENCE
    {
    ipadUserIndex               INTEGER,
    ipadUserFilterByDLCI        INTEGER,
    ipadUserService             INTEGER,
    ipadUserDLCI                INTEGER,
    ipadUserFilterByIPAddress   INTEGER,
    ipadUserIPAddress           IpAddress,
    ipadUserIPMask              IpAddress,
    ipadUserFilterByIPPort      INTEGER,
    ipadUserIPPort              INTEGER,
    ipadUserTxAlmThreshold      INTEGER,
    ipadUserTxAlmAlarm          INTEGER
    }

ipadUserIndex    OBJECT-TYPE
    SYNTAX  INTEGER
    ACCESS  read-only
    STATUS  mandatory
    DESCRIPTION
        "Index into the ipad user table."
    ::= { ipadUserTableEntry 1 }

ipadUserFilterByDLCI    OBJECT-TYPE
    SYNTAX  INTEGER
    {
    disabled(1),
    enabled(2)
    }
    ACCESS  read-write
    STATUS  mandatory
    DESCRIPTION
        "Enables Service+DLCI filtering for this user statistic."
    ::= { ipadUserTableEntry 2 }

ipadUserService    OBJECT-TYPE
    SYNTAX  INTEGER
    ACCESS  read-write
    STATUS  mandatory
    DESCRIPTION
        "Specifies the service for this user type; identifies an entry in the
        ipad DLCI table when combined with ipadUserDLCI.  Meaningful when 
        ipadUserFilterByDLCI is enabled.  Meaningless when collecting
        PPP statistics."
    ::= { ipadUserTableEntry 3 }
    
ipadUserDLCI    OBJECT-TYPE
    SYNTAX  INTEGER
    ACCESS  read-write
    STATUS  mandatory
    DESCRIPTION
        "Specifies the DLCI for this user type; identifies an entry in the
        ipad DLCI table when combined with ipadUserService.   Meaningful when 
        ipadUserFilterByDLCI is enabled.  Meaningless when collecting
        PPP statistics."
    ::= { ipadUserTableEntry 4 }

ipadUserFilterByIPAddress   OBJECT-TYPE
    SYNTAX  INTEGER
    {
    disabled(1),
    enabled(2)
    }
    ACCESS  read-write
    STATUS  mandatory
    DESCRIPTION
        "Enables IP address filtering for this user statistic.  A
        packet is counted towards the user statistics if the
        result of a bitwise-and of an IP address in a transmitted
        packet with ipadUserIPMask equals ipadUserIPAddress."
    ::= { ipadUserTableEntry 5 }

ipadUserIPAddress    OBJECT-TYPE
    SYNTAX  IpAddress
    ACCESS  read-write
    STATUS  mandatory
    DESCRIPTION
        "Specifies the IP address for this user type." 
    ::= { ipadUserTableEntry 6 }
    
ipadUserIPMask          OBJECT-TYPE
    SYNTAX  IpAddress
    ACCESS  read-write
    STATUS  mandatory
    DESCRIPTION
        "Specifies the IP address mask for this user type."
    ::= { ipadUserTableEntry 7 }

ipadUserFilterByIPPort    OBJECT-TYPE
    SYNTAX  INTEGER
    {
    disabled(1),
    enabled(2)
    }
    ACCESS  read-write
    STATUS  mandatory
    DESCRIPTION
        "Enables IP Port filtering for this user statistic."
    ::= { ipadUserTableEntry 8 }

ipadUserIPPort          OBJECT-TYPE
    SYNTAX  INTEGER
    {
    rje(5),
    echo(7),
    systat(11),
    qotd(17),
    ftpdata(20),
    ftp(21),
    telnet(23),
    smtp(25),
    msgauth(31),
    time(37),
    nameserver(42),
    domain(53),
    sqlnet(66),
    tftp(69),
    gopher(70),
    finger(79),
    http(80),
    kerberos(88),
    npp(92),
    hostname(101),
    rtelnet(107),
    pop2(109),
    pop3(110),
    sunrpc(111),
    auth(113),
    nntp(119),
    netbiosns(137),
    netbiosdgm(138),
    netbiosssn(139),
    sgmp(153),
    snmp(161),
    snmptrap(162),
    cmipman(163),
    cmipagent(164),
    send(169),
    bgp(179),
    irc(194),
    atrtmp(201),
    atnbp(202),
    atecho(204),
    atzis(206),
    ipx(213),
    netcp(395),
    netwareip(396),
    snpp(444),
    povray(494),
    netwall(533),
    uucp(540),
    uucprlogin(541),
    ipcserver(600),
    kerberosadm(749)
    }
    ACCESS  read-write
    STATUS  mandatory
    DESCRIPTION
        "Specifies the IP port for this user type."
    ::= { ipadUserTableEntry 9 }
    
ipadUserTxAlmThreshold    OBJECT-TYPE
    SYNTAX  INTEGER
    ACCESS  read-write
    STATUS  mandatory
    DESCRIPTION     
        "Sets the tx throughput alarm threshold in 
        octets per second.  Setting this field to 0 
        disables the alarm."
    ::= { ipadUserTableEntry 10 }

ipadUserTxAlmAlarm    OBJECT-TYPE
    SYNTAX  INTEGER
    {
    other(1),
    noAlarm(2),
    thresholdExceeded(3)
    }
    ACCESS  read-only
    STATUS  mandatory
    DESCRIPTION
        "Reports if the tx throughput threshold has been exceeded."
    ::= { ipadUserTableEntry 11 }

ipadUserIPStatTimeRemaining OBJECT-TYPE
    SYNTAX  INTEGER
    ACCESS  read-write
    STATUS  mandatory
    DESCRIPTION
        "Specifies seconds until the next IP TopN report is generated."
    ::= { ipadUser 2 }

ipadUserIPStatTimeDuration OBJECT-TYPE
    SYNTAX  INTEGER
    ACCESS  read-only
    STATUS  mandatory
    DESCRIPTION
        "The value of TimeRemaining when TimeRemaining was last set.  Indicates
         the number of seconds that the next IP TopN report will cover."
    ::= { ipadUser 3 }
    
ipadUserIPStatStartTime OBJECT-TYPE
    SYNTAX   TimeTicks
    ACCESS   read-only
    STATUS   mandatory
    DESCRIPTION
        "The value of SysUpTime when TimeRemaining was last set."
    ::= { ipadUser 4 }
    
ipadUserIPStatRequestedReportSize OBJECT-TYPE
    SYNTAX  INTEGER
    ACCESS  read-write
    STATUS  mandatory
    DESCRIPTION
        "Determines the requested maximum number of entries in the 
        topN report." 
    ::= { ipadUser 5 }

ipadUserIPStatGrantedReportSize OBJECT-TYPE
    SYNTAX  INTEGER
    ACCESS  read-only
    STATUS  mandatory
    DESCRIPTION
        "Determines the granted number of entries in the 
        topN report.  This is by definition less than or equal
        to requested report size." 
    ::= { ipadUser 6 }

ipadUserIPStatReportNumber OBJECT-TYPE
    SYNTAX  INTEGER
    ACCESS  read-only
    STATUS  mandatory
    DESCRIPTION
        "Specifies the number of reports that have been generated.
        This value resets to zero when the unit is restarted."
    ::= { ipadUser 7 }    

ipadUserIPStatDiscardType OBJECT-TYPE
    SYNTAX  INTEGER
    {
    byTime(1),
    byFrames(2),
    byOctets(3)
    }
    ACCESS  read-write
    STATUS  mandatory
    DESCRIPTION
        "The internal table used to track TopN statistics is
        finite in size.  On the condition when the internal table
        is full and a new IP address is encountered, an element
        already existing in the table must be removed.  This
        variable determines the manner of selection.  Writing
        byTime(1) will cause the entry with the least recent
        frame to be discarded.  That is, all other entries in the
        table will have transmitted or received at least one packet
        more recently.  Writing byFrames(2) will select the entry
        with the fewest transmitted or received frames.  Writing
        byOctets(3) will select the entry with the fewest transmitted
        or received octets.  The default is byTime(1)."
    ::= { ipadUser 8 }

-- IPAD PPP section
-- This section contains the IPAD PPP configuration and statistics tables

ipadPPPCfgTable    OBJECT-TYPE
    SYNTAX  SEQUENCE OF IpadPPPCfgTableEntry
    ACCESS  not-accessible
    STATUS  optional
    DESCRIPTION
        "The ipad PPP configuration table."
    ::= { ipadPPP 1 }

ipadPPPCfgTableEntry    OBJECT-TYPE
    SYNTAX  IpadPPPCfgTableEntry
    ACCESS  not-accessible
    STATUS  mandatory
    DESCRIPTION
        "An entry in the ipad PPP configuration table."
    INDEX   { ipadPPPCfgService }
    ::= { ipadPPPCfgTable 1 }

IpadPPPCfgTableEntry ::=
    SEQUENCE
    {
    ipadPPPCfgService               INTEGER,
    ipadPPPCfgDialMode              INTEGER,
    ipadPPPCfgInactivityTimer       INTEGER,
    ipadPPPCfgNegotiationInit       INTEGER,
    ipadPPPCfgMRU                   INTEGER,
    ipadPPPCfgACCM                  INTEGER,
    ipadPPPCfgNegMRU                INTEGER,
    ipadPPPCfgNegACCM               INTEGER,
    ipadPPPCfgNegMagic              INTEGER,
    ipadPPPCfgNegCompression        INTEGER,
    ipadPPPCfgNegAddress            INTEGER,
    ipadPPPCfgNegPAP                INTEGER,
    ipadPPPCfgNegCHAP               INTEGER,
    ipadPPPCfgAllowPAP              INTEGER,
    ipadPPPCfgAllowCHAP             INTEGER,
    ipadPPPCfgPAPUsername           DisplayString,
    ipadPPPCfgPAPPassword           DisplayString,
    ipadPPPCfgCHAPUsername          DisplayString,
    ipadPPPCfgCHAPSecret            DisplayString,
    ipadPPPCfgPortIpAddress         IpAddress,
    ipadPPPCfgPeerIpAddress         IpAddress,
    ipadPPPCfgNegIpAddress          INTEGER,
    ipadPPPCfgNegIPCPCompression    INTEGER,
    ipadPPPCfgSubnetMask            IpAddress,
    ipadPPPCfgAuthChallengeInterval INTEGER
    }

ipadPPPCfgService     OBJECT-TYPE
    SYNTAX  INTEGER
    ACCESS  read-only
    STATUS  mandatory
    DESCRIPTION
        "The index into the PPP configuration table;
        an entry in the ipad service table."
    ::= { ipadPPPCfgTableEntry 1 }

ipadPPPCfgDialMode    OBJECT-TYPE
    SYNTAX  INTEGER
    {
    other(1),
    direct(2),
    dialup(3),
    demanddial(4)
    }
    ACCESS  read-write
    STATUS  mandatory
    DESCRIPTION
        "Determines the permancency of a communications connection."
    ::= { ipadPPPCfgTableEntry 2 }

ipadPPPCfgInactivityTimer    OBJECT-TYPE
    SYNTAX  INTEGER
    ACCESS  read-write
    STATUS  mandatory
    DESCRIPTION
        "Determines when a dial-up or demand-dial connection will be
        disconnected due to inactivity in both directions.  When this
        parameter is set to zero then the timer is disabled."
    ::= { ipadPPPCfgTableEntry 3 }

ipadPPPCfgNegotiationInit    OBJECT-TYPE
    SYNTAX  INTEGER
    {
    other(1),
    no(2),
    yes(3)
    }
    ACCESS  read-write
    STATUS  mandatory
    DESCRIPTION
        "Determines if the port waits for the other end to initiate
        parameter negotiations."
    ::= { ipadPPPCfgTableEntry 4 }

ipadPPPCfgMRU    OBJECT-TYPE
    SYNTAX  INTEGER
    ACCESS  read-write
    STATUS  mandatory
    DESCRIPTION
        "The maximum receive unit the interface will accept.  Valid values
        are in the range 128 - 4096, default is 1500."
    ::= { ipadPPPCfgTableEntry 5 }

ipadPPPCfgACCM    OBJECT-TYPE
    SYNTAX  INTEGER
    ACCESS  read-write
    STATUS  mandatory
    DESCRIPTION
        "Sets the async control character map used when generating
        async HDLC frames.  Setting a bit in the map causes the
        corresponding character to be mapped for transparency."
    ::= { ipadPPPCfgTableEntry 6 }

ipadPPPCfgNegMRU    OBJECT-TYPE
    SYNTAX  INTEGER
    {
    other(1),
    no(2),
    yes(3)
    }
    ACCESS  read-write
    STATUS  mandatory
    DESCRIPTION
        "Determines if MRU size is negotiated."
    ::= { ipadPPPCfgTableEntry 7 }

ipadPPPCfgNegACCM    OBJECT-TYPE
    SYNTAX  INTEGER
    {
    other(1),
    no(2),
    yes(3)
    }
    ACCESS  read-write
    STATUS  mandatory
    DESCRIPTION
        "Determines if ACCM is negotiated."
    ::= { ipadPPPCfgTableEntry 8 }

ipadPPPCfgNegMagic    OBJECT-TYPE
    SYNTAX  INTEGER
    {
    other(1),
    no(2),
    yes(3)
    }
    ACCESS  read-write
    STATUS  mandatory
    DESCRIPTION
        "Determines if the magic number is negotiated."
    ::= { ipadPPPCfgTableEntry 9 }

ipadPPPCfgNegCompression    OBJECT-TYPE
    SYNTAX  INTEGER
    {
    other(1),
    no(2),
    yes(3)
    }
    ACCESS  read-write
    STATUS  mandatory
    DESCRIPTION
        "Determines if the PPP protocol header compression is negotiated."
    ::= { ipadPPPCfgTableEntry 10 }

ipadPPPCfgNegAddress    OBJECT-TYPE
    SYNTAX  INTEGER
    {
    other(1),
    no(2),
    yes(3)
    }
    ACCESS  read-write
    STATUS  mandatory
    DESCRIPTION
        "Determines if the PPP HDLC header compression is negotiated."
    ::= { ipadPPPCfgTableEntry 11 }

ipadPPPCfgNegPAP    OBJECT-TYPE
    SYNTAX  INTEGER
    {
    other(1),
    no(2),
    yes(3)
    }
    ACCESS  read-write
    STATUS  mandatory
    DESCRIPTION
        "Determines if PAP is negotiated with the peer when a more secure
        authentication protocol is rejected."
    ::= { ipadPPPCfgTableEntry 12 }

ipadPPPCfgNegCHAP    OBJECT-TYPE
    SYNTAX  INTEGER
    {
    other(1),
    no(2),
    yes(3)
    }
    ACCESS  read-write
    STATUS  mandatory
    DESCRIPTION
        "Determines if CHAP is negotiated with the peer when a more secure
        authentication protocol is rejected."
    ::= { ipadPPPCfgTableEntry 13 }

ipadPPPCfgAllowPAP    OBJECT-TYPE
    SYNTAX  INTEGER
    {
    other(1),
    no(2),
    yes(3)
    }
    ACCESS  read-write
    STATUS  mandatory
    DESCRIPTION
        "Determines if PAP is allowed to be negotiated by the peer."
    ::= { ipadPPPCfgTableEntry 14 }

ipadPPPCfgAllowCHAP    OBJECT-TYPE
    SYNTAX  INTEGER
    {
    other(1),
    no(2),
    yes(3)
    }
    ACCESS  read-write
    STATUS  mandatory
    DESCRIPTION
        "Determines if CHAP is allowed to be negotiated by the peer."
    ::= { ipadPPPCfgTableEntry 15 }

ipadPPPCfgPAPUsername    OBJECT-TYPE
    SYNTAX  DisplayString ( SIZE(0..30) )
    ACCESS  read-write
    STATUS  mandatory
    DESCRIPTION
        "Identification string to determine the user identity."
    ::= { ipadPPPCfgTableEntry 16 }

ipadPPPCfgPAPPassword    OBJECT-TYPE
    SYNTAX  DisplayString ( SIZE(0..30) )
    ACCESS  read-write
    STATUS  mandatory
    DESCRIPTION
        "Password string to validate the user identity."
    ::= { ipadPPPCfgTableEntry 17 }

ipadPPPCfgCHAPUsername    OBJECT-TYPE
    SYNTAX  DisplayString ( SIZE(0..30) )
    ACCESS  read-write
    STATUS  mandatory
    DESCRIPTION
        "Identification string to determine the user identity."
    ::= { ipadPPPCfgTableEntry 18 }

ipadPPPCfgCHAPSecret    OBJECT-TYPE
    SYNTAX  DisplayString ( SIZE(0..30) )
    ACCESS  read-write
    STATUS  mandatory
    DESCRIPTION
        "Password string to validate the user identity."
    ::= { ipadPPPCfgTableEntry 19 }

ipadPPPCfgPortIpAddress    OBJECT-TYPE
    SYNTAX  IpAddress
    ACCESS  read-write
    STATUS  mandatory
    DESCRIPTION
        "Sets the IP address of the unit's port."
    ::= { ipadPPPCfgTableEntry 20 }

ipadPPPCfgPeerIpAddress    OBJECT-TYPE
    SYNTAX  IpAddress
    ACCESS  read-write
    STATUS  mandatory
    DESCRIPTION
        "Sets the IP address of the unit's peer."
    ::= { ipadPPPCfgTableEntry 21 }

ipadPPPCfgNegIpAddress    OBJECT-TYPE
    SYNTAX  INTEGER
    {
    other(1),
    no(2),
    yes(3)
    }
    ACCESS  read-write
    STATUS  mandatory
    DESCRIPTION
        "Determines if IP addresses are dynamically negotiated."
    ::= { ipadPPPCfgTableEntry 22 }

ipadPPPCfgNegIPCPCompression    OBJECT-TYPE
    SYNTAX  INTEGER
    {
    other(1),
    no(2),
    yes(3)
    }
    ACCESS  read-write
    STATUS  mandatory
    DESCRIPTION
        "Determines if Van Jacobson TCPIP header compression is negotiated."
    ::= { ipadPPPCfgTableEntry 23 }
    
ipadPPPCfgSubnetMask    OBJECT-TYPE
    SYNTAX  IpAddress
    ACCESS  read-write
    STATUS  mandatory
    DESCRIPTION
        "Specifies the subnet mask."
    ::= { ipadPPPCfgTableEntry 24 }

ipadPPPCfgAuthChallengeInterval    OBJECT-TYPE
    SYNTAX  INTEGER
    ACCESS  read-write
    STATUS  mandatory
    DESCRIPTION
        "Specifies the authentication challenge interval."
    ::= { ipadPPPCfgTableEntry 25 }

-- PPP PAP association table
-- common to all PPP interfaces

ipadPPPPAPTable    OBJECT-TYPE
    SYNTAX  SEQUENCE OF IpadPPPPAPTableEntry
    ACCESS  not-accessible
    STATUS  optional
    DESCRIPTION
        "Table of PAP authentication parameters."
    ::= { ipadPPP 2 }

ipadPPPPAPTableEntry    OBJECT-TYPE
    SYNTAX  IpadPPPPAPTableEntry
    ACCESS  not-accessible
    STATUS  mandatory
    DESCRIPTION
        "An entry in the ipad PPP PAP table."
    INDEX   { ipadPPPPAPTableIndex }
    ::= { ipadPPPPAPTable 1 }

IpadPPPPAPTableEntry ::=
    SEQUENCE
    {
    ipadPPPPAPTableIndex        INTEGER,
    ipadPPPPAPTableUsername     DisplayString,
    ipadPPPPAPTablePassword     DisplayString
    }

ipadPPPPAPTableIndex    OBJECT-TYPE
    SYNTAX  INTEGER
    ACCESS  read-only
    STATUS  mandatory
    DESCRIPTION
        "The index into the PPP PAP association table."
    ::= { ipadPPPPAPTableEntry 1 }

ipadPPPPAPTableUsername    OBJECT-TYPE
    SYNTAX  DisplayString ( SIZE(0..30) )
    ACCESS  read-write
    STATUS  mandatory
    DESCRIPTION
        "Identification string to identify the user."
    ::= { ipadPPPPAPTableEntry 2 }

ipadPPPPAPTablePassword    OBJECT-TYPE
    SYNTAX  DisplayString ( SIZE(0..30) )
    ACCESS  read-write
    STATUS  mandatory
    DESCRIPTION
        "Password string to validate the user identity."
    ::= { ipadPPPPAPTableEntry 3 }

-- PPP CHAP association table
-- common to all PPP interfaces

ipadPPPCHAPTable    OBJECT-TYPE
    SYNTAX  SEQUENCE OF IpadPPPCHAPTableEntry
    ACCESS  not-accessible
    STATUS  optional
    DESCRIPTION
        "Table of CHAP authentication parameters."
    ::= { ipadPPP 3 }

ipadPPPCHAPTableEntry    OBJECT-TYPE
    SYNTAX  IpadPPPCHAPTableEntry
    ACCESS  not-accessible
    STATUS  mandatory
    DESCRIPTION
        "An entry in the ipad PPP CHAP table."
    INDEX   { ipadPPPCHAPTableIndex }
    ::= { ipadPPPCHAPTable 1 }

IpadPPPCHAPTableEntry ::=
    SEQUENCE
    {
    ipadPPPCHAPTableIndex       INTEGER,
    ipadPPPCHAPTableUsername    DisplayString,
    ipadPPPCHAPTableSecret      DisplayString
    }

ipadPPPCHAPTableIndex    OBJECT-TYPE
    SYNTAX  INTEGER
    ACCESS  read-only
    STATUS  mandatory
    DESCRIPTION
        "The index into the PPP CHAP association table."
    ::= { ipadPPPCHAPTableEntry 1 }

ipadPPPCHAPTableUsername    OBJECT-TYPE
    SYNTAX  DisplayString ( SIZE(0..30) )
    ACCESS  read-write
    STATUS  mandatory
    DESCRIPTION
        "Identification string to identify the user."
    ::= { ipadPPPCHAPTableEntry 2 }

ipadPPPCHAPTableSecret    OBJECT-TYPE
    SYNTAX  DisplayString ( SIZE(0..30) )
    ACCESS  read-write
    STATUS  mandatory
    DESCRIPTION
        "Password string to validate the user identity."
    ::= { ipadPPPCHAPTableEntry 3 }

-- Modem Dialing parameters
-- parameters needed by a port that can connect to a modem

ipadModemDialTable    OBJECT-TYPE
    SYNTAX  SEQUENCE OF IpadModemDialTableEntry
    ACCESS  not-accessible
    STATUS  optional
    DESCRIPTION
        "Table of modem dialing parameters."
    ::= { ipadModem 1 }

ipadModemDialTableEntry    OBJECT-TYPE
    SYNTAX  IpadModemDialTableEntry
    ACCESS  not-accessible
    STATUS  mandatory
    DESCRIPTION
        "An entry in the ipad modem dialing parameters table."
    INDEX   { ipadModemDialTableIndex }
    ::= { ipadModemDialTable 1 }

IpadModemDialTableEntry ::=
    SEQUENCE
    {
    ipadModemDialTableIndex        INTEGER,
    ipadModemDialDataIndex         INTEGER,
    ipadModemDialNumber            DisplayString,
    ipadModemDialAbortTimer        INTEGER,
    ipadModemDialRedialAttempts    INTEGER,
    ipadModemDialDelayBeforeRedial INTEGER,
    ipadModemDialLoginScript       DisplayString,
    ipadModemDialUsername          DisplayString,
    ipadModemDialPassword          DisplayString
    }

ipadModemDialTableIndex    OBJECT-TYPE
    SYNTAX  INTEGER
    {
    supervisor(1),
    network1(2),
    network2(3),
    user1(4),
    user2(5),
    ethernet(6)
    }
    ACCESS  read-only
    STATUS  mandatory
    DESCRIPTION
        "The index into the ipad modem dialing parameters table.
        Equivalent to MIB-II ifIndex."
    ::= { ipadModemDialTableEntry 1 }

ipadModemDialDataIndex    OBJECT-TYPE
    SYNTAX  INTEGER
    ACCESS  read-write
    STATUS  mandatory
    DESCRIPTION
        "An index into the Modem Data Table, which selects a modem."
    ::= { ipadModemDialTableEntry 2 }

ipadModemDialNumber    OBJECT-TYPE
    SYNTAX  DisplayString ( SIZE(0..30) )
    ACCESS  read-write
    STATUS  mandatory
    DESCRIPTION
        "Specifies the telephone number to dial."
    ::= { ipadModemDialTableEntry 3 }

ipadModemDialAbortTimer    OBJECT-TYPE
    SYNTAX  INTEGER
    ACCESS  read-write
    STATUS  mandatory
    DESCRIPTION
        "Aborts a connection attempt if an initialed dial-up
        connection has failed to connect within the specified
        number of seconds.  Range is 1..255."
    ::= { ipadModemDialTableEntry 4 }

ipadModemDialRedialAttempts    OBJECT-TYPE
    SYNTAX  INTEGER
    ACCESS  read-write
    STATUS  mandatory
    DESCRIPTION
        "Determines how many attempts to initiate a dial-up 
        connection after the initial failure.  Range is 0..10."
    ::= { ipadModemDialTableEntry 5 }

ipadModemDialDelayBeforeRedial    OBJECT-TYPE
    SYNTAX  INTEGER
    ACCESS  read-write
    STATUS  mandatory
    DESCRIPTION
        "Specifies the number of seconds to wait before 
        redialing.  Range is 1..255."
    ::= { ipadModemDialTableEntry 6 }

ipadModemDialLoginScript    OBJECT-TYPE
    SYNTAX  DisplayString ( SIZE(0..50) )
    ACCESS  read-write
    STATUS  mandatory
    DESCRIPTION
        "Script string interpreted after a dial-up 
        connection is first established."
    ::= { ipadModemDialTableEntry 7 }

ipadModemDialUsername    OBJECT-TYPE
    SYNTAX  DisplayString ( SIZE(0..30) )
    ACCESS  read-write
    STATUS  mandatory
    DESCRIPTION
        "Identification string to determine the user identity."
    ::= { ipadModemDialTableEntry 8 }

ipadModemDialPassword    OBJECT-TYPE
    SYNTAX  DisplayString ( SIZE(0..30) )
    ACCESS  read-write
    STATUS  mandatory
    DESCRIPTION
        "Password string to validate the user identity."
    ::= { ipadModemDialTableEntry 9 }

-- Modem Database parameters
-- modem characterization parameters, global to all modem interfaces.

ipadModemDataTable    OBJECT-TYPE
    SYNTAX  SEQUENCE OF IpadModemDataTableEntry
    ACCESS  not-accessible
    STATUS  optional
    DESCRIPTION
        "Table of modem database parameters."
    ::= { ipadModem 2 }

ipadModemDataTableEntry    OBJECT-TYPE
    SYNTAX  IpadModemDataTableEntry
    ACCESS  not-accessible
    STATUS  mandatory
    DESCRIPTION
        "An entry in the ipad modem database parameters table."
    INDEX   { ipadModemDataTableIndex }
    ::= { ipadModemDataTable 1 }

IpadModemDataTableEntry ::=
    SEQUENCE
    {
    ipadModemDataTableIndex     INTEGER,
    ipadModemDataModemName      DisplayString,
    ipadModemDataSetupScript    DisplayString,
    ipadModemDataDialingScript  DisplayString,
    ipadModemDataAnswerScript   DisplayString,
    ipadModemDataHangupScript   DisplayString
    }

ipadModemDataTableIndex    OBJECT-TYPE
    SYNTAX  INTEGER
    ACCESS  read-only
    STATUS  mandatory
    DESCRIPTION
        "The index into the ipad modem database parameters table."
    ::= { ipadModemDataTableEntry 1 }

ipadModemDataModemName    OBJECT-TYPE
    SYNTAX  DisplayString ( SIZE(0..10) )
    ACCESS  read-write
    STATUS  mandatory
    DESCRIPTION
        "Identification string for the modem database."
    ::= { ipadModemDataTableEntry 2 }

ipadModemDataSetupScript    OBJECT-TYPE
    SYNTAX  DisplayString ( SIZE(0..50) )
    ACCESS  read-write
    STATUS  mandatory
    DESCRIPTION
        "Script interpreted when a modem port is first started."
    ::= { ipadModemDataTableEntry 3 }

ipadModemDataDialingScript    OBJECT-TYPE
    SYNTAX  DisplayString ( SIZE(0..50) )
    ACCESS  read-write
    STATUS  mandatory
    DESCRIPTION
        "Script interpreted when a dial-up connection 
        is initiated."
    ::= { ipadModemDataTableEntry 4 }

ipadModemDataAnswerScript    OBJECT-TYPE
    SYNTAX  DisplayString ( SIZE(0..50) )
    ACCESS  read-write
    STATUS  mandatory
    DESCRIPTION
        "Script interpreted when a modem port is waiting 
        for an incoming call."
    ::= { ipadModemDataTableEntry 5 }

ipadModemDataHangupScript    OBJECT-TYPE
    SYNTAX  DisplayString ( SIZE(0..50) )
    ACCESS  read-write
    STATUS  mandatory
    DESCRIPTION
        "Script interpreted when a dial-up connection 
        is no longer needed."
    ::= { ipadModemDataTableEntry 6 }

-- ipadSvcAware section
-- port statistics table

ipadFrPortStatsTable    OBJECT-TYPE
    SYNTAX  SEQUENCE OF IpadFrPortStatsEntry
    ACCESS  not-accessible
    STATUS  optional
    DESCRIPTION
        "Port statistics."
    ::= { ipadSvcAware 1 }

ipadFrPortStatsEntry    OBJECT-TYPE
    SYNTAX  IpadFrPortStatsEntry
    ACCESS  not-accessible
    STATUS  mandatory
    DESCRIPTION
        "An entry in the service aware ports statistics table."
    INDEX    { ipadFrPortStatsService, ipadFrPortStatsPeriod }
    ::= { ipadFrPortStatsTable 1 }

IpadFrPortStatsEntry ::=
    SEQUENCE
    {
    ipadFrPortStatsService         INTEGER,
    ipadFrPortStatsPeriod          INTEGER,
    ipadFrPortStatsTxFrames        INTEGER,
    ipadFrPortStatsRxFrames        INTEGER,
    ipadFrPortStatsTxOctets        INTEGER,
    ipadFrPortStatsRxOctets        INTEGER,
    ipadFrPortStatsTxMgmtFrames    INTEGER,
    ipadFrPortStatsRxMgmtFrames    INTEGER,
    ipadFrPortStatsTxMgmtOctets    INTEGER,
    ipadFrPortStatsRxMgmtOctets    INTEGER,
    ipadFrPortStatsRxFECN          INTEGER,
    ipadFrPortStatsRxBECN          INTEGER,
    ipadFrPortStatsRxInvalid       INTEGER,
    ipadFrPortStatsTxStatInq       INTEGER,
    ipadFrPortStatsRxStatInq       INTEGER,
    ipadFrPortStatsTxStatResp      INTEGER,
    ipadFrPortStatsRxStatResp      INTEGER,
    ipadFrPortStatsRxInvLMI        INTEGER,
    ipadFrPortStatsPeak            INTEGER,
    ipadFrPortStatsAverage         INTEGER
    }

ipadFrPortStatsService    OBJECT-TYPE
    SYNTAX  INTEGER
    ACCESS  read-only
    STATUS  mandatory
    DESCRIPTION
        "Port index in the ipadFrPortStats table;
        an entry in the ipad service table."
    ::= { ipadFrPortStatsEntry 1 }

ipadFrPortStatsPeriod    OBJECT-TYPE
    SYNTAX  INTEGER
    {
    portStatsSummary(1),
    portStatsCurrent(2),

    portStatsperiod1(3),
    portStatsperiod2(4),
    portStatsperiod3(5),
    portStatsperiod4(6),
    portStatsperiod5(7),
    portStatsperiod6(8),
    portStatsperiod7(9),
    portStatsperiod8(10),
    portStatsperiod9(11),

    portStatsperiod10(12),
    portStatsperiod11(13),
    portStatsperiod12(14),
    portStatsperiod13(15),
    portStatsperiod14(16),
    portStatsperiod15(17),
    portStatsperiod16(18),
    portStatsperiod17(19),
    portStatsperiod18(20),
    portStatsperiod19(21),

    portStatsperiod20(22),
    portStatsperiod21(23),
    portStatsperiod22(24),
    portStatsperiod23(25),
    portStatsperiod24(26),
    portStatsperiod25(27),
    portStatsperiod26(28),
    portStatsperiod27(29),
    portStatsperiod28(30),
    portStatsperiod29(31),

    portStatsperiod30(32),
    portStatsperiod31(33),
    portStatsperiod32(34),
    portStatsperiod33(35),
    portStatsperiod34(36),
    portStatsperiod35(37),
    portStatsperiod36(38),
    portStatsperiod37(39),
    portStatsperiod38(40),
    portStatsperiod39(41),

    portStatsperiod40(42),
    portStatsperiod41(43),
    portStatsperiod42(44),
    portStatsperiod43(45),
    portStatsperiod44(46),
    portStatsperiod45(47),
    portStatsperiod46(48),
    portStatsperiod47(49),
    portStatsperiod48(50),
    portStatsperiod49(51),

    portStatsperiod50(52),
    portStatsperiod51(53),
    portStatsperiod52(54),
    portStatsperiod53(55),
    portStatsperiod54(56),
    portStatsperiod55(57),
    portStatsperiod56(58),
    portStatsperiod57(59),
    portStatsperiod58(60),
    portStatsperiod59(61),

    portStatsperiod60(62),
    portStatsperiod61(63),
    portStatsperiod62(64),
    portStatsperiod63(65),
    portStatsperiod64(66),
    portStatsperiod65(67),
    portStatsperiod66(68),
    portStatsperiod67(69),
    portStatsperiod68(70),
    portStatsperiod69(71),

    portStatsperiod70(72),
    portStatsperiod71(73),
    portStatsperiod72(74),
    portStatsperiod73(75),
    portStatsperiod74(76),
    portStatsperiod75(77),
    portStatsperiod76(78),
    portStatsperiod77(79),
    portStatsperiod78(80),
    portStatsperiod79(81),

    portStatsperiod80(82),
    portStatsperiod81(83),
    portStatsperiod82(84),
    portStatsperiod83(85),
    portStatsperiod84(86),
    portStatsperiod85(87),
    portStatsperiod86(88),
    portStatsperiod87(89),
    portStatsperiod88(90),
    portStatsperiod89(91),

    portStatsperiod90(92),
    portStatsperiod91(93),
    portStatsperiod92(94),
    portStatsperiod93(95),
    portStatsperiod94(96),
    portStatsperiod95(97),
    portStatsperiod96(98)
    }
    ACCESS  read-only
    STATUS  mandatory
    DESCRIPTION
        "The index into the port stats 24-hour table."
    ::= { ipadFrPortStatsEntry 2 }

ipadFrPortStatsTxFrames    OBJECT-TYPE
    SYNTAX  INTEGER
    ACCESS  read-only
    STATUS  mandatory
    DESCRIPTION
        "Number of transmitted frames for the period."
    ::= { ipadFrPortStatsEntry 3 }

ipadFrPortStatsRxFrames    OBJECT-TYPE
    SYNTAX  INTEGER
    ACCESS  read-only
    STATUS  mandatory
    DESCRIPTION
        "Number of received frames for the period."
    ::= { ipadFrPortStatsEntry 4 }

ipadFrPortStatsTxOctets    OBJECT-TYPE
    SYNTAX  INTEGER
    ACCESS  read-only
    STATUS  mandatory
    DESCRIPTION
        "Number of transmitted octets for the period."
    ::= { ipadFrPortStatsEntry 5 }

ipadFrPortStatsRxOctets    OBJECT-TYPE
    SYNTAX  INTEGER
    ACCESS  read-only
    STATUS  mandatory
    DESCRIPTION
        "Number of received octets for the period."
    ::= { ipadFrPortStatsEntry 6 }

ipadFrPortStatsTxMgmtFrames    OBJECT-TYPE
    SYNTAX  INTEGER
    ACCESS  read-only
    STATUS  mandatory
    DESCRIPTION
        "Number of transmitted management frames for the period."
    ::= { ipadFrPortStatsEntry 7 }

ipadFrPortStatsRxMgmtFrames    OBJECT-TYPE
    SYNTAX  INTEGER
    ACCESS  read-only
    STATUS  mandatory
    DESCRIPTION
        "Number of received management frames for the period."
    ::= { ipadFrPortStatsEntry 8 }

ipadFrPortStatsTxMgmtOctets    OBJECT-TYPE
    SYNTAX  INTEGER
    ACCESS  read-only
    STATUS  mandatory
    DESCRIPTION
        "Number of transmitted management octets for the period."
    ::= { ipadFrPortStatsEntry 9 }

ipadFrPortStatsRxMgmtOctets    OBJECT-TYPE
    SYNTAX  INTEGER
    ACCESS  read-only
    STATUS  mandatory
    DESCRIPTION
        "Number of received management octets for the period."
    ::= { ipadFrPortStatsEntry 10 }

ipadFrPortStatsRxFECN    OBJECT-TYPE
    SYNTAX  INTEGER
    ACCESS  read-only
    STATUS  mandatory
    DESCRIPTION
        "Number of received frames with FECN set for the period."
    ::= { ipadFrPortStatsEntry 11 }

ipadFrPortStatsRxBECN    OBJECT-TYPE
    SYNTAX  INTEGER
    ACCESS  read-only
    STATUS  mandatory
    DESCRIPTION
        "Number of received frames with BECN set for the period."
    ::= { ipadFrPortStatsEntry 12 }

ipadFrPortStatsRxInvalid    OBJECT-TYPE
    SYNTAX  INTEGER
    ACCESS  read-only
    STATUS  mandatory
    DESCRIPTION
        "Number of invalid received frames for the period."
    ::= { ipadFrPortStatsEntry 13 }

ipadFrPortStatsTxStatInq    OBJECT-TYPE
    SYNTAX  INTEGER
    ACCESS  read-only
    STATUS  mandatory
    DESCRIPTION
        "Number of transmitted status inquiry frames for the period."
    ::= { ipadFrPortStatsEntry 14 }

ipadFrPortStatsRxStatInq    OBJECT-TYPE
    SYNTAX  INTEGER
    ACCESS  read-only
    STATUS  mandatory
    DESCRIPTION
        "Number of received status inquiry frames for the period."
    ::= { ipadFrPortStatsEntry 15 }

ipadFrPortStatsTxStatResp    OBJECT-TYPE
    SYNTAX  INTEGER
    ACCESS  read-only
    STATUS  mandatory
    DESCRIPTION
        "Number of transmitted status response frames for the period."
    ::= { ipadFrPortStatsEntry 16 }

ipadFrPortStatsRxStatResp    OBJECT-TYPE
    SYNTAX  INTEGER
    ACCESS  read-only
    STATUS  mandatory
    DESCRIPTION
        "Number of received status response frames for the period."
    ::= { ipadFrPortStatsEntry 17 }

ipadFrPortStatsRxInvLMI    OBJECT-TYPE
    SYNTAX  INTEGER
    ACCESS  read-only
    STATUS  mandatory
    DESCRIPTION
        "Number of received frames with an invalid LMI for the period."
    ::= { ipadFrPortStatsEntry 18 }

ipadFrPortStatsPeak    OBJECT-TYPE
    SYNTAX  INTEGER
    ACCESS  read-only
    STATUS  mandatory
    DESCRIPTION
        "Peak throughput rate for the period (in octets/second)."
    ::= { ipadFrPortStatsEntry 19 }

ipadFrPortStatsAverage    OBJECT-TYPE
    SYNTAX  INTEGER
    ACCESS  read-only
    STATUS  mandatory
    DESCRIPTION
        "Average throughput rate for the period (in octets/second)."    
    ::= { ipadFrPortStatsEntry 20 }

-- DLCI statistics table

ipadDLCIstatsTable    OBJECT-TYPE
    SYNTAX  SEQUENCE OF IpadDLCIstatsEntry
    ACCESS  not-accessible
    STATUS  optional
    DESCRIPTION
        "Port statistics."
    ::= { ipadSvcAware 2 }

ipadDLCIstatsEntry    OBJECT-TYPE
    SYNTAX  IpadDLCIstatsEntry
    ACCESS  not-accessible
    STATUS  mandatory
    DESCRIPTION
        "An entry in the service aware DLCI statistics table."
    INDEX    { ipadDLCIstatsService, ipadDLCIstatsDLCI, ipadDLCIstatsPeriod }
    ::= { ipadDLCIstatsTable 1 }

IpadDLCIstatsEntry ::=
    SEQUENCE
    {
    ipadDLCIstatsService            INTEGER,
    ipadDLCIstatsDLCI               INTEGER,
    ipadDLCIstatsPeriod             INTEGER,
    ipadDLCIstatsTxFrames           INTEGER,
    ipadDLCIstatsRxFrames           INTEGER,
    ipadDLCIstatsTxOctets           INTEGER,
    ipadDLCIstatsRxOctets           INTEGER,
    ipadDLCIstatsRxFECN             INTEGER,
    ipadDLCIstatsRxBECN             INTEGER,
    ipadDLCIstatsRxDE               INTEGER,
    ipadDLCIstatsTxExcessCIR        INTEGER,
    ipadDLCIstatsTxExcessBe         INTEGER,
    ipadDLCIstatsTxMgmtFrames       INTEGER,
    ipadDLCIstatsRxMgmtFrames       INTEGER,
    ipadDLCIstatsTxMgmtOctets       INTEGER,
    ipadDLCIstatsRxMgmtOctets       INTEGER,
    ipadDLCIstatsPeak               INTEGER,
    ipadDLCIstatsAverage            INTEGER,
    ipadDLCIstatsDelayPeak          INTEGER,
    ipadDLCIstatsDelayAverage       INTEGER,
    ipadDLCIstatsRoundTripTimeouts  INTEGER,
    ipadDLCIstatsUAS                INTEGER
    }

ipadDLCIstatsService    OBJECT-TYPE
    SYNTAX  INTEGER
    ACCESS  read-only
    STATUS  mandatory
    DESCRIPTION
        "The service index for the service aware stats table; identifies an
        entry in the ipad DLCI table when combined with ipadDLCIstatsDLCI."
    ::= { ipadDLCIstatsEntry 1 }    
    
ipadDLCIstatsDLCI    OBJECT-TYPE
    SYNTAX  INTEGER
    ACCESS  read-only
    STATUS  mandatory
    DESCRIPTION
        "The DLCI index for the service aware stats table; identifies an
        entry in the ipad DLCI table when combined with ipadDLCIstatsService."
    ::= { ipadDLCIstatsEntry 2 }    

ipadDLCIstatsPeriod    OBJECT-TYPE
    SYNTAX  INTEGER
    {
    dlciStatsSummary(1),
    dlciStatsCurrent(2),

    dlciStatsperiod1(3),
    dlciStatsperiod2(4),
    dlciStatsperiod3(5),
    dlciStatsperiod4(6),
    dlciStatsperiod5(7),
    dlciStatsperiod6(8),
    dlciStatsperiod7(9),
    dlciStatsperiod8(10),
    dlciStatsperiod9(11),

    dlciStatsperiod10(12),
    dlciStatsperiod11(13),
    dlciStatsperiod12(14),
    dlciStatsperiod13(15),
    dlciStatsperiod14(16),
    dlciStatsperiod15(17),
    dlciStatsperiod16(18),
    dlciStatsperiod17(19),
    dlciStatsperiod18(20),
    dlciStatsperiod19(21),

    dlciStatsperiod20(22),
    dlciStatsperiod21(23),
    dlciStatsperiod22(24),
    dlciStatsperiod23(25),
    dlciStatsperiod24(26),
    dlciStatsperiod25(27),
    dlciStatsperiod26(28),
    dlciStatsperiod27(29),
    dlciStatsperiod28(30),
    dlciStatsperiod29(31),

    dlciStatsperiod30(32),
    dlciStatsperiod31(33),
    dlciStatsperiod32(34),
    dlciStatsperiod33(35),
    dlciStatsperiod34(36),
    dlciStatsperiod35(37),
    dlciStatsperiod36(38),
    dlciStatsperiod37(39),
    dlciStatsperiod38(40),
    dlciStatsperiod39(41),

    dlciStatsperiod40(42),
    dlciStatsperiod41(43),
    dlciStatsperiod42(44),
    dlciStatsperiod43(45),
    dlciStatsperiod44(46),
    dlciStatsperiod45(47),
    dlciStatsperiod46(48),
    dlciStatsperiod47(49),
    dlciStatsperiod48(50),
    dlciStatsperiod49(51),

    dlciStatsperiod50(52),
    dlciStatsperiod51(53),
    dlciStatsperiod52(54),
    dlciStatsperiod53(55),
    dlciStatsperiod54(56),
    dlciStatsperiod55(57),
    dlciStatsperiod56(58),
    dlciStatsperiod57(59),
    dlciStatsperiod58(60),
    dlciStatsperiod59(61),

    dlciStatsperiod60(62),
    dlciStatsperiod61(63),
    dlciStatsperiod62(64),
    dlciStatsperiod63(65),
    dlciStatsperiod64(66),
    dlciStatsperiod65(67),
    dlciStatsperiod66(68),
    dlciStatsperiod67(69),
    dlciStatsperiod68(70),
    dlciStatsperiod69(71),

    dlciStatsperiod70(72),
    dlciStatsperiod71(73),
    dlciStatsperiod72(74),
    dlciStatsperiod73(75),
    dlciStatsperiod74(76),
    dlciStatsperiod75(77),
    dlciStatsperiod76(78),
    dlciStatsperiod77(79),
    dlciStatsperiod78(80),
    dlciStatsperiod79(81),

    dlciStatsperiod80(82),
    dlciStatsperiod81(83),
    dlciStatsperiod82(84),
    dlciStatsperiod83(85),
    dlciStatsperiod84(86),
    dlciStatsperiod85(87),
    dlciStatsperiod86(88),
    dlciStatsperiod87(89),
    dlciStatsperiod88(90),
    dlciStatsperiod89(91),

    dlciStatsperiod90(92),
    dlciStatsperiod91(93),
    dlciStatsperiod92(94),
    dlciStatsperiod93(95),
    dlciStatsperiod94(96),
    dlciStatsperiod95(97),
    dlciStatsperiod96(98)
    }
    ACCESS  read-only
    STATUS  mandatory
    DESCRIPTION
        "The index into the DLCI stats 24-hour table."
    ::= { ipadDLCIstatsEntry 3 }    

ipadDLCIstatsTxFrames    OBJECT-TYPE
    SYNTAX  INTEGER
    ACCESS  read-only
    STATUS  mandatory
    DESCRIPTION
        "The number of transmitted frames for the period."
    ::= { ipadDLCIstatsEntry 4 }    

ipadDLCIstatsRxFrames    OBJECT-TYPE
    SYNTAX  INTEGER
    ACCESS  read-only
    STATUS  mandatory
    DESCRIPTION
        "The number of received frames for the period."
    ::= { ipadDLCIstatsEntry 5 }

ipadDLCIstatsTxOctets    OBJECT-TYPE
    SYNTAX  INTEGER
    ACCESS  read-only
    STATUS  mandatory
    DESCRIPTION
        "The number of transmitted octets for the period."
    ::= { ipadDLCIstatsEntry 6 }    

ipadDLCIstatsRxOctets    OBJECT-TYPE
    SYNTAX  INTEGER
    ACCESS  read-only
    STATUS  mandatory
    DESCRIPTION
        "The number of received octets for the period."
    ::= { ipadDLCIstatsEntry 7 }    

ipadDLCIstatsRxFECN    OBJECT-TYPE
    SYNTAX  INTEGER
    ACCESS  read-only
    STATUS  mandatory
    DESCRIPTION
        "The number of received frames with FECN set for the period."
    ::= { ipadDLCIstatsEntry 8 }    

ipadDLCIstatsRxBECN    OBJECT-TYPE
    SYNTAX  INTEGER
    ACCESS  read-only
    STATUS  mandatory
    DESCRIPTION
        "The number of received frames with BECN set for the period."
    ::= { ipadDLCIstatsEntry 9 }    

ipadDLCIstatsRxDE    OBJECT-TYPE
    SYNTAX  INTEGER
    ACCESS  read-only
    STATUS  mandatory
    DESCRIPTION
        "The number of received frames with DE bit set for the period."
    ::= { ipadDLCIstatsEntry 10 }    

ipadDLCIstatsTxExcessCIR    OBJECT-TYPE
    SYNTAX  INTEGER
    ACCESS  read-only
    STATUS  mandatory
    DESCRIPTION
        "The number of transmitted octets in excess of CIR for the period."
    ::= { ipadDLCIstatsEntry 11 }    

ipadDLCIstatsTxExcessBe    OBJECT-TYPE
    SYNTAX  INTEGER
    ACCESS  read-only
    STATUS  mandatory
    DESCRIPTION
        "The number of transmitted octets in excess of Be for the period."
    ::= { ipadDLCIstatsEntry 12 }    

ipadDLCIstatsTxMgmtFrames    OBJECT-TYPE
    SYNTAX  INTEGER
    ACCESS  read-only
    STATUS  mandatory
    DESCRIPTION
        "The number of transmitted management frames for the period."
    ::= { ipadDLCIstatsEntry 13 }    

ipadDLCIstatsRxMgmtFrames    OBJECT-TYPE
    SYNTAX  INTEGER
    ACCESS  read-only
    STATUS  mandatory
    DESCRIPTION
        "The number of received management frames for the period."
    ::= { ipadDLCIstatsEntry 14 }    

ipadDLCIstatsTxMgmtOctets    OBJECT-TYPE
    SYNTAX  INTEGER
    ACCESS  read-only
    STATUS  mandatory
    DESCRIPTION
        "The number of transmitted management octets for the period."
    ::= { ipadDLCIstatsEntry 15 }    

ipadDLCIstatsRxMgmtOctets    OBJECT-TYPE
    SYNTAX  INTEGER
    ACCESS  read-only
    STATUS  mandatory
    DESCRIPTION
        "The number of received management octets for the period."
    ::= { ipadDLCIstatsEntry 16 }    

ipadDLCIstatsPeak    OBJECT-TYPE
    SYNTAX  INTEGER
    ACCESS  read-only
    STATUS  mandatory
    DESCRIPTION
        "Peak throughput rate for the period (in octets/second)."
    ::= { ipadDLCIstatsEntry 17 }    

ipadDLCIstatsAverage    OBJECT-TYPE
    SYNTAX  INTEGER
    ACCESS  read-only
    STATUS  mandatory
    DESCRIPTION
        "Average throughput rate for the period (in octets/second)."
    ::= { ipadDLCIstatsEntry 18 }    

ipadDLCIstatsDelayPeak    OBJECT-TYPE
    SYNTAX  INTEGER
    ACCESS  read-only
    STATUS  mandatory
    DESCRIPTION
        "Peak roundtrip delay for the period."
    ::= { ipadDLCIstatsEntry 19 }    

ipadDLCIstatsDelayAverage    OBJECT-TYPE
    SYNTAX  INTEGER
    ACCESS  read-only
    STATUS  mandatory
    DESCRIPTION
        "Average roundtrip delay for the period."
    ::= { ipadDLCIstatsEntry 20 }    

ipadDLCIstatsRoundTripTimeouts    OBJECT-TYPE
    SYNTAX  INTEGER
    ACCESS  read-only
    STATUS  mandatory
    DESCRIPTION
        "Number of timeouts on roundtrip delay for the period."
    ::= { ipadDLCIstatsEntry 21 }    

ipadDLCIstatsUAS    OBJECT-TYPE
    SYNTAX  INTEGER
    ACCESS  read-only
    STATUS  mandatory
    DESCRIPTION
        "Number of seconds the DLCI is unavailable."
    ::= { ipadDLCIstatsEntry 22 }    

ipadUserStatsTable    OBJECT-TYPE
    SYNTAX  SEQUENCE OF IpadUserStatsEntry
    ACCESS  not-accessible
    STATUS  optional
    DESCRIPTION
        "User-selected protocol statistics."
    ::= { ipadSvcAware 3 }

ipadUserStatsEntry    OBJECT-TYPE
    SYNTAX  IpadUserStatsEntry
    ACCESS  not-accessible
    STATUS  mandatory
    DESCRIPTION
        "An entry in the user statistics table."
    INDEX    { ipadUserStatsIndex, ipadUserStatsPeriod }
    ::= { ipadUserStatsTable 1 }

IpadUserStatsEntry ::=
    SEQUENCE
    {
    ipadUserStatsIndex           INTEGER,
    ipadUserStatsPeriod          INTEGER,
    ipadUserStatsTxFrames        INTEGER,
    ipadUserStatsRxFrames        INTEGER,
    ipadUserStatsTxOctets        INTEGER,
    ipadUserStatsRxOctets        INTEGER,
    ipadUserStatsTxRatePeak      INTEGER,
    ipadUserStatsTxRateAverage   INTEGER
    }

ipadUserStatsIndex    OBJECT-TYPE
    SYNTAX  INTEGER
    ACCESS  read-only
    STATUS  mandatory
    DESCRIPTION
        "Index into the user statistics table."
    ::= { ipadUserStatsEntry 1 }    

ipadUserStatsPeriod    OBJECT-TYPE
    SYNTAX  INTEGER
    {
    userStatsSummary(1),
    userStatsCurrent(2),

    userStatsperiod1(3),
    userStatsperiod2(4),
    userStatsperiod3(5),
    userStatsperiod4(6),
    userStatsperiod5(7),
    userStatsperiod6(8),
    userStatsperiod7(9),
    userStatsperiod8(10),
    userStatsperiod9(11),

    userStatsperiod10(12),
    userStatsperiod11(13),
    userStatsperiod12(14),
    userStatsperiod13(15),
    userStatsperiod14(16),
    userStatsperiod15(17),
    userStatsperiod16(18),
    userStatsperiod17(19),
    userStatsperiod18(20),
    userStatsperiod19(21),

    userStatsperiod20(22),
    userStatsperiod21(23),
    userStatsperiod22(24),
    userStatsperiod23(25),
    userStatsperiod24(26),
    userStatsperiod25(27),
    userStatsperiod26(28),
    userStatsperiod27(29),
    userStatsperiod28(30),
    userStatsperiod29(31),

    userStatsperiod30(32),
    userStatsperiod31(33),
    userStatsperiod32(34),
    userStatsperiod33(35),
    userStatsperiod34(36),
    userStatsperiod35(37),
    userStatsperiod36(38),
    userStatsperiod37(39),
    userStatsperiod38(40),
    userStatsperiod39(41),

    userStatsperiod40(42),
    userStatsperiod41(43),
    userStatsperiod42(44),
    userStatsperiod43(45),
    userStatsperiod44(46),
    userStatsperiod45(47),
    userStatsperiod46(48),
    userStatsperiod47(49),
    userStatsperiod48(50),
    userStatsperiod49(51),

    userStatsperiod50(52),
    userStatsperiod51(53),
    userStatsperiod52(54),
    userStatsperiod53(55),
    userStatsperiod54(56),
    userStatsperiod55(57),
    userStatsperiod56(58),
    userStatsperiod57(59),
    userStatsperiod58(60),
    userStatsperiod59(61),

    userStatsperiod60(62),
    userStatsperiod61(63),
    userStatsperiod62(64),
    userStatsperiod63(65),
    userStatsperiod64(66),
    userStatsperiod65(67),
    userStatsperiod66(68),
    userStatsperiod67(69),
    userStatsperiod68(70),
    userStatsperiod69(71),

    userStatsperiod70(72),
    userStatsperiod71(73),
    userStatsperiod72(74),
    userStatsperiod73(75),
    userStatsperiod74(76),
    userStatsperiod75(77),
    userStatsperiod76(78),
    userStatsperiod77(79),
    userStatsperiod78(80),
    userStatsperiod79(81),

    userStatsperiod80(82),
    userStatsperiod81(83),
    userStatsperiod82(84),
    userStatsperiod83(85),
    userStatsperiod84(86),
    userStatsperiod85(87),
    userStatsperiod86(88),
    userStatsperiod87(89),
    userStatsperiod88(90),
    userStatsperiod89(91),

    userStatsperiod90(92),
    userStatsperiod91(93),
    userStatsperiod92(94),
    userStatsperiod93(95),
    userStatsperiod94(96),
    userStatsperiod95(97),
    userStatsperiod96(98)
    }
    ACCESS  read-only
    STATUS  mandatory
    DESCRIPTION
        "The index into the user stats 24-hour table."
    ::= { ipadUserStatsEntry 2 }    

ipadUserStatsTxFrames    OBJECT-TYPE
    SYNTAX  INTEGER
    ACCESS  read-only
    STATUS  mandatory
    DESCRIPTION
        "Number of transmitted frames for the period."
    ::= { ipadUserStatsEntry 3 }    

ipadUserStatsRxFrames    OBJECT-TYPE
    SYNTAX  INTEGER
    ACCESS  read-only
    STATUS  mandatory
    DESCRIPTION
        "Number of received frames for the period."
    ::= { ipadUserStatsEntry 4 }    

ipadUserStatsTxOctets    OBJECT-TYPE
    SYNTAX  INTEGER
    ACCESS  read-only
    STATUS  mandatory
    DESCRIPTION
        "Number of transmitted octets for the period."
    ::= { ipadUserStatsEntry 5 }    

ipadUserStatsRxOctets    OBJECT-TYPE
    SYNTAX  INTEGER
    ACCESS  read-only
    STATUS  mandatory
    DESCRIPTION
        "Number of received octets for the period."
    ::= { ipadUserStatsEntry 6 }    

ipadUserStatsTxRatePeak    OBJECT-TYPE
    SYNTAX  INTEGER
    ACCESS  read-only
    STATUS  mandatory
    DESCRIPTION
        "Peak throughput rate for the period (in octets/second)."
    ::= { ipadUserStatsEntry 7 }

ipadUserStatsTxRateAverage    OBJECT-TYPE
    SYNTAX  INTEGER
    ACCESS  read-only
    STATUS  mandatory
    DESCRIPTION
        "Average throughput rate for the period (in octets/second)."    
    ::= { ipadUserStatsEntry 8 }

-- IPTopN stats section

ipadIPTopNStatsTable    OBJECT-TYPE
    SYNTAX  SEQUENCE OF IpadIPTopNStatsEntry
    ACCESS  not-accessible
    STATUS  optional
    DESCRIPTION
        "IP TopN statistics."
    ::= { ipadSvcAware 4 }

ipadIPTopNStatsEntry    OBJECT-TYPE
    SYNTAX  IpadIPTopNStatsEntry
    ACCESS  not-accessible
    STATUS  mandatory
    DESCRIPTION
        "An entry in the user statistics table."
    INDEX    { ipadIPTopNStatsIndex }
    ::= { ipadIPTopNStatsTable 1 }

IpadIPTopNStatsEntry ::=
    SEQUENCE
    {
    ipadIPTopNStatsIndex            INTEGER,
    ipadIPTopNStatsAddress          OCTET STRING,
    ipadIPTopNStatsTimestamp        TimeTicks,
    ipadIPTopNStatsRxFrames         INTEGER,
    ipadIPTopNStatsRxOctets         INTEGER,
    ipadIPTopNStatsTxFrames         INTEGER,
    ipadIPTopNStatsTxOctets         INTEGER
    }

ipadIPTopNStatsIndex    OBJECT-TYPE
    SYNTAX  INTEGER
    ACCESS  read-only
    STATUS  mandatory
    DESCRIPTION
        "Index into the IP TopN statistics table."
    ::= { ipadIPTopNStatsEntry 1 }    

ipadIPTopNStatsAddress    OBJECT-TYPE
    SYNTAX  OCTET STRING (SIZE(1..16))
    ACCESS  read-only
    STATUS  mandatory
    DESCRIPTION
        "IP address of this entry."
    ::= { ipadIPTopNStatsEntry 2 }

ipadIPTopNStatsTimestamp    OBJECT-TYPE
    SYNTAX  TimeTicks
    ACCESS  read-only
    STATUS  mandatory
    DESCRIPTION
        "Time of last IP frame for this entry."
    ::= { ipadIPTopNStatsEntry 3 }

ipadIPTopNStatsRxFrames    OBJECT-TYPE
    SYNTAX  INTEGER
    ACCESS  read-only
    STATUS  mandatory
    DESCRIPTION
        "Number of received IP frames for this entry."
    ::= { ipadIPTopNStatsEntry 4 }    

ipadIPTopNStatsRxOctets    OBJECT-TYPE
    SYNTAX  INTEGER
    ACCESS  read-only
    STATUS  mandatory
    DESCRIPTION
        "Number of received IP octets for this entry."
    ::= { ipadIPTopNStatsEntry 5 }    

ipadIPTopNStatsTxFrames    OBJECT-TYPE
    SYNTAX  INTEGER
    ACCESS  read-only
    STATUS  mandatory
    DESCRIPTION
        "Number of transmitted IP frames for this entry."
    ::= { ipadIPTopNStatsEntry 6 }    

ipadIPTopNStatsTxOctets    OBJECT-TYPE
    SYNTAX  INTEGER
    ACCESS  read-only
    STATUS  mandatory
    DESCRIPTION
        "Number of transmitted IP octets for this entry."
    ::= { ipadIPTopNStatsEntry 7 }    

-- ipadPktSwitch section
-- packet switch parameters

ipadPktSwOperatingMode    OBJECT-TYPE
    SYNTAX  INTEGER
    {
    other(1),
    tdm(2),
    monitor(3),
    packet(4),
    remoteConfig(5)
    }
    ACCESS  read-write
    STATUS  mandatory
    DESCRIPTION
        "Selects overall mode of operation."
    ::= { ipadPktSwitch 1 }

ipadPktSwCfgTable    OBJECT-TYPE
    SYNTAX  SEQUENCE OF IpadPktSwCfgTableEntry
    ACCESS  not-accessible
    STATUS  optional
    DESCRIPTION
        "The ipad packet switch configuration table."
    ::= { ipadPktSwitch 2 }

ipadPktSwCfgTableEntry    OBJECT-TYPE
    SYNTAX  IpadPktSwCfgTableEntry
    ACCESS  not-accessible
    STATUS  mandatory
    DESCRIPTION
        "An entry in the ipad packet switch configuration table."
    INDEX   { ipadPktSwCfgService }
    ::= { ipadPktSwCfgTable 1 }

IpadPktSwCfgTableEntry ::=
    SEQUENCE
    {
    ipadPktSwCfgService        INTEGER,
    ipadPktSwCfgInterfaceType  INTEGER,
    ipadPktSwCfgLnkMgmtType    INTEGER,
    ipadPktSwCfgMaxFrameSize   INTEGER,
    ipadPktSwCfgnN1            INTEGER,
    ipadPktSwCfgnN2            INTEGER,
    ipadPktSwCfgnN3            INTEGER,
    ipadPktSwCfgnT1            INTEGER,
    ipadPktSwCfgDefCIR         INTEGER,
    ipadPktSwCfgDefExBurst     INTEGER,
    ipadPktSwCfgCIREE          INTEGER,
    ipadPktSwCfgLinkInjection  INTEGER,
    ipadPktSwCfgAutoDiagnostic INTEGER,
    ipadPktSwCfgAutoDiscovery  INTEGER,
	ipadPktSwCfgMgmtDLCI       INTEGER
    }

ipadPktSwCfgService        OBJECT-TYPE
    SYNTAX  INTEGER
    ACCESS  read-only
    STATUS  mandatory
    DESCRIPTION
        "The index into the packet switch configuration table;
        an entry in the ipad Service table."
    ::= { ipadPktSwCfgTableEntry 1 }

ipadPktSwCfgInterfaceType    OBJECT-TYPE
    SYNTAX  INTEGER
    {
    uni(1),
    ni(2),
    nni(3)
    }
    ACCESS  read-write
    STATUS  mandatory
    DESCRIPTION
        "Network ports should be set to User Network Interface (uni) 
        and user ports should be set to Network Interface (ni)."
    ::= { ipadPktSwCfgTableEntry 2 }

ipadPktSwCfgLnkMgmtType        OBJECT-TYPE
    SYNTAX  INTEGER
    {
    other(1),
    auto(2),
    ccitt(3),
    ansi(4),
    lmi(5),
    none(6)
    }
    ACCESS  read-write
    STATUS  mandatory
    DESCRIPTION
        "If set to auto, the frame relay LMI type will 
        be learned from the network side.  If set to 
        none, all DLCI must be configured."
    ::= { ipadPktSwCfgTableEntry 3 }

ipadPktSwCfgMaxFrameSize    OBJECT-TYPE
    SYNTAX  INTEGER
    ACCESS  read-write
    STATUS  mandatory
    DESCRIPTION
        "This is the maximum frame size configured in the frame relay network."
    ::= { ipadPktSwCfgTableEntry 4 }

ipadPktSwCfgnN1            OBJECT-TYPE
    SYNTAX  INTEGER
    ACCESS  read-write
    STATUS  mandatory
    DESCRIPTION
        "Number of keep alive requests between full status request."
    ::= { ipadPktSwCfgTableEntry 5 }

ipadPktSwCfgnN2            OBJECT-TYPE
    SYNTAX  INTEGER
    ACCESS  read-write
    STATUS  mandatory
    DESCRIPTION
        "Number of errors from FRAD before alarm."
    ::= { ipadPktSwCfgTableEntry 6 }

ipadPktSwCfgnN3            OBJECT-TYPE
    SYNTAX  INTEGER
    ACCESS  read-write
    STATUS  mandatory
    DESCRIPTION
        "Number of events to sample nN2."
    ::= { ipadPktSwCfgTableEntry 7 }

ipadPktSwCfgnT1            OBJECT-TYPE
    SYNTAX  INTEGER
    ACCESS  read-write
    STATUS  mandatory
    DESCRIPTION
        "Delay before issuing a poll sequence."
    ::= { ipadPktSwCfgTableEntry 8 }

ipadPktSwCfgDefCIR        OBJECT-TYPE
    SYNTAX  INTEGER
    ACCESS  read-write
    STATUS  mandatory
    DESCRIPTION
        "Default committed information rate in bits per second."
    ::= { ipadPktSwCfgTableEntry 9 }

ipadPktSwCfgDefExBurst        OBJECT-TYPE
    SYNTAX  INTEGER
    ACCESS  read-write
    STATUS  mandatory
    DESCRIPTION
        "Default excess burst rate in bits per second."
    ::= { ipadPktSwCfgTableEntry 10 }

ipadPktSwCfgCIREE        OBJECT-TYPE
    SYNTAX  INTEGER
    {
    other(1),
    no(2),
    yes(3)
    }
    ACCESS  read-write
    STATUS  mandatory
    DESCRIPTION
        "Determines if the interface will enforce CIR and 
        excess burst configured values."
    ::= { ipadPktSwCfgTableEntry 11 }

ipadPktSwCfgLinkInjection    OBJECT-TYPE
    SYNTAX  INTEGER
    {
    other(1),
    standard(2),
    buffered(3),
    forced(4)
    }
    ACCESS  read-write
    STATUS  mandatory
    DESCRIPTION
        "Indicates how to process frames in excess 
        of the CIR when congestion exists."
    ::= { ipadPktSwCfgTableEntry 12 }

ipadPktSwCfgAutoDiagnostic    OBJECT-TYPE
    SYNTAX  INTEGER
    {
    other(1),
    no(2),
    yes(3)
    }
    ACCESS  read-write
    STATUS  mandatory
    DESCRIPTION
        "Determines if the unit will put itself into 
        diagnostic mode everytime it determines that
        there are no LMI received on a network service."
    ::= { ipadPktSwCfgTableEntry 13 }

ipadPktSwCfgAutoDiscovery    OBJECT-TYPE
    SYNTAX  INTEGER
    {
    other(1),
    no(2),
    yes(3)
    }
    ACCESS  read-write
    STATUS  mandatory
    DESCRIPTION
        "Determines if the unit will learn the DLCIs 
        from the LMMI received on this service."
    ::= { ipadPktSwCfgTableEntry 14 }

ipadPktSwCfgMgmtDLCI	OBJECT-TYPE
	SYNTAX  INTEGER(0..4096)
    ACCESS  read-write
    STATUS  mandatory
    DESCRIPTION
        "Specifies the DLCI that will be used by the unit
		for management information.  Specifying a 0 disables
		this feature."
    ::= { ipadPktSwCfgTableEntry 15 }

-- ipadTrapDest    section
-- ipadTrapDestTable contains trap destinations

ipadTrapDestTable    OBJECT-TYPE
    SYNTAX  SEQUENCE OF IpadTrapDestTableEntry
    ACCESS  not-accessible
    STATUS  optional
    DESCRIPTION
        "The ipad trap destination table."
    ::= { ipadTrapDest 1 }

ipadTrapDestTableEntry    OBJECT-TYPE
    SYNTAX  IpadTrapDestTableEntry
    ACCESS  not-accessible
    STATUS  mandatory
    DESCRIPTION
        "An entry in the ipad trap destination table."
    INDEX    { ipadTrapDestIndex }
    ::= { ipadTrapDestTable 1 }

IpadTrapDestTableEntry ::=
    SEQUENCE
    {
    ipadTrapDestIndex        INTEGER,
    ipadTrapDestination      IpAddress
    }

ipadTrapDestIndex    OBJECT-TYPE
    SYNTAX  INTEGER
    ACCESS  read-only
    STATUS  mandatory
    DESCRIPTION
        "Index into the ipad trap destination table."
    ::= { ipadTrapDestTableEntry 1 }

ipadTrapDestination    OBJECT-TYPE
    SYNTAX  IpAddress
    ACCESS  read-write
    STATUS  mandatory
    DESCRIPTION
        "Trap destination."
    ::= { ipadTrapDestTableEntry 2 }

-- ipad-specific Service Aware trap definitions

ipadFrPortRxInvalidFramesExceeded    TRAP-TYPE
    ENTERPRISE    hbu
    DESCRIPTION
        "This trap is sent out when an ipad frame relay
        port receive invalid frames alarm threshold has 
        been exceeded."
    ::= 25000 

ipadFrPortRxThroughputExceeded    TRAP-TYPE
    ENTERPRISE    hbu
    DESCRIPTION
        "This trap is sent out when an ipad frame relay
        port receive throughput threshold has been exceeded."
    ::= 25001

ipadFrPortTxThroughputExceeded    TRAP-TYPE
    ENTERPRISE    hbu
    DESCRIPTION
        "This trap is sent out when an ipad frame relay
        port transmit throughput threshold has been exceeded."
    ::= 25002

ipadDLCItxCIRexceeded    TRAP-TYPE
    ENTERPRISE    hbu
    DESCRIPTION
        "This trap is sent out when the Tx over CIR threshold
        has been exceeded.  This threshold is the number of
        frames in excess of CIR."
    ::= 25003

ipadDLCItxBEexceeded    TRAP-TYPE
    ENTERPRISE    hbu
    DESCRIPTION
        "This trap is sent out when the Tx over Be threshold
        has been exceeded.  This threshold is the number of
        frames in excess of Be."
    ::= 25004

ipadDLCIRxCongestionExceeded    TRAP-TYPE
    ENTERPRISE    hbu
    DESCRIPTION
        "This trap is sent out when the Rx congestion threshold
        has been exceeded.  This threshold is the number of
        frames received with BECN/FECN."
    ::= 25005

ipadUserTxExceeded    TRAP-TYPE
    ENTERPRISE    hbu
    DESCRIPTION
        "This trap is sent out when the Tx throughput threshold
        in bits per second has been exceeded.  This threshold
        represents the number of bits for the user-selected
        protocol."
    ::= 25006

ipadDlciRxBECNinCIRAlarm    TRAP-TYPE
    ENTERPRISE    hbu
    DESCRIPTION
        "This trap is sent out when a frame with BECN set has
        been received within CIR."
    ::= 25007
    
ipadDlciUASExceeded    TRAP-TYPE
    ENTERPRISE    hbu
    DESCRIPTION
        "This trap is sent out when the UAS (unavailable seconds)
        threshold for the DLCI has been exceeded."
    ::= 25008

-- ipad-specific Serial DTE alarm trap definitions

ipadserialDteDTRAlarmExists    TRAP-TYPE
    ENTERPRISE    hbu
    DESCRIPTION
        "This trap is sent out when a DTR Loss alarm is declared."
    ::= 25009


-- ipad-specific T1E1 alarm trap definitions

ipadt1e1ESAlarmDeclared        TRAP-TYPE
    ENTERPRISE    hbu
    DESCRIPTION
        "This trap is sent out when an Errored Seconds
        alarm is declared."
    ::= 25010

ipadt1e1SESAlarmDeclared    TRAP-TYPE
    ENTERPRISE    hbu
    DESCRIPTION
        "This trap is sent out when a Severely Errored Seconds
        alarm is declared."
    ::= 25011

ipadt1e1LOSSAlarmDeclared    TRAP-TYPE
    ENTERPRISE    hbu
    DESCRIPTION
        "This trap is sent out when a Loss of Signal Seconds
        alarm is declared."
    ::= 25012

ipadt1e1UASAlarmDeclared    TRAP-TYPE
    ENTERPRISE    hbu
    DESCRIPTION
        "This trap is sent out when an Unavailable Seconds
        alarm is declared."
    ::= 25013

ipadt1e1CSSAlarmDeclared    TRAP-TYPE
    ENTERPRISE    hbu
    DESCRIPTION
        "This trap is sent out when a Controlled Slip Seconds
        alarm is declared."
    ::= 25014

ipadt1e1BPVSAlarmDeclared    TRAP-TYPE
    ENTERPRISE    hbu
    DESCRIPTION
        "This trap is sent out when a Bipolar Violation Seconds
        alarm is declared."
    ::= 25015

ipadt1e1OOFSAlarmDeclared    TRAP-TYPE
    ENTERPRISE    hbu
    DESCRIPTION
        "This trap is sent out when an Out of Frame Seconds
        alarm is declared."
    ::= 25016

ipadt1e1AISAlarmExists    TRAP-TYPE
    ENTERPRISE    hbu
    DESCRIPTION
        "This trap is sent out when an Alarm Indication Signal
        alarm is declared."
    ::= 25017

ipadt1e1RASAlarmExists    TRAP-TYPE
    ENTERPRISE    hbu
    DESCRIPTION
        "This trap is sent out when a Remote Alarm Signal
        alarm is declared."
    ::= 25018

-- ipad specific remote SOS alarm

ipadDLCIremoteSOSAlarm TRAP-TYPE
    ENTERPRISE    hbu
    DESCRIPTION
        "This trap is sent when the remote unit for a
        DLCI senses and reports an SOS condition."
    ::= 25019
    
-- ipadMisc section
-- ipadMiscPortSettings contains, currently, a table indicating if a
--    serial interface should be set for DTE or DCE

ipadMiscPortSettings    OBJECT-TYPE
    SYNTAX  SEQUENCE OF IpadMiscPortSettingsEntry
    ACCESS  not-accessible
    STATUS  optional
    DESCRIPTION
        "The ipad miscellaneous port settings table."
    ::= { ipadMisc 1 }

ipadMiscPortSettingsEntry    OBJECT-TYPE
    SYNTAX  IpadMiscPortSettingsEntry
    ACCESS  not-accessible
    STATUS  mandatory
    DESCRIPTION
        "An entry in the ipad miscellaneous port settings table."
    INDEX    { ipadMiscPortSettingsIndex }
    ::= { ipadMiscPortSettings 1 }

IpadMiscPortSettingsEntry ::=
    SEQUENCE
    {
    ipadMiscPortSettingsIndex         INTEGER,
    ipadMiscPortSettingsSerialType    INTEGER
    }

ipadMiscPortSettingsIndex    OBJECT-TYPE
    SYNTAX  INTEGER
    {
    supervisor(1),
    network1(2),
    network2(3),
    user1(4),
    user2(5),
    ethernet(6)
    }
    ACCESS  read-only
    STATUS  mandatory
    DESCRIPTION
        "The MIB-II ifIndex for this port."
    ::= { ipadMiscPortSettingsEntry 1 }

ipadMiscPortSettingsSerialType        OBJECT-TYPE
    SYNTAX  INTEGER
    {
    other(1),
    dce(2),
    dte(3)
    }
    ACCESS  read-write
    STATUS  mandatory
    DESCRIPTION
        "The type of this serial port."
    ::= { ipadMiscPortSettingsEntry 2 }

ipadMiscClearStatusCounts    OBJECT-TYPE
    SYNTAX  INTEGER
    {
    other(1),
    clear(2)
    }
    ACCESS  read-write
    STATUS  mandatory
    DESCRIPTION
        "Writing a 2 to this field will clear all status counts."
    ::= { ipadMisc 2 }

-- ipadSoftKey section
-- contains software key table

ipadSoftKeyTable OBJECT-TYPE
    SYNTAX    SEQUENCE OF IpadSoftKeyTableEntry
    ACCESS    not-accessible
    STATUS    mandatory
    DESCRIPTION
        "Table of software keys."
    ::= { ipadSoftKey 1 }

ipadSoftKeyTableEntry OBJECT-TYPE
    SYNTAX  IpadSoftKeyTableEntry
    ACCESS  not-accessible
    STATUS  mandatory
    DESCRIPTION
        "An entry in the software key table."
    INDEX   { ipadSoftKeyIndex }
    ::= { ipadSoftKeyTable 1 }

IpadSoftKeyTableEntry ::=
    SEQUENCE
    {
    ipadSoftKeyIndex             INTEGER,
    ipadSoftKeyAcronym           DisplayString,
    ipadSoftKeyDescription       DisplayString,
    ipadSoftKeyExpirationDate    DisplayString
    }

ipadSoftKeyIndex OBJECT-TYPE
    SYNTAX  INTEGER
    ACCESS  read-only
    STATUS  mandatory
    DESCRIPTION
        "Index into the ipad software key table."
    ::= { ipadSoftKeyTableEntry 1 }

ipadSoftKeyAcronym OBJECT-TYPE
    SYNTAX  DisplayString(SIZE(0..3))
    ACCESS  read-only
    STATUS  mandatory
    DESCRIPTION
        "Three-letter acronym for software key."
    ::= { ipadSoftKeyTableEntry 2 }

ipadSoftKeyDescription OBJECT-TYPE
    SYNTAX  DisplayString(SIZE(0..80))
    ACCESS  read-only
    STATUS  mandatory
    DESCRIPTION
        "Description, if available, of this software key."
    ::= { ipadSoftKeyTableEntry 3 }

ipadSoftKeyExpirationDate OBJECT-TYPE
    SYNTAX  DisplayString(SIZE(0..8))
    ACCESS  read-only
    STATUS  mandatory
    DESCRIPTION
        "Expiration date of this software key in the format YY/MM/DD."
    ::= { ipadSoftKeyTableEntry 4 }

ipadSoftKeyEntry OBJECT-TYPE
    SYNTAX    DisplayString(SIZE(0..80))
    ACCESS    read-write
    STATUS    mandatory
    DESCRIPTION
        "Writing a software key will enable that feature (assuming
        a correct and valid key is entered)."
    ::= { ipadSoftKey 2 }

END
