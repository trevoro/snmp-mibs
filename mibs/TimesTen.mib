--
-- TimesTen-MIB.txt
--
-- LAST-UPDATED "200407262303Z"
-- DESCRIPTION "The SMIv1 version of the TimesTen enterprise private MIB"
--

        TimesTen DEFINITIONS ::= BEGIN

                IMPORTS
                        OBJECT-TYPE
                                FROM RFC-1212
                        TRAP-TYPE
                                FROM RFC-1215
                        enterprises
                                FROM RFC1155-SMI;


--
-- Node definitions
--

-- This is the enterprise private TimesTen MIB
                -- 1.3.6.1.4.1.5549
                timesten OBJECT IDENTIFIER ::= { enterprises 5549 }


-- System Stuff
                -- 1.3.6.1.4.1.5549.1
                ttSystem OBJECT IDENTIFIER ::= { timesten 1 }


                -- 1.3.6.1.4.1.5549.1.1
                ttTimeStamp OBJECT-TYPE
                        SYNTAX OCTET STRING
                        ACCESS read-only
                        STATUS mandatory
                        DESCRIPTION
                                "A TimeStamp String."
                        ::= { ttSystem 1 }


                -- 1.3.6.1.4.1.5549.1.2
                ttVersion OBJECT-TYPE
                        SYNTAX OCTET STRING
                        ACCESS read-only
                        STATUS mandatory
                        DESCRIPTION
                                "TimesTen version string"
                        ::= { ttSystem 2 }


                -- 1.3.6.1.4.1.5549.1.3
                ttPid OBJECT-TYPE
                        SYNTAX INTEGER
                        ACCESS read-only
                        STATUS mandatory
                        DESCRIPTION
                                "Process ID String"
                        ::= { ttSystem 3 }


                -- 1.3.6.1.4.1.5549.1.4
                ttProcessName OBJECT-TYPE
                        SYNTAX OCTET STRING
                        ACCESS read-only
                        STATUS obsolete
                        DESCRIPTION
                                "Process Name String"
                        ::= { ttSystem 4 }


                -- 1.3.6.1.4.1.5549.1.5
                ttUid OBJECT-TYPE
                        SYNTAX OCTET STRING
                        ACCESS read-only
                        STATUS mandatory
                        DESCRIPTION
                                "User ID String"
                        ::= { ttSystem 5 }


                -- 1.3.6.1.4.1.5549.1.6
                ttUserName OBJECT-TYPE
                        SYNTAX OCTET STRING
                        ACCESS read-only
                        STATUS obsolete
                        DESCRIPTION
                                "User Name String"
                        ::= { ttSystem 6 }


-- Messages
                -- 1.3.6.1.4.1.5549.2
                ttMsg OBJECT IDENTIFIER ::= { timesten 2 }


                -- 1.3.6.1.4.1.5549.2.1
                ttMesg OBJECT-TYPE
                        SYNTAX OCTET STRING
                        ACCESS read-only
                        STATUS mandatory
                        DESCRIPTION
                                "Generic Message String"
                        ::= { ttMsg 1 }


-- Traps
                -- 1.3.6.1.4.1.5549.5
                ttTraps OBJECT IDENTIFIER ::= { timesten 5 }


                -- 1.3.6.1.4.1.5549.5.1
                ttAssertTraps OBJECT IDENTIFIER ::= { ttTraps 1 }


                -- 1.3.6.1.4.1.5549.5.10
                ttDSTraps OBJECT IDENTIFIER ::= { ttTraps 10 }


                -- 1.3.6.1.4.1.5549.5.20
                ttFileTraps OBJECT IDENTIFIER ::= { ttTraps 20 }


                -- 1.3.6.1.4.1.5549.5.40
                ttDaemonTraps OBJECT IDENTIFIER ::= { ttTraps 40 }


                -- 1.3.6.1.4.1.5549.5.50
                ttRepTraps OBJECT IDENTIFIER ::= { ttTraps 50 }


                -- 1.3.6.1.4.1.5549.5.60
                ttOraTraps OBJECT IDENTIFIER ::= { ttTraps 60 }


                -- 1.3.6.1.4.1.5549.5.70
                ttRecoveryTraps OBJECT IDENTIFIER ::= { ttTraps 70 }


                -- 1.3.6.1.4.1.5549.5.100
                ttTrapTruncated OBJECT-TYPE
                        SYNTAX INTEGER
                        ACCESS read-only
                        STATUS mandatory
                        DESCRIPTION
                                "1 If the trap is too large and has been truncated."
                        ::= { ttTraps 100 }


-- Datastore related
                -- 1.3.6.1.4.1.5549.10
                ttDataStore OBJECT IDENTIFIER ::= { timesten 10 }


                -- 1.3.6.1.4.1.5549.10.2
                ttDSName OBJECT-TYPE
                        SYNTAX OCTET STRING
                        ACCESS read-only
                        STATUS mandatory
                        DESCRIPTION
                                "Data store name"
                        ::= { ttDataStore 2 }


                -- 1.3.6.1.4.1.5549.10.3
                ttDSPath OBJECT-TYPE
                        SYNTAX OCTET STRING
                        ACCESS read-only
                        STATUS mandatory
                        DESCRIPTION
                                "Data store path"
                        ::= { ttDataStore 3 }


                -- 1.3.6.1.4.1.5549.10.4
                ttDSShmKey OBJECT-TYPE
                        SYNTAX OCTET STRING
                        ACCESS read-only
                        STATUS mandatory
                        DESCRIPTION
                                "Data store Shared Memory ID/Key"
                        ::= { ttDataStore 4 }


                -- 1.3.6.1.4.1.5549.10.7
                ttDSNConn OBJECT-TYPE
                        SYNTAX INTEGER
                        ACCESS read-only
                        STATUS mandatory
                        DESCRIPTION
                                "Connection number.  Starting with 0."
                        ::= { ttDataStore 7 }


                -- 1.3.6.1.4.1.5549.10.8
                ttDSMaxSize OBJECT-TYPE
                        SYNTAX INTEGER
                        ACCESS read-only
                        STATUS mandatory
                        DESCRIPTION
                                "Maximum size of data store, in KB."
                        ::= { ttDataStore 8 }


                -- 1.3.6.1.4.1.5549.10.9
                ttDSCurSize OBJECT-TYPE
                        SYNTAX INTEGER
                        ACCESS read-only
                        STATUS mandatory
                        DESCRIPTION
                                "Current size of data store, in KB."
                        ::= { ttDataStore 9 }


                -- 1.3.6.1.4.1.5549.10.10
                ttDSReqSize OBJECT-TYPE
                        SYNTAX INTEGER
                        ACCESS read-only
                        STATUS mandatory
                        DESCRIPTION
                                "Requested increase in data store size, in KB."
                        ::= { ttDataStore 10 }


                -- 1.3.6.1.4.1.5549.10.11
                ttDSPartition OBJECT-TYPE
                        SYNTAX OCTET STRING
                        ACCESS read-only
                        STATUS mandatory
                        DESCRIPTION
                                "Name of the data store partition, ie. Permanent or Temporary."
                        ::= { ttDataStore 11 }


-- File I/O Related
                -- 1.3.6.1.4.1.5549.20
                ttFile OBJECT IDENTIFIER ::= { timesten 20 }


                -- 1.3.6.1.4.1.5549.20.3
                ttFilePath OBJECT-TYPE
                        SYNTAX OCTET STRING
                        ACCESS read-only
                        STATUS mandatory
                        DESCRIPTION
                                "Full path of file."
                        ::= { ttFile 3 }


                -- 1.3.6.1.4.1.5549.20.6
                ttReadSize OBJECT-TYPE
                        SYNTAX OCTET STRING
                        ACCESS read-write
                        STATUS mandatory
                        DESCRIPTION
                                "Number of bytes successfully read from a file."
                        ::= { ttFile 6 }


                -- 1.3.6.1.4.1.5549.20.7
                ttReadReq OBJECT-TYPE
                        SYNTAX OCTET STRING
                        ACCESS read-only
                        STATUS mandatory
                        DESCRIPTION
                                "Number of bytes requested to be read from a file."
                        ::= { ttFile 7 }


                -- 1.3.6.1.4.1.5549.20.8
                ttWriteSize OBJECT-TYPE
                        SYNTAX OCTET STRING
                        ACCESS read-only
                        STATUS mandatory
                        DESCRIPTION
                                "Number of bytes successfully written to a file."
                        ::= { ttFile 8 }


                -- 1.3.6.1.4.1.5549.20.9
                ttWriteReq OBJECT-TYPE
                        SYNTAX OCTET STRING
                        ACCESS read-only
                        STATUS mandatory
                        DESCRIPTION
                                "Number of bytes requested to be written to a file."
                        ::= { ttFile 9 }


-- Daemon related
                -- 1.3.6.1.4.1.5549.40
                ttDaemon OBJECT IDENTIFIER ::= { timesten 40 }


                -- 1.3.6.1.4.1.5549.40.2
                ttDaeName OBJECT-TYPE
                        SYNTAX OCTET STRING
                        ACCESS read-only
                        STATUS mandatory
                        DESCRIPTION
                                "Executable name of daemon, ie. timestend or timestensubd."
                        ::= { ttDaemon 2 }


                -- 1.3.6.1.4.1.5549.40.4
                ttDaePid OBJECT-TYPE
                        SYNTAX INTEGER
                        ACCESS read-only
                        STATUS mandatory
                        DESCRIPTION
                                "Process ID of the daemon."
                        ::= { ttDaemon 4 }


                -- 1.3.6.1.4.1.5549.40.6
                ttDaeInst OBJECT-TYPE
                        SYNTAX INTEGER
                        ACCESS read-only
                        STATUS mandatory
                        DESCRIPTION
                                "Daemon number, starting with 0."
                        ::= { ttDaemon 6 }


-- Replication related
                -- 1.3.6.1.4.1.5549.50
                ttReplication OBJECT IDENTIFIER ::= { timesten 50 }


                -- 1.3.6.1.4.1.5549.50.1
                ttRepPid OBJECT-TYPE
                        SYNTAX INTEGER
                        ACCESS read-only
                        STATUS mandatory
                        DESCRIPTION
                                "Process ID of replication agent."
                        ::= { ttReplication 1 }


                -- 1.3.6.1.4.1.5549.50.2
                ttRepName OBJECT-TYPE
                        SYNTAX OCTET STRING
                        ACCESS read-only
                        STATUS mandatory
                        DESCRIPTION
                                "This is last component of my datastore path name."
                        ::= { ttReplication 2 }


                -- 1.3.6.1.4.1.5549.50.3
                ttRepPeerStoreID OBJECT-TYPE
                        SYNTAX OCTET STRING
                        ACCESS read-only
                        STATUS mandatory
                        DESCRIPTION
                                "The unique Store-ID of my peer (master or subscriber)."
                        ::= { ttReplication 3 }


                -- 1.3.6.1.4.1.5549.50.4
                ttRepPeerName OBJECT-TYPE
                        SYNTAX OCTET STRING
                        ACCESS read-only
                        STATUS mandatory
                        DESCRIPTION
                                "This is last component of my peer's datastore path name."
                        ::= { ttReplication 4 }


                -- 1.3.6.1.4.1.5549.50.5
                ttRepMasterHost OBJECT-TYPE
                        SYNTAX OCTET STRING
                        ACCESS read-only
                        STATUS mandatory
                        DESCRIPTION
                                "The master's host name."
                        ::= { ttReplication 5 }


                -- 1.3.6.1.4.1.5549.50.6
                ttRepMasterPort OBJECT-TYPE
                        SYNTAX INTEGER
                        ACCESS read-only
                        STATUS mandatory
                        DESCRIPTION
                                "The master's port."
                        ::= { ttReplication 6 }


                -- 1.3.6.1.4.1.5549.50.7
                ttRepSubscriberHost OBJECT-TYPE
                        SYNTAX OCTET STRING
                        ACCESS read-only
                        STATUS mandatory
                        DESCRIPTION
                                "The subscriber's host name."
                        ::= { ttReplication 7 }


                -- 1.3.6.1.4.1.5549.50.8
                ttRepSubscriberPort OBJECT-TYPE
                        SYNTAX INTEGER
                        ACCESS read-only
                        STATUS mandatory
                        DESCRIPTION
                                "The subscriber's port."
                        ::= { ttReplication 8 }


                -- 1.3.6.1.4.1.5549.50.9
                ttRepTable OBJECT-TYPE
                        SYNTAX OCTET STRING
                        ACCESS read-only
                        STATUS mandatory
                        ::= { ttReplication 9 }


                -- 1.3.6.1.4.1.5549.50.10
                ttRepAction OBJECT-TYPE
                        SYNTAX OCTET STRING
                        ACCESS read-only
                        STATUS mandatory
                        ::= { ttReplication 10 }


                -- 1.3.6.1.4.1.5549.50.11
                ttRepReason OBJECT-TYPE
                        SYNTAX OCTET STRING
                        ACCESS read-only
                        STATUS mandatory
                        ::= { ttReplication 11 }


                -- 1.3.6.1.4.1.5549.50.12
                ttRepConflictKey OBJECT-TYPE
                        SYNTAX OCTET STRING
                        ACCESS read-only
                        STATUS mandatory
                        ::= { ttReplication 12 }


-- Oracle Cache Agent related
                -- 1.3.6.1.4.1.5549.60
                ttOraCache OBJECT IDENTIFIER ::= { timesten 60 }


                -- 1.3.6.1.4.1.5549.60.2
                ttOraAgentName OBJECT-TYPE
                        SYNTAX OCTET STRING
                        ACCESS read-only
                        STATUS mandatory
                        DESCRIPTION
                                "Executable path name of Oracle Cache agent."
                        ::= { ttOraCache 2 }


                -- 1.3.6.1.4.1.5549.60.3
                ttOraAgentPid OBJECT-TYPE
                        SYNTAX INTEGER
                        ACCESS read-only
                        STATUS mandatory
                        DESCRIPTION
                                "Process ID of Orache Cache agent."
                        ::= { ttOraCache 3 }


                -- 1.3.6.1.4.1.5549.60.4
                ttOraDSName OBJECT-TYPE
                        SYNTAX OCTET STRING
                        ACCESS read-only
                        STATUS mandatory
                        DESCRIPTION
                                "Name of TimesTen data store used by Oracle Cache Agent."
                        ::= { ttOraCache 4 }


                -- 1.3.6.1.4.1.5549.60.5
                ttOraCacheGroupName OBJECT-TYPE
                        SYNTAX OCTET STRING
                        ACCESS read-only
                        STATUS mandatory
                        DESCRIPTION
                                "Name of cache groups managed Oracle Cache Agent."
                        ::= { ttOraCache 5 }


-- Data store recovery related
                -- 1.3.6.1.4.1.5549.70
                ttRecovery OBJECT IDENTIFIER ::= { timesten 70 }


                -- 1.3.6.1.4.1.5549.70.1
                endLFN OBJECT-TYPE
                        SYNTAX OCTET STRING
                        ACCESS read-only
                        STATUS mandatory
                        DESCRIPTION
                                "Last log file number reached during data store recovery."
                        ::= { ttRecovery 1 }


                -- 1.3.6.1.4.1.5549.70.2
                endLFO OBJECT-TYPE
                        SYNTAX OCTET STRING
                        ACCESS read-only
                        STATUS mandatory
                        DESCRIPTION
                                "Last log file offset reached during data store recovery."
                        ::= { ttRecovery 2 }


                -- 1.3.6.1.4.1.5549.70.3
                maxLFN OBJECT-TYPE
                        SYNTAX OCTET STRING
                        ACCESS read-only
                        STATUS mandatory
                        DESCRIPTION
                                "Maximum log file number expected during data store recovery."
                        ::= { ttRecovery 3 }



--
-- Trap definitions
--

-- Severity Level: Error
                ttAssertFailTrap TRAP-TYPE
                        ENTERPRISE ttAssertTraps
                        VARIABLES { ttTimeStamp, ttPid, ttUid, ttVersion, ttMesg
                                 }
                        DESCRIPTION
                                "TimesTen assertion failure."
                        ::=  1

-- Severity Level: Informational
                ttMainDaemonReadyTrap TRAP-TYPE
                        ENTERPRISE ttDaemonTraps
                        VARIABLES { ttTimeStamp, ttPid, ttUid, ttVersion, ttMesg,
                                ttDaeName, ttDaeInst, ttDaePid }
                        DESCRIPTION
                                "Main or sub daemons starting."
                        ::=  2

-- Severity Level: Informational
                ttMainDaemonExitingTrap TRAP-TYPE
                        ENTERPRISE ttDaemonTraps
                        VARIABLES { ttTimeStamp, ttPid, ttUid, ttVersion, ttMesg,
                                ttDaeName, ttDaeInst, ttDaePid }
                        DESCRIPTION
                                "Main or sub daemons exiting normally."
                        ::=  3

-- Severity Level: Error
                ttMainDaemonDiedTrap TRAP-TYPE
                        ENTERPRISE ttDaemonTraps
                        VARIABLES { ttTimeStamp, ttPid, ttUid, ttVersion, ttMesg,
                                ttDaeName, ttDaeInst, ttDaePid }
                        DESCRIPTION
                                "Main or sub daemons died abnormally."
                        ::=  4

-- Severity Level: Error
                ttDSGoingInvalidTrap TRAP-TYPE
                        ENTERPRISE ttDSTraps
                        VARIABLES { ttTimeStamp, ttPid, ttUid, ttVersion, ttMesg,
                                ttDSName, ttDSShmKey, ttDSNConn }
                        DESCRIPTION
                                "Setting data store to invalid state."
                        ::=  5

-- Severity Level: Informational
                ttRepAgentStartingTrap TRAP-TYPE
                        ENTERPRISE ttRepTraps
                        VARIABLES { ttTimeStamp, ttPid, ttUid, ttVersion, ttMesg,
                                ttDSName }
                        DESCRIPTION
                                "Replication agent starting."
                        ::=  6

-- Severity Level: Informational
                ttRepAgentExitingTrap TRAP-TYPE
                        ENTERPRISE ttRepTraps
                        VARIABLES { ttTimeStamp, ttPid, ttUid, ttVersion, ttMesg,
                                ttDSName }
                        DESCRIPTION
                                "Replication agent exiting normally."
                        ::=  7

-- Severity Level: Error
                ttRepAgentDiedTrap TRAP-TYPE
                        ENTERPRISE ttRepTraps
                        VARIABLES { ttTimeStamp, ttPid, ttUid, ttVersion, ttMesg,
                                ttDSName, ttRepPid }
                        DESCRIPTION
                                "Replication agent died abnormally."
                        ::=  8

-- Severity Level: Warning
                ttRepUpdateFailedTrap TRAP-TYPE
                        ENTERPRISE ttRepTraps
                        VARIABLES { ttTimeStamp, ttPid, ttUid, ttVersion, ttMesg,
                                ttRepPeerStoreID, ttRepName, ttDSName, ttRepReason, ttRepTable,
                                ttRepAction, ttRepPeerName, ttRepConflictKey }
                        DESCRIPTION
                                "A replication insert, update or delete operation failed."
                        ::=  9

-- Severity Level: Error
                ttRepSubscriberFailedTrap TRAP-TYPE
                        ENTERPRISE ttRepTraps
                        VARIABLES { ttTimeStamp, ttPid, ttUid, ttVersion, ttMesg,
                                ttRepPeerStoreID, ttRepName, ttDSName, ttRepReason, ttRepSubscriberHost,
                                ttRepSubscriberPort }
                        DESCRIPTION
                                "Subscriber marked as failed because too much log accumulated
                                on its behalf by the master."
                        ::=  10

-- Severity Level: Warning
                ttPartitionSpaceStateTrap TRAP-TYPE
                        ENTERPRISE ttDSTraps
                        VARIABLES { ttTimeStamp, ttPid, ttUid, ttVersion, ttMesg,
                                ttDSName, ttDSMaxSize, ttDSCurSize, ttDSReqSize, ttDSPartition
                                 }
                        DESCRIPTION
                                "Data store partition (permanent or temporary) space is
                                transitioning from OK to Low, or vice versa."
                        ::=  11

-- Severity Level: Error
                ttPartitionSpaceExhaustedTrap TRAP-TYPE
                        ENTERPRISE ttDSTraps
                        VARIABLES { ttTimeStamp, ttPid, ttUid, ttVersion, ttMesg,
                                ttDSName, ttDSMaxSize, ttDSCurSize, ttDSReqSize, ttDSPartition
                                 }
                        DESCRIPTION
                                "Data store partition (permanent or temporary) space is
                                exhausted."
                        ::=  12

-- Severity Level: Error
                ttDaemonOutOfMemoryTrap TRAP-TYPE
                        ENTERPRISE ttDaemonTraps
                        VARIABLES { ttTimeStamp, ttPid, ttUid, ttVersion, ttMesg,
                                ttDaeName, ttDaeInst }
                        DESCRIPTION
                                "Call to malloc failed in TimesTen daemon."
                        ::=  13

-- Severity Level: Warning
                ttOraAutoRefQueFullTrap TRAP-TYPE
                        ENTERPRISE ttOraTraps
                        VARIABLES { ttTimeStamp, ttPid, ttUid, ttVersion, ttMesg,
                                ttOraAgentPid, ttOraAgentName }
                        DESCRIPTION
                                "TimesTen Oracle Connect autorefresh queue is full."
                        ::=  14

-- Severity Level: Error
                ttOraIncAutoRefFailedTrap TRAP-TYPE
                        ENTERPRISE ttOraTraps
                        VARIABLES { ttTimeStamp, ttPid, ttUid, ttVersion, ttMesg,
                                ttOraAgentPid, ttOraAgentName, ttOraDSName }
                        DESCRIPTION
                                "TimesTen Oracle Connect incremental autorefresh failed."
                        ::=  15

-- Severity Level: Error
                ttOraAgentDiedTrap TRAP-TYPE
                        ENTERPRISE ttOraTraps
                        VARIABLES { ttTimeStamp, ttPid, ttUid, ttVersion, ttMesg,
                                ttOraAgentPid, ttOraDSName }
                        DESCRIPTION
                                "TimesTen Oracle Connect daemon died."
                        ::=  17

-- Severity Level: Warning
                ttRepReturnReceiptTransitionTrap TRAP-TYPE
                        ENTERPRISE ttRepTraps
                        VARIABLES { ttTimeStamp, ttPid, ttUid, ttVersion, ttMesg,
                                ttRepPeerStoreID, ttRepName, ttDSName, ttRepReason, ttRepSubscriberHost
                                 }
                        DESCRIPTION
                                "Return receipt has been disabled or enabled on the subscriber."
                        ::=  19

-- Severity Level: Error
                ttFileWriteErrorTrap TRAP-TYPE
                        ENTERPRISE ttFileTraps
                        VARIABLES { ttTimeStamp, ttPid, ttUid, ttVersion, ttMesg,
                                ttDSName, ttFilePath, ttWriteSize, ttWriteReq }
                        DESCRIPTION
                                "Error encountered during file I/O write."
                        ::=  20

-- Severity Level: Error
                ttDSDataCorruptionTrap TRAP-TYPE
                        ENTERPRISE ttDSTraps
                        VARIABLES { ttTimeStamp, ttPid, ttUid, ttVersion, ttMesg,
                                ttDSName }
                        DESCRIPTION
                                "TimesTen Internal Data Corruption."
                        ::=  21

-- Severity Level: Error
                ttUnexpectedEndOfLogTrap TRAP-TYPE
                        ENTERPRISE ttRecoveryTraps
                        VARIABLES { ttTimeStamp, ttPid, ttUid, ttVersion, ttMesg,
                                ttDSName, endLFN, endLFO, maxLFN }
                        DESCRIPTION
                                "Premature end of log file reached during data store recovery."
                        ::=  22

-- Severity Level: Warning
                ttRepCatchupStartTrap TRAP-TYPE
                        ENTERPRISE ttRepTraps
                        VARIABLES { ttTimeStamp, ttPid, ttUid, ttVersion, ttMesg,
                                ttDSName }
                        DESCRIPTION
                                "Replication Master Catchup starting."
                        ::=  23

-- Severity Level: Warning
                ttRepCatchupStopTrap TRAP-TYPE
                        ENTERPRISE ttRepTraps
                        VARIABLES { ttTimeStamp, ttPid, ttUid, ttVersion, ttMesg,
                                ttDSName }
                        DESCRIPTION
                                "Replication Master Catchup stopping."
                        ::=  24

-- Severity Level: Error
                ttOraValidationErrorTrap TRAP-TYPE
                        ENTERPRISE ttOraTraps
                        VARIABLES { ttTimeStamp, ttPid, ttUid, ttVersion, ttMesg,
                                ttOraAgentPid, ttOraAgentName, ttOraDSName }
                        DESCRIPTION
                                "TimesTen Oracle Connect detected serious error during self validation."
                        ::=  25

-- Severity Level: Warning
                ttOraValidationWarningTrap TRAP-TYPE
                        ENTERPRISE ttOraTraps
                        VARIABLES { ttTimeStamp, ttPid, ttUid, ttVersion, ttMesg,
                                ttOraAgentPid, ttOraAgentName, ttOraDSName }
                        DESCRIPTION
                                "TimesTen Oracle Connect detected non-fatal error during self validation."
                        ::=  26

-- Severity Level: Error
                ttOraValidationAbortedTrap TRAP-TYPE
                        ENTERPRISE ttOraTraps
                        VARIABLES { ttTimeStamp, ttPid, ttUid, ttVersion, ttMesg,
                                ttOraAgentPid, ttOraAgentName, ttOraDSName }
                        DESCRIPTION
                                "TimesTen Oracle Connect aborted self validation."
                        ::=  27


        END

--
-- TimesTen-MIB.txt
--
