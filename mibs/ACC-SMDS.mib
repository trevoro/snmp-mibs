ACC-SMDS DEFINITIONS ::= BEGIN

    IMPORTS
		OBJECT-TYPE, IpAddress, TimeTicks, Gauge, Counter FROM RFC1155-SMI
		TRAP-TYPE FROM RFC-1215
      accTrapLogSeqNum FROM ACC-SYSTEM
	accBRG, DisplayString, RowStatus, IfIndex, SmdsAddress
             FROM ACC-MIB;
-- SMDS Group
      accSMDS         OBJECT IDENTIFIER ::= { accBRG 26 }
               -- The SMDS Port group
               accSmdsPortTable  OBJECT-TYPE
                   SYNTAX  SEQUENCE OF AccSmdsPortEntry
                   ACCESS  not-accessible
                   STATUS  mandatory
                   DESCRIPTION
                           "This table contains SMDS port parameters and
                           state variables, one entry per SMDS port."
                  ::= { accSMDS 1 }
              accSmdsPortEntry  OBJECT-TYPE
                  SYNTAX  AccSmdsPortEntry
                  ACCESS  not-accessible
                  STATUS  mandatory
                  DESCRIPTION
                          "This list contains SMDS port parameters and
                          state variables."
                 INDEX   { accSmdsPortIndex }
                 ::= { accSmdsPortTable 1 }
             AccSmdsPortEntry  ::= SEQUENCE {
                 accSmdsPortIndex
                     INTEGER,
                 accSmdsPortIA
                     SmdsAddress,
                 accSmdsPortPollingStatus 
		     INTEGER 
                 }
             accSmdsPortIndex  OBJECT-TYPE
                 SYNTAX  INTEGER (1..65535)
                 ACCESS  read-only
                 STATUS  mandatory
                 DESCRIPTION
                         "The value of this object identifies the SIP
                         port interface for which this entry contains
                         management information.  The value of this
                         object for a particular interface has the same
                         value as the ifIndex object, defined in RFC
                         1156 and RFC 1213, for the same interface."
                ::= { accSmdsPortEntry 1 }
             accSmdsPortIA  OBJECT-TYPE
                 SYNTAX  SmdsAddress
                 ACCESS  read-write
                 STATUS  mandatory
                 DESCRIPTION
                         "The value of this object specifies the SNI
			 Individual address configured for this SIP
			 interface port."
                ::= { accSmdsPortEntry 2 }
             accSmdsPortPollingStatus OBJECT-TYPE
		SYNTAX INTEGER {
			enabled(1),
			disabled(2)
			}
		ACCESS read-write
		STATUS mandatory
		DESCRIPTION
			"The administrative status of heartbeat
			polling for this SMDS port.  ON enables
			the generation of heartbeat polls, 
			and OFF disables it. Note: the status of
			this object does not affect the response
			to heartbeat polls received. We always 
			respond to polls received."
		DEFVAL { disabled }
		::= { accSmdsPortEntry 3 }
               -- The SIP Level 3 group
               -- Implementation of the SIP Level 3 group is mandatory
               -- for all systems implementing SIP Level 3.
               accSipL3Table  OBJECT-TYPE
                   SYNTAX  SEQUENCE OF AccSipL3Entry
                   ACCESS  not-accessible
                   STATUS  mandatory
                   DESCRIPTION
                           "This table contains SIP L3 parameters and
                           state variables, one entry per SIP port."
                  ::= { accSMDS 2 }
              accSipL3Entry  OBJECT-TYPE
                  SYNTAX  AccSipL3Entry
                  ACCESS  not-accessible
                  STATUS  mandatory
                  DESCRIPTION
                          "This list contains SIP L3 parameters and
                          state variables."
                 INDEX   { accSipL3Index }
                 ::= { accSipL3Table 1 }
             AccSipL3Entry  ::= SEQUENCE {
                 accSipL3Index
                     INTEGER,
                 accSipL3RcvIAs
                     Counter,
                 accSipL3RcvGAs
                     Counter,
                 accSipL3UnkIAs
                     Counter,
                 accSipL3UnkGAs
                     Counter,
                 accSipL3SndIAs
                     Counter,
                 accSipL3SndGAs
                     Counter,
                 accSipL3Errors
                     Counter,
                 accSipL3InvAddrs
                     Counter
                 }
             accSipL3Index  OBJECT-TYPE
                 SYNTAX  INTEGER (1..65535)
                 ACCESS  read-only
                 STATUS  mandatory
                 DESCRIPTION
                         "The value of this object identifies the SIP
                         port interface for which this entry contains
                         management information.  The value of this
                         object for a particular interface has the same
                         value as the ifIndex object, defined in RFC
                         1156 and RFC 1213, for the same interface."
                ::= { accSipL3Entry 1 }
            accSipL3RcvIAs OBJECT-TYPE
                SYNTAX  Counter
                ACCESS  read-only
                STATUS  mandatory
                DESCRIPTION
                        "The total number of individually addressed SIP
                        Level 3 PDUs received from the remote system
                        across the SNI.  The total includes only
                        unerrored L3PDUs."
               ::= { accSipL3Entry 2 }
           accSipL3RcvGAs OBJECT-TYPE
               SYNTAX  Counter
               ACCESS  read-only
               STATUS  mandatory
               DESCRIPTION
                       "The total number of group addressed SIP Level 3
                       PDUs received from the remote system across the
                       SNI.  The total includes only unerrored L3PDUs."
              ::= { accSipL3Entry 3 }
          accSipL3UnkIAs OBJECT-TYPE
              SYNTAX  Counter
              ACCESS  read-only
              STATUS  mandatory
              DESCRIPTION
                      "The number of SIP Level 3 PDUs received from the
                      remote system with invalid or unknown individual
                      destination addresses (Destination Address
                      Screening violations are not included).  See SMDS
                      Subscription MIB module."
              ::= { accSipL3Entry 4 }
          accSipL3UnkGAs OBJECT-TYPE
              SYNTAX  Counter
              ACCESS  read-only
              STATUS  mandatory
              DESCRIPTION
                      "The number of SIP Level 3 PDUs received from the
                      remote system with invalid or unknown group
                      addresses.  (Destination Address Screening
                      violations are not included).  See SMDS
                      Subscription MIB module."
              ::= { accSipL3Entry 5 }
          accSipL3SndIAs OBJECT-TYPE
              SYNTAX  Counter
              ACCESS  read-only
              STATUS  mandatory
              DESCRIPTION
                      "The number of individually addressed SIP Level 3
                      PDUs that have been sent by this system across the
                      SNI."
              ::= { accSipL3Entry 6 }
          accSipL3SndGAs OBJECT-TYPE
              SYNTAX  Counter
              ACCESS  read-only
              STATUS  mandatory
              DESCRIPTION
                      "The number of group addressed SIP L3PDUs that
                      have been sent by this system across the SNI."
              ::= { accSipL3Entry 7 }
          -- The total number of SIP L3PDU errors can be calculated as
          -- (Syntactic errors + Semantic Service errors )
          -- Syntactic errors include:
          --    accSipL3Errors
          -- Latest occurrences of syntactic error types are logged in
          --    accSipL3PDUErrorTable.
          -- Semantic Service errors include:
          --    accSipL3UnkIAs
          --    accSipL3UnkGAs
          --    accSipL3InvAddrs
          -- Note that public networks supporting SMDS may discard
          -- SIP L3PDUs due to subscription violations.  Related
          -- managed objects are defined in Definitions of Managed
          -- Objects for SMDS Subscription.
          accSipL3Errors OBJECT-TYPE
              SYNTAX  Counter
              ACCESS  read-only
              STATUS  mandatory
              DESCRIPTION
                      "The total number of SIP Level 3 PDUs received
                      from the remote system that were discovered to
                      have errors (including protocol processing and bit
                      errors but excluding addressing-related errors)
                      and were discarded.  Includes both group addressed
                      L3PDUs and L3PDUs containing an individual
                      destination address."
              ::= { accSipL3Entry 8 }
          accSipL3InvAddrs OBJECT-TYPE
              SYNTAX  Counter
              ACCESS  read-only
              STATUS  mandatory
              DESCRIPTION
                      "The number of SIP Level 3 PDUs received from the
                      remote system that had the Source or Destination
                      Address_Type subfields, (the four most significant
                      bits of the 64 bit address field), not equal to
                      the value 1100 or 1110.  Also, an error is
                      considered to have occurred if the Address_Type
                      field for a Source Address, the four most
                      significant bits of the 64 bits, is equal to 1110
                      (a group address)."
              ::= { accSipL3Entry 9 }

END
