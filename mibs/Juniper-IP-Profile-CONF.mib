-- *****************************************************************************
-- Juniper-IP-Profile-CONF
--
-- SNMP Agent Capabilities definitions for the IP Profile MIB.
--
-- Copyright (c) 2001 Unisphere Networks, Inc.
-- Copyright (c) 2002, 2003 Juniper Networks, Inc.
--   All rights reserved.
-- *****************************************************************************

Juniper-IP-Profile-CONF  DEFINITIONS ::= BEGIN

IMPORTS
    MODULE-IDENTITY
        FROM SNMPv2-SMI
    AGENT-CAPABILITIES
        FROM SNMPv2-CONF
    juniProfileAgents
        FROM Juniper-Agents;

juniIpProfileAgent  MODULE-IDENTITY
    LAST-UPDATED "200509131721Z"  -- 13-Sep-05 01:21 PM EDT
    ORGANIZATION "Juniper Networks, Inc."
    CONTACT-INFO
        "       Juniper Networks, Inc.
        Postal: 10 Technology Park Drive
                Westford, MA  01886-3146
                USA
        Tel:    +1 978 589 5800
        E-mail: mib@Juniper.net"
    DESCRIPTION
        "The agent capabilities definitions for the IP Profile Manager component
        of the SNMP agent in the Juniper E-series family of products."
    -- Revision History

    REVISION    "200509131721Z"  -- 13-Sep-05 01:21 PM EDT  - JUNOSe 7.2
    DESCRIPTION
        "Added support for Flow Stats a.k.a. J-Flow for  IP Interfaces -
        rsIpProfileFlowStats."
    REVISION    "200410051404Z"  -- 05-Oct-04 10:04 AM EDT  - JUNOSe 7.0
    DESCRIPTION
        "Added support for IP filter options all for  IP Interfaces -
        rsIpProfileFilterOptionsAll."
    REVISION    "200309241533Z"  -- 24-Sep-03 11:33 AM EDT  - JUNOSe 5.2
    DESCRIPTION
        "Added support for TCP MSS configuration of IP Interfaces -
        rsIpProfileTcpMss."
    REVISION    "200210091431Z"  -- 09-Oct-02 10:31 AM EDT  - JUNOSe 5.0
    DESCRIPTION
        "Replaced Unisphere names with Juniper names.
        Obsoleted loopback objects for unnumbered interfaces and added
        inherited numbered interface objects in juniIpProfileTable
        (required the addition of juniIpProfileGroup3)."
    REVISION    "200103282143Z"  -- 28-Mar-01 04:43 PM EST  - JUNOSe 3.2
    DESCRIPTION
        "The initial release of this management information module."
    ::= { juniProfileAgents 2 }


-- *****************************************************************************
-- IP Profile SNMP Agent Capabilities definitions
-- *****************************************************************************
juniIpProfileAgentV1  AGENT-CAPABILITIES
    PRODUCT-RELEASE
        "Version 1 of the IP Profile component of the JUNOSe SNMP agent.  This
        version of the IP Profile Manager component was supported in JUNOSe 1.x
        system releases."
    STATUS      obsolete
    DESCRIPTION
        "The MIB supported by the SNMP agent for the IP Profile Manager
        application in JUNOSe.  These capabilities became obsolete when the
        profile loopback object changed."
    SUPPORTS    Juniper-IP-PROFILE-MIB
        INCLUDES {
            juniIpProfileGroup }
    ::= { juniIpProfileAgent 1 }

juniIpProfileAgentV2  AGENT-CAPABILITIES
    PRODUCT-RELEASE
        "Version 2 of the IP Profile component of the JUNOSe SNMP agent.  This
        version of the IP Profile Manager component was supported in JUNOSe 2.x
        system releases."
    STATUS      obsolete
    DESCRIPTION
        "The MIB supported by the SNMP agent for the IP Profile Manager
        application in JUNOSe.  These capabilities became obsolete when
        juniIpProfileRowStatus was deprecate and the juniIpProfileSetMap and
        juniIpProfileSrcAddrValidEnable objects were added."
    SUPPORTS    Juniper-IP-PROFILE-MIB
        INCLUDES {
            juniIpProfileGroup1 }
    ::= { juniIpProfileAgent 2 }

juniIpProfileAgentV3  AGENT-CAPABILITIES
    PRODUCT-RELEASE
        "Version 3 of the IP Profile component of the JUNOSe SNMP agent.  This
        version of the IP Profile Manager component was supported in JUNOSe 3.0
        through 4.x system releases."
    STATUS      obsolete
    DESCRIPTION
        "The MIB supported by the SNMP agent for the IP Profile Manager
        application in JUNOSe.  These capabilities became obsolete when
        juniIpProfileLoopback was made obsolete and the
        juniIpProfileInheritNumString object was added."
    SUPPORTS    Juniper-IP-PROFILE-MIB
        INCLUDES {
            juniIpProfileGroup2,
            juniIpProfileDeprecatedGroup }
        VARIATION   juniIpProfileRowStatus
            ACCESS      read-only
            DESCRIPTION
                "Entries in the juniIpProfileTable cannot be created via SNMP in
                this agent."
        VARIATION   juniIpProfileRouterName
            ACCESS      read-write
            DESCRIPTION
                "Entries in the juniIpProfileTable cannot be created via SNMP in
                this agent."
        VARIATION   juniIpProfileIpAddr
            ACCESS      read-write
            DESCRIPTION
                "Entries in the juniIpProfileTable cannot be created via SNMP in
                this agent."
        VARIATION   juniIpProfileIpMask
            ACCESS      read-write
            DESCRIPTION
                "Entries in the juniIpProfileTable cannot be created via SNMP in
                this agent."
        VARIATION   juniIpProfileDirectedBcastEnable
            ACCESS      read-write
            DESCRIPTION
                "Entries in the juniIpProfileTable cannot be created via SNMP in
                this agent."
        VARIATION   juniIpProfileIcmpRedirectEnable
            ACCESS      read-write
            DESCRIPTION
                "Entries in the juniIpProfileTable cannot be created via SNMP in
                this agent."
        VARIATION   juniIpProfileAccessRoute
            ACCESS      read-write
            DESCRIPTION
                "Entries in the juniIpProfileTable cannot be created via SNMP in
                this agent."
        VARIATION   juniIpProfileMtu
            ACCESS      read-write
            DESCRIPTION
                "Entries in the juniIpProfileTable cannot be created via SNMP in
                this agent."
        VARIATION   juniIpProfileLoopback
            ACCESS      read-write
            DESCRIPTION
                "Entries in the juniIpProfileTable cannot be created via SNMP in
                this agent."
        VARIATION   juniIpProfileSetMap
            ACCESS      read-write
            DESCRIPTION
                "Entries in the juniIpProfileTable cannot be created via SNMP in
                this agent."
        VARIATION   juniIpProfileSrcAddrValidEnable
            ACCESS      read-write
            DESCRIPTION
                "Entries in the juniIpProfileTable cannot be created via SNMP in
                this agent."
    ::= { juniIpProfileAgent 3 }

juniIpProfileAgentV4  AGENT-CAPABILITIES
    PRODUCT-RELEASE
        "Version 4 of the IP Profile component of the JUNOSe SNMP agent.  This
        version of the IP Profile Manager component was supported in JUNOSe 5.0
        and 5.1 system releases."
    STATUS      obsolete
    DESCRIPTION
        "The MIB supported by the SNMP agent for the IP Profile Manager
        application in JUNOSe.  These capabilities were made obsolete when TCP
        MSS configuration support for IP Interface was added."
    SUPPORTS    Juniper-IP-PROFILE-MIB
        INCLUDES {
            juniIpProfileGroup3,
            juniIpProfileDeprecatedGroup }
        VARIATION   juniIpProfileRowStatus
            ACCESS      read-only
            DESCRIPTION
                "Entries in the juniIpProfileTable cannot be created via SNMP in
                this agent."
        VARIATION   juniIpProfileRouterName
            ACCESS      read-write
            DESCRIPTION
                "Entries in the juniIpProfileTable cannot be created via SNMP in
                this agent."
        VARIATION   juniIpProfileIpAddr
            ACCESS      read-write
            DESCRIPTION
                "Entries in the juniIpProfileTable cannot be created via SNMP in
                this agent."
        VARIATION   juniIpProfileIpMask
            ACCESS      read-write
            DESCRIPTION
                "Entries in the juniIpProfileTable cannot be created via SNMP in
                this agent."
        VARIATION   juniIpProfileDirectedBcastEnable
            ACCESS      read-write
            DESCRIPTION
                "Entries in the juniIpProfileTable cannot be created via SNMP in
                this agent."
        VARIATION   juniIpProfileIcmpRedirectEnable
            ACCESS      read-write
            DESCRIPTION
                "Entries in the juniIpProfileTable cannot be created via SNMP in
                this agent."
        VARIATION   juniIpProfileAccessRoute
            ACCESS      read-write
            DESCRIPTION
                "Entries in the juniIpProfileTable cannot be created via SNMP in
                this agent."
        VARIATION   juniIpProfileMtu
            ACCESS      read-write
            DESCRIPTION
                "Entries in the juniIpProfileTable cannot be created via SNMP in
                this agent."
        VARIATION   juniIpProfileLoopback
            ACCESS      read-write
            DESCRIPTION
                "Entries in the juniIpProfileTable cannot be created via SNMP in
                this agent."
        VARIATION   juniIpProfileSetMap
            ACCESS      read-write
            DESCRIPTION
                "Entries in the juniIpProfileTable cannot be created via SNMP in
                this agent."
        VARIATION   juniIpProfileSrcAddrValidEnable
            ACCESS      read-write
            DESCRIPTION
                "Entries in the juniIpProfileTable cannot be created via SNMP in
                this agent."
    ::= { juniIpProfileAgent 4 }

juniIpProfileAgentV5  AGENT-CAPABILITIES
    PRODUCT-RELEASE
        "Version 5 of the IP Profile component of the JUNOSe SNMP agent.  This
        version of the IP Profile Manager component was supported in JUNOSe 5.2, 5.3, and 6.x
        Now obsolete after IP filter options all support"
    STATUS      obsolete
    DESCRIPTION
        "The MIB supported by the SNMP agent for the IP Profile Manager
        application in JUNOSe."
    SUPPORTS    Juniper-IP-PROFILE-MIB
        INCLUDES {
            juniIpProfileGroup4,
            juniIpProfileDeprecatedGroup }
        VARIATION   juniIpProfileRowStatus
            ACCESS      read-only
            DESCRIPTION
                "Entries in the juniIpProfileTable cannot be created via SNMP in
                this agent."
        VARIATION   juniIpProfileRouterName
            ACCESS      read-write
            DESCRIPTION
                "Entries in the juniIpProfileTable cannot be created via SNMP in
                this agent."
        VARIATION   juniIpProfileIpAddr
            ACCESS      read-write
            DESCRIPTION
                "Entries in the juniIpProfileTable cannot be created via SNMP in
                this agent."
        VARIATION   juniIpProfileIpMask
            ACCESS      read-write
            DESCRIPTION
                "Entries in the juniIpProfileTable cannot be created via SNMP in
                this agent."
        VARIATION   juniIpProfileDirectedBcastEnable
            ACCESS      read-write
            DESCRIPTION
                "Entries in the juniIpProfileTable cannot be created via SNMP in
                this agent."
        VARIATION   juniIpProfileIcmpRedirectEnable
            ACCESS      read-write
            DESCRIPTION
                "Entries in the juniIpProfileTable cannot be created via SNMP in
                this agent."
        VARIATION   juniIpProfileAccessRoute
            ACCESS      read-write
            DESCRIPTION
                "Entries in the juniIpProfileTable cannot be created via SNMP in
                this agent."
        VARIATION   juniIpProfileMtu
            ACCESS      read-write
            DESCRIPTION
                "Entries in the juniIpProfileTable cannot be created via SNMP in
                this agent."
        VARIATION   juniIpProfileLoopback
            ACCESS      read-write
            DESCRIPTION
                "Entries in the juniIpProfileTable cannot be created via SNMP in
                this agent."
        VARIATION   juniIpProfileSetMap
            ACCESS      read-write
            DESCRIPTION
                "Entries in the juniIpProfileTable cannot be created via SNMP in
                this agent."
        VARIATION   juniIpProfileSrcAddrValidEnable
            ACCESS      read-write
            DESCRIPTION
                "Entries in the juniIpProfileTable cannot be created via SNMP in
                this agent."
        VARIATION   juniIpProfileTcpMss
            ACCESS      read-write
            DESCRIPTION
                "Entries in the juniIpProfileTable cannot be created via SNMP in
                this agent."
    ::= { juniIpProfileAgent 5 }

juniIpProfileAgentV6  AGENT-CAPABILITIES
    PRODUCT-RELEASE
        "Version 6 of the IP Profile component of the JUNOSe SNMP agent.  This
        version of the IP Profile Manager component is supported in JUNOSe 7.0
        and subsequent system releases. "
    STATUS      current
    DESCRIPTION
        "The MIB supported by the SNMP agent for the IP Profile Manager
        application in JUNOSe."
    SUPPORTS    Juniper-IP-PROFILE-MIB
        INCLUDES {
            juniIpProfileGroup5,
            juniIpProfileDeprecatedGroup }
        VARIATION   juniIpProfileRowStatus
            ACCESS      read-only
            DESCRIPTION
                "Entries in the juniIpProfileTable cannot be created via SNMP in
                this agent."
        VARIATION   juniIpProfileRouterName
            ACCESS      read-write
            DESCRIPTION
                "Entries in the juniIpProfileTable cannot be created via SNMP in
                this agent."
        VARIATION   juniIpProfileIpAddr
            ACCESS      read-write
            DESCRIPTION
                "Entries in the juniIpProfileTable cannot be created via SNMP in
                this agent."
        VARIATION   juniIpProfileIpMask
            ACCESS      read-write
            DESCRIPTION
                "Entries in the juniIpProfileTable cannot be created via SNMP in
                this agent."
        VARIATION   juniIpProfileDirectedBcastEnable
            ACCESS      read-write
            DESCRIPTION
                "Entries in the juniIpProfileTable cannot be created via SNMP in
                this agent."
        VARIATION   juniIpProfileIcmpRedirectEnable
            ACCESS      read-write
            DESCRIPTION
                "Entries in the juniIpProfileTable cannot be created via SNMP in
                this agent."
        VARIATION   juniIpProfileAccessRoute
            ACCESS      read-write
            DESCRIPTION
                "Entries in the juniIpProfileTable cannot be created via SNMP in
                this agent."
        VARIATION   juniIpProfileMtu
            ACCESS      read-write
            DESCRIPTION
                "Entries in the juniIpProfileTable cannot be created via SNMP in
                this agent."
        VARIATION   juniIpProfileLoopback
            ACCESS      read-write
            DESCRIPTION
                "Entries in the juniIpProfileTable cannot be created via SNMP in
                this agent."
        VARIATION   juniIpProfileSetMap
            ACCESS      read-write
            DESCRIPTION
                "Entries in the juniIpProfileTable cannot be created via SNMP in
                this agent."
        VARIATION   juniIpProfileSrcAddrValidEnable
            ACCESS      read-write
            DESCRIPTION
                "Entries in the juniIpProfileTable cannot be created via SNMP in
                this agent."
        VARIATION   juniIpProfileTcpMss
            ACCESS      read-write
            DESCRIPTION
                "Entries in the juniIpProfileTable cannot be created via SNMP in
                this agent."
        VARIATION   juniIpProfileFilterOptionsAll
            ACCESS      read-write
            DESCRIPTION
                "Entries in the juniIpProfileTable cannot be created via SNMP in
                this agent."
    ::= { juniIpProfileAgent 6 }

END
