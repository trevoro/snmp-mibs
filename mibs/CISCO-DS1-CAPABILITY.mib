-- *****************************************************************
-- CISCO-DS1-CAPABILITY
--
-- AGENT-CAPABILITIES MIB for DS1-MIB for CISCO Products
--
-- December 2003, Yizhong Shen
--
-- Copyright(c) 2002, 2003, 2005 by Cisco Systems,Inc.
-- 
-- *****************************************************************

CISCO-DS1-CAPABILITY DEFINITIONS ::= BEGIN

IMPORTS
        MODULE-IDENTITY
                FROM SNMPv2-SMI
        AGENT-CAPABILITIES
                FROM SNMPv2-CONF
        ciscoAgentCapability
                FROM CISCO-SMI;

ciscoDs1Capability MODULE-IDENTITY
        LAST-UPDATED    "200507110000Z"
        ORGANIZATION    "Cisco Systems, Inc."
        CONTACT-INFO
                "       Cisco Systems
                        Customer Service

                Postal: 170 W Tasman Drive
                        San Jose, CA  95134
                        USA

                        Tel: +1 800 553-NETS

                E-mail: cs-wanatm@cisco.com"
DESCRIPTION
    "The agent capabilities for DS1-MIB for Cisco Products Series.
     - ciscoDs1AxsmeCapabilityV3R00 is for
       Enhanced ATM Switch Service Module(AXSM-E), and
       Enhanced Processor Switch Module 1(PXM1E) uplink.

     - ciscoDs1CapabilityV5R00 is for Voice Switch
       Service Module(VXSM) and MPSM Module Release 5.0.0."

REVISION    "200507110000Z"
DESCRIPTION
    "Added ciscoDs1CapabilityV5R100 for MPSM and VXSM support in 
     MGX8880 release 5.1.0."

REVISION    "200312220000Z"
DESCRIPTION
    "ciscoDs1CapabilityV5R00 added for MPSM and VXSM support."

REVISION    "200204280000Z"
DESCRIPTION
    "Initial version of this MIB module."

::= { ciscoAgentCapability  273 }


ciscoDs1AxsmeCapabilityV3R00 AGENT-CAPABILITIES

PRODUCT-RELEASE "MGX8850 Release 3.0"
STATUS          current
DESCRIPTION     "DS1-MIB Capabilities."

SUPPORTS        DS1-MIB
INCLUDES        { ds1NearEndConfigGroup, ds1NearEndStatisticsGroup,
                  ds1FarEndGroup }

VARIATION       dsx1LineType
SYNTAX          INTEGER {dsx1ESF(2),
                         dsx1E1CRCMF(7)}
ACCESS          read-only
DESCRIPTION     "Supported with limitation.
                 dsx1ESF(2)     used only for T1 mode,
                 dsx1E1CRCMF(7) used only for E1 mode."

VARIATION       dsx1LineCoding
SYNTAX          INTEGER {dsx1B8ZS(2),
                         dsx1HDB3(3)}
ACCESS          read-only
DESCRIPTION     "Supported with limitation.
                 dsx1B8ZS(2)    used only for T1 mode,
                 dsx1HDB3(3)    used only for E1 mode."

VARIATION       dsx1SendCode
ACCESS          not-implemented
DESCRIPTION     "Not Supported."

VARIATION       dsx1CircuitIdentifier
ACCESS          not-implemented
DESCRIPTION     "Not Supported."

VARIATION       dsx1LoopbackConfig
SYNTAX          INTEGER {dsx1NoLoop(1),
                         dsx1LineLoop(3),
                         dsx1InwardLoop(5)}
DESCRIPTION     "Supported with limitation."

VARIATION       dsx1SignalMode
ACCESS          not-implemented
DESCRIPTION     "Not Supported."

VARIATION       dsx1Fdl
ACCESS          not-implemented
DESCRIPTION     "Not Supported."

VARIATION       dsx1LineStatusLastChange
ACCESS          not-implemented
DESCRIPTION     "Not Supported."

VARIATION       dsx1LineStatusChangeTrapEnable
ACCESS          not-implemented
DESCRIPTION     "Not Supported."

VARIATION       dsx1LoopbackStatus
DESCRIPTION     "The agent only sets following bits:
                  1  dsx1NoLoopback
                 16  dsx1NearEndInwardLoopback
                 64  dsx1FarEndLineLoopback."

VARIATION       dsx1Ds1ChannelNumber
ACCESS          not-implemented
DESCRIPTION     "Not Supported."

VARIATION       dsx1Channelization
ACCESS          not-implemented
DESCRIPTION     "Not Supported."

VARIATION       dsx1CurrentCSSs
ACCESS          not-implemented
DESCRIPTION     "Not Supported."

VARIATION       dsx1CurrentBESs
ACCESS          not-implemented
DESCRIPTION     "Not Supported."

VARIATION       dsx1CurrentDMs
ACCESS          not-implemented
DESCRIPTION     "Not Supported."

VARIATION       dsx1IntervalCSSs
ACCESS          not-implemented
DESCRIPTION     "Not Supported."

VARIATION       dsx1IntervalBESs
ACCESS          not-implemented
DESCRIPTION     "Not Supported."

VARIATION       dsx1IntervalDMs
ACCESS          not-implemented
DESCRIPTION     "Not Supported."

VARIATION       dsx1TotalCSSs
ACCESS          not-implemented
DESCRIPTION     "Not Supported."

VARIATION       dsx1TotalBESs
ACCESS          not-implemented
DESCRIPTION     "Not Supported."

VARIATION       dsx1TotalDMs
ACCESS          not-implemented
DESCRIPTION     "Not Supported."

VARIATION       dsx1FarEndCurrentCSSs
ACCESS          not-implemented
DESCRIPTION     "Not Supported."

VARIATION       dsx1FarEndCurrentBESs
ACCESS          not-implemented
DESCRIPTION     "Not Supported."

VARIATION       dsx1FarEndCurrentDMs
ACCESS          not-implemented
DESCRIPTION     "Not Supported."

VARIATION       dsx1FarEndIntervalCSSs
ACCESS          not-implemented
DESCRIPTION     "Not Supported."

VARIATION       dsx1FarEndIntervalBESs
ACCESS          not-implemented
DESCRIPTION     "Not Supported."

VARIATION       dsx1FarEndIntervalDMs
ACCESS          not-implemented
DESCRIPTION     "Not Supported."

VARIATION       dsx1FarEndTotalCSSs
ACCESS          not-implemented
DESCRIPTION     "Not Supported."

VARIATION       dsx1FarEndTotalBESs
ACCESS          not-implemented
DESCRIPTION     "Not Supported."

VARIATION       dsx1FarEndTotalDMs
ACCESS          not-implemented
DESCRIPTION     "Not Supported."

    ::= { ciscoDs1Capability 1 }

ciscoDs1CapabilityV5R00 AGENT-CAPABILITIES

PRODUCT-RELEASE "MGX8850 Release 5.0.0"
STATUS          current
DESCRIPTION     "DS1 MIB capabilities for VXSM and
                 MPSM in release 5.0.0"

SUPPORTS     DS1-MIB
INCLUDES     {  ds1NearEndConfigGroup,
                ds1NearEndStatisticsGroup,
                ds1FarEndGroup,
                ds1NearEndOptionalConfigGroup         
             }

--
-- VXSM variation
--
VARIATION    dsx1LineCoding
DESCRIPTION  "Only supported by T1/E1 card 
              (entPhysicalVendorType is cevVxsm48t1e1)."

--
-- VXSM variation
--
VARIATION    dsx1LineLength
SYNTAX       INTEGER (0..200)
DESCRIPTION  "Only supported by T1/E1 card 
              (entPhysicalVendorType is cevVxsm48t1e1),
              for T1 only."

VARIATION    dsx1CircuitIdentifier
ACCESS       not-implemented
DESCRIPTION  "Not supported."

VARIATION    dsx1LineStatusLastChange
ACCESS       not-implemented
DESCRIPTION  "Not supported."

VARIATION    dsx1Ds1ChannelNumber
ACCESS       not-implemented
DESCRIPTION  "Not supported."

--
-- VXSM variation
--
VARIATION    dsx1LineMode
DESCRIPTION  "Only supported by T1/E1 card 
              (entPhysicalVendorType is cevVxsm48t1e1), 
              for T1 only."

--
-- VXSM variation
--
VARIATION    dsx1LineBuildOut
DESCRIPTION  "Only supported by T1/E1 card 
              (entPhysicalVendorType is cevVxsm48t1e1), 
              for T1 only."

VARIATION    dsx1CurrentDMs
ACCESS       not-implemented
DESCRIPTION  "Not supported."

VARIATION    dsx1IntervalDMs
ACCESS       not-implemented
DESCRIPTION  "Not supported."

VARIATION    dsx1TotalDMs
ACCESS       not-implemented
DESCRIPTION  "Not supported."

VARIATION    dsx1FarEndCurrentDMs
ACCESS       not-implemented
DESCRIPTION  "Not supported."

VARIATION    dsx1FarEndIntervalDMs
ACCESS       not-implemented
DESCRIPTION  "Not supported."

VARIATION    dsx1FarEndTotalDMs
ACCESS       not-implemented
DESCRIPTION  "Not supported."

VARIATION    dsx1LineType
SYNTAX       INTEGER { dsx1ESF(2),
                       dsx1D4(3),
                       dsx1E1(4),
                       dsx1E1CRC(5),
                       dsx1E1MF(6),
                       dsx1E1CRCMF(7),
                       dsx1E1Q50(12),
                       dsx1E1Q50CRC(13) 
                     }
DESCRIPTION  "Limited data values are supported.
              For T1, valid values are 2 and 3.
              For E1, valud values are 4..7, 12 and 13."

VARIATION    dsx1SendCode
SYNTAX       INTEGER { dsx1SendNoCode   (1), 
                       dsx1SendLineCode (2),
                       dsx1SendResetCode(4) 
                     }
DESCRIPTION  "dsx1SendPayloadCode(3),
              dsx1SendQRS(5), 
              dsx1Send511Pattern(6),
              dsx1Send3in24Pattern(7),
              dsx1SendOtherTestPattern(8) 
              are not supported on T1.
              This object is not supported on E1."

VARIATION    dsx1LoopbackConfig
SYNTAX       INTEGER { dsx1NoLoop    (1), 
                       dsx1LineLoop  (3),
                       dsx1InwardLoop(5) 
                     }
DESCRIPTION  "dsx1PayloadLoop(2), dsx1OtherLoop(4), 
              and dsx1DualLoop(6) are not supported."

VARIATION    dsx1LineStatus
DESCRIPTION  "dsx1OtherFailure (bit 4096) is used to indicate
              the line is in BERT testing."

VARIATION    dsx1SignalMode
SYNTAX       INTEGER { none            (1), 
                       robbedBit       (2),
                       bitOriented     (3),
                       messageOriented (4)
                     }
DESCRIPTION  "other(5) is not supported.
              For T1, valid values are 1, 2 and 4.
              For E1, valid values are 1, 3 and 4."

VARIATION    dsx1Fdl
SYNTAX       INTEGER (2..2)
ACCESS       read-only
DESCRIPTION  "Only  dsx1AnsiT1403(2) is supported.
              Set is not allowed."

VARIATION    dsx1LineStatusChangeTrapEnable
DEFVAL       { enabled }
DESCRIPTION  "The initial value is enabled(1)."

VARIATION    dsx1Channelization
SYNTAX       INTEGER { enabledDs0(2) }
ACCESS       read-only
DESCRIPTION  "disabled(1) and enabledDs1(3) are not supported.
              Set is not allowed."

VARIATION    dsx1FarEndCurrentTable
DESCRIPTION  "It is not supported on E1."

VARIATION    dsx1FarEndIntervalTable
DESCRIPTION  "It is not supported on E1."

VARIATION    dsx1FarEndTotalTable
DESCRIPTION  "It is not supported on E1."

    ::= { ciscoDs1Capability 2 }

ciscoDs1CapabilityV5R100 AGENT-CAPABILITIES

PRODUCT-RELEASE "MGX8880 Release 5.1.0"
STATUS          current
DESCRIPTION     "DS1 MIB capabilities for VXSM and
                 MPSM in release 5.1.0"

SUPPORTS     DS1-MIB
INCLUDES     {  ds1NearEndConfigGroup,
                ds1NearEndStatisticsGroup,
                ds1FarEndGroup,
                ds1NearEndOptionalConfigGroup         
             }

--
-- VXSM variation
--
VARIATION    dsx1LineCoding
DESCRIPTION  "Only supported by T1/E1 card 
              (entPhysicalVendorType is cevVxsm48t1e1)."

--
-- VXSM variation
--
VARIATION    dsx1LineLength
SYNTAX       INTEGER (0..200)
DESCRIPTION  "Only supported by T1/E1 card 
              (entPhysicalVendorType is cevVxsm48t1e1),
              for T1 only."

VARIATION    dsx1CircuitIdentifier
ACCESS       not-implemented
DESCRIPTION  "Not supported."

VARIATION    dsx1LineStatusLastChange
ACCESS       not-implemented
DESCRIPTION  "Not supported."

VARIATION    dsx1Ds1ChannelNumber
ACCESS       not-implemented
DESCRIPTION  "Not supported."

--
-- VXSM variation
--
VARIATION    dsx1LineMode
DESCRIPTION  "Only supported by T1/E1 card 
              (entPhysicalVendorType is cevVxsm48t1e1), 
              for T1 only."

--
-- VXSM variation
--
VARIATION    dsx1LineBuildOut
DESCRIPTION  "Only supported by T1/E1 card 
              (entPhysicalVendorType is cevVxsm48t1e1), 
              for T1 only."

VARIATION    dsx1CurrentDMs
ACCESS       not-implemented
DESCRIPTION  "Not supported."

VARIATION    dsx1IntervalDMs
ACCESS       not-implemented
DESCRIPTION  "Not supported."

VARIATION    dsx1TotalDMs
ACCESS       not-implemented
DESCRIPTION  "Not supported."

VARIATION    dsx1FarEndCurrentDMs
ACCESS       not-implemented
DESCRIPTION  "Not supported."

VARIATION    dsx1FarEndIntervalDMs
ACCESS       not-implemented
DESCRIPTION  "Not supported."

VARIATION    dsx1FarEndTotalDMs
ACCESS       not-implemented
DESCRIPTION  "Not supported."

VARIATION    dsx1LineType
SYNTAX       INTEGER { dsx1ESF(2),
                       dsx1D4(3),
                       dsx1E1(4),
                       dsx1E1CRC(5),
                       dsx1E1MF(6),
                       dsx1E1CRCMF(7),
                       dsx1E1Q50(12),
                       dsx1E1Q50CRC(13) 
                     }
DESCRIPTION  "Limited data values are supported.
              For T1, valid values are 2 and 3.
              For E1, valud values are 4..7, 12 and 13."

VARIATION    dsx1SendCode
SYNTAX       INTEGER { dsx1SendNoCode   (1), 
                       dsx1SendLineCode (2),
                       dsx1SendResetCode(4) 
                     }
DESCRIPTION  "dsx1SendPayloadCode(3),
              dsx1SendQRS(5), 
              dsx1Send511Pattern(6),
              dsx1Send3in24Pattern(7),
              dsx1SendOtherTestPattern(8) 
              are not supported on T1.
              This object is not supported on E1."

VARIATION    dsx1LoopbackConfig
SYNTAX       INTEGER { dsx1NoLoop    (1), 
                       dsx1LineLoop  (3),
                       dsx1InwardLoop(5) 
                     }
DESCRIPTION  "dsx1PayloadLoop(2), dsx1OtherLoop(4), 
              and dsx1DualLoop(6) are not supported."

VARIATION    dsx1LineStatus
DESCRIPTION  "dsx1OtherFailure (bit 4096) is used to indicate
              the line is in BERT testing."

VARIATION    dsx1SignalMode
SYNTAX       INTEGER { none            (1), 
                       robbedBit       (2),
                       bitOriented     (3)
                     }
DESCRIPTION  "other(5) is not supported.
              For T1, valid values are 1, and 2 
              For E1, valid values are 1, and 3."

VARIATION    dsx1Fdl
SYNTAX       INTEGER (2..2)
ACCESS       read-only
DESCRIPTION  "Only  dsx1AnsiT1403(2) is supported.
              Set is not allowed."

VARIATION    dsx1LineStatusChangeTrapEnable
DEFVAL       { enabled }
DESCRIPTION  "The initial value is enabled(1)."

VARIATION    dsx1Channelization
SYNTAX       INTEGER { enabledDs0(2) }
ACCESS       read-only
DESCRIPTION  "disabled(1) and enabledDs1(3) are not supported.
              Set is not allowed."

VARIATION    dsx1FarEndCurrentTable
DESCRIPTION  "It is not supported on E1."

VARIATION    dsx1FarEndIntervalTable
DESCRIPTION  "It is not supported on E1."

VARIATION    dsx1FarEndTotalTable
DESCRIPTION  "It is not supported on E1."

    ::= { ciscoDs1Capability 3 }

END
