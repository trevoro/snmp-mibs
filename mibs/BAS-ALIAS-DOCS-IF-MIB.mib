BAS-ALIAS-DOCS-IF-MIB DEFINITIONS ::= BEGIN

  IMPORTS
        MODULE-IDENTITY,
        OBJECT-TYPE,
  -- do not import        BITS,
        Unsigned32,
        Integer32,
        Counter32,
        TimeTicks,
        IpAddress,
        transmission
                FROM SNMPv2-SMI
        TEXTUAL-CONVENTION,
        MacAddress,
        RowStatus,
        TruthValue,
        TimeInterval,
        TimeStamp
                FROM SNMPv2-TC
        OBJECT-GROUP,

        MODULE-COMPLIANCE
                FROM SNMPv2-CONF
        ifIndex --, InterfaceIndexOrZero
                FROM IF-MIB

		basAliasDocsIf, 
		BasChassisId,
		BasSlotId,
		BasInterfaceId,
		BasLogicalPortId
				FROM BAS-MIB;

basAliasDocsIfMib MODULE-IDENTITY
        LAST-UPDATED    "9908190000Z" -- August 19, 1999
		ORGANIZATION "Broadband Access Systems"
        CONTACT-INFO
		" Tech Support
		  Broadband Access Systems
		  8 Technology Drive
		  Westborough, MA  01581
		  U.S.A.
		  
		  (508)366-8833
		  support@basystems.com"
        DESCRIPTION
            "This is the MIB Module for MCNS/DOCSIS compliant Radio
             Frequency (RF) interfaces in Cable Modems (CM) and
             Cable Modem Termination Systems (CMTS)."
        REVISION "9908190000Z"
        DESCRIPTION
		"This MIB module defines the Alias DocsIf MIB objects
		 for a Broadband Access System Cluster."
	::= { basAliasDocsIf 1 }

-- Textual Conventions

-- The following textual convention is from the
-- Interfaces MIB draft. It should go away once this
-- draft has been published as RFC.

InterfaceIndexOrZero ::= TEXTUAL-CONVENTION
    DISPLAY-HINT "d"
    STATUS       current
    DESCRIPTION
            "This textual convention is an extension of the
            InterfaceIndex convention.  The latter defines a
            greater than zero value used to identify an interface
            or interface sub-layer in the managed system.  This
            extension permits the additional value of zero.  the
            value zero is object-specific and must therefore be
            defined as part of the description of any object which
            uses this syntax.  Examples of the usage of zero might
            include situations where interface was unknown, or
            when none or all interfaces need to be referenced."
    SYNTAX       Integer32 (0..2147483647)

TenthdBmV ::= TEXTUAL-CONVENTION
        DISPLAY-HINT "d-1"
        STATUS       current
        DESCRIPTION
            "This data type represents power levels that are normally
             expressed in dBmV. Units are in tenths of a dBmV;
             for example, 5.1 dBmV will be represented as 51."
        SYNTAX       Integer32

TenthdB ::= TEXTUAL-CONVENTION
        DISPLAY-HINT "d-1"
        STATUS       current
        DESCRIPTION
            "This data type represents power levels that are normally
             expressed in dB. Units are in tenths of a dB;
             for example, 5.1 dB will be represented as 51."
        SYNTAX       Integer32

basDocsIfMibObjects  OBJECT IDENTIFIER ::= { basAliasDocsIfMib 1 }

basDocsIfBaseObjects OBJECT IDENTIFIER ::= { basDocsIfMibObjects 1 }
basDocsIfCmObjects   OBJECT IDENTIFIER ::= { basDocsIfMibObjects 2 }
basDocsIfCmtsObjects OBJECT IDENTIFIER ::= { basDocsIfMibObjects 3 }

--
-- BASE GROUP
--

-- The following table describes the attributes of each class of
-- service.  The entries in this table are referenced from the
-- docsIfServiceEntries.  They exist as a separate table in order to
-- reduce redundant information in docsIfServiceTable.
--
-- This table is implemented at both the CM and the CMTS.
-- The CM need only maintain entries for the classes of service
-- referenced by its docsIfServiceTable.
--

basDocsIfQosProfileTable OBJECT-TYPE
        SYNTAX      SEQUENCE OF BasDocsIfQosProfileEntry
        MAX-ACCESS  not-accessible
        STATUS      current
        DESCRIPTION
            "Describes the attributes for each class of service."
        ::= { basDocsIfBaseObjects 3 }

basDocsIfQosProfileEntry OBJECT-TYPE
        SYNTAX      BasDocsIfQosProfileEntry
        MAX-ACCESS  not-accessible
        STATUS      current
        DESCRIPTION
            "Describes the attributes for a single class of service.

             If implemented as read-create in the Cable Modem
             Termination System, creation of entries in this table is
             controlled by the value of docsIfCmtsQosProfilePermissions.

             If implemented as read-only, entries are created based
             on information in REG-REQ MAC messages received from
             Cable Modems (Cable Modem Termination System
             implementation), or based on information extracted from
             the TFTP option file (Cable Modem implementation).
             In the Cable Modem Termination system, read-only entries
             are removed if no longer referenced by
             docsIfCmtsServiceTable.

             An entry in this table must not be removed while it is
             referenced by an entry in docsIfCmServiceTable (Cable Modem)
             or docsIfCmtsServiceTable (Cable Modem Termination System).

             An entry in this table should not be changeable while
             it is referenced by an entry in docsIfCmtsServiceTable.

             If this table is created automatically, there should only
             be a single entry for each Class of Service. Multiple
             entries with the same Class of Service parameters are not


             recommended."
        INDEX { 
				basDocsIfQosProfChassis,
				basDocsIfQosProfSlot,
				basDocsIfQosProfIf,
				basDocsIfQosProfLPort,
				basDocsIfQosProfIndex 
				}
        ::= { basDocsIfQosProfileTable 1 }

BasDocsIfQosProfileEntry ::= SEQUENCE {
            basDocsIfQosProfIndex                Integer32,
            basDocsIfQosProfPriority             Integer32,
            basDocsIfQosProfMaxUpBandwidth       Integer32,
            basDocsIfQosProfGuarUpBandwidth      Integer32,
            basDocsIfQosProfMaxDownBandwidth     Integer32,
            basDocsIfQosProfMaxTxBurst           Integer32,
            basDocsIfQosProfBaselinePrivacy      TruthValue,
            basDocsIfQosProfStatus               RowStatus, 
			basDocsIfQosProfChassis				BasChassisId,
			basDocsIfQosProfSlot				BasSlotId,
			basDocsIfQosProfIf					BasInterfaceId,
			basDocsIfQosProfLPort				BasLogicalPortId
        }

basDocsIfQosProfIndex OBJECT-TYPE
        SYNTAX      Integer32 (1..16383)
        MAX-ACCESS  not-accessible
        STATUS      current
        DESCRIPTION
            "The index value which uniquely identifies an entry
             in the docsIfQosProfileTable."
        ::= { basDocsIfQosProfileEntry 1 }

basDocsIfQosProfPriority  OBJECT-TYPE
        SYNTAX      Integer32 (0..7)
        MAX-ACCESS  read-create
        STATUS      current
        DESCRIPTION
            "A relative priority assigned to this service when
             allocating bandwidth. Zero indicates lowest priority;
             and seven indicates highest priority.
             Interpretation of priority is device-specific.
             MUST NOT be changed while this row is active."
        DEFVAL { 0 }
        ::= { basDocsIfQosProfileEntry 2 }

basDocsIfQosProfMaxUpBandwidth OBJECT-TYPE
        SYNTAX      Integer32 (0..100000000)
        MAX-ACCESS  read-create
        STATUS      current
        DESCRIPTION
            "The maximum upstream bandwidth, in bits per second,
             allowed for a service with this service class.
             Zero if there is no restriction of upstream bandwidth.
             MUST NOT be changed while this row is active."
        DEFVAL { 0 }
        ::= { basDocsIfQosProfileEntry 3 }


basDocsIfQosProfGuarUpBandwidth OBJECT-TYPE
        SYNTAX      Integer32 (0..100000000)
        MAX-ACCESS  read-create
        STATUS      current
        DESCRIPTION
            "Minimum guaranteed upstream bandwidth, in bits per second,
             allowed for a service with this service class.
             MUST NOT be changed while this row is active."
        DEFVAL { 0 }
        ::= { basDocsIfQosProfileEntry 4 }

basDocsIfQosProfMaxDownBandwidth OBJECT-TYPE
        SYNTAX      Integer32 (0..100000000)
        MAX-ACCESS  read-create
        STATUS      current
        DESCRIPTION
            "The maximum downstream bandwidth, in bits per second,
             allowed for a service with this service class.
             Zero if there is no restriction of downstream bandwidth.
             MUST NOT be changed while this row is active."
        DEFVAL { 0 }
        ::= { basDocsIfQosProfileEntry 5 }

basDocsIfQosProfMaxTxBurst OBJECT-TYPE
        SYNTAX      Integer32 (0..255)
        MAX-ACCESS  read-create
        STATUS      current
        DESCRIPTION
            "The maximum number of mini-slots that may be requested
             for a single upstream transmission.
             A value of zero means there is no limit.
             MUST NOT be changed while this row is active."
        DEFVAL { 0 }
        ::= { basDocsIfQosProfileEntry 6 }

basDocsIfQosProfBaselinePrivacy  OBJECT-TYPE
        SYNTAX      TruthValue
        MAX-ACCESS  read-create
        STATUS      current
        DESCRIPTION
            "Indicates whether Baseline Privacy is enabled for this
             service class.
             MUST NOT be changed while this row is active."
        DEFVAL { false }
        ::= { basDocsIfQosProfileEntry 7 }

basDocsIfQosProfStatus OBJECT-TYPE
        SYNTAX      RowStatus


        MAX-ACCESS  read-create
        STATUS      current
        DESCRIPTION
            "This is object is to used to create or delete rows in
             this table.  This object MUST NOT be changed from active
             while the row is referenced by the any entry in either
             docsIfCmServiceTable (on the CM), or the
             docsIfCmtsServiceTable (on the CMTS)."
        ::= { basDocsIfQosProfileEntry 8 }

basDocsIfQosProfChassis OBJECT-TYPE
	SYNTAX		BasChassisId
	MAX-ACCESS	not-accessible
	STATUS		current
	DESCRIPTION
		"The BAS Chassis ID of this card."
	::= { basDocsIfQosProfileEntry 9 }

basDocsIfQosProfSlot OBJECT-TYPE
	SYNTAX		BasSlotId
	MAX-ACCESS	not-accessible
	STATUS		current
	DESCRIPTION
		"The BAS Slot ID of this card."
	::= { basDocsIfQosProfileEntry 10 }

basDocsIfQosProfIf OBJECT-TYPE
	SYNTAX		BasInterfaceId
	MAX-ACCESS	not-accessible
	STATUS		current
	DESCRIPTION
		"The BAS interface ID of this card."
	::= { basDocsIfQosProfileEntry 11 }

basDocsIfQosProfLPort OBJECT-TYPE
	SYNTAX		BasLogicalPortId
	MAX-ACCESS	not-accessible
	STATUS		current
	DESCRIPTION
		"The BAS logical port ID of this card."
	::= { basDocsIfQosProfileEntry 12 }

--
-- CMTS GROUP
--

--
-- CM status table (within CMTS).
-- This table is implemented only at the CMTS.
-- It contains per CM status information available in the CMTS.
--

basDocsIfCmtsCmStatusTable OBJECT-TYPE
        SYNTAX      SEQUENCE OF BasDocsIfCmtsCmStatusEntry
        MAX-ACCESS  not-accessible
        STATUS      current
        DESCRIPTION
            "A set of objects in the CMTS, maintained for each
             Cable Modem connected to this CMTS."
        ::= { basDocsIfCmtsObjects 3 }

basDocsIfCmtsCmStatusEntry OBJECT-TYPE
        SYNTAX      BasDocsIfCmtsCmStatusEntry
        MAX-ACCESS  not-accessible
        STATUS      current
        DESCRIPTION
            "Status information for a single Cable Modem.
             An entry in this table exists for each Cable Modem
             that is connected to the CMTS implementing this table."
        INDEX { 
				basDocsIfCmtsCmStatusChassis,
				basDocsIfCmtsCmStatusSlot,
				basDocsIfCmtsCmStatusIf,
				basDocsIfCmtsCmStatusLPort,
				basDocsIfCmtsCmStatusIndex 
				}
        ::= { basDocsIfCmtsCmStatusTable 1 }

BasDocsIfCmtsCmStatusEntry ::= SEQUENCE {
            basDocsIfCmtsCmStatusIndex               Integer32,
            basDocsIfCmtsCmStatusMacAddress          MacAddress,
            basDocsIfCmtsCmStatusIpAddress           IpAddress,
            basDocsIfCmtsCmStatusDownChannelIfIndex  InterfaceIndexOrZero,
            basDocsIfCmtsCmStatusUpChannelIfIndex    InterfaceIndexOrZero,
            basDocsIfCmtsCmStatusRxPower             TenthdBmV,
            basDocsIfCmtsCmStatusTimingOffset        Unsigned32,
            basDocsIfCmtsCmStatusEqualizationData    OCTET STRING,


            basDocsIfCmtsCmStatusValue               INTEGER,
            basDocsIfCmtsCmStatusUnerroreds          Counter32,
            basDocsIfCmtsCmStatusCorrecteds          Counter32,
            basDocsIfCmtsCmStatusUncorrectables      Counter32,
            basDocsIfCmtsCmStatusSignalNoise         TenthdB,
            basDocsIfCmtsCmStatusMicroreflections    Integer32, 
			basDocsIfCmtsCmStatusChassis			BasChassisId,
			basDocsIfCmtsCmStatusSlot				BasSlotId,
			basDocsIfCmtsCmStatusIf					BasInterfaceId,
			basDocsIfCmtsCmStatusLPort				BasLogicalPortId
        }

basDocsIfCmtsCmStatusIndex OBJECT-TYPE
        SYNTAX      Integer32 (1..2147483647)
        MAX-ACCESS  not-accessible
        STATUS      current
        DESCRIPTION
            "Index value to uniquely identify an entry in this table.
             For an individual Cable Modem, this index value should
             not change during CMTS uptime."
        ::= { basDocsIfCmtsCmStatusEntry 1 }

basDocsIfCmtsCmStatusMacAddress OBJECT-TYPE
        SYNTAX      MacAddress
        MAX-ACCESS  read-only
        STATUS      current
        DESCRIPTION
            "MAC address of this Cable Modem. If the Cable Modem has
             multiple MAC addresses, this is the MAC address associated
             with the Cable interface."
        ::= { basDocsIfCmtsCmStatusEntry 2 }

basDocsIfCmtsCmStatusIpAddress OBJECT-TYPE
        SYNTAX      IpAddress
        MAX-ACCESS  read-only
        STATUS      current
        DESCRIPTION
            "IP address of this Cable Modem. If the Cable Modem has no
             IP address assigned, or the IP address is unknown, this
             object returns a value of 0.0.0.0. If the Cable Modem has
             multiple IP addresses, this object returns the IP address
             associated with the Cable interface."
        ::= { basDocsIfCmtsCmStatusEntry 3 }

basDocsIfCmtsCmStatusDownChannelIfIndex OBJECT-TYPE
        SYNTAX      InterfaceIndexOrZero
        MAX-ACCESS  read-only
        STATUS      current
        DESCRIPTION
            "IfIndex of the downstream channel this CM is connected
             to. If the downstream channel is unknown, this object
             returns a value of zero."


        ::= { basDocsIfCmtsCmStatusEntry 4 }

basDocsIfCmtsCmStatusUpChannelIfIndex OBJECT-TYPE
        SYNTAX      InterfaceIndexOrZero
        MAX-ACCESS  read-write
        STATUS      current
        DESCRIPTION
            "IfIndex of the upstream channel this CM is connected
             to. If the upstream channel is unknown, this object
             returns a value of zero."
        ::= { basDocsIfCmtsCmStatusEntry 5 }

basDocsIfCmtsCmStatusRxPower OBJECT-TYPE
        SYNTAX      TenthdBmV
        UNITS       "dBmV"
        MAX-ACCESS  read-only
        STATUS      current
        DESCRIPTION
            "The receive power as percieved for upstream data from
             this Cable Modem.
             If the receive power is unknown, this object returns
             a value of zero."
        REFERENCE
            "DOCSIS Radio Frequency Interface Specification,
             Table 4-13."
        ::= { basDocsIfCmtsCmStatusEntry 6 }

basDocsIfCmtsCmStatusTimingOffset OBJECT-TYPE
        SYNTAX      Unsigned32
        MAX-ACCESS  read-only
        STATUS      current
        DESCRIPTION
            "A measure of the current round trip time for this CM.
             Used for timing of CM upstream transmissions to ensure
             synchronized arrivals at the CMTS. Units are in terms
             of (6.25 microseconds/64). Returns zero if the value
             is unknown."
        REFERENCE
            "DOCSIS Radio Frequency Interface Specification,
             Section 6.5."
        ::= { basDocsIfCmtsCmStatusEntry 7 }

basDocsIfCmtsCmStatusEqualizationData OBJECT-TYPE
        SYNTAX      OCTET STRING
        MAX-ACCESS  read-only
        STATUS      current
        DESCRIPTION
            "Equalization data for this CM. Returns an empty string


             if the value is unknown or if there is no equalization
             data available or defined."
        REFERENCE
            "DOCSIS Radio Frequency Interface Specification,
             Figure 6-23."
        ::= { basDocsIfCmtsCmStatusEntry 8 }

basDocsIfCmtsCmStatusValue OBJECT-TYPE
        SYNTAX      INTEGER {
            other(1),
            ranging(2),
            rangingAborted(3),
            rangingComplete(4),
            ipComplete(5),
            registrationComplete(6),
            accessDenied(7)
        }
        MAX-ACCESS  read-only
        STATUS      current
        DESCRIPTION
            "Current Cable Modem connectivity state, as specified
             in the RF Interface Specification. Returned status
             information is the CM status as assumed by the CMTS,
             and indicates the following events:
             other(1)
                Any state other than below.
             ranging(2)
                The CMTS has received an Initial Ranging Request
                message from the CM, and the ranging process is not
                yet complete.
             rangingAborted(3)
                The CMTS has sent a Ranging Abort message to the CM.
             rangingComplete(4)
                The CMTS has sent a Ranging Complete message to the CM.
             ipComplete(5)
                The CMTS has received a DHCP reply message and forwarded
                it to the CM.
             registrationComplete(6)
                The CMTS has sent a Registration Response mesage to
                the CM.
             accessDenied(7)
                The CMTS has sent a Registration Aborted message
                to the CM.
             The CMTS only needs to report states it is able to detect."
        REFERENCE
            "DOCSIS Radio Frequency Interface Specification,
             Chapter 7.2."
        ::= { basDocsIfCmtsCmStatusEntry 9 }


basDocsIfCmtsCmStatusUnerroreds OBJECT-TYPE
        SYNTAX      Counter32
        MAX-ACCESS  read-only
        STATUS      current
        DESCRIPTION
            "Codewords received without error from this Cable Modem."
        REFERENCE
            "DOCSIS Radio Frequency Interface specification,
             Section 4.2.3"
        ::= { basDocsIfCmtsCmStatusEntry 10 }

basDocsIfCmtsCmStatusCorrecteds OBJECT-TYPE
        SYNTAX      Counter32
        MAX-ACCESS  read-only
        STATUS      current
        DESCRIPTION
            "Codewords received with correctable errors from this
             Cable Modem."
        REFERENCE
            "DOCSIS Radio Frequency Interface specification,
             Section 4.2.3"
        ::= { basDocsIfCmtsCmStatusEntry 11 }

basDocsIfCmtsCmStatusUncorrectables OBJECT-TYPE
        SYNTAX      Counter32
        MAX-ACCESS  read-only
        STATUS      current
        DESCRIPTION
            "Codewords received with uncorrectable errors from this
             Cable Modem."
        REFERENCE
            "DOCSIS Radio Frequency Interface specification,
             Section 4.2.3"
        ::= { basDocsIfCmtsCmStatusEntry 12 }

basDocsIfCmtsCmStatusSignalNoise OBJECT-TYPE
        SYNTAX      TenthdB
        UNITS       "dB"
        MAX-ACCESS  read-only
        STATUS      current
        DESCRIPTION
            "Signal/Noise ratio as perceived for upstream data from
             this Cable Modem.
             If the Signal/Noise is unknown, this object returns
             a value of zero."
        ::= { basDocsIfCmtsCmStatusEntry 13 }

basDocsIfCmtsCmStatusMicroreflections OBJECT-TYPE


        SYNTAX      Integer32 (0..255)
        UNITS       "dBc"
        MAX-ACCESS  read-only
        STATUS      current
        DESCRIPTION
            "Total microreflections including in-channel response
             as perceived on this interface, measured in dBc below
             the signal level.
             This object is not assumed to return an absolutely
             accurate value, but should give a rough indication
             of microreflections received on this interface.
             It is up to the implementor to provide information
             as accurate as possible."
        REFERENCE
            "DOCSIS Radio Frequency Interface specification,
             Table 2-1 and 2-2"
        ::= { basDocsIfCmtsCmStatusEntry 14 }

basDocsIfCmtsCmStatusChassis OBJECT-TYPE
	SYNTAX		BasChassisId
	MAX-ACCESS	not-accessible
	STATUS		current
	DESCRIPTION
		"The BAS Chassis ID of this card."
	::= { basDocsIfCmtsCmStatusEntry 15 }

basDocsIfCmtsCmStatusSlot OBJECT-TYPE
	SYNTAX		BasSlotId
	MAX-ACCESS	not-accessible
	STATUS		current
	DESCRIPTION
		"The BAS Slot ID of this card."
	::= { basDocsIfCmtsCmStatusEntry 16 }

basDocsIfCmtsCmStatusIf OBJECT-TYPE
	SYNTAX		BasInterfaceId
	MAX-ACCESS	not-accessible
	STATUS		current
	DESCRIPTION
		"The BAS interface ID of this card."
	::= { basDocsIfCmtsCmStatusEntry 17 }

basDocsIfCmtsCmStatusLPort OBJECT-TYPE
	SYNTAX		BasLogicalPortId
	MAX-ACCESS	not-accessible
	STATUS		current
	DESCRIPTION
		"The BAS logical port ID of this card."
	::= { basDocsIfCmtsCmStatusEntry 18 }


basDocsIfCmtsQosProfileTable OBJECT-TYPE
        SYNTAX      SEQUENCE OF BasDocsIfCmtsQosProfileEntry
        MAX-ACCESS  not-accessible
        STATUS      current
        DESCRIPTION
            "Provides modulation profile information for this CMTS."
        ::= { basDocsIfCmtsObjects 6 }

basDocsIfCmtsQosProfileEntry OBJECT-TYPE
        SYNTAX      BasDocsIfCmtsQosProfileEntry
        MAX-ACCESS  not-accessible
        STATUS      current
        DESCRIPTION
            ""

        INDEX { 
				basDocsIfCmtsQosProfileChassis,
				basDocsIfCmtsQosProfileSlot,
				basDocsIfCmtsQosProfileIf,
				basDocsIfCmtsQosProfileLPort
			  }
        ::= { basDocsIfCmtsQosProfileTable 1 }

BasDocsIfCmtsQosProfileEntry ::= SEQUENCE {
			basDocsIfCmtsQosProfilePermissions		BITS,
			basDocsIfCmtsQosProfileChassis			BasChassisId,
			basDocsIfCmtsQosProfileSlot				BasSlotId,
			basDocsIfCmtsQosProfileIf				BasInterfaceId,
			basDocsIfCmtsQosProfileLPort			BasLogicalPortId
        }

basDocsIfCmtsQosProfilePermissions OBJECT-TYPE
        SYNTAX      BITS {
            createByManagement(0),
            updateByManagement(1),
            createByModems(2)
        }
        MAX-ACCESS  read-write
        STATUS      current
        DESCRIPTION
            "This object specifies permitted methods of creating
             entries in docsIfQosProfileTable.
             CreateByManagement(0) is set if entries can be created
             using SNMP. UpdateByManagement(1) is set if updating
             entries using SNMP is permitted. CreateByModems(2)
             is set if entries can be created based on information
             in REG-REQ MAC messages received from Cable Modems.
             Information in this object is only applicable if
             docsIfQosProfileTable is implemented as read-create.
             Otherwise, this object is implemented as read-only
             and returns CreateByModems(2).
             Either CreateByManagement(0) or CreateByModems(1)
             must be set when writing to this object."
        ::= { basDocsIfCmtsQosProfileEntry 6 }

basDocsIfCmtsQosProfileChassis OBJECT-TYPE
	SYNTAX		BasChassisId
	MAX-ACCESS	not-accessible
	STATUS		current
	DESCRIPTION
		"The BAS Chassis ID of this card."
	::= { basDocsIfCmtsQosProfileEntry 7 }

basDocsIfCmtsQosProfileSlot OBJECT-TYPE
	SYNTAX		BasSlotId
	MAX-ACCESS	not-accessible
	STATUS		current
	DESCRIPTION
		"The BAS Slot ID of this card."
	::= { basDocsIfCmtsQosProfileEntry 8 }

basDocsIfCmtsQosProfileIf OBJECT-TYPE
	SYNTAX		BasInterfaceId
	MAX-ACCESS	not-accessible
	STATUS		current
	DESCRIPTION
		"The BAS interface ID of this card."
	::= { basDocsIfCmtsQosProfileEntry 9 }

basDocsIfCmtsQosProfileLPort OBJECT-TYPE
	SYNTAX		BasLogicalPortId
	MAX-ACCESS	not-accessible
	STATUS		current
	DESCRIPTION
		"The BAS logical port ID of this card."
	::= { basDocsIfCmtsQosProfileEntry 10 }

basDocsIfCmtsMacToCmTable OBJECT-TYPE
        SYNTAX      SEQUENCE OF BasDocsIfCmtsMacToCmEntry


        MAX-ACCESS  not-accessible
        STATUS      current
        DESCRIPTION
            "This is a table to provide a quick access index into the
             docsIfCmtsCmStatusTable. There is exactly one row in this
             table for each row in the docsIfCmtsCmStatusTable. In
             general, the management station should use this table only
             to get a pointer into the docsIfCmtsCmStatusTable (which
             corresponds to the CM's RF interface MAC address), and
             should not iterate (e.g. GetNext through) this table."
    ::= { basDocsIfCmtsObjects 7 }

basDocsIfCmtsMacToCmEntry OBJECT-TYPE
        SYNTAX      BasDocsIfCmtsMacToCmEntry
        MAX-ACCESS  not-accessible
        STATUS      current
        DESCRIPTION
            "A row in the docsIfCmtsMacToCmTable.
             An entry in this table exists for each Cable Modem
             that is connected to the CMTS implementing this table."
        INDEX { 
				basDocsIfCmtsCmChassis,
				basDocsIfCmtsCmSlot,
				basDocsIfCmtsCmIf,
				basDocsIfCmtsCmLPort, 
				basDocsIfCmtsCmMac 
				}
        ::= { basDocsIfCmtsMacToCmTable 1 }

BasDocsIfCmtsMacToCmEntry ::= SEQUENCE {
                basDocsIfCmtsCmMac     MacAddress,
                basDocsIfCmtsCmPtr     Integer32, 
				basDocsIfCmtsCmChassis			BasChassisId,
				basDocsIfCmtsCmSlot				BasSlotId,
				basDocsIfCmtsCmIf				BasInterfaceId,
				basDocsIfCmtsCmLPort			BasLogicalPortId
        }

basDocsIfCmtsCmMac OBJECT-TYPE
        SYNTAX      MacAddress
        MAX-ACCESS  not-accessible
        STATUS      current
        DESCRIPTION
            "The RF side MAC address for the referenced CM. (E.g. the
             interface on the CM that has docsCableMacLayer(127) as
             its ifType."
    ::= { basDocsIfCmtsMacToCmEntry 1 }

basDocsIfCmtsCmPtr OBJECT-TYPE
        SYNTAX      Integer32 (1..2147483647)
        MAX-ACCESS  read-only
        STATUS      current
        DESCRIPTION
            "An row index into docsIfCmtsCmStatusTable. When queried
             with the correct instance value (e.g. a CM's MAC address),
             returns the index in docsIfCmtsCmStatusTable which
             represents that CM."
    ::= { basDocsIfCmtsMacToCmEntry 2 }

basDocsIfCmtsCmChassis OBJECT-TYPE
	SYNTAX		BasChassisId
	MAX-ACCESS	not-accessible
	STATUS		current
	DESCRIPTION
		"The BAS Chassis ID of this card."
	::= { basDocsIfCmtsMacToCmEntry 3 }

basDocsIfCmtsCmSlot OBJECT-TYPE
	SYNTAX		BasSlotId
	MAX-ACCESS	not-accessible
	STATUS		current
	DESCRIPTION
		"The BAS Slot ID of this card."
	::= { basDocsIfCmtsMacToCmEntry 4 }

basDocsIfCmtsCmIf OBJECT-TYPE
	SYNTAX		BasInterfaceId
	MAX-ACCESS	not-accessible
	STATUS		current
	DESCRIPTION
		"The BAS interface ID of this card."
	::= { basDocsIfCmtsMacToCmEntry 5 }

basDocsIfCmtsCmLPort OBJECT-TYPE
	SYNTAX		BasLogicalPortId
	MAX-ACCESS	not-accessible
	STATUS		current
	DESCRIPTION
		"The BAS logical port ID of this card."
	::= { basDocsIfCmtsMacToCmEntry 6 }


END
