-- OC9100 MIB Definitions
-- $Revision: 5 $
-- $Date: 11/09/98 3:06p $

-- This MIB module contains definitions of MIB objects specific to
-- the Olicom Crossfire ATM Switch

-- Olicom-crossfireAtmSwitch-MIB  { iso(1) org(3) dod(6) internet(1) private(4)
--                                  enterprises(1) olicom(285) ocmibs(2)
--                                  ocmibsCrossfireAtmMIB(6) }

Olicom-crossfireAtmSwitch-MIB   DEFINITIONS ::= BEGIN

IMPORTS
	TRAP-TYPE FROM RFC-1215
        enterprises, Counter, TimeTicks, Gauge, IpAddress
                FROM RFC1155-SMI
        DisplayString, ifIndex
                FROM RFC1213-MIB
        MacAddress
                FROM RFC1231-MIB
        OBJECT-TYPE
                FROM RFC-1212
        ocmibsCrossfireAtmMIB, controlTime
                FROM Olicom-MIB;

-- Textual conventions

AtmAddress ::= OCTET STRING (SIZE (20))    -- a 20 octet ATM address


-- TERMINOLOGY:
--
-- In this MIB the following terms are used:
-- xModule:         An expansion module
-- feature module:  A traffic management module  
-- ePort:           External port, i.e. an ATM attachment port
-- iPort:           Internal port, i.e. the Core Access Point located
--                  in the switch core


-- Sections

-- nws / modified 7/24/00
olicom			  OBJECT IDENTIFIER ::= { enterprises 285 }
ocmibs			  OBJECT IDENTIFIER ::= { olicom 2 }
ocmibsCrossfireAtmMIB	  OBJECT IDENTIFIER ::= { ocmibs 6 }
-- nws / end modification

crossfireAtmInfo          OBJECT IDENTIFIER ::= { ocmibsCrossfireAtmMIB 1 }
crossfireAtmConfiguration OBJECT IDENTIFIER ::= { ocmibsCrossfireAtmMIB 2 }
crossfireAtmStatus        OBJECT IDENTIFIER ::= { ocmibsCrossfireAtmMIB 3 }
crossfireAtmStatistics    OBJECT IDENTIFIER ::= { ocmibsCrossfireAtmMIB 4 }
crossfireAtmTrapControl   OBJECT IDENTIFIER ::= { ocmibsCrossfireAtmMIB 5 }
crossfireAtmTest          OBJECT IDENTIFIER ::= { ocmibsCrossfireAtmMIB 6 }
crossfirexlx		  OBJECT IDENTIFIER ::= { ocmibsCrossfireAtmMIB 7 }

-- Info section

-- The info section contains version information for the hardware
-- modules and information about why the switch was last restarted

infoProcessorModule       OBJECT IDENTIFIER ::= { crossfireAtmInfo 1 }
infoFeatureModule         OBJECT IDENTIFIER ::= { crossfireAtmInfo 2 }
infoXModule               OBJECT IDENTIFIER ::= { crossfireAtmInfo 3 }
infoIfIndex               OBJECT IDENTIFIER ::= { crossfireAtmInfo 4 }
termRestartInfo           OBJECT IDENTIFIER ::= { crossfireAtmInfo 5 }

-- Processor module

infoProcessorModuleHwProductId OBJECT-TYPE
        SYNTAX  DisplayString
        ACCESS  read-only
        STATUS  mandatory
        DESCRIPTION
                "The processor module product ID from the EEPROM."
        ::= { infoProcessorModule 1 }

infoProcessorModuleHwVersion OBJECT-TYPE
        SYNTAX  DisplayString
        ACCESS  read-only
        STATUS  mandatory
        DESCRIPTION
                "The processor module version from the EEPROM."
        ::= { infoProcessorModule 2 }

infoProcessorModuleHwEcoLevel OBJECT-TYPE
        SYNTAX  DisplayString
        ACCESS  read-only
        STATUS  mandatory
        DESCRIPTION
                "The processor module ECO level - not used."
        ::= { infoProcessorModule 3 }

infoProcessorModuleHwSerialNumber OBJECT-TYPE
        SYNTAX  DisplayString
        ACCESS  read-only
        STATUS  mandatory
        DESCRIPTION
                "The processor module serial number from the EEPROM."
        ::= { infoProcessorModule 4 }

infoProcessorModuleHwOptionTable OBJECT-TYPE
        SYNTAX  SEQUENCE OF InfoProcessorModuleHwOptionEntry
        ACCESS  not-accessible
        STATUS  mandatory
        DESCRIPTION
                "The table of processor module options as found in the
                EEPROM."
        ::= { infoProcessorModule 5 }

infoProcessorModuleHwOptionEntry OBJECT-TYPE
        SYNTAX  InfoProcessorModuleHwOptionEntry
        ACCESS  not-accessible
        STATUS  mandatory
        DESCRIPTION
                "Each row in this table describes one processor module
                option."
        INDEX   { infoProcessorModuleHwOptionNo }
        ::= { infoProcessorModuleHwOptionTable 1 }

InfoProcessorModuleHwOptionEntry ::=
        SEQUENCE {
            infoProcessorModuleHwOptionNo
                INTEGER,
            infoProcessorModuleHwOption
                DisplayString
        }

infoProcessorModuleHwOptionNo OBJECT-TYPE
        SYNTAX  INTEGER
        ACCESS  read-only
        STATUS  mandatory
        DESCRIPTION
                "An arbitrary integer used to differentiate multiple
                rows in the table."
        ::= { infoProcessorModuleHwOptionEntry 1 }

infoProcessorModuleHwOption OBJECT-TYPE
        SYNTAX  DisplayString
        ACCESS  read-only
        STATUS  mandatory
        DESCRIPTION
                "A processor module option string from the EEPROM."
        ::= { infoProcessorModuleHwOptionEntry 2 }


-- Feature Module

-- The feature module is also known as the Traffic Management module

infoFeatureModuleHwProductId OBJECT-TYPE
        SYNTAX  DisplayString
        ACCESS  read-only
        STATUS  mandatory
        DESCRIPTION
                "The feature module product ID from the EEPROM."
        ::= { infoFeatureModule 1 }

infoFeatureModuleHwVersion OBJECT-TYPE
        SYNTAX  DisplayString
        ACCESS  read-only
        STATUS  mandatory
        DESCRIPTION
                "The feature module version from the EEPROM."
        ::= { infoFeatureModule 2 }

infoFeatureModuleHwEcoLevel OBJECT-TYPE
        SYNTAX  DisplayString
        ACCESS  read-only
        STATUS  mandatory
        DESCRIPTION
                "The feature module ECO level - not used."
        ::= { infoFeatureModule 3 }

infoFeatureModuleHwSerialNumber OBJECT-TYPE
        SYNTAX  DisplayString
        ACCESS  read-only
        STATUS  mandatory
        DESCRIPTION
                "The feature module serial number from the EEPROM."
        ::= { infoFeatureModule 4 }

infoFeatureModuleHwOptionTable OBJECT-TYPE
        SYNTAX  SEQUENCE OF InfoFeatureModuleHwOptionEntry
        ACCESS  not-accessible
        STATUS  mandatory
        DESCRIPTION
                "The table of feature module options as found in the
                EEPROM."
        ::= { infoFeatureModule 5 }

infoFeatureModuleHwOptionEntry OBJECT-TYPE
        SYNTAX  InfoFeatureModuleHwOptionEntry
        ACCESS  not-accessible
        STATUS  mandatory
        DESCRIPTION
                "Each row in this table describes one feature module
                option."
        INDEX   { infoFeatureModuleHwOptionNo }
        ::= { infoFeatureModuleHwOptionTable 1 }

InfoFeatureModuleHwOptionEntry ::=
        SEQUENCE {
            infoFeatureModuleHwOptionNo
                INTEGER,
            infoFeatureModuleHwOption
                DisplayString
        }

infoFeatureModuleHwOptionNo OBJECT-TYPE
        SYNTAX  INTEGER
        ACCESS  read-only
        STATUS  mandatory
        DESCRIPTION
                "An arbitrary integer used to differentiate multiple
                rows in the table."
        ::= { infoFeatureModuleHwOptionEntry 1 }

infoFeatureModuleHwOption OBJECT-TYPE
        SYNTAX  DisplayString
        ACCESS  read-only
        STATUS  mandatory
        DESCRIPTION
                "A feature module option string from the EEPROM."
        ::= { infoFeatureModuleHwOptionEntry 2 }

                                                     
-- xModules

infoXModuleTable OBJECT-TYPE
        SYNTAX  SEQUENCE OF InfoXModuleEntry
        ACCESS  not-accessible
        STATUS  mandatory
        DESCRIPTION
                "This table contains information for each of the
                expansion modules installed in the switch."
        ::= { infoXModule 1 }

infoXModuleEntry OBJECT-TYPE
        SYNTAX  InfoXModuleEntry
        ACCESS  not-accessible
        STATUS  mandatory
        DESCRIPTION
                "Each row in this table contains information for one
                expansion module."
        INDEX   { infoXModuleSlotIndex }
        ::= { infoXModuleTable 1 }

InfoXModuleEntry ::=
        SEQUENCE {
            infoXModuleSlotIndex
                INTEGER,
            infoXModuleHwProductId
                DisplayString,
            infoXModuleHwVersion
                DisplayString,
            infoXModuleHwEcoLevel
                DisplayString,
            infoXModuleHwSerialNumber
                DisplayString
        }


infoXModuleSlotIndex OBJECT-TYPE
        SYNTAX  INTEGER (1..8)
        ACCESS  read-only
        STATUS  mandatory
        DESCRIPTION
                "The slot number for the expansion module. It is used
                to index the expansion module in the table."
        ::= { infoXModuleEntry 1 }

infoXModuleHwProductId OBJECT-TYPE
        SYNTAX  DisplayString
        ACCESS  read-only
        STATUS  mandatory
        DESCRIPTION
                "The expansion module product ID from the EEPROM."
        ::= { infoXModuleEntry 2 }

infoXModuleHwVersion OBJECT-TYPE
        SYNTAX  DisplayString
        ACCESS  read-only
        STATUS  mandatory
        DESCRIPTION
                "The expansion module version from the EEPROM."
        ::= { infoXModuleEntry 3 }

infoXModuleHwEcoLevel OBJECT-TYPE
        SYNTAX  DisplayString
        ACCESS  read-only
        STATUS  mandatory
        DESCRIPTION
                "The expansion module ECO level - not used."
        ::= { infoXModuleEntry 4 }

infoXModuleHwSerialNumber OBJECT-TYPE
        SYNTAX  DisplayString
        ACCESS  read-only
        STATUS  mandatory
        DESCRIPTION
                "The expansion module serial number from the EEPROM."
        ::= { infoXModuleEntry 5 }

infoXModuleHwOptionTable OBJECT-TYPE
        SYNTAX  SEQUENCE OF InfoXModuleHwOptionEntry
        ACCESS  not-accessible
        STATUS  mandatory
        DESCRIPTION
                "The table of expansion module options as found in the
                EEPROM. There is one row in the table for each
                expansion module and each option."
        ::= { infoXModule 2 }

infoXModuleHwOptionEntry OBJECT-TYPE
        SYNTAX  InfoXModuleHwOptionEntry
        ACCESS  not-accessible
        STATUS  mandatory
        DESCRIPTION
                "Each row in this table describes one expansion module
                option."
        INDEX   { infoXModuleHwOptionSlotIndex,infoXModuleHwOptionNo }
        ::= { infoXModuleHwOptionTable 1 }

InfoXModuleHwOptionEntry ::=
        SEQUENCE {
            infoXModuleHwOptionSlotIndex
                INTEGER,
            infoXModuleHwOptionNo
                INTEGER,
            infoXModuleHwOption
                DisplayString
        }

infoXModuleHwOptionSlotIndex OBJECT-TYPE
        SYNTAX  INTEGER
        ACCESS  read-only
        STATUS  mandatory
        DESCRIPTION
                "The slot number for the expansion module. It is used
                to index the expansion module in the table."
        ::= { infoXModuleHwOptionEntry 1 }

infoXModuleHwOptionNo OBJECT-TYPE
        SYNTAX  INTEGER
        ACCESS  read-only
        STATUS  mandatory
        DESCRIPTION
                "An arbitrary integer used to differentiate multiple
                rows for the same expansion module."
        ::= { infoXModuleHwOptionEntry 2 }

infoXModuleHwOption OBJECT-TYPE
        SYNTAX  DisplayString
        ACCESS  read-only
        STATUS  mandatory
        DESCRIPTION
                "An expansion module option string from the EEPROM."
        ::= { infoXModuleHwOptionEntry 3 }

-- IfIndex values

-- This is a collection of ifIndex values that have a special meaning
-- in the switch

infoIfIndexLan OBJECT-TYPE
        SYNTAX  INTEGER         -- always 1
        ACCESS  read-only
        STATUS  mandatory
        DESCRIPTION
                "This ifIndex value designates the Ethernet LAN
                interface on the switch."
        ::= { infoIfIndex 1 }


infoIfIndexSlip OBJECT-TYPE     -- always 2
        SYNTAX  INTEGER
        ACCESS  read-only
        STATUS  mandatory
        DESCRIPTION
                "This ifIndex value designates the SLIP interface on
                the switch."
        ::= { infoIfIndex 2 }


infoIfIndexElan OBJECT-TYPE
        SYNTAX  INTEGER         -- always 3
        ACCESS  read-only
        STATUS  mandatory
        DESCRIPTION
                "This ifIndex value designates the emulated LAN
                user side virtual interface on the switch."
        ::= { infoIfIndex 3 }


infoIfIndexClassicalIp OBJECT-TYPE
        SYNTAX  INTEGER         -- always 4
        ACCESS  read-only
        STATUS  mandatory
        DESCRIPTION
                "This ifIndex value designates the Classical IP
                virtual interface on the switch."
        ::= { infoIfIndex 4 }


infoIfIndexRfc1483Bridged OBJECT-TYPE
        SYNTAX  INTEGER         -- always 5
        ACCESS  read-only
        STATUS  mandatory
        DESCRIPTION
                "This ifIndex value designates the Classical IP (RFC
                1483 bridged encapsulation) virtual interface on the
                switch."
        ::= { infoIfIndex 5 }


infoIfIndexRfc1483Routed OBJECT-TYPE
        SYNTAX  INTEGER         -- always 6
        ACCESS  read-only
        STATUS  mandatory
        DESCRIPTION
                "This ifIndex value designates the Classical IP (RFC
                1483 routed encapsulation) virtual interface on the
                switch."
        ::= { infoIfIndex 6 }


infoIfIndexAtmNode OBJECT-TYPE
        SYNTAX  INTEGER         -- always 7
        ACCESS  read-only
        STATUS  mandatory
        DESCRIPTION
                "This ifIndex value designates the network node side
                virtual interface on the switch which is used when the
                switch communicates with itself."
        ::= { infoIfIndex 7 }



-- Termination & Restart Info

termRestartInfoRestartTime OBJECT-TYPE
        SYNTAX  INTEGER
        ACCESS  read-only
        STATUS  mandatory
        DESCRIPTION
                "Time when the system was restarted (measured in
                seconds since 00:00:00 UTC on 1 January 1970)."
        ::= { termRestartInfo 1 }

termRestartInfoSwSection1StatusWord OBJECT-TYPE
        SYNTAX  INTEGER
        ACCESS  read-only
        STATUS  mandatory
        DESCRIPTION
                "The value of the status word in the first section of
                the software image flash memory."
        ::= { termRestartInfo 2 }

termRestartInfoSwSection2StatusWord OBJECT-TYPE
        SYNTAX  INTEGER
        ACCESS  read-only
        STATUS  mandatory
        DESCRIPTION
                "The value of the status word in the second section of
                the software image flash memory."
        ::= { termRestartInfo 3 }

termRestartInfoSwImageLoaded OBJECT-TYPE
        SYNTAX  INTEGER { image1(1), image2(2) }
        ACCESS  read-only
        STATUS  mandatory
        DESCRIPTION
                "The number of the software image currently running."
        ::= { termRestartInfo 4 }

termRestartInfoFutureTestMode OBJECT-TYPE
        SYNTAX  INTEGER { yes(1), no(2) }
        ACCESS  read-only
        STATUS  mandatory
        DESCRIPTION
                "Indicates if the software is running in 'Future Test'
                mode, i.e. if this is a one-shot test of a software
                image."
        ::= { termRestartInfo 5 }

termRestartInfoBootpExecuted OBJECT-TYPE
        SYNTAX  INTEGER { yes(1), no(2) }
        ACCESS  read-only
        STATUS  mandatory
        DESCRIPTION
                "Indicates if BOOTP was executed to load the software
                image."
        ::= { termRestartInfo 6 }

termRestartInfoReloadTime OBJECT-TYPE
        SYNTAX  INTEGER
        ACCESS  read-only
        STATUS  mandatory
        DESCRIPTION 
                "Time when the software was stored in the switch
                (measured in seconds since 00:00:00 UTC on 1 January
                1970)."
        ::= { termRestartInfo 7 }

termRestartInfoBootpReason OBJECT-TYPE
        SYNTAX  INTEGER { noSw(1),
                          chksumError(2),
                          invalidSwStatus(3),
                          pushButtons(4),
                          undefined(5) }
        ACCESS  read-only
        STATUS  mandatory
        DESCRIPTION
                "The reason that BOOTP was executed to load the
                software. The possible values are:
                   noSw             There was no executable software
                                    image in the switch.

                   chksumError      The software image in the switch
                                    had a check sum error.

                   invalidSwStatus  The status word associated with
                                    the software image in the switch
                                    was invalid.

                   pushButtons      The 'default' and 'reset' buttons
                                    on the switch font panel were
                                    pressed.

                   undefined        Other reasons."
        ::= { termRestartInfo 8 }

termRestartInfoServerIpAddress OBJECT-TYPE
        SYNTAX  IpAddress
        ACCESS  read-only
        STATUS  mandatory
        DESCRIPTION
                "The IP address of the server that provided the
                software image during the BOOTP operation."
        ::= { termRestartInfo 9 }

termRestartInfoServerMacAddress OBJECT-TYPE
        SYNTAX  MacAddress
        ACCESS  read-only
        STATUS  mandatory
        DESCRIPTION
                "The MAC address of the of the server that provided
                the software image during the BOOTP operation."
        ::= { termRestartInfo 10 }

termRestartInfoFileName OBJECT-TYPE
        SYNTAX  DisplayString
        ACCESS  read-only
        STATUS  mandatory
        DESCRIPTION
                "The name of the software image file on the BOOTP
                server."
        ::= { termRestartInfo 11 }

termRestartInfoBbsramTerminationTimestamp OBJECT-TYPE
        SYNTAX  INTEGER
        ACCESS  read-only
        STATUS  mandatory
        DESCRIPTION
                "Time when the system last closed down (measured in
                seconds since 00:00:00 UTC on 1 January 1970)."
        ::= { termRestartInfo 12 }

termRestartInfoTerminationReason OBJECT-TYPE
        SYNTAX  INTEGER { unknown(1),
                          controlled(2),
                          controlledHalt(3),
                          fatal(4),
                          watchdog(5),
                          temperatureAlarm(6),
                          psuFailure(7),
                          featureModuleRemoved(8) }
        ACCESS  read-only
        STATUS  mandatory
        DESCRIPTION
                "The reason the system last closed down. Possible
                values are:
                   unknown                Unknown reason.

                   controlled             Management requested
                                          termination.

                   controlledHalt         The switch was halted,
                                          possibly because of an
                                          inconsistent configuration.

                   fatal                  A fatal error was
                                          encountered in the software.

                   watchdog               The software watchdog timed
                                          out.

                   temperatureAlarm       The temperature within the
                                          switch reached a value above
                                          temperatureCriticalTrapThreshold.

                   psuFailure             Power supply failure.

                   featureModuleRemoved   The feature module was
                                          removed while the switch was
                                          operating."
        ::= { termRestartInfo 13 }

termRestartInfoRestartReason OBJECT-TYPE
        SYNTAX  INTEGER { reset(1),
                          default(2),
                          resetDefault(3),
                          watchdog(4),
                          fatal(5),
                          controlled(6),
                          coldStart(7),
                          unknown(8),
                          featureModuleRemoved(9) }

        ACCESS  read-only
        STATUS  mandatory
        DESCRIPTION
                "The reason the system started. Possible values are:
                   reset                  The 'reset' button on the
                                          switch font panel was
                                          pressed.

                   default                The 'default' button on the
                                          switch front panel was
                                          pressed.

                   resetDefault           The 'reset' and 'default'
                                          buttons on the switch front
                                          panel were pressed.

                   watchdog               The software watchdog timed
                                          out.

                   fatal                  A fatal error was
                                          encountered in the software.

                   controlled             Management requested
                                          restart.

                   coldStart              Power up.

                   unknown                Unknown reason.

                   featureModuleRemoved   The feature module was
                                          removed while the switch was
                                          operating."
        ::= { termRestartInfo 14 }

termRestartInfoHwReconfigState OBJECT-TYPE
        SYNTAX  INTEGER { totalReconfig(1),
                          partialReconfig(2),
                          noReconfig(3) }
        ACCESS  read-only
        STATUS  mandatory
        DESCRIPTION
                "The reconfiguration state of the switch. Possible
                values are:
                   totalReconfig     The stored configuration is
                                     invalidated because of hardware
                                     changes.

                   partialReconfig   The stored expansion module
                                     configuration does not match the
                                     physically installed expansion
                                     modules. Some configuration is
                                     invalidated.
 
                   noReconfig        The stored configuration is used
                                     unchanged."
        ::= { termRestartInfo 15 }

termRestartInfoBbsram OBJECT-TYPE
        SYNTAX  OCTET STRING (SIZE(50))
        ACCESS  read-only
        STATUS  mandatory
        DESCRIPTION
                "Data stored in battery backed-up RAM when the switch
                terminated."
        ::= { termRestartInfo 16 }


-- Configuration section

-- This section contains objects that configure the switch

configAddressing          OBJECT IDENTIFIER ::= { crossfireAtmConfiguration 1 }
configClocking            OBJECT IDENTIFIER ::= { crossfireAtmConfiguration 2 }
configLane                OBJECT IDENTIFIER ::= { crossfireAtmConfiguration 3 }
configMonitoring          OBJECT IDENTIFIER ::= { crossfireAtmConfiguration 4 }
-- Deleted: configRouting             OBJECT IDENTIFIER ::= { crossfireAtmConfiguration 5 }
configTm                  OBJECT IDENTIFIER ::= { crossfireAtmConfiguration 6 }
configTrafficDescr        OBJECT IDENTIFIER ::= { crossfireAtmConfiguration 7 }
configServiceReg          OBJECT IDENTIFIER ::= { crossfireAtmConfiguration 8 }
configSar                 OBJECT IDENTIFIER ::= { crossfireAtmConfiguration 9 }
configXModule             OBJECT IDENTIFIER ::= { crossfireAtmConfiguration 10 }
configFeatureModule       OBJECT IDENTIFIER ::= { crossfireAtmConfiguration 11 }
configCommonEPort         OBJECT IDENTIFIER ::= { crossfireAtmConfiguration 12 }
configEPort               OBJECT IDENTIFIER ::= { crossfireAtmConfiguration 13 }
configCpuQ                OBJECT IDENTIFIER ::= { crossfireAtmConfiguration 14 }
configCommonIPort         OBJECT IDENTIFIER ::= { crossfireAtmConfiguration 15 }
configIPort               OBJECT IDENTIFIER ::= { crossfireAtmConfiguration 16 }
configPvpPvc              OBJECT IDENTIFIER ::= { crossfireAtmConfiguration 17 }
configSvpSvc              OBJECT IDENTIFIER ::= { crossfireAtmConfiguration 18 }
configCommonSignalling    OBJECT IDENTIFIER ::= { crossfireAtmConfiguration 19 }
configIisp                OBJECT IDENTIFIER ::= { crossfireAtmConfiguration 20 }
configIpArp               OBJECT IDENTIFIER ::= { crossfireAtmConfiguration 21 }
configQosClass            OBJECT IDENTIFIER ::= { crossfireAtmConfiguration 22 }
configSerial              OBJECT IDENTIFIER ::= { crossfireAtmConfiguration 23 }
configOam                 OBJECT IDENTIFIER ::= { crossfireAtmConfiguration 24 }
configTest                OBJECT IDENTIFIER ::= { crossfireAtmConfiguration 25 }
configPriorityBuffer      OBJECT IDENTIFIER ::= { crossfireAtmConfiguration 26 }



-- Addressing

-- This section describes the ATM address of the switch

configSwitchAddrPrefixType OBJECT-TYPE
        SYNTAX  INTEGER { dcc(57),      -- 0x39
                          iso(69),      -- 0x45
                          icd(71) }     -- 0x47
        ACCESS  read-write
        STATUS  mandatory
        DESCRIPTION
                "The ATM address prefix type."
        ::= { configAddressing 1 }

configSwitchAddrPrefixSize OBJECT-TYPE
        SYNTAX  INTEGER (1..12)
        ACCESS  read-write
        STATUS  mandatory
        DESCRIPTION
                "The number of octets in configSwitchAddrAtmPrefix."
        ::= { configAddressing 2 }

configSwitchAddrAtmPrefix OBJECT-TYPE
        SYNTAX  OCTET STRING (SIZE (12))
        ACCESS  read-write
        STATUS  mandatory
        DESCRIPTION
                "The next octets of the ATM address."
        ::= { configAddressing 3 }
                          
configSwitchAddrAtmAddress OBJECT-TYPE
        SYNTAX  AtmAddress
        ACCESS  read-only
        STATUS  mandatory
        DESCRIPTION
                "The complete ATM address (with a 0 in the final
                octet, i.e. the selector)."
        ::= { configAddressing 4 }


-- Network Clocking

-- The objects in this section are currently not implemented

configNetworkClockSource OBJECT-TYPE
        SYNTAX  INTEGER { internal(1), external(2) }
        ACCESS  read-write
        STATUS  mandatory
        DESCRIPTION
                "Controls whether the internal clock is the master
                clock or an incoming network clock is redistributed to
                all other ports."
        ::= { configClocking 1 }

configNetworkClockEPortIndex OBJECT-TYPE
        SYNTAX  INTEGER
        ACCESS  read-write
        STATUS  mandatory
        DESCRIPTION
                "The ePort that is the clock source if
                configNetworkClockSource has the value 'external'."
        ::= { configClocking 2 }


-- LANE Control

configLaneControlAdminStatus OBJECT-TYPE
        SYNTAX  INTEGER { up(1), down(2) }
        ACCESS  read-write
        STATUS  mandatory
        DESCRIPTION
                "Enable or disable LAN emulation services."
        ::= { configLane 1 }

configLaneControlLecsAdminStatus OBJECT-TYPE
        SYNTAX  INTEGER { up(1), down(2) }
        ACCESS  read-write
        STATUS  mandatory
        DESCRIPTION
                "Enable or disable the LAN Emulation Configuration
                Server (LECS)."
        ::= { configLane 2 }

configLaneControlLesBusAdminStatus OBJECT-TYPE
        SYNTAX  INTEGER { up(1), down(2) }
        ACCESS  read-write
        STATUS  mandatory
        DESCRIPTION
                "Enable or disable the LAN Emulation Server (LES) and
                Broadcast and Unknown Server (BUS)."
        ::= { configLane 3 }


-- Monitor Port

-- The switch may be instructed to send a copy to the last iPort of
-- all inbound or outbound cells to/from a given iPort. The operation
-- is controlled by the objects in this section

configMonitorEPortAdminStatus OBJECT-TYPE
        SYNTAX  INTEGER { up(1), down(2) }
        ACCESS  read-write
        STATUS  mandatory
        DESCRIPTION
                "Enable or disable copying of cells to the last iPort."
        ::= { configMonitoring 1 }

configMonitorEPortIPortSlotIndex OBJECT-TYPE
        SYNTAX  INTEGER (1..8)
        ACCESS  read-write
        STATUS  mandatory
        DESCRIPTION
                "The number of the expansion module containing the
                iPort whose inbound or outbound cells are to be copied."
        ::= { configMonitoring 2 }

configMonitorEPortIPortRIndex OBJECT-TYPE
        SYNTAX  INTEGER (1..2)
        ACCESS  read-write
        STATUS  mandatory
        DESCRIPTION
                "The number of the iPort whose inbound or outbound
                cells are to be copied."
        ::= { configMonitoring 3 }

configMonitorEPortDirection OBJECT-TYPE
        SYNTAX  INTEGER { rx(1), tx(2) }
        ACCESS  read-write
        STATUS  mandatory
        DESCRIPTION
                "Controls if the inbound (rx) or outbound (tx) cells
                are to be copied."
        ::= { configMonitoring 4 }

-- Global TM Control

-- The objects in this section control the Traffic Management operation

configTmControlMode OBJECT-TYPE
        SYNTAX  INTEGER { efci(1), er(2), none(3) }
        ACCESS  read-write
        STATUS  mandatory
        DESCRIPTION
                "Controls whether ABR traffic should be controlled
                through EFCI (Explicit Forward Congestion Indication),
                ER (Explicit Rate) or no mechanism at all."
        ::= { configTm 1 }

configTmControlEarlyPacketDiscardAdminStatus OBJECT-TYPE
        SYNTAX  INTEGER { up(1), down(2) }
        ACCESS  read-write
        STATUS  mandatory
        DESCRIPTION
                "Enables or disables early packed discard."
        ::= { configTm 2 }

configTmControlVbrTrafficAllocation OBJECT-TYPE
        SYNTAX  INTEGER { strictAllocation(1), overSubscribe(2) }
        ACCESS  read-write
        STATUS  mandatory
        DESCRIPTION
                "Indicates if bandwidth allocation of VBR connections
                should be based on the peak cell rate
                (strictAllocation) or a calculation of equivalent
                bandwidth (overSubscribe)."
        ::= { configTm 3 }

configTmControlErTuningAlpha OBJECT-TYPE
        SYNTAX  INTEGER
        ACCESS  read-write
        STATUS  mandatory
        DESCRIPTION
                "100 times the value of the alpha parameter in the
                explicit rate algorithm."
        ::= { configTm 4 }

configTmControlErTuningBeta OBJECT-TYPE
        SYNTAX  INTEGER
        ACCESS  read-write
        STATUS  mandatory
        DESCRIPTION
                "The value of the beta parameter in the explicit rate
                algorithm."
        ::= { configTm 5 }

configTmControlErTuningGamma OBJECT-TYPE
        SYNTAX  INTEGER
        ACCESS  read-write
        STATUS  mandatory
        DESCRIPTION
                "The value of the gamma parameter in the explicit rate
                algorithm."
        ::= { configTm 6 }

configTmControlErTuningDelta OBJECT-TYPE
        SYNTAX  INTEGER
        ACCESS  read-write
        STATUS  mandatory
        DESCRIPTION
                "100 times the value of the delta parameter in the
                explicit rate algorithm."
        ::= { configTm 7 }

configTmControlErTuningLambda OBJECT-TYPE
        SYNTAX  INTEGER
        ACCESS  read-write
        STATUS  mandatory
        DESCRIPTION
                "The value of the lambda parameter in the explicit
                rate algorithm."
        ::= { configTm 8 }

configTmControlErTuningTau OBJECT-TYPE
        SYNTAX  INTEGER
        ACCESS  read-write
        STATUS  mandatory
        DESCRIPTION
                "The value (in microseconds) of the tau parameter in
                the explicit rate algorithm."
        ::= { configTm 9 }

configTmControlErTuningPhi OBJECT-TYPE
        SYNTAX  INTEGER
        ACCESS  read-write
        STATUS  mandatory
        DESCRIPTION
                "100 times the value of the phi parameter in the
                explicit rate algorithm."
        ::= { configTm 10 }

configTmControlErTuningPsi OBJECT-TYPE
        SYNTAX  INTEGER
        ACCESS  read-write
        STATUS  mandatory
        DESCRIPTION
                "The value of the psi parameter in the explicit rate
                algorithm."
        ::= { configTm 11 }

configTmServiceClassMapTable OBJECT-TYPE
        SYNTAX  SEQUENCE OF ConfigTmServiceClassMapEntry
        ACCESS  not-accessible
        STATUS  mandatory
        DESCRIPTION
                "This table maps each traffic category to one of the
                four scheduling queues that are associated with each
                iPort in the switch."
        ::= { configTm 12 }

configTmServiceClassMapEntry OBJECT-TYPE
        SYNTAX  ConfigTmServiceClassMapEntry
        ACCESS  not-accessible
        STATUS  mandatory
        DESCRIPTION
                "Each row in this table describes one service
                category."
        INDEX   { configTmServiceClassMapServiceClass }
        ::= { configTmServiceClassMapTable 1 }

ConfigTmServiceClassMapEntry ::=
        SEQUENCE {
            configTmServiceClassMapServiceClass
                INTEGER,
            configTmServiceClassMapSchedulingQueue
                INTEGER
        }

configTmServiceClassMapServiceClass OBJECT-TYPE
        SYNTAX  INTEGER { other(1),
                          cbr(2),
                          rtVbr(3),
                          nrtVbr(4),
                          abr(5),
                          ubr(6) }
        ACCESS  read-only
        STATUS  mandatory
        DESCRIPTION
                "The service category described by this row."
        ::= { configTmServiceClassMapEntry 1 }

configTmServiceClassMapSchedulingQueue OBJECT-TYPE
        SYNTAX  INTEGER (1..4)
        ACCESS  read-write
        STATUS  mandatory
        DESCRIPTION
                "The cell scheduling queue used by this service
                category."
        ::= { configTmServiceClassMapEntry 2 }


-- Traffic Descriptor Table

trafficDescriptorTableNextIndex OBJECT-TYPE
        SYNTAX  INTEGER
        ACCESS  read-only
        STATUS  mandatory
        DESCRIPTION
                "The next unused row in trafficDescriptorTable."
        ::= { configTrafficDescr 1 }


trafficDescriptorTable OBJECT-TYPE
        SYNTAX  SEQUENCE OF TrafficDescriptorEntry
        ACCESS  not-accessible
        STATUS  mandatory
        DESCRIPTION
                "This table contains all the traffic descriptors in
                the switch. Each traffic descriptor may be associated
                with zero or more connections passing through the
                switch."
        ::= { configTrafficDescr 2 }

trafficDescriptorEntry OBJECT-TYPE
        SYNTAX  TrafficDescriptorEntry
        ACCESS  not-accessible
        STATUS  mandatory
        DESCRIPTION
                "Each row in this table describes one traffic
                descriptor."
        INDEX   { trafficDescriptorIndex }
        ::= { trafficDescriptorTable 1 }

TrafficDescriptorEntry ::=
        SEQUENCE {
            trafficDescriptorIndex
                INTEGER,
            trafficDescriptorCreationMode
                INTEGER,
            trafficDescriptorServiceClass
                INTEGER,
            trafficDescriptorPcr01
                INTEGER,
            trafficDescriptorPcr0
                INTEGER,
            trafficDescriptorScr01
                INTEGER,
            trafficDescriptorScr0
                INTEGER,
            trafficDescriptorMbs01
                INTEGER,
            trafficDescriptorMbs0
                INTEGER,
            trafficDescriptorTaggingFlag
                INTEGER,
            trafficDescriptorFrameDiscardFlag
                INTEGER,
            trafficDescriptorBestEffortFlag
                INTEGER,
            trafficDescriptorMcr
                INTEGER,
            trafficDescriptorAbrIcr
                INTEGER,
            trafficDescriptorAbrTbe
                INTEGER,
            trafficDescriptorAbrFrtt
                INTEGER,
            trafficDescriptorAbrRif
                INTEGER,
            trafficDescriptorAbrRdf
                INTEGER,
            trafficDescriptorAbrNrm
                INTEGER,
            trafficDescriptorAbrTrm
                INTEGER,
            trafficDescriptorAbrCdf
                INTEGER,
            trafficDescriptorAbrAdtf
                INTEGER,
            trafficDescriptorTrafficType
                INTEGER,
            trafficDescriptorRowStatus
                INTEGER,
            trafficDescriptorCtd
                INTEGER,
            trafficDescriptorCdv
                INTEGER,
            trafficDescriptorLogClr
                INTEGER
        }

trafficDescriptorIndex OBJECT-TYPE
        SYNTAX  INTEGER
        ACCESS  read-only
        STATUS  mandatory
        DESCRIPTION
                "An arbitrary integer used to differentiate multiple
                rows in the table."
        ::= { trafficDescriptorEntry 1 }

trafficDescriptorCreationMode OBJECT-TYPE
        SYNTAX  INTEGER { switchedConnection(1),
                          management(2),
                          default(3) }
        ACCESS  read-only
        STATUS  mandatory
        DESCRIPTION
                "The reason this traffic descriptor was created.
                Possible values are:
                   switchedConnection  The traffic descriptor was
                                       created because signalling
                                       established a connection
                                       through the switch.

                   management          The traffic descriptor was
                                       created through management.

                   default             The traffic descriptor is one
                                       of the default descriptors
                                       present in the switch."
        ::= { trafficDescriptorEntry 2 }

trafficDescriptorServiceClass OBJECT-TYPE
        SYNTAX  INTEGER { other(1),
                          cbr(2),
                          rtVbr(3),
                          nrtVbr(4),
                          abr(5),
                          ubr(6) }
        ACCESS  read-write
        STATUS  mandatory
        DESCRIPTION
                "The service category for this traffic descriptor."
        ::= { trafficDescriptorEntry 3 }

trafficDescriptorPcr01 OBJECT-TYPE
        SYNTAX  INTEGER
        ACCESS  read-write
        STATUS  mandatory
        DESCRIPTION
                "The Peak Cell Rate (in cells/second) for the CLP0+1
                flow. The value -1 is used to indicate that this value
                is not used."
        ::= { trafficDescriptorEntry 4 }

trafficDescriptorPcr0 OBJECT-TYPE
        SYNTAX  INTEGER
        ACCESS  read-write
        STATUS  mandatory
        DESCRIPTION
                "The Peak Cell Rate (in cells/second) for the CLP0
                flow. The value -1 is used to indicate that this value
                is not used."
        ::= { trafficDescriptorEntry 5 }

trafficDescriptorScr01 OBJECT-TYPE
        SYNTAX  INTEGER
        ACCESS  read-write
        STATUS  mandatory
        DESCRIPTION
                "The Sustainable Cell Rate (in cells/second) for the
                CLP0+1 flow. The value -1 is used to indicate that
                this value is not used."
        ::= { trafficDescriptorEntry 6 }

trafficDescriptorScr0 OBJECT-TYPE
        SYNTAX  INTEGER
        ACCESS  read-write
        STATUS  mandatory
        DESCRIPTION
                "The Sustainable Cell Rate (in cells/second) for the
                CLP0 flow. The value -1 is used to indicate that this
                value is not used."
        ::= { trafficDescriptorEntry 7 }

trafficDescriptorMbs01 OBJECT-TYPE
        SYNTAX  INTEGER
        ACCESS  read-write
        STATUS  mandatory
        DESCRIPTION
                "The Maximum Burst Size for the CLP0+1 flow. The value
                -1 is used to indicate that this value is not used."
         ::= { trafficDescriptorEntry 8 }

trafficDescriptorMbs0 OBJECT-TYPE
        SYNTAX  INTEGER
        ACCESS  read-write
        STATUS  mandatory
        DESCRIPTION
                "The Maximum Burst Size for the CLP0 flow. The value
                -1 is used to indicate that this value is not used."
        ::= { trafficDescriptorEntry 9 }

trafficDescriptorTaggingFlag OBJECT-TYPE
        SYNTAX  INTEGER { noTagging(1), tagging(2) }
        ACCESS  read-write
        STATUS  mandatory
        DESCRIPTION
                "Indicates if tagging is disabled or enabled."
        ::= { trafficDescriptorEntry 10 }

trafficDescriptorFrameDiscardFlag OBJECT-TYPE
        SYNTAX  INTEGER { noDiscard(1), discard(2) }
        ACCESS  read-write
        STATUS  mandatory
        DESCRIPTION
                "Indicates if frame discard is enabled or disabled.
                This only has any effect if
                configTmControlEarlyPacketDiscardAdminStatus is up."
        ::= { trafficDescriptorEntry 11 }

trafficDescriptorBestEffortFlag OBJECT-TYPE
        SYNTAX  INTEGER { noBestEffort(1),
                          bestEffort(2) }
        ACCESS  read-write
        STATUS  mandatory
        DESCRIPTION
                "Indicates that best-effort delivery should be used
                (i.e. UBR service)."
        ::= { trafficDescriptorEntry 12 }

trafficDescriptorMcr OBJECT-TYPE
        SYNTAX  INTEGER
        ACCESS  read-write
        STATUS  mandatory
        DESCRIPTION
                "The Minimum Cell Rate (in cells/second). The value -1
                is used to indicate that this value is not used."
        ::= { trafficDescriptorEntry 13 }

trafficDescriptorAbrIcr OBJECT-TYPE
        SYNTAX  INTEGER
        ACCESS  read-write
        STATUS  mandatory
        DESCRIPTION
                "The Initial Cell Rate (in cells/second). The value -1
                is used to indicate that this value is not used."
        ::= { trafficDescriptorEntry 14 }

trafficDescriptorAbrTbe OBJECT-TYPE
        SYNTAX  INTEGER
        ACCESS  read-write
        STATUS  mandatory
        DESCRIPTION
                "The Transient Buffer Exposure. The value -1 is used
                to indicate that this value is not used."
        ::= { trafficDescriptorEntry 15 }

trafficDescriptorAbrFrtt OBJECT-TYPE
        SYNTAX  INTEGER
        ACCESS  read-write
        STATUS  mandatory
        DESCRIPTION
                "The Fixed Round Trip time (in microseconds). The
                value -1 is used to indicate that this value is not
                used."
        ::= { trafficDescriptorEntry 16 }

trafficDescriptorAbrRif OBJECT-TYPE
        SYNTAX  INTEGER  { rifOneOver32768(1),
                           rifOneOver16384(2),
                           rifOneOver8192(3),
                           rifOneOver4096(4),
                           rifOneOver2048(5),
                           rifOneOver1024(6),
                           rifOneOver512(7),
                           rifOneOver256(8),
                           rifOneOver128(9),
                           rifOneOver64(10),
                           rifOneOver32(11),
                           rifOneOver16(12),
                           rifOneOver8(13),
                           rifOneOver4(14),
                           rifOneOver2(15),
                           rifOne(16) }
        ACCESS  read-write
        STATUS  mandatory
        DESCRIPTION
                "The Rate Increase Factor. A value such as, for
                example, rifOneOver128 indicates a RIF value of 1/128."
        ::= { trafficDescriptorEntry 17 }

trafficDescriptorAbrRdf OBJECT-TYPE
        SYNTAX  INTEGER  { rdfOneOver32768(1),
                           rdfOneOver16384(2),
                           rdfOneOver8192(3),
                           rdfOneOver4096(4),
                           rdfOneOver2048(5),
                           rdfOneOver1024(6),
                           rdfOneOver512(7),
                           rdfOneOver256(8),
                           rdfOneOver128(9),
                           rdfOneOver64(10),
                           rdfOneOver32(11),
                           rdfOneOver16(12),
                           rdfOneOver8(13),
                           rdfOneOver4(14),
                           rdfOneOver2(15),
                           rdfOne(16) }
        ACCESS  read-write
        STATUS  mandatory
        DESCRIPTION
                "The Rate Decrease Factor. A value such as, for
                example, rdfOneOver128 indicates a RIF value of 1/128."
        ::= { trafficDescriptorEntry 18 }
                 
trafficDescriptorAbrNrm OBJECT-TYPE
        SYNTAX  INTEGER { nrm2(1),
                          nrm4(2),
                          nrm8(3),
                          nrm16(4),
                          nrm32(5),
                          nrm64(6),
                          nrm128(7),
                          nrm256(8) }

        ACCESS  read-write
        STATUS  mandatory
        DESCRIPTION
                "The number of cells between each Resource Management
                (RM) cell. A value such as, for example, nrm32
                indicates an Nrm value of 32."
        ::= { trafficDescriptorEntry 19 }

trafficDescriptorAbrTrm OBJECT-TYPE
        SYNTAX  INTEGER { trm0Point78125(1),
                          trm1Point5625(2),
                          trm3Point125(3),
                          trm6Point25(4),
                          trm12Point5(5),
                          trm25(6),
                          trm50(7),
                          trm100(8) }
        ACCESS  read-write
        STATUS  mandatory
        DESCRIPTION
                "The maximum time between each Resource Management
                (RM) cell. A value such as, for example, trm3Point125
                indicates a Trm value of 3.125 milliseconds."
        ::= { trafficDescriptorEntry 20 }

trafficDescriptorAbrCdf OBJECT-TYPE
        SYNTAX  INTEGER { cdf0(1),
                          cdfOneOver64(2),
                          cdfOneOver32(3),
                          cdfOneOver16(4),
                          cdfOneOver8(5),
                          cdfOneOver4(6),
                          cdfOneOver2(7),
                          cdfOne(8) }
        ACCESS  read-write
        STATUS  mandatory
        DESCRIPTION
                "The Cutoff Decrease Factor. A value such as, for
                example, cdfOneOver16 indicates a CDF value of 1/16."
        ::= { trafficDescriptorEntry 21 }

trafficDescriptorAbrAdtf OBJECT-TYPE
        SYNTAX  INTEGER
        ACCESS  read-write
        STATUS  mandatory
        DESCRIPTION
                "The value (in centiseconds) of the ACR Decrease Time
                Factor."
        ::= { trafficDescriptorEntry 22 }

trafficDescriptorTrafficType OBJECT-TYPE
        SYNTAX  INTEGER (1..9)
        ACCESS  read-only
        STATUS  mandatory
        DESCRIPTION
                "The traffic descriptor type. This value is identical
                to the last component of the object ID of the MIB
                objects in the atmfTrafficDescrTypes subtree of the
                ILMI MIB."
        ::= { trafficDescriptorEntry 23 }

trafficDescriptorRowStatus OBJECT-TYPE
        SYNTAX  INTEGER { active(1),
                          notInService(2),
                          notReady(3),
                          createAndGo(4),
                          createAndWait(5),
                          destroy(6) }
        ACCESS  read-write
        STATUS  mandatory
        DESCRIPTION
                "Used to control creation and deletion of new rows in
                the table."
        ::= { trafficDescriptorEntry 24 }

trafficDescriptorCtd OBJECT-TYPE
        SYNTAX  INTEGER
        ACCESS  read-write
        STATUS  mandatory
        DESCRIPTION
                "The Cell Transfer Delay (in microseconds). The value
                -1 is used to indicate that this value is not used."
        ::= { trafficDescriptorEntry 25 }

trafficDescriptorCdv OBJECT-TYPE
        SYNTAX  INTEGER
        ACCESS  read-write
        STATUS  mandatory
        DESCRIPTION
                "The Cell Delay Variation (in microseconds). The value
                -1 is used to indicate that this value is not used."
        ::= { trafficDescriptorEntry 26 }

trafficDescriptorLogClr OBJECT-TYPE
        SYNTAX  INTEGER
        ACCESS  read-write
        STATUS  mandatory
        DESCRIPTION
                "Minus the base 10 logarithm of the Cell Loss Ratio. The
                value 0 is used to indicate that this value is not
                used."
        ::= { trafficDescriptorEntry 27 }


-- Service Registry

configIlmiServiceRegistryTable OBJECT-TYPE
        SYNTAX  SEQUENCE OF ConfigIlmiServiceRegistryEntry
        ACCESS  not-accessible
        STATUS  mandatory
        DESCRIPTION
                "This table is used to configure the contents of the
                ILMI service registry on all ATM ports."
        ::= { configServiceReg 1 }

configIlmiServiceRegistryEntry OBJECT-TYPE
        SYNTAX  ConfigIlmiServiceRegistryEntry
        ACCESS  not-accessible
        STATUS  mandatory
        DESCRIPTION
                "Each row in this table describes one service provided
                by one service provider."
        INDEX   { configIlmiServiceRegistryServiceId,
                  configIlmiServiceRegistryAddressIndex }
        ::= { configIlmiServiceRegistryTable 1 }

ConfigIlmiServiceRegistryEntry ::=
        SEQUENCE {
            configIlmiServiceRegistryAddressIndex
                INTEGER,
            configIlmiServiceRegistryServiceId
                OBJECT IDENTIFIER,
            configIlmiServiceRegistryAtmAddress
                AtmAddress,
            configIlmiServiceRegistryParm1
                OCTET STRING,
            configIlmiServiceRegistryRowStatus
                INTEGER
        }

configIlmiServiceRegistryAddressIndex OBJECT-TYPE
        SYNTAX  INTEGER
        ACCESS  read-only
        STATUS  mandatory
        DESCRIPTION
                "An arbitrary integer used to differentiate multiple
                rows containing different ATM addresses for the same
                service."
        ::= { configIlmiServiceRegistryEntry 1 }

configIlmiServiceRegistryServiceId OBJECT-TYPE
        SYNTAX  OBJECT IDENTIFIER
        ACCESS  read-write
        STATUS  mandatory
        DESCRIPTION
                "The service identifier which uniquely identifies the
                type of service at the address provided in the table.
                Legal values are given in the Service Registry MIB in
                the ILMI specification."
        ::= { configIlmiServiceRegistryEntry 2 }

configIlmiServiceRegistryAtmAddress OBJECT-TYPE
        SYNTAX  AtmAddress
        ACCESS  read-write
        STATUS  mandatory
        DESCRIPTION
                "The full ATM address of the service. The user-side
                IME may use this address to establish a connection
                with the service."
        ::= { configIlmiServiceRegistryEntry 3 }

configIlmiServiceRegistryParm1 OBJECT-TYPE
        SYNTAX  OCTET STRING (SIZE (1..255))
        ACCESS  read-write
        STATUS  mandatory
        DESCRIPTION
                "An octet string whose size and meaning is determined
                by the value of configIlmiServiceRegistryServiceId."
        ::= { configIlmiServiceRegistryEntry 4 }

configIlmiServiceRegistryRowStatus OBJECT-TYPE
        SYNTAX  INTEGER { active(1),
                          notInService(2),
                          notReady(3),
                          createAndGo(4),
                          createAndWait(5),
                          destroy(6) }
        ACCESS  read-write
        STATUS  mandatory
        DESCRIPTION
                "Used to control creation and deletion of new rows
                in the table."
        ::= { configIlmiServiceRegistryEntry 5 }

-- SAR Configuration

-- The SAR is used to assemble frames intended for the switch itself.
-- It shares the first iPort with the first ePort through a multiplexer.

configSarMuxFillThreshold OBJECT-TYPE
        SYNTAX  INTEGER (1..63)
        ACCESS  read-write
        STATUS  mandatory
        DESCRIPTION
                "The number of cells in the SAR multiplexer FIFO that
                will cause the PHY to take priority over the SAR."
        ::= { configSar 1 }

configSarMuxSarVpi OBJECT-TYPE
        SYNTAX  INTEGER (1..255)
        ACCESS  read-write
        STATUS  mandatory
        DESCRIPTION
                "The VPI used to distinguish cells on iPort 0 that are
                intended for the SAR."
        ::= { configSar 2 }

configSarEmptyCellHandling OBJECT-TYPE
        SYNTAX  INTEGER { idle(1), unassigned(2) }
        ACCESS  read-write
        STATUS  mandatory
        DESCRIPTION
                ""
        ::= { configSar 3 }


-- xModules Configuration

configXModuleTable OBJECT-TYPE
        SYNTAX  SEQUENCE OF ConfigXModuleEntry
        ACCESS  not-accessible
        STATUS  mandatory
        DESCRIPTION
                "This table contains configuration information for the
                expansion modules."
        ::= { configXModule 1 }

configXModuleEntry OBJECT-TYPE
        SYNTAX  ConfigXModuleEntry
        ACCESS  not-accessible
        STATUS  mandatory
        DESCRIPTION
                "Each row in this table contains information about one
                expansion module."
        INDEX   { configXModuleSlotIndex }
        ::= { configXModuleTable 1 }

ConfigXModuleEntry ::=
        SEQUENCE {
            configXModuleSlotIndex
                INTEGER,
            configXModuleAdminStatus
                INTEGER
        }

configXModuleSlotIndex OBJECT-TYPE
        SYNTAX  INTEGER (1..8)
        ACCESS  read-only
        STATUS  mandatory
        DESCRIPTION
                "The slot number for the expansion module. It is used
                to index the expansion module in the table."
        ::= { configXModuleEntry 1 }

configXModuleAdminStatus OBJECT-TYPE
        SYNTAX  INTEGER { up(1),
                          down(2),
                          reset(3) }
        ACCESS  read-write
        STATUS  mandatory
        DESCRIPTION 
                "Enables, disables, or resets the expansion module."
        ::= { configXModuleEntry 2 }


-- Feature Module Configuration

configFeatureModuleAdminStatus OBJECT-TYPE
        SYNTAX  INTEGER { up(1), down(2) }
        ACCESS  read-write
        STATUS  mandatory
        DESCRIPTION
                "Enables or disables the feature module."
        ::= { configFeatureModule 1 }


-- Common ePort Configuration

-- The objects in this section contain configuration that is common to
-- all ePorts. The value of objects whose name start with
-- 'configCommonEPort...' may be overridden by values in
-- configEPortTable.


configCommonEPortIlmiAdminStatus OBJECT-TYPE
        SYNTAX  INTEGER { full(1),
                          -- limited(2), deleted
                          off(3) }
        ACCESS  read-write
        STATUS  mandatory
        DESCRIPTION
                "Enables or disables ILMI on an ATM port."
        ::= { configCommonEPort 1 }

configCommonEPortAddrRegistrationAdminStatus OBJECT-TYPE
        SYNTAX  INTEGER { supported(1), unsupported(2) }
        ACCESS  read-write
        STATUS  mandatory
        DESCRIPTION
                "Enables or disables the address registration protocol
                on an ATM port."
        ::= { configCommonEPort 2 }

configCommonEPortMaxVpcs OBJECT-TYPE
        SYNTAX  INTEGER (0..255)
        ACCESS  read-write
        STATUS  mandatory
        DESCRIPTION
                "The maximum number of VPCs on an ATM port."
        ::= { configCommonEPort 3 }

configCommonEPortMaxVccs OBJECT-TYPE
        SYNTAX  INTEGER (0..32767)
        ACCESS  read-write
        STATUS  mandatory
        DESCRIPTION
                "The maximum number of VCCs on an ATM port."
        ::= { configCommonEPort 4 }

configCommonEPortMaxVpiBits OBJECT-TYPE
        SYNTAX  INTEGER (0..8)
        ACCESS  read-write
        STATUS  mandatory
        DESCRIPTION
                "The number of bits used in a VPI on an ATM port."
        ::= { configCommonEPort 5 }

configCommonEPortMaxVciBits OBJECT-TYPE
        SYNTAX  INTEGER (0..14)
        ACCESS  read-write
        STATUS  mandatory
        DESCRIPTION
                "The number of bits used in a VCI on an ATM port."
        ::= { configCommonEPort 6 }

configCommonEPortUniType OBJECT-TYPE
        SYNTAX  INTEGER { public(1), private(2) }
        ACCESS  read-write
        STATUS  mandatory
        DESCRIPTION
                "The UNI type on an ATM port."
        ::= { configCommonEPort 7 }

configCommonEPortUniVersion OBJECT-TYPE
        SYNTAX  INTEGER { version3point0(2),
                          version3point1(3),
                          version4point0(4) }
        ACCESS  read-write
        STATUS  mandatory
        DESCRIPTION
                "The highest UNI version used on an ATM port."
        ::= { configCommonEPort 8 }

configCommonEPortDeviceType OBJECT-TYPE
        SYNTAX  INTEGER { user(1), node(2) }
        ACCESS  read-write
        STATUS  mandatory
        DESCRIPTION
                "The ATM port device type."
        ::= { configCommonEPort 9 }

configCommonEPortIlmiVersion OBJECT-TYPE
        SYNTAX  INTEGER { unsupported(1),
                          version4point0(2) }
        ACCESS  read-write
        STATUS  mandatory
        DESCRIPTION
                "The highest ILMI version used on an ATM port."
        ::= { configCommonEPort 10 }

configCommonEPortNniSigVersion OBJECT-TYPE
        SYNTAX  INTEGER { unsupported(1),
                          iisp(2),
                          pnniVersion1point0(3) }
        ACCESS  read-write
        STATUS  mandatory
        DESCRIPTION
                "The NNI signalling protocol used on an ATM port."
        ::= { configCommonEPort 11 }

configCommonEPortSignallingVpi OBJECT-TYPE
        SYNTAX  INTEGER (0..255)
        ACCESS  read-write
        STATUS  mandatory
        DESCRIPTION
                "The VPI used for signalling."
        ::= { configCommonEPort 12 }

configCommonEPortSignallingVci OBJECT-TYPE
        SYNTAX  INTEGER (0..16383)
        ACCESS  read-write
        STATUS  mandatory
        DESCRIPTION
                "The VCI used for signalling."
        ::= { configCommonEPort 13 }

configCommonEPortIlmiVpi OBJECT-TYPE
        SYNTAX  INTEGER (0..255)
        ACCESS  read-write
        STATUS  mandatory
        DESCRIPTION
                "The VPI used for ILMI."
        ::= { configCommonEPort 14 }

configCommonEPortIlmiVci OBJECT-TYPE
        SYNTAX  INTEGER (0..16383)
        ACCESS  read-write
        STATUS  mandatory
        DESCRIPTION
                "The VCI used for ILMI."
        ::= { configCommonEPort 15 }

configCommonEPortLecsVpi OBJECT-TYPE
        SYNTAX  INTEGER (0..255)
        ACCESS  read-write
        STATUS  mandatory
        DESCRIPTION
                "The VPI used for LECS."
        ::= { configCommonEPort 16 }

configCommonEPortLecsVci OBJECT-TYPE
        SYNTAX  INTEGER (0..16383)
        ACCESS  read-write
        STATUS  mandatory
        DESCRIPTION
                "The VCI used for LECS."
        ::= { configCommonEPort 17 }

configCommonEPortPnniVpi OBJECT-TYPE
        SYNTAX  INTEGER (0..255)
        ACCESS  read-write
        STATUS  mandatory
        DESCRIPTION
                "The VPI used for PNNI."
        ::= { configCommonEPort 18 }

configCommonEPortPnniVci OBJECT-TYPE
        SYNTAX  INTEGER (0..16383)
        ACCESS  read-write
        STATUS  mandatory
        DESCRIPTION
                "The VCI used for PNNI."
        ::= { configCommonEPort 19 }

configCommonEPortAbrBandwidthAllocation OBJECT-TYPE
        SYNTAX  INTEGER (0..100)
        ACCESS  read-write
        STATUS  mandatory
        DESCRIPTION
                "The maximum percentage of the ATM link bandwidth that
                may be used for ABR traffic."
        ::= { configCommonEPort 20 }

configCommonEPortVbrRtBandwidthAllocation OBJECT-TYPE
        SYNTAX  INTEGER (0..100)
        ACCESS  read-write
        STATUS  mandatory
        DESCRIPTION
                "The maximum percentage of the ATM link bandwidth that
                may be used for rt-VBR traffic."
        ::= { configCommonEPort 21 }

configCommonEPortVbrNrtBandwidthAllocation OBJECT-TYPE
        SYNTAX  INTEGER (0..100)
        ACCESS  read-write
        STATUS  mandatory
        DESCRIPTION
                "The maximum percentage of the ATM link bandwidth that
                may be used for nrt-VBR traffic."
        ::= { configCommonEPort 22 }

configCommonEPortCbrBandwidthAllocation OBJECT-TYPE
        SYNTAX  INTEGER (0..100)
        ACCESS  read-write
        STATUS  mandatory
        DESCRIPTION
                "The maximum percentage of the ATM link bandwidth that
                may be used for CBR traffic."
        ::= { configCommonEPort 23 }

configStaticEPortIlmiPollFrequency OBJECT-TYPE
        SYNTAX  INTEGER (1..20)
        ACCESS  read-write
        STATUS  mandatory
        DESCRIPTION
                "Polling frequency in seconds for maintaining ILMI
                connectivity."
        ::= { configCommonEPort 24 }

configStaticEPortIlmiPollRetries OBJECT-TYPE
        SYNTAX  INTEGER (1..10)
        ACCESS  read-write
        STATUS  mandatory
        DESCRIPTION
                "The number of retries before declaring a loss of ILMI
                connectivity."
        ::= { configCommonEPort 25 }

configStaticEPortMaxTransientPhyFailureTime OBJECT-TYPE
        SYNTAX  INTEGER (0..10)
        ACCESS  read-write
        STATUS  mandatory
        DESCRIPTION
                "The maximum time in seconds where loss of signal or
                lack of rx sync is not considered a loss of PHY
                connectivity. A value of 0 indicates that failures
                will never be considered transient."
        ::= { configCommonEPort 26 }

configStaticEPortMaxPhyFailuresPerMinute OBJECT-TYPE
        SYNTAX  INTEGER (1..10)
        ACCESS  read-write
        STATUS  deprecated
        DESCRIPTION
                "The maximum number of transient or non-transient PHY
                failures per minute before an ATM port is automatically
                disabled and an ePortAutoDisabled trap is generated."
        ::= { configCommonEPort 27 }

configCommonEPortLinkDelay OBJECT-TYPE
        SYNTAX  INTEGER
        ACCESS  read-write
        STATUS  mandatory
        DESCRIPTION
                "The expected transmission delay on the ATM link (in
                microseconds)."
        ::= { configCommonEPort 28 }

configCommonEPortTransientPhyOffTime OBJECT-TYPE
        SYNTAX  INTEGER
        ACCESS  read-write
        STATUS  deprecated
        DESCRIPTION
                "The time (in seconds) that the PHY may be
                disconnected during
                configCommonEPortTransientPhyWindowTime before an
                ePortAutoDisabled trap is sent."
        ::= { configCommonEPort 29 }

configCommonEPortTransientPhyWindowTime OBJECT-TYPE
        SYNTAX  INTEGER
        ACCESS  read-write
        STATUS  deprecated
        DESCRIPTION
                "The duration (in seconds) of the window used for
                measuring PHY down time."
        ::= { configCommonEPort 30 }

configCommonEPortTransientPhyDisconnectCount OBJECT-TYPE
        SYNTAX  INTEGER (1..100)
        ACCESS  read-write
        STATUS  mandatory
        DESCRIPTION
                "Number of PHY disconnects that may occur during
                configCommonEPortTransientPhyDisconnectTimer before an
                ePortAutoDisabled trap is sent."
        ::= { configCommonEPort 31 }

configCommonEPortTransientPhyDisconnectTimer OBJECT-TYPE
        SYNTAX  INTEGER
        ACCESS  read-write
        STATUS  mandatory
        DESCRIPTION
                "The duration (in seconds) of the time used for
                counting PHY disconnects."
        ::= { configCommonEPort 32 }

configCommonEPortDefaultSigVersion OBJECT-TYPE
        SYNTAX  INTEGER { uni(1),
                          pnni(2),
                          iispNetworkSide(3),
                          iispUserSide(4) }
        ACCESS  read-write
        STATUS  mandatory
        DESCRIPTION
                "The signalling version used if ILMI autoconfiguration
                is not possible."
        ::= { configCommonEPort 33 }

configCommonEPortMaxSvpcVpi OBJECT-TYPE
        SYNTAX  INTEGER (0..4096)
        ACCESS  read-write
        STATUS  mandatory
        DESCRIPTION
                "The maximum VPI that the signalling stack on the port
                is configured to support for allocation to SVPCs."
        ::= { configCommonEPort 34 }

configCommonEPortMaxSvccVpi OBJECT-TYPE
        SYNTAX  INTEGER (0..4096)
        ACCESS  read-write
        STATUS  mandatory
        DESCRIPTION
                "The maximum VPI that the signalling stack on the port
                is configured to support for allocation to SVCCs."
        ::= { configCommonEPort 35 }

configCommonEPortMinSvccVci OBJECT-TYPE
        SYNTAX  INTEGER (0..65536)
        ACCESS  read-write
        STATUS  mandatory
        DESCRIPTION
                "The minimum VCI that the signalling stack on the port
                is configured to support for allocation to SVCCs. The
                same value applies to all SVCC VPI values for which
                the signalling stack is configured."
        ::= { configCommonEPort 36 }

-- ePort Configuration Table

-- The entries in configEPortTable are atomically updated by copying a
-- row in the table to the ePort 'scratch pad', modifying the contents
-- of the scratch pad, and saving the contents of the scratch pad in
-- configEPortTable. This is done in the following manner:
--
-- 1. Store the row number in configEPortScratchPadEPortIndex.
-- 2. Check that configEPortScratchPadScratchPadStatus is 'notReady'.
-- 3. Set configEPortScratchPadScratchPadStatus to 'copy'.
-- 4. Wait for configEPortScratchPadScratchPadStatus to become 'copied'.
-- 5. Check configEPortScratchPadActionStatus.
-- 6. Modify the contents of the configEPortScratchPad... objects.
-- 7. Set configEPortScratchPadScratchPadStatus to 'updateAndGo'.
-- 8. Check configEPortScratchPadActionStatus.


configEPortScratchPadScratchPadStatus OBJECT-TYPE
        SYNTAX  INTEGER { notReady(1),
                          copy(2),
                          copied(3),
                          updateAndGo(4) }
        ACCESS  read-write
        STATUS  mandatory
        DESCRIPTION
                "Controls the copying of data between configEPortTable
                and the ePort scratch pad."
        ::= { configEPort 1 }


configEPortScratchPadEPortIndex OBJECT-TYPE
        SYNTAX  INTEGER
        ACCESS  read-write
        STATUS  mandatory
        DESCRIPTION
                "Set to the row index in configEPortTable before the
                contents of the row are copied to the ePort scratch
                pad."
        ::= { configEPort 2 }

configEPortScratchPadIpAddress OBJECT-TYPE
        SYNTAX  IpAddress
        ACCESS  read-only
        STATUS  mandatory
        DESCRIPTION
                "The IP address of the manager that uses the ePort
                scratch pad. Used as a lock."
        ::= { configEPort 3 }

configEPortScratchPadActionStatus OBJECT-TYPE
        SYNTAX  INTEGER { ok(1),
                          failed(2),
                          notPossible(3) }
        ACCESS  read-only
        STATUS  mandatory
        DESCRIPTION
                "The result of an attempt to copy between
                configEPortTable and the scratch pad."
        ::= { configEPort 4 }

configEPortScratchPadHwConfigTxClocking OBJECT-TYPE
        SYNTAX  INTEGER { network(1), local(2) }
        ACCESS  read-write
        STATUS  mandatory
        DESCRIPTION
                "A copy of configEPortHwConfigTxClocking."
        ::= { configEPort 5 }

configEPortScratchPadHwConfigSonetSdh OBJECT-TYPE
        SYNTAX  INTEGER { sonet(1), sdh(2), none(3) }
        ACCESS  read-write
        STATUS  mandatory
        DESCRIPTION
                "A copy of configEPortHwConfigSonetSdh."
        ::= { configEPort 6 }

configEPortScratchPadUseCommonEPortConfig OBJECT-TYPE
        SYNTAX  INTEGER { yes(1), no(2) }
        ACCESS  read-write
        STATUS  mandatory
        DESCRIPTION
                "A copy of configEPortUseCommonEPortConfig."
        ::= { configEPort 7 }

configEPortScratchPadLoopback OBJECT-TYPE
        SYNTAX  INTEGER { none(1),
                          line(2),
                          payload(3),
                          diag(4),
                          externalLine(5) }
        ACCESS  read-write
        STATUS  mandatory
        DESCRIPTION
                "A copy of configEPortLoopback."
        ::= { configEPort 8 }

configEPortScratchPadIlmiConfigIlmiAdminStatus OBJECT-TYPE
        SYNTAX  INTEGER { full(1),
                          -- limited(2), deleted
                          off(3) }
        ACCESS  read-write
        STATUS  mandatory
        DESCRIPTION
                "A copy of configEPortIlmiConfigIlmiAdminStatus."
        ::= { configEPort 9 }

configEPortScratchPadIlmiConfigAddrRegistrationAdminStatus OBJECT-TYPE
        SYNTAX  INTEGER { supported(1), unsupported(2) }
        ACCESS  read-write
        STATUS  mandatory
        DESCRIPTION
                "A copy of
                configEPortIlmiConfigAddrRegistrationAdminStatus."
        ::= { configEPort 10 }

configEPortScratchPadIlmiConfigMaxVpcs OBJECT-TYPE
        SYNTAX  INTEGER (0..255)
        ACCESS  read-write
        STATUS  mandatory
        DESCRIPTION
                "A copy of configEPortIlmiConfigMaxVpcs."
        ::= { configEPort 11 }

configEPortScratchPadIlmiConfigMaxVccs OBJECT-TYPE
        SYNTAX  INTEGER (0..32767)
        ACCESS  read-write
        STATUS  mandatory
        DESCRIPTION
                "A copy of configEPortIlmiConfigMaxVccs."
        ::= { configEPort 12 }

configEPortScratchPadIlmiConfigMaxVpiBits OBJECT-TYPE
        SYNTAX  INTEGER (0..8)
        ACCESS  read-write
        STATUS  mandatory
        DESCRIPTION
                "A copy of configEPortIlmiConfigMaxVpiBits."
        ::= { configEPort 13 }

configEPortScratchPadIlmiConfigMaxVciBits OBJECT-TYPE
        SYNTAX  INTEGER (0..14)
        ACCESS  read-write
        STATUS  mandatory
        DESCRIPTION
                "A copy of configEPortIlmiConfigMaxVciBits."
        ::= { configEPort 14 }

configEPortScratchPadIlmiConfigUniType OBJECT-TYPE
        SYNTAX  INTEGER { public(1), private(2) }
        ACCESS  read-write
        STATUS  mandatory
        DESCRIPTION
                "A copy of configEPortIlmiConfigUniType."
        ::= { configEPort 15 }

configEPortScratchPadIlmiConfigUniVersion OBJECT-TYPE
        SYNTAX  INTEGER { version3point0(2),
                          version3point1(3),
                          version4point0(4) }
        ACCESS  read-write
        STATUS  mandatory
        DESCRIPTION
                "A copy of configEPortIlmiConfigUniVersion."
        ::= { configEPort 16 }

configEPortScratchPadIlmiConfigDeviceType OBJECT-TYPE
        SYNTAX  INTEGER { user(1), node(2) }
        ACCESS  read-write
        STATUS  mandatory
        DESCRIPTION
                "A copy of configEPortIlmiConfigDeviceType."
        ::= { configEPort 17 }

configEPortScratchPadIlmiConfigIlmiVersion OBJECT-TYPE
        SYNTAX  INTEGER { unsupported(1),
                          version4point0(2) }
        ACCESS  read-write
        STATUS  mandatory
        DESCRIPTION
                "A copy of configEPortIlmiConfigIlmiVersion."
        ::= { configEPort 18 }

configEPortScratchPadIlmiConfigNniSigVersion OBJECT-TYPE
        SYNTAX  INTEGER { unsupported(1),
                          iisp(2),
                          pnniVersion1point0(3) }
        ACCESS  read-write
        STATUS  mandatory
        DESCRIPTION
                "A copy of configEPortIlmiConfigNniSigVersion."
        ::= { configEPort 19 }

configEPortScratchPadIlmiConfigSignallingVpi OBJECT-TYPE
        SYNTAX  INTEGER (0..255)
        ACCESS  read-write
        STATUS  mandatory
        DESCRIPTION
                "A copy of configEPortIlmiConfigSignallingVpi."
        ::= { configEPort 20 }

configEPortScratchPadIlmiConfigSignallingVci OBJECT-TYPE
        SYNTAX  INTEGER (0..16383)
        ACCESS  read-write
        STATUS  mandatory
        DESCRIPTION
                "A copy of configEPortIlmiConfigSignallingVci."
        ::= { configEPort 21 }

configEPortScratchPadIlmiConfigIlmiVpi OBJECT-TYPE
        SYNTAX  INTEGER (0..255)
        ACCESS  read-write
        STATUS  mandatory
        DESCRIPTION
                "A copy of configEPortIlmiConfigIlmiVpi."
        ::= { configEPort 22 }

configEPortScratchPadIlmiConfigIlmiVci OBJECT-TYPE
        SYNTAX  INTEGER (0..16383)
        ACCESS  read-write
        STATUS  mandatory
        DESCRIPTION
                "A copy of configEPortIlmiConfigIlmiVci."
        ::= { configEPort 23 }

configEPortScratchPadIlmiConfigLecsVpi OBJECT-TYPE
        SYNTAX  INTEGER (0..255)
        ACCESS  read-write
        STATUS  mandatory
        DESCRIPTION
                "A copy of configEPortIlmiConfigLecsVpi."
        ::= { configEPort 24 }

configEPortScratchPadIlmiConfigLecsVci OBJECT-TYPE
        SYNTAX  INTEGER (0..16383)
        ACCESS  read-write
        STATUS  mandatory
        DESCRIPTION
                "A copy of configEPortIlmiConfigLecsVci."
        ::= { configEPort 25 }

configEPortScratchPadIlmiConfigPnniVpi OBJECT-TYPE
        SYNTAX  INTEGER (0..255)
        ACCESS  read-write
        STATUS  mandatory
        DESCRIPTION
                "A copy of configEPortIlmiConfigPnniVpi."
        ::= { configEPort 26 }

configEPortScratchPadIlmiConfigPnniVci OBJECT-TYPE
        SYNTAX  INTEGER (0..16383)
        ACCESS  read-write
        STATUS  mandatory
        DESCRIPTION
                "A copy of configEPortIlmiConfigPnniVci."
        ::= { configEPort 27 }

configEPortScratchPadAbrBandwidthAllocation OBJECT-TYPE
        SYNTAX  INTEGER (0..100)
        ACCESS  read-write
        STATUS  mandatory
        DESCRIPTION
                "A copy of configEPortAbrBandwidthAllocation."
        ::= { configEPort 28 }

configEPortScratchPadVbrRtBandwidthAllocation OBJECT-TYPE
        SYNTAX  INTEGER (0..100)
        ACCESS  read-write
        STATUS  mandatory
        DESCRIPTION
                "A copy of configEPortVbrRtBandwidthAllocation."
        ::= { configEPort 29 }

configEPortScratchPadVbrNrtBandwidthAllocation OBJECT-TYPE
        SYNTAX  INTEGER (0..100)
        ACCESS  read-write
        STATUS  mandatory
        DESCRIPTION
                "A copy of configEPortVbrNrtBandwidthAllocation."
        ::= { configEPort 30 }

configEPortScratchPadCbrBandwidthAllocation OBJECT-TYPE
        SYNTAX  INTEGER (0..100)
        ACCESS  read-write
        STATUS  mandatory
        DESCRIPTION
                "A copy of configEPortCbrBandwidthAllocation."
        ::= { configEPort 31 }

configEPortScratchPadLinkDelay OBJECT-TYPE
        SYNTAX  INTEGER
        ACCESS  read-write
        STATUS  mandatory
        DESCRIPTION
                "A copy of configEPortLinkDelay."
        ::= { configEPort 32 }

configEPortScratchPadTransientPhyOffTime OBJECT-TYPE
        SYNTAX  INTEGER
        ACCESS  read-write
        STATUS  deprecated
        DESCRIPTION
                "A copy of configEPortTransientPhyOffTime."
        ::= { configEPort 33 }

configEPortScratchPadTransientPhyWindowTime OBJECT-TYPE
        SYNTAX  INTEGER
        ACCESS  read-write
        STATUS  deprecated
        DESCRIPTION
                "A copy of configEPortTransientPhyWindowTime."
        ::= { configEPort 34 }

configEPortScratchPadTransientPhyDisconnectCount OBJECT-TYPE
        SYNTAX  INTEGER (1..100)
        ACCESS  read-write
        STATUS  mandatory
        DESCRIPTION
                "A copy of configEPortTransientPhyDisconnectCount."
        ::= { configEPort 35 }

configEPortScratchPadTransientPhyDisconnectTimer OBJECT-TYPE
        SYNTAX  INTEGER
        ACCESS  read-write
        STATUS  mandatory
        DESCRIPTION
                "A copy of configEPortTransientPhyDisconnectTimer."
        ::= { configEPort 36 }

configEPortScratchPadBandwidthLimit OBJECT-TYPE
        SYNTAX  INTEGER
        ACCESS  read-write
        STATUS  mandatory
        DESCRIPTION
                "A copy of configEPortBandwidthLimit."
        ::= { configEPort 37 }

-- Note: { configEPort 38 } is located below

configEPortScratchPadDefaultSigVersion OBJECT-TYPE
        SYNTAX  INTEGER { uni(1),
                          pnni(2),
                          iispNetworkSide(3),
                          iispUserSide(4) }
        ACCESS  read-write
        STATUS  mandatory
        DESCRIPTION
                "A copy of configEPortDefaultSigVersion."
        ::= { configEPort 39 }

configEPortScratchPadIlmiConfigMaxSvpcVpi OBJECT-TYPE
        SYNTAX  INTEGER (0..4096)
        ACCESS  read-write
        STATUS  mandatory
        DESCRIPTION
                "A copy of configEPortIlmiConfigMaxSvpcVpi."
        ::= { configEPort 40 }

configEPortScratchPadIlmiConfigMaxSvccVpi OBJECT-TYPE
        SYNTAX  INTEGER (0..4096)
        ACCESS  read-write
        STATUS  mandatory
        DESCRIPTION
                "A copy of configEPortIlmiConfigMaxSvccVpi."
        ::= { configEPort 41 }

configEPortScratchPadIlmiConfigMinSvccVci OBJECT-TYPE
        SYNTAX  INTEGER (0..65536)
        ACCESS  read-write
        STATUS  mandatory
        DESCRIPTION
                "A copy of configEPortIlmiConfigMinSvccVci."
        ::= { configEPort 42 }


configEPortTable OBJECT-TYPE
        SYNTAX  SEQUENCE OF ConfigEPortEntry
        ACCESS  not-accessible
        STATUS  mandatory
        DESCRIPTION
                "This table contains configuration for each ATM port
                (ePort) in the switch. The table may be modified
                through the ePort scratch pad."
        ::= { configEPort 38 }

configEPortEntry OBJECT-TYPE
        SYNTAX  ConfigEPortEntry
        ACCESS  not-accessible
        STATUS  mandatory
        DESCRIPTION
                "Each row in this table describes one ATM port
                (ePort)."
        INDEX   { configEPortIfIndex }
        ::= { configEPortTable 1 }

ConfigEPortEntry ::=
        SEQUENCE {
            configEPortIfIndex
                INTEGER,
            configEPortHwConfigTxClocking
                INTEGER,
            configEPortHwConfigSonetSdh
                INTEGER,
            configEPortUseCommonEPortConfig
                INTEGER,
            configEPortLoopback
                INTEGER,
            configEPortIlmiConfigIlmiAdminStatus
                INTEGER,
            configEPortIlmiConfigAddrRegistrationAdminStatus
                INTEGER,
            configEPortIlmiConfigMaxVpcs
                INTEGER,
            configEPortIlmiConfigMaxVccs
                INTEGER,
            configEPortIlmiConfigMaxVpiBits
                INTEGER,
            configEPortIlmiConfigMaxVciBits
                INTEGER,
            configEPortIlmiConfigUniType
                INTEGER,
            configEPortIlmiConfigUniVersion
                INTEGER,
            configEPortIlmiConfigDeviceType
                INTEGER,
            configEPortIlmiConfigIlmiVersion
                INTEGER,
            configEPortIlmiConfigNniSigVersion
                INTEGER,
            configEPortIlmiConfigSignallingVpi
                INTEGER,
            configEPortIlmiConfigSignallingVci
                INTEGER,
            configEPortIlmiConfigIlmiVpi
                INTEGER,
            configEPortIlmiConfigIlmiVci
                INTEGER,
            configEPortIlmiConfigLecsVpi
                INTEGER,
            configEPortIlmiConfigLecsVci
                INTEGER,
            configEPortIlmiConfigPnniVpi
                INTEGER,
            configEPortIlmiConfigPnniVci
                INTEGER,
            configEPortAbrBandwidthAllocation
                INTEGER,
            configEPortVbrRtBandwidthAllocation
                INTEGER,
            configEPortVbrNrtBandwidthAllocation
                INTEGER,
            configEPortCbrBandwidthAllocation
                INTEGER,
            configEPortLinkDelay
                INTEGER,
            configEPortTransientPhyOffTime
                INTEGER,
            configEPortTransientPhyWindowTime
                INTEGER,
            configEPortTransientPhyDisconnectCount
                INTEGER,
            configEPortTransientPhyDisconnectTimer
                INTEGER,
            configEPortBandwidthLimit
                INTEGER,
            configEPortDefaultSigVersion
                INTEGER,
            configEPortIlmiConfigMaxSvpcVpi
                INTEGER,
            configEPortIlmiConfigMaxSvccVpi
                INTEGER,
            configEPortIlmiConfigMinSvccVci
                INTEGER
        }

configEPortIfIndex OBJECT-TYPE
        SYNTAX  INTEGER
        ACCESS  read-only
        STATUS  mandatory
        DESCRIPTION
                "The ifIndex of the ATM port described by this row."
        ::= { configEPortEntry 1 }

configEPortHwConfigTxClocking OBJECT-TYPE
        SYNTAX  INTEGER { network(1), local(2) }
        ACCESS  read-only
        STATUS  mandatory
        DESCRIPTION
                 "The clocking source for this ATM port. This setting
                is disregarded if this port is configured to receive
                the master clock from the network."
        ::= { configEPortEntry 2 }

configEPortHwConfigSonetSdh OBJECT-TYPE
        SYNTAX  INTEGER { sonet(1), sdh(2), none(3) }
        ACCESS  read-only
        STATUS  mandatory
        DESCRIPTION
                "The cell framing used on this ATM port."
        ::= { configEPortEntry 3 }

configEPortUseCommonEPortConfig OBJECT-TYPE
        SYNTAX  INTEGER { yes(1), no(2) }
        ACCESS  read-only
        STATUS  mandatory
        DESCRIPTION
                "Indicates if this ATM port should use the common
                ePort configuration (found in the configCommonEPort
                MIB subtree) or its own configuration."
        ::= { configEPortEntry 4 }

configEPortLoopback OBJECT-TYPE
        SYNTAX  INTEGER { none(1),
                          line(2),
                          payload(3),
                          diag(4),
                          externalLine(5) }
        ACCESS  read-only
        STATUS  mandatory
        DESCRIPTION
                "The hardware loopback type on this ATM port."
        ::= { configEPortEntry 5 }

configEPortIlmiConfigIlmiAdminStatus OBJECT-TYPE
        SYNTAX  INTEGER { full(1),
                          -- limited(2), deleted
                          off(3) }
        ACCESS  read-only
        STATUS  mandatory
        DESCRIPTION
                "Enables or disables ILMI on this ATM port."
        ::= { configEPortEntry 6 }

configEPortIlmiConfigAddrRegistrationAdminStatus OBJECT-TYPE
        SYNTAX  INTEGER { supported(1), unsupported(2) }
        ACCESS  read-only
        STATUS  mandatory
        DESCRIPTION
                "Enables or disables the address registration protocol
                on this ATM port."
        ::= { configEPortEntry 7 }

configEPortIlmiConfigMaxVpcs OBJECT-TYPE
        SYNTAX  INTEGER (0..255)
        ACCESS  read-only
        STATUS  mandatory
        DESCRIPTION
                "The maximum number of VPCs on this ATM port."
        ::= { configEPortEntry 8 }

configEPortIlmiConfigMaxVccs OBJECT-TYPE
        SYNTAX  INTEGER (0..32767)
        ACCESS  read-only
        STATUS  mandatory
        DESCRIPTION
                "The maximum number of VCCs on this ATM port."
        ::= { configEPortEntry 9 }

configEPortIlmiConfigMaxVpiBits OBJECT-TYPE
        SYNTAX  INTEGER (0..8)
        ACCESS  read-only
        STATUS  mandatory
        DESCRIPTION
                "The number of bits used in a VPI on this ATM port."
        ::= { configEPortEntry 10 }

configEPortIlmiConfigMaxVciBits OBJECT-TYPE
        SYNTAX  INTEGER (0..14)
        ACCESS  read-only
        STATUS  mandatory
        DESCRIPTION
                "The number of bits used in a VCI on this ATM port."
        ::= { configEPortEntry 11 }

configEPortIlmiConfigUniType OBJECT-TYPE
        SYNTAX  INTEGER { public(1), private(2) }
        ACCESS  read-only
        STATUS  mandatory
        DESCRIPTION
                "The UNI type on this ATM port."
        ::= { configEPortEntry 12 }

configEPortIlmiConfigUniVersion OBJECT-TYPE
        SYNTAX  INTEGER { version3point0(2),
                          version3point1(3),
                          version4point0(4) }
        ACCESS  read-only
        STATUS  mandatory
        DESCRIPTION
                "The highest UNI version used on this ATM port."
        ::= { configEPortEntry 13 }

configEPortIlmiConfigDeviceType OBJECT-TYPE
        SYNTAX  INTEGER { user(1), node(2) }
        ACCESS  read-only
        STATUS  mandatory
        DESCRIPTION
                "The ATM port device type."
        ::= { configEPortEntry 14 }

configEPortIlmiConfigIlmiVersion OBJECT-TYPE
        SYNTAX  INTEGER { unsupported(1),
                          version4point0(2) }
        ACCESS  read-only
        STATUS  mandatory
        DESCRIPTION
                "The highest ILMI version used on this ATM port."
        ::= { configEPortEntry 15 }

configEPortIlmiConfigNniSigVersion OBJECT-TYPE
        SYNTAX  INTEGER { unsupported(1),
                          iisp(2),
                          pnniVersion1point0(3) }
        ACCESS  read-only
        STATUS  mandatory
        DESCRIPTION
                "The NNI signalling protocol used on this ATM port."
        ::= { configEPortEntry 16 }

configEPortIlmiConfigSignallingVpi OBJECT-TYPE
        SYNTAX  INTEGER (0..255)
        ACCESS  read-only
        STATUS  mandatory
        DESCRIPTION
                "The VPI used for signalling."
        ::= { configEPortEntry 17 }

configEPortIlmiConfigSignallingVci OBJECT-TYPE
        SYNTAX  INTEGER (0..16383)
        ACCESS  read-only
        STATUS  mandatory
        DESCRIPTION
                "The VCI used for signalling."
        ::= { configEPortEntry 18 }

configEPortIlmiConfigIlmiVpi OBJECT-TYPE
        SYNTAX  INTEGER (0..255)
        ACCESS  read-only
        STATUS  mandatory
        DESCRIPTION
                "The VPI used for ILMI."
        ::= { configEPortEntry 19 }

configEPortIlmiConfigIlmiVci OBJECT-TYPE
        SYNTAX  INTEGER (0..16383)
        ACCESS  read-only
        STATUS  mandatory
        DESCRIPTION
                "The VCI used for ILMI."
        ::= { configEPortEntry 20 }

configEPortIlmiConfigLecsVpi OBJECT-TYPE
        SYNTAX  INTEGER (0..255)
        ACCESS  read-only
        STATUS  mandatory
        DESCRIPTION
                "The VPI used for LECS."
        ::= { configEPortEntry 21 }

configEPortIlmiConfigLecsVci OBJECT-TYPE
        SYNTAX  INTEGER (0..16383)
        ACCESS  read-only
        STATUS  mandatory
        DESCRIPTION
                "The VCI used for LECS."
        ::= { configEPortEntry 22 }

configEPortIlmiConfigPnniVpi OBJECT-TYPE
        SYNTAX  INTEGER (0..255)
        ACCESS  read-only
        STATUS  mandatory
        DESCRIPTION
                "The VPI used for PNNI."
        ::= { configEPortEntry 23 }

configEPortIlmiConfigPnniVci OBJECT-TYPE
        SYNTAX  INTEGER (0..16383)
        ACCESS  read-only
        STATUS  mandatory
        DESCRIPTION
                "The VCI used for PNNI."
        ::= { configEPortEntry 24 }

configEPortAbrBandwidthAllocation OBJECT-TYPE
        SYNTAX  INTEGER (0..100)
        ACCESS  read-only
        STATUS  mandatory
        DESCRIPTION
                "The maximum percentage of the ATM link bandwidth that
                may be used for ABR traffic."
        ::= { configEPortEntry 25 }

configEPortVbrRtBandwidthAllocation OBJECT-TYPE
        SYNTAX  INTEGER (0..100)
        ACCESS  read-only
        STATUS  mandatory
        DESCRIPTION
                "The maximum percentage of the ATM link bandwidth that
                may be used for rt-VBR traffic."
        ::= { configEPortEntry 26 }

configEPortVbrNrtBandwidthAllocation OBJECT-TYPE
        SYNTAX  INTEGER (0..100)
        ACCESS  read-only
        STATUS  mandatory
        DESCRIPTION
                "The maximum percentage of the ATM link bandwidth that
                may be used for nrt-VBR traffic."
        ::= { configEPortEntry 27 }

configEPortCbrBandwidthAllocation OBJECT-TYPE
        SYNTAX  INTEGER (0..100)
        ACCESS  read-only
        STATUS  mandatory
        DESCRIPTION
                "The maximum percentage of the ATM link bandwidth that
                may be used for CBR traffic."
        ::= { configEPortEntry 28 }

configEPortLinkDelay OBJECT-TYPE
        SYNTAX  INTEGER
        ACCESS  read-only
        STATUS  mandatory
        DESCRIPTION
                "The expected transmission delay on the ATM link (in
                microseconds)."
        ::= { configEPortEntry 29 }

configEPortTransientPhyOffTime OBJECT-TYPE
        SYNTAX  INTEGER
        ACCESS  read-only
        STATUS  deprecated
        DESCRIPTION
                "The time (in seconds) that the PHY may be
                disconnected during configEPortTransientPhyWindowTime
                before an ePortAutoDisabled trap is sent."
        ::= { configEPortEntry 30 }

configEPortTransientPhyWindowTime OBJECT-TYPE
        SYNTAX  INTEGER
        ACCESS  read-only
        STATUS  deprecated
        DESCRIPTION
                "The duration (in seconds) of the window used for
                measuring PHY down time."
        ::= { configEPortEntry 31 }

configEPortTransientPhyDisconnectCount OBJECT-TYPE
        SYNTAX  INTEGER (1..100)
        ACCESS  read-only
        STATUS  mandatory
        DESCRIPTION
                "Number of PHY disconnects that may occur during
                configEPortTransientPhyDisconnectTimer before an
                ePortAutoDisabled trap is sent."
        ::= { configEPortEntry 32 }

configEPortTransientPhyDisconnectTimer OBJECT-TYPE
        SYNTAX  INTEGER
        ACCESS  read-only
        STATUS  mandatory
        DESCRIPTION
                "The duration (in seconds) of the time used for
                counting PHY disconnects."
        ::= { configEPortEntry 33 }

configEPortBandwidthLimit OBJECT-TYPE
        SYNTAX  INTEGER
        ACCESS  read-only
        STATUS  mandatory
        DESCRIPTION
                "The maximum total bandwidth that may be used on this
                ATM port (in cells/seconds). A value of -1 indicates that
                the full link rate may be used."
        ::= { configEPortEntry 34 }

configEPortDefaultSigVersion OBJECT-TYPE
        SYNTAX  INTEGER { uni(1),
                          pnni(2),
                          iispNetworkSide(3),
                          iispUserSide(4) }
        ACCESS  read-only
        STATUS  mandatory
        DESCRIPTION
                "The signalling version used if ILMI autoconfiguration
                is not possible."
        ::= { configEPortEntry 35 }

configEPortIlmiConfigMaxSvpcVpi OBJECT-TYPE
        SYNTAX  INTEGER (0..4096)
        ACCESS  read-only
        STATUS  mandatory
        DESCRIPTION
                "The maximum VPI that the signalling stack on the port
                is configured to support for allocation to SVPCs."
        ::= { configEPortEntry 36 }

configEPortIlmiConfigMaxSvccVpi OBJECT-TYPE
        SYNTAX  INTEGER (0..4096)
        ACCESS  read-only
        STATUS  mandatory
        DESCRIPTION
                "The maximum VPI that the signalling stack on the port
                is configured to support for allocation to SVCCs."
        ::= { configEPortEntry 37 }

configEPortIlmiConfigMinSvccVci OBJECT-TYPE
        SYNTAX  INTEGER (0..65536)
        ACCESS  read-only
        STATUS  mandatory
        DESCRIPTION
                "The minimum VCI that the signalling stack on the port
                is configured to support for allocation to SVCCs. The
                same value applies to all SVCC VPI values for which
                the signalling stack is configured."
        ::= { configEPortEntry 38 }


-- Note: { configEPort 39 } etc. are located before configEPortTable


-- CPU Queue Configuration

-- These objects configure the switch core's switch processor queue
-- and reset queue

configCpuPortCpuQueueSize OBJECT-TYPE
        SYNTAX  INTEGER
        ACCESS  read-write
        STATUS  mandatory
        DESCRIPTION
                "The maximum size of the switch processor queue. This
                must be an number of the form 255+256*N, where N is an
                integer."
        ::= { configCpuQ 1 }

configCpuPortResetQueueSize OBJECT-TYPE
        SYNTAX  INTEGER
        ACCESS  read-write
        STATUS  mandatory
        DESCRIPTION
                "The maximum size of the reset queue. This must be an
                number of the form 255+256*N, where N is an integer."
        ::= { configCpuQ 2 }


-- Common iPort Configuration

-- The objects in this section contain configuration that is common to
-- all iPorts. The value of objects whose name start with
-- 'configCommonIPort...' may be overridden by values in
-- configIPortQueueTable.


configCommonIPortQueueTable OBJECT-TYPE
        SYNTAX  SEQUENCE OF ConfigCommonIPortQueueEntry
        ACCESS  not-accessible
        STATUS  mandatory
        DESCRIPTION
                "This table contains configuration data for the four
                queues associated with each iPort."
        ::= { configCommonIPort 1 }

configCommonIPortQueueEntry OBJECT-TYPE
        SYNTAX  ConfigCommonIPortQueueEntry
        ACCESS  not-accessible
        STATUS  mandatory
        DESCRIPTION
                "Each row in this table contains data for one queue,
                but common to all iPorts."
        INDEX   { configCommonIPortQueueIndex }
        ::= { configCommonIPortQueueTable 1 }

ConfigCommonIPortQueueEntry ::=
        SEQUENCE {
            configCommonIPortQueueIndex
                INTEGER,
            configCommonIPortEfciTaggingAdminStatus
                INTEGER,
            configCommonIPortClpDiscardAdminStatus
                INTEGER,
            configCommonIPortEfciTaggingThreshold
                INTEGER,
            configCommonIPortClpDiscardThreshold
                INTEGER,
            configCommonIPortQueueSize
                INTEGER,
            configCommonIPortLogClr
                INTEGER,
            configCommonIPortCdv
                INTEGER
        }

configCommonIPortQueueIndex OBJECT-TYPE
        SYNTAX  INTEGER (1..4)
        ACCESS  read-only
        STATUS  mandatory
        DESCRIPTION
                "The queue number."
        ::= { configCommonIPortQueueEntry 1 }

configCommonIPortEfciTaggingAdminStatus OBJECT-TYPE
        SYNTAX  INTEGER { up(1), down(2) }
        ACCESS  read-write
        STATUS  mandatory
        DESCRIPTION
                "Enables or disables Explicit Forward Congestion
                Indication (EFCI) on a queue."
        ::= { configCommonIPortQueueEntry 2 }

configCommonIPortClpDiscardAdminStatus OBJECT-TYPE
        SYNTAX  INTEGER { up(1), down(2) }
        ACCESS  read-write
        STATUS  mandatory
        DESCRIPTION
                "Enables or disables discarding of CLP=1 cells on a
                queue."
        ::= { configCommonIPortQueueEntry 3 }

configCommonIPortEfciTaggingThreshold OBJECT-TYPE
        SYNTAX  INTEGER { oneEighth(1),
                          oneFourth(2),
                          oneHalf(3) }
        ACCESS  read-write
        STATUS  mandatory
        DESCRIPTION
                "The queue length threshold beyond which cells in the
                queue are tagged with EFCI. The threshold is given as
                a fraction of the maximum queue length."
        ::= { configCommonIPortQueueEntry 4 }

configCommonIPortClpDiscardThreshold OBJECT-TYPE
        SYNTAX  INTEGER { oneEighth(1),
                          oneFourth(2),
                          oneHalf(3) }
        ACCESS  read-write
        STATUS  mandatory
        DESCRIPTION
                "The queue length threshold beyond which CLP=1 cells
                are dropped rather than added to the queue. The
                threshold is given as a fraction of the maximum queue
                length."
        ::= { configCommonIPortQueueEntry 5 }

configCommonIPortQueueSize OBJECT-TYPE
        SYNTAX  INTEGER
        ACCESS  read-write
        STATUS  mandatory
        DESCRIPTION
                "The maximum queue size. This must be an number of the
                form 255+256*N, where N is an integer."
        ::= { configCommonIPortQueueEntry 6 }

configCommonIPortLogClr OBJECT-TYPE
        SYNTAX  INTEGER
        ACCESS  read-write
        STATUS  mandatory
        DESCRIPTION
                "The worst expected Cell Loss Ratio for this queue.
                The number is expressed as minus the base 10 logarithm
                of the Cell Loss Ratio."
        ::= { configCommonIPortQueueEntry 7 }

configCommonIPortCdv OBJECT-TYPE
        SYNTAX  INTEGER
        ACCESS  read-write
        STATUS  mandatory
        DESCRIPTION
                "The worst expected Cell Delay Variation (in
                microseconds) for this queue."
        ::= { configCommonIPortQueueEntry 8 }


-- Per priority buffer configuration

-- These objects configure the maximum cell buffer allocation per
-- queue priority

configPriorityBufferTable OBJECT-TYPE
        SYNTAX  SEQUENCE OF ConfigPriorityBufferEntry
        ACCESS  not-accessible
        STATUS  mandatory
        DESCRIPTION
                "This table contains the maximum total number of cells
                buffers that may be allocated to a particular queue
                priority."
        ::= { configPriorityBuffer 1 }

configPriorityBufferEntry OBJECT-TYPE
        SYNTAX  ConfigPriorityBufferEntry
        ACCESS  not-accessible
        STATUS  mandatory
        DESCRIPTION 
                "Each row in this table describes one queue priority."
        INDEX   { configPriorityBufferIndex }
        ::= { configPriorityBufferTable 1 }

ConfigPriorityBufferEntry ::=
        SEQUENCE {
            configPriorityBufferIndex
                INTEGER,
            configPriorityBufferSize
                INTEGER
        }

configPriorityBufferIndex OBJECT-TYPE
        SYNTAX  INTEGER (1..4)
        ACCESS  read-only
        STATUS  mandatory
        DESCRIPTION
                "The queue priority."
        ::= { configPriorityBufferEntry 1 }

configPriorityBufferSize OBJECT-TYPE
        SYNTAX  INTEGER
        ACCESS  read-write
        STATUS  mandatory
        DESCRIPTION
                "The maximum total cell buffer allocation for this
                queue priority."
        ::= { configPriorityBufferEntry 2 }


-- iPort Configuration Table

-- The entries in configIPortTable and configIPortQueueTable are
-- atomically updated by copying a row in the table to the iPort
-- 'scratch pad', modifying the contents of the scratch pad, and
-- saving the contents of the scratch pad in configIPortTable. This is
-- done in the following manner:
--
-- 1. Store the row indices in configIPortScratchPadSlotIndex and
--    configIPortScratchPadIPortRIndex.
-- 2. Check that configIPortScratchPadScratchPadStatus is 'notReady'.
-- 3. Set configIPortScratchPadScratchPadStatus to 'copy'.
-- 4. Wait for configIPortScratchPadScratchPadStatus to become 'copied'.
-- 5. Check configIPortScratchPadActionStatus.
-- 6. Modify the contents of the configIPortScratchPad... objects.
-- 7. Set configIPortScratchPadScratchPadStatus to 'updateAndGo'.
-- 8. Check configIPortScratchPadActionStatus.

configIPortScratchPadScratchPadStatus OBJECT-TYPE
        SYNTAX  INTEGER { notReady(1),
                          copy(2),
                          copied(3),
                          updateAndGo(4) }
        ACCESS  read-write
        STATUS  mandatory
        DESCRIPTION
                "Controls the copying of data between
                configIPort(Queue)Table and the iPort scratch pad."
        ::= { configIPort 1 }

configIPortScratchPadSlotIndex OBJECT-TYPE
        SYNTAX  INTEGER (1..8)
        ACCESS  read-write
        STATUS  mandatory
        DESCRIPTION
                "Set to the expansion module number in
                configIPort(Queue)Table before the contents of the row
                are copied to the iPort scratch pad."
        ::= { configIPort 2 }

configIPortScratchPadIPortRIndex OBJECT-TYPE
        SYNTAX  INTEGER (1..2)
        ACCESS  read-write
        STATUS  mandatory
        DESCRIPTION
                "Set to the iPort number in configIPort(Queue)Table
                before the contents of the row are copied to the iPort
                scratch pad."
        ::= { configIPort 3 }

configIPortScratchPadIpAddress OBJECT-TYPE
        SYNTAX  IpAddress
        ACCESS  read-only
        STATUS  mandatory
        DESCRIPTION
                "The IP address of the manager that uses the iPort
                scratch pad. Used as a lock."
        ::= { configIPort 4 }

configIPortScratchPadActionStatus OBJECT-TYPE
        SYNTAX  INTEGER { ok(1),
                          failed(2),
                          notPossible(3) }
        ACCESS  read-only
        STATUS  mandatory
        DESCRIPTION
                "The result of an attempt to copy between
                configEPortTable and the scratch pad."
        ::= { configIPort 5 }

configIPortScratchPadUseCommonIPortConfig OBJECT-TYPE
        SYNTAX  INTEGER { yes(1), no(2) }
        ACCESS  read-write
        STATUS  mandatory
        DESCRIPTION
                "A copy of configIPortUseCommonIPortConfig."
        ::= { configIPort 6 }

configIPortScratchPadQueueTable OBJECT-TYPE
        SYNTAX  SEQUENCE OF ConfigIPortScratchPadQueueEntry
        ACCESS  not-accessible
        STATUS  mandatory
        DESCRIPTION
                "A copy of configIPortQueueTable for one iPort."
        ::= { configIPort 7 }

configIPortScratchPadQueueEntry OBJECT-TYPE
        SYNTAX  ConfigIPortScratchPadQueueEntry
        ACCESS  not-accessible
        STATUS  mandatory
        DESCRIPTION
                "Each row in this table describes one queue for one
                iPort."
        INDEX   { configIPortScratchPadQueueQueueIndex }
        ::= { configIPortScratchPadQueueTable 1 }

ConfigIPortScratchPadQueueEntry ::=
        SEQUENCE {
            configIPortScratchPadQueueQueueIndex
                INTEGER,
            configIPortScratchPadQueueEfciTaggingAdminStatus
                INTEGER,
            configIPortScratchPadQueueClpDiscardAdminStatus
                INTEGER,
            configIPortScratchPadQueueEfciTaggingThreshold
                INTEGER,
            configIPortScratchPadQueueClpDiscardThreshold
                INTEGER,
            configIPortScratchPadQueueSize
                INTEGER,
            configIPortScratchPadQueueLogClr
                INTEGER,
            configIPortScratchPadQueueCdv
                INTEGER
        }

configIPortScratchPadQueueQueueIndex OBJECT-TYPE
        SYNTAX  INTEGER (1..4)
        ACCESS  read-only
        STATUS  mandatory
        DESCRIPTION
                "A copy of configIPortQueueSlotIndex."
        ::= { configIPortScratchPadQueueEntry 1 }

configIPortScratchPadQueueEfciTaggingAdminStatus OBJECT-TYPE
        SYNTAX  INTEGER { up(1), down(2) }
        ACCESS  read-write
        STATUS  mandatory
        DESCRIPTION
                "A copy of configIPortQueueEfciTaggingAdminStatus."
        ::= { configIPortScratchPadQueueEntry 2 }

configIPortScratchPadQueueClpDiscardAdminStatus OBJECT-TYPE
        SYNTAX  INTEGER { up(1), down(2) }
        ACCESS  read-write
        STATUS  mandatory
        DESCRIPTION
                "A copy of configIPortQueueClpDiscardAdminStatus."
        ::= { configIPortScratchPadQueueEntry 3 }

configIPortScratchPadQueueEfciTaggingThreshold OBJECT-TYPE
        SYNTAX  INTEGER { oneEighth(1),
                          oneFourth(2),
                          oneHalf(3) }
        ACCESS  read-write
        STATUS  mandatory
        DESCRIPTION
                "A copy of configIPortQueueEfciTaggingThreshold."
        ::= { configIPortScratchPadQueueEntry 4 }

configIPortScratchPadQueueClpDiscardThreshold OBJECT-TYPE
        SYNTAX  INTEGER { oneEighth(1),
                          oneFourth(2),
                          oneHalf(3) }
        ACCESS  read-write
        STATUS  mandatory
        DESCRIPTION
                "A copy of configIPortQueueClpDiscardThreshold."
        ::= { configIPortScratchPadQueueEntry 5 }

configIPortScratchPadQueueSize OBJECT-TYPE
        SYNTAX  INTEGER
        ACCESS  read-write
        STATUS  mandatory
        DESCRIPTION
                "A copy of configIPortQueueSize."
        ::= { configIPortScratchPadQueueEntry 6 }

configIPortScratchPadQueueLogClr OBJECT-TYPE
        SYNTAX  INTEGER
        ACCESS  read-write
        STATUS  mandatory
        DESCRIPTION
                "A copy of configIPortQueueLogClr."
        ::= { configIPortScratchPadQueueEntry 7 }

configIPortScratchPadQueueCdv OBJECT-TYPE
        SYNTAX  INTEGER
        ACCESS  read-write
        STATUS  mandatory
        DESCRIPTION
                "A copy of configIPortQueueCdv."
        ::= { configIPortScratchPadQueueEntry 8 }



configIPortTable OBJECT-TYPE
        SYNTAX  SEQUENCE OF ConfigIPortEntry
        ACCESS  not-accessible
        STATUS  mandatory
        DESCRIPTION
                "This table contains configuration for each Core
                Access Point (iPort) in the switch. The table may be
                modified through the iPort scratch pad."
        ::= { configIPort 8 }

configIPortEntry OBJECT-TYPE
        SYNTAX  ConfigIPortEntry
        ACCESS  not-accessible
        STATUS  mandatory
        DESCRIPTION
                "Each row in this table describes one Core Access Point
                (iPort)."
        INDEX   { configIPortSlotIndex, configIPortRIndex }
        ::= { configIPortTable 1 }

ConfigIPortEntry ::=
        SEQUENCE {
            configIPortSlotIndex
                INTEGER,
            configIPortRIndex
                INTEGER,
            configIPortUseCommonIPortConfig
                INTEGER
        }

configIPortSlotIndex OBJECT-TYPE
        SYNTAX  INTEGER (1..8)
        ACCESS  read-only
        STATUS  mandatory
        DESCRIPTION
                "The number of the expansion module to which the iPort
                is connected."
        ::= { configIPortEntry 1 }

configIPortRIndex OBJECT-TYPE
        SYNTAX  INTEGER (1..2)
        ACCESS  read-only
        STATUS  mandatory
        DESCRIPTION
                "The number of the iPort within the expansion module."
        ::= { configIPortEntry 2 }

configIPortUseCommonIPortConfig OBJECT-TYPE
        SYNTAX  INTEGER { yes(1), no(2) }
        ACCESS  read-only
        STATUS  mandatory
        DESCRIPTION
                "Indicates if this iPort should use the common iPort
                configuration (found in the configCommonIPort MIB
                subtree) or its own configuration."
        ::= { configIPortEntry 3 }


configIPortQueueTable OBJECT-TYPE
        SYNTAX  SEQUENCE OF ConfigIPortQueueEntry
        ACCESS  not-accessible
        STATUS  mandatory
        DESCRIPTION
                "This table contains configuration for each queue. The
                table may be modified through the iPort scratch pad."
        ::= { configIPort 9 }

configIPortQueueEntry OBJECT-TYPE
        SYNTAX  ConfigIPortQueueEntry
        ACCESS  not-accessible
        STATUS  mandatory
        DESCRIPTION
                "Each row in this table describes one queue."
        INDEX   { configIPortQueueSlotIndex,
                  configIPortQueueRIndex,
                  configIPortQueueQueueIndex }
        ::= { configIPortQueueTable 1 }

ConfigIPortQueueEntry ::=
        SEQUENCE {
            configIPortQueueSlotIndex
                INTEGER,
            configIPortQueueRIndex
                INTEGER,
            configIPortQueueQueueIndex
                INTEGER,
            configIPortQueueEfciTaggingAdminStatus
                INTEGER,
            configIPortQueueClpDiscardAdminStatus
                INTEGER,
            configIPortQueueEfciTaggingThreshold
                INTEGER,
            configIPortQueueClpDiscardThreshold
                INTEGER,
            configIPortQueueSize
                INTEGER,
            configIPortQueueLogClr
                INTEGER,
            configIPortQueueCdv
                INTEGER
        }

configIPortQueueSlotIndex OBJECT-TYPE
        SYNTAX  INTEGER (1..8)
        ACCESS  read-only
        STATUS  mandatory
        DESCRIPTION
                "The number of the expansion module to which the iPort
                for this queue is connected."
        ::= { configIPortQueueEntry 1 }

configIPortQueueRIndex OBJECT-TYPE
        SYNTAX  INTEGER (1..2)
        ACCESS  read-only
        STATUS  mandatory
        DESCRIPTION
                "The number of the iPort within the expansion module."
        ::= { configIPortQueueEntry 2 }

configIPortQueueQueueIndex OBJECT-TYPE
        SYNTAX  INTEGER (1..4)
        ACCESS  read-only
        STATUS  mandatory
        DESCRIPTION
                "The queue priority."
        ::= { configIPortQueueEntry 3 }

configIPortQueueEfciTaggingAdminStatus OBJECT-TYPE
        SYNTAX  INTEGER { up(1), down(2) }
        ACCESS  read-only
        STATUS  mandatory
        DESCRIPTION
                "Enables or disables Explicit Forward Congestion
                Indication (EFCI) on this queue."
        ::= { configIPortQueueEntry 4 }

configIPortQueueClpDiscardAdminStatus OBJECT-TYPE
        SYNTAX  INTEGER { up(1), down(2) }
        ACCESS  read-only
        STATUS  mandatory
        DESCRIPTION
                "Enables or disables discarding of CLP=1 cells on this
                queue."
        ::= { configIPortQueueEntry 5 }

configIPortQueueEfciTaggingThreshold OBJECT-TYPE
        SYNTAX  INTEGER { oneEighth(1),
                          oneFourth(2),
                          oneHalf(3) }
        ACCESS  read-only
        STATUS  mandatory
        DESCRIPTION
                "The queue length threshold beyond which cells in the
                queue are tagged with EFCI. The threshold is given as
                a fraction of the maximum queue length."
        ::= { configIPortQueueEntry 6 }

configIPortQueueClpDiscardThreshold OBJECT-TYPE
        SYNTAX  INTEGER { oneEighth(1),
                          oneFourth(2),
                          oneHalf(3) }
        ACCESS  read-only
        STATUS  mandatory
        DESCRIPTION
                "The queue length threshold beyond which CLP=1 cells
                are dropped rather than added to the queue. The
                threshold is given as a fraction of the maximum queue
                length."
        ::= { configIPortQueueEntry 7 }

configIPortQueueSize OBJECT-TYPE
        SYNTAX  INTEGER
        ACCESS  read-only
        STATUS  mandatory
        DESCRIPTION
                "The maximum queue size. This must be an number of the
                form 255+256*N, where N is an integer."
        ::= { configIPortQueueEntry 8 }

configIPortQueueLogClr OBJECT-TYPE
        SYNTAX  INTEGER
        ACCESS  read-write
        STATUS  mandatory
        DESCRIPTION
                "The worst expected Cell Loss Ratio for this queue.
                The number is expressed as minus the base 10 logarithm
                of the Cell Loss Ratio."
        ::= { configIPortQueueEntry 9 }

configIPortQueueCdv OBJECT-TYPE
        SYNTAX  INTEGER
        ACCESS  read-write
        STATUS  mandatory
        DESCRIPTION
                "The worst expected Cell Delay Variation (in
                microseconds) for this queue."
        ::= { configIPortQueueEntry 10 }



-- PVP and PVC Setup Tables

-- These tables can be used to create PVPs and PVCs. The relevant
-- traffic descriptor must be created before an entry is added to
-- these tables.

pvpSetupTableNextIndex OBJECT-TYPE
        SYNTAX  INTEGER
        ACCESS  read-only
        STATUS  mandatory
        DESCRIPTION
                "The next unused row in pvpSetupTable."
        ::= { configPvpPvc 1 }

pvpSetupTable OBJECT-TYPE
        SYNTAX  SEQUENCE OF PvpSetupEntry
        ACCESS  not-accessible
        STATUS  mandatory
        DESCRIPTION
                "This table contains all Permanent Virtual Paths
                (PVPs) in the switch."
        ::= { configPvpPvc 2 }

pvpSetupEntry OBJECT-TYPE
        SYNTAX  PvpSetupEntry
        ACCESS  not-accessible
        STATUS  mandatory
        DESCRIPTION
                "Each row in this table describes one PVP. PVPs
                typically connect two ATM ports. The numerically
                lowest of these is called the 'low' port, and the
                numerically highest is called the 'high' port."
        INDEX   { pvpSetupIndex }
        ::= { pvpSetupTable 1 }

PvpSetupEntry ::=
        SEQUENCE {
            pvpSetupIndex
                INTEGER,
            pvpSetupApplication
                INTEGER,
            pvpSetupLowEPortIndex
                INTEGER,
            pvpSetupLowVpi
                INTEGER,
            pvpSetupHighEPortIndex
                INTEGER,
            pvpSetupHighVpi
                INTEGER,
            pvpSetupVpCrossConnectIndex
                INTEGER,
            pvpSetupL2HTrafficDescriptorIndex
                INTEGER,
            pvpSetupH2LTrafficDescriptorIndex
                INTEGER,
            pvpSetupRowStatus
                INTEGER
        }

pvpSetupIndex OBJECT-TYPE
        SYNTAX  INTEGER
        ACCESS  read-only
        STATUS  mandatory
        DESCRIPTION
                "An arbitrary integer used to differentiate multiple
                rows in the table."
        ::= { pvpSetupEntry 1 }

pvpSetupApplication OBJECT-TYPE
        SYNTAX  INTEGER { transitVp(1),
                          softPvpOriginatorVpl(2) }
        ACCESS  read-write
        STATUS  mandatory
        DESCRIPTION
                "The PVP type. The value 'transitVp' indicates a PVP
                that passes through the switch and has high and low
                end configuration. The value 'softPvpOriginatorVpl'
                indicates a PVP that terminates in the switch itself
                and only low end configuration is present."
        ::= { pvpSetupEntry 2 }

pvpSetupLowEPortIndex OBJECT-TYPE
        SYNTAX  INTEGER
        ACCESS  read-write
        STATUS  mandatory
        DESCRIPTION
                "The ifIndex of the low port connected to this PVP."
        ::= { pvpSetupEntry 3 }

pvpSetupLowVpi OBJECT-TYPE
        SYNTAX  INTEGER
        ACCESS  read-write
        STATUS  mandatory
        DESCRIPTION
                "The VPI used at the low end of the PVP."
        ::= { pvpSetupEntry 4 }

pvpSetupHighEPortIndex OBJECT-TYPE
        SYNTAX  INTEGER
        ACCESS  read-write
        STATUS  mandatory
        DESCRIPTION
                "The ifIndex of the high port connected to this PVP."
        ::= { pvpSetupEntry 5 }

pvpSetupHighVpi OBJECT-TYPE
        SYNTAX  INTEGER
        ACCESS  read-write
        STATUS  mandatory
        DESCRIPTION
                "The VPI used at the high end of the PVP."
        ::= { pvpSetupEntry 6 }

pvpSetupVpCrossConnectIndex OBJECT-TYPE
        SYNTAX  INTEGER
        ACCESS  read-only
        STATUS  mandatory
        DESCRIPTION
                "After the PVP has been created, this is the index
                into the atmVpCrossConnectTable in the ATM MIB."
        ::= { pvpSetupEntry 7 }

pvpSetupL2HTrafficDescriptorIndex OBJECT-TYPE
        SYNTAX  INTEGER
        ACCESS  read-write
        STATUS  mandatory
        DESCRIPTION
                "The index into the trafficDescriptorTable for the
                traffic descriptor used in the direction low-to-high."
        ::= { pvpSetupEntry 8 }

pvpSetupH2LTrafficDescriptorIndex OBJECT-TYPE
        SYNTAX  INTEGER
        ACCESS  read-write
        STATUS  mandatory
        DESCRIPTION
                "The index into the trafficDescriptorTable for the
                traffic descriptor used in the direction high-to-low."
        ::= { pvpSetupEntry 9 }

pvpSetupRowStatus OBJECT-TYPE
        SYNTAX  INTEGER { active(1),
                          notInService(2),
                          notReady(3),
                          createAndGo(4),
                          createAndWait(5),
                          destroy(6) }
        ACCESS  read-write
        STATUS  mandatory
        DESCRIPTION
                "Used to control creation and deletion of new rows in
                the table."
        ::= { pvpSetupEntry 10 }


pvcSetupTableNextIndex OBJECT-TYPE
        SYNTAX  INTEGER
        ACCESS  read-only
        STATUS  mandatory
        DESCRIPTION
                "The next unused row in pvcSetupTable."
        ::= { configPvpPvc 3 }


pvcSetupTable OBJECT-TYPE
        SYNTAX  SEQUENCE OF PvcSetupEntry
        ACCESS  not-accessible
        STATUS  mandatory
        DESCRIPTION
                "This table contains all Permanent Virtual Channels
                (PVCs) in the switch."
        ::= { configPvpPvc 4 }

pvcSetupEntry OBJECT-TYPE
        SYNTAX  PvcSetupEntry
        ACCESS  not-accessible
        STATUS  mandatory
        DESCRIPTION
                "Each row in this table describes one PVC. PVCs
                typically connect two ATM ports. The numerically
                lowest of these is called the 'low' port, and the
                numerically highest is called the 'high' port."
        INDEX   { pvcSetupIndex }
        ::= { pvcSetupTable 1 }

PvcSetupEntry ::=
        SEQUENCE {
            pvcSetupIndex
                INTEGER,
            pvcSetupApplication
                INTEGER,
            pvcSetupLowEPortIndex
                INTEGER,
            pvcSetupLowVpi
                INTEGER,
            pvcSetupLowVci
                INTEGER,
            pvcSetupHighEPortIndex
                INTEGER,
            pvcSetupHighVpi
                INTEGER,
            pvcSetupHighVci
                INTEGER,
            pvcSetupVcCrossConnectIndex
                INTEGER,
            pvcSetupL2HTrafficDescriptorIndex
                INTEGER,
            pvcSetupH2LTrafficDescriptorIndex
                INTEGER,
            pvcSetupRowStatus
                INTEGER
        }

pvcSetupIndex OBJECT-TYPE
        SYNTAX  INTEGER
        ACCESS  read-only
        STATUS  mandatory
        DESCRIPTION
                "An arbitrary integer used to differentiate multiple
                rows in the table."
        ::= { pvcSetupEntry 1 }

pvcSetupApplication OBJECT-TYPE
        SYNTAX  INTEGER { transitVc(1),
                          softPvcOriginatorVcl(2),
                          classicalIpArpSrvVcl(3),
                          lesCntrlDirectVcl(4),
                          busMcastSendVcl(5) }
        ACCESS  read-write
        STATUS  mandatory
        DESCRIPTION
                "The PVC type. The value 'transitVc' indicates a PVC
                that passes through the switch and has high and low
                end configuration. The other values indicate a PVP
                that terminates in the switch itself and only low end
                configuration is present.

                Legal values are:
                   transitVc             A PVC that passes through the
                                         switch.

                   softPvcOriginatorVcl  One end of a soft PVC.

                   classicalIpArpSrvVcl  The PVC connects the
                                         classical IP ARP server to
                                         the specified ATM port.

                   lesCntrlDirectVcl     The PVC connects the LAN
                                         Emulation Server (LES) to the
                                         specified ATM port.

                   busMcastSendVcl       The PVC connects the
                                         Broadcast and Unknown Server
                                         (BUS) to the specified ATM port."
        ::= { pvcSetupEntry 2 }

pvcSetupLowEPortIndex OBJECT-TYPE
        SYNTAX  INTEGER
        ACCESS  read-write
        STATUS  mandatory
        DESCRIPTION
                "The ifIndex of the low port connected to this PVC."
        ::= { pvcSetupEntry 3 }

pvcSetupLowVpi OBJECT-TYPE
        SYNTAX  INTEGER
        ACCESS  read-write
        STATUS  mandatory
        DESCRIPTION
                "The VPI used at the low end of the PVC."
        ::= { pvcSetupEntry 4 }

pvcSetupLowVci OBJECT-TYPE
        SYNTAX  INTEGER
        ACCESS  read-write
        STATUS  mandatory
        DESCRIPTION
                "The VCI used at the low end of the PVC."
        ::= { pvcSetupEntry 5 }

pvcSetupHighEPortIndex OBJECT-TYPE
        SYNTAX  INTEGER
        ACCESS  read-write
        STATUS  mandatory
        DESCRIPTION
                "The ifIndex of the high port connected to this PVC."
        ::= { pvcSetupEntry 6 }

pvcSetupHighVpi OBJECT-TYPE
        SYNTAX  INTEGER
        ACCESS  read-write
        STATUS  mandatory
        DESCRIPTION
                "The VPI used at the high end of the PVC."
        ::= { pvcSetupEntry 7 }

pvcSetupHighVci OBJECT-TYPE
        SYNTAX  INTEGER
        ACCESS  read-write
        STATUS  mandatory
        DESCRIPTION
                "The VCI used at the high end of the PVC."
        ::= { pvcSetupEntry 8 }

pvcSetupVcCrossConnectIndex OBJECT-TYPE
        SYNTAX  INTEGER
        ACCESS  read-only
        STATUS  mandatory
        DESCRIPTION
                "After the PVC has been created, this is the index
                into the atmVcCrossConnectTable in the ATM MIB."
        ::= { pvcSetupEntry 9 }

pvcSetupL2HTrafficDescriptorIndex OBJECT-TYPE
        SYNTAX  INTEGER
        ACCESS  read-write
        STATUS  mandatory
        DESCRIPTION
                "The index into the trafficDescriptorTable for the
                traffic descriptor used in the direction low-to-high."
        ::= { pvcSetupEntry 10 }

pvcSetupH2LTrafficDescriptorIndex OBJECT-TYPE
        SYNTAX  INTEGER
        ACCESS  read-write
        STATUS  mandatory
        DESCRIPTION
                "The index into the trafficDescriptorTable for the
                traffic descriptor used in the direction high-to-low."
        ::= { pvcSetupEntry 11 }

pvcSetupRowStatus OBJECT-TYPE
        SYNTAX  INTEGER { active(1),
                          notInService(2),
                          notReady(3),
                          createAndGo(4),
                          createAndWait(5),
                          destroy(6) }
        ACCESS  read-write
        STATUS  mandatory
        DESCRIPTION
                "Used to control creation and deletion of new rows in
                the table."
        ::= { pvcSetupEntry 12 }


-- SVP and SVC Setup Tables

-- These tables can be used to create Soft VPs and Soft VCs. The
-- relevant traffic descriptor must be created before an entry is
-- added to these tables.
-- SVPs and SVCs are similar to PVPs and PVCs with the following
-- exceptions:
-- PVPs may connect two ATM ports, SVPs connect an ATM port to a
-- station with a given ATM address (using signalling).
-- SVPs may connect the switch itself to a station at an ATM port,
-- SVCs connect the switch to a station with a given ATM address
-- (using signalling).


svpSetupTableNextIndex OBJECT-TYPE
        SYNTAX  INTEGER
        ACCESS  read-only
        STATUS  mandatory
        DESCRIPTION
                "The next unused row in svpSetupTable."
        ::= { configSvpSvc 1 }

svpSetupTable OBJECT-TYPE
        SYNTAX  SEQUENCE OF SvpSetupEntry
        ACCESS  not-accessible
        STATUS  mandatory
        DESCRIPTION
                "This table contains all Soft Virtual Paths
                (SVPs) in the switch."
        ::= { configSvpSvc 2 }

svpSetupEntry OBJECT-TYPE
        SYNTAX  SvpSetupEntry
        ACCESS  not-accessible
        STATUS  mandatory
        DESCRIPTION
                "Each row in this table describes one SVP."
        INDEX   { svpSetupIndex }
        ::= { svpSetupTable 1 }

SvpSetupEntry ::=
        SEQUENCE {
            svpSetupIndex
                INTEGER,
            svpSetupApplication
                INTEGER,
            svpSetupEPortIndex
                INTEGER,
            svpSetupPreferredVpi
                INTEGER,
            svpSetupTermAtmAddr
                AtmAddress,
            svpSetupVpCrossConnectIndex
                INTEGER,
            svpSetupTxTrafficDescriptorIndex
                INTEGER,
            svpSetupRxTrafficDescriptorIndex
                INTEGER,
            svpSetupRowStatus
                INTEGER
        }

svpSetupIndex OBJECT-TYPE
        SYNTAX  INTEGER
        ACCESS  read-only
        STATUS  mandatory
        DESCRIPTION
                "An arbitrary integer used to differentiate multiple
                rows in the table."
        ::= { svpSetupEntry 1 }

svpSetupApplication OBJECT-TYPE
        SYNTAX  INTEGER { tunnel(1) }
        ACCESS  read-only
        STATUS  mandatory
        DESCRIPTION
                "The SVP type. Only one type (tunnel) is currently
                available."
        ::= { svpSetupEntry 2 }

svpSetupEPortIndex OBJECT-TYPE
        SYNTAX  INTEGER
        ACCESS  read-write
        STATUS  mandatory
        DESCRIPTION
                "The ifIndex of the ATM port connected to this SVP."
        ::= { svpSetupEntry 3 }

svpSetupPreferredVpi OBJECT-TYPE
        SYNTAX  INTEGER
        ACCESS  read-write
        STATUS  mandatory
        DESCRIPTION
                "The preferred VPI number to use on the ATM port given
                in svpSetupEPortIndex."
        ::= { svpSetupEntry 4 }

svpSetupTermAtmAddr OBJECT-TYPE
        SYNTAX  AtmAddress
        ACCESS  read-write
        STATUS  mandatory
        DESCRIPTION
                "The ATM address to which the SVP should be connected."
        ::= { svpSetupEntry 5 }

svpSetupVpCrossConnectIndex OBJECT-TYPE
        SYNTAX  INTEGER
        ACCESS  read-only
        STATUS  mandatory
        DESCRIPTION
                "After the SVP has been created, this is the index
                into the atmVpCrossConnectTable in the ATM MIB."
        ::= { svpSetupEntry 6 }

svpSetupTxTrafficDescriptorIndex OBJECT-TYPE
        SYNTAX  INTEGER
        ACCESS  read-write
        STATUS  mandatory
        DESCRIPTION
                "The index into the trafficDescriptorTable for the
                traffic descriptor used in the direction
                svpSetupEPortIndex-to-svpSetupTermAtmAddr."
        ::= { svpSetupEntry 7 }

svpSetupRxTrafficDescriptorIndex OBJECT-TYPE
        SYNTAX  INTEGER
        ACCESS  read-write
        STATUS  mandatory
        DESCRIPTION
                "The index into the trafficDescriptorTable for the
                traffic descriptor used in the direction
                svpSetupTermAtmAddr-to-svpSetupEPortIndex."
        ::= { svpSetupEntry 8 }

svpSetupRowStatus OBJECT-TYPE
        SYNTAX  INTEGER { active(1),
                          notInService(2),
                          notReady(3),
                          createAndGo(4),
                          createAndWait(5),
                          destroy(6) }
        ACCESS  read-write
        STATUS  mandatory
        DESCRIPTION
                "Used to control creation and deletion of new rows in
                the table."
        ::= { svpSetupEntry 9 }


svcSetupTableNextIndex OBJECT-TYPE
        SYNTAX  INTEGER
        ACCESS  read-only
        STATUS  mandatory
        DESCRIPTION
                "The next unused row in svcSetupTable."
        ::= { configSvpSvc 3 }

svcSetupTable OBJECT-TYPE
        SYNTAX  SEQUENCE OF SvcSetupEntry
        ACCESS  not-accessible
        STATUS  mandatory
        DESCRIPTION
                "This table contains all Soft Virtual Channels
                (SVCs) in the switch."
        ::= { configSvpSvc 4 }

svcSetupEntry OBJECT-TYPE
        SYNTAX  SvcSetupEntry
        ACCESS  not-accessible
        STATUS  mandatory
        DESCRIPTION
                "Each row in this table describes one SVC."
        INDEX   { svcSetupIndex }
        ::= { svcSetupTable 1 }

SvcSetupEntry ::=
        SEQUENCE {
            svcSetupIndex
                INTEGER,
            svcSetupApplication
                INTEGER,
            svcSetupTermAtmAddr
                AtmAddress,
            svcSetupVcCrossConnectIndex
                INTEGER,
            svcSetupTxTrafficDescriptorIndex
                INTEGER,
            svcSetupRxTrafficDescriptorIndex
                INTEGER,
            svcSetupRowStatus
                INTEGER
        }

svcSetupIndex OBJECT-TYPE
        SYNTAX  INTEGER
        ACCESS  read-only
        STATUS  mandatory
        DESCRIPTION
                "An arbitrary integer used to differentiate multiple
                rows in the table."
        ::= { svcSetupEntry 1 }

svcSetupApplication OBJECT-TYPE
        SYNTAX  INTEGER { classicalIpArpSrv(1),
                          lecsConfigDirectSvc(2),
                          lesCntrlDirectSvc(3),
                          busMcastSendSvc(4) }
        ACCESS  read-only
        STATUS  mandatory
        DESCRIPTION
                "The SVC type. The following values exist:
                   classicalIpArpSrv     The SVC connects the
                                         classical IP ARP server with
                                         the specified ATM address.

                   lecsConfigDirectSvc   The SVC connects the LAN
                                         Emulation Configuration
                                         Server (LECS) with the
                                         specified ATM address.

                   lesCntrlDirectSvc     The SVC connects the LAN
                                         Emulation Server (LES) with
                                         the specified ATM address.

                   busMcastSendSvc       The SVC connects the
                                         Broadcast and Unknown Server
                                         (BUS) with the specified ATM address."
        ::= { svcSetupEntry 2 }

svcSetupTermAtmAddr OBJECT-TYPE
        SYNTAX  AtmAddress
        ACCESS  read-write
        STATUS  mandatory
        DESCRIPTION
                "The ATM address to which the SVC should be connected."
        ::= { svcSetupEntry 3 }

svcSetupVcCrossConnectIndex OBJECT-TYPE
        SYNTAX  INTEGER
        ACCESS  read-only
        STATUS  mandatory
        DESCRIPTION
                "After the SVC has been created, this is the index
                into the atmVpCrossConnectTable in the ATM MIB."
        ::= { svcSetupEntry 4 }

svcSetupTxTrafficDescriptorIndex OBJECT-TYPE
        SYNTAX  INTEGER
        ACCESS  read-write
        STATUS  mandatory
        DESCRIPTION
                "The index into the trafficDescriptorTable for the
                traffic descriptor used in the direction
                switch-to-svcSetupTermAtmAddr."
        ::= { svcSetupEntry 5 }

svcSetupRxTrafficDescriptorIndex OBJECT-TYPE
        SYNTAX  INTEGER
        ACCESS  read-write
        STATUS  mandatory
        DESCRIPTION
                "The index into the trafficDescriptorTable for the
                traffic descriptor used in the direction
                svcSetupTermAtmAddr-to-switch."
        ::= { svcSetupEntry 6 }

svcSetupRowStatus OBJECT-TYPE
        SYNTAX  INTEGER { active(1),
                          notInService(2),
                          notReady(3),
                          createAndGo(4),
                          createAndWait(5),
                          destroy(6) }
        ACCESS  read-write
        STATUS  mandatory
        DESCRIPTION
                "Used to control creation and deletion of new rows in
                the table."
        ::= { svcSetupEntry 7 }


-- Signalling and SSCOP Configuration

configCommonSignallingMaxTunnels OBJECT-TYPE
        SYNTAX  INTEGER (1..16)
        ACCESS  read-write
        STATUS  mandatory
        DESCRIPTION
                "The maximum number of additional signalling and SSCOP
                incarnations needed to service tunnels."
        ::= { configCommonSignalling 1 }

configCommonSignallingMaxSaps OBJECT-TYPE
        SYNTAX  INTEGER (1..511)
        ACCESS  read-write
        STATUS  mandatory
        DESCRIPTION
                "The maximum number of SAPs (logical users) supported
                by the signalling subsystem. This value must be at
                least the number of ATM ports present plus the number
                of virtual ports (for LEC, LES and CLIP) plus the
                number of signalling tunnels."
        ::= { configCommonSignalling 2 }

configCommonSignallingMaxPvcs OBJECT-TYPE
        SYNTAX  INTEGER (1..8192)
        ACCESS  read-write
        STATUS  obsolete
        DESCRIPTION
                "The maximum number of simultaneously active PVCs
                (connections) in the entire switch."
        ::= { configCommonSignalling 3 }

configCommonSignallingMaxSvcs OBJECT-TYPE
        SYNTAX  INTEGER (1..16384)
        ACCESS  read-write
        STATUS  mandatory
        DESCRIPTION
                "The maximum number of simultaneously active SVCs
                (calls/connections) signalling instances in the entire
                switch. Note that each call/connection through the
                switch uses two of these (in and out), so the maximum
                number of SVC calls/connections through the switch is
                half this value. This values encompasses both
                point-to-point SVCs and SVPs, as well as
                point-to-multipoint SVCs (basic call part of pt-to-mpt
                connection)."
        ::= { configCommonSignalling 4 }

configCommonSignallingMaxConManStevs OBJECT-TYPE
        SYNTAX  INTEGER (1..128)
        ACCESS  read-write
        STATUS  obsolete
        DESCRIPTION
                "The maximum number of Connection Manager state-event
                machines, i.e. the maximum number of SVC+PVC
                calls/connections being processed simultaneously."
        ::= { configCommonSignalling 5 }

configCommonSignallingMaxSigProtStevs OBJECT-TYPE
        SYNTAX  INTEGER (1..128)
        ACCESS  read-write
        STATUS  mandatory
        DESCRIPTION
                "The maximum number SVC calls/connections setup or
                clear operations that can be processed concurrently in
                the entire switch. Actually twice this number of call
                processors will be allocated - half for incoming and
                half for outgoing operations. Since the switch uses
                two call processors for a 'through-switch' call (one
                incoming and one outgoing), this means that this value
                directly describes the number of simultaneous
                'through-switch' call/connection setup or clear
                operations supported by the switch."
        ::= { configCommonSignalling 6 }

configCommonSignallingT301 OBJECT-TYPE
        SYNTAX  INTEGER (1..65535)
        ACCESS  read-write
        STATUS  mandatory
        DESCRIPTION
                "The maximum time (in seconds) to wait for CONNECT
                after receiving ALERTING. Should be at least 3 minutes
                (180 seconds)."
        ::= { configCommonSignalling 7 }

configCommonSignallingT302 OBJECT-TYPE
        SYNTAX  INTEGER (1..255)
        ACCESS  read-write
        STATUS  mandatory
        DESCRIPTION
                "For N-ISDN interworking. Currently not used."
        ::= { configCommonSignalling 8 }

configCommonSignallingT303 OBJECT-TYPE
        SYNTAX  INTEGER (1..255)
        ACCESS  read-write
        STATUS  mandatory
        DESCRIPTION
                "The maximum time (in seconds) to wait for response to
                SETUP (i.e. CALL-PROCEEDING, ALERTING or CONNECT)."
        ::= { configCommonSignalling 9 }

configCommonSignallingT304 OBJECT-TYPE
        SYNTAX  INTEGER (1..255)
        ACCESS  read-write
        STATUS  mandatory
        DESCRIPTION
                "For N-ISDN interworking. Currently not used."
        ::= { configCommonSignalling 10 }

configCommonSignallingT306 OBJECT-TYPE
        SYNTAX  INTEGER (1..255)
        ACCESS  read-write
        STATUS  mandatory
        DESCRIPTION
                "For N-ISDN interworking. Currently not used."
        ::= { configCommonSignalling 11 }

configCommonSignallingT308 OBJECT-TYPE
        SYNTAX  INTEGER (1..255)
        ACCESS  read-write
        STATUS  mandatory
        DESCRIPTION
                "The maximum time to wait for response to RELEASE."
        ::= { configCommonSignalling 12 }

configCommonSignallingT309 OBJECT-TYPE
        SYNTAX  INTEGER (1..255)
        ACCESS  read-write
        STATUS  mandatory
        DESCRIPTION
                "The maximum time (in seconds) allowing SAAL (SSCOP)
                connection loss. If SSCOP experiences connection loss
                for longer than this time for a signalling connection,
                the signalling instance will clear all its calls:
                active calls, as well as calls under establishment.
                The switch will propagate these call clearings through
                towards the remote endpoint."
        ::= { configCommonSignalling 13 }

configCommonSignallingT310 OBJECT-TYPE
        SYNTAX  INTEGER (1..255)
        ACCESS  read-write
        STATUS  mandatory
        DESCRIPTION
                "The maximum time (in seconds) to wait for response to
                SETUP (i.e. ALERTING or CONNECT) after receiving CALL
                PROCEEDING."
        ::= { configCommonSignalling 14 }

configCommonSignallingT313 OBJECT-TYPE
        SYNTAX  INTEGER (1..255)
        ACCESS  read-write
        STATUS  mandatory
        DESCRIPTION
                "The maximum time (in seconds) to wait for response to
                CONNECT."
        ::= { configCommonSignalling 15 }

configCommonSignallingT316 OBJECT-TYPE
        SYNTAX  INTEGER (1..255)
        ACCESS  read-write
        STATUS  mandatory
        DESCRIPTION
                "The maximum time (in seconds) to wait for response to
                RESTART."
        ::= { configCommonSignalling 16 }

configCommonSignallingT317 OBJECT-TYPE
        SYNTAX  INTEGER (1..255)
        ACCESS  read-write
        STATUS  mandatory
        DESCRIPTION
                "The maximum time (in seconds) to act on RESTART.
                Should be less than configCommonSignallingT316."
        ::= { configCommonSignalling 17 }

configCommonSignallingT322 OBJECT-TYPE
        SYNTAX  INTEGER (1..255)
        ACCESS  read-write
        STATUS  mandatory
        DESCRIPTION
                "The maximum time (in seconds) to wait for response to
                STATUS ENQUIRY."
        ::= { configCommonSignalling 18 }

configCommonSignallingT331 OBJECT-TYPE
        SYNTAX  INTEGER (1..255)
        ACCESS  read-write
        STATUS  mandatory
        DESCRIPTION
                "For Leaf Initiated Join support: The maximum time (in
                seconds) to wait for response to LEAF SETUP REQUEST."
        ::= { configCommonSignalling 19 }

configCommonSignallingT333 OBJECT-TYPE
        SYNTAX  INTEGER (1..255)
        ACCESS  read-write
        STATUS  obsolete
        DESCRIPTION
                "This timer value is no longer used. Was removed from
                final UNI4.0 signalling specification."
        ::= { configCommonSignalling 20 }

configCommonSignallingT397 OBJECT-TYPE
        SYNTAX  INTEGER (1..1000)
        ACCESS  read-write
        STATUS  mandatory
        DESCRIPTION
                "The maximum time (in seconds) to wait for ADD PARTY
                ACK after receiving ALERTING or ADD PARTY ALERTED.
                Should be minimum 3 minutes (180 seconds). Note:
                Should usually be the same as
                configCommonSignallingT301."
        ::= { configCommonSignalling 21 }

configCommonSignallingT398 OBJECT-TYPE
        SYNTAX  INTEGER (1..255)
        ACCESS  read-write
        STATUS  mandatory
        DESCRIPTION
                "For point-to-multipoint support: The maximum time (in
                seconds) to wait for response to DROP PARTY."
        ::= { configCommonSignalling 22 }

configCommonSignallingT399 OBJECT-TYPE
        SYNTAX  INTEGER (1..255)
        ACCESS  read-write
        STATUS  mandatory
        DESCRIPTION
                "For point-to-multipoint support: The maximum time (in
                seconds) to wait for response to ADD PARTY."
        ::= { configCommonSignalling 23 }

configCommonSignallingPtmpMaxLeafs OBJECT-TYPE
        SYNTAX  INTEGER (1..16384)
        ACCESS  read-write
        STATUS  mandatory
        DESCRIPTION
                "The maximum number of simultaneously active
                point-to-multipoint SVC leaf connection signalling
                instances (in the entire switch). Note that each leaf
                connection through the switch uses two of these (in
                and out), so the maximum number of SVC leaf
                connections through the switch is half this value."
        ::= { configCommonSignalling 24 }

configCommonSignallingPtmpMaxLeafOperations OBJECT-TYPE
        SYNTAX  INTEGER (1..128)
        ACCESS  read-write
        STATUS  mandatory
        DESCRIPTION
                "The maximum number of signalling pt-to-mpt SVC leaf
                add or drop operations that can be processed
                concurrently in the entire switch. Actually twice this
                number of leaf processors will be allocated - half for
                incoming and half for outgoing operations. So since
                the switch uses two leaf processors (one incoming and
                one outgoing) to process a 'through-switch' operation,
                this means that this value directly describes the
                number of simultaneous 'through-switch' leaf add or
                drop operations supported by the switch."
        ::= { configCommonSignalling 25 }

configCommonSignallingPtmpMaxLeafsDropByClear OBJECT-TYPE
        SYNTAX  INTEGER (1..255)
        ACCESS  read-write
        STATUS  mandatory
        DESCRIPTION
                "The maximum number of concurrent leaf drop operations
                (for a single pt-to-mpt connection) when initiated by
                call clearing."
        ::= { configCommonSignalling 26 }

configCommonSignallingPtmpMaxP2mpSvcs OBJECT-TYPE
        SYNTAX  INTEGER (1..1024)
        ACCESS  read-write
        STATUS  mandatory
        DESCRIPTION
                "The maximum number of the Signalling SVCs in the
                switch that can provide point-to-multipoint support.
                Note that each pt-to-mpt connection through the switch
                uses two of these (incoming and outgoing), so the
                maximum number of SVCs that can provide pt-to-mpt
                support through the switch is half this value."
        ::= { configCommonSignalling 27 }

configCommonSscopMaxSaps OBJECT-TYPE
        SYNTAX  INTEGER
        ACCESS  read-write
        STATUS  obsolete
        DESCRIPTION
                "The maximum number of SSCOP SAPs. This value is not
                used."
        ::= { configCommonSignalling 28 }

configCommonSscopMaxLinks OBJECT-TYPE
        SYNTAX  INTEGER
        ACCESS  read-write
        STATUS  obsolete
        DESCRIPTION
                "The maximum number of SSCOP Links. This value is not
                used."
        ::= { configCommonSignalling 29 }

configCommonSscopMaxRcvWinSize OBJECT-TYPE
        SYNTAX  INTEGER (1..16777215)
        ACCESS  read-write
        STATUS  mandatory
        DESCRIPTION
                "The maximum SSCOP protocol receive window size.
                Q.2110, app.IV, defines calculation of window size."
        ::= { configCommonSignalling 30 }

configCommonSscopMaxCc OBJECT-TYPE
        SYNTAX  INTEGER (1..255)
        ACCESS  read-write
        STATUS  mandatory
        DESCRIPTION
                "The maximum SSCOP Connection Control state variable
                value (the maximum transmissions of a BGN, END, ER or
                RS PDU)."
        ::= { configCommonSignalling 31 }

configCommonSscopMaxPd OBJECT-TYPE
        SYNTAX  INTEGER (1..255)
        ACCESS  read-write
        STATUS  mandatory
        DESCRIPTION
                "The maximum SSCOP Poll Data state variable value (the
                maximum transmissions of between polls)."
        ::= { configCommonSignalling 32 }

configCommonSscopMaxStat OBJECT-TYPE
        SYNTAX  INTEGER (3..1023)
        ACCESS  read-write
        STATUS  mandatory
        DESCRIPTION
                "The maximum number of list elements placed in a SSCOP
                STAT PDU."
        ::= { configCommonSignalling 33 }

configCommonSscopTimerPoll OBJECT-TYPE
        SYNTAX  INTEGER (1..10000)
        ACCESS  read-write
        STATUS  mandatory
        DESCRIPTION
                "SSCOP Timer-POLL (in milliseconds). This defines the
                maximum interval between SSCOP sending POLLs, while it
                has unacknowledged SD PDU transmits. Ensures that peer
                receiver is polled often enough to return its status.
                Optimized to maintain optimum flow.
                Timer-NO-RESPONSE must be greater than timer-POLL."
        ::= { configCommonSignalling 34 }

configCommonSscopTimerNoResponse OBJECT-TYPE
        SYNTAX  INTEGER (1..255)
        ACCESS  read-write
        STATUS  mandatory
        DESCRIPTION
                "SSCOP Timer-NO-RESPONSE (in seconds). The time
                interval during which at least one STAT PDU must be
                received, when there are unacknowledged SD PDU
                transmits. Must be at least Timer-KEEP-ALIVE +
                round-trip delay.
                Timer-NO-RESPONSE must be greater than timer-POLL."
        ::= { configCommonSignalling 35 }

configCommonSscopTimerKeepAlive OBJECT-TYPE
        SYNTAX  INTEGER (1..255)
        ACCESS  read-write
        STATUS  mandatory
        DESCRIPTION
                "SSCOP Timer-KEEP-ALIVE (in seconds). Used when there
                are no unacknowledged SD PDU transmits. Defines the
                time period after sending a POLL, during which a STAT
                response must have been received. Generally, this
                value is greater than both Timer-POLL and round-trip
                delay."
        ::= { configCommonSignalling 36 }

configCommonSscopTimerIdle OBJECT-TYPE
        SYNTAX  INTEGER (1..255)
        ACCESS  read-write
        STATUS  mandatory
        DESCRIPTION
                "SSCOP Timer-IDLE (in seconds). Defines the
                idle-period during which no POLL PDUs are sent, when
                there are no unacknowledged SD PDU transmits. May be
                much greater than Timer-KEEP-ALIVE."
        ::= { configCommonSignalling 37 }

configCommonSscopTimerCc OBJECT-TYPE
        SYNTAX  INTEGER (1..255)
        ACCESS  read-write
        STATUS  mandatory
        DESCRIPTION
                "SSCOP Timer-CC (in units of 100 milliseconds).
                Defines the maximum time to wait for response, during
                outgoing link establish, release, resynch and
                recovery. Should be somewhat greater than a round-trip
                delay."
        ::= { configCommonSignalling 38 }

configCommonSscopMaxSduSize OBJECT-TYPE
        SYNTAX  INTEGER (512..16384)
        ACCESS  read-write
        STATUS  mandatory
        DESCRIPTION
                "The maximum SSCOP SDU size (SAAL Service Data Unit
                size) in bytes."
        ::= { configCommonSignalling 39 }

configCommonSscopMaxUuSize OBJECT-TYPE
        SYNTAX  INTEGER (512..16384)
        ACCESS  read-write
        STATUS  mandatory
        DESCRIPTION
                "The maximum SSCOP UU size (User-to-User data size) in
                bytes. Note: This value is currently not needed
                according to Q.2130, and hence not used."
        ::= { configCommonSignalling 40 }


-- IISP Next Hop Routing Table

-- This table is used to configure IISP routing

configNextHopRoutingTableNextIndex OBJECT-TYPE
        SYNTAX  INTEGER
        ACCESS  read-only
        STATUS  mandatory
        DESCRIPTION
                "The next unused row in configNextHopRoutingTable."
        ::= { configIisp 1 }

configNextHopRoutingTable OBJECT-TYPE
        SYNTAX  SEQUENCE OF ConfigNextHopRoutingEntry
        ACCESS  not-accessible
        STATUS  mandatory
        DESCRIPTION
                "This table contains the IISP routing information."
        ::= { configIisp 2 }

configNextHopRoutingEntry OBJECT-TYPE
        SYNTAX  ConfigNextHopRoutingEntry
        ACCESS  not-accessible
        STATUS  mandatory
        DESCRIPTION
                "Each row in this table describes the route to one ATM
                address prefix."
        INDEX   { configNextHopRoutingIndex }
        ::= { configNextHopRoutingTable 1 }

ConfigNextHopRoutingEntry ::=
        SEQUENCE {
            configNextHopRoutingIndex
                INTEGER,
            configNextHopRoutingAtmAddress
                AtmAddress,
            configNextHopRoutingAddressLength
                INTEGER,
            configNextHopRoutingEPort
                INTEGER,
            configNextHopRoutingSignallingType
                INTEGER,
            configNextHopRoutingRowStatus
                INTEGER
        }

configNextHopRoutingIndex OBJECT-TYPE
        SYNTAX  INTEGER
        ACCESS  read-only
        STATUS  mandatory
        DESCRIPTION
                "An arbitrary integer used to differentiate multiple
                rows in the table."
        ::= { configNextHopRoutingEntry 1 }

configNextHopRoutingAtmAddress OBJECT-TYPE
        SYNTAX  AtmAddress
        ACCESS  read-write
        STATUS  mandatory
        DESCRIPTION
                "The ATM address or ATM summary address to which this
                row describes a route."
        ::= { configNextHopRoutingEntry 2 }

configNextHopRoutingAddressLength OBJECT-TYPE
        SYNTAX  INTEGER
        ACCESS  read-write
        STATUS  mandatory
        DESCRIPTION
                "The number of valid bits in
                configNextHopRoutingAtmAddress."
        ::= { configNextHopRoutingEntry 3 }

configNextHopRoutingEPort OBJECT-TYPE
        SYNTAX  INTEGER
        ACCESS  read-write
        STATUS  mandatory
        DESCRIPTION
                "The ifIndex of the ATM port that leads to the
                specified ATM address."
        ::= { configNextHopRoutingEntry 4 }

configNextHopRoutingSignallingType OBJECT-TYPE
        SYNTAX  INTEGER { userSide(1), networkSide(2) }
        ACCESS  read-write
        STATUS  obsolete
        DESCRIPTION
                "Not used."
        ::= { configNextHopRoutingEntry 5 }

configNextHopRoutingRowStatus OBJECT-TYPE
        SYNTAX  INTEGER { active(1),
                          notInService(2),
                          notReady(3),
                          createAndGo(4),
                          createAndWait(5),
                          destroy(6) }
        ACCESS  read-write
        STATUS  mandatory
        DESCRIPTION
                "Used to control creation and deletion of new rows in
                the table."
        ::= { configNextHopRoutingEntry 6 }


-- ATM IP ARP Table and IP ARP server enabling

atmIpArpTable OBJECT-TYPE
        SYNTAX  SEQUENCE OF AtmIpArpEntry
        ACCESS  not-accessible
        STATUS  mandatory
        DESCRIPTION
                "This table contains the IP-address-to-ATM-address
                translation table used by the IP ARP server."
        ::= { configIpArp 1 }

atmIpArpEntry OBJECT-TYPE
        SYNTAX  AtmIpArpEntry
        ACCESS  not-accessible
        STATUS  mandatory
        DESCRIPTION
                "Each row in this table describes one IP address."
        INDEX   { atmIpArpServerIndex, atmIpArpIpAddress }
        ::= { atmIpArpTable 1 }

AtmIpArpEntry ::=
        SEQUENCE {
            atmIpArpServerIndex
                INTEGER,
            atmIpArpIpAddress
                IpAddress,
            atmIpArpAtmAddress
                AtmAddress,
            atmIpArpType
                INTEGER
        }

atmIpArpServerIndex OBJECT-TYPE
        SYNTAX  INTEGER
        ACCESS  read-write
        STATUS  mandatory
        DESCRIPTION
                "The index of the IP ARP server that handles this
                row."
        ::= { atmIpArpEntry 1 }

atmIpArpIpAddress OBJECT-TYPE
        SYNTAX  IpAddress
        ACCESS  read-write
        STATUS  mandatory
        DESCRIPTION
                "The IP address that this row translates."
        ::= { atmIpArpEntry 2 }

atmIpArpAtmAddress OBJECT-TYPE
        SYNTAX  AtmAddress
        ACCESS  read-write
        STATUS  mandatory
        DESCRIPTION
                "The ATM address that corresponds to
                atmIpArpIpAddress."
        ::= { atmIpArpEntry 3 }

atmIpArpType OBJECT-TYPE
        SYNTAX  INTEGER { other(1),
                          invalid(2),
                          dynamic(3),
                          static(4) }
        ACCESS  read-write
        STATUS  mandatory
        DESCRIPTION
                "The entry type. 'Dynamic' means created
                automatically, 'static' means created by management."
        ::= { atmIpArpEntry 4 }

configIpArpServerTableNextIndex OBJECT-TYPE
        SYNTAX  INTEGER
        ACCESS  read-only
        STATUS  mandatory
        DESCRIPTION
                "The next unused row in configIpArpServerTable."
        ::= { configIpArp 2 }

configIpArpServerTable OBJECT-TYPE
        SYNTAX  SEQUENCE OF ConfigIpArpServerEntry
        ACCESS  not-accessible
        STATUS  mandatory
        DESCRIPTION
                "This table is used to create and configure the IP ARP
                servers."
        ::= { configIpArp 3 }

configIpArpServerEntry OBJECT-TYPE
        SYNTAX  ConfigIpArpServerEntry
        ACCESS  not-accessible
        STATUS  mandatory
        DESCRIPTION
                "Each row in this table describes one IP ARP server,
                servicing one IP subnet."
        INDEX   { configIpArpServerIndex }
        ::= { configIpArpServerTable 1 }

ConfigIpArpServerEntry ::=
        SEQUENCE {
            configIpArpServerIndex
                INTEGER,
            configIpArpServerAtmAddressSpec
                AtmAddress,
            configIpArpServerAtmAddressMask
                AtmAddress,
            configIpArpServerAtmAddressActual
                AtmAddress,
            configIpArpServerIpSubnetAddress
                IpAddress,
            configIpArpServerIpSubnetMask
                IpAddress,
            configIpArpServerAdminStatus
                INTEGER,
            configIpArpServerOperStatus
                INTEGER,
            configIpArpServerRowStatus
                INTEGER
        }

configIpArpServerIndex OBJECT-TYPE
        SYNTAX  INTEGER
        ACCESS  read-only
        STATUS  mandatory
        DESCRIPTION
                "An arbitrary integer used to differentiate multiple
                rows containing different IP ARP servers."
        ::= { configIpArpServerEntry 1 }

configIpArpServerAtmAddressSpec OBJECT-TYPE
        SYNTAX  AtmAddress
        ACCESS  read-write
        STATUS  mandatory
        DESCRIPTION
                "An ATM Address specified by the network or local
                management that, with the ATM address mask, determines
                a portion of the ATM address that the IP ARP Server
                will use to derive the actual ATM address from the
                network or ILMI. The derived ATM address is specified
                in the object configIpArpServerAtmAddressActual,
                which is used to receive ATM IP ARP requests."
        ::= { configIpArpServerEntry 2 }

configIpArpServerAtmAddressMask OBJECT-TYPE
        SYNTAX  AtmAddress
        ACCESS  read-write
        STATUS  mandatory
        DESCRIPTION
                "The ATM address mask associated with the object
                configIpArpServerAtmAddressSpec. The value of the
                mask is an ATM address with the don't care portion
                set to zero and the valid ATM address portion set
                to one."
        ::= { configIpArpServerEntry 3 }

configIpArpServerAtmAddressActual OBJECT-TYPE
        SYNTAX  AtmAddress
        ACCESS  read-only
        STATUS  mandatory
        DESCRIPTION
                "The resultant ATM address in use by the IP ARP
                Server. This object is a product of the specified
                ATM address, mask, and interaction with the network.
                This object is created by the agent."
        ::= { configIpArpServerEntry 4 }

configIpArpServerIpSubnetAddress OBJECT-TYPE
        SYNTAX  IpAddress
        ACCESS  read-write
        STATUS  mandatory
        DESCRIPTION
                "The address of the IP subnet serviced by this IP ARP
                server."
        ::= { configIpArpServerEntry 5 }

configIpArpServerIpSubnetMask OBJECT-TYPE
        SYNTAX  IpAddress
        ACCESS  read-write
        STATUS  mandatory
        DESCRIPTION
                "The subnet mask of the IP subnet serviced by this IP
                ARP server."
        ::= { configIpArpServerEntry 6 }

configIpArpServerAdminStatus OBJECT-TYPE
        SYNTAX  INTEGER { up(1), down(2) }
        ACCESS  read-write
        STATUS  mandatory
        DESCRIPTION
                "Enables or disable the IP ARP server."
        ::= { configIpArpServerEntry 7 }

configIpArpServerOperStatus OBJECT-TYPE
        SYNTAX  INTEGER { other(1), up(2), down(3) }
        ACCESS  read-only
        STATUS  mandatory
        DESCRIPTION
                "Operational state of this IP ARP Server entry."
        ::= { configIpArpServerEntry 8 }

configIpArpServerRowStatus OBJECT-TYPE
        SYNTAX  INTEGER { active(1),
                          notInService(2),
                          notReady(3),
                          createAndGo(4),
                          createAndWait(5),
                          destroy(6) }
        ACCESS  read-write
        STATUS  mandatory
        DESCRIPTION
                "Used to control creation and deletion of new rows
                in the table."
        ::= { configIpArpServerEntry 9 }


configClipArpServer OBJECT-TYPE
        SYNTAX  AtmAddress
        ACCESS  read-write
        STATUS  mandatory
        DESCRIPTION
                "The ATM address of the IP ARP server used by the CLIP
                client in the switch."
        ::= { configIpArp 4 }

-- QoS Class Table

qosClassTable OBJECT-TYPE
        SYNTAX  SEQUENCE OF QosClassEntry
        ACCESS  not-accessible
        STATUS  mandatory
        DESCRIPTION
                "This table provides the translation between the
                Quality of Service (QoS) classes used in UNI 3.1
                signalling and the corresponding values of the QoS
                parameters. Only classes 1 through 4 can be
                configured."
        ::= { configQosClass 1 }

qosClassEntry OBJECT-TYPE
        SYNTAX  QosClassEntry
        ACCESS  not-accessible
        STATUS  mandatory
        DESCRIPTION
                "Each row in this table describes one QoS class."
        INDEX   { qosClassClass }
        ::= { qosClassTable 1 }

QosClassEntry ::=
        SEQUENCE {
            qosClassClass
                INTEGER,
            qosClassCtd
                INTEGER,
            qosClassCdv
                INTEGER,
            qosClassLogClr
                INTEGER
        }

qosClassClass OBJECT-TYPE
        SYNTAX  INTEGER (1..4)
        ACCESS  read-only
        STATUS  mandatory
        DESCRIPTION
                "The QoS class number."
        ::= { qosClassEntry 1 }

qosClassCtd OBJECT-TYPE
        SYNTAX  INTEGER
        ACCESS  read-write
        STATUS  mandatory
        DESCRIPTION
                "The Cell Transfer Delay (in microseconds) for this
                QoS class."
        ::= { qosClassEntry 2 }

qosClassCdv OBJECT-TYPE
        SYNTAX  INTEGER
        ACCESS  read-write
        STATUS  mandatory
        DESCRIPTION
                "The Cell Delay Variation (in microseconds) for this
                QoS class."
        ::= { qosClassEntry 3 }

qosClassLogClr OBJECT-TYPE
        SYNTAX  INTEGER
        ACCESS  read-write
        STATUS  mandatory
        DESCRIPTION
                "Minus the base 10 logarithm of the Cell Loss Ratio
                for this QoS class."
        ::= { qosClassEntry 4 }


-- Serial line configuration

configSerialObmSlip OBJECT-TYPE
        SYNTAX  INTEGER { none(1),
                          obm(2),
                          slip(3) }
        ACCESS  read-write
        STATUS  mandatory
        DESCRIPTION
                "Controls if the serial line is used for OBM or SLIP."
        ::= { configSerial 1 }

-- Oam section

-- This section contains a copy of a part of the ifMIB defined in RFC 1573
-- and a part of the atmTESTMIB taken from draft rfc <draft-ietf-atommib-test-00.txt>.

ifMIBObjects            OBJECT IDENTIFIER ::= { configOam 1 }
atmTESTMIBObjects       OBJECT IDENTIFIER ::= { configOam 2 }


ifTestTable OBJECT-TYPE
        SYNTAX  SEQUENCE OF IfTestEntry
        ACCESS  not-accessible
        STATUS  mandatory
        DESCRIPTION
                "This table contains one entry per interface.
                It is a copy of the ifTestTable in the ifMIB
                as defined in RFC 1573."
        ::= { ifMIBObjects 3 }

ifTestEntry OBJECT-TYPE
        SYNTAX  IfTestEntry
        ACCESS  not-accessible
        STATUS  mandatory
        DESCRIPTION
                "An entry containing objects for invoking tests on an
                interface."
        INDEX  { ifIndex }
        ::= { ifTestTable 1 }

IfTestEntry ::=
        SEQUENCE {
                ifTestId        INTEGER,
                ifTestStatus    INTEGER,
                ifTestType      OBJECT IDENTIFIER,
                ifTestResult    INTEGER,
                ifTestCode      OBJECT IDENTIFIER,
                ifTestOwner     OCTET STRING (SIZE(0..255))
        }

ifTestId OBJECT-TYPE
--      SYNTAX  TestAndIncr
        SYNTAX  INTEGER (0..2147483647)
        ACCESS  read-write
        STATUS  mandatory
        DESCRIPTION
                "This object identifies the current invocation of the
                interface's test.
		The type of this object is identical to the textual 
		convention TestAndIncr, defined in RFC 1903."
        ::= { ifTestEntry 1 }

ifTestStatus OBJECT-TYPE
        SYNTAX  INTEGER { notInUse(1), inUse(2) }
        ACCESS  read-write
        STATUS  mandatory
        DESCRIPTION
                "This object indicates whether or not some manager
                currently has the necessary 'ownership' required to
                invoke a test on this interface.  A write to this
                object is only successful when it changes its value
                from 'notInUse(1)' to 'inUse(2)'.  After completion of
                a test, the agent resets the value back to
                'notInUse(1)'."
        ::= { ifTestEntry 2 }

ifTestType OBJECT-TYPE
        SYNTAX  OBJECT IDENTIFIER
        ACCESS  read-write
        STATUS  mandatory
        DESCRIPTION
                "A control variable used to start and stop operator-
                initiated interface tests.  Most OBJECT IDENTIFIER
                values assigned to tests are defined elsewhere, in
                association with specific types of interface.
                However, this document assigns a value for a full-
                duplex loopback test, and defines the special meanings
                of the subject identifier:

                        noTest  OBJECT IDENTIFIER ::= { 0 0 }

                When the value noTest is written to this object, no
                action is taken unless a test is in progress, in which
                case the test is aborted.  Writing any other value to
                this object is only valid when no test is currently in
                progress, in which case the indicated test is
                initiated.

                When read, this object always returns the most recent
                value that ifTestType was set to.  If it has not been
                set since the last initialization of the network
                management subsystem on the agent, a value of noTest
                is returned."
        ::= { ifTestEntry 3 }

ifTestResult OBJECT-TYPE
        SYNTAX  INTEGER { none(1),      -- no test yet requested
                        success(2),
                        inProgress(3),
                        notSupported(4),
                        unAbleToRun(5), -- due to state of system
                        aborted(6),
                        failed(7) }

        ACCESS  read-only
        STATUS  mandatory
        DESCRIPTION
                "This object contains the result of the most recently
                requested test, or the value none(1) if no tests have
                been requested since the last reset.  Note that this
                facility provides no provision for saving the results
                of one test when starting another, as could be
                required if used by multiple managers concurrently."
        ::= { ifTestEntry 4 }

ifTestCode OBJECT-TYPE
        SYNTAX  OBJECT IDENTIFIER
        ACCESS  read-only
        STATUS  mandatory
        DESCRIPTION
                "This object contains a code which contains more
                specific information on the test result, for example
                an error-code after a failed test.  Error codes and
                other values this object may take are specific to the
                type of interface and/or test.  The value may have the
                semantics of either the AutonomousType or
                InstancePointer textual conventions as defined in RFC
                1443.  The identifier:

                        testCodeUnknown  OBJECT IDENTIFIER ::= { 0 0 }

                is defined for use if no additional result code is
                available."
        ::= { ifTestEntry 5 }

ifTestOwner OBJECT-TYPE
        SYNTAX  OCTET STRING (SIZE(0..255))
        ACCESS  read-write
        STATUS  mandatory
        DESCRIPTION
                "The entity which currently has the 'ownership'
                required to invoke a test on this interface."
        ::= { ifTestEntry 6 }

atmLoopbackTestGroup    OBJECT IDENTIFIER ::= { atmTESTMIBObjects 1}
atmLoopbackTestTypes    OBJECT IDENTIFIER ::= { atmLoopbackTestGroup 4 }
atmLoopbackVpE2e        OBJECT IDENTIFIER ::= { atmLoopbackTestTypes 1 }
atmLoopbackVcE2e        OBJECT IDENTIFIER ::= { atmLoopbackTestTypes 2 }
atmLoopbackVpSegment    OBJECT IDENTIFIER ::= { atmLoopbackTestTypes 3 }
atmLoopbackVcSegment    OBJECT IDENTIFIER ::= { atmLoopbackTestTypes 4 }


-- Test control section

controlDeleteCode OBJECT-TYPE
        SYNTAX  INTEGER
        ACCESS  write-only
        STATUS  optional
        DESCRIPTION
                "Writing a value of 0x54455354 (i.e. 'TEST') to this
                object causes both installed code blocks to be erased"
        ::= { configTest 1 }

controlDeleteConfig OBJECT-TYPE
        SYNTAX  INTEGER
        ACCESS  write-only
        STATUS  optional
        DESCRIPTION
                "Writing a value of 0x54455354 (i.e. 'TEST') to this
                object causes the configuration flash to be erased"
        ::= { configTest 2 }


-- Status section

-- This section provides status information about the operation of the
-- switch

statusBasicHw           OBJECT IDENTIFIER ::= { crossfireAtmStatus 1 }
statusProcessorModule   OBJECT IDENTIFIER ::= { crossfireAtmStatus 2 }
statusFeatureModule     OBJECT IDENTIFIER ::= { crossfireAtmStatus 3 }
statusXModule           OBJECT IDENTIFIER ::= { crossfireAtmStatus 4 }
-- deleted: statusSar               OBJECT IDENTIFIER ::= { crossfireAtmStatus 5 }
statusEPort             OBJECT IDENTIFIER ::= { crossfireAtmStatus 6 }
statusVpcVcc            OBJECT IDENTIFIER ::= { crossfireAtmStatus 7 }
statusFatalLog          OBJECT IDENTIFIER ::= { crossfireAtmStatus 8 }


-- Basic HW Status

statusHwChassisCurrentXModules OBJECT-TYPE
        SYNTAX  INTEGER (0..8)
        ACCESS  read-only
        STATUS  mandatory
        DESCRIPTION
                "The number of installed expansion modules."
        ::= { statusBasicHw 1 }

statusHwChassisCurrentEPorts OBJECT-TYPE
        SYNTAX  INTEGER (0..96)
        ACCESS  read-only
        STATUS  mandatory
        DESCRIPTION
                "The number of installed ATM ports."
        ::= { statusBasicHw 2 }

statusHwChassisUpsOperState OBJECT-TYPE
        SYNTAX  INTEGER { operational(1),
                          inUse(2),
                          failed(3),
                          notPresent(4) }
        ACCESS  read-only
        STATUS  mandatory
        DESCRIPTION
                "The operational state of the Uninterrupted Power
                Supply (UPS)."
        ::= { statusBasicHw 3 }

statusHwChassisSwitchingSystemSize OBJECT-TYPE
        SYNTAX  INTEGER (16..32)
        ACCESS  read-only
        STATUS  mandatory
        DESCRIPTION
                "The number of Core Access Points in the switch."
        ::= { statusBasicHw 4 }

statusHwChassisCellBufferSize OBJECT-TYPE
        SYNTAX  INTEGER (16..64)
        ACCESS  read-only
        STATUS  mandatory
        DESCRIPTION
                "The size (in K cells) of the switch core cell buffer."
        ::= { statusBasicHw 5 }

statusCurrentTemperatureConditionState OBJECT-TYPE
        SYNTAX  INTEGER { normal(1),
                          highDecreasing(2),
                          normalIncreasing(3),
                          high(4) }
        ACCESS  read-only
        STATUS  mandatory
        DESCRIPTION
                "The current state of the temperature within the
                switch. Possible values are:
                  normal             The temperature is below
                                     fhTrapDashboardControlThresholdLow.

                  highDecreasing     The temperature is between
                                     fhTrapDashboardControlThresholdLow
                                     and fhTrapDashboardControlThresholdHigh,
                                     and it is decreasing.

                  normalIncreasing   The temperature is between
                                     fhTrapDashboardControlThresholdLow
                                     and fhTrapDashboardControlThresholdHigh,
                                     and it is increasing.

                  high               The temperature is above
                                     fhTrapDashboardControlThresholdHigh.
                The references to fhTrapDashboardControlThresholdLow/High
                refer to the temperatureWarning entry in
                fhTrapDashboardControlTable."
        ::= { statusBasicHw 6 }

statusCurrentTemperatureGauge OBJECT-TYPE
        SYNTAX  Gauge
        ACCESS  read-only
        STATUS  mandatory
        DESCRIPTION
                "The current temperature in degrees Celsius."
        ::= { statusBasicHw 7 }

statusCurrentTemperatureLatch OBJECT-TYPE
        SYNTAX  INTEGER { on(1), off(2) }
        ACCESS  read-write
        STATUS  mandatory
        DESCRIPTION
                "Indicates if the temperature has been above
                fhTrapDashboardControlThresholdHigh. This object is
                writable so that it can be reset by management."
        ::= { statusBasicHw 8 }

statusCurrentTemperatureLatchTime OBJECT-TYPE
        SYNTAX  TimeTicks
        ACCESS  read-only
        STATUS  mandatory
        DESCRIPTION
                "The value of sysUpTime when the system turned
                statusCurrentTemperatureLatch on."
        ::= { statusBasicHw 9 }

statusFanOperStatus OBJECT-TYPE
        SYNTAX  INTEGER { inService(1), outOfService(2) }
        ACCESS  read-only
        STATUS  mandatory
        DESCRIPTION
                "Indicates if the fan is running."
        ::= { statusBasicHw 10 }


statusPsuStatusTable OBJECT-TYPE
        SYNTAX  SEQUENCE OF StatusPsuStatusEntry
        ACCESS  not-accessible
        STATUS  mandatory
        DESCRIPTION
                "This table contains status information about the two
                power supplies in the switch."
        ::= { statusBasicHw 11 }

statusPsuStatusEntry OBJECT-TYPE
        SYNTAX  StatusPsuStatusEntry
        ACCESS  not-accessible
        STATUS  mandatory
        DESCRIPTION
                "Each row in this table describes one power supply."
        INDEX   { statusPsuIndex }
        ::= { statusPsuStatusTable 1 }

StatusPsuStatusEntry ::=
        SEQUENCE {
            statusPsuIndex
                INTEGER,
            statusPsuOperStatus
                INTEGER
        }

statusPsuIndex OBJECT-TYPE
        SYNTAX  INTEGER (1..2)
        ACCESS  read-only
        STATUS  mandatory
        DESCRIPTION
                "The power supply number."
        ::= { statusPsuStatusEntry 1 }

statusPsuOperStatus OBJECT-TYPE
        SYNTAX  INTEGER { inService(1), outOfService(2) }
        ACCESS  read-only
        STATUS  mandatory
        DESCRIPTION
                "Indicates the operational state of the power supply."
        ::= { statusPsuStatusEntry 2 }


-- Processor Module Status

statusProcessorModuleStatusLed OBJECT-TYPE
        SYNTAX  INTEGER { off(1),
                          on(2),
                          flash(3) }
        ACCESS  read-only
        STATUS  mandatory
        DESCRIPTION
                "Indicates the state of the status LED on the
                processor module."
        ::= { statusProcessorModule 1 }

statusProcessorModuleFaultLed OBJECT-TYPE
        SYNTAX  INTEGER { off(1),
                          on(2),
                          flash(3) }
        ACCESS  read-only
        STATUS  mandatory
        DESCRIPTION
                "Indicates the state of the fault LED on the
                processor module."
        ::= { statusProcessorModule 2 }


-- Feature Module Status

statusFeatureModuleOperStatus OBJECT-TYPE
        SYNTAX  INTEGER { inService(1),
                          outOfService(2),
                          testing(3),
                          unknown(4) }
        ACCESS  read-only
        STATUS  mandatory
        DESCRIPTION
                "Indicates the operational state of the feature
                module."
        ::= { statusFeatureModule 1 }

statusFeatureModuleStatusLed OBJECT-TYPE
        SYNTAX  INTEGER { off(1),
                          on(2),
                          flash(3) }
        ACCESS  read-only
        STATUS  mandatory
        DESCRIPTION
                "Indicates the state of the LED on the feature
                module."
        ::= { statusFeatureModule 2 }


-- xModules Status


statusXModuleTable OBJECT-TYPE
        SYNTAX  SEQUENCE OF StatusXModuleEntry
        ACCESS  not-accessible
        STATUS  mandatory
        DESCRIPTION
                "This table contains status information about the
                expansion modules in the switch."
        ::= { statusXModule 1 }

statusXModuleEntry OBJECT-TYPE
        SYNTAX  StatusXModuleEntry
        ACCESS  not-accessible
        STATUS  mandatory
        DESCRIPTION
                "Each row in this table describes one expansion module."
        INDEX   { statusXModuleSlotIndex }
        ::= { statusXModuleTable 1 }

StatusXModuleEntry ::=
        SEQUENCE {
            statusXModuleSlotIndex
                INTEGER,
            statusXModuleOperStatus
                INTEGER,
            statusXModuleNoOfSlotsUsed
                INTEGER,
            statusXModuleIPort1SlotIndex
                INTEGER,
            statusXModuleIPort1RIndex
                INTEGER,
            statusXModuleIPort2SlotIndex
                INTEGER,
            statusXModuleIPort2RIndex
                INTEGER,
            statusXModuleIPort3SlotIndex
                INTEGER,
            statusXModuleIPort3RIndex
                INTEGER,
            statusXModuleIPort4SlotIndex
                INTEGER,
            statusXModuleIPort4RIndex
                INTEGER
        }
        
statusXModuleSlotIndex OBJECT-TYPE
        SYNTAX  INTEGER (1..8)
        ACCESS  read-only
        STATUS  mandatory
        DESCRIPTION
                "The expansion module slot in the switch."
        ::= { statusXModuleEntry 1 }

statusXModuleOperStatus OBJECT-TYPE
        SYNTAX  INTEGER { unknown(1),
                          inService(2),
                          slave(3),
                          failed(4),
                          lost(5),
                          disabledChanged(6),
                          disabledReplaced(7),
                          disabledByManagement(8) }
        ACCESS  read-only
        STATUS  mandatory
        DESCRIPTION
                "The operational state of the expansion module."
        ::= { statusXModuleEntry 2 }

statusXModuleNoOfSlotsUsed OBJECT-TYPE
        SYNTAX  INTEGER (1..2)
        ACCESS  read-only
        STATUS  mandatory
        DESCRIPTION
                "Indicates the number of slots occupied by this
                expansion module."
        ::= { statusXModuleEntry 3 }
                                                     
statusXModuleIPort1SlotIndex OBJECT-TYPE
        SYNTAX  INTEGER (0..8)
        ACCESS  read-only
        STATUS  mandatory
        DESCRIPTION
                "The slot number for the first iPort connected to this
                expansion module. This slot number can be used to
                index, for example, configIPortTable. A value of 0
                indicates that the iPort is non-existent."
        ::= { statusXModuleEntry 4 }

statusXModuleIPort1RIndex OBJECT-TYPE
        SYNTAX  INTEGER (0..2)
        ACCESS  read-only
        STATUS  mandatory
        DESCRIPTION
                "The index of the first iPort connected to this
                expansion module. This value can be used to index, for
                example, configIPortTable."
        ::= { statusXModuleEntry 5 }

statusXModuleIPort2SlotIndex OBJECT-TYPE
        SYNTAX  INTEGER (0..8)
        ACCESS  read-only
        STATUS  mandatory
        DESCRIPTION
                "The slot number for the second iPort connected to this
                expansion module. This slot number can be used to
                index, for example, configIPortTable. A value of 0
                indicates that the iPort is non-existent."
        ::= { statusXModuleEntry 6 }

statusXModuleIPort2RIndex OBJECT-TYPE
        SYNTAX  INTEGER (0..2)
        ACCESS  read-only
        STATUS  mandatory
        DESCRIPTION
                "The index of the second iPort connected to this
                expansion module. This value can be used to index, for
                example, configIPortTable."
        ::= { statusXModuleEntry 7 }

statusXModuleIPort3SlotIndex OBJECT-TYPE
        SYNTAX  INTEGER (0..8)
        ACCESS  read-only
        STATUS  mandatory
        DESCRIPTION
                "The slot number for the third iPort connected to this
                expansion module. This slot number can be used to
                index, for example, configIPortTable. A value of 0
                indicates that the iPort is non-existent."
        ::= { statusXModuleEntry 8 }

statusXModuleIPort3RIndex OBJECT-TYPE
        SYNTAX  INTEGER (0..2)
        ACCESS  read-only
        STATUS  mandatory
        DESCRIPTION
                "The index of the third iPort connected to this
                expansion module. This value can be used to index, for
                example, configIPortTable."
        ::= { statusXModuleEntry 9 }

statusXModuleIPort4SlotIndex OBJECT-TYPE
        SYNTAX  INTEGER (0..8)
        ACCESS  read-only
        STATUS  mandatory
        DESCRIPTION
                "The slot number for the fourth iPort connected to this
                expansion module. This slot number can be used to
                index, for example, configIPortTable. A value of 0
                indicates that the iPort is non-existent."
        ::= { statusXModuleEntry 10 }

statusXModuleIPort4RIndex OBJECT-TYPE
        SYNTAX  INTEGER (0..2)
        ACCESS  read-only
        STATUS  mandatory
        DESCRIPTION
                "The index of the fourth iPort connected to this
                expansion module. This value can be used to index, for
                example, configIPortTable."
        ::= { statusXModuleEntry 11 }




-- ePort Status Table


statusEPortTable OBJECT-TYPE
        SYNTAX  SEQUENCE OF StatusEPortEntry
        ACCESS  not-accessible
        STATUS  mandatory
        DESCRIPTION
                "This table provides status information about the ATM
                ports on the switch."
        ::= { statusEPort 1 }

statusEPortEntry OBJECT-TYPE
        SYNTAX  StatusEPortEntry
        ACCESS  not-accessible
        STATUS  mandatory
        DESCRIPTION
                "Each row in this table describes one ATM port."
        INDEX   { statusEPortIfIndex }
        ::= { statusEPortTable 1 }

StatusEPortEntry ::=
        SEQUENCE {
            statusEPortIfIndex
                INTEGER,
            statusEPortXModuleIndex
                INTEGER,
            statusEPortRIndex
                INTEGER,
            statusEPortOperStatus
                INTEGER,
            statusEPortPhyState
                INTEGER,
            statusEPortType
                INTEGER,
            statusEPortRxSyncLedState
                INTEGER,
            statusEPortSignalLossLedState
                INTEGER,
            statusEPortPhyPortIndex
                INTEGER,
            statusEPortLoopbackState
                INTEGER,
            statusEPortLoopbackErrorCode
                OCTET STRING,
            statusEPortIlmiState
                INTEGER,
            statusEPortAdjInfoTransmissionType
                INTEGER,
            statusEPortAdjInfoMediaType
                INTEGER,
            statusEPortAdjInfoIfName
                OCTET STRING,
            statusEPortAdjInfoSystemIdentifier
                OCTET STRING,
            statusEPortAdjInfoMaxVpcs
                INTEGER,
            statusEPortAdjInfoMaxVccs
                INTEGER,
            statusEPortAdjInfoMaxVpiBits
                INTEGER,
            statusEPortAdjInfoMaxVciBits
                INTEGER,
            statusEPortAdjInfoUniType
                INTEGER,
            statusEPortAdjInfoUniVersion
                INTEGER,
            statusEPortAdjInfoDeviceType
                INTEGER,
            statusEPortAdjInfoIlmiVersion
                INTEGER,
            statusEPortAdjInfoNniSigVersion
                INTEGER,
            statusEPortAutoconfigMaxVpcs
                INTEGER,
            statusEPortAutoconfigMaxVccs
                INTEGER,
            statusEPortAutoconfigMaxVpiBits
                INTEGER,
            statusEPortAutoconfigMaxVciBits
                INTEGER,
            statusEPortAutoconfigUniVersion
                INTEGER,
            statusEPortAutoconfigDeviceType
                INTEGER,
            statusEPortAutoconfigDerivedInterfaceType
                INTEGER,
            statusEPortAutoconfigMaxSvpcVpi
                INTEGER,
            statusEPortAutoconfigMaxSvccVpi
                INTEGER,
            statusEPortAutoconfigMinSvccVci
                INTEGER,
            statusEPortAdjInfoMaxSvpcVpi
                INTEGER,
            statusEPortAdjInfoMaxSvccVpi
                INTEGER,
            statusEPortAdjInfoMinSvccVci
                INTEGER
        }

statusEPortIfIndex OBJECT-TYPE
        SYNTAX  INTEGER
        ACCESS  read-only
        STATUS  mandatory
        DESCRIPTION
                "The ifIndex of the ATM port."
        ::= { statusEPortEntry 1 }

statusEPortXModuleIndex OBJECT-TYPE
        SYNTAX  INTEGER (1..8)
        ACCESS  read-only
        STATUS  mandatory
        DESCRIPTION
                "The expansion module on which this ATM port is
                located."
        ::= { statusEPortEntry 2 }

statusEPortRIndex OBJECT-TYPE
        SYNTAX  INTEGER (1..24)
        ACCESS  read-only
        STATUS  mandatory
        DESCRIPTION
                "The position within the expansion module of this ATM
                port."
        ::= { statusEPortEntry 3 }

statusEPortOperStatus OBJECT-TYPE
        SYNTAX  INTEGER { up(1),
                          down(2),
                          testing(3) }
        ACCESS  read-only
        STATUS  mandatory
        DESCRIPTION
                "The operational state of the ATM port."
        ::= { statusEPortEntry 4 }

statusEPortPhyState OBJECT-TYPE
        SYNTAX  INTEGER { offlineDisabled(1),
                          offlineRestart(2),
                          onlineOk(3),
                          onlineTransPhyFault(4),
                          onlineSignalLoss(5),
                          onlineNoRxSync(6),
                          onlineAutoDisable(7),
                          onlineTesting(8) }
        ACCESS  read-only
        STATUS  mandatory
        DESCRIPTION
                "The state of the ATM port PHY."
        ::= { statusEPortEntry 5 }

statusEPortType OBJECT-TYPE
        SYNTAX  INTEGER { none(1),
                          utp25(2),
                          mmf155(3),
                          utp155(4),
                          mmf622(5),
                          smf155(6),
                          smf622(7),
                          ds3(8),
                          vpTunnel(9) }
        ACCESS  read-only
        STATUS  mandatory
        DESCRIPTION
                "The ATM port type."
        ::= { statusEPortEntry 6 }

statusEPortRxSyncLedState OBJECT-TYPE
        SYNTAX  INTEGER { off(1),
                          on(2),
                          flash(3) }
        ACCESS  read-only
        STATUS  mandatory
        DESCRIPTION
                "The state of the RXSYNC LED at the ATM port."
        ::= { statusEPortEntry 7 }

statusEPortSignalLossLedState OBJECT-TYPE
        SYNTAX  INTEGER { off(1),
                          on(2),
                          flash(3) }
        ACCESS  read-only
        STATUS  mandatory
        DESCRIPTION
                "The state of the SIGLOSS LED at the ATM port."
        ::= { statusEPortEntry 8 }

statusEPortPhyPortIndex OBJECT-TYPE
        SYNTAX  INTEGER
        ACCESS  read-only
        STATUS  mandatory
        DESCRIPTION
                "Index into a physical layer table."
        ::= { statusEPortEntry 9 }

statusEPortLoopbackState OBJECT-TYPE
        SYNTAX  INTEGER { ok(1),
                          error(2),
                          unknown(3) }
        ACCESS  read-only
        STATUS  mandatory
        DESCRIPTION
                "The loopback state of the ATM port."
        ::= { statusEPortEntry 10 }

statusEPortLoopbackErrorCode OBJECT-TYPE
        SYNTAX  OCTET STRING
        ACCESS  read-only
        STATUS  mandatory
        DESCRIPTION
                "Loopback test error information."
        ::= { statusEPortEntry 11 }

statusEPortIlmiState OBJECT-TYPE
        SYNTAX  INTEGER { stopped(1),
                          linkFailing(2),
                          establishing(3),
                          configuring(4),
                          retrieving(5),
                          registering(6),
                          verifying(7),
                          cleanUp(8) }
        ACCESS  read-only
        STATUS  mandatory
        DESCRIPTION
                "State of the ILMI protocol on the ATM port."
        ::= { statusEPortEntry 12 }

-- Adjacency information, i.e. information about the remote ATM port
-- to which this ATM port is connected

statusEPortAdjInfoTransmissionType OBJECT-TYPE
        SYNTAX  INTEGER
        ACCESS  read-only
        STATUS  mandatory
        DESCRIPTION
                "UNI 2.0 only: Transmission type of the remote ATM
                port to which this ATM port is connected."
        ::= { statusEPortEntry 13 }

statusEPortAdjInfoMediaType OBJECT-TYPE
        SYNTAX  INTEGER
        ACCESS  read-only
        STATUS  mandatory
        DESCRIPTION
                "UNI 3.1 only: The media type of the remote ATM port
                to which this ATM port is connected."
        ::= { statusEPortEntry 14 }

statusEPortAdjInfoIfName OBJECT-TYPE
        SYNTAX  DisplayString
        ACCESS  read-only
        STATUS  mandatory
        DESCRIPTION
                "The ifName from MIB-II of the remote ATM port to
                which this ATM port is connected."
        ::= { statusEPortEntry 15 }

statusEPortAdjInfoSystemIdentifier OBJECT-TYPE
        SYNTAX  OCTET STRING (SIZE (6))
        ACCESS  read-only
        STATUS  mandatory
        DESCRIPTION
                "The IEEE MAC address of the remote ATM port to which
                this ATM port is connected."
        ::= { statusEPortEntry 16 }

statusEPortAdjInfoMaxVpcs OBJECT-TYPE
        SYNTAX  INTEGER
        ACCESS  read-only
        STATUS  mandatory
        DESCRIPTION
                "The maximum number of VPCs on the remote ATM port to
                which this ATM port is connected."
        ::= { statusEPortEntry 17 }

statusEPortAdjInfoMaxVccs OBJECT-TYPE
        SYNTAX  INTEGER
        ACCESS  read-only
        STATUS  mandatory
        DESCRIPTION
                "The maximum number of VCC on the remote ATM port to
                which this ATM port is connected."
        ::= { statusEPortEntry 18 }

statusEPortAdjInfoMaxVpiBits OBJECT-TYPE
        SYNTAX  INTEGER
        ACCESS  read-only
        STATUS  mandatory
        DESCRIPTION
                "The number of bits used in a VPI on the remote ATM
                port to which this ATM port is connected."
        ::= { statusEPortEntry 19 }

statusEPortAdjInfoMaxVciBits OBJECT-TYPE
        SYNTAX  INTEGER
        ACCESS  read-only
        STATUS  mandatory
        DESCRIPTION
                "The number of bits used in a VCI on the remote ATM
                port to which this ATM port is connected."
        ::= { statusEPortEntry 20 }

statusEPortAdjInfoUniType OBJECT-TYPE
        SYNTAX  INTEGER { public(1), private(2) }
        ACCESS  read-only
        STATUS  mandatory
        DESCRIPTION
                "The UNI type of the remote ATM port to which the ATM
                port is connected."
        ::= { statusEPortEntry 21 }

statusEPortAdjInfoUniVersion OBJECT-TYPE
        SYNTAX  INTEGER { version2point0(1),
                          version3point0(2),
                          version3point1(3),
                          version4point0(4) }
        ACCESS  read-only
        STATUS  mandatory
        DESCRIPTION
                "The UNI version of the remote ATM port to which this
                ATM port is connected."
        ::= { statusEPortEntry 22 }

statusEPortAdjInfoDeviceType OBJECT-TYPE
        SYNTAX  INTEGER { user(1), node(2) }
        ACCESS  read-only
        STATUS  mandatory
        DESCRIPTION
                "The device type of the remote ATM port to which this
                ATM port is connected."
        ::= { statusEPortEntry 23 }

statusEPortAdjInfoIlmiVersion OBJECT-TYPE
        SYNTAX  INTEGER { unsupported(1),
                          version4point0(2) }
        ACCESS  read-only
        STATUS  mandatory
        DESCRIPTION
                "The ILMI version used by the remote ATM port to which
                this ATM port is connected."
        ::= { statusEPortEntry 24 }

statusEPortAdjInfoNniSigVersion OBJECT-TYPE
        SYNTAX  INTEGER { unsupported(1),
                          iisp(2),
                          pnniVersion1point0(3) }
        ACCESS  read-only
        STATUS  mandatory
        DESCRIPTION
                "The NNI signalling protocol used by the remote ATM
                port to which this ATM port is connected."
        ::= { statusEPortEntry 25 }

-- Autoconfiguration information, i.e. the values resulting from
-- negotiation between this ATM port and the remote port to which
-- it is connected

statusEPortAutoconfigMaxVpcs OBJECT-TYPE
        SYNTAX  INTEGER
        ACCESS  read-only
        STATUS  mandatory
        DESCRIPTION
                "The maximum number of VPCs that the connection between
                this ATM port and its peer will use."
        ::= { statusEPortEntry 26 }

statusEPortAutoconfigMaxVccs OBJECT-TYPE
        SYNTAX  INTEGER
        ACCESS  read-only
        STATUS  mandatory
        DESCRIPTION
                "The maximum number of VCCs that the connection
                between this ATM port and its peer will use."
        ::= { statusEPortEntry 27 }

statusEPortAutoconfigMaxVpiBits OBJECT-TYPE
        SYNTAX  INTEGER
        ACCESS  read-only
        STATUS  mandatory
        DESCRIPTION
                "The number of bits used in a VPI on the connection
                between this ATM port and its peer."
        ::= { statusEPortEntry 28 }

statusEPortAutoconfigMaxVciBits OBJECT-TYPE
        SYNTAX  INTEGER
        ACCESS  read-only
        STATUS  mandatory
        DESCRIPTION
                "The number of bits used in a VCI on the connection
                between this ATM port and its peer."
        ::= { statusEPortEntry 29 }

statusEPortAutoconfigUniVersion OBJECT-TYPE
        SYNTAX  INTEGER { undefined(1),
                          version3point0(2),
                          version3point1(3),
                          version4point0(4) }
        ACCESS  read-only
        STATUS  mandatory
        DESCRIPTION
                "The UNI version used between this ATM port and its
                peer."
        ::= { statusEPortEntry 30 }

statusEPortAutoconfigDeviceType OBJECT-TYPE
        SYNTAX  INTEGER { user(1), node(2) }
        ACCESS  read-only
        STATUS  mandatory
        DESCRIPTION
                "The device type of this ATM port used in its
                communication with its peer."
        ::= { statusEPortEntry 31 }

statusEPortAutoconfigDerivedInterfaceType OBJECT-TYPE
        SYNTAX  INTEGER { undefined(1),
                          publicUni(2),
                          privateUni(3),
                          privateNni(4) }
        ACCESS  read-only
        STATUS  mandatory
        DESCRIPTION
                "The UNI/NNI interface type of this ATM port used in
                its communication with its peer."
        ::= { statusEPortEntry 32 }

statusEPortAutoconfigMaxSvpcVpi OBJECT-TYPE
        SYNTAX  INTEGER (0..4096)
        ACCESS  read-only
        STATUS  mandatory
        DESCRIPTION
                "The highest VPI number used for signalled VPCs
                between this ATM port and its peer."
        ::= { statusEPortEntry 33 }

statusEPortAutoconfigMaxSvccVpi OBJECT-TYPE
        SYNTAX  INTEGER (0..4096)
        ACCESS  read-only
        STATUS  mandatory
        DESCRIPTION
                "The highest VPI number used for signalled VCCs
                between this ATM port and its peer."
        ::= { statusEPortEntry 34 }

statusEPortAutoconfigMinSvccVci OBJECT-TYPE
        SYNTAX  INTEGER (0..65536)
        ACCESS  read-only
        STATUS  mandatory
        DESCRIPTION
                "The lowest VCI number used for signalled VCCs
                between this ATM port and its peer."
        ::= { statusEPortEntry 35 }

statusEPortAdjInfoMaxSvpcVpi OBJECT-TYPE
        SYNTAX  INTEGER (0..4096)
        ACCESS  read-only
        STATUS  mandatory
        DESCRIPTION
                "The MaxSvpcVpi value of the remote port."
        ::= { statusEPortEntry 36 }

statusEPortAdjInfoMaxSvccVpi OBJECT-TYPE
        SYNTAX  INTEGER (0..4096)
        ACCESS  read-only
        STATUS  mandatory
        DESCRIPTION
                "The MaxSvccVpi value of the remote port."
        ::= { statusEPortEntry 37 }

statusEPortAdjInfoMinSvccVci OBJECT-TYPE
        SYNTAX  INTEGER (0..65536)
        ACCESS  read-only
        STATUS  mandatory
        DESCRIPTION
                "The MinSvccVci value of the remote port."
        ::= { statusEPortEntry 38 }


-- VPC and VCC Extension Tables

vpcExtensionTable OBJECT-TYPE
        SYNTAX  SEQUENCE OF VpcExtensionEntry
        ACCESS  not-accessible
        STATUS  mandatory
        DESCRIPTION
                "This table provides information about VPCs in
                addition to what is found in the ATM MIB."
        ::= { statusVpcVcc 1 }

vpcExtensionEntry OBJECT-TYPE
        SYNTAX  VpcExtensionEntry
        ACCESS  not-accessible
        STATUS  mandatory
        DESCRIPTION
                "Each row in this table describes one VPC."
        INDEX   { vpcExtensionIndex }
        ::= { vpcExtensionTable 1 }

VpcExtensionEntry ::=
        SEQUENCE {
            vpcExtensionIndex
                INTEGER,
            vpcExtensionVpCrossConnectIndex
                INTEGER,
            vpcExtensionOrigAtmAddr
                AtmAddress,
            vpcExtensionTermAtmAddr
                AtmAddress,
            vpcExtensionCapabilities
                INTEGER
        }

vpcExtensionIndex OBJECT-TYPE
        SYNTAX  INTEGER
        ACCESS  read-only
        STATUS  mandatory
        DESCRIPTION
                "An arbitrary integer used to differentiate multiple
                rows in this table."
        ::= { vpcExtensionEntry 1 }

vpcExtensionVpCrossConnectIndex OBJECT-TYPE
        SYNTAX  INTEGER
        ACCESS  read-only
        STATUS  mandatory
        DESCRIPTION
                "The index of this VPC in the atmVpCrossConnectTable
                in the ATM MIB."
        ::= { vpcExtensionEntry 2 }

vpcExtensionOrigAtmAddr OBJECT-TYPE
        SYNTAX  AtmAddress
        ACCESS  read-only
        STATUS  mandatory
        DESCRIPTION
                "The ATM address that originated this VPC."
        ::= { vpcExtensionEntry 3 }

vpcExtensionTermAtmAddr OBJECT-TYPE
        SYNTAX  AtmAddress
        ACCESS  read-only
        STATUS  mandatory
        DESCRIPTION
                "The ATM address at which this VPC terminates."
        ::= { vpcExtensionEntry 4 }

vpcExtensionCapabilities OBJECT-TYPE
        SYNTAX  INTEGER
        ACCESS  read-only
        STATUS  mandatory
        DESCRIPTION
                "Reserved for special capabilities."
        ::= { vpcExtensionEntry 5 }


vccExtensionTable OBJECT-TYPE
        SYNTAX  SEQUENCE OF VccExtensionEntry
        ACCESS  not-accessible
        STATUS  mandatory
        DESCRIPTION
                "This table provides information about VCCs in
                addition to what is found in the ATM MIB."
        ::= { statusVpcVcc 2 }

vccExtensionEntry OBJECT-TYPE
        SYNTAX  VccExtensionEntry
        ACCESS  not-accessible
        STATUS  mandatory
        DESCRIPTION
                "Each row in this table describes one VCC."
        INDEX   { vccExtensionIndex }
        ::= { vccExtensionTable 1 }

VccExtensionEntry ::=
        SEQUENCE {
            vccExtensionIndex
                INTEGER,
            vccExtensionVcCrossConnectIndex
                INTEGER,
            vccExtensionOrigAtmAddr
                AtmAddress,
            vccExtensionTermAtmAddr
                AtmAddress,
            vccExtensionCapabilities
                INTEGER,
            vccExtensionEarlyPacketDiscard
                INTEGER
        }

vccExtensionIndex OBJECT-TYPE
        SYNTAX  INTEGER
        ACCESS  read-only
        STATUS  mandatory
        DESCRIPTION
                "An arbitrary integer used to differentiate multiple
                rows in this table."
        ::= { vccExtensionEntry 1 }

vccExtensionVcCrossConnectIndex OBJECT-TYPE
        SYNTAX  INTEGER
        ACCESS  read-only
        STATUS  mandatory
        DESCRIPTION
                "The index of this VCC in the atmVcCrossConnectTable
                in the ATM MIB."
        ::= { vccExtensionEntry 2 }

vccExtensionOrigAtmAddr OBJECT-TYPE
        SYNTAX  AtmAddress
        ACCESS  read-only
        STATUS  mandatory
        DESCRIPTION
                "The ATM address that originated this VCC."
        ::= { vccExtensionEntry 3 }

vccExtensionTermAtmAddr OBJECT-TYPE
        SYNTAX  AtmAddress
        ACCESS  read-only
        STATUS  mandatory
        DESCRIPTION
                "The ATM address at which this VPC terminates."
        ::= { vccExtensionEntry 4 }

vccExtensionCapabilities OBJECT-TYPE
        SYNTAX  INTEGER
        ACCESS  read-only
        STATUS  mandatory
        DESCRIPTION
                "Reserved for special capabilities."
        ::= { vccExtensionEntry 5 }

vccExtensionEarlyPacketDiscard OBJECT-TYPE
        SYNTAX  INTEGER { on(1), off(2) }
        ACCESS  read-only
        STATUS  mandatory
        DESCRIPTION
                "Indicates if early packet discard is allowed on this VCC."
        ::= { vccExtensionEntry 6 }


-- Fatal Log Section

-- These objects contain information about the size and contents of
-- the software FATAL log

statusFatalStatUsed OBJECT-TYPE
        SYNTAX  INTEGER
        ACCESS  read-only
        STATUS  mandatory
        DESCRIPTION
                "The number of currently used entries in the FATAL
                log."
        ::= { statusFatalLog 1 }

statusFatalStatFree OBJECT-TYPE
        SYNTAX  INTEGER
        ACCESS  read-only
        STATUS  mandatory
        DESCRIPTION
                "The number of free entries in the FATAL log."
        ::= { statusFatalLog 2 }

statusFatalStatOverflow OBJECT-TYPE
        SYNTAX  INTEGER { yes(1), no(2) }
        ACCESS  read-only
        STATUS  mandatory
        DESCRIPTION
                "Indicates if there has been an overflow in the FATAL
                log."
        ::= { statusFatalLog 3 }

statusFatalStatMaxDumpLength OBJECT-TYPE
        SYNTAX  INTEGER
        ACCESS  read-only
        STATUS  mandatory
        DESCRIPTION
                "The maximum number of bytes that can be dumped."
        ::= { statusFatalLog 4 }

statusFatalTable OBJECT-TYPE
        SYNTAX  SEQUENCE OF StatusFatalEntry
        ACCESS  not-accessible
        STATUS  mandatory
        DESCRIPTION
                "This table contains the contents of the FATAL log."
        ::= { statusFatalLog 5 }

statusFatalEntry OBJECT-TYPE
        SYNTAX  StatusFatalEntry
        ACCESS  not-accessible
        STATUS  mandatory
        DESCRIPTION
                "Each row in this table describes one entry in the
                FATAL log."
        INDEX   { statusFatalIndex }
        ::= { statusFatalTable 1 }

StatusFatalEntry ::=
        SEQUENCE {
            statusFatalIndex
                INTEGER,
            statusFatalSerial
                INTEGER,
            statusFatalTimestamp
                INTEGER,
            statusFatalTimeString
                DisplayString,
            statusFatalSource
                DisplayString,
            statusFatalLine
                INTEGER,
            statusFatalOriginalDumpSize
                INTEGER,
            statusFatalDumpSize
                INTEGER,
            statusFatalDump
                OCTET STRING
        }

statusFatalIndex OBJECT-TYPE
        SYNTAX  INTEGER
        ACCESS  read-only
        STATUS  mandatory
        DESCRIPTION
                "An arbitrary integer used to differentiate multiple
                rows in the table."
        ::= { statusFatalEntry 1 }

statusFatalSerial OBJECT-TYPE
        SYNTAX  INTEGER
        ACCESS  read-only
        STATUS  mandatory
        DESCRIPTION
                "The serial number of this entry."
        ::= { statusFatalEntry 2 }

statusFatalTimestamp OBJECT-TYPE
        SYNTAX  INTEGER
        ACCESS  read-only
        STATUS  mandatory
        DESCRIPTION
                "Time when the FATAL error occurred (measured in
                seconds since 00:00:00 UTC on 1 January 1970)."
        ::= { statusFatalEntry 3 }

statusFatalTimeString OBJECT-TYPE
        SYNTAX  DisplayString
        ACCESS  read-only
        STATUS  mandatory
        DESCRIPTION
                "Time when the FATAL error occurred (as a string
                giving the UTC time and date)."
        ::= { statusFatalEntry 4 }

statusFatalSource OBJECT-TYPE
        SYNTAX  DisplayString
        ACCESS  read-only
        STATUS  mandatory
        DESCRIPTION
                "Source file name of version of the software that
                generated the FATAL error."
        ::= { statusFatalEntry 5 }

statusFatalLine OBJECT-TYPE
        SYNTAX  INTEGER
        ACCESS  read-only
        STATUS  mandatory
        DESCRIPTION
                "The line number of the source code instruction that
                generated the FATAL error."
        ::= { statusFatalEntry 6 }

statusFatalOriginalDumpSize OBJECT-TYPE
        SYNTAX  INTEGER
        ACCESS  read-only
        STATUS  mandatory
        DESCRIPTION
                "The original size of the dumped objects."
        ::= { statusFatalEntry 7 }

statusFatalDumpSize OBJECT-TYPE
        SYNTAX  INTEGER
        ACCESS  read-only
        STATUS  mandatory
        DESCRIPTION
                "The actual size of the dumped objects."
        ::= { statusFatalEntry 8 }

statusFatalDump OBJECT-TYPE
        SYNTAX  OCTET STRING
        ACCESS  read-only
        STATUS  mandatory
        DESCRIPTION
                "The dumped objects."
        ::= { statusFatalEntry 9 }


-- Statistics Section

-- This section provides statistics about the operation of the switch


statisticsGlobal  OBJECT IDENTIFIER ::= { crossfireAtmStatistics 1 }
statisticsCpuPort OBJECT IDENTIFIER ::= { crossfireAtmStatistics 2 }
statisticsEPort   OBJECT IDENTIFIER ::= { crossfireAtmStatistics 3 }
statisticsIPort   OBJECT IDENTIFIER ::= { crossfireAtmStatistics 4 }


-- Global Switch Statistics

statsGlobalCongestionState OBJECT-TYPE
        SYNTAX  INTEGER { normal(1),
                          highDecreasing(2),
                          normalIncreasing(3),
                          high(4) }
        ACCESS  read-only
        STATUS  mandatory
        DESCRIPTION
                "The current congestion state within the switch, based
                on the number of globally discarded cells. Possible
                values are:
                  normal             The cell discard rate is below
                                     fhTrapDashboardControlThresholdLow.

                  highDecreasing     The cell discard rate is between
                                     fhTrapDashboardControlThresholdLow
                                     and fhTrapDashboardControlThresholdHigh,
                                     and it is decreasing.

                  normalIncreasing   The cell discard rate is between
                                     fhTrapDashboardControlThresholdLow
                                     and fhTrapDashboardControlThresholdHigh,
                                     and it is increasing.

                  high               The cell discard rate is above
                                     fhTrapDashboardControlThresholdHigh.
                The references to fhTrapDashboardControlThresholdLow/High
                refer to the globalCongestion entry in
                fhTrapDashboardControlTable."
        ::= { statisticsGlobal 1 }

statsGlobalCongestionDiscardCellRate OBJECT-TYPE
        SYNTAX  Gauge
        ACCESS  read-only
        STATUS  mandatory
        DESCRIPTION
                "The rate of globally discarded cells (measured in
                cells/second), averaged over 10 seconds."
        ::= { statisticsGlobal 2 }

statsGlobalCongestionDiscardCellCounter OBJECT-TYPE
        SYNTAX  Counter
        ACCESS  read-only
        STATUS  mandatory
        DESCRIPTION
                "The number of globally discarded cells."
        ::= { statisticsGlobal 3 }

statsGlobalCongestionDiscardCellLatch OBJECT-TYPE
        SYNTAX  INTEGER { on(1), off(2) }
        ACCESS  read-write
        STATUS  mandatory
        DESCRIPTION
                "Indicates if the cell discard rate has been above
                fhTrapDashboardControlThresholdHigh. This object is
                writable so that it can be reset by management."
        ::= { statisticsGlobal 4 }

statsGlobalCongestionDiscardCellLatchTime OBJECT-TYPE
        SYNTAX  TimeTicks
        ACCESS  read-only
        STATUS  mandatory
        DESCRIPTION
                "The value of sysUpTime when the system turned
                statsGlobalCongestionDiscardCellLatch on."
        ::= { statisticsGlobal 5 }


statsInvalidCellRateState OBJECT-TYPE
        SYNTAX  INTEGER { normal(1),
                          highDecreasing(2),
                          normalIncreasing(3),
                          high(4) }
        ACCESS  read-only
        STATUS  mandatory
        DESCRIPTION
                "The current invalid cell state within the switch, based
                on the number of invalid cells received. Possible
                values are:
                  normal             The invalid cell rate is below
                                     fhTrapDashboardControlThresholdLow.

                  highDecreasing     The invalid cell rate is between
                                     fhTrapDashboardControlThresholdLow
                                     and fhTrapDashboardControlThresholdHigh,
                                     and it is decreasing.

                  normalIncreasing   The invalid cell rate is between
                                     fhTrapDashboardControlThresholdLow
                                     and fhTrapDashboardControlThresholdHigh,
                                     and it is increasing.

                  high               The invalid cell rate is above
                                     fhTrapDashboardControlThresholdHigh.
                The references to fhTrapDashboardControlThresholdLow/High
                refer to the globalInvalidCellRate entry in
                fhTrapDashboardControlTable."
        ::= { statisticsGlobal 6 }

statsInvalidCellRate OBJECT-TYPE
        SYNTAX  Gauge
        ACCESS  read-only
        STATUS  mandatory
        DESCRIPTION
                "The rate of invalid cells (measured in cells/second),
                averaged over 10 seconds."
        ::= { statisticsGlobal 7 }

statsInvalidCellCounter OBJECT-TYPE
        SYNTAX  Counter
        ACCESS  read-only
        STATUS  mandatory
        DESCRIPTION
                "The number of invalid cells received."
        ::= { statisticsGlobal 8 }

statsInvalidCellLatch OBJECT-TYPE
        SYNTAX  INTEGER { on(1), off(2) }
        ACCESS  read-write
        STATUS  mandatory
        DESCRIPTION
                "Indicates if the invalid cell rate has been above
                fhTrapDashboardControlThresholdHigh. This object is
                writable so that it can be reset by management."
        ::= { statisticsGlobal 9 }

statsInvalidCellLatchTime OBJECT-TYPE
        SYNTAX  TimeTicks
        ACCESS  read-only
        STATUS  mandatory
        DESCRIPTION
                "The value of sysUpTime when the system turned
                statsInvalidCellLatch on."
        ::= { statisticsGlobal 10 }


-- CPU Port Statistics

statsCpuPortCongestionState OBJECT-TYPE
        SYNTAX  INTEGER { normal(1),
                          highDecreasing(2),
                          normalIncreasing(3),
                          high(4) }
        ACCESS  read-only
        STATUS  mandatory
        DESCRIPTION
                "The current congestion state of the switch processor
                queue, based on the number of cells in the switch
                processor queue. Possible values are:
                  normal             The queue length is below
                                     fhTrapDashboardControlThresholdLow.

                  highDecreasing     The queue length is between
                                     fhTrapDashboardControlThresholdLow
                                     and fhTrapDashboardControlThresholdHigh,
                                     and it is decreasing.

                  normalIncreasing   The queue length is between
                                     fhTrapDashboardControlThresholdLow
                                     and fhTrapDashboardControlThresholdHigh,
                                     and it is increasing.

                  high               The queue length is above
                                     fhTrapDashboardControlThresholdHigh.
                The references to fhTrapDashboardControlThresholdLow/High
                refer to the cpuPortCongestion entry in
                fhTrapDashboardControlTable."
        ::= { statisticsCpuPort 1 }

statsCpuPortDiscardCellRate OBJECT-TYPE
        SYNTAX  Gauge
        ACCESS  read-only
        STATUS  mandatory
        DESCRIPTION
                "The rate of discarded cells per second destined for
                the switch processor queue (measured in cells/second),
                averaged over 10 seconds."
        ::= { statisticsCpuPort 2 }

statsCpuPortDiscardCellCounter OBJECT-TYPE
        SYNTAX  Counter
        ACCESS  read-only
        STATUS  mandatory
        DESCRIPTION
                "The number of cells, destined for the switch
                processor queue, that have been discarded."
        ::= { statisticsCpuPort 3 }

statsCpuPortDiscardCellLatch OBJECT-TYPE
        SYNTAX  INTEGER { on(1), off(2) }
        ACCESS  read-write
        STATUS  mandatory
        DESCRIPTION
                "Indicates if the switch processor queue cell discard
                rate has been above fhTrapDashboardControlThresholdHigh.
                This object is writable so that it can be reset by
                management."
        ::= { statisticsCpuPort 4 }

statsCpuPortDiscardCellLatchTime OBJECT-TYPE
        SYNTAX  TimeTicks
        ACCESS  read-only
        STATUS  mandatory
        DESCRIPTION
                "The value of sysUpTime when the system turned
                statsCpuPortDiscardCellLatch on."
        ::= { statisticsCpuPort 5 }


-- ePort Statistics Table


statsEportTable OBJECT-TYPE
        SYNTAX  SEQUENCE OF StatsEportEntry
        ACCESS  not-accessible
        STATUS  mandatory
        DESCRIPTION
                "This table contains ATM port HEC error statistics."
        ::= { statisticsEPort 1 }

statsEportEntry OBJECT-TYPE
        SYNTAX  StatsEportEntry
        ACCESS  not-accessible
        STATUS  mandatory
        DESCRIPTION
                "Each row in this table describes one ATM port."
        INDEX   { statsEPortIfIndex }
        ::= { statsEportTable 1 }

StatsEportEntry ::=
        SEQUENCE {
            statsEPortIfIndex
                INTEGER,
            statsEPortHecErrorRateConditionState
                INTEGER,
            statsEPortRxHecErrorCellRate
                Gauge,
            statsEPortRxHecErrorCellCounter
                Counter,
            statsEPortRxHecErrorCellLatch
                INTEGER,
            statsEPortRxHecErrorCellLatchTime
                TimeTicks
        }

statsEPortIfIndex OBJECT-TYPE
        SYNTAX  INTEGER
        ACCESS  read-only
        STATUS  mandatory
        DESCRIPTION
                "The ifIndex of the ATM port."
        ::= { statsEportEntry 1 }

statsEPortHecErrorRateConditionState OBJECT-TYPE
        SYNTAX  INTEGER { normal(1),
                          highDecreasing(2),
                          normalIncreasing(3),
                          high(4) }
        ACCESS  read-only
        STATUS  mandatory
        DESCRIPTION
                "The current HEC error state within the switch, based
                on the rate of cells with HEC errors. Possible values
                are:
                  normal             The HEC error cell rate is below
                                     fhTrapDashboardControlThresholdLow.

                  highDecreasing     The HEC error cell rate is between
                                     fhTrapDashboardControlThresholdLow
                                     and fhTrapDashboardControlThresholdHigh,
                                     and it is decreasing.

                  normalIncreasing   The HEC error cell rate is between
                                     fhTrapDashboardControlThresholdLow
                                     and fhTrapDashboardControlThresholdHigh,
                                     and it is increasing.

                  high               The HEC cell rate is above
                                     fhTrapDashboardControlThresholdHigh.
                The references to fhTrapDashboardControlThresholdLow/High
                refer to the ePortHecErrorRate entry in
                fhTrapDashboardControlTable."
        ::= { statsEportEntry 2 }

statsEPortRxHecErrorCellRate OBJECT-TYPE
        SYNTAX  Gauge
        ACCESS  read-only
        STATUS  mandatory
        DESCRIPTION
                "The rate of cells with HEC errors received on this
                ATM port (measured in cells/second), averaged over 10
                seconds."
        ::= { statsEportEntry 3 }

statsEPortRxHecErrorCellCounter OBJECT-TYPE
        SYNTAX  Counter
        ACCESS  read-only
        STATUS  mandatory
        DESCRIPTION
                "The number of cells with HEC errors received on this
                ATM port."
        ::= { statsEportEntry 4 }

statsEPortRxHecErrorCellLatch OBJECT-TYPE
        SYNTAX  INTEGER { on(1), off(2) }
        ACCESS  read-write
        STATUS  mandatory
        DESCRIPTION
                "Indicates if the HEC error cell rate has been above
                fhTrapDashboardControlThresholdHigh. This object is
                writable so that it can be reset by management."
        ::= { statsEportEntry 5 }

statsEPortRxHecErrorCellLatchTime OBJECT-TYPE
        SYNTAX  TimeTicks
        ACCESS  read-only
        STATUS  mandatory
        DESCRIPTION
                "The value of sysUpTime when the system turned
                statsEPortRxHecErrorCellLatch on."
        ::= { statsEportEntry 6 }


-- iPort Status and Statistics Table


statsIPortTable OBJECT-TYPE
        SYNTAX  SEQUENCE OF StatsIPortEntry
        ACCESS  not-accessible
        STATUS  mandatory
        DESCRIPTION
                "This table contains statistics for the Core Access
                Points (iPorts) in the switch)."
        ::= { statisticsIPort 1 }

statsIPortEntry OBJECT-TYPE
        SYNTAX  StatsIPortEntry
        ACCESS  not-accessible
        STATUS  mandatory
        DESCRIPTION
                "Each row in this table describes one iPort."
        INDEX   { statsIPortSlotIndex,
                  statsIPortRIndex }
        ::= { statsIPortTable 1 }

StatsIPortEntry ::=
        SEQUENCE {
            statsIPortSlotIndex
                INTEGER,
            statsIPortRIndex
                INTEGER,
            statsIPortRxCellRate
                Gauge,
            statsIPortTxCellRate
                Gauge,
            statsIPortTxParityErrorCellCounter
                Counter
        }

statsIPortSlotIndex OBJECT-TYPE
        SYNTAX  INTEGER (1..8)
        ACCESS  read-only
        STATUS  mandatory
        DESCRIPTION
                "The number of the expansion module to which the iPort
                is connected."
        ::= { statsIPortEntry 1 }

statsIPortRIndex OBJECT-TYPE
        SYNTAX  INTEGER (1..2)
        ACCESS  read-only
        STATUS  mandatory
        DESCRIPTION
                "The number of the iPort within the expansion module."
        ::= { statsIPortEntry 2 }

statsIPortRxCellRate OBJECT-TYPE
        SYNTAX  Gauge
        ACCESS  read-only
        STATUS  mandatory
        DESCRIPTION
                "The rate of cells received on this iPort (measured in
                cells/second), averaged over 5 samples, sampled every
                2 seconds, computed as 0.8*previous+0.2*current."
        ::= { statsIPortEntry 3 }

statsIPortTxCellRate OBJECT-TYPE
        SYNTAX  Gauge
        ACCESS  read-only
        STATUS  mandatory
        DESCRIPTION
                "The rate of cells transmitted on this iPort (measured
                in cells/second), averaged over 5 samples, sampled
                every 2 seconds, computed as
                0.8*previous+0.2*current."
        ::= { statsIPortEntry 4 }
                                                     
statsIPortTxParityErrorCellCounter OBJECT-TYPE
        SYNTAX  Counter
        ACCESS  read-only
        STATUS  mandatory
        DESCRIPTION
                "The number of cells with memory parity error that
                were read from the switch core cell buffer."
        ::= { statsIPortEntry 5 }


statsQueueCongestionTable OBJECT-TYPE
        SYNTAX  SEQUENCE OF StatsQueueCongestionEntry
        ACCESS  not-accessible
        STATUS  mandatory
        DESCRIPTION
                "This table contains congestion information for each
                queue attached to each Core Access Point (iPort)."
        ::= { statisticsIPort 2 }

statsQueueCongestionEntry OBJECT-TYPE
        SYNTAX  StatsQueueCongestionEntry
        ACCESS  not-accessible
        STATUS  mandatory
        DESCRIPTION
                "Each row in this table describes one queue on one
                iPort."
        INDEX   { statsQueueCongestionSlotIndex,
                  statsQueueCongestionIPortRIndex,
                  statsQueueCongestionQueueIndex }
        ::= { statsQueueCongestionTable 1 }

StatsQueueCongestionEntry ::=
        SEQUENCE {
            statsQueueCongestionSlotIndex
                INTEGER,
            statsQueueCongestionIPortRIndex
                INTEGER,
            statsQueueCongestionQueueIndex
                INTEGER,
            statsQueueCongestionConditionState
                INTEGER,
            statsQueueCongestionCellsInQueueGauge
                Gauge,
            statsQueueCongestionCellsInQueueLatch
                INTEGER,
            statsQueueCongestionCellsInQueueLatchTime
                TimeTicks
        }

statsQueueCongestionSlotIndex OBJECT-TYPE
        SYNTAX  INTEGER (1..8)
        ACCESS  read-only
        STATUS  mandatory
        DESCRIPTION
                "The number of the expansion module to which the iPort
                is connected."
        ::= { statsQueueCongestionEntry 1 }

statsQueueCongestionIPortRIndex OBJECT-TYPE
        SYNTAX  INTEGER (1..2)
        ACCESS  read-only
        STATUS  mandatory
        DESCRIPTION
                "The number of the iPort within the expansion module."
        ::= { statsQueueCongestionEntry 2 }

statsQueueCongestionQueueIndex OBJECT-TYPE
        SYNTAX  INTEGER (1..4)
        ACCESS  read-only
        STATUS  mandatory
        DESCRIPTION
                "The queue priority."
        ::= { statsQueueCongestionEntry 3 }

statsQueueCongestionConditionState OBJECT-TYPE
        SYNTAX  INTEGER { normal(1),
                          highDecreasing(2),
                          normalIncreasing(3),
                          high(4) }
        ACCESS  read-only
        STATUS  mandatory
        DESCRIPTION
                "The current congestion state on the iPort queue,
                based on the length of the queue. Possible
                values are:
                  normal             The queue length is below
                                     fhTrapDashboardControlThresholdLow.

                  highDecreasing     The queue length is between
                                     fhTrapDashboardControlThresholdLow
                                     and fhTrapDashboardControlThresholdHigh,
                                     and it is decreasing.

                  normalIncreasing   The queue length is between
                                     fhTrapDashboardControlThresholdLow
                                     and fhTrapDashboardControlThresholdHigh,
                                     and it is increasing.

                  high               The queue length is above
                                     fhTrapDashboardControlThresholdHigh.
                The references to fhTrapDashboardControlThresholdLow/High
                refer to the iPortCongestion entry in
                fhTrapDashboardControlTable."
        ::= { statsQueueCongestionEntry 4 }

statsQueueCongestionCellsInQueueGauge OBJECT-TYPE
        SYNTAX  Gauge
        ACCESS  read-only
        STATUS  mandatory
        DESCRIPTION
                "The current length of the iPort queue."
        ::= { statsQueueCongestionEntry 5 }

statsQueueCongestionCellsInQueueLatch OBJECT-TYPE
        SYNTAX  INTEGER
        ACCESS  read-write
        STATUS  mandatory
        DESCRIPTION
                "Indicates if the iPort queue length has been above
                fhTrapDashboardControlThresholdHigh. This object is
                writable so that it can be reset by management."
        ::= { statsQueueCongestionEntry 6 }

statsQueueCongestionCellsInQueueLatchTime OBJECT-TYPE
        SYNTAX  TimeTicks
        ACCESS  read-only
        STATUS  mandatory
        DESCRIPTION
                "The value of sysUpTime when the system turned
                statsQueueCongestionCellsInQueueLatch on."
        ::= { statsQueueCongestionEntry 7 }


-- Trap Control Section

-- This section contains objects that define threshold levels that
-- trigger the generation of various traps. The actual enabling or
-- disabling of traps is controlled via the controlTrapTable in the
-- Olicom MIB.

fhTrapFrequencyCntrlFrequency OBJECT-TYPE
        SYNTAX  INTEGER (1..60)
        ACCESS  read-write
        STATUS  mandatory
        DESCRIPTION
                "Controls how frequently a threshold-exceeded trap may
                be generated. This object is the maximum number of
                times each trap may be sent per minute."
        ::= { crossfireAtmTrapControl 1 }

fhTrapFrequencyCntrlMaxTraps OBJECT-TYPE
        SYNTAX  INTEGER (1..1000)
        ACCESS  read-write
        STATUS  mandatory
        DESCRIPTION
                "The maximum number of times each threshold-exceeded
                trap may be generated during one threshold-exceeded
                incident if fhTrapDashboardControlFrequencyMode is
                upToMax."
        ::= { crossfireAtmTrapControl 2 }


fhTrapDashboardControlTable OBJECT-TYPE
        SYNTAX  SEQUENCE OF FhTrapDashboardControlEntry
        ACCESS  not-accessible
        STATUS  mandatory
        DESCRIPTION
                "This table contains the thresholds that trigger
                various traps."
        ::= { crossfireAtmTrapControl 3 }

fhTrapDashboardControlEntry OBJECT-TYPE
        SYNTAX  FhTrapDashboardControlEntry
        ACCESS  not-accessible
        STATUS  mandatory
        DESCRIPTION
                "Each row in this table describes one trap type."
        INDEX   { fhTrapDashboardControlTrapTypeIndex }
        ::= { fhTrapDashboardControlTable 1 }

FhTrapDashboardControlEntry ::=
        SEQUENCE {
            fhTrapDashboardControlTrapTypeIndex
                INTEGER,
            fhTrapDashboardControlFrequencyMode
                INTEGER,
            fhTrapDashboardControlThresholdLow
                INTEGER,
            fhTrapDashboardControlThresholdHigh
                INTEGER,
            fhTrapDashboardControlSamplingInterval
                INTEGER,
            fhTrapDashboardControlNoSamples
                INTEGER
        }

fhTrapDashboardControlTrapTypeIndex OBJECT-TYPE
        SYNTAX  INTEGER { globalCongestion(1),
                          globalInvalidCellRate(2),
                          cpuPortCongestion(3),
                          iPortCongestion(4),
                          ePortHecErrorRate(5),
                          temperatureWarning(6),
                          psuMonitor(7), -- only fhTrapDashboardControlFrequencyMode applies
                          fanMonitor(8)  -- only fhTrapDashboardControlFrequencyMode applies
                          }
        ACCESS  read-only
        STATUS  mandatory
        DESCRIPTION
                "The trap type."
        ::= { fhTrapDashboardControlEntry 1 }

fhTrapDashboardControlFrequencyMode OBJECT-TYPE
        SYNTAX  INTEGER { oneShot(1),
                          forever(2),
                          upToMax(3) }
        ACCESS  read-write
        STATUS  mandatory
        DESCRIPTION
                "Controls the number of times this trap may be
                generated. The legal values are:
                   oneShot    Generate a trap once for each
                              threshold-exceeded incident.

                   forever    Generate traps at the rate specified in
                              fhTrapFrequencyCntrlFrequency.

                   upToMax    Generate traps at the rate specified in
                              fhTrapFrequencyCntrlFrequency, but do
                              not generate more than
                              fhTrapFrequencyCntrlMaxTraps traps for
                              each threshold-exceeded incident."
        ::= { fhTrapDashboardControlEntry 2 }

fhTrapDashboardControlThresholdLow OBJECT-TYPE
        SYNTAX  INTEGER
        ACCESS  read-write
        STATUS  mandatory
        DESCRIPTION
                "The low threshold hysteresis value. When the measured
                value drops below this number, trap generation stops.
                This value must be smaller than or equal to
                fhTrapDashboardControlThresholdHigh."
        ::= { fhTrapDashboardControlEntry 3 }

fhTrapDashboardControlThresholdHigh OBJECT-TYPE
        SYNTAX  INTEGER
        ACCESS  read-write
        STATUS  mandatory
        DESCRIPTION
                "The high threshold hysteresis value. When the measured
                value rises above this number, trap generation starts.
                This value must be greater than or equal to
                fhTrapDashboardControlThresholdLow."
        ::= { fhTrapDashboardControlEntry 4 }

fhTrapDashboardControlSamplingInterval OBJECT-TYPE
        SYNTAX  INTEGER (1..65535)
        ACCESS  read-write
        STATUS  mandatory
        DESCRIPTION
                "Sampling interval (in seconds) for the value that is
                to be compared with the thresholds."
        ::= { fhTrapDashboardControlEntry 5 }

fhTrapDashboardControlNoSamples OBJECT-TYPE
        SYNTAX  INTEGER (1..32)
        ACCESS  read-write
        STATUS  mandatory
        DESCRIPTION
                "The number of samples in a running average. A value
                of 1 indicates no running average."
        ::= { fhTrapDashboardControlEntry 6 }


temperatureCriticalTrapThreshold OBJECT-TYPE
        SYNTAX  INTEGER
        ACCESS  read-write
        STATUS  mandatory
        DESCRIPTION
                "If the temperature in the switch rises above this
                value (in degrees Celsius, the temperatureCriticalTrap
                trap is generated, and the switch is shut down."
        ::= { crossfireAtmTrapControl 4 }


--
-- Traps section
--

restart TRAP-TYPE
        ENTERPRISE  ocmibsCrossfireAtmMIB
        VARIABLES   { termRestartInfoRestartTime,
                      termRestartInfoRestartReason,
                      termRestartInfoTerminationReason,
                      termRestartInfoBbsram }
        DESCRIPTION
                "The switch has restarted."
    ::= 1

-- reload TRAP-TYPE         deleted
--	  ENTERPRISE  ocmibsCrossfireAtmMIB
--	  VARIABLES   { termRestartInfoReloadTime,
--			termRestartInfoBootpReason,
--			termRestartInfoServerIpAddress,
--			termRestartInfoServerMacAddress,
--			termRestartInfoFileName }
--	  DESCRIPTION
--		  "The software has been reloaded - either by the boot
--		  PROM or by the operational software."
--    ::= 2

globalCongestionTrap TRAP-TYPE
        ENTERPRISE  ocmibsCrossfireAtmMIB
        VARIABLES   { statsGlobalCongestionState,
                      statsGlobalCongestionDiscardCellRate,
                      controlTime }
        DESCRIPTION
                "The rate of globally discarded cells/second rises or
                falls above/below defined threshold."
    ::= 3

globalInvalidCellRateTrap TRAP-TYPE
        ENTERPRISE  ocmibsCrossfireAtmMIB
        VARIABLES   { statsInvalidCellRateState,
                      statsInvalidCellRate,
                      controlTime }
        DESCRIPTION
                "The rate of invalid cells/second is above the defined
                threshold."
    ::= 4

cpuPortCongestionTrap TRAP-TYPE
        ENTERPRISE  ocmibsCrossfireAtmMIB
        VARIABLES   { statsCpuPortCongestionState,
                      controlTime }
        DESCRIPTION
                "The number of cells in the switch processor queue
                is above the defined threshold."
    ::= 5

queueCongestionTrap TRAP-TYPE
        ENTERPRISE  ocmibsCrossfireAtmMIB
        VARIABLES   { statsQueueCongestionSlotIndex,
                      statsQueueCongestionIPortRIndex,
                      statsQueueCongestionQueueIndex,
                      statsQueueCongestionConditionState,
                      controlTime }
        DESCRIPTION
                "The number of cells in an iPort queue is above the
                defined threshold."
    ::= 6

ePortHecErrorRateTrap TRAP-TYPE
        ENTERPRISE  ocmibsCrossfireAtmMIB
        VARIABLES   { statsEPortIfIndex,
                      statusEPortXModuleIndex,
                      statusEPortRIndex,
                      statsEPortHecErrorRateConditionState,
                      statsEPortRxHecErrorCellRate,
                      controlTime }
        DESCRIPTION
                "The rate of HEC error cells/second is above the
                defined threshold."
    ::= 7

iPortTxParityErrorTrap TRAP-TYPE
        ENTERPRISE  ocmibsCrossfireAtmMIB
        VARIABLES   { statsIPortSlotIndex,
                      statsIPortRIndex,
                      statsIPortTxParityErrorCellCounter }
        DESCRIPTION
                "The rate of cell buffer memory parity errors is above
                the defined threshold."
    ::= 8

ePortAutoDisabled TRAP-TYPE
        ENTERPRISE  ocmibsCrossfireAtmMIB
        VARIABLES   { statusEPortIfIndex,
                      controlTime }
        DESCRIPTION
                "An ATM port has been automatically disabled due to a
                hardware failure."
    ::= 9

featureModuleStatusChange TRAP-TYPE
        ENTERPRISE  ocmibsCrossfireAtmMIB
        VARIABLES   { statusFeatureModuleOperStatus,
                      controlTime }
        DESCRIPTION
                "Informs the management station that an expected
                feature module is not present, the system will operate
                without a feature module."
    ::= 10

xModuleStatusChange TRAP-TYPE
        ENTERPRISE  ocmibsCrossfireAtmMIB
        VARIABLES   { statusXModuleSlotIndex,
                      statusXModuleOperStatus,
                      controlTime }
        DESCRIPTION
                "Informs the management station about a change in the
                state of an expansion module, e.g. when its state
                changes to failed, lost, disabledChanged, or
                disabledReplaced."
    ::= 11

temperatureWarningTrap TRAP-TYPE
        ENTERPRISE  ocmibsCrossfireAtmMIB
        VARIABLES   { statusCurrentTemperatureConditionState,
                      statusCurrentTemperatureGauge,
                      controlTime }
        DESCRIPTION
                "The temerature in the switch is above the defined
                threshold."
    ::= 12

fanFailureTrap TRAP-TYPE
        ENTERPRISE  ocmibsCrossfireAtmMIB
        VARIABLES   { statusFanOperStatus,
                      statusCurrentTemperatureGauge,
                      controlTime }
        DESCRIPTION
                "The fan has stopped working."
    ::= 13

psuFailureTrap TRAP-TYPE
        ENTERPRISE  ocmibsCrossfireAtmMIB
        VARIABLES   { statusPsuIndex,
                      statusPsuOperStatus,
                      controlTime }
        DESCRIPTION
                "A power supply has stopped working."
    ::= 14

temperatureCriticalTrap TRAP-TYPE
        ENTERPRISE  ocmibsCrossfireAtmMIB
        VARIABLES   { statusCurrentTemperatureConditionState,
                      statusCurrentTemperatureGauge,
                      controlTime }
        DESCRIPTION
                "The temperature has reached an unacceptable level.
                The switch will be shut down."
    ::= 15

oamFlowNoResponseTrap TRAP-TYPE
        ENTERPRISE  ocmibsCrossfireAtmMIB
        VARIABLES   { ifIndex, controlTime }
        DESCRIPTION
                "An F4 or F5 OAM cell was not returned within 5
                seconds."
    ::= 16

--END

-- xlx Section

-- ocAtm			OBJECT IDENTIFIER ::= { crossfirexlx 1 }
-- ocUni			OBJECT IDENTIFIER ::= { crossfirexlx 2 }
ocCNNI				OBJECT IDENTIFIER ::= { crossfirexlx 3 }
ocDsx3              OBJECT IDENTIFIER ::= { crossfirexlx 4 }

--        MIB-CNNI DEFINITIONS ::= BEGIN

--        IMPORTS
--                IpAddress, Counter
--                        FROM RFC1155-SMI
--                OBJECT-TYPE
--                        FROM RFC-1212
--                ocCNNI
--                        FROM CCOLICOM-MIB;

        -- XLX CNNI definitions


        -- CNNI Monitor simple objects


        ocCNNIMonSimple OBJECT-TYPE
                SYNTAX  SEQUENCE OF OcCNNIMonSEntry
                ACCESS  not-accessible
                STATUS  optional
                ::= { ocCNNI 1 }

        ocCNNIMonSEntry OBJECT-TYPE
                SYNTAX  OcCNNIMonSEntry
                ACCESS  not-accessible
                STATUS  optional
                INDEX   { ocCNNIApplID }
                ::= { ocCNNIMonSimple 1 }

        OcCNNIMonSEntry ::= SEQUENCE {
                ocCNNIRoutingTableChanged
                        INTEGER,
                ocCNNINeighborTableChanged
                        INTEGER,
                ocCNNILineStatus
                        OCTET STRING,
                ocCNNIMACAddress
                        OCTET STRING,
                ocCNNIMode
                        INTEGER,
                ocCNNIProtocolVersion
                        INTEGER,
                ocCNNIApplID
                        INTEGER
                }

        ocCNNIRoutingTableChanged OBJECT-TYPE
                SYNTAX  INTEGER {
                        no(0),
                        yes(1)
                        }
                ACCESS  read-only
                STATUS  optional
                ::= { ocCNNIMonSEntry 1 }

        ocCNNINeighborTableChanged OBJECT-TYPE
                SYNTAX  INTEGER {
                        no(0),
                        yes(1)
                        }
                ACCESS  read-only
                STATUS  optional
                ::= { ocCNNIMonSEntry 2 }

        ocCNNILineStatus OBJECT-TYPE
                SYNTAX  OCTET STRING
                ACCESS  read-only
                STATUS  optional
                ::= { ocCNNIMonSEntry 3 }

        ocCNNIMACAddress OBJECT-TYPE
                SYNTAX  OCTET STRING
                ACCESS  read-only
                STATUS  optional
                ::= { ocCNNIMonSEntry 4 }

        ocCNNIMode OBJECT-TYPE
                SYNTAX  INTEGER {
                        off(1),
                        on(2)
                        }
                ACCESS  read-only
                STATUS  optional
                ::= { ocCNNIMonSEntry 5 }

        ocCNNIProtocolVersion OBJECT-TYPE
                SYNTAX  INTEGER
                ACCESS  read-only
                STATUS  optional
                ::= { ocCNNIMonSEntry 6 }

        ocCNNIApplID OBJECT-TYPE
                SYNTAX  INTEGER
                ACCESS  read-only
                STATUS  optional
                ::= { ocCNNIMonSEntry 7 }

        -- CNNI Monitor tables

        ocCNNIMonTables OBJECT IDENTIFIER ::= { ocCNNI 2 }

        -- CNNI Monitor routing table

        ocCNNIRoutingTable OBJECT-TYPE
                SYNTAX  SEQUENCE OF OcCNNIRoutingTableEntry
                ACCESS  not-accessible
                STATUS  optional
                ::= { ocCNNIMonTables 1 }

        ocCNNIRoutingTableEntry OBJECT-TYPE
                SYNTAX  OcCNNIRoutingTableEntry
                ACCESS  not-accessible
                STATUS  optional
                INDEX   { ocCNNIApplID, ocCNNIAddress }
                ::= { ocCNNIRoutingTable 1 }

        OcCNNIRoutingTableEntry ::= SEQUENCE {
                ocCNNIAddress
                        OCTET STRING,
                ocCNNIRoutingTableData
                        OCTET STRING,
                ocCNNIAddressAlias
                        OCTET STRING
                }

        ocCNNIAddress OBJECT-TYPE
                SYNTAX  OCTET STRING
                ACCESS  read-only
                STATUS  optional
                ::= { ocCNNIRoutingTableEntry 1 }

        ocCNNIRoutingTableData OBJECT-TYPE
                SYNTAX  OCTET STRING
                ACCESS  read-only
                STATUS  optional
                ::= { ocCNNIRoutingTableEntry 2 }

        ocCNNIAddressAlias OBJECT-TYPE
                SYNTAX  OCTET STRING
                ACCESS  read-only
                STATUS  optional
                ::= { ocCNNIRoutingTableEntry 3 }

        -- CNNI Monitor neighbor table

        ocCNNINeighborTable OBJECT-TYPE
                SYNTAX  SEQUENCE OF OcCNNINeighborTableEntry
                ACCESS  not-accessible
                STATUS  optional
                ::= { ocCNNIMonTables 2 }

        ocCNNINeighborTableEntry OBJECT-TYPE
                SYNTAX  OcCNNINeighborTableEntry
                ACCESS  not-accessible
                STATUS  optional
                INDEX   { ocCNNIApplID, ocCNNIPort }
                ::= { ocCNNINeighborTable 1 }

        OcCNNINeighborTableEntry ::= SEQUENCE {
                ocCNNIPort
                        INTEGER,
                ocCNNINeighborTableData
                        OCTET STRING
                }

        ocCNNIPort OBJECT-TYPE
                SYNTAX  INTEGER
                ACCESS  read-only
                STATUS  optional
                ::= { ocCNNINeighborTableEntry 1 }

        ocCNNINeighborTableData OBJECT-TYPE
                SYNTAX  OCTET STRING
                ACCESS  read-only
                STATUS  optional
                ::= { ocCNNINeighborTableEntry 2 }

        -- CNNI Monitor trap client table

        ocCNNITrapClientTable OBJECT-TYPE
                SYNTAX  SEQUENCE OF OcCNNITrapClientTableEntry
                ACCESS  not-accessible
                STATUS  optional
                ::= { ocCNNIMonTables 3 }

        ocCNNITrapClientTableEntry OBJECT-TYPE
                SYNTAX  OcCNNITrapClientTableEntry
                ACCESS  not-accessible
                STATUS  optional
                INDEX   { ocCNNIApplID, ocCNNITrapClientAddress }
                ::= { ocCNNITrapClientTable 1 }

        OcCNNITrapClientTableEntry ::= SEQUENCE {
                ocCNNITrapClientIndex
                        OCTET STRING,
                ocCNNITrapClientAddress
                        IpAddress,
                ocCNNITrapClientCommName
                        OCTET STRING
                }

        ocCNNITrapClientIndex OBJECT-TYPE
                SYNTAX  OCTET STRING
                ACCESS  read-only
                STATUS  optional
                ::= { ocCNNITrapClientTableEntry 1 }

        ocCNNITrapClientAddress OBJECT-TYPE
                SYNTAX  IpAddress
                ACCESS  read-write
                STATUS  optional
                ::= { ocCNNITrapClientTableEntry 2 }

        ocCNNITrapClientCommName OBJECT-TYPE
                SYNTAX  OCTET STRING
                ACCESS  read-write
                STATUS  optional
                ::= { ocCNNITrapClientTableEntry 3 }

        -- general CNNI configuration objects

        ocCNNIConfig OBJECT IDENTIFIER ::= { ocCNNI 3 }

        ocCNNIConfigMethod OBJECT-TYPE
                SYNTAX  INTEGER {
                        first(0),
                        best(1) }
                ACCESS  read-write
                STATUS  optional
                DESCRIPTION
                        "An alorithm used by CNNI. First (0) means that the 
                        SETUP frame which arrives first is accepted, all 
                        consecutive are discarded.  Best (1) means that we 
                        delay the decision of accepting a SETUP frame for 
                        some time and accept the one that carries the 
                        smallest cost."
                ::= { ocCNNIConfig 1 }

        ocCNNIConfigAlgorithm OBJECT-TYPE
                SYNTAX  INTEGER
                ACCESS  read-write
                STATUS  optional
                DESCRIPTION
                        "An algorithm that is used to determine the cost of 
                        a SETUP frame if ocCNNIConfigMethod equals Best (1)."
                ::= { ocCNNIConfig 2 }

        -- CNNI port configuration objects

        ocCNNIPortConfig OBJECT-TYPE
                SYNTAX  SEQUENCE OF OcCNNIPortEntry
                ACCESS  not-accessible
                STATUS  optional
                DESCRIPTION
                        "A table of parameter information for CNNI ports."
                ::= { ocCNNI 4 }

        ocCNNIPortEntry OBJECT-TYPE
                SYNTAX  OcCNNIPortEntry
                ACCESS  not-accessible
                STATUS  optional
                DESCRIPTION
                        "An entry in the table, containing information about 
                        parameters for CNNI ports."
                INDEX   { ocCNNIPort }
                ::= { ocCNNIPortConfig 1 }

        OcCNNIPortEntry ::= SEQUENCE {
                ocCNNIPortProtocol
                        INTEGER,
                ocCNNIPortBorder
                        INTEGER,
                ocCNNIPortAutoreroute
                        INTEGER,
                ocCNNIPortReroute
                        INTEGER,
                ocCNNIPortAssign
                        INTEGER
                }

        ocCNNIPortProtocol OBJECT-TYPE
                SYNTAX  INTEGER {
                        cnni(0),
                        pnni(1),
                        none(2)
                        }
                ACCESS  read-write
                STATUS  optional
                DESCRIPTION
                        "Routing protocol used on an ATM port."
                ::= { ocCNNIPortEntry 1 }

        ocCNNIPortBorder OBJECT-TYPE
                SYNTAX  INTEGER {
                        no(0),
                        yes(1)
                        }
                ACCESS  read-write
                STATUS  optional
                DESCRIPTION
                        "Definition of a role this port has in CNNI cloud. 
                        no (0) means that it is connected to another device 
                        running CNNI.  yes (1) means it is connected to a 
                        non-CNNI device.  no (0) requires that 
                        atmfAtmLayerUniVersion equals NNI(6)."
                ::= { ocCNNIPortEntry 2 }

        ocCNNIPortAutoreroute OBJECT-TYPE
                SYNTAX  INTEGER {
                        no(0),
                        yes(1)
                        }
                ACCESS  read-write
                STATUS  optional
                DESCRIPTION
                        "An indication if all calls coming from this port 
                        should be automatically rerouted by CNNI if a path 
                        they are traversing becomes invalid.  Refers to UNI 
                        ports."
                ::= { ocCNNIPortEntry 3 }

        ocCNNIPortReroute OBJECT-TYPE
                SYNTAX  INTEGER {
                        no(0),
                        yes(1)
                        }
                ACCESS  read-write
                STATUS  optional
                DESCRIPTION
                        "An indication if a port should be considered an 
                        alternate path for automatic rerouting.  Refers to ports 
                        that have ocCNNIPortProtocol set to cnni (0)."
                ::= { ocCNNIPortEntry 4 }

        ocCNNIPortAssign OBJECT-TYPE
                SYNTAX  INTEGER {
                        no(0),
                        yes(1)
                        }
                ACCESS  read-write
                STATUS  optional
                DESCRIPTION
                        "Defines if CNNI should assign VPI/VCI identifiers for 
                        this port.  For CNNI link (ocCNNIPortProtocol set to 
                        cnni (0)) only one end should have it set to yes(1)."
                ::= { ocCNNIPortEntry 5 }

        -- general CNNI statistics

        ocCNNIGlobalStats OBJECT IDENTIFIER ::= { ocCNNI 5 }

        ocCNNIGlobalStatsTotal OBJECT-TYPE
                SYNTAX  Counter
                ACCESS  read-only
                STATUS  optional
                DESCRIPTION
                        "Total number of active switched connection 
                        established by CNNI."
                ::= { ocCNNIGlobalStats 1 }

        ocCNNIGlobalStatsCreated OBJECT-TYPE
                SYNTAX  Counter
                ACCESS  read-only
                STATUS  optional
                DESCRIPTION
                        "Number of connections set up by CNNI that are in 
                        CREATED phase."
                ::= { ocCNNIGlobalStats 2 }

        ocCNNIGlobalStatsOneWay OBJECT-TYPE
                SYNTAX  Counter
                ACCESS  read-only
                STATUS  optional
                DESCRIPTION
                        "Number of connections set up by CNNI that are in 
                        ONE WAY phase."
                ::= { ocCNNIGlobalStats 3 }

        ocCNNIGlobalStatsConnected OBJECT-TYPE
                SYNTAX  Counter
                ACCESS  read-only
                STATUS  optional
                DESCRIPTION
                        "Number of connections set up by CNNI that are in 
                        CONNECTED phase."
                ::= { ocCNNIGlobalStats 4 }

        ocCNNIGlobalStatsBrokenLeaf OBJECT-TYPE
                SYNTAX  Counter
                ACCESS  read-only
                STATUS  optional
                DESCRIPTION
                        "Number of connections set up by CNNI that are in 
                        BROKEN LEAF phase."
                ::= { ocCNNIGlobalStats 5 }

        ocCNNIGlobalStatsBrokenRoot OBJECT-TYPE
                SYNTAX  Counter
                ACCESS  read-only
                STATUS  optional
                DESCRIPTION
                        "Number of connections set up by CNNI that are in 
                        BROKEN ROOT phase."
                ::= { ocCNNIGlobalStats 6 }

        ocCNNIGlobalStatsRerouteWaiting OBJECT-TYPE
                SYNTAX  Counter
                ACCESS  read-only
                STATUS  optional
                DESCRIPTION
                        "Number of connections set up by CNNI that are in 
                        REROUTE WAITING phase."
                ::= { ocCNNIGlobalStats 7 }

        -- CNNI address statistics

        ocCNNIAddrStats OBJECT-TYPE
                SYNTAX  SEQUENCE OF OcCNNIAddrStatsEntry
                ACCESS  not-accessible
                STATUS  optional
                DESCRIPTION
                        "A table of CNNI statistics information for an ATM 
                        address."
                ::= { ocCNNI 6 }

        ocCNNIAddrStatsEntry OBJECT-TYPE
                SYNTAX  OcCNNIAddrStatsEntry
                ACCESS  not-accessible
                STATUS  optional
                DESCRIPTION
                        "An entry in a table of CNNI statistics information 
                        for an ATM address."
                INDEX   { ocCNNIAddress }
                ::= { ocCNNIAddrStats 1 }

        OcCNNIAddrStatsEntry ::= SEQUENCE {
                ocCNNIAddrStatsToTotal
                        Counter,
                ocCNNIAddrStatsToCreated
                        Counter,
                ocCNNIAddrStatsToOneWay
                        Counter,
                ocCNNIAddrStatsToConnected
                        Counter,
                ocCNNIAddrStatsToBrokenLeaf
                        Counter,
                ocCNNIAddrStatsToBrokenRoot
                        Counter,
                ocCNNIAddrStatsToRerouteWaiting
                        Counter,
                ocCNNIAddrStatsFromTotal
                        Counter,
                ocCNNIAddrStatsFromCreated
                        Counter,
                ocCNNIAddrStatsFromOneWay
                        Counter,
                ocCNNIAddrStatsFromConnected
                        Counter,
                ocCNNIAddrStatsFromBrokenLeaf
                        Counter,
                ocCNNIAddrStatsFromBrokenRoot
                        Counter,
                ocCNNIAddrStatsFromRerouteWaiting
                        Counter
                }

        ocCNNIAddrStatsToTotal OBJECT-TYPE
                SYNTAX  Counter
                ACCESS  read-only
                STATUS  optional
                DESCRIPTION
                        "Total number of active switched connection 
                        established by CNNI to this address."
                ::= { ocCNNIAddrStatsEntry 1 }

        ocCNNIAddrStatsToCreated OBJECT-TYPE
                SYNTAX  Counter
                ACCESS  read-only
                STATUS  optional
                DESCRIPTION
                        "Number of active switched connection set up by CNNI 
                        to this address that are in CREATED phase."
                ::= { ocCNNIAddrStatsEntry 2 }

        ocCNNIAddrStatsToOneWay OBJECT-TYPE
                SYNTAX  Counter
                ACCESS  read-only
                STATUS  optional
                DESCRIPTION
                        "Number of active switched connection set up by CNNI 
                        to this address that are in ONE WAY phase."
                ::= { ocCNNIAddrStatsEntry 3 }

        ocCNNIAddrStatsToConnected OBJECT-TYPE
                SYNTAX  Counter
                ACCESS  read-only
                STATUS  optional
                DESCRIPTION
                        "Number of active switched connection set up by CNNI 
                        to this address that are in CONNECTED phase."
                ::= { ocCNNIAddrStatsEntry 4 }

        ocCNNIAddrStatsToBrokenLeaf OBJECT-TYPE
                SYNTAX  Counter
                ACCESS  read-only
                STATUS  optional
                DESCRIPTION
                        "Number of active switched connection set up by CNNI 
                        to this address that are in BROKEN LEAF phase."
                ::= { ocCNNIAddrStatsEntry 5 }

        ocCNNIAddrStatsToBrokenRoot OBJECT-TYPE
                SYNTAX  Counter
                ACCESS  read-only
                STATUS  optional
                DESCRIPTION
                        "Number of active switched connection set up by CNNI 
                        to this address that are in BROKEN ROOT phase."
                ::= { ocCNNIAddrStatsEntry 6 }

        ocCNNIAddrStatsToRerouteWaiting OBJECT-TYPE
                SYNTAX  Counter
                ACCESS  read-only
                STATUS  optional
                DESCRIPTION
                        "Number of active switched connection set up by CNNI 
                        to this address that are in REROUTE WAITING phase."
                ::= { ocCNNIAddrStatsEntry 7 }

        ocCNNIAddrStatsFromTotal OBJECT-TYPE
                SYNTAX  Counter
                ACCESS  read-only
                STATUS  optional
                DESCRIPTION
                        "Total number of active switched connection set up by 
                        CNNI from this address."
                ::= { ocCNNIAddrStatsEntry 8 }

        ocCNNIAddrStatsFromCreated OBJECT-TYPE
                SYNTAX  Counter
                ACCESS  read-only
                STATUS  optional
                DESCRIPTION
                        "Number of active switched connection set up by CNNI 
                        from this address that are in CREATED phase."
                ::= { ocCNNIAddrStatsEntry 9 }

        ocCNNIAddrStatsFromOneWay OBJECT-TYPE
                SYNTAX  Counter
                ACCESS  read-only
                STATUS  optional
                DESCRIPTION
                        "Number of active switched connection set up by CNNI 
                        from this address that are in ONE WAY phase."
                ::= { ocCNNIAddrStatsEntry 10 }

        ocCNNIAddrStatsFromConnected OBJECT-TYPE
                SYNTAX  Counter
                ACCESS  read-only
                STATUS  optional
                DESCRIPTION
                        "Number of active switched connection set up by CNNI 
                        from this address that are in CONNECTED phase."
                ::= { ocCNNIAddrStatsEntry 11 }

        ocCNNIAddrStatsFromBrokenLeaf OBJECT-TYPE
                SYNTAX  Counter
                ACCESS  read-only
                STATUS  optional
                DESCRIPTION
                        "Number of active switched connection set up by CNNI 
                        from this address that are in BROKEN LEAF phase."
                ::= { ocCNNIAddrStatsEntry 12 }

        ocCNNIAddrStatsFromBrokenRoot OBJECT-TYPE
                SYNTAX  Counter
                ACCESS  read-only
                STATUS  optional
                DESCRIPTION
                        "Number of active switched connection set up by CNNI 
                        from this address that are in BROKEN ROOT phase."
                ::= { ocCNNIAddrStatsEntry 13 }

        ocCNNIAddrStatsFromRerouteWaiting OBJECT-TYPE
                SYNTAX  Counter
                ACCESS  read-only
                STATUS  optional
                DESCRIPTION
                        "Number of active switched connection set up by CNNI 
                        from this address that are in REROUTE WAITING phase."
                ::= { ocCNNIAddrStatsEntry 14 }

        -- CNNI alias table

        ocCNNIAliasTable OBJECT-TYPE
                SYNTAX  SEQUENCE OF OcCNNIAliasTableEntry
                ACCESS  not-accessible
                STATUS  optional
                DESCRIPTION
                        "A table of symbolic names assigned to ATM addresses."
                ::= { ocCNNI 7 }

        ocCNNIAliasTableEntry OBJECT-TYPE
                SYNTAX  OcCNNIAliasTableEntry
                ACCESS  not-accessible
                STATUS  optional
                DESCRIPTION
                        "An entry in a table of symbolic names assigned to 
                        ATM addresses."
                INDEX   { ocCNNIAddress }
                ::= { ocCNNIAliasTable 1 }

        OcCNNIAliasTableEntry ::= SEQUENCE {
                ocCNNIAlias
                        OCTET STRING
                }

        ocCNNIAlias OBJECT-TYPE
                SYNTAX  OCTET STRING
                ACCESS  read-write
                STATUS  optional
                DESCRIPTION
                        "A symbolic name assigned to an ATM address.  It can 
                        be 15 characters long max."
                ::= { ocCNNIAliasTableEntry 1 }

        -- CNNI connection database browsing

        ocCNNIConnDB OBJECT IDENTIFIER ::= { ocCNNI 8 }


        -- a) assigning empty filter identifier

        ocCNNIFilterAssignID OBJECT-TYPE
                SYNTAX  INTEGER
                ACCESS  read-only
                STATUS  optional
                DESCRIPTION
                        "First empty slot in CNNI filter table.  The NMS 
                        station should obtain it first, before setting filter 
                        parameters."
                ::= { ocCNNIConnDB 1 }

        -- b) filter definition
        
        ocCNNIFilterTable OBJECT-TYPE
                SYNTAX  SEQUENCE OF OcCNNIFilterTableEntry
                ACCESS  not-accessible
                STATUS  optional
                DESCRIPTION
                        "Table of filters defined for tracing signalling 
                        messages."
                ::= { ocCNNIConnDB 2 }

        ocCNNIFilterTableEntry OBJECT-TYPE
                SYNTAX  OcCNNIFilterTableEntry
                ACCESS  not-accessible
                STATUS  optional
                DESCRIPTION
                        "Entry in a table of filters for tracing signalling 
                        messages."
                INDEX   { ocCNNIFilterID }
                ::= { ocCNNIFilterTable 1 }

        OcCNNIFilterTableEntry ::= SEQUENCE {
                ocCNNIFilterID
                        INTEGER,
                ocCNNIFilterTypePres
                        INTEGER,
                ocCNNIFilterTypeData
                        INTEGER,
                ocCNNIFilterInPortPres
                        INTEGER,
                ocCNNIFilterInPortData
                        INTEGER,
                ocCNNIFilterOutPortPres
                        INTEGER,
                ocCNNIFilterOutPortData
                        INTEGER,
                ocCNNIFilterCgPtyPres
                        INTEGER,
                ocCNNIFilterCgPtyData
                        OCTET STRING,
                ocCNNIFilterCdPtyPres
                        INTEGER,
                ocCNNIFilterCdPtyData
                        OCTET STRING,
                ocCNNIFilterStatePres
                        INTEGER,
                ocCNNIFilterStateData
                        INTEGER
                }

        ocCNNIFilterID OBJECT-TYPE
                SYNTAX  INTEGER
                ACCESS  read-only
                STATUS  optional
                DESCRIPTION
                        "Unique identificator of a filter."
                ::= { ocCNNIFilterTableEntry 1 }

        ocCNNIFilterTypePres OBJECT-TYPE
                SYNTAX  INTEGER {
                        notpresent(0),  
                        present(1)
                        }
                ACCESS  read-write
                STATUS  optional
                DESCRIPTION
                        "Indicates if a connection type field is present in 
                        the filter definition."
                ::= { ocCNNIFilterTableEntry 2 }

        ocCNNIFilterTypeData OBJECT-TYPE
                SYNTAX  INTEGER {
                        pointtopoint(0),
                        pointtomulitpoint(1)
                        }
                ACCESS  read-write
                STATUS  optional
                DESCRIPTION
                        "Connection type field in the filter definition. 
                        This field has any meaning only if 
                        ocCNNIFilterTypePres is set to present (1)."
                ::= { ocCNNIFilterTableEntry 3 }

        ocCNNIFilterInPortPres OBJECT-TYPE
                SYNTAX  INTEGER {
                        notpresent(0),  
                        present(1)
                        }
                ACCESS  read-write
                STATUS  optional
                DESCRIPTION
                        "Indicates if a incoming port field is present in the 
                        filter definition."
                ::= { ocCNNIFilterTableEntry 4 }

        ocCNNIFilterInPortData OBJECT-TYPE
                SYNTAX  INTEGER
                ACCESS  read-write
                STATUS  optional
                DESCRIPTION
                        "Incoming port field in the filter definition. 
                        This field has any meaning only if 
                        ocCNNIFilterInPortPres is set to present (1)."
                ::= { ocCNNIFilterTableEntry 5 }

        ocCNNIFilterOutPortPres OBJECT-TYPE
                SYNTAX  INTEGER {
                        notpresent(0),  
                        present(1)
                        }
                ACCESS  read-write
                STATUS  optional
                DESCRIPTION
                        "Indicates if a outgoing port field is present in the 
                        filter definition."
                ::= { ocCNNIFilterTableEntry 6 }

        ocCNNIFilterOutPortData OBJECT-TYPE
                SYNTAX  INTEGER
                ACCESS  read-write
                STATUS  optional
                DESCRIPTION
                        "Outgoing port field in the filter definition. 
                        This field has any meaning only if 
                        ocCNNIFilterOutPortPres is set to present (1)."
                ::= { ocCNNIFilterTableEntry 7 }

        ocCNNIFilterCgPtyPres OBJECT-TYPE
                SYNTAX  INTEGER {
                        notpresent(0),  
                        present(1)
                        }
                ACCESS  read-write
                STATUS  optional
                DESCRIPTION
                        "Indicates if a calling party field is present in the 
                        filter definition."
                ::= { ocCNNIFilterTableEntry 8 }

        ocCNNIFilterCgPtyData OBJECT-TYPE
                SYNTAX  OCTET STRING
                ACCESS  read-write
                STATUS  optional
                DESCRIPTION
                        "Calling party field in the filter definition. 
                        This field has any meaning only if 
                        ocCNNIFilterCgPtyPres is set to present (1)."
                ::= { ocCNNIFilterTableEntry 9 }

        ocCNNIFilterCdPtyPres OBJECT-TYPE
                SYNTAX  INTEGER {
                        notpresent(0),  
                        present(1)
                        }
                ACCESS  read-write
                STATUS  optional
                DESCRIPTION
                        "Indicates if a called party field is present in the 
                        filter definition."
                ::= { ocCNNIFilterTableEntry 10 }

        ocCNNIFilterCdPtyData OBJECT-TYPE
                SYNTAX  OCTET STRING
                ACCESS  read-write
                STATUS  optional
                DESCRIPTION
                        "Called party field in the filter definition. 
                        This field has any meaning only if 
                        ocCNNIFilterCdPtyPres is set to present (1)."
                ::= { ocCNNIFilterTableEntry 11 }

        ocCNNIFilterStatePres OBJECT-TYPE
                SYNTAX  INTEGER {
                        notpresent(0),  
                        present(1)
                        }
                ACCESS  read-write
                STATUS  optional
                DESCRIPTION
                        "Indicates if a connection phase field is present in 
                        the filter definition."
                ::= { ocCNNIFilterTableEntry 12 }

        ocCNNIFilterStateData OBJECT-TYPE
                SYNTAX  INTEGER {
                        created(0),
                        oneway(1),
                        connected(2),
                        brokenroot(3),
                        brokenleaf(4),
                        reroutewaiting(5)
                        }
                ACCESS  read-write
                STATUS  optional
                DESCRIPTION
                        "Connection state field in the filter definition. 
                        This field has any meaning only if 
                        ocCNNIFilterStatePres is set to present (1)."
                ::= { ocCNNIFilterTableEntry 13 }

        -- c) connection data
        
        ocCNNISessTable OBJECT-TYPE
                SYNTAX  SEQUENCE OF OcCNNISessTableEntry
                ACCESS  not-accessible
                STATUS  optional
                DESCRIPTION
                        "Table containing info about session data.  In order 
                        to read from this table one must first define a filter 
                        using ocCNNIFilterTable."
                ::= { ocCNNIConnDB 3 }

        ocCNNISessTableEntry OBJECT-TYPE
                SYNTAX  OcCNNISessTableEntry
                ACCESS  not-accessible
                STATUS  optional
                DESCRIPTION
                        "An entry in a table containing info about session 
                        data."
                INDEX   { ocCNNIFilterID, ocCNNISessID }
                ::= { ocCNNISessTable 1 }

        OcCNNISessTableEntry ::= SEQUENCE {
                ocCNNISessID
                        INTEGER,
                ocCNNISessDataType
                        INTEGER,
                ocCNNISessDataInPort
                        INTEGER,
                ocCNNISessDataOutPort
                        INTEGER,
                ocCNNISessDataCgPty
                        OCTET STRING,
                ocCNNISessDataCdPty
                        OCTET STRING,
                ocCNNISessDataState
                        INTEGER
                }

        ocCNNISessID OBJECT-TYPE
                SYNTAX  INTEGER
                ACCESS  read-only
                STATUS  optional
                DESCRIPTION
                        "A unique session identifier."
                ::= { ocCNNISessTableEntry 1 }

        ocCNNISessDataType OBJECT-TYPE
                SYNTAX  INTEGER {
                        pointtopoint(0),
                        pointtomulitpoint(1)
                        }
                ACCESS  read-only
                STATUS  optional
                DESCRIPTION
                        "Connection type: pointtopoint (0) or 
                        pointtomultipoint (1)."
                ::= { ocCNNISessTableEntry 2 }

        ocCNNISessDataInPort OBJECT-TYPE
                SYNTAX  INTEGER
                ACCESS  read-only
                STATUS  optional
                DESCRIPTION
                        "Incoming port (a port from which we received a SETUP 
                        frame that was accepted)."
                ::= { ocCNNISessTableEntry 3 }

        ocCNNISessDataOutPort OBJECT-TYPE
                SYNTAX  INTEGER
                ACCESS  read-only
                STATUS  optional
                DESCRIPTION
                        "Outgoing port (a port to which we sent a SETUP frame 
                        that was accepted)."
                ::= { ocCNNISessTableEntry 4 }

        ocCNNISessDataCgPty OBJECT-TYPE
                SYNTAX  OCTET STRING
                ACCESS  read-only
                STATUS  optional
                DESCRIPTION
                        "ATM address of a calling party."
                ::= { ocCNNISessTableEntry 5 }

        ocCNNISessDataCdPty OBJECT-TYPE
                SYNTAX  OCTET STRING
                ACCESS  read-only
                STATUS  optional
                DESCRIPTION
                        "ATM address of a called party."
                ::= { ocCNNISessTableEntry 6 }

        ocCNNISessDataState OBJECT-TYPE
                SYNTAX  INTEGER {
                        created(0),
                        oneway(1),
                        connected(2),
                        brokenroot(3),
                        brokenleaf(4),
                        reroutewaiting(5)
                        }
                ACCESS  read-only
                STATUS  optional
                DESCRIPTION
                        "State of the connection."
                ::= { ocCNNISessTableEntry 7 }

        --END

--        MIB-OCDS3 DEFINITIONS ::= BEGIN


--        IMPORTS
--                OBJECT-TYPE
--                        FROM RFC-1212
--                dsx3LineIndex
--                        FROM RFC1407-MIB

--v2    DESCRIPTION
--v2            "This is the Olicom MIB extensions for RFC1407."
--                ocDsx3
--                        FROM Olicom-crossfireAtmSwitch-MIB;

        ocDsx3MIBObjs  OBJECT IDENTIFIER ::= {ocDsx3 1}



        -- This DS3 MIB Module consists of the following groups:
        -- (1) ccDsx3ConfigTable for customize configuration parameters
        -- (2) ccDsx3SuniPdhStats error counts from DS3 chip



        ocDsx3ConfigTable OBJECT-TYPE
                SYNTAX  SEQUENCE OF OcDsx3ConfigEntry
                ACCESS  not-accessible
                STATUS  mandatory
                DESCRIPTION
                        "The Olicom extensions to the
                        DS3/E3 Configuration table."
                ::= { ocDsx3MIBObjs 1 }


        ocDsx3ConfigEntry OBJECT-TYPE
                SYNTAX  OcDsx3ConfigEntry
                ACCESS  not-accessible
                STATUS  mandatory
                DESCRIPTION
                        "An entry in the DS3/E3 Configuration table."
                INDEX   { dsx3LineIndex }
                ::= { ocDsx3ConfigTable 1 }


        OcDsx3ConfigEntry ::= SEQUENCE {
                ocDsx3Xor55
                        INTEGER,
                ocDsx3Scrambling
                        INTEGER,
                ocDsx3Delineation
                        INTEGER,
                ocDsx3HcsPassThru
                        INTEGER,
                ocDsx3Ext8kRefClk
                        INTEGER,
                ocDsx3ShortCable
                        INTEGER,
                ocDsx3CntHcsCorrectedErrs
                        INTEGER
                }



        ocDsx3Xor55 OBJECT-TYPE
                SYNTAX  INTEGER {
                        enabled(1),
                        disabled(2)
                        }
                ACCESS  read-write
                STATUS  mandatory
                DESCRIPTION
                        "This tests the FIFO data path between the
                        the ATM layer, Atomizer and PHY/TC layer.
                        Normally this option is disabled. "
                ::= { ocDsx3ConfigEntry 1 }



        ocDsx3Scrambling OBJECT-TYPE
                SYNTAX  INTEGER {
                        enabled(1),
                        disabled(2)
                        }
                ACCESS  read-write
                STATUS  mandatory
                DESCRIPTION
                        "Scrambles the cell payload using a self
                        synchronizing scrambler with an XX^43+1.
                        Required by ITU-T in I.432
                        Not used on ATMF UNI DS3 interface, but may
                        be required in future."
                ::= { ocDsx3ConfigEntry 2 }


        ocDsx3Delineation OBJECT-TYPE
                SYNTAX  INTEGER {
                        hec(1),
                        plcp(2)
                        }
                ACCESS  read-write
                STATUS  mandatory
                DESCRIPTION
                        "Provides ATM cell delineation based on the
                        cell HEC byte or by the PLCP direct based
                        mapping of ATM cells into the DS3 payload
                        envelopes. Normally PLCP delineation is used."
                ::= { ocDsx3ConfigEntry 3 }


        ocDsx3HcsPassThru OBJECT-TYPE
                SYNTAX  INTEGER {
                        enabled(1),
                        disabled(2)
                        }
                ACCESS  read-write
                STATUS  mandatory
                DESCRIPTION
                        "Allows cells with detected HCS errors to
                        pass to the receive FIFO. This is ussually
                        disabled. "
                ::= { ocDsx3ConfigEntry 4 }


        ocDsx3Ext8kRefClk OBJECT-TYPE
                SYNTAX  INTEGER {
                        enabled-master(1),
                        disabled(2),
                        slave(3)
                        }
                ACCESS  read-write
                STATUS  mandatory
                DESCRIPTION
                        "The option selects an internal frame
                        reference clock. When the interface is used
                        to source line timing, this reference clock
                        should be active. On an XLX one of the four
                        ports of an adapter may be used as the master
                        supplier or source of the clock, and the
                        other 3 can reference the master's clock as
                        slaves."
                ::= { ocDsx3ConfigEntry 5 }


        ocDsx3ShortCable OBJECT-TYPE
                SYNTAX  INTEGER {
                        enabled(1),
                        disabled(2)
                        }
                ACCESS  read-write
                STATUS  mandatory
                DESCRIPTION
                        "If the coaxial cables attached to the DS3
                        interface are 225 feet or less, select the
                        short. If length is greater than 225 feet
                        do not select short. This selection changes
                        the DS3 Line build-out characteristics. Do
                        not use cables longer than 450 feet. Cable
                        type should be good quality RG-59/U. This is
                        75 ohm coax. Do not us 50 ohm coax, such as
                        that used for Ethernet applications."
                ::= { ocDsx3ConfigEntry 6 }


        ocDsx3CntHcsCorrectedErrs OBJECT-TYPE
                SYNTAX  INTEGER {
                        enabled(1),
                        disabled(2)
                        }
                ACCESS  read-write
                STATUS  mandatory
                DESCRIPTION
                        "If this parameter is enabled(1) the CPPM HCS
                        counter will count the number of correctable
                        header checksum errors. If disabled(1) the
                        CPPM HCS counter will count the number of
                        uncorrectable HCS errors."
                ::= { ocDsx3ConfigEntry 7 }


        ocDsx3SuniPdhTable OBJECT-TYPE
                SYNTAX  SEQUENCE OF OcDsx3SuniPdhEntry
                ACCESS  not-accessible
                STATUS  mandatory
                DESCRIPTION
                        "The Olicom extensions to the
                        DS3/E3 Configuration table."
                ::= { ocDsx3MIBObjs 2 }

        ocDsx3SuniPdhEntry OBJECT-TYPE
                SYNTAX  OcDsx3SuniPdhEntry
                ACCESS  not-accessible
                STATUS  mandatory
                DESCRIPTION
                        "An entry in the DS3/E3 Configuration table."
                INDEX   { dsx3LineIndex }
                ::= { ocDsx3SuniPdhTable 1 }



        OcDsx3SuniPdhEntry ::= SEQUENCE {
                ocDsx3SuniPmonLcv
                        INTEGER,
                ocDsx3SuniPmonFerr
                        INTEGER,
                ocDsx3SuniPmonExzs
                        INTEGER,
                ocDsx3SuniPmonPeec
                        INTEGER,
                ocDsx3SuniPmonPpec
                        INTEGER,
                ocDsx3SuniPmonFebeErr
                        INTEGER,
                ocDsx3SuniB1Bip8Err
                        INTEGER,
                ocDsx3SuniCppmFrameErr
                        INTEGER,
                ocDsx3SuniCppmFebeErr
                        INTEGER,
                ocDsx3SuniCppmHcsErr
                        INTEGER,
                ocDsx3SuniCppmRcvCells
                        INTEGER,
                ocDsx3SuniCppmXmtCells
                        INTEGER,
                ocDsx3SuniCppmIdleCells
                        INTEGER,
                ocDsx3SuniCppmMegaRcvCells
                        INTEGER,
                ocDsx3SuniCppmMegaXmtCells
                        INTEGER,
                ocDsx3SuniCppmMegaIdleCells
                        INTEGER
                }


        ocDsx3SuniPmonLcv OBJECT-TYPE
                SYNTAX  INTEGER
                ACCESS  read-only
                STATUS  mandatory
                DESCRIPTION
                        "Represents the number of Line Code
                        Violations since last polled."
                ::= { ocDsx3SuniPdhEntry 1 }


        ocDsx3SuniPmonFerr OBJECT-TYPE
                SYNTAX  INTEGER
                ACCESS  read-only
                STATUS  mandatory
                DESCRIPTION
                        "Represents the number of DS3 F and M bit
                        errors since last polled."
                ::= { ocDsx3SuniPdhEntry 2 }


        ocDsx3SuniPmonExzs OBJECT-TYPE
                SYNTAX  INTEGER
                ACCESS  read-only
                STATUS  mandatory
                DESCRIPTION
                        "Represents the number of summed excessivce
                        zeros that occured during the previous
                        accumulation period. One or more excessive
                        zeros occurrence withan an 85 bit DS3
                        information block is counterd as one summed
                        excessive zero."
                ::= { ocDsx3SuniPdhEntry 3 }


        ocDsx3SuniPmonPeec OBJECT-TYPE
                SYNTAX  INTEGER
                ACCESS  read-only
                STATUS  mandatory
                DESCRIPTION
                        "Represents the number of DS3 P bits errors
                        that have been detected since last polled."
                ::= { ocDsx3SuniPdhEntry 4 }


        ocDsx3SuniPmonPpec OBJECT-TYPE
                SYNTAX  INTEGER
                ACCESS  read-only
                STATUS  mandatory
                DESCRIPTION
                        "Represents the number of DS3 path parity
                        errprs that have been detected since
                        last polled."
                ::= { ocDsx3SuniPdhEntry 5 }


        ocDsx3SuniPmonFebeErr OBJECT-TYPE
                SYNTAX  INTEGER
                ACCESS  read-only
                STATUS  mandatory
                DESCRIPTION
                        "Represents the number of DS3 far end block
                        errors that have been detected since last
                        polled."
                ::= { ocDsx3SuniPdhEntry 6 }


        ocDsx3SuniB1Bip8Err OBJECT-TYPE
                SYNTAX  INTEGER
                ACCESS  read-only
                STATUS  mandatory
                DESCRIPTION
                        "Represents the number of B1 Bit-Interleaved
                        Parity (BIP8) errors since last polled."
                ::= { ocDsx3SuniPdhEntry 7 }

        ocDsx3SuniCppmFrameErr OBJECT-TYPE
                SYNTAX  INTEGER
                ACCESS  read-only
                STATUS  mandatory
                DESCRIPTION
                        "Represents the number of PLCP frame errors
                        that have occurred since last polled."
                ::= { ocDsx3SuniPdhEntry 8 }

        ocDsx3SuniCppmFebeErr OBJECT-TYPE
                SYNTAX  INTEGER
                ACCESS  read-only
                STATUS  mandatory
                DESCRIPTION
                        "Represent the number of PLCP Far End Block
                        Errors since last polled."
                ::= { ocDsx3SuniPdhEntry 9 }

        ocDsx3SuniCppmHcsErr OBJECT-TYPE
                SYNTAX  INTEGER
                ACCESS  read-only
                STATUS  mandatory
                DESCRIPTION
                        "If the ocDsx3CntHcsCorrectedErrs is enabled
                        this counter represents the number of
                        correctable Header Checksum errors that
                        have occurred since last polled.
                        If the ocDsx3CntHcsCorrectedErrs is disabled
                        this counter represents the number of
                        uncorrectable Header Checksum errors that
                        have occurred since last polled. "
                ::= { ocDsx3SuniPdhEntry 10 }


        ocDsx3SuniCppmRcvCells OBJECT-TYPE
                SYNTAX  INTEGER
                ACCESS  read-only
                STATUS  mandatory
                DESCRIPTION
                        "Represents the number of cells received
                        by the PHY device since power on."
                ::= { ocDsx3SuniPdhEntry 11 }

        ocDsx3SuniCppmXmtCells OBJECT-TYPE
                SYNTAX  INTEGER
                ACCESS  read-only
                STATUS  mandatory
                DESCRIPTION
                        "Represents the number of cells transmitted
                        by the PHY device since power on."
                ::= { ocDsx3SuniPdhEntry 12 }

        ocDsx3SuniCppmIdleCells OBJECT-TYPE
                SYNTAX  INTEGER
                ACCESS  read-only
                STATUS  mandatory
                DESCRIPTION
                        "Represents the number of received idle
                        cells by the PHY device since power on."
                ::= { ocDsx3SuniPdhEntry 13 }

        ocDsx3SuniCppmMegaRcvCells OBJECT-TYPE
                SYNTAX  INTEGER
                ACCESS  read-only
                STATUS  mandatory
                DESCRIPTION
                        "Represents the millions of cells received
                        by the PHY device since power on."
                ::= { ocDsx3SuniPdhEntry 14 }

        ocDsx3SuniCppmMegaXmtCells OBJECT-TYPE
                SYNTAX  INTEGER
                ACCESS  read-only
                STATUS  mandatory
                DESCRIPTION
                        "Represents the millions of cells transmitted
                        by the PHY device since power on."
                ::= { ocDsx3SuniPdhEntry 15 }

        ocDsx3SuniCppmMegaIdleCells OBJECT-TYPE
                SYNTAX  INTEGER
                ACCESS  read-only
                STATUS  mandatory
                DESCRIPTION
                        "Represents the millions of received idle
                        cells by the PHY device since power on."
                ::= { ocDsx3SuniPdhEntry 16 }

--        END

END
