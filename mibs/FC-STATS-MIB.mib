FC-STATS-MIB DEFINITIONS ::= BEGIN

-- Title:       FastComm Communications Adapter MIB in concise format
-- Version      5.0.4
-- Date:        September 30, 2000

-- Copyright 1993,1994,1995,1996,1997,1998 FastComm Communications, Inc. 
-- All Rights Reserved.  Reproduction of this document is authorized 
-- on condition that the foregoing copyright notice is included.
-- This FastComm SNMP Management Information Base Specification
-- (Specification) embodies FastComm's confidential and proprietary
-- intellectual property.  FastComm retains all title and ownership 
-- in the Specification, including any revisions.  
--
-- It is FastComm's intent to encourage the widespread use of this
-- Specification in connection with the management of FastComm
-- products. FastComm grants vendors, end-users, and other interested 
-- parties a non-exclusive license to use this Specification in 
-- connection with the management of FastComm products.
--
-- This Specification is supplied "AS IS," and FastComm makes no
-- warranty, either express or implied, as to the use, operation, 
-- condition, or performance of the Specification.


IMPORTS
	fsStats
		FROM FC-FASTC-MIB
	Counter, IpAddress
		FROM RFC1155-SMI
	OBJECT-TYPE
		FROM RFC-1212
	DisplayString FROM SNMPv2-TC;

fsFrameRelayStats             OBJECT IDENTIFIER ::= { fsStats 1 }
fsAsyncEncapsulationStats     OBJECT IDENTIFIER ::= { fsStats 2 }
fsBitSyncEncapsulationStats   OBJECT IDENTIFIER ::= { fsStats 3 }
fsSlipStats                   OBJECT IDENTIFIER ::= { fsStats 6 }
fsRipRoutingStats			OBJECT IDENTIFIER ::= { fsStats 8 }
fsAsyncBurosEmulationStats    OBJECT IDENTIFIER ::= { fsStats 9 }
fsSyncBurosEmulationStats     OBJECT IDENTIFIER ::= { fsStats 10 }
fsSdlcRoutingStats            OBJECT IDENTIFIER ::= { fsStats 11 }
fsByteSyncEncapsulationStats  OBJECT IDENTIFIER ::= { fsStats 12 }
fsTelnetTerminalStats         OBJECT IDENTIFIER ::= { fsStats 13 }
fsIpxStats                    OBJECT IDENTIFIER ::= { fsStats 15 }
fsALCStats                    OBJECT IDENTIFIER ::= { fsStats 17 }
fsTokenStats                  OBJECT IDENTIFIER ::= { fsStats 18 }    
fsEtherStats			OBJECT IDENTIFIER ::= { fsStats 20 }               
fsIPStats                     OBJECT IDENTIFIER ::= { fsStats 30 }
fsICMPStats                   OBJECT IDENTIFIER ::= { fsStats 31 }
fsUDPStats                    OBJECT IDENTIFIER ::= { fsStats 32 }
fsTCPStats                    OBJECT IDENTIFIER ::= { fsStats 33 }
fsSNMPStats                   OBJECT IDENTIFIER ::= { fsStats 34 }
fsNetLoaderStats              OBJECT IDENTIFIER ::= { fsStats 35 }
fsPriorityStats               OBJECT IDENTIFIER ::= { fsStats 38 }
fsSdlc2Stats              	OBJECT IDENTIFIER ::= { fsStats 39 }
fsLlcStats                	OBJECT IDENTIFIER ::= { fsStats 40 }
fsSnaSwStats               	OBJECT IDENTIFIER ::= { fsStats 41 }
fsT1DsuStats			OBJECT IDENTIFIER ::= { fsStats 43 }
fsE1DsuStats			OBJECT IDENTIFIER ::= { fsStats 44 }
fsX25NewStats                 OBJECT IDENTIFIER ::= { fsStats 46 }
fsXPadStats                   OBJECT IDENTIFIER ::= { fsStats 47 }
fsISDNStats				OBJECT IDENTIFIER ::= { fsStats 51 }
fsIpFilteringStats		OBJECT IDENTIFIER ::= { fsStats 52 }
fsNewPPPStats                 OBJECT IDENTIFIER ::= { fsStats 53 }
fsMLPStats                    OBJECT IDENTIFIER ::= { fsStats 54 }
fsTrigStats                   OBJECT IDENTIFIER ::= { fsStats 55 }
fsVoiceStats                  OBJECT IDENTIFIER ::= { fsStats 56 }

-- ***************************************************************************
-- Frame Relay Stats

fsFrameRelayTable OBJECT-TYPE
	SYNTAX  SEQUENCE OF FsFrameRelayEntry
	ACCESS  not-accessible
	STATUS  mandatory
	DESCRIPTION  ""
	::= { fsFrameRelayStats 1 }

	FsFrameRelayEntry ::= SEQUENCE {
		fsFrameRelayPortIndex               INTEGER,
		fsFrameRelayMngtProtocol	 	DisplayString,
		fsFrameRelayMngtStatus          	INTEGER,
		fsFrameRelayTotalFramesRx       	Counter,
		fsFrameRelayTotalFramesTx       	Counter,
		fsFrameRelayMngtFramesRx        	Counter,
		fsFrameRelayMngtFramesRxError   	Counter,
		fsFrameRelayMngtFramesTx        	Counter,
		fsFrameRelayRxNonRoutableIP     	Counter,
		fsFrameRelayRxNonRoutableIPX    	Counter,
		fsFrameRelayRxNonRoutableEncaps 	Counter,
		fsFrameRelayRxUnknownFrameType  	Counter,
		fsFrameRelayRxInactiveDLCIs     	Counter,
		fsFrameRelayTxInactiveDLCIs     	Counter,
		fsFrameRelayLastInvalidDLCI     	INTEGER
		}

	fsFrameRelayEntry OBJECT-TYPE
		SYNTAX  FsFrameRelayEntry
		ACCESS  not-accessible
		STATUS  mandatory
		DESCRIPTION ""
		INDEX { fsFrameRelayPortIndex }
		::= { fsFrameRelayTable 1 }

	fsFrameRelayPortIndex OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-only
		STATUS  mandatory
		DESCRIPTION ""
		::= { fsFrameRelayEntry 1 }

	fsFrameRelayMngtProtocol OBJECT-TYPE
		SYNTAX  DisplayString (SIZE (0..25))
		ACCESS  read-only
		STATUS  mandatory
		DESCRIPTION "Management protocol selected for Frame Relay."
		::= { fsFrameRelayEntry 2 }

	fsFrameRelayMngtStatus OBJECT-TYPE
		SYNTAX  INTEGER {
			none                    (0),
			receivingPolls       	(1),
			notReceivingPolls    	(2),
			respondingToPolls    	(3),
			notRespondingToPolls 	(4)
			}
		ACCESS  read-only
		STATUS  mandatory
		DESCRIPTION "Status of the Frame Relay port. In its default 
			       state as Frame Relay User, the FRAD initates 
				 polling to the switch, and the switch responds. 
				 Receiving Polls means that the FRAD is receiving 
				 a response from the switch.  If the FRAD has been 
				 configured as a switch Frame Relay Network, it 
				 should be responding To Polls from a user device."
		::= { fsFrameRelayEntry 3 }

	fsFrameRelayTotalFramesRx OBJECT-TYPE
		SYNTAX  Counter
		ACCESS  read-only
		STATUS  mandatory
		DESCRIPTION "Total Number of incoming DATA frames on 
				 the Frame Relay port."
		::= { fsFrameRelayEntry 4 }

	fsFrameRelayTotalFramesTx OBJECT-TYPE
		SYNTAX  Counter
		ACCESS  read-only
		STATUS  mandatory
		DESCRIPTION "Total Number of outgoing DATA frames on the 
			       Frame Relay port. This count excludes management 
				 frames."
		::= { fsFrameRelayEntry 5 }

	fsFrameRelayMngtFramesRx OBJECT-TYPE
		SYNTAX  Counter
		ACCESS  read-only
		STATUS  mandatory
		DESCRIPTION "Total number of Frame Relay management frames 
				 received."
		::= { fsFrameRelayEntry 6 }

	fsFrameRelayMngtFramesRxError OBJECT-TYPE
		SYNTAX  Counter
		ACCESS  read-only
		STATUS  mandatory
		DESCRIPTION "Total number of Frame Relay management frames 
				 received in error."
		::= { fsFrameRelayEntry 7 }

	fsFrameRelayMngtFramesTx OBJECT-TYPE
		SYNTAX  Counter
		ACCESS  read-only
		STATUS  mandatory
		DESCRIPTION "Total number of Frame Relay management frames sent."
		::= { fsFrameRelayEntry 8 }

	fsFrameRelayRxNonRoutableIP OBJECT-TYPE
		SYNTAX  Counter
		ACCESS  read-only
		STATUS  mandatory
		DESCRIPTION "IP frames received and discarded because their 
				 route could not be determined."
		::= { fsFrameRelayEntry 9 }

	fsFrameRelayRxNonRoutableIPX OBJECT-TYPE
		SYNTAX  Counter
		ACCESS  read-only
		STATUS  mandatory
		DESCRIPTION "IPX frames received and discarded because their 
				 route could not be determined."
		::= { fsFrameRelayEntry 10 }

	fsFrameRelayRxNonRoutableEncaps OBJECT-TYPE
		SYNTAX  Counter
		ACCESS  read-only
		STATUS  mandatory
		DESCRIPTION "Frames received on an Encapsulation DLCI and 
				 discarded because the destination port is not 
				 configured for that protocol."
		::= { fsFrameRelayEntry 11 }

	fsFrameRelayRxUnknownFrameType OBJECT-TYPE
		SYNTAX  Counter
		ACCESS  read-only
		STATUS  mandatory
		DESCRIPTION "Frames received and discarded because the 
				 type of protocol was unknown."
		::= { fsFrameRelayEntry 12 }

	fsFrameRelayRxInactiveDLCIs OBJECT-TYPE
		SYNTAX  Counter
		ACCESS  read-only
		STATUS  mandatory
		DESCRIPTION "Frames received and discarded because the 
				 DLCIs were not configured in the FRAD."
		::= { fsFrameRelayEntry 13 }

	fsFrameRelayTxInactiveDLCIs OBJECT-TYPE
		SYNTAX  Counter
		ACCESS  read-only
		STATUS  mandatory
		DESCRIPTION "Number of transmit frames discarded because 
				 a device attached to the FRAD attempted to send 
				 data using a DLCI that was not assigned by the 
				 carrier to the circuit, or it is inactive."
		::= { fsFrameRelayEntry 14 }

	fsFrameRelayLastInvalidDLCI OBJECT-TYPE
		SYNTAX  INTEGER (16..1007)
		ACCESS  read-write
		STATUS  mandatory
		DESCRIPTION "Last received DLCI that is not configured on this FRAD."
		::= { fsFrameRelayEntry 15 }


-- ***************************************************************************
-- Async Encapsulation Stats

fsAsyncEncapsTable OBJECT-TYPE
	SYNTAX  SEQUENCE OF FsAsyncEncapsEntry
	ACCESS  not-accessible
	STATUS  mandatory
	DESCRIPTION  ""
	::= { fsAsyncEncapsulationStats 1 }

	FsAsyncEncapsEntry ::= SEQUENCE {
		fsAsyncEncapsPortIndex        INTEGER,
		fsAsyncEncapsRxBytes          Counter,
		fsAsyncEncapsTxBytes          Counter,
		fsAsyncEncapsRxBreak          Counter,
		fsAsyncEncapsRxParityErr      Counter,
		fsAsyncEncapsRxOverrun        Counter,
		fsAsyncEncapsRxFramingErr     Counter
		}

	fsAsyncEncapsEntry OBJECT-TYPE
		SYNTAX  FsAsyncEncapsEntry
		ACCESS  not-accessible
		STATUS  mandatory
		DESCRIPTION ""
		INDEX { fsAsyncEncapsPortIndex }
		::= { fsAsyncEncapsTable 1 }

	fsAsyncEncapsPortIndex OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-only
		STATUS  mandatory
		DESCRIPTION ""
		::= { fsAsyncEncapsEntry 1 }

	fsAsyncEncapsRxBytes OBJECT-TYPE
		SYNTAX  Counter
		ACCESS  read-only
		STATUS  mandatory
		DESCRIPTION "Number of incoming bytes."
		::= { fsAsyncEncapsEntry 2 }

	fsAsyncEncapsTxBytes OBJECT-TYPE
		SYNTAX  Counter
		ACCESS  read-only
		STATUS  mandatory
		DESCRIPTION "Number of outgoing bytes"
		::= { fsAsyncEncapsEntry 3 }

	fsAsyncEncapsRxBreak OBJECT-TYPE
		SYNTAX  Counter
		ACCESS  read-only
		STATUS  mandatory
		DESCRIPTION "Number of break characters received."
		::= { fsAsyncEncapsEntry 4 }

	fsAsyncEncapsRxParityErr OBJECT-TYPE
		SYNTAX  Counter
		ACCESS  read-only
		STATUS  mandatory
		DESCRIPTION "Received characters with parity errors."
		::= { fsAsyncEncapsEntry 5 }

	fsAsyncEncapsRxOverrun OBJECT-TYPE
		SYNTAX  Counter
		ACCESS  read-only
		STATUS  mandatory
		DESCRIPTION "Count of overrun errors on the receive port."
		::= { fsAsyncEncapsEntry 6 }

	fsAsyncEncapsRxFramingErr OBJECT-TYPE
		SYNTAX  Counter
		ACCESS  read-only
		STATUS  mandatory
		DESCRIPTION "Number of characters received with framing errors."
		::= { fsAsyncEncapsEntry 7 }


-- ***************************************************************************
-- Bit Synchronous Encapsulation Stats

fsBitSyncEncapsTable OBJECT-TYPE
	SYNTAX  SEQUENCE OF FsBitSyncEncapsEntry
	ACCESS  not-accessible
	STATUS  mandatory
	DESCRIPTION  ""
	::= { fsBitSyncEncapsulationStats 1 }

	FsBitSyncEncapsEntry ::= SEQUENCE {
		fsBitSyncEncapsPortIndex      INTEGER,
		fsBitSyncEncapsRxFrames       Counter,
		fsBitSyncEncapsTxFrames       Counter,
		fsBitSyncEncapsRxTooBig       Counter,
		fsBitSyncEncapsRxCrcError     Counter,
		fsBitSyncEncapsRxOverrun      Counter,
		fsBitSyncEncapsRxNonAligned   Counter,
		fsBitSyncEncapsRxAbort        Counter,
		fsBitSyncEncapsTxUnderrun     Counter
		}

	fsBitSyncEncapsEntry OBJECT-TYPE
		SYNTAX  FsBitSyncEncapsEntry
		ACCESS  not-accessible
		STATUS  mandatory
		DESCRIPTION ""
		INDEX { fsBitSyncEncapsPortIndex }
		::= { fsBitSyncEncapsTable 1 }

	fsBitSyncEncapsPortIndex OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-only
		STATUS  mandatory
		DESCRIPTION ""
		::= { fsBitSyncEncapsEntry 1 }

	fsBitSyncEncapsRxFrames OBJECT-TYPE
		SYNTAX  Counter
		ACCESS  read-only
		STATUS  mandatory
		DESCRIPTION "Number of incoming frames."
		::= { fsBitSyncEncapsEntry 2 }

	fsBitSyncEncapsTxFrames OBJECT-TYPE
		SYNTAX  Counter
		ACCESS  read-only
		STATUS  mandatory
		DESCRIPTION "Number of outgoing frames."
		::= { fsBitSyncEncapsEntry 3 }

	fsBitSyncEncapsRxTooBig OBJECT-TYPE
		SYNTAX  Counter
		ACCESS  read-only
		STATUS  mandatory
		DESCRIPTION "Frame length greater than maximum allowed (4K bytes)."
		::= { fsBitSyncEncapsEntry 4 }

	fsBitSyncEncapsRxCrcError OBJECT-TYPE
		SYNTAX  Counter
		ACCESS  read-only
		STATUS  mandatory
		DESCRIPTION "Receiver Cyclic Redundancy Check errors."
		::= { fsBitSyncEncapsEntry 5 }

	fsBitSyncEncapsRxOverrun OBJECT-TYPE
		SYNTAX  Counter
		ACCESS  read-only
		STATUS  mandatory
		DESCRIPTION "Count of overrun errors occurred on the receive port."
		::= { fsBitSyncEncapsEntry 6 }

	fsBitSyncEncapsRxNonAligned OBJECT-TYPE
		SYNTAX  Counter
		ACCESS  read-only
		STATUS  mandatory
		DESCRIPTION "NonOctet Aligned frames received."
		::= { fsBitSyncEncapsEntry 7 }

	fsBitSyncEncapsRxAbort OBJECT-TYPE
		SYNTAX  Counter
		ACCESS  read-only
		STATUS  mandatory
		DESCRIPTION "Count of Receiver Abort messages received."
		::= { fsBitSyncEncapsEntry 8 }

	fsBitSyncEncapsTxUnderrun OBJECT-TYPE
		SYNTAX  Counter
		ACCESS  read-only
		STATUS  mandatory
		DESCRIPTION "Number of transmit underrun errors."
		::= { fsBitSyncEncapsEntry 9 }

-- ***************************************************************************
-- SLIP Stats

fsSlipTable OBJECT-TYPE
	SYNTAX  SEQUENCE OF FsSlipEntry
	ACCESS  not-accessible
	STATUS  mandatory
	DESCRIPTION  ""
	::= { fsSlipStats 1 }

	FsSlipEntry ::= SEQUENCE {
		fsSlipPortIndex           INTEGER,
		fsSlipRxFrames            Counter,
		fsSlipTxFrames            Counter,
		fsSlipRxNonRoutableFrames Counter,
		fsSlipRxBreak             Counter,
		fsSlipRxParityErr         Counter,
		fsSlipRxOverrun           Counter,
		fsSlipRxFramingErr        Counter
		}

	fsSlipEntry OBJECT-TYPE
		SYNTAX  FsSlipEntry
		ACCESS  not-accessible
		STATUS  mandatory
		DESCRIPTION ""
		INDEX { fsSlipPortIndex }
		::= { fsSlipTable 1 }

	fsSlipPortIndex OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-only
		STATUS  mandatory
		DESCRIPTION "SLIP port number."
		::= { fsSlipEntry 1 }

	fsSlipRxFrames OBJECT-TYPE
		SYNTAX  Counter
		ACCESS  read-only
		STATUS  mandatory
		DESCRIPTION "Total number of frames received."
		::= { fsSlipEntry 2 }

	fsSlipTxFrames OBJECT-TYPE
		SYNTAX  Counter
		ACCESS  read-only
		STATUS  mandatory
		DESCRIPTION "Total number of frames sent."
		::= { fsSlipEntry 3 }

	fsSlipRxNonRoutableFrames OBJECT-TYPE
		SYNTAX  Counter
		ACCESS  read-only
		STATUS  mandatory
		DESCRIPTION "This is the total number of frames discarded 
				 because their routing could not be determined."
		::= { fsSlipEntry 4 }

	fsSlipRxBreak OBJECT-TYPE
		SYNTAX  Counter
		ACCESS  read-only
		STATUS  mandatory
		DESCRIPTION "Number of Break characters received."
		::= { fsSlipEntry 5 }

	fsSlipRxParityErr OBJECT-TYPE
		SYNTAX  Counter
		ACCESS  read-only
		STATUS  mandatory
		DESCRIPTION "Total number of parity errors received."
		::= { fsSlipEntry 6 }

	fsSlipRxOverrun OBJECT-TYPE
		SYNTAX  Counter
		ACCESS  read-only
		STATUS  mandatory
		DESCRIPTION "Total number of receiver overruns."
		::= { fsSlipEntry 7 }

	fsSlipRxFramingErr OBJECT-TYPE
		SYNTAX  Counter
		ACCESS  read-only
		STATUS  mandatory
		DESCRIPTION "Total number of framing errors."
		::= { fsSlipEntry 8 }

-- ***************************************************************************
-- Rip Routing Stats

fsRipRoutingTable OBJECT-TYPE
	SYNTAX  SEQUENCE OF FsRipRoutingEntry
	ACCESS  not-accessible
	STATUS  mandatory
	DESCRIPTION  ""
	::= { fsRipRoutingStats 1 }

	FsRipRoutingEntry ::= SEQUENCE {
		fsRipRoutingTableIndex        INTEGER,
		fsRipRoutingNetwork           IpAddress,
	  	fsRipRoutingMask              IpAddress,
		fsRipRoutingGateway           IpAddress,
		fsRipRoutingHops              INTEGER,
    		fsRipRoutingTimer             INTEGER,
		fsRipRoutingPort              DisplayString,
		fsRipRoutingDlci              INTEGER
		}

	fsRipRoutingEntry OBJECT-TYPE
		SYNTAX  FsRipRoutingEntry
		ACCESS  not-accessible
		STATUS  mandatory
		DESCRIPTION ""
		INDEX { fsRipRoutingTableIndex }
		::= { fsRipRoutingTable 1 }

	fsRipRoutingTableIndex OBJECT-TYPE
		SYNTAX  INTEGER 
		ACCESS  read-only
		STATUS  mandatory
		DESCRIPTION ""
		::= { fsRipRoutingEntry 1 }

	fsRipRoutingNetwork OBJECT-TYPE
		SYNTAX  IpAddress 
		ACCESS  read-only
		STATUS  mandatory
		DESCRIPTION "Destination Network address."
		::= { fsRipRoutingEntry 2 }

	fsRipRoutingMask OBJECT-TYPE
		SYNTAX  IpAddress 
		ACCESS  read-only
		STATUS  mandatory
		DESCRIPTION "Subnet mask for destination network."
		::= { fsRipRoutingEntry 3 }

	fsRipRoutingGateway OBJECT-TYPE
		SYNTAX  IpAddress 
		ACCESS  read-only
		STATUS  mandatory
		DESCRIPTION "IP Address of next hop gateway (all 0s indicates 
				 a network directly attached to the FRAD)."
		::= { fsRipRoutingEntry 4 }

	fsRipRoutingHops OBJECT-TYPE
		SYNTAX  INTEGER 
		ACCESS  read-only
		STATUS  mandatory
		DESCRIPTION "Number of links from the FRAD to the network."
		::= { fsRipRoutingEntry 5 }

	fsRipRoutingTimer OBJECT-TYPE
		SYNTAX  INTEGER 
		ACCESS  read-only
		STATUS  mandatory
		DESCRIPTION "Maximum number of hops."
		::= { fsRipRoutingEntry 6 }

	fsRipRoutingPort OBJECT-TYPE
		SYNTAX  DisplayString (SIZE (1..8))
		ACCESS  read-only
		STATUS  mandatory
		DESCRIPTION "Local Port on the FRAD being used to access network."
		::= { fsRipRoutingEntry 7 }

	fsRipRoutingDlci OBJECT-TYPE
		SYNTAX  INTEGER (16..1007)
		ACCESS  read-only
		STATUS  mandatory
		DESCRIPTION "For Frame Relay port, the DLCI to get to the network."
		::= { fsRipRoutingEntry 8 }


-- ***************************************************************************
-- Async Buros Emulation Stats

fsAsyncBurosTable OBJECT-TYPE
	SYNTAX  SEQUENCE OF FsAsyncBurosEntry
	ACCESS  not-accessible
	STATUS  mandatory
	DESCRIPTION  ""
	::= { fsAsyncBurosEmulationStats 1 }

	FsAsyncBurosEntry ::= SEQUENCE {
		fsAsyncBurosPortIndex           INTEGER,
		fsAsyncBurosRxNoSession         Counter,
		fsAsyncBurosTxTimeouts          Counter,
		fsAsyncBurosRxBreak             Counter,
		fsAsyncBurosRxParityErr         Counter,
		fsAsyncBurosRxOverrun           Counter,
		fsAsyncBurosRxFramingErr        Counter
		}

	fsAsyncBurosEntry OBJECT-TYPE
		SYNTAX  FsAsyncBurosEntry
		ACCESS  not-accessible
		STATUS  mandatory
		DESCRIPTION ""
		INDEX { fsAsyncBurosPortIndex }
		::= { fsAsyncBurosTable 1 }

	fsAsyncBurosPortIndex OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-only
		STATUS  mandatory
		DESCRIPTION ""
		::= { fsAsyncBurosEntry 1 }

	fsAsyncBurosRxNoSession OBJECT-TYPE
		SYNTAX  Counter
		ACCESS  read-only
		STATUS  mandatory
		DESCRIPTION "Received frames discarded due to lack of connection."
		::= { fsAsyncBurosEntry 2 }

	fsAsyncBurosTxTimeouts OBJECT-TYPE
		SYNTAX  Counter
		ACCESS  read-only
		STATUS  mandatory
		DESCRIPTION "Transmitter timeouts issued because device is not responding."
		::= { fsAsyncBurosEntry 3 }

	fsAsyncBurosRxBreak OBJECT-TYPE
		SYNTAX  Counter
		ACCESS  read-only
		STATUS  mandatory
		DESCRIPTION "Number of break characters received."
		::= { fsAsyncBurosEntry 4 }

	fsAsyncBurosRxParityErr OBJECT-TYPE
		SYNTAX  Counter
		ACCESS  read-only
		STATUS  mandatory
		DESCRIPTION "Received characters with parity errors."
		::= { fsAsyncBurosEntry 5 }

	fsAsyncBurosRxOverrun OBJECT-TYPE
		SYNTAX  Counter
		ACCESS  read-only
		STATUS  mandatory
		DESCRIPTION "Count of overrun errors on the receive port."
		::= { fsAsyncBurosEntry 6 }

	fsAsyncBurosRxFramingErr OBJECT-TYPE
		SYNTAX  Counter
		ACCESS  read-only
		STATUS  mandatory
		DESCRIPTION "Number of characters received with framing errors."
		::= { fsAsyncBurosEntry 7 }

-- ***************************************************************************
-- Sync Buros Emulation Stats

fsSyncBurosTable OBJECT-TYPE
	SYNTAX  SEQUENCE OF FsSyncBurosEntry
	ACCESS  not-accessible
	STATUS  mandatory
	DESCRIPTION  ""
	::= { fsSyncBurosEmulationStats 1 }

	FsSyncBurosEntry ::= SEQUENCE {
		fsSyncBurosPortIndex           INTEGER,
		fsSyncBurosRxNoSession         Counter,
		fsSyncBurosTxTimeouts          Counter,
		fsSyncBurosRxParityError       Counter,
		fsSyncBurosRxOverrun           Counter,
		fsSyncBurosRxBcsError          Counter,
		fsSyncBurosTxUnderrun          Counter
		}

	fsSyncBurosEntry OBJECT-TYPE
		SYNTAX  FsSyncBurosEntry
		ACCESS  not-accessible
		STATUS  mandatory
		DESCRIPTION ""
		INDEX { fsSyncBurosPortIndex }
		::= { fsSyncBurosTable 1 }

	fsSyncBurosPortIndex OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-only
		STATUS  mandatory
		DESCRIPTION ""
		::= { fsSyncBurosEntry 1 }

	fsSyncBurosRxNoSession OBJECT-TYPE
		SYNTAX  INTEGER
		ACCESS  read-only
		STATUS  mandatory
		DESCRIPTION "Received frames discarded for lack of connection."
		::= { fsSyncBurosEntry 2 }

	fsSyncBurosTxTimeouts OBJECT-TYPE
		SYNTAX  INTEGER
		ACCESS  read-only
		STATUS  mandatory
		DESCRIPTION "Transmitter timeouts issued because device is not responding."
		::= { fsSyncBurosEntry 3 }

	fsSyncBurosRxParityError OBJECT-TYPE
		SYNTAX  Counter
		ACCESS  read-only
		STATUS  mandatory
		DESCRIPTION "Received characters with parity errors."
		::= { fsSyncBurosEntry 4 }

	fsSyncBurosRxOverrun OBJECT-TYPE
		SYNTAX  Counter
		ACCESS  read-only
		STATUS  mandatory
		DESCRIPTION "Count of overrun errors on the receive port."
		::= { fsSyncBurosEntry 5 }

	fsSyncBurosRxBcsError OBJECT-TYPE
		SYNTAX  Counter
		ACCESS  read-only
		STATUS  mandatory
		DESCRIPTION "Received frames with block check errors."
		::= { fsSyncBurosEntry 6 }

	fsSyncBurosTxUnderrun OBJECT-TYPE
		SYNTAX  Counter
		ACCESS  read-only
		STATUS  mandatory
		DESCRIPTION "Count of underrun errors occurred on the transmit port."
		::= { fsSyncBurosEntry 7 }

-- ***************************************************************************
-- SDLC Routing Stats

fsSdlcRoutingTable OBJECT-TYPE
	SYNTAX  SEQUENCE OF FsSdlcRoutingEntry
	ACCESS  not-accessible
	STATUS  mandatory
	DESCRIPTION  ""
	::= { fsSdlcRoutingStats 1 }

	FsSdlcRoutingEntry ::= SEQUENCE {
		fsSdlcRoutingPortIndex           INTEGER,
		fsSdlcRoutingRxNoAddress         INTEGER,
		fsSdlcRoutingRxTooBig            Counter,
		fsSdlcRoutingRxCrcError          Counter,
		fsSdlcRoutingRxOverrun           Counter,
		fsSdlcRoutingRxNonAligned        Counter,
		fsSdlcRoutingRxAbort             Counter,
		fsSdlcRoutingTxUnderrun          Counter
		}

	fsSdlcRoutingEntry OBJECT-TYPE
		SYNTAX  FsSdlcRoutingEntry
		ACCESS  not-accessible
		STATUS  mandatory
		DESCRIPTION ""
		INDEX { fsSdlcRoutingPortIndex }
		::= { fsSdlcRoutingTable 1 }

	fsSdlcRoutingPortIndex OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-only
		STATUS  mandatory
		DESCRIPTION ""
		::= { fsSdlcRoutingEntry 1 }

	fsSdlcRoutingRxNoAddress OBJECT-TYPE
		SYNTAX  INTEGER
		ACCESS  read-only
		STATUS  mandatory
		DESCRIPTION "Number of frames with undefined addresses."
		::= { fsSdlcRoutingEntry 2 }

	fsSdlcRoutingRxTooBig OBJECT-TYPE
		SYNTAX  Counter
		ACCESS  read-only
		STATUS  mandatory
		DESCRIPTION "Frames received with more bytes than specified 
				 maximum length of 4K butes."
		::= { fsSdlcRoutingEntry 3 }

	fsSdlcRoutingRxCrcError OBJECT-TYPE
		SYNTAX  Counter
		ACCESS  read-only
		STATUS  mandatory
		DESCRIPTION "Receiver Cyclic Redundancy Check errors."
		::= { fsSdlcRoutingEntry 4 }

	fsSdlcRoutingRxOverrun OBJECT-TYPE
		SYNTAX  Counter
		ACCESS  read-only
		STATUS  mandatory
		DESCRIPTION "Count of overrun errors occurred on the receive port."
		::= { fsSdlcRoutingEntry 5 }

	fsSdlcRoutingRxNonAligned OBJECT-TYPE
		SYNTAX  Counter
		ACCESS  read-only
		STATUS  mandatory
		DESCRIPTION "NonOctet Aligned frames received."
		::= { fsSdlcRoutingEntry 6 }

	fsSdlcRoutingRxAbort OBJECT-TYPE
		SYNTAX  Counter
		ACCESS  read-only
		STATUS  mandatory
		DESCRIPTION "Count of aborted frames received."
		::= { fsSdlcRoutingEntry 7 }

	fsSdlcRoutingTxUnderrun OBJECT-TYPE
		SYNTAX  Counter
		ACCESS  read-only
		STATUS  mandatory
		DESCRIPTION "Count of underrun errors which occurred 
				 on the transmit port."
		::= { fsSdlcRoutingEntry 8 }

-- ***************************************************************************
-- Byte Synchronous Encapsulation Stats

fsByteSyncEncapsTable OBJECT-TYPE
	SYNTAX  SEQUENCE OF FsByteSyncEncapsEntry
	ACCESS  not-accessible
	STATUS  mandatory
	DESCRIPTION  ""
	::= { fsByteSyncEncapsulationStats 1 }

	FsByteSyncEncapsEntry ::= SEQUENCE {
		fsByteSyncEncapsPortIndex           INTEGER,
		fsByteSyncEncapsRxMessages          Counter,
		fsByteSyncEncapsTxMessages          Counter
		}

	fsByteSyncEncapsEntry OBJECT-TYPE
		SYNTAX  FsByteSyncEncapsEntry
		ACCESS  not-accessible
		STATUS  mandatory
		DESCRIPTION ""
		INDEX { fsByteSyncEncapsPortIndex }
		::= { fsByteSyncEncapsTable 1 }

	fsByteSyncEncapsPortIndex OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-only
		STATUS  mandatory
		DESCRIPTION ""
		::= { fsByteSyncEncapsEntry 1 }

	fsByteSyncEncapsRxMessages OBJECT-TYPE
		SYNTAX  Counter
		ACCESS  read-only
		STATUS  mandatory
		DESCRIPTION "Number of incoming frames."
		::= { fsByteSyncEncapsEntry 2 }

	fsByteSyncEncapsTxMessages OBJECT-TYPE
		SYNTAX  Counter
		ACCESS  read-only
		STATUS  mandatory
		DESCRIPTION "Number of outgoing frames."
		::= { fsByteSyncEncapsEntry 3 }


-- ***************************************************************************
-- Telnet Terminal Stats

fsTelnetTermTable OBJECT-TYPE
	SYNTAX  SEQUENCE OF FsTelnetTermEntry
	ACCESS  not-accessible
	STATUS  mandatory
	DESCRIPTION  ""
	::= { fsTelnetTerminalStats 1 }

	FsTelnetTermEntry ::= SEQUENCE {
		fsTelnetTermPortIndex           INTEGER,
		fsTelnetTermRxBytes             Counter,
		fsTelnetTermTxBytes             Counter,
		fsTelnetTermSuccessfulConnects  Counter,
		fsTelnetTermFailedConnects      Counter,
		fsTelnetTermSuccessfulPings     Counter,
		fsTelnetTermFailedPings         Counter,
		fsTelnetTermRxBreak             Counter,
		fsTelnetTermRxParityErr         Counter,
		fsTelnetTermRxOverrun           Counter,
		fsTelnetTermRxFramingErr        Counter
		}

	fsTelnetTermEntry OBJECT-TYPE
		SYNTAX  FsTelnetTermEntry
		ACCESS  not-accessible
		STATUS  mandatory
		DESCRIPTION ""
		INDEX { fsTelnetTermPortIndex }
		::= { fsTelnetTermTable 1 }

	fsTelnetTermPortIndex OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-only
		STATUS  mandatory
		DESCRIPTION ""
		::= { fsTelnetTermEntry 1 }

	fsTelnetTermRxBytes OBJECT-TYPE
		SYNTAX  Counter
		ACCESS  read-only
		STATUS  mandatory
		DESCRIPTION "Number of incoming bytes."
		::= { fsTelnetTermEntry 2 }

	fsTelnetTermTxBytes OBJECT-TYPE
		SYNTAX  Counter
		ACCESS  read-only
		STATUS  mandatory
		DESCRIPTION "Number of outgoing bytes."
		::= { fsTelnetTermEntry 3 }

	fsTelnetTermSuccessfulConnects OBJECT-TYPE
		SYNTAX  Counter
		ACCESS  read-only
		STATUS  mandatory
		DESCRIPTION "Number of successful connections made."
		::= { fsTelnetTermEntry 4 }

	fsTelnetTermFailedConnects OBJECT-TYPE
		SYNTAX  Counter
		ACCESS  read-only
		STATUS  mandatory
		DESCRIPTION "Number of connection attempts that failed."
		::= { fsTelnetTermEntry 5 }

	fsTelnetTermSuccessfulPings OBJECT-TYPE
		SYNTAX  Counter
		ACCESS  read-only
		STATUS  mandatory
		DESCRIPTION "Number of PINGs that had responses."
		::= { fsTelnetTermEntry 6 }

	fsTelnetTermFailedPings OBJECT-TYPE
		SYNTAX  Counter
		ACCESS  read-only
		STATUS  mandatory
		DESCRIPTION "Number of PINGs that had no response."
		::= { fsTelnetTermEntry 7 }

	fsTelnetTermRxBreak OBJECT-TYPE
		SYNTAX  Counter
		ACCESS  read-only
		STATUS  mandatory
		DESCRIPTION "Number of break characters received."
		::= { fsTelnetTermEntry 8 }

	fsTelnetTermRxParityErr OBJECT-TYPE
		SYNTAX  Counter
		ACCESS  read-only
		STATUS  mandatory
		DESCRIPTION "Number of received parity errors."
		::= { fsTelnetTermEntry 9 }

	fsTelnetTermRxOverrun OBJECT-TYPE
		SYNTAX  Counter
		ACCESS  read-only
		STATUS  mandatory
		DESCRIPTION "Count of overrun errors on the receive port."
		::= { fsTelnetTermEntry 10 }

	fsTelnetTermRxFramingErr OBJECT-TYPE
		SYNTAX  Counter
		ACCESS  read-only
		STATUS  mandatory
		DESCRIPTION "Number of improper frames received."
		::= { fsTelnetTermEntry 11 }

-- ***************************************************************************
-- IPX RIP Table Stats

fsIpxRipTable OBJECT-TYPE
	SYNTAX  SEQUENCE OF FsIpxRipTableEntry
	ACCESS  not-accessible
	STATUS  mandatory
	DESCRIPTION  ""
	::= { fsIpxStats 1 }

	FsIpxRipTableEntry ::= SEQUENCE {
		fsIpxRipTableIndex    INTEGER,
		fsIpxRipNetwork       DisplayString,
		fsIpxRipHops          INTEGER,
		fsIpxRipPort          DisplayString,
		fsIpxRipDlci          INTEGER,
            fsIpxRipGptName       DisplayString
		}

	fsIpxRipTableEntry OBJECT-TYPE
		SYNTAX  FsIpxRipTableEntry
		ACCESS  not-accessible
		STATUS  mandatory
		DESCRIPTION ""
		INDEX { fsIpxRipTableIndex }
		::= { fsIpxRipTable 1 }

	fsIpxRipTableIndex OBJECT-TYPE
		SYNTAX  INTEGER (1..50)
		ACCESS  read-only
		STATUS  mandatory
		DESCRIPTION ""
		::= { fsIpxRipTableEntry 1 }

	fsIpxRipNetwork OBJECT-TYPE
		SYNTAX  DisplayString (SIZE (1..8))
		ACCESS  read-only
		STATUS  mandatory
		DESCRIPTION "IPX RIP network number."
		::= { fsIpxRipTableEntry 2 }

	fsIpxRipHops OBJECT-TYPE
		SYNTAX  INTEGER (1..255)
		ACCESS  read-only
		STATUS  mandatory
		DESCRIPTION "Number of hops to the network."
		::= { fsIpxRipTableEntry 3 }

	fsIpxRipPort OBJECT-TYPE
		SYNTAX  DisplayString (SIZE (1..8))
		ACCESS  read-only
		STATUS  mandatory
		DESCRIPTION "Port number."
		::= { fsIpxRipTableEntry 4 }

	fsIpxRipDlci OBJECT-TYPE
		SYNTAX  INTEGER (16..1007)
		ACCESS  read-only
		STATUS  mandatory
		DESCRIPTION "IPX RIP DLCI."
		::= { fsIpxRipTableEntry 5 }

	fsIpxRipGptName OBJECT-TYPE
		SYNTAX  DisplayString (SIZE (11))
		ACCESS  read-only
		STATUS  mandatory
		DESCRIPTION  ""
		::= { fsIpxRipTableEntry 6 }

-- ***************************************************************************
-- IPX SAP Table Stats

fsIpxSapTable OBJECT-TYPE
	SYNTAX  SEQUENCE OF FsIpxSapTableEntry
	ACCESS  not-accessible
	STATUS  mandatory
	DESCRIPTION  ""
	::= { fsIpxStats 2 }

	FsIpxSapTableEntry ::= SEQUENCE {
		fsIpxSapTableIndex    INTEGER,
		fsIpxSapType          DisplayString,
		fsIpxSapNetwork       DisplayString,
		fsIpxSapNode          DisplayString,
		fsIpxSapSocket        DisplayString,
		fsIpxSapHops          INTEGER,
		fsIpxSapName          DisplayString
		}

	fsIpxSapTableEntry OBJECT-TYPE
		SYNTAX  FsIpxSapTableEntry
		ACCESS  not-accessible
		STATUS  mandatory
		DESCRIPTION ""
		INDEX { fsIpxSapTableIndex }
		::= { fsIpxSapTable 1 }

	fsIpxSapTableIndex OBJECT-TYPE
		SYNTAX  INTEGER (1..7)
		ACCESS  read-only
		STATUS  mandatory
		DESCRIPTION ""
		::= { fsIpxSapTableEntry 1 }

	fsIpxSapType OBJECT-TYPE
		SYNTAX  DisplayString (SIZE (1..4))
		ACCESS  read-only
		STATUS  mandatory
		DESCRIPTION "Device type (i.e. server, printer)."
		::= { fsIpxSapTableEntry 2 }

	fsIpxSapNetwork OBJECT-TYPE
		SYNTAX  DisplayString (SIZE (1..8))
		ACCESS  read-only
		STATUS  mandatory
		DESCRIPTION "SAP network number."
		::= { fsIpxSapTableEntry 3 }

	fsIpxSapNode OBJECT-TYPE
		SYNTAX  DisplayString (SIZE (1..12))
		ACCESS  read-only
		STATUS  mandatory
		DESCRIPTION "SAP node number."
		::= { fsIpxSapTableEntry 4 }

	fsIpxSapSocket OBJECT-TYPE
		SYNTAX  DisplayString (SIZE (1..4))
		ACCESS  read-only
		STATUS  mandatory
		DESCRIPTION "SAP socket number."
		::= { fsIpxSapTableEntry 5 }

	fsIpxSapHops OBJECT-TYPE
		SYNTAX  INTEGER (1..255)
		ACCESS  read-only
		STATUS  mandatory
		DESCRIPTION "SAP hops."
		::= { fsIpxSapTableEntry 6 }

	fsIpxSapName OBJECT-TYPE
		SYNTAX  DisplayString (SIZE (1..30))
		ACCESS  read-only
		STATUS  mandatory
		DESCRIPTION "SAP device name."
		::= { fsIpxSapTableEntry 7 }

-- ***************************************************************************
-- ALC Stats

fsALCTable OBJECT-TYPE
	SYNTAX  SEQUENCE OF FsALCEntry
    	ACCESS  not-accessible
     	STATUS  mandatory
     	DESCRIPTION  ""
     	::= { fsALCStats 1 }

   	FsALCEntry ::= SEQUENCE {
      	fsALCPortIndex          INTEGER,
		fsALCResToPoll          INTEGER,
		fsALCNumPolls           Counter,
		fsALCResTimeOut         Counter,
		fsALCFrameRec           Counter,
		fsALCFrameTrans         Counter,
		fsALCCCCErrors          Counter,
		fsALCStreamDetect       INTEGER,
		fsALCAttemPollWhileRTS  Counter,
		fsALCLargeFrameRec      Counter
  		}

     	fsALCEntry OBJECT-TYPE
       	SYNTAX  FsALCEntry
            ACCESS  not-accessible
            STATUS  mandatory
            DESCRIPTION ""
            INDEX { fsALCPortIndex }
            ::= { fsALCTable 1 }

	fsALCPortIndex OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
         	ACCESS  read-only
            STATUS  mandatory
            DESCRIPTION ""
            ::= { fsALCEntry 1 }

     	fsALCResToPoll OBJECT-TYPE
         	SYNTAX  INTEGER {
            	no    (0),
                  yes   (1)
                  }
         	ACCESS  read-only
            STATUS  mandatory
            DESCRIPTION "Is there a response to the poll."
            ::= { fsALCEntry 2 }

    	fsALCNumPolls OBJECT-TYPE
 		SYNTAX  Counter
         	ACCESS  read-only
            STATUS  mandatory
            DESCRIPTION "Number of polls."
            ::= { fsALCEntry 3 }

    	fsALCResTimeOut OBJECT-TYPE
 		SYNTAX  Counter
          	ACCESS  read-only
            STATUS  mandatory
            DESCRIPTION "Number of response timeouts."
            ::= { fsALCEntry 4 }

    	fsALCFrameRec OBJECT-TYPE
 		SYNTAX  Counter
          	ACCESS  read-only
            STATUS  mandatory
            DESCRIPTION "Number of frames received."
            ::= { fsALCEntry 5 }

    	fsALCFrameTrans OBJECT-TYPE
 		SYNTAX  Counter
          	ACCESS  read-only
            STATUS  mandatory
            DESCRIPTION "Number of frames sent."
            ::= { fsALCEntry 6 }

    	fsALCCCCErrors OBJECT-TYPE
 		SYNTAX  Counter
            ACCESS  read-only
            STATUS  mandatory
            DESCRIPTION "Number of ALC CCC errors."
            ::= { fsALCEntry 7 }

   	fsALCStreamDetect OBJECT-TYPE
       	SYNTAX  INTEGER {
            	no    (0),
                  yes   (1)
                  }
            ACCESS  read-only
            STATUS  mandatory
            DESCRIPTION "Is the device streaming."
            ::= { fsALCEntry 8 }

   	fsALCAttemPollWhileRTS OBJECT-TYPE
 		SYNTAX  Counter
            ACCESS  read-only
            STATUS  mandatory
            DESCRIPTION "Streaming indication if yes."
            ::= { fsALCEntry 9 }

   	fsALCLargeFrameRec OBJECT-TYPE
 		SYNTAX  Counter
            ACCESS  read-only
            STATUS  mandatory
            DESCRIPTION "Number of frames received that were too big."
            ::= { fsALCEntry 10 }

-- ***************************************************************************
-- Token Ring Stats

fsTokenStatsTable OBJECT-TYPE
 	SYNTAX  SEQUENCE OF FsTokenStatsTableEntry
      ACCESS  not-accessible
      STATUS  mandatory
      DESCRIPTION  ""
      ::= { fsTokenStats 1 }

  	FsTokenStatsTableEntry ::= SEQUENCE {
		fsTokenStatsTableIndex  INTEGER,
		fsTokenRingState        INTEGER,
		fsTokenFrameRx          Counter,
		fsTokenIPFrameRx        Counter,
		fsTokenIPXFrameRx       Counter,
		fsTokenARPFrameRx       Counter,
		fsTokenFrameTx          Counter,
		fsTokenIPFrameTx        Counter,
		fsTokenIPXFrameTx       Counter,
		fsTokenARPFrameTx       Counter,
		fsTokenRxNonRoutable    Counter,
		fsTokenRxInvalid        Counter,
		fsTokenRxLowBuffer      Counter,
		fsTokenRxSouRouteBridge Counter,
		fsTokenTxInactive       Counter,
		fsTokenTxNoMACAddr      Counter
		}

  	fsTokenStatsTableEntry OBJECT-TYPE
       	SYNTAX  FsTokenStatsTableEntry
            ACCESS  not-accessible
            STATUS  mandatory
            DESCRIPTION ""
            INDEX { fsTokenStatsTableIndex }
            ::= { fsTokenStatsTable 1 }

	fsTokenStatsTableIndex OBJECT-TYPE
		SYNTAX  INTEGER 
		ACCESS  read-only
		STATUS  mandatory
		DESCRIPTION  ""
		::=  { fsTokenStatsTableEntry 1 }

	fsTokenRingState OBJECT-TYPE
		SYNTAX  INTEGER {
			idle        (1),
			init        (2),
			active      (3),
			failed      (4)
			}
		ACCESS  read-only
		STATUS  mandatory
		DESCRIPTION  "State of the token Ring interface 
				 (idle, initializing, active, failed)."
		::=  { fsTokenStatsTableEntry 2 }

	fsTokenFrameRx OBJECT-TYPE
		SYNTAX  Counter 
		ACCESS  read-only
		STATUS  mandatory
		DESCRIPTION  "Total number of frames received."
		::=  { fsTokenStatsTableEntry 3 }

	fsTokenIPFrameRx OBJECT-TYPE
		SYNTAX  Counter 
		ACCESS  read-only
		STATUS  mandatory
		DESCRIPTION  "Number of IP frames received on the Token Ring interface."
		::=  { fsTokenStatsTableEntry 4 }

	fsTokenIPXFrameRx OBJECT-TYPE
		SYNTAX  Counter 
		ACCESS  read-only
		STATUS  mandatory
		DESCRIPTION  "Number of IPX frames received on the Token Ring port."
		::=  { fsTokenStatsTableEntry 5 }

	fsTokenARPFrameRx OBJECT-TYPE
		SYNTAX  Counter 
		ACCESS  read-only
		STATUS  mandatory
		DESCRIPTION  "Number of ARPs received."
		::=  { fsTokenStatsTableEntry 6 }

	fsTokenFrameTx OBJECT-TYPE
		SYNTAX  Counter 
		ACCESS  read-only
		STATUS  mandatory
		DESCRIPTION  "Total number of frames sent."
		::=  { fsTokenStatsTableEntry 7 }

	fsTokenIPFrameTx OBJECT-TYPE
		SYNTAX  Counter 
		ACCESS  read-only
		STATUS  mandatory
		DESCRIPTION  "Number of IP frames sent."
		::=  { fsTokenStatsTableEntry 8 }

	fsTokenIPXFrameTx OBJECT-TYPE
		SYNTAX  Counter 
		ACCESS  read-only
		STATUS  mandatory
		DESCRIPTION  "Number of IPX frames sent."
		::=  { fsTokenStatsTableEntry 9 }

	fsTokenARPFrameTx OBJECT-TYPE
		SYNTAX  Counter 
		ACCESS  read-only
		STATUS  mandatory
		DESCRIPTION  "Number of ARP frames sent."
		::=  { fsTokenStatsTableEntry 10 }

	fsTokenRxNonRoutable OBJECT-TYPE
		SYNTAX  Counter 
		ACCESS  read-only
		STATUS  mandatory
		DESCRIPTION  "Number of frames discarded because their routing 
				  could not be determined."
		::=  { fsTokenStatsTableEntry 11 }

	fsTokenRxInvalid OBJECT-TYPE
		SYNTAX  Counter 
		ACCESS  read-only
		STATUS  mandatory
		DESCRIPTION  "Number of invalid frames received."
		::=  { fsTokenStatsTableEntry 12 }

	fsTokenRxLowBuffer OBJECT-TYPE
		SYNTAX  Counter 
		ACCESS  read-only
		STATUS  mandatory
		DESCRIPTION  "Number of low buffer messages received from the FRAD."
		::=  { fsTokenStatsTableEntry 13 }

	fsTokenRxSouRouteBridge OBJECT-TYPE
		SYNTAX  Counter 
		ACCESS  read-only
		STATUS  mandatory
		DESCRIPTION  ""
		::=  { fsTokenStatsTableEntry 14 }

	fsTokenTxInactive OBJECT-TYPE
		SYNTAX  Counter 
		ACCESS  read-only
		STATUS  mandatory
		DESCRIPTION  ""
		::=  { fsTokenStatsTableEntry 15 }

	fsTokenTxNoMACAddr OBJECT-TYPE
		SYNTAX  Counter 
		ACCESS  read-only
		STATUS  mandatory
		DESCRIPTION  "Number of frames received with no MAC address."
		::=  { fsTokenStatsTableEntry 16 }

-- ***************************************************************************
-- Ether Stats

fsEtherStatsTable OBJECT-TYPE
	SYNTAX  SEQUENCE OF FsEtherStatsTableEntry
	ACCESS  not-accessible
	STATUS  mandatory
	DESCRIPTION  ""
	::= { fsEtherStats 1 }

	FsEtherStatsTableEntry ::= SEQUENCE {
		fsEtherTableIndex             INTEGER,
		fsEtherFrameReceived          Counter,
		fsEtherIPReceived             Counter,
		fsEtherArpReceived            Counter,
		fsEtherFrameTrans             Counter,
		fsEtherIPTrans                Counter,
		fsEtherArpTrans               Counter,
		fsEtherBadMulticast           Counter,
		fsEtherNonRoutable            Counter,
		fsEtherInvalidType            Counter,
		fsEtherLowBuffer              Counter,
		fsEtherNoMACAddr              Counter
		}

	fsEtherStatsTableEntry OBJECT-TYPE	
		SYNTAX  FsEtherStatsTableEntry
		ACCESS  not-accessible
		STATUS  mandatory
		DESCRIPTION ""
		INDEX { fsEtherTableIndex }
		::= { fsEtherStatsTable 1 }

	fsEtherTableIndex OBJECT-TYPE
		SYNTAX  INTEGER
		ACCESS  read-only
		STATUS  mandatory
		DESCRIPTION ""
		::=  { fsEtherStatsTableEntry 1 }

	fsEtherFrameReceived OBJECT-TYPE
		SYNTAX  Counter
		ACCESS  read-only
		STATUS  mandatory
		DESCRIPTION "Total number of frames received."
		::= { fsEtherStatsTableEntry 2 }

	fsEtherIPReceived OBJECT-TYPE
		SYNTAX  Counter
		ACCESS  read-only
		STATUS  mandatory
		DESCRIPTION "Number of IP frames received."
		::= { fsEtherStatsTableEntry 3 }

	fsEtherArpReceived OBJECT-TYPE
		SYNTAX  Counter
		ACCESS  read-only
		STATUS  mandatory
		DESCRIPTION "Number of ARPs received."
		::= { fsEtherStatsTableEntry 4 }

	fsEtherFrameTrans OBJECT-TYPE
		SYNTAX  Counter
		ACCESS  read-only
		STATUS  mandatory
		DESCRIPTION "Total number of frames sent."
		::= { fsEtherStatsTableEntry 5 }

	fsEtherIPTrans OBJECT-TYPE
		SYNTAX  Counter
		ACCESS  read-only
		STATUS  mandatory
		DESCRIPTION "Total number of IP frames sent."
		::= { fsEtherStatsTableEntry 6 }

	fsEtherArpTrans OBJECT-TYPE
		SYNTAX  Counter
		ACCESS  read-only
		STATUS  mandatory
		DESCRIPTION "Number of ARPs sent."
		::= { fsEtherStatsTableEntry 7 }

	fsEtherBadMulticast OBJECT-TYPE
		SYNTAX  Counter
		ACCESS  read-only
		STATUS  mandatory
		DESCRIPTION ""
		::= { fsEtherStatsTableEntry 8 }

	fsEtherNonRoutable OBJECT-TYPE
		SYNTAX  Counter
		ACCESS  read-only
		STATUS  mandatory
		DESCRIPTION "Number of non-routable frames discarded."
		::= { fsEtherStatsTableEntry 9 }

	fsEtherInvalidType OBJECT-TYPE
		SYNTAX  Counter
		ACCESS  read-only
		STATUS  mandatory
		DESCRIPTION "Number of invalid frames detected."
		::= { fsEtherStatsTableEntry 10 }

	fsEtherLowBuffer OBJECT-TYPE
		SYNTAX  Counter
		ACCESS  read-only
		STATUS  mandatory
		DESCRIPTION "Number of low buffer messages received from the FRAD."
		::= { fsEtherStatsTableEntry 11 }

	fsEtherNoMACAddr OBJECT-TYPE
		SYNTAX  Counter
		ACCESS  read-only
		STATUS  mandatory
		DESCRIPTION "Number of frames received with no MAC address."
		::= { fsEtherStatsTableEntry 12 }


-- ***************************************************************************
-- IP Stats

fsIPStatsTable OBJECT-TYPE
	SYNTAX  SEQUENCE OF FsIPStatsTableEntry
	ACCESS  not-accessible
	STATUS  mandatory
	DESCRIPTION  ""
	::= { fsIPStats 1 }

	FsIPStatsTableEntry ::= SEQUENCE {
		fsIPStatsTableIndex           INTEGER,
		fsIPInMsgReceived             Counter,
		fsIPInMsgHeaderErr            Counter,
		fsIPInMsgUnsupport            Counter,
		fsIPInMsgToUpperLevel         Counter,
		fsIPOutMsgFromUpperLevel      Counter,
		fsIPOutMsgNoAvailBuffer       Counter,
		fsIPOutMsgErrDesRoute         Counter
		}

	fsIPStatsTableEntry OBJECT-TYPE	
		SYNTAX  FsIPStatsTableEntry
		ACCESS  not-accessible
		STATUS  mandatory
		DESCRIPTION ""
		INDEX { fsIPStatsTableIndex }
		::= { fsIPStatsTable 1 }

	fsIPStatsTableIndex OBJECT-TYPE
		SYNTAX  INTEGER
		ACCESS  read-only
		STATUS  mandatory
		DESCRIPTION ""
		::=  { fsIPStatsTableEntry 1 }

	fsIPInMsgReceived OBJECT-TYPE
		SYNTAX  Counter
		ACCESS  read-only
		STATUS  mandatory
		DESCRIPTION "Number of messages received by the local IP stack."
		::= { fsIPStatsTableEntry 2 }

	fsIPInMsgHeaderErr OBJECT-TYPE
		SYNTAX  Counter
		ACCESS  read-only
		STATUS  mandatory
		DESCRIPTION "Number of messages with header errors detected 
				 by the local stack."
		::= { fsIPStatsTableEntry 3 }

	fsIPInMsgUnsupport OBJECT-TYPE
		SYNTAX  Counter
		ACCESS  read-only
		STATUS  mandatory
		DESCRIPTION "Number of messages received by the local stack 
				 that are unsupported."
		::= { fsIPStatsTableEntry 4 }

	fsIPInMsgToUpperLevel OBJECT-TYPE
		SYNTAX  Counter
		ACCESS  read-only
		STATUS  mandatory
		DESCRIPTION "Number of messages receive by the local stack 
				 that were sent to upper levels."
		::= { fsIPStatsTableEntry 5 }

	fsIPOutMsgFromUpperLevel OBJECT-TYPE
		SYNTAX  Counter
		ACCESS  read-only
		STATUS  mandatory
		DESCRIPTION "Number of messages sent by the local stack."
		::= { fsIPStatsTableEntry 6 }

	fsIPOutMsgNoAvailBuffer OBJECT-TYPE
		SYNTAX  Counter
		ACCESS  read-only
		STATUS  mandatory
		DESCRIPTION "No buffer messages sent by the local stack."
		::= { fsIPStatsTableEntry 7 }

	fsIPOutMsgErrDesRoute OBJECT-TYPE
		SYNTAX  Counter
		ACCESS  read-only
		STATUS  mandatory
		DESCRIPTION "Routing errors."
		::= { fsIPStatsTableEntry 8 }


-- ***************************************************************************
-- ICMP Stats

fsICMPStatsTable OBJECT-TYPE
	SYNTAX  SEQUENCE OF FsICMPStatsTableEntry
	ACCESS  not-accessible
	STATUS  mandatory
	DESCRIPTION  ""
	::= { fsICMPStats 1 }

	FsICMPStatsTableEntry ::= SEQUENCE {
		fsICMPStatsTableIndex         INTEGER,
		fsICMPInMsgTotal              Counter,
		fsICMPInMsgErrReceived        Counter,
		fsICMPInMsgDesUnreach         Counter,
		fsICMPInMsgTimeExceed         Counter,
		fsICMPInMsgSourceQuench       Counter,
		fsICMPInMsgEchoMsg            Counter,
		fsICMPInMsgEchoReply          Counter,
		fsICMPOutMsgAttemptSent       Counter,
		fsICMPOutMsgErrNotSent        Counter,
		fsICMPOutMsgSourceQuenchSent  Counter,
		fsICMPOutMsgEchoReplySent     Counter,
		fsICMPOutMsgTimeExceedSent    Counter,
		fsICMPOutMsgDesUnreachSent    Counter
		}

	fsICMPStatsTableEntry OBJECT-TYPE	
		SYNTAX  FsICMPStatsTableEntry
		ACCESS  not-accessible
		STATUS  mandatory
		DESCRIPTION ""
		INDEX { fsICMPStatsTableIndex }
		::= { fsICMPStatsTable 1 }

	fsICMPStatsTableIndex OBJECT-TYPE
		SYNTAX  INTEGER
		ACCESS  read-only
		STATUS  mandatory
		DESCRIPTION ""
		::=  { fsICMPStatsTableEntry 1 }

	fsICMPInMsgTotal OBJECT-TYPE
		SYNTAX  Counter
		ACCESS  read-only
		STATUS  mandatory
		DESCRIPTION "Number of ICMP messages received by the local stack."
		::= { fsICMPStatsTableEntry 2 }

	fsICMPInMsgErrReceived OBJECT-TYPE
		SYNTAX  Counter
		ACCESS  read-only
		STATUS  mandatory
		DESCRIPTION "Number of ICMP messages received by the local stack 
				 that were in error."
		::= { fsICMPStatsTableEntry 3 }

	fsICMPInMsgDesUnreach OBJECT-TYPE
		SYNTAX  Counter
		ACCESS  read-only
		STATUS  mandatory
		DESCRIPTION "Number of messages received by the local stack that 
				 had a destination that was unreachable."
		::= { fsICMPStatsTableEntry 4 }

	fsICMPInMsgTimeExceed OBJECT-TYPE
		SYNTAX  Counter
		ACCESS  read-only
		STATUS  mandatory
		DESCRIPTION "Number of messages received by the local stack 
				 that had exceeded it timeout period."
		::= { fsICMPStatsTableEntry 5 }

	fsICMPInMsgSourceQuench OBJECT-TYPE
		SYNTAX  Counter
		ACCESS  read-only
		STATUS  mandatory
		DESCRIPTION "Number of source quench messages received by the 
				 local stack."
		::= { fsICMPStatsTableEntry 6 }

	fsICMPInMsgEchoMsg OBJECT-TYPE
		SYNTAX  Counter
		ACCESS  read-only
		STATUS  mandatory
		DESCRIPTION "Number of echo request (PING) messages received."
		::= { fsICMPStatsTableEntry 7 }

	fsICMPInMsgEchoReply OBJECT-TYPE
		SYNTAX  Counter
		ACCESS  read-only
		STATUS  mandatory
		DESCRIPTION "Number of echo request messages (PINGs) for which the 
				 far end replied."
		::= { fsICMPStatsTableEntry 8 }

	fsICMPOutMsgAttemptSent OBJECT-TYPE
		SYNTAX  Counter
		ACCESS  read-only
		STATUS  mandatory
		DESCRIPTION "Number of ICMP messages sent."
		::= { fsICMPStatsTableEntry 9 }

	fsICMPOutMsgErrNotSent OBJECT-TYPE
		SYNTAX  Counter
		ACCESS  read-only
		STATUS  mandatory
		DESCRIPTION "Number of ICMP error messages that were unable 
				 to be sent."
		::= { fsICMPStatsTableEntry 10 }

	fsICMPOutMsgSourceQuenchSent OBJECT-TYPE
		SYNTAX  Counter
		ACCESS  read-only
		STATUS  mandatory
		DESCRIPTION "Not supported."
		::= { fsICMPStatsTableEntry 11 }

	fsICMPOutMsgEchoReplySent OBJECT-TYPE
		SYNTAX  Counter
		ACCESS  read-only
		STATUS  mandatory
		DESCRIPTION "Number of echo request (PING) messages for which the 
				 local stack replied."
		::= { fsICMPStatsTableEntry 12 }

	fsICMPOutMsgTimeExceedSent OBJECT-TYPE
		SYNTAX  Counter
		ACCESS  read-only
		STATUS  mandatory
		DESCRIPTION ""
		::= { fsICMPStatsTableEntry 13 }

	fsICMPOutMsgDesUnreachSent OBJECT-TYPE
		SYNTAX  Counter
		ACCESS  read-only
		STATUS  mandatory
		DESCRIPTION "Number of destination unreachable messages sent."
		::= { fsICMPStatsTableEntry 14 }


-- ***************************************************************************
-- UDP Stats

fsUDPStatsTable OBJECT-TYPE
	SYNTAX  SEQUENCE OF FsUDPStatsTableEntry
	ACCESS  not-accessible
	STATUS  mandatory
	DESCRIPTION  ""
	::= { fsUDPStats 1 }

	FsUDPStatsTableEntry ::= SEQUENCE {
		fsUDPStatsTableIndex		INTEGER,
		fsUDPInMsgToApp     		Counter,
		fsUDPInMsgWithNoApp		Counter,
		fsUDPInMsgNoDeliverable		Counter,
		fsUDPOutMsgSent			Counter
		}

	fsUDPStatsTableEntry OBJECT-TYPE	
		SYNTAX  FsUDPStatsTableEntry
		ACCESS  not-accessible
		STATUS  mandatory
		DESCRIPTION ""
		INDEX { fsUDPStatsTableIndex }
		::= { fsUDPStatsTable 1 }

	fsUDPStatsTableIndex OBJECT-TYPE
		SYNTAX  INTEGER
		ACCESS  read-only
		STATUS  mandatory
		DESCRIPTION ""
		::=  { fsUDPStatsTableEntry 1 }

	fsUDPInMsgToApp OBJECT-TYPE
		SYNTAX  Counter
		ACCESS  read-only
		STATUS  mandatory
		DESCRIPTION "Number of incoming messages delivered to applications."
		::= { fsUDPStatsTableEntry 2 }

	fsUDPInMsgWithNoApp OBJECT-TYPE
		SYNTAX  Counter
		ACCESS  read-only
		STATUS  mandatory
		DESCRIPTION "Number of messages with no application."
		::= { fsUDPStatsTableEntry 3 }

	fsUDPInMsgNoDeliverable OBJECT-TYPE
		SYNTAX  Counter
		ACCESS  read-only
		STATUS  mandatory
		DESCRIPTION "Number of messages that were undeliverable."
		::= { fsUDPStatsTableEntry 4 }

	fsUDPOutMsgSent OBJECT-TYPE
		SYNTAX  Counter
		ACCESS  read-only
		STATUS  mandatory
		DESCRIPTION "Number of messages sent."
		::= { fsUDPStatsTableEntry 5 }


-- ***************************************************************************
-- TCP Stats

fsTCPStatsTable OBJECT-TYPE
	SYNTAX  SEQUENCE OF FsTCPStatsTableEntry
	ACCESS  not-accessible
	STATUS  mandatory
	DESCRIPTION  ""
	::= { fsTCPStats 1 }

	FsTCPStatsTableEntry ::= SEQUENCE {
		fsTCPStatsTableIndex		INTEGER,
		fsTCPInConnAccept     		Counter,
		fsTCPInConnReject			Counter,
		fsTCPInSegReceived		Counter,
		fsTCPInSegErrReceived		Counter,
		fsTCPOutConnAttempt		Counter,
		fsTCPOutConnFailed		Counter,
		fsTCPOutSegSent			Counter,
		fsTCPOutSegRetransmit		Counter,
		fsTCPOutSegSentWithRST		Counter,
		fsTCPOutCurrentEstConn		Counter,
		fsTCPOutNumDisconnect		Counter
		}

	fsTCPStatsTableEntry OBJECT-TYPE	
		SYNTAX  FsTCPStatsTableEntry
		ACCESS  not-accessible
		STATUS  mandatory
		DESCRIPTION ""
		INDEX { fsTCPStatsTableIndex }
		::= { fsTCPStatsTable 1 }

	fsTCPStatsTableIndex OBJECT-TYPE
		SYNTAX  INTEGER
		ACCESS  read-only
		STATUS  mandatory
		DESCRIPTION ""
		::=  { fsTCPStatsTableEntry 1 }

	fsTCPInConnAccept OBJECT-TYPE
		SYNTAX  Counter
		ACCESS  read-only
		STATUS  mandatory
		DESCRIPTION "Number of TCP connections accepted."
		::= { fsTCPStatsTableEntry 2 }

	fsTCPInConnReject OBJECT-TYPE
		SYNTAX  Counter
		ACCESS  read-only
		STATUS  mandatory
		DESCRIPTION "Number of TCP messages rejected."
		::= { fsTCPStatsTableEntry 3 }

	fsTCPInSegReceived OBJECT-TYPE
		SYNTAX  Counter
		ACCESS  read-only
		STATUS  mandatory
		DESCRIPTION "Number of TCP segments received."
		::= { fsTCPStatsTableEntry 4 }

	fsTCPInSegErrReceived OBJECT-TYPE
		SYNTAX  Counter
		ACCESS  read-only
		STATUS  mandatory
		DESCRIPTION "Number of TCP segments received in error."
		::= { fsTCPStatsTableEntry 5 }

	fsTCPOutConnAttempt OBJECT-TYPE
		SYNTAX  Counter
		ACCESS  read-only
		STATUS  mandatory
		DESCRIPTION "Number of TCP connections attempted."
		::= { fsTCPStatsTableEntry 6 }

	fsTCPOutConnFailed OBJECT-TYPE
		SYNTAX  Counter
		ACCESS  read-only
		STATUS  mandatory
		DESCRIPTION "Number of failed connections."
		::= { fsTCPStatsTableEntry 7 }

	fsTCPOutSegSent OBJECT-TYPE
		SYNTAX  Counter
		ACCESS  read-only
		STATUS  mandatory
		DESCRIPTION "Number of segments sent."
		::= { fsTCPStatsTableEntry 8 }

	fsTCPOutSegRetransmit OBJECT-TYPE
		SYNTAX  Counter
		ACCESS  read-only
		STATUS  mandatory
		DESCRIPTION "Number of segments retransmitted."
		::= { fsTCPStatsTableEntry 9 }

	fsTCPOutSegSentWithRST OBJECT-TYPE
		SYNTAX  Counter
		ACCESS  read-only
		STATUS  mandatory
		DESCRIPTION "Number of segments sent with a reset."
		::= { fsTCPStatsTableEntry 10 }

	fsTCPOutCurrentEstConn OBJECT-TYPE
		SYNTAX  Counter
		ACCESS  read-only
		STATUS  mandatory
		DESCRIPTION "Number of currently established conections."
		::= { fsTCPStatsTableEntry 11 }

	fsTCPOutNumDisconnect OBJECT-TYPE
		SYNTAX  Counter
		ACCESS  read-only
		STATUS  mandatory
		DESCRIPTION "Number of disconnects."
		::= { fsTCPStatsTableEntry 12 }


-- ***************************************************************************
-- SNMP Stats

fsSNMPStatsTable OBJECT-TYPE
	SYNTAX  SEQUENCE OF FsSNMPStatsTableEntry
	ACCESS  not-accessible
	STATUS  mandatory
	DESCRIPTION  ""
	::= { fsSNMPStats 1 }

	FsSNMPStatsTableEntry ::= SEQUENCE {
		fsSNMPStatsTableIndex         INTEGER,
		fsSNMPInMsgTotalReceived      Counter,
		fsSNMPInMsgUnsupportVer       Counter,
		fsSNMPInMsgUnknownComm        Counter,
		fsSNMPInMsgNoAllowOper        Counter,
		fsSNMPInMsgASNParseErr        Counter,
		fsSNMPInMsgUnknownType        Counter,
		fsSNMPInMsgTooBig             Counter,
		fsSNMPInMsgNoSuchName         Counter,
		fsSNMPInMsgBadValue           Counter,
		fsSNMPInMsgReadOnly           Counter,
		fsSNMPInMsgMIBRetrived        Counter,
		fsSNMPInMsgMIBAltered         Counter,
		fsSNMPInMsgGetProcess         Counter,
		fsSNMPInMsgGetNextProcess     Counter,
		fsSNMPInMsgSetProcess         Counter,
		fsSNMPOutMsgSent              Counter,
		fsSNMPOutMsgGetRepGenerate    Counter,
		fsSNMPOutMsgTrapGenerate      Counter
		}

	fsSNMPStatsTableEntry OBJECT-TYPE	
		SYNTAX  FsSNMPStatsTableEntry
		ACCESS  not-accessible
		STATUS  mandatory
		DESCRIPTION ""
		INDEX { fsSNMPStatsTableIndex }
		::= { fsSNMPStatsTable 1 }

	fsSNMPStatsTableIndex OBJECT-TYPE
		SYNTAX  INTEGER
		ACCESS  read-only
		STATUS  mandatory
		DESCRIPTION ""
		::=  { fsSNMPStatsTableEntry 1 }

	fsSNMPInMsgTotalReceived OBJECT-TYPE
		SYNTAX  Counter
		ACCESS  read-only
		STATUS  mandatory
		DESCRIPTION "Total number of SNMP messages received."
		::= { fsSNMPStatsTableEntry 2 }

	fsSNMPInMsgUnsupportVer OBJECT-TYPE
		SYNTAX  Counter
		ACCESS  read-only
		STATUS  mandatory
		DESCRIPTION "Number of messages received that have an unsupported 
				 version."
		::= { fsSNMPStatsTableEntry 3 }

	fsSNMPInMsgUnknownComm OBJECT-TYPE
		SYNTAX  Counter
		ACCESS  read-only
		STATUS  mandatory
		DESCRIPTION ""
		::= { fsSNMPStatsTableEntry 4 }

	fsSNMPInMsgNoAllowOper OBJECT-TYPE
		SYNTAX  Counter
		ACCESS  read-only
		STATUS  mandatory
		DESCRIPTION "Number of messages received where the operation is not 
				 allowed by the FRAD."
		::= { fsSNMPStatsTableEntry 5 }

	fsSNMPInMsgASNParseErr OBJECT-TYPE
		SYNTAX  Counter
		ACCESS  read-only
		STATUS  mandatory
		DESCRIPTION ""
		::= { fsSNMPStatsTableEntry 6 }

	fsSNMPInMsgUnknownType OBJECT-TYPE
		SYNTAX  Counter
		ACCESS  read-only
		STATUS  mandatory
		DESCRIPTION "Number of messages received of an unknown type."
		::= { fsSNMPStatsTableEntry 7 }

	fsSNMPInMsgTooBig OBJECT-TYPE
		SYNTAX  Counter
		ACCESS  read-only
		STATUS  mandatory
		DESCRIPTION "Number of messages received where the size was too big."
		::= { fsSNMPStatsTableEntry 8 }

	fsSNMPInMsgNoSuchName OBJECT-TYPE
		SYNTAX  Counter
		ACCESS  read-only
		STATUS  mandatory
		DESCRIPTION "Number of messages where the variable does not exist."
		::= { fsSNMPStatsTableEntry 9 }

	fsSNMPInMsgBadValue OBJECT-TYPE
		SYNTAX  Counter
		ACCESS  read-only
		STATUS  mandatory
		DESCRIPTION "Number of messages received where the value is invalid."
		::= { fsSNMPStatsTableEntry 10 }

	fsSNMPInMsgReadOnly OBJECT-TYPE
		SYNTAX  Counter
		ACCESS  read-only
		STATUS  mandatory
		DESCRIPTION "Number of messages that are for read only parameters."
		::= { fsSNMPStatsTableEntry 11 }

	fsSNMPInMsgMIBRetrived OBJECT-TYPE
		SYNTAX  Counter
		ACCESS  read-only
		STATUS  mandatory
		DESCRIPTION "Number of messages that retrieved a MIB variable."
		::= { fsSNMPStatsTableEntry 12 }

	fsSNMPInMsgMIBAltered OBJECT-TYPE
		SYNTAX  Counter
		ACCESS  read-only
		STATUS  mandatory
		DESCRIPTION "Number of message that altered a MIB object."
		::= { fsSNMPStatsTableEntry 13 }

	fsSNMPInMsgGetProcess OBJECT-TYPE
		SYNTAX  Counter
		ACCESS  read-only
		STATUS  mandatory
		DESCRIPTION "Number of messages that requested information (GET)."
		::= { fsSNMPStatsTableEntry 14 }

	fsSNMPInMsgGetNextProcess OBJECT-TYPE
		SYNTAX  Counter
		ACCESS  read-only
		STATUS  mandatory
		DESCRIPTION "Number of get-next messages received."
		::= { fsSNMPStatsTableEntry 15 }

	fsSNMPInMsgSetProcess OBJECT-TYPE
		SYNTAX  Counter
		ACCESS  read-only
		STATUS  mandatory
		DESCRIPTION "Number of Set messages received."
		::= { fsSNMPStatsTableEntry 16 }

	fsSNMPOutMsgSent OBJECT-TYPE
		SYNTAX  Counter
		ACCESS  read-only
		STATUS  mandatory
		DESCRIPTION "Total of SNMP messages sent."
		::= { fsSNMPStatsTableEntry 17 }

	fsSNMPOutMsgGetRepGenerate OBJECT-TYPE
		SYNTAX  Counter
		ACCESS  read-only
		STATUS  mandatory
		DESCRIPTION "Number of replies that were generated."
		::= { fsSNMPStatsTableEntry 18 }

	fsSNMPOutMsgTrapGenerate OBJECT-TYPE
		SYNTAX  Counter
		ACCESS  read-only
		STATUS  mandatory
		DESCRIPTION "Number of traps that were generated."
		::= { fsSNMPStatsTableEntry 19 }


-- ***************************************************************************
-- Loader Stats

fsNetLoaderStatsTable OBJECT-TYPE
	SYNTAX  SEQUENCE OF FsNetLoaderStatsTableEntry
	ACCESS  not-accessible
	STATUS  mandatory
	DESCRIPTION  ""
	::= { fsNetLoaderStats 1 }

	FsNetLoaderStatsTableEntry ::= SEQUENCE {
		fsNetLoaderStatsTableIndex    INTEGER,
		fsNetLoaderState              INTEGER,
		fsNetLoaderAttemptTrans       Counter,
		fsNetLoaderSuccConn           Counter,
		fsNetLoaderFailTrans          Counter,
		fsNetLoaderCompleteTrans      Counter,
		fsNetLoaderFileTransState     INTEGER,
		fsNetLoaderByteReceived       Counter,
		fsNetLoaderStartRegAddr       DisplayString,
		fsNetLoaderFlashWriteAddr     DisplayString,
		fsNetLoaderEndRegAddr         DisplayString
		}

	fsNetLoaderStatsTableEntry OBJECT-TYPE	
		SYNTAX  FsNetLoaderStatsTableEntry
		ACCESS  not-accessible
		STATUS  mandatory
		DESCRIPTION ""
		INDEX { fsNetLoaderStatsTableIndex }
		::= { fsNetLoaderStatsTable 1 }

	fsNetLoaderStatsTableIndex OBJECT-TYPE
		SYNTAX  INTEGER
		ACCESS  read-only
		STATUS  mandatory
		DESCRIPTION ""
		::=  { fsNetLoaderStatsTableEntry 1 }

	fsNetLoaderState OBJECT-TYPE
		SYNTAX  INTEGER {
			idle		(0),
			attempt	(1),
			program	(2)
			}
		ACCESS  read-only
		STATUS  mandatory
		DESCRIPTION "Current state of the loader (idle, attempt, 
				 programming)."
		::=  { fsNetLoaderStatsTableEntry 2 }

	fsNetLoaderAttemptTrans OBJECT-TYPE
		SYNTAX  Counter
		ACCESS  read-only
		STATUS  mandatory
		DESCRIPTION "Number of time the loader attempted a transmission."
		::= { fsNetLoaderStatsTableEntry 3 }

	fsNetLoaderSuccConn OBJECT-TYPE
		SYNTAX  Counter
		ACCESS  read-only
		STATUS  mandatory
		DESCRIPTION "Number of successful connections to the loader."
		::= { fsNetLoaderStatsTableEntry 4 }

	fsNetLoaderFailTrans OBJECT-TYPE
		SYNTAX  Counter
		ACCESS  read-only
		STATUS  mandatory
		DESCRIPTION "Number of time the transmission of data failed 
				 in the loader."
		::= { fsNetLoaderStatsTableEntry 5 }

	fsNetLoaderCompleteTrans OBJECT-TYPE
		SYNTAX  Counter
		ACCESS  read-only
		STATUS  mandatory
		DESCRIPTION "Number of time the loader completed."
		::= { fsNetLoaderStatsTableEntry 6 }

	fsNetLoaderFileTransState OBJECT-TYPE
		SYNTAX  INTEGER {
			none              (0),
			active            (1),
			err-region        (2),
			err-parsing       (3),
			err-tftp          (4),
			err-unknown       (5),
			complete          (6)
			}
		ACCESS  read-only
		STATUS  mandatory
		DESCRIPTION "Current state of the file being loaded (none, 
				 active, err-region, err-parsing, err-tftp, 
				 err-unknown, complete)."
		::=  { fsNetLoaderStatsTableEntry 7 }

	fsNetLoaderByteReceived OBJECT-TYPE
		SYNTAX  Counter
		ACCESS  read-only
		STATUS  mandatory
		DESCRIPTION "Number of bytes received by the loader."
		::= { fsNetLoaderStatsTableEntry 8 }

	fsNetLoaderStartRegAddr OBJECT-TYPE
		SYNTAX  DisplayString (SIZE (0..8))
		ACCESS  read-only
		STATUS  mandatory
		DESCRIPTION "Starting register address of the loader."
		::= { fsNetLoaderStatsTableEntry 9 }

	fsNetLoaderFlashWriteAddr OBJECT-TYPE
		SYNTAX  DisplayString (SIZE (0..8))
		ACCESS  read-only
		STATUS  mandatory
		DESCRIPTION "Flash write address."
		::= { fsNetLoaderStatsTableEntry 10 }

	fsNetLoaderEndRegAddr OBJECT-TYPE
		SYNTAX  DisplayString (SIZE (0..8))
		ACCESS  read-only
		STATUS  mandatory
		DESCRIPTION "Ending address of the Flash loader."
		::= { fsNetLoaderStatsTableEntry 11 }

-- ***************************************************************************
-- Priority Queue Stats

fsPriByteTransTable OBJECT-TYPE
	SYNTAX  SEQUENCE OF FsPriByteTransEntry
	ACCESS  not-accessible
	STATUS  mandatory
	DESCRIPTION  ""
	::= { fsPriorityStats 1 }

	FsPriByteTransEntry ::= SEQUENCE {
		fsPriBytePortIndex          INTEGER,
		fsPriByteCommitImmediate    Counter,
		fsPriByteCommitHigh         Counter,
		fsPriByteCommitMedium       Counter,
            fsPriByteCommitLow          Counter,
		fsPriByteExcessImmediate    Counter,
		fsPriByteExcessHigh         Counter,
		fsPriByteExcessMedium       Counter,
            fsPriByteExcessLow          Counter
		}

	fsPriByteTransEntry OBJECT-TYPE
		SYNTAX  FsPriByteTransEntry
		ACCESS  not-accessible
		STATUS  mandatory
		DESCRIPTION ""
		INDEX { fsPriBytePortIndex }
		::= { fsPriByteTransTable 1 }

	fsPriBytePortIndex OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-only
		STATUS  mandatory
		DESCRIPTION ""
		::= { fsPriByteTransEntry 1 }

	fsPriByteCommitImmediate OBJECT-TYPE
		SYNTAX  Counter
		ACCESS  read-only
		STATUS  mandatory
		DESCRIPTION "Number of bytes sent with committed immediate priority."
		::= { fsPriByteTransEntry 2 }

	fsPriByteCommitHigh OBJECT-TYPE
		SYNTAX  Counter
		ACCESS  read-only
		STATUS  mandatory
		DESCRIPTION "Number of bytes sent with committed high priority."
		::= { fsPriByteTransEntry 3 }

	fsPriByteCommitMedium OBJECT-TYPE
		SYNTAX  Counter
		ACCESS  read-only
		STATUS  mandatory
		DESCRIPTION "Number of bytes sent with committed medium priority."
		::= { fsPriByteTransEntry 4 }

	fsPriByteCommitLow OBJECT-TYPE
		SYNTAX  Counter
		ACCESS  read-only
		STATUS  mandatory
		DESCRIPTION "Number of bytes sent with committed low priority."
		::= { fsPriByteTransEntry 5 }

	fsPriByteExcessImmediate OBJECT-TYPE
		SYNTAX  Counter
		ACCESS  read-only
		STATUS  mandatory
		DESCRIPTION "Number of bytes sent with excess immediate priority."
		::= { fsPriByteTransEntry 6 }

	fsPriByteExcessHigh OBJECT-TYPE
		SYNTAX  Counter
		ACCESS  read-only
		STATUS  mandatory
		DESCRIPTION " Number of bytes sent with excess high priority."
		::= { fsPriByteTransEntry 7 }

	fsPriByteExcessMedium OBJECT-TYPE
		SYNTAX  Counter
		ACCESS  read-only
		STATUS  mandatory
		DESCRIPTION " Number of bytes sent with excess medium priority."
		::= { fsPriByteTransEntry 8 }

	fsPriByteExcessLow OBJECT-TYPE
		SYNTAX  Counter
		ACCESS  read-only
		STATUS  mandatory
		DESCRIPTION " Number of bytes sent with excess immediate priority."
		::= { fsPriByteTransEntry 9 }

fsPriFrameTransTable OBJECT-TYPE
	SYNTAX  SEQUENCE OF FsPriFrameTransEntry
	ACCESS  not-accessible
	STATUS  mandatory
	DESCRIPTION  ""
	::= { fsPriorityStats 2 }

	FsPriFrameTransEntry ::= SEQUENCE {
		fsPriFramePortIndex          INTEGER,
		fsPriFrameCommitImmediate    Counter,
		fsPriFrameCommitHigh         Counter,
		fsPriFrameCommitMedium       Counter,
            fsPriFrameCommitLow          Counter,
		fsPriFrameExcessImmediate    Counter,
		fsPriFrameExcessHigh         Counter,
		fsPriFrameExcessMedium       Counter,
            fsPriFrameExcessLow          Counter
		}

	fsPriFrameTransEntry OBJECT-TYPE
		SYNTAX  FsPriFrameTransEntry
		ACCESS  not-accessible
		STATUS  mandatory
		DESCRIPTION ""
		INDEX { fsPriFramePortIndex }
		::= { fsPriFrameTransTable 1 }

	fsPriFramePortIndex OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-only
		STATUS  mandatory
		DESCRIPTION ""
		::= { fsPriFrameTransEntry 1 }

	fsPriFrameCommitImmediate OBJECT-TYPE
		SYNTAX  Counter
		ACCESS  read-only
		STATUS  mandatory
		DESCRIPTION "Number of frames sent within CIR with immediate priority."
		::= { fsPriFrameTransEntry 2 }

	fsPriFrameCommitHigh OBJECT-TYPE
		SYNTAX  Counter
		ACCESS  read-only
		STATUS  mandatory
		DESCRIPTION "Number of frames sent within CIR with high priority."
		::= { fsPriFrameTransEntry 3 }

	fsPriFrameCommitMedium OBJECT-TYPE
		SYNTAX  Counter
		ACCESS  read-only
		STATUS  mandatory
		DESCRIPTION " Number of frames sent within CIR with medium priority."
		::= { fsPriFrameTransEntry 4 }

	fsPriFrameCommitLow OBJECT-TYPE
		SYNTAX  Counter
		ACCESS  read-only
		STATUS  mandatory
		DESCRIPTION " Number of frames sent within CIR with low priority."
		::= { fsPriFrameTransEntry 5 }

	fsPriFrameExcessImmediate OBJECT-TYPE
		SYNTAX  Counter
		ACCESS  read-only
		STATUS  mandatory
		DESCRIPTION "Number of frames sent in excess CIR with immediate priority."
		::= { fsPriFrameTransEntry 6 }

	fsPriFrameExcessHigh OBJECT-TYPE
		SYNTAX  Counter
		ACCESS  read-only
		STATUS  mandatory
		DESCRIPTION " Number of frames sent in excess CIR with high priority."
		::= { fsPriFrameTransEntry 7 }

	fsPriFrameExcessMedium OBJECT-TYPE
		SYNTAX  Counter
		ACCESS  read-only
		STATUS  mandatory
		DESCRIPTION " Number of frames sent in excess CIR with medium priority."
		::= { fsPriFrameTransEntry 8 }

	fsPriFrameExcessLow OBJECT-TYPE
		SYNTAX  Counter
		ACCESS  read-only
		STATUS  mandatory
		DESCRIPTION " Number of frames sent in excess CIR with low priority."
		::= { fsPriFrameTransEntry 9 }

-- ***************************************************************************
-- SDLC2 Port Stats

fsSdlc2PortStatsTable OBJECT-TYPE
   	SYNTAX  SEQUENCE OF FsSdlc2PortStatsEntry
    	ACCESS  not-accessible
    	STATUS  mandatory
    	DESCRIPTION
	   	"Each entry in this table contains statistics
	    	for a specific SDLC port."
    	::= { fsSdlc2Stats  1 }

	FsSdlc2PortStatsEntry ::= SEQUENCE {
		fsSdlc2PortIndex                    INTEGER,
		fsSdlc2PortStatsPhysicalFailures    Counter,
		fsSdlc2PortStatsInvalidAddresses    Counter,
	 	fsSdlc2PortStatsDwarfFrames         Counter,
		fsSdlc2PortStatsPollsIn             Counter,
		fsSdlc2PortStatsPollsOut            Counter,
		fsSdlc2PortStatsPollRspsIn          Counter,
		fsSdlc2PortStatsPollRspsOut         Counter,
		fsSdlc2PortStatsLocalBusies         Counter,
		fsSdlc2PortStatsRemoteBusies        Counter,
		fsSdlc2PortStatsIFramesIn           Counter,
		fsSdlc2PortStatsIFramesOut          Counter,
		fsSdlc2PortStatsOctetsIn            Counter,
		fsSdlc2PortStatsOctetsOut           Counter,
		fsSdlc2PortStatsProtocolErrs        Counter, 
		fsSdlc2PortStatsActivityTOs         Counter,
		fsSdlc2PortStatsRetriesExps         Counter,
		fsSdlc2PortStatsRetransmitsIn       Counter,
		fsSdlc2PortStatsRetransmitsOut      Counter
    		}

	fsSdlc2PortStatsEntry OBJECT-TYPE
    		SYNTAX  FsSdlc2PortStatsEntry
    		ACCESS  not-accessible
    		STATUS  mandatory
    		DESCRIPTION
	   		"A list of statistics for an SDLC port."
    		INDEX   { fsSdlc2PortIndex }
    		::= { fsSdlc2PortStatsTable  1 }

	fsSdlc2PortIndex OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
    		ACCESS  read-only
    		STATUS  mandatory
    		DESCRIPTION
	   		"This object reflects the total number of times
	    		this port has failed due to its physical media
	    		since port startup.  At port startup time,
	    		this object must be initialized to zero."
    		::= { fsSdlc2PortStatsEntry  1 }

	fsSdlc2PortStatsPhysicalFailures OBJECT-TYPE
    		SYNTAX  Counter
    		ACCESS  read-only
    		STATUS  mandatory
    		DESCRIPTION
	   		"This object reflects the total number of times
	    		this port has failed due to its physical media
	    		since port startup.  At port startup time,
	    		this object must be initialized to zero."
    		::= { fsSdlc2PortStatsEntry  2 }

	fsSdlc2PortStatsInvalidAddresses OBJECT-TYPE
    		SYNTAX  Counter
    		ACCESS  read-only
    		STATUS  mandatory
    		DESCRIPTION
	   		"This object reflects the total number of
	    		frames received by this port with invalid link
	    		station addresses."
    		::= { fsSdlc2PortStatsEntry  3 }

	fsSdlc2PortStatsDwarfFrames OBJECT-TYPE
    		SYNTAX  Counter
    		ACCESS  read-only
    		STATUS  mandatory
    		DESCRIPTION
	   		"This object reflects the total number of
	    		frames received by this port which were
	    		delivered intact by the physical layer but were
	    		too short to be legal."
    		::= { fsSdlc2PortStatsEntry  4 }

	fsSdlc2PortStatsPollsIn OBJECT-TYPE
    		SYNTAX  Counter
    		ACCESS  read-only
    		STATUS  mandatory
    		DESCRIPTION
	   		"This object reflects the total number of polls
	    		received by this port since the port was
	    		created."
    		::= { fsSdlc2PortStatsEntry  5 }

	fsSdlc2PortStatsPollsOut OBJECT-TYPE
    		SYNTAX  Counter
    		ACCESS  read-only
    		STATUS  mandatory
    		DESCRIPTION
	   		"This object reflects the total number of polls
	    		sent by this port since the port was created."
    		::= { fsSdlc2PortStatsEntry  6 }

	fsSdlc2PortStatsPollRspsIn OBJECT-TYPE
    		SYNTAX  Counter
    		ACCESS  read-only
    		STATUS  mandatory
    		DESCRIPTION
	   		"This object reflects the total number of poll
	    		responses received by this port since the port
	    		was created."
    		::= { fsSdlc2PortStatsEntry  7 }

	fsSdlc2PortStatsPollRspsOut OBJECT-TYPE
    		SYNTAX  Counter
    		ACCESS  read-only
    		STATUS  mandatory
    		DESCRIPTION
	   		"This object reflects the total number of poll
	    		responses sent by this port since the port was
	    		created."
    		::= { fsSdlc2PortStatsEntry  8 }

	fsSdlc2PortStatsLocalBusies OBJECT-TYPE
    		SYNTAX  Counter
    		ACCESS  read-only
    		STATUS  mandatory
    		DESCRIPTION
	   		"This object reflects the total number of
	    		times that the local SDLC link stations on
	    		this port have entered a busy state (RNR).
	    		This object is initialized to zero when the
	    		port is created."
    		::= { fsSdlc2PortStatsEntry  9 }

	fsSdlc2PortStatsRemoteBusies OBJECT-TYPE
    		SYNTAX  Counter
    		ACCESS  read-only
    		STATUS  mandatory
    		DESCRIPTION
	   		"This object reflects the total number of
	    		times that the adjacent (i.e., remote) SDLC
	    		link stations on this port have entered a busy
	    		state (RNR).  This object is initialized to
	    		zero when the port is created."
    		::= { fsSdlc2PortStatsEntry  10 }

	fsSdlc2PortStatsIFramesIn OBJECT-TYPE
		SYNTAX  Counter
		ACCESS  read-only
		STATUS  mandatory
		DESCRIPTION
			"This object reflects the total number of
			I-Frames that have been received by SDLC link
			stations on this port.  This object is
			initialized to zero when the port is created."
		::= { fsSdlc2PortStatsEntry  11 }

	fsSdlc2PortStatsIFramesOut OBJECT-TYPE
		SYNTAX  Counter
		ACCESS  read-only
		STATUS  mandatory
		DESCRIPTION
			"This object reflects the total number of
			I-Frames that have been transmitted by SDLC
			link stations on this port.  This object is
			initialized to zero when the port is created."
		::= { fsSdlc2PortStatsEntry  12 }

	fsSdlc2PortStatsOctetsIn OBJECT-TYPE
		SYNTAX  Counter
		ACCESS  read-only
		STATUS  mandatory
		DESCRIPTION
			"This object reflects the total octets
			received from adjacent SDLC link stations on
			this port.  This object covers the address,
			control, and information field of I-Frames
			only.  This object is initialized to zero when
			the port is created."
		::= { fsSdlc2PortStatsEntry  13 }

	fsSdlc2PortStatsOctetsOut OBJECT-TYPE
		SYNTAX  Counter
		ACCESS  read-only
		STATUS  mandatory
		DESCRIPTION
			"This object reflects the total octets
			transmitted to adjacent SDLC link stations on
			this port.  This object covers the address,
			control, and information field of I-Frames
			only.  This object is initialized to zero when
			the port is created."
		::= { fsSdlc2PortStatsEntry  14 }

	fsSdlc2PortStatsProtocolErrs OBJECT-TYPE
		SYNTAX  Counter
		ACCESS  read-only
		STATUS  mandatory
		DESCRIPTION
			"This object reflects the total number of
			times that the SDLC link stations on this port
			have deactivated the link as a result of
			having received a protocol violation from the
			adjacent link station.  This object is
			initialized to zero when the port is created."
		::= { fsSdlc2PortStatsEntry  15 }

	fsSdlc2PortStatsActivityTOs OBJECT-TYPE
		SYNTAX  Counter
		ACCESS  read-only
		STATUS  mandatory
		DESCRIPTION
			"This object reflects the total number of
			times that the SDLC link stations on this port
			have deactivated the link as a result of no
			activity on the link.  This object is
			initialized to zero when the port is created."
		::= { fsSdlc2PortStatsEntry  16 }

	fsSdlc2PortStatsRetriesExps OBJECT-TYPE
		SYNTAX  Counter
		ACCESS  read-only
		STATUS  mandatory
		DESCRIPTION
			"This object reflects the total number of
			times that the SDLC link stations on this port
			have deactivated the link as a result of a
			retry sequence being exhausted.  This object
			is initialized to zero when the port is
			created."
		::= { fsSdlc2PortStatsEntry  17 }

	fsSdlc2PortStatsRetransmitsIn OBJECT-TYPE
		SYNTAX  Counter
		ACCESS  read-only
		STATUS  mandatory
		DESCRIPTION
			"This object reflects the total number of
			I-Frames retransmitted by remote link stations
			for all SDLC link stations on this port.  This
			object is initialized to zero when the port is
			created."
		::= { fsSdlc2PortStatsEntry  18 }

	fsSdlc2PortStatsRetransmitsOut OBJECT-TYPE
		SYNTAX  Counter
		ACCESS  read-only
		STATUS  mandatory
		DESCRIPTION
			"This object reflects the total number of
			I-Frames retransmitted by all local SDLC link
			stations on this port.  This object is
			initialized to zero when the port is created."
		::= { fsSdlc2PortStatsEntry  19 }

-- ***************************************************************************
-- SDLC2 Stn Stats

fsSdlc2LSStatsTable OBJECT-TYPE
	SYNTAX  SEQUENCE OF FsSdlc2LSStatsEntry
	ACCESS  not-accessible
	STATUS  mandatory
	DESCRIPTION
		"Each entry in this table contains statistics
		for a specific SDLC link station."
	::= { fsSdlc2Stats  2 }

	FsSdlc2LSStatsEntry ::= SEQUENCE {
		fsSdlc2LSPortIndex            INTEGER,
		fsSdlc2LSStnRecid             INTEGER,
		fsSdlc2LSStnAddress           DisplayString,
		fsSdlc2LSStatsBLUsIn          Counter,
		fsSdlc2LSStatsBLUsOut         Counter,
		fsSdlc2LSStatsOctetsIn        Counter,
		fsSdlc2LSStatsOctetsOut       Counter,
		fsSdlc2LSStatsPollsIn         Counter,
		fsSdlc2LSStatsPollsOut        Counter,
		fsSdlc2LSStatsPollRspsIn      Counter,
		fsSdlc2LSStatsPollRspsOut     Counter,
		fsSdlc2LSStatsLocalBusies     Counter,
		fsSdlc2LSStatsRemoteBusies    Counter,
		fsSdlc2LSStatsIFramesIn       Counter,
		fsSdlc2LSStatsIFramesOut      Counter,
		fsSdlc2LSStatsXIDsIn          Counter,
		fsSdlc2LSStatsXIDsOut         Counter,
		fsSdlc2LSStatsREJsIn          Counter,
		fsSdlc2LSStatsFRMRsIn         Counter,
		fsSdlc2LSStatsFRMRsOut        Counter
		}

	fsSdlc2LSStatsEntry OBJECT-TYPE
		SYNTAX  FsSdlc2LSStatsEntry
		ACCESS  not-accessible
		STATUS  mandatory
		DESCRIPTION
			"A list of statistics for an SDLC link station."
		INDEX   { fsSdlc2LSPortIndex, fsSdlc2LSStnRecid }
		::= { fsSdlc2LSStatsTable  1 }

	fsSdlc2LSPortIndex OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-only
		STATUS  mandatory
		DESCRIPTION
			"This is the Port number of the port which the station 
			 belongs to."
		::= { fsSdlc2LSStatsEntry  1 }

	fsSdlc2LSStnRecid OBJECT-TYPE
		SYNTAX  INTEGER
		ACCESS  read-only
		STATUS  mandatory
		DESCRIPTION
			"This is the Record id the station record."
		::= { fsSdlc2LSStatsEntry  2 }

	fsSdlc2LSStnAddress OBJECT-TYPE
		SYNTAX  DisplayString (SIZE(2))
		ACCESS  read-only
		STATUS  mandatory
		DESCRIPTION
			"This is the address of the SDLC station."
		::= { fsSdlc2LSStatsEntry  3 }

	fsSdlc2LSStatsBLUsIn OBJECT-TYPE
		SYNTAX  Counter
		ACCESS  read-only
		STATUS  mandatory
		DESCRIPTION
			"This object reflects the total basic link
			units (BLUs; frames) received from an adjacent
			SDLC link station since link station startup.
			At link station startup time, this object must
			be initialized to zero."
		::= { fsSdlc2LSStatsEntry  4 }

	fsSdlc2LSStatsBLUsOut OBJECT-TYPE
		SYNTAX  Counter
		ACCESS  read-only
		STATUS  mandatory
		DESCRIPTION
			"This object reflects the total basic link
			units (BLUs; frames), transmitted to an
			adjacent SDLC link station since link station
			startup.  At link station startup time, this
			object must be initialized to zero."
		::= { fsSdlc2LSStatsEntry  5 }

	fsSdlc2LSStatsOctetsIn OBJECT-TYPE
		SYNTAX  Counter
		ACCESS  read-only
		STATUS  mandatory
		DESCRIPTION
			"This object reflects the total octets received
			from an adjacent SDLC link station since link
			station startup.  This object covers the
			address, control, and information field of
			I-Frames only.  At link station startup time,
			this object must be initialized to zero."
		::= { fsSdlc2LSStatsEntry  6 }

	fsSdlc2LSStatsOctetsOut OBJECT-TYPE
		SYNTAX  Counter
		ACCESS  read-only
		STATUS  mandatory
		DESCRIPTION
			"This object reflects the total octets
			transmitted to an adjacent SDLC link station
			since link station startup.  This object covers
			the address, control, and information field of
			I-Frames only.  At link station startup time,
			this object must be initialized to zero."
		::= { fsSdlc2LSStatsEntry  7 }

	fsSdlc2LSStatsPollsIn OBJECT-TYPE
		SYNTAX  Counter
		ACCESS  read-only
		STATUS  mandatory
		DESCRIPTION
			"This object reflects the total polls received
			from an adjacent SDLC link station since link
			station startup.  At link station startup time,
			this object must be initialized to zero."
		::= { fsSdlc2LSStatsEntry  8 }

	fsSdlc2LSStatsPollsOut OBJECT-TYPE
		SYNTAX  Counter
		ACCESS  read-only
		STATUS  mandatory
		DESCRIPTION
			"This object reflects the total polls sent to
			an adjacent SDLC link station since link
			station startup.  At link station startup time,
			this object must be initialized to zero."
		::= { fsSdlc2LSStatsEntry  9 }

	fsSdlc2LSStatsPollRspsIn OBJECT-TYPE
		SYNTAX  Counter
		ACCESS  read-only
		STATUS  mandatory
		DESCRIPTION
			"This object reflects the total number of poll
			responses received from the adjacent SDLC link
			station since station startup.  This value
			includes I-frames that are received in response
			to a poll.
			At link station startup time, this object must
			be initialized to zero."
		::= { fsSdlc2LSStatsEntry  10 }

	fsSdlc2LSStatsPollRspsOut OBJECT-TYPE
		SYNTAX  Counter
		ACCESS  read-only
		STATUS  mandatory
		DESCRIPTION
			"This object reflects the total number of poll
			responses sent to the adjacent SDLC link
			station since link station startup.  This value
			includes I-frames that are sent in response to
			a poll.
			At link station startup time, this object must
			be initialized to zero."
		::= { fsSdlc2LSStatsEntry  11 }

	fsSdlc2LSStatsLocalBusies OBJECT-TYPE
		SYNTAX  Counter
		ACCESS  read-only
		STATUS  mandatory
		DESCRIPTION
			"This object reflects the total number of times
			that the local SDLC link station has entered a
			busy state (RNR) since link station startup.
			At link station startup time, this object must
			be initialized to zero."
		::= { fsSdlc2LSStatsEntry  12 }

	fsSdlc2LSStatsRemoteBusies OBJECT-TYPE
		SYNTAX  Counter
		ACCESS  read-only
		STATUS  mandatory
		DESCRIPTION
			"This object reflects the total number of times
			that an adjacent ( remote) SDLC link station
			has entered a busy state (RNR) since link
			station startup.  At link station startup time,
			this object must be initialized to zero."
		::= { fsSdlc2LSStatsEntry  13 }

	fsSdlc2LSStatsIFramesIn OBJECT-TYPE
		SYNTAX  Counter
		ACCESS  read-only
		STATUS  mandatory
		DESCRIPTION
			"This object reflects the total I-frames
			received from an adjacent SDLC link station
			since link station startup.  At link station
			startup time, this object must be initialized
			to zero."
		::= { fsSdlc2LSStatsEntry  14 }

	fsSdlc2LSStatsIFramesOut OBJECT-TYPE
		SYNTAX  Counter
		ACCESS  read-only
		STATUS  mandatory
		DESCRIPTION
			"This object reflects the total I-frames
			transmitted to an adjacent SDLC link station
			since link station startup.  At link station
			startup time, this object must be initialized
			to zero."
		::= { fsSdlc2LSStatsEntry  15 }

	fsSdlc2LSStatsXIDsIn OBJECT-TYPE
		SYNTAX  Counter
		ACCESS  read-only
		STATUS  mandatory
		DESCRIPTION
			"This object reflects the total XID frames
			received from an adjacent SDLC link station
			since link station startup."
		::= { fsSdlc2LSStatsEntry  16 }

	fsSdlc2LSStatsXIDsOut OBJECT-TYPE
		SYNTAX  Counter
		ACCESS  read-only
		STATUS  mandatory
		DESCRIPTION
			"This object reflects the total XID frames
			transmitted to an adjacent SDLC link station
			since link station startup."
		::= { fsSdlc2LSStatsEntry  17 }

	fsSdlc2LSStatsREJsIn OBJECT-TYPE
		SYNTAX  Counter
		ACCESS  read-only
		STATUS  mandatory
		DESCRIPTION
			"This object reflects the total REJ frames
			received from an adjacent SDLC link station
			since link station startup."
		::= { fsSdlc2LSStatsEntry  18 }

	fsSdlc2LSStatsFRMRsIn OBJECT-TYPE
		SYNTAX  Counter
		ACCESS  read-only
		STATUS  mandatory
		DESCRIPTION
	   		"This object reflects the total frame reject
	    		(FRMR) frames received from an adjacent SDLC
	    		link station since link station startup."
		::= { fsSdlc2LSStatsEntry  19 }

	fsSdlc2LSStatsFRMRsOut OBJECT-TYPE
		SYNTAX  Counter
		ACCESS  read-only
		STATUS  mandatory
		DESCRIPTION
			"This object reflects the total frame reject
			(FRMR) frames transmitted to an adjacent SDLC
			link station since link station startup."
		::= { fsSdlc2LSStatsEntry  20 }

-- ***************************************************************************
-- LLC Stn Stats

fsLlcStationStatisticsTable OBJECT-TYPE
	SYNTAX  SEQUENCE OF FsLlcStationStatisticsEntry
	ACCESS  not-accessible
	STATUS  mandatory
	DESCRIPTION
		"Statistics Table for Station Component. Each entry
		would be accessed serially by the object
		'fsLlcStationStatisticsIndex'."
	::= { fsLlcStats 1 }

	FsLlcStationStatisticsEntry ::= SEQUENCE {
		fsLlcStationStatisticsIndex         INTEGER,
		fsLlcStationStatisticsIfId          INTEGER,
		fsLlcStationStatisticsCircuit       INTEGER,
		fsLlcStationNumActiveSAPs           INTEGER,
		fsLlcStationNumActiveConns          INTEGER
		}

	fsLlcStationStatisticsEntry OBJECT-TYPE
		SYNTAX  FsLlcStationStatisticsEntry
		ACCESS  not-accessible
		STATUS  mandatory
		DESCRIPTION
			"Entries of the fsLlcStationStatisticsTable."
		INDEX   { fsLlcStationStatisticsIndex }
		::= { fsLlcStationStatisticsTable 1 }

	fsLlcStationStatisticsIndex OBJECT-TYPE
		SYNTAX  INTEGER
		ACCESS  read-only
		STATUS  mandatory
		DESCRIPTION
			"The index value for the Llc Station Table."
		::= { fsLlcStationStatisticsEntry 1 }

	fsLlcStationStatisticsIfId OBJECT-TYPE
		SYNTAX  INTEGER
		ACCESS  read-only
		STATUS  mandatory
		DESCRIPTION
			"The Port Number for this LLC Station."
		::= { fsLlcStationStatisticsEntry 2 }

	fsLlcStationStatisticsCircuit OBJECT-TYPE
		SYNTAX  INTEGER
		ACCESS  read-only
		STATUS  mandatory
		DESCRIPTION
			"The circuit number for Frame Relay interface.
			The circuit number is set to 0 for Ethernet and Token
			Ring interfaces."
		::= { fsLlcStationStatisticsEntry 3 }

	fsLlcStationNumActiveSAPs OBJECT-TYPE
		SYNTAX  INTEGER (1..7)
		ACCESS  read-only
		STATUS  mandatory
		DESCRIPTION
			"The number of active LSAPs under this Station
			Component.
			The valid values range from 1 to 7."
		::= { fsLlcStationStatisticsEntry 4 }

	fsLlcStationNumActiveConns OBJECT-TYPE
		SYNTAX  INTEGER (0..512)
		ACCESS  read-only
		STATUS  mandatory
		DESCRIPTION
			"The number of active connections under this Station
			Component.
			The valid values range from 0 to 512."
		::= { fsLlcStationStatisticsEntry 5 }

-- ***************************************************************************
-- LLC SAP Stats

fsLlcLSAPStatsTable OBJECT-TYPE
	SYNTAX  SEQUENCE OF FsLlcLSAPStatsEntry
	ACCESS  not-accessible
	STATUS  mandatory
	DESCRIPTION
		"The Statistics Table for LSAPs."
	::= { fsLlcStats 2 }

	FsLlcLSAPStatsEntry ::= SEQUENCE {
		fsLlcLSAPStatsIndex           INTEGER,
		fsLlcLSAPStatsAddr            DisplayString,
		fsLlcLSAPStatsIfId            INTEGER,
		fsLlcLSAPStatsCircuit         INTEGER,
		fsLlcLSAPStatsInTestCmds      Counter,
		fsLlcLSAPStatsOutTestCmds     Counter,
		fsLlcLSAPStatsInTestRsps      Counter,
		fsLlcLSAPStatsOutTestRsps     Counter,
		fsLlcLSAPStatsInXIDCmds       Counter,
		fsLlcLSAPStatsOutXIDCmds      Counter,
		fsLlcLSAPStatsInXIDRsps       Counter,
		fsLlcLSAPStatsOutXIDRsps      Counter,
		fsLlcLSAPStatsInUIs           Counter,
		fsLlcLSAPStatsOutUIs          Counter
		}

	fsLlcLSAPStatsEntry OBJECT-TYPE
		SYNTAX  FsLlcLSAPStatsEntry
		ACCESS  not-accessible
		STATUS  mandatory
		DESCRIPTION
			"Entries of the fsLlcLSAPTable."
		INDEX   { fsLlcLSAPStatsIndex }
		::= { fsLlcLSAPStatsTable 1 }

	fsLlcLSAPStatsIndex OBJECT-TYPE
		SYNTAX  INTEGER
		ACCESS  read-only
		STATUS  mandatory
		DESCRIPTION
			"The index value for the SAP Table."
		::= { fsLlcLSAPStatsEntry 1 }

	fsLlcLSAPStatsAddr OBJECT-TYPE
		SYNTAX  DisplayString (SIZE (2))
		ACCESS  read-only
		STATUS  mandatory
		DESCRIPTION
			"The SAP (Service Access Point) Address."
		::= { fsLlcLSAPStatsEntry 2 }

	fsLlcLSAPStatsIfId OBJECT-TYPE
		SYNTAX  INTEGER
		ACCESS  read-only
		STATUS  mandatory
		DESCRIPTION
			"The Port number on which this SAP is configured."
		::= { fsLlcLSAPStatsEntry 3 }

	fsLlcLSAPStatsCircuit OBJECT-TYPE
		SYNTAX  INTEGER
		ACCESS  read-only
		STATUS  mandatory
		DESCRIPTION
			"The circuit number for Frame Relay.
			The circuit number is set to 0 for Ethernet and Token
			Ring interfaces."
		::= { fsLlcLSAPStatsEntry 4 }

	fsLlcLSAPStatsInTestCmds OBJECT-TYPE
		SYNTAX  Counter
		ACCESS  read-only
		STATUS  mandatory
		DESCRIPTION
			"Number of Test commands received."
		::= { fsLlcLSAPStatsEntry 5 }

	fsLlcLSAPStatsOutTestCmds OBJECT-TYPE
		SYNTAX  Counter
		ACCESS  read-only
		STATUS  mandatory
		DESCRIPTION
			"Number of Test commands sent."
		::= { fsLlcLSAPStatsEntry 6 }

	fsLlcLSAPStatsInTestRsps OBJECT-TYPE
		SYNTAX  Counter
		ACCESS  read-only
		STATUS  mandatory
		DESCRIPTION
			"Number of Test responses received."
		::= { fsLlcLSAPStatsEntry 7 }

	fsLlcLSAPStatsOutTestRsps OBJECT-TYPE
		SYNTAX  Counter
		ACCESS  read-only
		STATUS  mandatory
		DESCRIPTION
			"Number of Test responses sent."
		::= { fsLlcLSAPStatsEntry 8 }

	fsLlcLSAPStatsInXIDCmds OBJECT-TYPE
		SYNTAX  Counter
		ACCESS  read-only
		STATUS  mandatory
		DESCRIPTION
			"Number of XID commands received."
		::= { fsLlcLSAPStatsEntry 9 }

	fsLlcLSAPStatsOutXIDCmds OBJECT-TYPE
		SYNTAX  Counter
		ACCESS  read-only
		STATUS  mandatory
		DESCRIPTION
			"Number of XID commands sent."
		::= { fsLlcLSAPStatsEntry 10 }

	fsLlcLSAPStatsInXIDRsps OBJECT-TYPE
		SYNTAX  Counter
		ACCESS  read-only
		STATUS  mandatory
		DESCRIPTION
			"Number of XID responses received."
		::= { fsLlcLSAPStatsEntry 11 }

	fsLlcLSAPStatsOutXIDRsps OBJECT-TYPE
		SYNTAX  Counter
		ACCESS  read-only
		STATUS  mandatory
		DESCRIPTION
			"Number of XID responses sent."
		::= { fsLlcLSAPStatsEntry 12 }

	fsLlcLSAPStatsInUIs OBJECT-TYPE
		SYNTAX  Counter
		ACCESS  read-only
		STATUS  mandatory
		DESCRIPTION
			"Number of UI Frames Received."
		::= { fsLlcLSAPStatsEntry 13 }

	fsLlcLSAPStatsOutUIs OBJECT-TYPE
		SYNTAX  Counter
		ACCESS  read-only
		STATUS  mandatory
		DESCRIPTION
			"Number of UI Frames sent."
		::= { fsLlcLSAPStatsEntry 14 }

-- ***************************************************************************
-- SDLC-FR Switching Stats

fsSnaSdlcFrStatsTable OBJECT-TYPE
	SYNTAX  SEQUENCE OF FsSnaSdlcFrStatsEntry
	ACCESS  not-accessible
	STATUS  mandatory
	DESCRIPTION
		"Statistics Table for SDLC-FR Switching. This table
		would contain the SDLC-FR switching entries, indexed by
		the table index 'fsSnaSdlcFrStatsIndex'."
	::= { fsSnaSwStats 1 }

	FsSnaSdlcFrStatsEntry ::= SEQUENCE {
		fsSnaSdlcFrStatsIndex         INTEGER,
		fsSnaSdlcFrStatsLocalMAC      DisplayString,
		fsSnaSdlcFrStatsLocalSAP      DisplayString,
		fsSnaSdlcFrStatsRemoteMAC     DisplayString,
		fsSnaSdlcFrStatsRemoteSAP     DisplayString,
		fsSnaSdlcFrStatsSdlcPortNum   INTEGER,
		fsSnaSdlcFrStatsSdlcStnAddr   DisplayString,
		fsSnaSdlcFrStatsFrPortNum     INTEGER,
		fsSnaSdlcFrStatsFrCircuit     INTEGER,
		fsSnaSdlcFrStatsState         DisplayString
		}

	fsSnaSdlcFrStatsEntry OBJECT-TYPE
		SYNTAX  FsSnaSdlcFrStatsEntry
		ACCESS  not-accessible
		STATUS  mandatory
		DESCRIPTION
			"Statistics Table Entry for SDLC-FR switching scenario."
		INDEX   { fsSnaSdlcFrStatsIndex }
		::= { fsSnaSdlcFrStatsTable 1 }

	fsSnaSdlcFrStatsIndex OBJECT-TYPE
		SYNTAX  INTEGER
		ACCESS  read-only
		STATUS  mandatory
		DESCRIPTION
			"The index value which uniquely identifies this		
			SDLC-FR switching configuration table entry."
		::= { fsSnaSdlcFrStatsEntry 1 }

	fsSnaSdlcFrStatsLocalMAC OBJECT-TYPE
		SYNTAX  DisplayString (SIZE (12))
		ACCESS  read-only
		STATUS  mandatory
		DESCRIPTION
			"The Pseudo-MAC address for this switching entry."
		::= { fsSnaSdlcFrStatsEntry 2 }

	fsSnaSdlcFrStatsLocalSAP OBJECT-TYPE
		SYNTAX  DisplayString (SIZE (2))
		ACCESS  read-only
		STATUS  mandatory
		DESCRIPTION
			"The Pseudo-SAP for this switching entry."
		::= { fsSnaSdlcFrStatsEntry 3 }

	fsSnaSdlcFrStatsRemoteMAC OBJECT-TYPE
		SYNTAX  DisplayString (SIZE (12))
		ACCESS  read-only
		STATUS  mandatory
		DESCRIPTION
			"The Remote MAC address for this switching entry."
		::= { fsSnaSdlcFrStatsEntry 4 }

	fsSnaSdlcFrStatsRemoteSAP OBJECT-TYPE
		SYNTAX  DisplayString (SIZE (2))
		ACCESS  read-only
		STATUS  mandatory
		DESCRIPTION
			"The Remote SAP for this switching entry."
		::= { fsSnaSdlcFrStatsEntry 5 }

	fsSnaSdlcFrStatsSdlcPortNum OBJECT-TYPE
		SYNTAX  INTEGER
		ACCESS  read-only
		STATUS  mandatory
		DESCRIPTION
			"The SDLC Port for this switching entry."
		::= { fsSnaSdlcFrStatsEntry 6 }
 
	fsSnaSdlcFrStatsSdlcStnAddr OBJECT-TYPE
		SYNTAX  DisplayString (SIZE(2))
		ACCESS  read-only
		STATUS  mandatory
		DESCRIPTION
			"The SDLC Station Address for this switching entry."
		::= { fsSnaSdlcFrStatsEntry 7 }

	fsSnaSdlcFrStatsFrPortNum OBJECT-TYPE
		SYNTAX  INTEGER
		ACCESS  read-only
		STATUS  mandatory
		DESCRIPTION
			"The Frame Relay Port for this switching entry."
		::= { fsSnaSdlcFrStatsEntry 8 }

	fsSnaSdlcFrStatsFrCircuit OBJECT-TYPE
		SYNTAX  INTEGER
		ACCESS  read-only
		STATUS  mandatory
		DESCRIPTION
			"The Frame Relay circuit for this switching entry."
		::= { fsSnaSdlcFrStatsEntry 9 }

	fsSnaSdlcFrStatsState OBJECT-TYPE
		SYNTAX  DisplayString (SIZE(0..14))
		ACCESS  read-only
		STATUS  mandatory
		DESCRIPTION
			"The State of this switching session."
		::= { fsSnaSdlcFrStatsEntry 10 }

-- ***************************************************************************
-- LLC-FR Switching Stats

fsSnaLlcFrStatsTable OBJECT-TYPE
	SYNTAX  SEQUENCE OF FsSnaLlcFrStatsEntry
	ACCESS  not-accessible
	STATUS  mandatory
	DESCRIPTION
		"Statistics Table for LLC-FR Switching. This table
		would contain the LLC-FR switching entries, indexed by
		the table index 'fsSnaLlcFrStatsIndex'."
	::= { fsSnaSwStats 2 }

	FsSnaLlcFrStatsEntry ::= SEQUENCE {
		fsSnaLlcFrStatsIndex          INTEGER,
		fsSnaLlcFrStatsLocalMAC       DisplayString,
		fsSnaLlcFrStatsLocalSAP       DisplayString,
		fsSnaLlcFrStatsRemoteMAC      DisplayString,
		fsSnaLlcFrStatsRemoteSAP      DisplayString,
		fsSnaLlcFrStatsLlcPortNum     INTEGER,
		fsSnaLlcFrStatsFrPortNum      INTEGER,
		fsSnaLlcFrStatsFrCircuit      INTEGER,
		fsSnaLlcFrStatsState          DisplayString
		}

	fsSnaLlcFrStatsEntry OBJECT-TYPE
		SYNTAX  FsSnaLlcFrStatsEntry
		ACCESS  not-accessible
		STATUS  mandatory
		DESCRIPTION
			"Statistics Table Entry for LLC-FR switching scenario."
		INDEX   { fsSnaLlcFrStatsIndex }
		::= { fsSnaLlcFrStatsTable 1 }

	fsSnaLlcFrStatsIndex OBJECT-TYPE
		SYNTAX  INTEGER
		ACCESS  read-only
		STATUS  mandatory
		DESCRIPTION
			"The index value which uniquely identifies this
			LLC-FR switching configuration table entry."
		::= { fsSnaLlcFrStatsEntry 1 }

	fsSnaLlcFrStatsLocalMAC OBJECT-TYPE
		SYNTAX  DisplayString (SIZE (12))
		ACCESS  read-only
		STATUS  mandatory
		DESCRIPTION
			"The Local-MAC address for this switching entry."
		::= { fsSnaLlcFrStatsEntry 2 }

	fsSnaLlcFrStatsLocalSAP OBJECT-TYPE
		SYNTAX  DisplayString (SIZE (2))
		ACCESS  read-only
		STATUS  mandatory
		DESCRIPTION
			"The Local-SAP for this switching entry."
		::= { fsSnaLlcFrStatsEntry 3 }

	fsSnaLlcFrStatsRemoteMAC OBJECT-TYPE
		SYNTAX  DisplayString (SIZE (12))
		ACCESS  read-only
		STATUS  mandatory
		DESCRIPTION
			"The Remote MAC address for this switching entry."
		::= { fsSnaLlcFrStatsEntry 4 }

	fsSnaLlcFrStatsRemoteSAP OBJECT-TYPE
		SYNTAX  DisplayString (SIZE (2))
		ACCESS  read-only
		STATUS  mandatory
		DESCRIPTION
			"The Remote SAP for this switching entry."
		::= { fsSnaLlcFrStatsEntry 5 }

	fsSnaLlcFrStatsLlcPortNum OBJECT-TYPE
		SYNTAX  INTEGER
		ACCESS  read-only
		STATUS  mandatory
		DESCRIPTION
			"The LLC Port for this switching entry."
		::= { fsSnaLlcFrStatsEntry 6 }

	fsSnaLlcFrStatsFrPortNum OBJECT-TYPE
		SYNTAX  INTEGER
		ACCESS  read-only
		STATUS  mandatory
		DESCRIPTION
			"The Frame Relay Port for this switching entry."
		::= { fsSnaLlcFrStatsEntry 7 }

	fsSnaLlcFrStatsFrCircuit OBJECT-TYPE
		SYNTAX  INTEGER
		ACCESS  read-only
		STATUS  mandatory
		DESCRIPTION
			"The Frame Relay circuit for this switching entry."
		::= { fsSnaLlcFrStatsEntry 8 }

	fsSnaLlcFrStatsState OBJECT-TYPE
		SYNTAX  DisplayString (SIZE(0..14))
		ACCESS  read-only
		STATUS  mandatory
		DESCRIPTION
			"The State of this switching session."
		::= { fsSnaLlcFrStatsEntry 9 }

-- ***************************************************************************
-- SDLC-LLC Switching Stats

fsSnaSdlcLlcStatsTable OBJECT-TYPE
	SYNTAX  SEQUENCE OF FsSnaSdlcLlcStatsEntry
	ACCESS  not-accessible
	STATUS  mandatory
	DESCRIPTION
		"Statistics Table for SDLC-LLC Switching. This table
		would contain the SDLC-LLC switching entries, indexed by
		the table index 'fsSnaSdlcLlcStatsIndex'."
	::= { fsSnaSwStats 3 }

	FsSnaSdlcLlcStatsEntry ::= SEQUENCE {
		fsSnaSdlcLlcStatsIndex        INTEGER,
		fsSnaSdlcLlcStatsLocalMAC     DisplayString,
		fsSnaSdlcLlcStatsLocalSAP     DisplayString,
		fsSnaSdlcLlcStatsRemoteMAC    DisplayString,
		fsSnaSdlcLlcStatsRemoteSAP    DisplayString,
		fsSnaSdlcLlcStatsLlcPortNum   INTEGER,
		fsSnaSdlcLlcStatsSdlcPortNum  INTEGER,
		fsSnaSdlcLlcStatsSdlcStnAddr  DisplayString,
		fsSnaSdlcLlcStatsState        DisplayString
		}

	fsSnaSdlcLlcStatsEntry OBJECT-TYPE
		SYNTAX  FsSnaSdlcLlcStatsEntry
		ACCESS  not-accessible
		STATUS  mandatory
		DESCRIPTION
			"Statistics Table Entry for SDLC-LLC switching scenario."
		INDEX   { fsSnaSdlcLlcStatsIndex }
		::= { fsSnaSdlcLlcStatsTable 1 }

	fsSnaSdlcLlcStatsIndex OBJECT-TYPE
		SYNTAX  INTEGER
		ACCESS  read-only
		STATUS  mandatory
		DESCRIPTION
			"The index value which uniquely identifies this
			SDLC-LLC switching configuration table entry."
		::= { fsSnaSdlcLlcStatsEntry 1 }

	fsSnaSdlcLlcStatsLocalMAC OBJECT-TYPE
		SYNTAX  DisplayString (SIZE (12))
		ACCESS  read-only
		STATUS  mandatory
		DESCRIPTION
			"The Pseudo-MAC address for this switching entry."
		::= { fsSnaSdlcLlcStatsEntry 2 }

	fsSnaSdlcLlcStatsLocalSAP OBJECT-TYPE
		SYNTAX  DisplayString (SIZE (2))
		ACCESS  read-only
		STATUS  mandatory
		DESCRIPTION
			"The Pseudo-SAP for this switching entry."
		::= { fsSnaSdlcLlcStatsEntry 3 }

	fsSnaSdlcLlcStatsRemoteMAC OBJECT-TYPE
		SYNTAX  DisplayString (SIZE (12))
		ACCESS  read-only
		STATUS  mandatory
		DESCRIPTION
			"The Remote MAC address for this switching entry."
		::= { fsSnaSdlcLlcStatsEntry 4 }

	fsSnaSdlcLlcStatsRemoteSAP OBJECT-TYPE
		SYNTAX  DisplayString (SIZE (2))
		ACCESS  read-only
		STATUS  mandatory
		DESCRIPTION
			"The Remote SAP for this switching entry."
		::= { fsSnaSdlcLlcStatsEntry 5 }

	fsSnaSdlcLlcStatsLlcPortNum OBJECT-TYPE
		SYNTAX  INTEGER
		ACCESS  read-only
		STATUS  mandatory
		DESCRIPTION
			"The LLC Port for this switching entry."
		::= { fsSnaSdlcLlcStatsEntry 6 }

	fsSnaSdlcLlcStatsSdlcPortNum OBJECT-TYPE
		SYNTAX  INTEGER
		ACCESS  read-only
		STATUS  mandatory
		DESCRIPTION
			"The SDLC Port for this switching entry."
		::= { fsSnaSdlcLlcStatsEntry 7 }
 
	fsSnaSdlcLlcStatsSdlcStnAddr OBJECT-TYPE
		SYNTAX  DisplayString (SIZE(2))
		ACCESS  read-only
		STATUS  mandatory
		DESCRIPTION
			"The SDLC Station Address for this switching entry."
		::= { fsSnaSdlcLlcStatsEntry 8 }

	fsSnaSdlcLlcStatsState OBJECT-TYPE
		SYNTAX  DisplayString (SIZE(0..14))
		ACCESS  read-only
		STATUS  mandatory
		DESCRIPTION
			"The State of this switching session."
		::= { fsSnaSdlcLlcStatsEntry 9 }

-- ***************************************************************************
-- T1 DSU Stats

fsT1DsuStatsTable OBJECT-TYPE
	SYNTAX  SEQUENCE OF FsT1DsuStatsEntry
	ACCESS  not-accessible
	STATUS  mandatory
	DESCRIPTION  ""
	::= { fsT1DsuStats 1 }

	FsT1DsuStatsEntry ::= SEQUENCE {
		fsT1DsuStatsTableIndex        INTEGER,
		fsT1DsuStatsBipolar           Counter,
		fsT1DsuStatsCRCError          Counter,
		fsT1DsuStatsFrameLoss         Counter,
		fsT1DsuStatsFrameError        Counter,
		fsT1DsuStatsErrorEvent        Counter,
		fsT1DsuStatsErrorSecond       Counter,
		fsT1DsuStatsSevereSecond      Counter,
		fsT1DsuStatsAvailSecond       Counter,
		fsT1DsuStatsUnavailSecond     Counter,
		fsT1DsuStatsAlarmRed          DisplayString,
		fsT1DsuStatsAlarmYellow       DisplayString,
		fsT1DsuStatsAlarmBlue         DisplayString,
		fsT1DsuStatsAlarmOOF          DisplayString,
		fsT1DsuStatsLocAnaLoopback    DisplayString,
		fsT1DsuStatsLocDigLoopback    DisplayString,
		fsT1DsuStatsRemAnaLoopback    DisplayString,
		fsT1DsuStatsRemDigLoopback    DisplayString
		}

	fsT1DsuStatsEntry OBJECT-TYPE
		SYNTAX  FsT1DsuStatsEntry
		ACCESS  not-accessible
		STATUS  mandatory
		DESCRIPTION ""
		INDEX { fsT1DsuStatsTableIndex }
		::= { fsT1DsuStatsTable 1 }

	fsT1DsuStatsTableIndex OBJECT-TYPE
		SYNTAX  INTEGER 
		ACCESS  read-only
		STATUS  mandatory
		DESCRIPTION ""
		::= { fsT1DsuStatsEntry 1 }

	fsT1DsuStatsBipolar OBJECT-TYPE
		SYNTAX  Counter
		ACCESS  read-only
		STATUS  mandatory
		DESCRIPTION ""
		::= { fsT1DsuStatsEntry 2 }

	fsT1DsuStatsCRCError OBJECT-TYPE
		SYNTAX  Counter
		ACCESS  read-only
		STATUS  mandatory
		DESCRIPTION ""
		::= { fsT1DsuStatsEntry 3 }

	fsT1DsuStatsFrameLoss OBJECT-TYPE
		SYNTAX  Counter
		ACCESS  read-only
		STATUS  mandatory
		DESCRIPTION ""
		::= { fsT1DsuStatsEntry 4 }

	fsT1DsuStatsFrameError OBJECT-TYPE
		SYNTAX  Counter
		ACCESS  read-only
		STATUS  mandatory
		DESCRIPTION ""
		::= { fsT1DsuStatsEntry 5 }

	fsT1DsuStatsErrorEvent OBJECT-TYPE
		SYNTAX  Counter
		ACCESS  read-only
		STATUS  mandatory
		DESCRIPTION ""
		::= { fsT1DsuStatsEntry 6 }

	fsT1DsuStatsErrorSecond OBJECT-TYPE
		SYNTAX  Counter
		ACCESS  read-only
		STATUS  mandatory
		DESCRIPTION ""
		::= { fsT1DsuStatsEntry 7 }

	fsT1DsuStatsSevereSecond OBJECT-TYPE
		SYNTAX  Counter
		ACCESS  read-only
		STATUS  mandatory
		DESCRIPTION ""
		::= { fsT1DsuStatsEntry 8 }

	fsT1DsuStatsAvailSecond OBJECT-TYPE
		SYNTAX  Counter
		ACCESS  read-only
		STATUS  mandatory
		DESCRIPTION ""
		::= { fsT1DsuStatsEntry 9 }

	fsT1DsuStatsUnavailSecond OBJECT-TYPE
		SYNTAX  Counter
		ACCESS  read-only
		STATUS  mandatory
		DESCRIPTION ""
		::= { fsT1DsuStatsEntry 10 }

	fsT1DsuStatsAlarmRed OBJECT-TYPE
		SYNTAX  DisplayString (SIZE (0..7))
		ACCESS  read-only
		STATUS  mandatory
		DESCRIPTION ""
		::= { fsT1DsuStatsEntry 11 }

	fsT1DsuStatsAlarmYellow OBJECT-TYPE
		SYNTAX  DisplayString (SIZE (0..7))
		ACCESS  read-only
		STATUS  mandatory
		DESCRIPTION ""
		::= { fsT1DsuStatsEntry 12 }

	fsT1DsuStatsAlarmBlue OBJECT-TYPE
		SYNTAX  DisplayString (SIZE (0..7))
		ACCESS  read-only
		STATUS  mandatory
		DESCRIPTION ""
		::= { fsT1DsuStatsEntry 13 }

	fsT1DsuStatsAlarmOOF OBJECT-TYPE
		SYNTAX  DisplayString (SIZE (0..7))
		ACCESS  read-only
		STATUS  mandatory
		DESCRIPTION ""
		::= { fsT1DsuStatsEntry 14 }

	fsT1DsuStatsLocAnaLoopback OBJECT-TYPE
		SYNTAX  DisplayString (SIZE (0..7))
		ACCESS  read-only
		STATUS  mandatory
		DESCRIPTION ""
		::= { fsT1DsuStatsEntry 15 }

	fsT1DsuStatsLocDigLoopback OBJECT-TYPE
		SYNTAX  DisplayString (SIZE (0..7))
		ACCESS  read-only
		STATUS  mandatory
		DESCRIPTION ""
		::= { fsT1DsuStatsEntry 16 }

	fsT1DsuStatsRemAnaLoopback OBJECT-TYPE
		SYNTAX  DisplayString (SIZE (0..7))
		ACCESS  read-only
		STATUS  mandatory
		DESCRIPTION ""
		::= { fsT1DsuStatsEntry 17 }

	fsT1DsuStatsRemDigLoopback OBJECT-TYPE
		SYNTAX  DisplayString (SIZE (0..7))
		ACCESS  read-only
		STATUS  mandatory
		DESCRIPTION ""
		::= { fsT1DsuStatsEntry 18 }

-- ***************************************************************************
-- E1 DSU Stats

fsE1DsuStatsTable OBJECT-TYPE
	SYNTAX  SEQUENCE OF FsE1DsuStatsEntry
	ACCESS  not-accessible
	STATUS  mandatory
	DESCRIPTION  ""
	::= { fsE1DsuStats 1 }

	FsE1DsuStatsEntry ::= SEQUENCE {
		fsE1DsuStatsTableIndex        INTEGER,
		fsE1DsuStatsCodeVio           Counter,
		fsE1DsuStatsCRC4Error         Counter,
		fsE1DsuStatsEbitError         Counter,
		fsE1DsuStatsFASbitError       Counter,
		fsE1DsuStatsAvailSec          Counter,
		fsE1DsuStatsErrorEvent        Counter,
		fsE1DsuStatsErrorSecond       Counter,
		fsE1DsuStatsBustyErrSecond    Counter,
		fsE1DsuStatsSeverErrSecond    Counter,
		fsE1DsuStatsUnavailSecond     Counter,
		fsE1DsuStatsAlarmLOS          DisplayString,
		fsE1DsuStatsAlarmFAS          DisplayString,
		fsE1DsuStatsAlarmAISRx        DisplayString,
		fsE1DsuStatsAlarmLOMF         DisplayString,
		fsE1DsuStatsAlarmLOF          DisplayString,
		fsE1DsuStatsAlarmRAI          DisplayString
		}

	fsE1DsuStatsEntry OBJECT-TYPE
		SYNTAX  FsE1DsuStatsEntry
		ACCESS  not-accessible
		STATUS  mandatory
		DESCRIPTION ""
		INDEX { fsE1DsuStatsTableIndex }
		::= { fsE1DsuStatsTable 1 }

	fsE1DsuStatsTableIndex OBJECT-TYPE
		SYNTAX  INTEGER 
		ACCESS  read-only
		STATUS  mandatory
		DESCRIPTION ""
		::= { fsE1DsuStatsEntry 1 }

	fsE1DsuStatsCodeVio OBJECT-TYPE
		SYNTAX  Counter
		ACCESS  read-only
		STATUS  mandatory
		DESCRIPTION ""
		::= { fsE1DsuStatsEntry 2 }

	fsE1DsuStatsCRC4Error OBJECT-TYPE
		SYNTAX  Counter
		ACCESS  read-only
		STATUS  mandatory
		DESCRIPTION ""
		::= { fsE1DsuStatsEntry 3 }

	fsE1DsuStatsEbitError OBJECT-TYPE
		SYNTAX  Counter
		ACCESS  read-only
		STATUS  mandatory
		DESCRIPTION ""
		::= { fsE1DsuStatsEntry 4 }

	fsE1DsuStatsFASbitError OBJECT-TYPE
		SYNTAX  Counter
		ACCESS  read-only
		STATUS  mandatory
		DESCRIPTION ""
		::= { fsE1DsuStatsEntry 5 }

	fsE1DsuStatsAvailSec OBJECT-TYPE
		SYNTAX  Counter
		ACCESS  read-only
		STATUS  mandatory
		DESCRIPTION ""
		::= { fsE1DsuStatsEntry 6 }

	fsE1DsuStatsErrorEvent OBJECT-TYPE
		SYNTAX  Counter
		ACCESS  read-only
		STATUS  mandatory
		DESCRIPTION ""
		::= { fsE1DsuStatsEntry 7 }

	fsE1DsuStatsErrorSecond OBJECT-TYPE
		SYNTAX  Counter
		ACCESS  read-only
		STATUS  mandatory
		DESCRIPTION ""
		::= { fsE1DsuStatsEntry 8 }

	fsE1DsuStatsBustyErrSecond OBJECT-TYPE
		SYNTAX  Counter
		ACCESS  read-only
		STATUS  mandatory
		DESCRIPTION ""
		::= { fsE1DsuStatsEntry 9 }

	fsE1DsuStatsSeverErrSecond OBJECT-TYPE
		SYNTAX  Counter
		ACCESS  read-only
		STATUS  mandatory
		DESCRIPTION ""
		::= { fsE1DsuStatsEntry 10 }

	fsE1DsuStatsUnavailSecond OBJECT-TYPE
		SYNTAX  Counter
		ACCESS  read-only
		STATUS  mandatory
		DESCRIPTION ""
		::= { fsE1DsuStatsEntry 11 }

	fsE1DsuStatsAlarmLOS OBJECT-TYPE
		SYNTAX  DisplayString (SIZE (0..7))
		ACCESS  read-only
		STATUS  mandatory
		DESCRIPTION ""
		::= { fsE1DsuStatsEntry 12 }

	fsE1DsuStatsAlarmFAS OBJECT-TYPE
		SYNTAX  DisplayString (SIZE (0..7))
		ACCESS  read-only
		STATUS  mandatory
		DESCRIPTION ""
		::= { fsE1DsuStatsEntry 13 }

	fsE1DsuStatsAlarmAISRx OBJECT-TYPE
		SYNTAX  DisplayString (SIZE (0..7))
		ACCESS  read-only
		STATUS  mandatory
		DESCRIPTION ""
		::= { fsE1DsuStatsEntry 14 }

	fsE1DsuStatsAlarmLOMF OBJECT-TYPE
		SYNTAX  DisplayString (SIZE (0..7))
		ACCESS  read-only
		STATUS  mandatory
		DESCRIPTION ""
		::= { fsE1DsuStatsEntry 15 }

	fsE1DsuStatsAlarmLOF OBJECT-TYPE
		SYNTAX  DisplayString (SIZE (0..7))
		ACCESS  read-only
		STATUS  mandatory
		DESCRIPTION ""
		::= { fsE1DsuStatsEntry 16 }

	fsE1DsuStatsAlarmRAI OBJECT-TYPE
		SYNTAX  DisplayString (SIZE (0..7))
		ACCESS  read-only
		STATUS  mandatory
		DESCRIPTION ""
		::= { fsE1DsuStatsEntry 17 }

-- ***************************************************************************
-- X25 New Stats

fsX25NewL1StatsTable OBJECT-TYPE
	SYNTAX  SEQUENCE OF FsX25NewL1StatsEntry
	ACCESS  not-accessible
	STATUS  mandatory
	DESCRIPTION ""
	::= { fsX25NewStats 1 }

	FsX25NewL1StatsEntry ::= SEQUENCE {
		fsX25NewL1StatsPort                INTEGER,
            fsX25NewL1RxOverFrames             Counter,
            fsX25NewL1NonOctetAligned          Counter,
		fsX25NewL1StatsCRCErrors           Counter,
            fsX25NewL1RxAbout                  Counter,
		fsX25NewL1StatsRxOverruns          Counter,
		fsX25NewL1StatsTxUnderruns         Counter,
		fsX25NewL1RTS	 	           DisplayString,
		fsX25NewL1CTS	 	           DisplayString,
		fsX25NewL1DTR	 	           DisplayString,
		fsX25NewL1DSR	 	           DisplayString,
		fsX25NewL1DCD	 	           DisplayString
		}


	fsX25NewL1StatsEntry OBJECT-TYPE
    		SYNTAX  FsX25NewL1StatsEntry
    		ACCESS  not-accessible
    		STATUS  mandatory
    		DESCRIPTION ""
    		INDEX   { fsX25NewL1StatsPort }
    		::= { fsX25NewL1StatsTable  1 }

	fsX25NewL1StatsPort OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
    		ACCESS  read-only
    		STATUS  mandatory
    		DESCRIPTION ""
    		::= { fsX25NewL1StatsEntry  1 }

	fsX25NewL1RxOverFrames OBJECT-TYPE
    		SYNTAX  Counter
    		ACCESS  read-only
    		STATUS  mandatory
    		DESCRIPTION ""
    		::= { fsX25NewL1StatsEntry  2   }

	fsX25NewL1NonOctetAligned OBJECT-TYPE
    		SYNTAX  Counter
    		ACCESS  read-only
    		STATUS  mandatory
    		DESCRIPTION ""
    		::= { fsX25NewL1StatsEntry 3  }

	fsX25NewL1StatsCRCErrors OBJECT-TYPE
    		SYNTAX  Counter
    		ACCESS  read-only
    		STATUS  mandatory
    		DESCRIPTION ""
    		::= { fsX25NewL1StatsEntry  4 }

	fsX25NewL1RxAbout OBJECT-TYPE
    		SYNTAX  Counter
    		ACCESS  read-only
    		STATUS  mandatory
    		DESCRIPTION ""
    		::= { fsX25NewL1StatsEntry 5  }

	fsX25NewL1StatsRxOverruns OBJECT-TYPE
    		SYNTAX  Counter
    		ACCESS  read-only
    		STATUS  mandatory
    		DESCRIPTION ""
    		::= { fsX25NewL1StatsEntry 6  }

	fsX25NewL1StatsTxUnderruns OBJECT-TYPE
    		SYNTAX  Counter
    		ACCESS  read-only
    		STATUS  mandatory
    		DESCRIPTION ""
    		::= { fsX25NewL1StatsEntry 7  }

	fsX25NewL1RTS OBJECT-TYPE
    		SYNTAX  DisplayString
    		ACCESS  read-only
    		STATUS  mandatory
    		DESCRIPTION ""
    		::= { fsX25NewL1StatsEntry 8  }

	fsX25NewL1CTS OBJECT-TYPE
    		SYNTAX  DisplayString
    		ACCESS  read-only
    		STATUS  mandatory
    		DESCRIPTION ""
    		::= { fsX25NewL1StatsEntry 9  }

	fsX25NewL1DTR OBJECT-TYPE
    		SYNTAX  DisplayString
    		ACCESS  read-only
    		STATUS  mandatory
    		DESCRIPTION ""
    		::= { fsX25NewL1StatsEntry 10  }

	fsX25NewL1DSR OBJECT-TYPE
    		SYNTAX  DisplayString
    		ACCESS  read-only
    		STATUS  mandatory
    		DESCRIPTION ""
    		::= { fsX25NewL1StatsEntry 11  }

	fsX25NewL1DCD OBJECT-TYPE
    		SYNTAX  DisplayString
    		ACCESS  read-only
    		STATUS  mandatory
    		DESCRIPTION ""
    		::= { fsX25NewL1StatsEntry 12  }

fsX25NewL2StatsTable OBJECT-TYPE
	SYNTAX  SEQUENCE OF FsX25NewL2StatsEntry
	ACCESS  not-accessible
	STATUS  mandatory
	DESCRIPTION
		"Statistics Table for Lapb Stats." 
	::= { fsX25NewStats 2 }

	FsX25NewL2StatsEntry ::= SEQUENCE {
		fsX25NewL2StatsPort                INTEGER,
		fsX25NewL2StatsFramesRcvd          Counter,
		fsX25NewL2StatsFramesSent          Counter,
		fsX25NewL2StatsBytesRcvd           Counter,
		fsX25NewL2StatsBytesSent           Counter,
		fsX25NewL2StatsRejectsRcvd         Counter,
		fsX25NewL2StatsRejectsSent         Counter,
		fsX25NewL2StatsFrmrRcvd            Counter,
		fsX25NewL2StatsFrmrSent            Counter,
		fsX25NewL2StatsRNRsRcvd            Counter,
		fsX25NewL2StatsRNRsSent            Counter,
		fsX25NewL2StatsLocalLinkResets     Counter,
		fsX25NewL2StatsRemoteLinkResets    Counter,
		fsX25NewL2StatsFramesRcvdfromL3    Counter,
		fsX25NewL2StatsReXmissions         Counter,
		fsX25NewL2StatsTxFailures          Counter,
		fsX25NewL2StatsTxerrors            Counter,
		fsX25NewL2StatsInvalidFramesRcvd   Counter,
		fsX25NewL2StatsIncorrectFramesRcvd Counter,
		fsX25NewL2StatsFramesDiscarded     Counter,
		fsX25NewL2StatsFramestooLong       Counter,
		fsX25NewL2StatsT1Recoveries        Counter,
		fsX25NewL2StatsT2Timeouts          Counter,
		fsX25NewL2StatsT3Timeouts          Counter
		}


	fsX25NewL2StatsEntry OBJECT-TYPE
    		SYNTAX  FsX25NewL2StatsEntry
    		ACCESS  not-accessible
    		STATUS  mandatory
    		DESCRIPTION
	   		"A list of statistics for an X25NEW port."
    		INDEX   { fsX25NewL2StatsPort }
    		::= { fsX25NewL2StatsTable  1 }

	fsX25NewL2StatsPort OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
    		ACCESS  read-only
    		STATUS  mandatory
    		DESCRIPTION ""
    		::= { fsX25NewL2StatsEntry  1 }

	fsX25NewL2StatsFramesRcvd OBJECT-TYPE
    		SYNTAX  Counter
    		ACCESS  read-only
    		STATUS  mandatory
    		DESCRIPTION ""
    		::= { fsX25NewL2StatsEntry  2   }

	fsX25NewL2StatsFramesSent OBJECT-TYPE
    		SYNTAX  Counter
    		ACCESS  read-only
    		STATUS  mandatory
    		DESCRIPTION ""
    		::= { fsX25NewL2StatsEntry 3  }

	fsX25NewL2StatsBytesRcvd OBJECT-TYPE
    		SYNTAX  Counter
    		ACCESS  read-only
    		STATUS  mandatory
    		DESCRIPTION ""
    		::= { fsX25NewL2StatsEntry  4 }

	fsX25NewL2StatsBytesSent OBJECT-TYPE
    		SYNTAX  Counter
    		ACCESS  read-only
    		STATUS  mandatory
    		DESCRIPTION ""
    		::= { fsX25NewL2StatsEntry 5  }

	fsX25NewL2StatsRejectsRcvd OBJECT-TYPE
    		SYNTAX  Counter
    		ACCESS  read-only
    		STATUS  mandatory
    		DESCRIPTION ""
    		::= { fsX25NewL2StatsEntry 6  }

	fsX25NewL2StatsRejectsSent OBJECT-TYPE
    		SYNTAX  Counter
    		ACCESS  read-only
    		STATUS  mandatory
    		DESCRIPTION ""
    		::= { fsX25NewL2StatsEntry 7  }

	fsX25NewL2StatsFrmrRcvd OBJECT-TYPE
    		SYNTAX  Counter
    		ACCESS  read-only
    		STATUS  mandatory
    		DESCRIPTION ""
    		::= { fsX25NewL2StatsEntry 8  }

	fsX25NewL2StatsFrmrSent OBJECT-TYPE
    		SYNTAX  Counter
    		ACCESS  read-only
    		STATUS  mandatory
    		DESCRIPTION ""
    		::= { fsX25NewL2StatsEntry 9  }

	fsX25NewL2StatsRNRsRcvd OBJECT-TYPE
    		SYNTAX  Counter
    		ACCESS  read-only
    		STATUS  mandatory
    		DESCRIPTION ""
    		::= { fsX25NewL2StatsEntry 10  }

	fsX25NewL2StatsRNRsSent OBJECT-TYPE
    		SYNTAX  Counter
    		ACCESS  read-only
    		STATUS  mandatory
    		DESCRIPTION ""
    		::= { fsX25NewL2StatsEntry 11  }

	fsX25NewL2StatsLocalLinkResets OBJECT-TYPE
    		SYNTAX  Counter
    		ACCESS  read-only
    		STATUS  mandatory
    		DESCRIPTION ""
    		::= { fsX25NewL2StatsEntry 12  }

	fsX25NewL2StatsRemoteLinkResets OBJECT-TYPE
    		SYNTAX  Counter
    		ACCESS  read-only
    		STATUS  mandatory
    		DESCRIPTION ""
    		::= { fsX25NewL2StatsEntry 13  }

	fsX25NewL2StatsFramesRcvdfromL3 OBJECT-TYPE
    		SYNTAX  Counter
    		ACCESS  read-only
    		STATUS  mandatory
    		DESCRIPTION ""
    		::= { fsX25NewL2StatsEntry 14  }

	fsX25NewL2StatsReXmissions OBJECT-TYPE
    		SYNTAX  Counter
    		ACCESS  read-only
    		STATUS  mandatory
    		DESCRIPTION ""
    		::= { fsX25NewL2StatsEntry 15  }

	fsX25NewL2StatsTxFailures OBJECT-TYPE
    		SYNTAX  Counter
    		ACCESS  read-only
    		STATUS  mandatory
    		DESCRIPTION ""
    		::= { fsX25NewL2StatsEntry 16  }

	fsX25NewL2StatsTxerrors OBJECT-TYPE
    		SYNTAX  Counter
    		ACCESS  read-only
    		STATUS  mandatory
    		DESCRIPTION ""
    		::= { fsX25NewL2StatsEntry 17  }

	fsX25NewL2StatsInvalidFramesRcvd OBJECT-TYPE
    		SYNTAX  Counter
    		ACCESS  read-only
    		STATUS  mandatory
    		DESCRIPTION ""
    		::= { fsX25NewL2StatsEntry 18  }

	fsX25NewL2StatsIncorrectFramesRcvd OBJECT-TYPE
    		SYNTAX  Counter
    		ACCESS  read-only
    		STATUS  mandatory
    		DESCRIPTION ""
    		::= { fsX25NewL2StatsEntry 19  }

	fsX25NewL2StatsFramesDiscarded OBJECT-TYPE
    		SYNTAX  Counter
    		ACCESS  read-only
    		STATUS  mandatory
    		DESCRIPTION ""
    		::= { fsX25NewL2StatsEntry 20  }

	fsX25NewL2StatsFramestooLong OBJECT-TYPE
    		SYNTAX  Counter
    		ACCESS  read-only
    		STATUS  mandatory
    		DESCRIPTION ""
    		::= { fsX25NewL2StatsEntry 21  }

	fsX25NewL2StatsT1Recoveries OBJECT-TYPE
    		SYNTAX  Counter
    		ACCESS  read-only
    		STATUS  mandatory
    		DESCRIPTION ""
    		::= { fsX25NewL2StatsEntry 22  }

	fsX25NewL2StatsT2Timeouts OBJECT-TYPE
    		SYNTAX  Counter
    		ACCESS  read-only
    		STATUS  mandatory
    		DESCRIPTION ""
    		::= { fsX25NewL2StatsEntry 23  }

	fsX25NewL2StatsT3Timeouts OBJECT-TYPE
    		SYNTAX  Counter
    		ACCESS  read-only
    		STATUS  mandatory
    		DESCRIPTION ""
    		::= { fsX25NewL2StatsEntry 24  }

-- ***************************************************************************
-- Plp Port Stats

fsX25NewL3PortStatsTable OBJECT-TYPE
	SYNTAX  SEQUENCE OF FsX25NewL3PortStatsEntry
	ACCESS  not-accessible
	STATUS  mandatory
	DESCRIPTION
		" "
	::= { fsX25NewStats  3 }

	FsX25NewL3PortStatsEntry ::= SEQUENCE {
		fsX25NewL3StatsPort				INTEGER,
		fsX25NewL3StatsInCalls                    Counter,
		fsX25NewL3StatsOutCalls                   Counter,
		fsX25NewL3StatsInCallRefusal              Counter,
		fsX25NewL3StatsOutCallFailures            Counter,
		fsX25NewL3StatsInRemoteResets             Counter,
		fsX25NewL3StatsOutResets                  Counter,
		fsX25NewL3StatsInDataPkts                 Counter,
		fsX25NewL3StatsOutDataPkts                Counter,
		fsX25NewL3StatsInDataPktsDiscarded        Counter,
		fsX25NewL3StatsOutDataPktsDiscarded       Counter,
		fsX25NewL3StatsInRNRs                     Counter,
		fsX25NewL3StatsOutRNRs                    Counter,
		fsX25NewL3StatsInInterrupts               Counter,
		fsX25NewL3StatsOutInterrupts              Counter,
		fsX25NewL3StatsInDataBytes                Counter,
		fsX25NewL3StatsOutDataBytes               Counter,
		fsX25NewL3StatsInProviderResets           Counter,
		fsX25NewL3StatsInRestarts                 Counter,
		fsX25NewL3StatsInProviderClear            Counter,
		fsX25NewL3StatsInRemoteClears             Counter,
		fsX25NewL3StatsInErrorPkts                Counter,
		fsX25NewL3StatsInPktsTooShort             Counter,
		fsX25NewL3StatsInPktsTooBig               Counter,
		fsX25NewL3StatsInUnassignLCs              Counter
		}

	fsX25NewL3PortStatsEntry OBJECT-TYPE
		SYNTAX  FsX25NewL3PortStatsEntry
		ACCESS  not-accessible
		STATUS  mandatory
		DESCRIPTION ""
		INDEX   { fsX25NewL3StatsPort }
		::= { fsX25NewL3PortStatsTable  1 }

	fsX25NewL3StatsPort OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-only
		STATUS  mandatory
		DESCRIPTION "" 
		::= { fsX25NewL3PortStatsEntry  1 }

	fsX25NewL3StatsInCalls OBJECT-TYPE
		SYNTAX  Counter 
		ACCESS  read-only
		STATUS  mandatory
		DESCRIPTION ""
		::= { fsX25NewL3PortStatsEntry 2  }

	fsX25NewL3StatsOutCalls OBJECT-TYPE
		SYNTAX  Counter 
		ACCESS  read-only
		STATUS  mandatory
		DESCRIPTION ""
		::= { fsX25NewL3PortStatsEntry 3  }

	fsX25NewL3StatsInCallRefusal OBJECT-TYPE
		SYNTAX  Counter 
		ACCESS  read-only
		STATUS  mandatory
		DESCRIPTION ""
		::= { fsX25NewL3PortStatsEntry 4  }

	fsX25NewL3StatsOutCallFailures OBJECT-TYPE
		SYNTAX  Counter 
		ACCESS  read-only
		STATUS  mandatory
		DESCRIPTION ""
		::= { fsX25NewL3PortStatsEntry 5  }

	fsX25NewL3StatsInRemoteResets OBJECT-TYPE
		SYNTAX  Counter 
		ACCESS  read-only
		STATUS  mandatory
		DESCRIPTION ""
		::= { fsX25NewL3PortStatsEntry 6  }

	fsX25NewL3StatsOutResets OBJECT-TYPE
		SYNTAX  Counter 
		ACCESS  read-only
		STATUS  mandatory
		DESCRIPTION ""
		::= { fsX25NewL3PortStatsEntry 7  }

	fsX25NewL3StatsInDataPkts OBJECT-TYPE
		SYNTAX  Counter 
		ACCESS  read-only
		STATUS  mandatory
		DESCRIPTION ""
		::= { fsX25NewL3PortStatsEntry 8  }

	fsX25NewL3StatsOutDataPkts OBJECT-TYPE
		SYNTAX  Counter 
		ACCESS  read-only
		STATUS  mandatory
		DESCRIPTION ""
		::= { fsX25NewL3PortStatsEntry 9  }

	fsX25NewL3StatsInDataPktsDiscarded OBJECT-TYPE
		SYNTAX  Counter 
		ACCESS  read-only
		STATUS  mandatory
		DESCRIPTION ""
		::= { fsX25NewL3PortStatsEntry 10  }

	fsX25NewL3StatsOutDataPktsDiscarded OBJECT-TYPE
		SYNTAX  Counter 
		ACCESS  read-only
		STATUS  mandatory
		DESCRIPTION ""
		::= { fsX25NewL3PortStatsEntry 11  }

	fsX25NewL3StatsInRNRs OBJECT-TYPE
		SYNTAX  Counter 
		ACCESS  read-only
		STATUS  mandatory
		DESCRIPTION ""
		::= { fsX25NewL3PortStatsEntry  12 }

	fsX25NewL3StatsOutRNRs OBJECT-TYPE
		SYNTAX  Counter 
		ACCESS  read-only
		STATUS  mandatory
		DESCRIPTION ""
		::= { fsX25NewL3PortStatsEntry  13 }

	fsX25NewL3StatsInInterrupts OBJECT-TYPE
		SYNTAX  Counter 
		ACCESS  read-only
		STATUS  mandatory
		DESCRIPTION ""
		::= { fsX25NewL3PortStatsEntry 14  }

	fsX25NewL3StatsOutInterrupts OBJECT-TYPE
		SYNTAX  Counter 
		ACCESS  read-only
		STATUS  mandatory
		DESCRIPTION ""
		::= { fsX25NewL3PortStatsEntry 15  }

	fsX25NewL3StatsInDataBytes OBJECT-TYPE
		SYNTAX  Counter 
		ACCESS  read-only
		STATUS  mandatory
		DESCRIPTION ""
		::= { fsX25NewL3PortStatsEntry 16  }

	fsX25NewL3StatsOutDataBytes OBJECT-TYPE
		SYNTAX  Counter 
		ACCESS  read-only
		STATUS  mandatory
		DESCRIPTION ""
		::= { fsX25NewL3PortStatsEntry 17  }

	fsX25NewL3StatsInProviderResets OBJECT-TYPE
		SYNTAX  Counter 
		ACCESS  read-only
		STATUS  mandatory
		DESCRIPTION ""
		::= { fsX25NewL3PortStatsEntry 18  }

	fsX25NewL3StatsInRestarts OBJECT-TYPE
		SYNTAX  Counter 
		ACCESS  read-only
		STATUS  mandatory
		DESCRIPTION ""
		::= { fsX25NewL3PortStatsEntry 19  }

	fsX25NewL3StatsInProviderClear OBJECT-TYPE
		SYNTAX  Counter 
		ACCESS  read-only
		STATUS  mandatory
		DESCRIPTION ""
		::= { fsX25NewL3PortStatsEntry  20 }

	fsX25NewL3StatsInRemoteClears OBJECT-TYPE
		SYNTAX  Counter 
		ACCESS  read-only
		STATUS  mandatory
		DESCRIPTION ""
		::= { fsX25NewL3PortStatsEntry  21 }

	fsX25NewL3StatsInErrorPkts OBJECT-TYPE
		SYNTAX  Counter 
		ACCESS  read-only
		STATUS  mandatory
		DESCRIPTION ""
		::= { fsX25NewL3PortStatsEntry  22 }

	fsX25NewL3StatsInPktsTooShort OBJECT-TYPE
		SYNTAX  Counter 
		ACCESS  read-only
		STATUS  mandatory
		DESCRIPTION ""
		::= { fsX25NewL3PortStatsEntry  23 }

	fsX25NewL3StatsInPktsTooBig OBJECT-TYPE
		SYNTAX  Counter 
		ACCESS  read-only
		STATUS  mandatory
		DESCRIPTION ""
		::= { fsX25NewL3PortStatsEntry  24 }

	fsX25NewL3StatsInUnassignLCs OBJECT-TYPE
		SYNTAX  Counter 
		ACCESS  read-only
		STATUS  mandatory
		DESCRIPTION ""
		::= { fsX25NewL3PortStatsEntry  25 }

-- ***************************************************************************
-- Plp Port Stats1

fsX25NewL3PortStats1Table OBJECT-TYPE
	SYNTAX  SEQUENCE OF FsX25NewL3PortStats1Entry
	ACCESS  not-accessible
	STATUS  mandatory
	DESCRIPTION
		" "
	::= { fsX25NewStats  4 }

	FsX25NewL3PortStats1Entry ::= SEQUENCE {
		fsX25NewL3Stats1Port				INTEGER,
		fsX25NewL3StatsActivePVCs                 Counter,
		fsX25NewL3StatsActiveSVCs                 Counter,
		fsX25NewL3StatsRestartTimeouts            Counter,
		fsX25NewL3StatsResetTimeouts              Counter,
		fsX25NewL3StatsCallTimeouts               Counter,
		fsX25NewL3StatsClearTimeouts              Counter,
		fsX25NewL3StatsLastCause                  Counter,
		fsX25NewL3StatsLastDiag                   Counter,
		fsX25NewL3StatsRetryCountExceededs        Counter,
		fsX25NewL3StatsClearCountExceededs        Counter,
		fsX25NewL3StatsLinkFailures               Counter,
		fsX25NewL3StatsPeakOutQLength             Counter,
		fsX25NewL3StatsDataBytesToL4              Counter,
		fsX25NewL3StatsDataBytesFromL4            Counter,
		fsX25NewL3StatsDataPktsToL4               Counter,
		fsX25NewL3StatsDataPktsFromL4             Counter
		}

	fsX25NewL3PortStats1Entry OBJECT-TYPE
		SYNTAX  FsX25NewL3PortStats1Entry
		ACCESS  not-accessible
		STATUS  mandatory
		DESCRIPTION ""
		INDEX   { fsX25NewL3Stats1Port }
		::= { fsX25NewL3PortStats1Table  1 }

	fsX25NewL3Stats1Port OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-only
		STATUS  mandatory
		DESCRIPTION "" 
		::= { fsX25NewL3PortStats1Entry  1 }

	fsX25NewL3StatsActivePVCs OBJECT-TYPE
		SYNTAX  Counter 
		ACCESS  read-only
		STATUS  mandatory
		DESCRIPTION ""
		::= { fsX25NewL3PortStats1Entry 2  }

	fsX25NewL3StatsActiveSVCs OBJECT-TYPE
		SYNTAX  Counter 
		ACCESS  read-only
		STATUS  mandatory
		DESCRIPTION ""
		::= { fsX25NewL3PortStats1Entry 3  }

	fsX25NewL3StatsRestartTimeouts OBJECT-TYPE
		SYNTAX  Counter 
		ACCESS  read-only
		STATUS  mandatory
		DESCRIPTION ""
		::= { fsX25NewL3PortStats1Entry 4  }

	fsX25NewL3StatsResetTimeouts OBJECT-TYPE
		SYNTAX  Counter 
		ACCESS  read-only
		STATUS  mandatory
		DESCRIPTION ""
		::= { fsX25NewL3PortStats1Entry  5 }

	fsX25NewL3StatsCallTimeouts OBJECT-TYPE
		SYNTAX  Counter 
		ACCESS  read-only
		STATUS  mandatory
		DESCRIPTION ""
		::= { fsX25NewL3PortStats1Entry 6  }

	fsX25NewL3StatsClearTimeouts OBJECT-TYPE
		SYNTAX  Counter 
		ACCESS  read-only
		STATUS  mandatory
		DESCRIPTION ""
		::= { fsX25NewL3PortStats1Entry 7  }

	fsX25NewL3StatsLastCause OBJECT-TYPE
		SYNTAX  Counter 
		ACCESS  read-only
		STATUS  mandatory
		DESCRIPTION ""
		::= { fsX25NewL3PortStats1Entry 8  }

	fsX25NewL3StatsLastDiag OBJECT-TYPE
		SYNTAX  Counter 
		ACCESS  read-only
		STATUS  mandatory
		DESCRIPTION ""
		::= { fsX25NewL3PortStats1Entry 9  }

	fsX25NewL3StatsRetryCountExceededs OBJECT-TYPE
		SYNTAX  Counter 
		ACCESS  read-only
		STATUS  mandatory
		DESCRIPTION ""
		::= { fsX25NewL3PortStats1Entry 10  }

	fsX25NewL3StatsClearCountExceededs OBJECT-TYPE
		SYNTAX  Counter 
		ACCESS  read-only
		STATUS  mandatory
		DESCRIPTION ""
		::= { fsX25NewL3PortStats1Entry 11  }

	fsX25NewL3StatsLinkFailures OBJECT-TYPE
		SYNTAX  Counter 
		ACCESS  read-only
		STATUS  mandatory
		DESCRIPTION ""
		::= { fsX25NewL3PortStats1Entry 12  }

	fsX25NewL3StatsPeakOutQLength OBJECT-TYPE
		SYNTAX  Counter 
		ACCESS  read-only
		STATUS  mandatory
		DESCRIPTION ""
		::= { fsX25NewL3PortStats1Entry 13  }

	fsX25NewL3StatsDataBytesToL4 OBJECT-TYPE
		SYNTAX  Counter 
		ACCESS  read-only
		STATUS  mandatory
		DESCRIPTION ""
		::= { fsX25NewL3PortStats1Entry 14  }

	fsX25NewL3StatsDataBytesFromL4 OBJECT-TYPE
		SYNTAX  Counter 
		ACCESS  read-only
		STATUS  mandatory
		DESCRIPTION ""
		::= { fsX25NewL3PortStats1Entry 15  }

	fsX25NewL3StatsDataPktsToL4 OBJECT-TYPE
		SYNTAX  Counter 
		ACCESS  read-only
		STATUS  mandatory
		DESCRIPTION ""
		::= { fsX25NewL3PortStats1Entry 16  }

	fsX25NewL3StatsDataPktsFromL4 OBJECT-TYPE
		SYNTAX  Counter 
		ACCESS  read-only
		STATUS  mandatory
		DESCRIPTION ""
		::= { fsX25NewL3PortStats1Entry 17  }

-- ***************************************************************************
-- Summary Stats

fsX25NewSummaryStatsTable OBJECT-TYPE
	SYNTAX  SEQUENCE OF FsX25NewSummaryStatsEntry
	ACCESS  not-accessible
	STATUS  mandatory
	DESCRIPTION
		" "
	::= { fsX25NewStats  5 }

	FsX25NewSummaryStatsEntry ::= SEQUENCE {
		fsX25NewSummaryStatsPort			INTEGER,
		fsX25NewSummaryL1Status                   INTEGER,
		fsX25NewSummaryL2Status                   INTEGER,
		fsX25NewSummaryL3Status                   INTEGER,
		fsX25NewSummaryRecFrames                  Counter,
		fsX25NewSummaryRxFrames                   Counter,
		fsX25NewSummaryActiveSVCs                 Counter,
		fsX25NewSummaryActivePVCs                 Counter
		}

	fsX25NewSummaryStatsEntry OBJECT-TYPE
		SYNTAX  FsX25NewSummaryStatsEntry
		ACCESS  not-accessible
		STATUS  mandatory
		DESCRIPTION ""
		INDEX   { fsX25NewSummaryStatsPort }
		::= { fsX25NewSummaryStatsTable  1 }

	fsX25NewSummaryStatsPort OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-only
		STATUS  mandatory
		DESCRIPTION "" 
		::= { fsX25NewSummaryStatsEntry  1 }

	fsX25NewSummaryL1Status OBJECT-TYPE
		SYNTAX  INTEGER {
			up		(1),
			down        (2)
			}
		ACCESS  read-only
		STATUS  mandatory
		DESCRIPTION ""
		::= { fsX25NewSummaryStatsEntry 2  }

	fsX25NewSummaryL2Status OBJECT-TYPE
		SYNTAX  INTEGER {
			up		(1),
			down        (2)
			}
		ACCESS  read-only
		STATUS  mandatory
		DESCRIPTION ""
		::= { fsX25NewSummaryStatsEntry 3  }

	fsX25NewSummaryL3Status OBJECT-TYPE
		SYNTAX  INTEGER {
			up		(1),
			down        (2)
			}
		ACCESS  read-only
		STATUS  mandatory
		DESCRIPTION ""
		::= { fsX25NewSummaryStatsEntry 4  }

	fsX25NewSummaryRecFrames OBJECT-TYPE
		SYNTAX  Counter 
		ACCESS  read-only
		STATUS  mandatory
		DESCRIPTION ""
		::= { fsX25NewSummaryStatsEntry 5  }

	fsX25NewSummaryRxFrames OBJECT-TYPE
		SYNTAX  Counter 
		ACCESS  read-only
		STATUS  mandatory
		DESCRIPTION ""
		::= { fsX25NewSummaryStatsEntry 6  }

	fsX25NewSummaryActiveSVCs OBJECT-TYPE
		SYNTAX  Counter 
		ACCESS  read-only
		STATUS  mandatory
		DESCRIPTION ""
		::= { fsX25NewSummaryStatsEntry 7  }

	fsX25NewSummaryActivePVCs OBJECT-TYPE
		SYNTAX  Counter 
		ACCESS  read-only
		STATUS  mandatory
		DESCRIPTION ""
		::= { fsX25NewSummaryStatsEntry 8  }

-- ***************************************************************************
-- Plp VC Stats

fsX25NewVCStatsTable OBJECT-TYPE
	SYNTAX  SEQUENCE OF FsX25NewVCStatsEntry
	ACCESS  not-accessible
	STATUS  mandatory
	DESCRIPTION ""
	::= { fsX25NewStats  6 }

	FsX25NewVCStatsEntry ::= SEQUENCE {
		fsX25NewVCStatsPort			INTEGER,
		fsX25NewVCStatsLCNNumber            INTEGER,
            fsX25NewVCStatsCallingAddr          DisplayString,
            fsX25NewVCStatsCalledAddr           DisplayString,
            fsX25NewVCStatsDirection            DisplayString,
            fsX25NewVCStatsDuration             DisplayString,
            fsX25NewVCStatsInDataPkts           Counter,
            fsX25NewVCStatsOutDataPkts          Counter
		}

	fsX25NewVCStatsEntry OBJECT-TYPE
		SYNTAX  FsX25NewVCStatsEntry
		ACCESS  not-accessible
		STATUS  mandatory
		DESCRIPTION ""
		INDEX   { fsX25NewVCStatsPort , fsX25NewVCStatsLCNNumber }
		::= { fsX25NewVCStatsTable  1 }

	fsX25NewVCStatsPort OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-only
		STATUS  mandatory
		DESCRIPTION ""
		::= { fsX25NewVCStatsEntry  1 }

	fsX25NewVCStatsLCNNumber OBJECT-TYPE
		SYNTAX  INTEGER
		ACCESS  read-only
		STATUS  mandatory
		DESCRIPTION "" 
		::= { fsX25NewVCStatsEntry  2 }

	fsX25NewVCStatsCallingAddr OBJECT-TYPE
		SYNTAX  DisplayString
		ACCESS  read-only
		STATUS  mandatory
		DESCRIPTION "" 
		::= { fsX25NewVCStatsEntry  3 }

	fsX25NewVCStatsCalledAddr OBJECT-TYPE
		SYNTAX  DisplayString
		ACCESS  read-only
		STATUS  mandatory
		DESCRIPTION "" 
		::= { fsX25NewVCStatsEntry  4 }

	fsX25NewVCStatsDirection OBJECT-TYPE
		SYNTAX  DisplayString
		ACCESS  read-only
		STATUS  mandatory
		DESCRIPTION "" 
		::= { fsX25NewVCStatsEntry  5 }

	fsX25NewVCStatsDuration OBJECT-TYPE
		SYNTAX  DisplayString
		ACCESS  read-only
		STATUS  mandatory
		DESCRIPTION "" 
		::= { fsX25NewVCStatsEntry  6 }

	fsX25NewVCStatsInDataPkts OBJECT-TYPE
		SYNTAX  Counter
		ACCESS  read-only
		STATUS  mandatory
		DESCRIPTION "" 
		::= { fsX25NewVCStatsEntry  7 }

	fsX25NewVCStatsOutDataPkts OBJECT-TYPE
		SYNTAX  Counter
		ACCESS  read-only
		STATUS  mandatory
		DESCRIPTION "" 
		::= { fsX25NewVCStatsEntry  8 }

-- ***************************************************************************
--  X25New Call Record  Stats

fsX25NewCallRecStatsTable OBJECT-TYPE
	SYNTAX  SEQUENCE OF FsX25NewCallRecStatsEntry
	ACCESS  not-accessible
	STATUS  mandatory
	DESCRIPTION ""
	::= { fsX25NewStats  7 }

	FsX25NewCallRecStatsEntry ::= SEQUENCE {
		fsX25NewCallRecStatsPort                    INTEGER,
		fsX25NewCallRecStatsCirNum                  INTEGER,
		fsX25NewCallRecChnl                         INTEGER,
		fsX25NewCallRecCallingAddress               DisplayString, 
		fsX25NewCallRecCalledAddress                DisplayString,
		fsX25NewCallRecCallDirection                DisplayString,
		fsX25NewCallRecClearDirection               DisplayString,
		fsX25NewCallRecClearCause                   INTEGER,
		fsX25NewCallRecDiagCode                     INTEGER,
		fsX25NewCallRecDuration                     DisplayString,
		fsX25NewCallRecInPDUs                       Counter,
		fsX25NewCallRecOutPDUs                      Counter
		}

	fsX25NewCallRecStatsEntry OBJECT-TYPE
		SYNTAX  FsX25NewCallRecStatsEntry
		ACCESS  not-accessible
		STATUS  mandatory
		DESCRIPTION ""
		INDEX   { fsX25NewCallRecStatsPort, fsX25NewCallRecStatsCirNum }
		::= { fsX25NewCallRecStatsTable  1 }

	fsX25NewCallRecStatsPort OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-only
		STATUS  mandatory
		DESCRIPTION
			" " 
		::= { fsX25NewCallRecStatsEntry 1 }

	fsX25NewCallRecStatsCirNum OBJECT-TYPE
		SYNTAX  INTEGER 
		ACCESS  read-only
		STATUS  mandatory
		DESCRIPTION
                      "The value of ifIndex for the port which cleared the
                      circuit that created the entry."
		::= { fsX25NewCallRecStatsEntry  2 }

	fsX25NewCallRecChnl OBJECT-TYPE
      	SYNTAX  INTEGER
            ACCESS  read-only
            STATUS  mandatory
            DESCRIPTION
                      "The channel number for this circuit.
                      The valid values range from 0 to 4095."
            ::= { fsX25NewCallRecStatsEntry 3 }

      fsX25NewCallRecCallingAddress OBJECT-TYPE
            SYNTAX  DisplayString
            ACCESS  read-only
            STATUS  mandatory
            DESCRIPTION
                      "The calling address from the cleared circuit.
                      The value is shown as an ASCII string of length 0-14."
            ::= { fsX25NewCallRecStatsEntry 4 }

      fsX25NewCallRecCalledAddress OBJECT-TYPE
            SYNTAX  DisplayString 
            ACCESS  read-only
            STATUS  mandatory
            DESCRIPTION
                      "The called address from the cleared circuit.
                      The value is shown as an ASCII string of length 0-15."
            ::= { fsX25NewCallRecStatsEntry 5 }

      fsX25NewCallRecCallDirection OBJECT-TYPE
            SYNTAX DisplayString
            ACCESS  read-only
            STATUS  mandatory
            DESCRIPTION
                       "Call initiator of the cleared VC ."
            ::= { fsX25NewCallRecStatsEntry 6 }

      fsX25NewCallRecClearDirection OBJECT-TYPE
            SYNTAX DisplayString
            ACCESS  read-only
            STATUS  mandatory
            DESCRIPTION
                       "End which initiated the clearing of the VC."
            ::= { fsX25NewCallRecStatsEntry 7 }

      fsX25NewCallRecClearCause OBJECT-TYPE
            SYNTAX INTEGER
            ACCESS  read-only
            STATUS  mandatory
            DESCRIPTION
                      "The Clearing Cause from the clear request or clear
                      indication packet that cleared the circuit.

                      The valid values range from 0 to 255."
            ::= { fsX25NewCallRecStatsEntry 8 }

      fsX25NewCallRecDiagCode OBJECT-TYPE
            SYNTAX  INTEGER
            ACCESS  read-only
            STATUS  mandatory
            DESCRIPTION
                      "The Diagnostic Code from the clear request or clear
                      indication packet that cleared the circuit.

                      The valid values range from 0 to 255."
            ::= { fsX25NewCallRecStatsEntry 9 }

      fsX25NewCallRecDuration OBJECT-TYPE
            SYNTAX  DisplayString 
            ACCESS  read-only
            STATUS  mandatory
            DESCRIPTION
                      "The value of sysUpTime when the circuit was cleared.
                      For locally initiated clears, this will be the time
                      when the clear confirmation was received. For remotely
                      initiated clears, this will be the time when the clear
                      indication was received."
            ::= { fsX25NewCallRecStatsEntry 10 }

      fsX25NewCallRecInPDUs OBJECT-TYPE
            SYNTAX  Counter
            ACCESS  read-only
            STATUS  mandatory
            DESCRIPTION
                      "The number of PDUs received on the circuit."
            ::= { fsX25NewCallRecStatsEntry 11 }
	
	fsX25NewCallRecOutPDUs OBJECT-TYPE
            SYNTAX  Counter
            ACCESS  read-only
            STATUS  mandatory
            DESCRIPTION
                      "The number of PDUs transmitted on the circuit."
            ::= { fsX25NewCallRecStatsEntry 12 }

-- ***************************************************************************
--  XPAD Stats

fsXPadStatsTable OBJECT-TYPE
	SYNTAX  SEQUENCE OF FsXPadStatsEntry
	ACCESS  not-accessible
	STATUS  mandatory
	DESCRIPTION
		"Statistics Table for XPAD Stats." 
	::= { fsXPadStats 1 }

	FsXPadStatsEntry ::= SEQUENCE {
		fsXPadStatsPort               INTEGER,
		fsXPadStatsAsyncBytesRcvd      Counter,
		fsXPadStatsAsyncBytesTx        Counter,
		fsXPadStatsX25BytesRcvd        Counter,
		fsXPadStatsX25BytesTx          Counter,
		fsXPadStatsPacketsRcvd         Counter,
		fsXPadStatsPacketsTx           Counter,
		fsXPadStatsResetsRcvd          Counter,
		fsXPadStatsResetsTx            Counter,
            fsXPadStatsRxBreakReceived     Counter,
            fsXPadStatsRxOverrun           Counter,
            fsXPadStatsRxParityError       Counter,
            fsXPadStatsRxFramingError      Counter,
            fsXPadStatsRTS                 Counter,
            fsXPadStatsCTS                 Counter,
            fsXPadStatsDTR                 Counter,
            fsXPadStatsDSR                 Counter,
            fsXPadStatsDCD                 Counter,
            fsXPadStatsActiveLED           Counter,
            fsXPadStatsErrorLED            Counter  
		}

	fsXPadStatsEntry OBJECT-TYPE
    		SYNTAX  FsXPadStatsEntry
    		ACCESS  not-accessible
    		STATUS  mandatory
    		DESCRIPTION
	   		"A list of statistics for a XXXPAD port."
    		INDEX   { fsXPadStatsPort }
    		::= { fsXPadStatsTable  1 }

	fsXPadStatsPort OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
    		ACCESS  read-only
    		STATUS  mandatory
    		DESCRIPTION
	   		"This object reflects the total number of times
	    		this port has failed due to its physical media
	    		since port startup.  At port startup time,
	    		this object must be initialized to zero."
    		::= { fsXPadStatsEntry  1 }

	fsXPadStatsAsyncBytesRcvd OBJECT-TYPE
    		SYNTAX  Counter
    		ACCESS  read-only
    		STATUS  mandatory
    		DESCRIPTION ""
    		::= { fsXPadStatsEntry 2    }

	fsXPadStatsAsyncBytesTx OBJECT-TYPE
    		SYNTAX  Counter
    		ACCESS  read-only
    		STATUS  mandatory
    		DESCRIPTION ""
    		::= { fsXPadStatsEntry 3    }

	fsXPadStatsX25BytesRcvd OBJECT-TYPE
    		SYNTAX  Counter
    		ACCESS  read-only
    		STATUS  mandatory
    		DESCRIPTION ""
    		::= { fsXPadStatsEntry  4   }

	fsXPadStatsX25BytesTx OBJECT-TYPE
    		SYNTAX  Counter
    		ACCESS  read-only
    		STATUS  mandatory
    		DESCRIPTION ""
    		::= { fsXPadStatsEntry  5   }

	fsXPadStatsPacketsRcvd OBJECT-TYPE
    		SYNTAX  Counter
    		ACCESS  read-only
    		STATUS  mandatory
    		DESCRIPTION ""
    		::= { fsXPadStatsEntry  6    }

	fsXPadStatsPacketsTx OBJECT-TYPE
    		SYNTAX  Counter
    		ACCESS  read-only
    		STATUS  mandatory
    		DESCRIPTION ""
    		::= { fsXPadStatsEntry  7   }

	fsXPadStatsResetsRcvd OBJECT-TYPE
    		SYNTAX  Counter
    		ACCESS  read-only
    		STATUS  mandatory
    		DESCRIPTION ""
    		::= { fsXPadStatsEntry  8   }

	fsXPadStatsResetsTx OBJECT-TYPE
    		SYNTAX  Counter
    		ACCESS  read-only
    		STATUS  mandatory
    		DESCRIPTION ""
    		::= { fsXPadStatsEntry  9   }

	fsXPadStatsRxBreakReceived OBJECT-TYPE
    		SYNTAX  Counter
    		ACCESS  read-only
    		STATUS  mandatory
    		DESCRIPTION ""
    		::= { fsXPadStatsEntry  10    }

	fsXPadStatsRxOverrun OBJECT-TYPE
    		SYNTAX  Counter
    		ACCESS  read-only
    		STATUS  mandatory
    		DESCRIPTION ""
    		::= { fsXPadStatsEntry   11  }

	fsXPadStatsRxParityError OBJECT-TYPE
    		SYNTAX  Counter
    		ACCESS  read-only
    		STATUS  mandatory
    		DESCRIPTION ""
    		::= { fsXPadStatsEntry  12   }

	fsXPadStatsRxFramingError OBJECT-TYPE
    		SYNTAX  Counter
    		ACCESS  read-only
    		STATUS  mandatory
    		DESCRIPTION ""
    		::= { fsXPadStatsEntry  13   }

	fsXPadStatsRTS OBJECT-TYPE
    		SYNTAX  Counter
    		ACCESS  read-only
    		STATUS  mandatory
    		DESCRIPTION ""
    		::= { fsXPadStatsEntry 14    }

	fsXPadStatsCTS OBJECT-TYPE
    		SYNTAX  Counter
    		ACCESS  read-only
    		STATUS  mandatory
    		DESCRIPTION ""
    		::= { fsXPadStatsEntry 15    }

	fsXPadStatsDTR OBJECT-TYPE
    		SYNTAX  Counter
    		ACCESS  read-only
    		STATUS  mandatory
    		DESCRIPTION ""
    		::= { fsXPadStatsEntry  16   }

	fsXPadStatsDSR OBJECT-TYPE
    		SYNTAX  Counter
    		ACCESS  read-only
    		STATUS  mandatory
    		DESCRIPTION ""
    		::= { fsXPadStatsEntry   17  }

	fsXPadStatsDCD OBJECT-TYPE
    		SYNTAX  Counter
    		ACCESS  read-only
    		STATUS  mandatory
    		DESCRIPTION ""
    		::= { fsXPadStatsEntry  18   }

	fsXPadStatsActiveLED OBJECT-TYPE
    		SYNTAX  Counter
    		ACCESS  read-only
    		STATUS  mandatory
    		DESCRIPTION ""
    		::= { fsXPadStatsEntry  19   }

	fsXPadStatsErrorLED OBJECT-TYPE
    		SYNTAX  Counter
    		ACCESS  read-only
    		STATUS  mandatory
    		DESCRIPTION ""
    		::= { fsXPadStatsEntry  20   }

-- ***************************************************************************
-- ISDN Stats

fsISDNChStatsTable OBJECT-TYPE
	SYNTAX  SEQUENCE OF FsISDNChStatsEntry
	ACCESS  not-accessible
	STATUS  mandatory
	DESCRIPTION  ""
	::= { fsISDNStats 1 }

	FsISDNChStatsEntry ::= SEQUENCE {
		fsISDNChTableIndex	INTEGER,
		fsISDNPhyLayerStatus	DisplayString,
		fsISDNCh1Tel		DisplayString,
		fsISDNCh1Spid		DisplayString,
		fsISDNCh1Status		DisplayString,
		fsISDNCh2Tel		DisplayString,
		fsISDNCh2Spid		DisplayString,
		fsISDNCh2Status		DisplayString
		}

	fsISDNChStatsEntry OBJECT-TYPE
		SYNTAX  FsISDNChStatsEntry
		ACCESS  not-accessible
		STATUS  mandatory
		DESCRIPTION ""
		INDEX { fsISDNChTableIndex }
		::= { fsISDNChStatsTable 1 }

	fsISDNChTableIndex OBJECT-TYPE
		SYNTAX  INTEGER 
		ACCESS  read-only
		STATUS  mandatory
		DESCRIPTION ""
		::= { fsISDNChStatsEntry 1 }

	fsISDNPhyLayerStatus OBJECT-TYPE
		SYNTAX  DisplayString (SIZE (0..32))
		ACCESS  read-only
		STATUS  mandatory
		DESCRIPTION ""
		::= { fsISDNChStatsEntry 2 }

	fsISDNCh1Tel OBJECT-TYPE
		SYNTAX  DisplayString (SIZE (0..32))
		ACCESS  read-only
		STATUS  mandatory
		DESCRIPTION ""
		::= { fsISDNChStatsEntry 3 }

	fsISDNCh1Spid OBJECT-TYPE
		SYNTAX  DisplayString (SIZE (0..32))
		ACCESS  read-only
		STATUS  mandatory
		DESCRIPTION ""
		::= { fsISDNChStatsEntry 4 }

	fsISDNCh1Status OBJECT-TYPE
		SYNTAX  DisplayString (SIZE (0..32))
		ACCESS  read-only
		STATUS  mandatory
		DESCRIPTION ""
		::= { fsISDNChStatsEntry 5 }

	fsISDNCh2Tel OBJECT-TYPE
		SYNTAX  DisplayString (SIZE (0..32))
		ACCESS  read-only
		STATUS  mandatory
		DESCRIPTION ""
		::= { fsISDNChStatsEntry 6 }

	fsISDNCh2Spid OBJECT-TYPE
		SYNTAX  DisplayString (SIZE (0..32))
		ACCESS  read-only
		STATUS  mandatory
		DESCRIPTION ""
		::= { fsISDNChStatsEntry 7 }

	fsISDNCh2Status OBJECT-TYPE
		SYNTAX  DisplayString (SIZE (0..32))
		ACCESS  read-only
		STATUS  mandatory
		DESCRIPTION ""
		::= { fsISDNChStatsEntry 8 }

fsISDNPortStatsTable OBJECT-TYPE
	SYNTAX  SEQUENCE OF FsISDNPortStatsEntry
	ACCESS  not-accessible
	STATUS  mandatory
	DESCRIPTION  ""
	::= { fsISDNStats 2 }

	FsISDNPortStatsEntry ::= SEQUENCE {
		fsISDNPortTableIndex	INTEGER,
		fsISDNPort3ISDNStatus	DisplayString,
		fsISDNPort3LocalTel1    DisplayString,
		fsISDNPort3RemoteTel1	DisplayString,
		fsISDNPort3BCh1Status	DisplayString,
		fsISDNPort3Sig1Status	DisplayString,
		fsISDNPort3LocalTel2    DisplayString,
		fsISDNPort3RemoteTel2	DisplayString,
		fsISDNPort3BCh2Status	DisplayString,
		fsISDNPort3Sig2Status	DisplayString,
		fsISDNPort4ISDNStatus	DisplayString,
		fsISDNPort4LocalTel1    DisplayString,
		fsISDNPort4RemoteTel1	DisplayString,
		fsISDNPort4BCh1Status	DisplayString,
		fsISDNPort4Sig1Status	DisplayString,
		fsISDNPort4LocalTel2    DisplayString,
		fsISDNPort4RemoteTel2	DisplayString,
		fsISDNPort4BCh2Status	DisplayString,
		fsISDNPort4Sig2Status	DisplayString
		}

	fsISDNPortStatsEntry OBJECT-TYPE
		SYNTAX  FsISDNPortStatsEntry
		ACCESS  not-accessible
		STATUS  mandatory
		DESCRIPTION ""
		INDEX { fsISDNPortTableIndex }
		::= { fsISDNPortStatsTable 1 }

	fsISDNPortTableIndex OBJECT-TYPE
		SYNTAX  INTEGER 
		ACCESS  read-only
		STATUS  mandatory
		DESCRIPTION ""
		::= { fsISDNPortStatsEntry 1 }

	fsISDNPort3ISDNStatus OBJECT-TYPE
		SYNTAX  DisplayString (SIZE (0..32))
		ACCESS  read-only
		STATUS  mandatory
		DESCRIPTION ""
		::= { fsISDNPortStatsEntry 2 }

	fsISDNPort3LocalTel1 OBJECT-TYPE
		SYNTAX  DisplayString (SIZE (0..32))
		ACCESS  read-only
		STATUS  mandatory
		DESCRIPTION ""
		::= { fsISDNPortStatsEntry 3 }

	fsISDNPort3RemoteTel1 OBJECT-TYPE
		SYNTAX  DisplayString (SIZE (0..32))
		ACCESS  read-only
		STATUS  mandatory
		DESCRIPTION ""
		::= { fsISDNPortStatsEntry 4 }

	fsISDNPort3BCh1Status OBJECT-TYPE
		SYNTAX  DisplayString (SIZE (0..32))
		ACCESS  read-only
		STATUS  mandatory
		DESCRIPTION ""
		::= { fsISDNPortStatsEntry 5 }

	fsISDNPort3Sig1Status OBJECT-TYPE
		SYNTAX  DisplayString (SIZE (0..32))
		ACCESS  read-only
		STATUS  mandatory
		DESCRIPTION ""
		::= { fsISDNPortStatsEntry 6 }

	fsISDNPort3LocalTel2 OBJECT-TYPE
		SYNTAX  DisplayString (SIZE (0..32))
		ACCESS  read-only
		STATUS  mandatory
		DESCRIPTION ""
		::= { fsISDNPortStatsEntry 7 }

	fsISDNPort3RemoteTel2 OBJECT-TYPE
		SYNTAX  DisplayString (SIZE (0..32))
		ACCESS  read-only
		STATUS  mandatory
		DESCRIPTION ""
		::= { fsISDNPortStatsEntry 8 }

	fsISDNPort3BCh2Status OBJECT-TYPE
		SYNTAX  DisplayString (SIZE (0..32))
		ACCESS  read-only
		STATUS  mandatory
		DESCRIPTION ""
		::= { fsISDNPortStatsEntry 9 }

	fsISDNPort3Sig2Status OBJECT-TYPE
		SYNTAX  DisplayString (SIZE (0..32))
		ACCESS  read-only
		STATUS  mandatory
		DESCRIPTION ""
		::= { fsISDNPortStatsEntry 10 }

	fsISDNPort4ISDNStatus OBJECT-TYPE
		SYNTAX  DisplayString (SIZE (0..32))
		ACCESS  read-only
		STATUS  mandatory
		DESCRIPTION ""
		::= { fsISDNPortStatsEntry 11 }

	fsISDNPort4LocalTel1 OBJECT-TYPE
		SYNTAX  DisplayString (SIZE (0..32))
		ACCESS  read-only
		STATUS  mandatory
		DESCRIPTION ""
		::= { fsISDNPortStatsEntry 12 }

	fsISDNPort4RemoteTel1 OBJECT-TYPE
		SYNTAX  DisplayString (SIZE (0..32))
		ACCESS  read-only
		STATUS  mandatory
		DESCRIPTION ""
		::= { fsISDNPortStatsEntry 13 }

	fsISDNPort4BCh1Status OBJECT-TYPE
		SYNTAX  DisplayString (SIZE (0..32))
		ACCESS  read-only
		STATUS  mandatory
		DESCRIPTION ""
		::= { fsISDNPortStatsEntry 14 }

	fsISDNPort4Sig1Status OBJECT-TYPE
		SYNTAX  DisplayString (SIZE (0..32))
		ACCESS  read-only
		STATUS  mandatory
		DESCRIPTION ""
		::= { fsISDNPortStatsEntry 15 }

	fsISDNPort4LocalTel2 OBJECT-TYPE
		SYNTAX  DisplayString (SIZE (0..32))
		ACCESS  read-only
		STATUS  mandatory
		DESCRIPTION ""
		::= { fsISDNPortStatsEntry 16 }

	fsISDNPort4RemoteTel2 OBJECT-TYPE
		SYNTAX  DisplayString (SIZE (0..32))
		ACCESS  read-only
		STATUS  mandatory
		DESCRIPTION ""
		::= { fsISDNPortStatsEntry 17 }

	fsISDNPort4BCh2Status OBJECT-TYPE
		SYNTAX  DisplayString (SIZE (0..32))
		ACCESS  read-only
		STATUS  mandatory
		DESCRIPTION ""
		::= { fsISDNPortStatsEntry 18 }

	fsISDNPort4Sig2Status OBJECT-TYPE
		SYNTAX  DisplayString (SIZE (0..32))
		ACCESS  read-only
		STATUS  mandatory
		DESCRIPTION ""
		::= { fsISDNPortStatsEntry 19 }

-- ***************************************************************************
-- IP Filtering Stats

fsIpFilteringPktStatsTable OBJECT-TYPE
	SYNTAX  SEQUENCE OF FsIpFilteringPktStatsEntry
	ACCESS  not-accessible
	STATUS  mandatory
	DESCRIPTION  ""
	::= { fsIpFilteringStats 1 }

	FsIpFilteringPktStatsEntry ::= SEQUENCE {
		fsIpFilteringPktIndex		INTEGER,
		fsIpFilteringPktTotalDiscard	Counter,
		fsIpFilteringPktFallDiscard   Counter
		}

	fsIpFilteringPktStatsEntry OBJECT-TYPE
		SYNTAX  FsIpFilteringPktStatsEntry
		ACCESS  not-accessible
		STATUS  mandatory
		DESCRIPTION ""
		INDEX { fsIpFilteringPktIndex }
		::= { fsIpFilteringPktStatsTable 1 }

	fsIpFilteringPktIndex OBJECT-TYPE
		SYNTAX  INTEGER 
		ACCESS  read-only
		STATUS  mandatory
		DESCRIPTION ""
		::= { fsIpFilteringPktStatsEntry 1 }

	fsIpFilteringPktTotalDiscard OBJECT-TYPE
		SYNTAX  Counter
		ACCESS  read-only
		STATUS  mandatory
		DESCRIPTION ""
		::= { fsIpFilteringPktStatsEntry 2 }

	fsIpFilteringPktFallDiscard OBJECT-TYPE
		SYNTAX  Counter
		ACCESS  read-only
		STATUS  mandatory
		DESCRIPTION ""
		::= { fsIpFilteringPktStatsEntry 3 }

fsIpFilteringLogStatsTable OBJECT-TYPE
	SYNTAX  SEQUENCE OF FsIpFilteringLogStatsEntry
	ACCESS  not-accessible
	STATUS  mandatory
	DESCRIPTION  ""
	::= { fsIpFilteringStats 2 }

	FsIpFilteringLogStatsEntry ::= SEQUENCE {
		fsIpFilteringLogIndex		INTEGER,
		fsIpFilteringLogSeconds		Counter,
		fsIpFilteringLogSourceAddr	DisplayString,
		fsIpFilteringLogSourcePort	DisplayString,
		fsIpFilteringLogDesAddr		DisplayString,
		fsIpFilteringLogDesPort		DisplayString,
		fsIpFilteringLogProtocol	INTEGER,
		fsIpFilteringLogPort		INTEGER,
		fsIpFilteringLogDlci		INTEGER
		}

	fsIpFilteringLogStatsEntry OBJECT-TYPE
		SYNTAX  FsIpFilteringLogStatsEntry
		ACCESS  not-accessible
		STATUS  mandatory
		DESCRIPTION ""
		INDEX { fsIpFilteringLogIndex }
		::= { fsIpFilteringLogStatsTable 1 }

	fsIpFilteringLogIndex OBJECT-TYPE
		SYNTAX  INTEGER 
		ACCESS  read-only
		STATUS  mandatory
		DESCRIPTION ""
		::= { fsIpFilteringLogStatsEntry 1 }

	fsIpFilteringLogSeconds OBJECT-TYPE
		SYNTAX  Counter
		ACCESS  read-only
		STATUS  mandatory
		DESCRIPTION ""
		::= { fsIpFilteringLogStatsEntry 2 }

	fsIpFilteringLogSourceAddr OBJECT-TYPE
		SYNTAX  DisplayString
		ACCESS  read-only
		STATUS  mandatory
		DESCRIPTION ""
		::= { fsIpFilteringLogStatsEntry 3 }

	fsIpFilteringLogSourcePort OBJECT-TYPE
		SYNTAX  DisplayString
		ACCESS  read-only
		STATUS  mandatory
		DESCRIPTION ""
		::= { fsIpFilteringLogStatsEntry 4 }

	fsIpFilteringLogDesAddr OBJECT-TYPE
		SYNTAX  DisplayString
		ACCESS  read-only
		STATUS  mandatory
		DESCRIPTION ""
		::= { fsIpFilteringLogStatsEntry 5 }

	fsIpFilteringLogDesPort OBJECT-TYPE
		SYNTAX  DisplayString
		ACCESS  read-only
		STATUS  mandatory
		DESCRIPTION ""
		::= { fsIpFilteringLogStatsEntry 6 }

	fsIpFilteringLogProtocol OBJECT-TYPE
		SYNTAX  INTEGER {
			any   (0),
			tcp   (1),
			udp   (2),
 			icmp  (3),
			ack   (4),
			rst   (5)
			}
		ACCESS  read-only
		STATUS  mandatory
		DESCRIPTION ""
		::= { fsIpFilteringLogStatsEntry 7 }

	fsIpFilteringLogPort OBJECT-TYPE
		SYNTAX  INTEGER {
                  any	      (0),
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-only
		STATUS  mandatory
		DESCRIPTION ""
		::= { fsIpFilteringLogStatsEntry 8 }

	fsIpFilteringLogDlci OBJECT-TYPE
		SYNTAX  INTEGER
		ACCESS  read-only
		STATUS  mandatory
		DESCRIPTION ""
		::= { fsIpFilteringLogStatsEntry 9 }

-- ***************************************************************************
-- New PPP Stats

fsNewPPPStatsTable OBJECT-TYPE
	SYNTAX  SEQUENCE OF FsNewPPPStatsEntry
	ACCESS  not-accessible
	STATUS  mandatory
	DESCRIPTION  ""
	::= { fsNewPPPStats 1 }

	FsNewPPPStatsEntry ::= SEQUENCE {
		fsNewPPPPortIndex             INTEGER,
            fsNewPPPTotalFrameRx          DisplayString,
		fsNewPPPTotalFrameTx          DisplayString,
		fsNewPPPRTS	 	            DisplayString,
		fsNewPPPCTS	 	            DisplayString,
		fsNewPPPDTR	 	            DisplayString,
		fsNewPPPDSR	 	            DisplayString,
		fsNewPPPDCD	 	            DisplayString,
		fsNewPPPFrameOversize         Counter,
     		fsNewPPPRxCRC			Counter,
            fsNewPPPRxOverrun             Counter,
            fsNewPPPRxNonAlign            Counter,
		fsNewPPPRxAbort               Counter,
            fsNewPPPTxUnderrun            Counter
		}

	fsNewPPPStatsEntry OBJECT-TYPE
		SYNTAX  FsNewPPPStatsEntry
		ACCESS  not-accessible
		STATUS  mandatory
		DESCRIPTION ""
		INDEX { fsNewPPPPortIndex }
		::= { fsNewPPPStatsTable 1 }

	fsNewPPPPortIndex OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-only
		STATUS  mandatory
		DESCRIPTION ""
		::= { fsNewPPPStatsEntry 1 }

	fsNewPPPTotalFrameRx OBJECT-TYPE
		SYNTAX  DisplayString
		ACCESS  read-only
		STATUS  mandatory
		DESCRIPTION ""
		::= { fsNewPPPStatsEntry 2 }

	fsNewPPPTotalFrameTx OBJECT-TYPE
		SYNTAX  DisplayString
		ACCESS  read-only
		STATUS  mandatory
		DESCRIPTION ""
		::= { fsNewPPPStatsEntry 3 }

	fsNewPPPRTS OBJECT-TYPE
		SYNTAX  DisplayString
		ACCESS  read-only
		STATUS  mandatory
		DESCRIPTION ""
		::= { fsNewPPPStatsEntry 4 }

	fsNewPPPCTS OBJECT-TYPE
		SYNTAX  DisplayString
		ACCESS  read-only
		STATUS  mandatory
		DESCRIPTION ""
		::= { fsNewPPPStatsEntry 5 }

	fsNewPPPDTR OBJECT-TYPE
		SYNTAX  DisplayString
		ACCESS  read-only
		STATUS  mandatory
		DESCRIPTION ""
		::= { fsNewPPPStatsEntry 6 }

	fsNewPPPDSR OBJECT-TYPE
		SYNTAX  DisplayString
		ACCESS  read-only
		STATUS  mandatory
		DESCRIPTION ""
		::= { fsNewPPPStatsEntry 7 }

	fsNewPPPDCD OBJECT-TYPE
		SYNTAX  DisplayString
		ACCESS  read-only
		STATUS  mandatory
		DESCRIPTION ""
		::= { fsNewPPPStatsEntry 8 }

	fsNewPPPFrameOversize OBJECT-TYPE
		SYNTAX  Counter
		ACCESS  read-only
		STATUS  mandatory
		DESCRIPTION ""
		::= { fsNewPPPStatsEntry 9 }

	fsNewPPPRxCRC OBJECT-TYPE
		SYNTAX  Counter
		ACCESS  read-only
		STATUS  mandatory
		DESCRIPTION ""
		::= { fsNewPPPStatsEntry 10 }

	fsNewPPPRxOverrun OBJECT-TYPE
		SYNTAX  Counter
		ACCESS  read-only
		STATUS  mandatory
		DESCRIPTION ""
		::= { fsNewPPPStatsEntry 11 }

	fsNewPPPRxNonAlign OBJECT-TYPE
		SYNTAX  Counter
		ACCESS  read-only
		STATUS  mandatory
		DESCRIPTION ""
		::= { fsNewPPPStatsEntry 12 }

	fsNewPPPRxAbort OBJECT-TYPE
		SYNTAX  Counter
		ACCESS  read-only
		STATUS  mandatory
		DESCRIPTION ""
		::= { fsNewPPPStatsEntry 13 }

	fsNewPPPTxUnderrun OBJECT-TYPE
		SYNTAX  Counter
		ACCESS  read-only
		STATUS  mandatory
		DESCRIPTION ""
		::= { fsNewPPPStatsEntry 14 }

-- ***************************************************************************
-- MLP Stats

fsMLPStatsTable OBJECT-TYPE
	SYNTAX  SEQUENCE OF FsMLPStatsEntry
	ACCESS  not-accessible
	STATUS  mandatory
	DESCRIPTION  ""
	::= { fsMLPStats 1 }

	FsMLPStatsEntry ::= SEQUENCE {
		fsMLPPortIndex			INTEGER,
		fsMLPRTS	 	            DisplayString,
		fsMLPCTS	 	            DisplayString,
		fsMLPDTR	 	            DisplayString,
		fsMLPDSR	 	            DisplayString,
		fsMLPDCD	 	            DisplayString,
		fsMLPFrameOversize            Counter,
     		fsMLPRxCRC			      Counter,
            fsMLPRxOverrun                Counter,
            fsMLPRxNonAlign               Counter,
		fsMLPRxAbort                  Counter,
            fsMLPTxUnderrun               Counter,
		fsMLPRxBreakRec               Counter,
            fsMLPRxParityErr              Counter,
            fsMLPRxFrameErr               Counter
		}

	fsMLPStatsEntry OBJECT-TYPE
		SYNTAX  FsMLPStatsEntry
		ACCESS  not-accessible
		STATUS  mandatory
		DESCRIPTION ""
		INDEX { fsMLPPortIndex }
		::= { fsMLPStatsTable 1 }

	fsMLPPortIndex OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
		ACCESS  read-only
		STATUS  mandatory
		DESCRIPTION ""
		::= { fsMLPStatsEntry 1 }

	fsMLPRTS OBJECT-TYPE
		SYNTAX  DisplayString
		ACCESS  read-only
		STATUS  mandatory
		DESCRIPTION ""
		::= { fsMLPStatsEntry 2 }

	fsMLPCTS OBJECT-TYPE
		SYNTAX  DisplayString
		ACCESS  read-only
		STATUS  mandatory
		DESCRIPTION ""
		::= { fsMLPStatsEntry 3 }

	fsMLPDTR OBJECT-TYPE
		SYNTAX  DisplayString
		ACCESS  read-only
		STATUS  mandatory
		DESCRIPTION ""
		::= { fsMLPStatsEntry 4 }

	fsMLPDSR OBJECT-TYPE
		SYNTAX  DisplayString
		ACCESS  read-only
		STATUS  mandatory
		DESCRIPTION ""
		::= { fsMLPStatsEntry 5 }

	fsMLPDCD OBJECT-TYPE
		SYNTAX  DisplayString
		ACCESS  read-only
		STATUS  mandatory
		DESCRIPTION ""
		::= { fsMLPStatsEntry 6 }

	fsMLPFrameOversize OBJECT-TYPE
		SYNTAX  Counter
		ACCESS  read-only
		STATUS  mandatory
		DESCRIPTION ""
		::= { fsMLPStatsEntry 7 }

	fsMLPRxCRC OBJECT-TYPE
		SYNTAX  Counter
		ACCESS  read-only
		STATUS  mandatory
		DESCRIPTION ""
		::= { fsMLPStatsEntry 8 }

	fsMLPRxOverrun OBJECT-TYPE
		SYNTAX  Counter
		ACCESS  read-only
		STATUS  mandatory
		DESCRIPTION ""
		::= { fsMLPStatsEntry 9 }

	fsMLPRxNonAlign OBJECT-TYPE
		SYNTAX  Counter
		ACCESS  read-only
		STATUS  mandatory
		DESCRIPTION ""
		::= { fsMLPStatsEntry 10 }

	fsMLPRxAbort OBJECT-TYPE
		SYNTAX  Counter
		ACCESS  read-only
		STATUS  mandatory
		DESCRIPTION ""
		::= { fsMLPStatsEntry 11 }

	fsMLPTxUnderrun OBJECT-TYPE
		SYNTAX  Counter
		ACCESS  read-only
		STATUS  mandatory
		DESCRIPTION ""
		::= { fsMLPStatsEntry 12 }

	fsMLPRxBreakRec OBJECT-TYPE
		SYNTAX  Counter
		ACCESS  read-only
		STATUS  mandatory
		DESCRIPTION ""
		::= { fsMLPStatsEntry 13 }

	fsMLPRxParityErr OBJECT-TYPE
		SYNTAX  Counter
		ACCESS  read-only
		STATUS  mandatory
		DESCRIPTION ""
		::= { fsMLPStatsEntry 14 }

	fsMLPRxFrameErr OBJECT-TYPE
		SYNTAX  Counter
		ACCESS  read-only
		STATUS  mandatory
		DESCRIPTION ""
		::= { fsMLPStatsEntry 15 }

-- ***************************************************************************
-- Trig Stats

fsTrigStatsTable OBJECT-TYPE
	SYNTAX  SEQUENCE OF FsTrigStatsEntry
	ACCESS  not-accessible
	STATUS  mandatory
	DESCRIPTION  ""
	::= { fsTrigStats 1 }

	FsTrigStatsEntry ::= SEQUENCE {
		fsTrigIndex		  INTEGER,
		fsTrigStatus	 	  DisplayString,
		fsTrigNoTriggers          Counter
		}

	fsTrigStatsEntry OBJECT-TYPE
		SYNTAX  FsTrigStatsEntry
		ACCESS  not-accessible
		STATUS  mandatory
		DESCRIPTION ""
		INDEX { fsTrigIndex }
		::= { fsTrigStatsTable 1 }

	fsTrigIndex OBJECT-TYPE
		SYNTAX  INTEGER 
		ACCESS  read-only
		STATUS  mandatory
		DESCRIPTION ""
		::= { fsTrigStatsEntry 1 }

	fsTrigStatus OBJECT-TYPE
		SYNTAX  DisplayString
		ACCESS  read-only
		STATUS  mandatory
		DESCRIPTION ""
		::= { fsTrigStatsEntry 2 }

	fsTrigNoTriggers OBJECT-TYPE
		SYNTAX  Counter
		ACCESS  read-only
		STATUS  mandatory
		DESCRIPTION ""
		::= { fsTrigStatsEntry 3 }

-- ***************************************************************************
-- Voice Overall QSMU Stats

fsOverallQsmuStats OBJECT IDENTIFIER ::= { fsVoiceStats 1 }

fsOverallQsmuStatsTable OBJECT-TYPE
	SYNTAX  SEQUENCE OF FsOverallQsmuStatsEntry
	ACCESS  not-accessible
	STATUS  mandatory
	DESCRIPTION  ""
	::= { fsOverallQsmuStats 1 }

	FsOverallQsmuStatsEntry ::= SEQUENCE {
		fsOverallQsmuIndex	INTEGER,
		fsQsmuOutCallAttempt	Counter,
            fsQsmuOutCallAccept     Counter,
            fsQsmuInCallAttempt     Counter,
            fsQsmuInCallAccept      Counter,
            fsQsmuTimeout           Counter
		}

	fsOverallQsmuStatsEntry OBJECT-TYPE
		SYNTAX  FsOverallQsmuStatsEntry
		ACCESS  not-accessible
		STATUS  mandatory
		DESCRIPTION ""
		INDEX { fsOverallQsmuIndex }
		::= { fsOverallQsmuStatsTable 1 }

	fsOverallQsmuIndex OBJECT-TYPE
		SYNTAX  INTEGER 
		ACCESS  read-only
		STATUS  mandatory
		DESCRIPTION ""
		::= { fsOverallQsmuStatsEntry 1 }

	fsQsmuOutCallAttempt OBJECT-TYPE
		SYNTAX  Counter
		ACCESS  read-only
		STATUS  mandatory
		DESCRIPTION ""
		::= { fsOverallQsmuStatsEntry 2 }

	fsQsmuOutCallAccept OBJECT-TYPE
		SYNTAX  Counter
		ACCESS  read-only
		STATUS  mandatory
		DESCRIPTION ""
		::= { fsOverallQsmuStatsEntry 3 }

	fsQsmuInCallAttempt OBJECT-TYPE
		SYNTAX  Counter
		ACCESS  read-only
		STATUS  mandatory
		DESCRIPTION ""
		::= { fsOverallQsmuStatsEntry 4 }

	fsQsmuInCallAccept OBJECT-TYPE
		SYNTAX  Counter
		ACCESS  read-only
		STATUS  mandatory
		DESCRIPTION ""
		::= { fsOverallQsmuStatsEntry 5 }

	fsQsmuTimeout OBJECT-TYPE
		SYNTAX  Counter
		ACCESS  read-only
		STATUS  mandatory
		DESCRIPTION ""
		::= { fsOverallQsmuStatsEntry 6 }

-- ***************************************************************************
-- Voice Overall FTMU Stats

fsOverallFtmuStats OBJECT IDENTIFIER ::= { fsVoiceStats 2 }

fsOverallFtmuStatsTable OBJECT-TYPE
	SYNTAX  SEQUENCE OF FsOverallFtmuStatsEntry
	ACCESS  not-accessible
	STATUS  mandatory
	DESCRIPTION  ""
	::= { fsOverallFtmuStats 1 }

	FsOverallFtmuStatsEntry ::= SEQUENCE {
		fsOverallFtmuIndex		INTEGER,
		fsFtmuNetPktsBadTCID	      Counter,
            fsFtmuNetPktsDropNoConfig     Counter,
		fsFtmuNetPktsBadPayload	      Counter,
            fsFtmuNetPktsTooLarge         Counter,
		fsFtmuNetPktsCombined	      Counter,
            fsFtmuNetPktsRecv             Counter,
		fsFtmuNetPktsTrans	      Counter,
            fsFtmuTelePktsRecv            Counter,
            fsFtmuTeleSubPktsRecv         Counter,
            fsFtmuTeleBadPktsRecv         Counter,
            fsFtmuTelePktsBadLength       Counter,
            fsFtmuTelePktsBadPayload      Counter,
            fsFtmuTelePktsNoTCID          Counter
		}

	fsOverallFtmuStatsEntry OBJECT-TYPE
		SYNTAX  FsOverallFtmuStatsEntry
		ACCESS  not-accessible
		STATUS  mandatory
		DESCRIPTION ""
		INDEX { fsOverallFtmuIndex }
		::= { fsOverallFtmuStatsTable 1 }

	fsOverallFtmuIndex OBJECT-TYPE
		SYNTAX  INTEGER 
		ACCESS  read-only
		STATUS  mandatory
		DESCRIPTION ""
		::= { fsOverallFtmuStatsEntry 1 }

	fsFtmuNetPktsBadTCID OBJECT-TYPE
		SYNTAX  Counter
		ACCESS  read-only
		STATUS  mandatory
		DESCRIPTION ""
		::= { fsOverallFtmuStatsEntry 2 }

	fsFtmuNetPktsDropNoConfig OBJECT-TYPE
		SYNTAX  Counter
		ACCESS  read-only
		STATUS  mandatory
		DESCRIPTION ""
		::= { fsOverallFtmuStatsEntry 3 }

	fsFtmuNetPktsBadPayload OBJECT-TYPE
		SYNTAX  Counter
		ACCESS  read-only
		STATUS  mandatory
		DESCRIPTION ""
		::= { fsOverallFtmuStatsEntry 4 }

	fsFtmuNetPktsTooLarge OBJECT-TYPE
		SYNTAX  Counter
		ACCESS  read-only
		STATUS  mandatory
		DESCRIPTION ""
		::= { fsOverallFtmuStatsEntry 5 }

	fsFtmuNetPktsCombined OBJECT-TYPE
		SYNTAX  Counter
		ACCESS  read-only
		STATUS  mandatory
		DESCRIPTION ""
		::= { fsOverallFtmuStatsEntry 6 }

	fsFtmuNetPktsRecv OBJECT-TYPE
		SYNTAX  Counter
		ACCESS  read-only
		STATUS  mandatory
		DESCRIPTION ""
		::= { fsOverallFtmuStatsEntry 7 }

	fsFtmuNetPktsTrans OBJECT-TYPE
		SYNTAX  Counter
		ACCESS  read-only
		STATUS  mandatory
		DESCRIPTION ""
		::= { fsOverallFtmuStatsEntry 8 }

	fsFtmuTelePktsRecv OBJECT-TYPE
		SYNTAX  Counter
		ACCESS  read-only
		STATUS  mandatory
		DESCRIPTION ""
		::= { fsOverallFtmuStatsEntry 9 }

	fsFtmuTeleSubPktsRecv OBJECT-TYPE
		SYNTAX  Counter
		ACCESS  read-only
		STATUS  mandatory
		DESCRIPTION ""
		::= { fsOverallFtmuStatsEntry 10 }

	fsFtmuTeleBadPktsRecv OBJECT-TYPE
		SYNTAX  Counter
		ACCESS  read-only
		STATUS  mandatory
		DESCRIPTION ""
		::= { fsOverallFtmuStatsEntry 11 }

	fsFtmuTelePktsBadLength OBJECT-TYPE
		SYNTAX  Counter
		ACCESS  read-only
		STATUS  mandatory
		DESCRIPTION ""
		::= { fsOverallFtmuStatsEntry 12 }

	fsFtmuTelePktsBadPayload OBJECT-TYPE
		SYNTAX  Counter
		ACCESS  read-only
		STATUS  mandatory
		DESCRIPTION ""
		::= { fsOverallFtmuStatsEntry 13 }

	fsFtmuTelePktsNoTCID OBJECT-TYPE
		SYNTAX  Counter
		ACCESS  read-only
		STATUS  mandatory
		DESCRIPTION ""
		::= { fsOverallFtmuStatsEntry 14 }

-- ***************************************************************************
-- Channel Qsmu Stats

fsChanQsmuStats OBJECT IDENTIFIER ::= { fsVoiceStats 3 }

fsChanQsmuStatsTable OBJECT-TYPE
	SYNTAX  SEQUENCE OF FsChanQsmuStatsEntry
	ACCESS  not-accessible
	STATUS  mandatory
	DESCRIPTION  ""
	::= { fsChanQsmuStats 1 }

	FsChanQsmuStatsEntry ::= SEQUENCE {
		fsChanQsmuIndex			INTEGER,
            fsQsmuToNetCallCollision      Counter,
            fsQsmuToNetCallFailNoCtrlBlk  Counter,
            fsQsmuToNetCallFailDisPort    Counter,
            fsQsmuFrNetCallFailDisPort    Counter,
            fsQsmuPktsDiscardNoCtrlBlk    Counter
		}

	fsChanQsmuStatsEntry OBJECT-TYPE
		SYNTAX  FsChanQsmuStatsEntry
		ACCESS  not-accessible
		STATUS  mandatory
		DESCRIPTION ""
		INDEX { fsChanQsmuIndex }
		::= { fsChanQsmuStatsTable 1 }

	fsChanQsmuIndex OBJECT-TYPE
		SYNTAX  INTEGER 
		ACCESS  read-only
		STATUS  mandatory
		DESCRIPTION ""
		::= { fsChanQsmuStatsEntry 1 }

	fsQsmuToNetCallCollision OBJECT-TYPE
		SYNTAX  Counter 
		ACCESS  read-only
		STATUS  mandatory
		DESCRIPTION ""
		::= { fsChanQsmuStatsEntry 2 }

	fsQsmuToNetCallFailNoCtrlBlk OBJECT-TYPE
		SYNTAX  Counter 
		ACCESS  read-only
		STATUS  mandatory
		DESCRIPTION ""
		::= { fsChanQsmuStatsEntry 3 }

	fsQsmuToNetCallFailDisPort OBJECT-TYPE
		SYNTAX  Counter 
		ACCESS  read-only
		STATUS  mandatory
		DESCRIPTION ""
		::= { fsChanQsmuStatsEntry 4 }

	fsQsmuFrNetCallFailDisPort OBJECT-TYPE
		SYNTAX  Counter 
		ACCESS  read-only
		STATUS  mandatory
		DESCRIPTION ""
		::= { fsChanQsmuStatsEntry 5 }

	fsQsmuPktsDiscardNoCtrlBlk OBJECT-TYPE
		SYNTAX  Counter 
		ACCESS  read-only
		STATUS  mandatory
		DESCRIPTION ""
		::= { fsChanQsmuStatsEntry 6 }

-- ***************************************************************************
-- Channel Ftmu Stats

fsChanFtmuStats OBJECT IDENTIFIER ::= { fsVoiceStats 4 }

fsChanFtmuStatsTable OBJECT-TYPE
	SYNTAX  SEQUENCE OF FsChanFtmuStatsEntry
	ACCESS  not-accessible
	STATUS  mandatory
	DESCRIPTION  ""
	::= { fsChanFtmuStats 1 }

	FsChanFtmuStatsEntry ::= SEQUENCE {
		fsChanFtmuIndex			INTEGER,
            fsFtmuNetPktsVoicePayload     Counter,
            fsFtmuNetPktsDigitPayload     Counter,
            fsFtmuNetPktsSignalPayload    Counter,
            fsFtmuNetPktsFaxPayload       Counter,
            fsFtmuNetPktsSilencePayload   Counter,
            fsFtmuNetPktsDropped          Counter,
            fsFtmuNetPktsUnknownPayload   Counter,
            fsFtmuTelePktsVoicePayload    Counter,
            fsFtmuTelePktsDigitPayload    Counter,
            fsFtmuTelePktsSignalPayload   Counter,
            fsFtmuTelePktsFaxPayload      Counter,
            fsFtmuTelePktsSilencePayload  Counter,
            fsFtmuTelePktsUnknownPayload  Counter,
            fsChanFtmuTelePktsBadLength   Counter,
            fsFtmuTelePktsDropQueuing     Counter
		}

	fsChanFtmuStatsEntry OBJECT-TYPE
		SYNTAX  FsChanFtmuStatsEntry
		ACCESS  not-accessible
		STATUS  mandatory
		DESCRIPTION ""
		INDEX { fsChanFtmuIndex }
		::= { fsChanFtmuStatsTable 1 }

	fsChanFtmuIndex OBJECT-TYPE
		SYNTAX  INTEGER 
		ACCESS  read-only
		STATUS  mandatory
		DESCRIPTION ""
		::= { fsChanFtmuStatsEntry 1 }

	fsFtmuNetPktsVoicePayload OBJECT-TYPE
		SYNTAX  Counter 
		ACCESS  read-only
		STATUS  mandatory
		DESCRIPTION ""
		::= { fsChanFtmuStatsEntry 2 }

	fsFtmuNetPktsDigitPayload OBJECT-TYPE
		SYNTAX  Counter 
		ACCESS  read-only
		STATUS  mandatory
		DESCRIPTION ""
		::= { fsChanFtmuStatsEntry 3 }

	fsFtmuNetPktsSignalPayload OBJECT-TYPE
		SYNTAX  Counter 
		ACCESS  read-only
		STATUS  mandatory
		DESCRIPTION ""
		::= { fsChanFtmuStatsEntry 4 }

	fsFtmuNetPktsFaxPayload OBJECT-TYPE
		SYNTAX  Counter 
		ACCESS  read-only
		STATUS  mandatory
		DESCRIPTION ""
		::= { fsChanFtmuStatsEntry 5 }

	fsFtmuNetPktsSilencePayload OBJECT-TYPE
		SYNTAX  Counter 
		ACCESS  read-only
		STATUS  mandatory
		DESCRIPTION ""
		::= { fsChanFtmuStatsEntry 6 }

	fsFtmuNetPktsDropped OBJECT-TYPE
		SYNTAX  Counter 
		ACCESS  read-only
		STATUS  mandatory
		DESCRIPTION ""
		::= { fsChanFtmuStatsEntry 7 }

	fsFtmuNetPktsUnknownPayload OBJECT-TYPE
		SYNTAX  Counter 
		ACCESS  read-only
		STATUS  mandatory
		DESCRIPTION ""
		::= { fsChanFtmuStatsEntry 8 }

	fsFtmuTelePktsVoicePayload OBJECT-TYPE
		SYNTAX  Counter 
		ACCESS  read-only
		STATUS  mandatory
		DESCRIPTION ""
		::= { fsChanFtmuStatsEntry 9 }

	fsFtmuTelePktsDigitPayload OBJECT-TYPE
		SYNTAX  Counter 
		ACCESS  read-only
		STATUS  mandatory
		DESCRIPTION ""
		::= { fsChanFtmuStatsEntry 10 }

	fsFtmuTelePktsSignalPayload OBJECT-TYPE
		SYNTAX  Counter 
		ACCESS  read-only
		STATUS  mandatory
		DESCRIPTION ""
		::= { fsChanFtmuStatsEntry 11 }

	fsFtmuTelePktsFaxPayload OBJECT-TYPE
		SYNTAX  Counter 
		ACCESS  read-only
		STATUS  mandatory
		DESCRIPTION ""
		::= { fsChanFtmuStatsEntry 12 }

	fsFtmuTelePktsSilencePayload OBJECT-TYPE
		SYNTAX  Counter 
		ACCESS  read-only
		STATUS  mandatory
		DESCRIPTION ""
		::= { fsChanFtmuStatsEntry 13 }

	fsFtmuTelePktsUnknownPayload OBJECT-TYPE
		SYNTAX  Counter 
		ACCESS  read-only
		STATUS  mandatory
		DESCRIPTION ""
		::= { fsChanFtmuStatsEntry 14 }

	fsChanFtmuTelePktsBadLength OBJECT-TYPE
		SYNTAX  Counter 
		ACCESS  read-only
		STATUS  mandatory
		DESCRIPTION ""
		::= { fsChanFtmuStatsEntry 15 }

	fsFtmuTelePktsDropQueuing OBJECT-TYPE
		SYNTAX  Counter 
		ACCESS  read-only
		STATUS  mandatory
		DESCRIPTION ""
		::= { fsChanFtmuStatsEntry 16 }

-- ***************************************************************************
-- Channel Voice Stats

fsChanVoiceStats OBJECT IDENTIFIER ::= { fsVoiceStats 5 }

fsChanVoiceStatsTable OBJECT-TYPE
	SYNTAX  SEQUENCE OF FsChanVoiceStatsEntry
	ACCESS  not-accessible
	STATUS  mandatory
	DESCRIPTION  ""
	::= { fsChanVoiceStats 1 }

	FsChanVoiceStatsEntry ::= SEQUENCE {
		fsChanVoiceIndex			INTEGER,
		fsChanVoiceAvgPlayDelay		Counter,
            fsChanVoiceLostPackets     	Counter,
            fsChanVoiceReplayPackets     	Counter,
            fsChanVoiceIdlePacketPlayed   Counter,
            fsChanVoicePacketDrop         Counter,
		fsChanVoicePacketSentPlayout	Counter,
            fsChanVoiceInvalidVoiceHead   Counter,
            fsChanVoiceBufferOverflow     Counter,
            fsChanVoiceLostEnhanPkts      Counter,
            fsChanVoiceCorePktsDrop       Counter,
		fsChanVoicePktsRecPlayout	Counter,
            fsChanVoicePktsTrans     	Counter,
            fsChanVoiceSilencePktsTrans   Counter,
            fsChanVoiceMinJitter     	Counter,
            fsChanVoiceMaxJitter          Counter
		}

	fsChanVoiceStatsEntry OBJECT-TYPE
		SYNTAX  FsChanVoiceStatsEntry
		ACCESS  not-accessible
		STATUS  mandatory
		DESCRIPTION ""
		INDEX { fsChanVoiceIndex }
		::= { fsChanVoiceStatsTable 1 }

	fsChanVoiceIndex OBJECT-TYPE
		SYNTAX  INTEGER 
		ACCESS  read-only
		STATUS  mandatory
		DESCRIPTION ""
		::= { fsChanVoiceStatsEntry 1 }

	fsChanVoiceAvgPlayDelay OBJECT-TYPE
		SYNTAX  Counter
		ACCESS  read-only
		STATUS  mandatory
		DESCRIPTION ""
		::= { fsChanVoiceStatsEntry 2 }

	fsChanVoiceLostPackets OBJECT-TYPE
		SYNTAX  Counter
		ACCESS  read-only
		STATUS  mandatory
		DESCRIPTION ""
		::= { fsChanVoiceStatsEntry 3 }

	fsChanVoiceReplayPackets OBJECT-TYPE
		SYNTAX  Counter
		ACCESS  read-only
		STATUS  mandatory
		DESCRIPTION ""
		::= { fsChanVoiceStatsEntry 4 }

	fsChanVoiceIdlePacketPlayed OBJECT-TYPE
		SYNTAX  Counter
		ACCESS  read-only
		STATUS  mandatory
		DESCRIPTION ""
		::= { fsChanVoiceStatsEntry 5 }

	fsChanVoicePacketDrop OBJECT-TYPE
		SYNTAX  Counter
		ACCESS  read-only
		STATUS  mandatory
		DESCRIPTION ""
		::= { fsChanVoiceStatsEntry 6 }

	fsChanVoicePacketSentPlayout OBJECT-TYPE
		SYNTAX  Counter
		ACCESS  read-only
		STATUS  mandatory
		DESCRIPTION ""
		::= { fsChanVoiceStatsEntry 7 }

	fsChanVoiceInvalidVoiceHead OBJECT-TYPE
		SYNTAX  Counter
		ACCESS  read-only
		STATUS  mandatory
		DESCRIPTION ""
		::= { fsChanVoiceStatsEntry 8 }

	fsChanVoiceBufferOverflow OBJECT-TYPE
		SYNTAX  Counter
		ACCESS  read-only
		STATUS  mandatory
		DESCRIPTION ""
		::= { fsChanVoiceStatsEntry 9 }

	fsChanVoiceLostEnhanPkts OBJECT-TYPE
		SYNTAX  Counter
		ACCESS  read-only
		STATUS  mandatory
		DESCRIPTION ""
		::= { fsChanVoiceStatsEntry 10 }

	fsChanVoiceCorePktsDrop OBJECT-TYPE
		SYNTAX  Counter
		ACCESS  read-only
		STATUS  mandatory
		DESCRIPTION ""
		::= { fsChanVoiceStatsEntry 11 }

	fsChanVoicePktsRecPlayout OBJECT-TYPE
		SYNTAX  Counter
		ACCESS  read-only
		STATUS  mandatory
		DESCRIPTION ""
		::= { fsChanVoiceStatsEntry 12 }

	fsChanVoicePktsTrans OBJECT-TYPE
		SYNTAX  Counter
		ACCESS  read-only
		STATUS  mandatory
		DESCRIPTION ""
		::= { fsChanVoiceStatsEntry 13 }

	fsChanVoiceSilencePktsTrans OBJECT-TYPE
		SYNTAX  Counter
		ACCESS  read-only
		STATUS  mandatory
		DESCRIPTION ""
		::= { fsChanVoiceStatsEntry 14 }

	fsChanVoiceMinJitter OBJECT-TYPE
		SYNTAX  Counter
		ACCESS  read-only
		STATUS  mandatory
		DESCRIPTION ""
		::= { fsChanVoiceStatsEntry 15 }

	fsChanVoiceMaxJitter OBJECT-TYPE
		SYNTAX  Counter
		ACCESS  read-only
		STATUS  mandatory
		DESCRIPTION ""
		::= { fsChanVoiceStatsEntry 16 }

-- ***************************************************************************
-- Channel Modem Stats

fsChanModemStats OBJECT IDENTIFIER ::= { fsVoiceStats 6 }

fsChanModemStatsTable OBJECT-TYPE
	SYNTAX  SEQUENCE OF FsChanModemStatsEntry
	ACCESS  not-accessible
	STATUS  mandatory
	DESCRIPTION  ""
	::= { fsChanModemStats 1 }

	FsChanModemStatsEntry ::= SEQUENCE {
		fsChanModemIndex			INTEGER,
            fsModemStatusRegister         INTEGER,
		fsModemRecvLevel    		INTEGER,
            fsModemRecvRate    		INTEGER,
		fsModemTransLevel    		INTEGER,
            fsModemTransRate    		INTEGER,
            fsModemSigToNoiseRatio    	INTEGER,
		fsModemCarFreOffset    		INTEGER,
            fsModemTimingFreOffset    	INTEGER
		}

	fsChanModemStatsEntry OBJECT-TYPE
		SYNTAX  FsChanModemStatsEntry
		ACCESS  not-accessible
		STATUS  mandatory
		DESCRIPTION ""
		INDEX { fsChanModemIndex }
		::= { fsChanModemStatsTable 1 }

	fsChanModemIndex OBJECT-TYPE
		SYNTAX  INTEGER 
		ACCESS  read-only
		STATUS  mandatory
		DESCRIPTION ""
		::= { fsChanModemStatsEntry 1 }

	fsModemStatusRegister OBJECT-TYPE
		SYNTAX  INTEGER 
		ACCESS  read-only
		STATUS  mandatory
		DESCRIPTION ""
		::= { fsChanModemStatsEntry 2 }

	fsModemRecvLevel OBJECT-TYPE
		SYNTAX  INTEGER 
		ACCESS  read-only
		STATUS  mandatory
		DESCRIPTION ""
		::= { fsChanModemStatsEntry 3 }

	fsModemRecvRate OBJECT-TYPE
		SYNTAX  INTEGER 
		ACCESS  read-only
		STATUS  mandatory
		DESCRIPTION ""
		::= { fsChanModemStatsEntry 4 }

	fsModemTransLevel OBJECT-TYPE
		SYNTAX  INTEGER 
		ACCESS  read-only
		STATUS  mandatory
		DESCRIPTION ""
		::= { fsChanModemStatsEntry 5 }

	fsModemTransRate OBJECT-TYPE
		SYNTAX  INTEGER 
		ACCESS  read-only
		STATUS  mandatory
		DESCRIPTION ""
		::= { fsChanModemStatsEntry 6 }

	fsModemSigToNoiseRatio OBJECT-TYPE
		SYNTAX  INTEGER 
		ACCESS  read-only
		STATUS  mandatory
		DESCRIPTION ""
		::= { fsChanModemStatsEntry 7 }

	fsModemCarFreOffset OBJECT-TYPE
		SYNTAX  INTEGER 
		ACCESS  read-only
		STATUS  mandatory
		DESCRIPTION ""
		::= { fsChanModemStatsEntry 8 }

	fsModemTimingFreOffset OBJECT-TYPE
		SYNTAX  INTEGER 
		ACCESS  read-only
		STATUS  mandatory
		DESCRIPTION ""
		::= { fsChanModemStatsEntry 9 }

-- ***************************************************************************
-- Channel Fax Stats

fsChanFaxStats OBJECT IDENTIFIER ::= { fsVoiceStats 7 }

fsChanFaxStatsTable OBJECT-TYPE
	SYNTAX  SEQUENCE OF FsChanFaxStatsEntry
	ACCESS  not-accessible
	STATUS  mandatory
	DESCRIPTION  ""
	::= { fsChanFaxStats 1 }

	FsChanFaxStatsEntry ::= SEQUENCE {
		fsChanFaxIndex		INTEGER,
		fsFaxTxPkts    		Counter,
            fsFaxRxPkts    		Counter,
            fsFaxPktsLost    		Counter,
            fsFaxPktsDropped        Counter,
            fsFaxPktsOutOfSeq       Counter,
            fsFaxModulation    	Counter,
            fsFaxPageCount    	Counter
		}

	fsChanFaxStatsEntry OBJECT-TYPE
		SYNTAX  FsChanFaxStatsEntry
		ACCESS  not-accessible
		STATUS  mandatory
		DESCRIPTION ""
		INDEX { fsChanFaxIndex }
		::= { fsChanFaxStatsTable 1 }

	fsChanFaxIndex OBJECT-TYPE
		SYNTAX  INTEGER 
		ACCESS  read-only
		STATUS  mandatory
		DESCRIPTION ""
		::= { fsChanFaxStatsEntry 1 }

	fsFaxTxPkts OBJECT-TYPE
		SYNTAX  Counter 
		ACCESS  read-only
		STATUS  mandatory
		DESCRIPTION ""
		::= { fsChanFaxStatsEntry 2 }

	fsFaxRxPkts OBJECT-TYPE
		SYNTAX  Counter 
		ACCESS  read-only
		STATUS  mandatory
		DESCRIPTION ""
		::= { fsChanFaxStatsEntry 3 }

	fsFaxPktsLost OBJECT-TYPE
		SYNTAX  Counter 
		ACCESS  read-only
		STATUS  mandatory
		DESCRIPTION ""
		::= { fsChanFaxStatsEntry 4 }

	fsFaxPktsDropped OBJECT-TYPE
		SYNTAX  Counter 
		ACCESS  read-only
		STATUS  mandatory
		DESCRIPTION ""
		::= { fsChanFaxStatsEntry 5 }

	fsFaxPktsOutOfSeq OBJECT-TYPE
		SYNTAX  Counter 
		ACCESS  read-only
		STATUS  mandatory
		DESCRIPTION ""
		::= { fsChanFaxStatsEntry 6 }

	fsFaxModulation OBJECT-TYPE
		SYNTAX  Counter 
		ACCESS  read-only
		STATUS  mandatory
		DESCRIPTION ""
		::= { fsChanFaxStatsEntry 7 }

	fsFaxPageCount OBJECT-TYPE
		SYNTAX  Counter 
		ACCESS  read-only
		STATUS  mandatory
		DESCRIPTION ""
		::= { fsChanFaxStatsEntry 8 }

-- ***************************************************************************
-- Channel Tele Stats

fsChanTeleStats OBJECT IDENTIFIER ::= { fsVoiceStats 8 }

fsChanTeleStatsTable OBJECT-TYPE
	SYNTAX  SEQUENCE OF FsChanTeleStatsEntry
	ACCESS  not-accessible
	STATUS  mandatory
	DESCRIPTION  ""
	::= { fsChanTeleStats 1 }

	FsChanTeleStatsEntry ::= SEQUENCE {
		fsChanTeleIndex		INTEGER,
		fsChanTeleOffhooks	Counter,
            fsChanTeleOnhooks     	Counter,
            fsChanTeleSeizures     	Counter
		}

	fsChanTeleStatsEntry OBJECT-TYPE
		SYNTAX  FsChanTeleStatsEntry
		ACCESS  not-accessible
		STATUS  mandatory
		DESCRIPTION ""
		INDEX { fsChanTeleIndex }
		::= { fsChanTeleStatsTable 1 }

	fsChanTeleIndex OBJECT-TYPE
		SYNTAX  INTEGER 
		ACCESS  read-only
		STATUS  mandatory
		DESCRIPTION ""
		::= { fsChanTeleStatsEntry 1 }

	fsChanTeleOffhooks OBJECT-TYPE
		SYNTAX  Counter
		ACCESS  read-only
		STATUS  mandatory
		DESCRIPTION ""
		::= { fsChanTeleStatsEntry 2 }

	fsChanTeleOnhooks OBJECT-TYPE
		SYNTAX  Counter
		ACCESS  read-only
		STATUS  mandatory
		DESCRIPTION ""
		::= { fsChanTeleStatsEntry 3 }

	fsChanTeleSeizures OBJECT-TYPE
		SYNTAX  Counter
		ACCESS  read-only
		STATUS  mandatory
		DESCRIPTION ""
		::= { fsChanTeleStatsEntry 4 }

-- ***************************************************************************
-- Channel Echo Stats

fsChanEchoStats OBJECT IDENTIFIER ::= { fsVoiceStats 9 }

fsChanEchoStatsTable OBJECT-TYPE
	SYNTAX  SEQUENCE OF FsChanEchoStatsEntry
	ACCESS  not-accessible
	STATUS  mandatory
	DESCRIPTION  ""
	::= { fsChanEchoStats 1 }

	FsChanEchoStatsEntry ::= SEQUENCE {
		fsChanEchoIndex		INTEGER,
            fsEchoCNVState          INTEGER,
            fsEchoPxLevel           INTEGER,
            fsEchoPyLevel           INTEGER,
            fsEchoPeLevel           INTEGER,
            fsEchoPostUpdateCnt     Counter,
            fsEchoAttempUpdateCnt   Counter,
            fsEchoDivergeCnt        Counter,
            fsEchoERLEBypassCnt     Counter,
            fsEchoXTONECnt          Counter,
            fsEchoForeSwitchCnt     Counter,
            fsEchoBackSwitchCnt     Counter,
            fsEchoXIDLECnt          Counter,
            fsEchoOtherBypassCnt    Counter
		}

	fsChanEchoStatsEntry OBJECT-TYPE
		SYNTAX  FsChanEchoStatsEntry
		ACCESS  not-accessible
		STATUS  mandatory
		DESCRIPTION ""
		INDEX { fsChanEchoIndex }
		::= { fsChanEchoStatsTable 1 }

	fsChanEchoIndex OBJECT-TYPE
		SYNTAX  INTEGER 
		ACCESS  read-only
		STATUS  mandatory
		DESCRIPTION ""
		::= { fsChanEchoStatsEntry 1 }

	fsEchoCNVState OBJECT-TYPE
		SYNTAX  INTEGER 
		ACCESS  read-only
		STATUS  mandatory
		DESCRIPTION ""
		::= { fsChanEchoStatsEntry 2 }

	fsEchoPxLevel OBJECT-TYPE
		SYNTAX  INTEGER 
		ACCESS  read-only
		STATUS  mandatory
		DESCRIPTION ""
		::= { fsChanEchoStatsEntry 3 }

	fsEchoPyLevel OBJECT-TYPE
		SYNTAX  INTEGER 
		ACCESS  read-only
		STATUS  mandatory
		DESCRIPTION ""
		::= { fsChanEchoStatsEntry 4 }

	fsEchoPeLevel OBJECT-TYPE
		SYNTAX  INTEGER 
		ACCESS  read-only
		STATUS  mandatory
		DESCRIPTION ""
		::= { fsChanEchoStatsEntry 5 }

	fsEchoPostUpdateCnt OBJECT-TYPE
		SYNTAX  Counter 
		ACCESS  read-only
		STATUS  mandatory
		DESCRIPTION ""
		::= { fsChanEchoStatsEntry 6 }

	fsEchoAttempUpdateCnt OBJECT-TYPE
		SYNTAX  Counter 
		ACCESS  read-only
		STATUS  mandatory
		DESCRIPTION ""
		::= { fsChanEchoStatsEntry 7 }

	fsEchoDivergeCnt OBJECT-TYPE
		SYNTAX  Counter 
		ACCESS  read-only
		STATUS  mandatory
		DESCRIPTION ""
		::= { fsChanEchoStatsEntry 8 }

	fsEchoERLEBypassCnt OBJECT-TYPE
		SYNTAX  Counter 
		ACCESS  read-only
		STATUS  mandatory
		DESCRIPTION ""
		::= { fsChanEchoStatsEntry 9 }

	fsEchoXTONECnt OBJECT-TYPE
		SYNTAX  Counter 
		ACCESS  read-only
		STATUS  mandatory
		DESCRIPTION ""
		::= { fsChanEchoStatsEntry 10 }

	fsEchoForeSwitchCnt OBJECT-TYPE
		SYNTAX  Counter 
		ACCESS  read-only
		STATUS  mandatory
		DESCRIPTION ""
		::= { fsChanEchoStatsEntry 11 }

	fsEchoBackSwitchCnt OBJECT-TYPE
		SYNTAX  Counter 
		ACCESS  read-only
		STATUS  mandatory
		DESCRIPTION ""
		::= { fsChanEchoStatsEntry 12 }

	fsEchoXIDLECnt OBJECT-TYPE
		SYNTAX  Counter 
		ACCESS  read-only
		STATUS  mandatory
		DESCRIPTION ""
		::= { fsChanEchoStatsEntry 13 }

	fsEchoOtherBypassCnt OBJECT-TYPE
		SYNTAX  Counter 
		ACCESS  read-only
		STATUS  mandatory
		DESCRIPTION ""
		::= { fsChanEchoStatsEntry 14 }

-- ***************************************************************************
-- CDR Stats

fsCdrStats OBJECT IDENTIFIER ::= { fsVoiceStats 10 }

fsCdrStatsTable OBJECT-TYPE
	SYNTAX  SEQUENCE OF FsCdrStatsEntry
	ACCESS  not-accessible
	STATUS  mandatory
	DESCRIPTION  ""
	::= { fsCdrStats 1 }

	FsCdrStatsEntry ::= SEQUENCE {
		fsCdrRecordNo	INTEGER,
		fsCdrBufLeft	DisplayString,
            fsCdrBufRight	DisplayString
		}

	fsCdrStatsEntry OBJECT-TYPE
		SYNTAX  FsCdrStatsEntry
		ACCESS  not-accessible
		STATUS  mandatory
		DESCRIPTION ""
		INDEX { fsCdrRecordNo }
		::= { fsCdrStatsTable 1 }

	fsCdrRecordNo OBJECT-TYPE
		SYNTAX  INTEGER 
		ACCESS  read-only
		STATUS  mandatory
		DESCRIPTION ""
		::= { fsCdrStatsEntry 1 }

	fsCdrBufLeft OBJECT-TYPE
		SYNTAX  DisplayString
		ACCESS  read-only
		STATUS  mandatory
		DESCRIPTION ""
		::= { fsCdrStatsEntry 2 }

	fsCdrBufRight OBJECT-TYPE
		SYNTAX  DisplayString
		ACCESS  read-only
		STATUS  mandatory
		DESCRIPTION ""
		::= { fsCdrStatsEntry 3 }
END
