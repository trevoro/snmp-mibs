--			Ascend mibatmspvc MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBATMSPVC-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibatmSoftPVcAddrProfile  OBJECT IDENTIFIER ::= { configuration 54}
    mibatmSpvcConfigProfile  OBJECT IDENTIFIER ::= { configuration 53}

	-- The mibatmSoftPVcAddrProfile table
	--
	-- This table contains parameters for the mibatmSoftPVcAddrProfile profile
	--

    mibatmSoftPVcAddrProfileTable	OBJECT-TYPE
	SYNTAX		SEQUENCE OF MibatmSoftPVcAddrProfileEntry
	ACCESS		not-accessible
	STATUS		mandatory
	DESCRIPTION	"A list of mibatmSoftPVcAddrProfile profile entries."
	::= { mibatmSoftPVcAddrProfile 1 }

    mibatmSoftPVcAddrProfileEntry	OBJECT-TYPE
	SYNTAX		MibatmSoftPVcAddrProfileEntry
	ACCESS		not-accessible
	STATUS		mandatory
	DESCRIPTION	"A mibatmSoftPVcAddrProfile entry containing objects that
			 maps to the parameters of mibatmSoftPVcAddrProfile profile."
	INDEX		{ atmSoftPVcAddrProfile-Shelf-o, atmSoftPVcAddrProfile-Slot-o, atmSoftPVcAddrProfile-Item-o, atmSoftPVcAddrProfile-LogicalItem-o }
	::= { mibatmSoftPVcAddrProfileTable 1 }

    MibatmSoftPVcAddrProfileEntry ::=
	SEQUENCE {
	    atmSoftPVcAddrProfile-Shelf-o
		INTEGER,
	    atmSoftPVcAddrProfile-Slot-o
		INTEGER,
	    atmSoftPVcAddrProfile-Item-o
		INTEGER,
	    atmSoftPVcAddrProfile-LogicalItem-o
		INTEGER,
	    atmSoftPVcAddrProfile-Index-PhysicalAddress-Shelf
		INTEGER,
	    atmSoftPVcAddrProfile-Index-PhysicalAddress-Slot
		INTEGER,
	    atmSoftPVcAddrProfile-Index-PhysicalAddress-ItemNumber
		INTEGER,
	    atmSoftPVcAddrProfile-Index-LogicalItem
		INTEGER,
	    atmSoftPVcAddrProfile-SpvcAtmAddress
		DisplayString,
	    atmSoftPVcAddrProfile-Action-o
		INTEGER
	}

    atmSoftPVcAddrProfile-Shelf-o	OBJECT-TYPE
	SYNTAX	INTEGER
	ACCESS	read-only
	STATUS	mandatory
	DESCRIPTION	""
	::= { mibatmSoftPVcAddrProfileEntry 1 }

    atmSoftPVcAddrProfile-Slot-o	OBJECT-TYPE
	SYNTAX	INTEGER
	ACCESS	read-only
	STATUS	mandatory
	DESCRIPTION	""
	::= { mibatmSoftPVcAddrProfileEntry 2 }

    atmSoftPVcAddrProfile-Item-o	OBJECT-TYPE
	SYNTAX	INTEGER
	ACCESS	read-only
	STATUS	mandatory
	DESCRIPTION	""
	::= { mibatmSoftPVcAddrProfileEntry 3 }

    atmSoftPVcAddrProfile-LogicalItem-o	OBJECT-TYPE
	SYNTAX	INTEGER
	ACCESS	read-only
	STATUS	mandatory
	DESCRIPTION	""
	::= { mibatmSoftPVcAddrProfileEntry 4 }

    atmSoftPVcAddrProfile-Index-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibatmSoftPVcAddrProfileEntry 5 }

    atmSoftPVcAddrProfile-Index-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibatmSoftPVcAddrProfileEntry 6 }

    atmSoftPVcAddrProfile-Index-PhysicalAddress-ItemNumber	OBJECT-TYPE
	SYNTAX	INTEGER
	ACCESS	read-write
	STATUS	mandatory
	DESCRIPTION	"A number that specifies an addressable entity within the context of shelf and slot."
	::= { mibatmSoftPVcAddrProfileEntry 7 }

    atmSoftPVcAddrProfile-Index-LogicalItem	OBJECT-TYPE
	SYNTAX	INTEGER
	ACCESS	read-write
	STATUS	mandatory
	DESCRIPTION	"A number that specifies an addressable logical entity within the context of a physical address."
	::= { mibatmSoftPVcAddrProfileEntry 8 }

    atmSoftPVcAddrProfile-SpvcAtmAddress	OBJECT-TYPE
	SYNTAX	DisplayString
	ACCESS	read-write
	STATUS	mandatory
	DESCRIPTION	"Soft PVC Interface ATM Address"
	::= { mibatmSoftPVcAddrProfileEntry 9 }

    atmSoftPVcAddrProfile-Action-o	OBJECT-TYPE
	SYNTAX	INTEGER {
		    noAction (1),
		    createProfile (2),
		    deleteProfile (3)
		}
	ACCESS	read-write
	STATUS	mandatory
	DESCRIPTION	""
	::= { mibatmSoftPVcAddrProfileEntry 10 }


	-- The mibatmSpvcConfigProfile table
	--
	-- This table contains parameters for the mibatmSpvcConfigProfile profile
	--

    mibatmSpvcConfigProfileTable	OBJECT-TYPE
	SYNTAX		SEQUENCE OF MibatmSpvcConfigProfileEntry
	ACCESS		not-accessible
	STATUS		mandatory
	DESCRIPTION	"A list of mibatmSpvcConfigProfile profile entries."
	::= { mibatmSpvcConfigProfile 1 }

    mibatmSpvcConfigProfileEntry	OBJECT-TYPE
	SYNTAX		MibatmSpvcConfigProfileEntry
	ACCESS		not-accessible
	STATUS		mandatory
	DESCRIPTION	"A mibatmSpvcConfigProfile entry containing objects that
			 maps to the parameters of mibatmSpvcConfigProfile profile."
	INDEX		{ atmSpvcConfigProfile-Index-o }
	::= { mibatmSpvcConfigProfileTable 1 }

    MibatmSpvcConfigProfileEntry ::=
	SEQUENCE {
	    atmSpvcConfigProfile-Index-o
		INTEGER,
	    atmSpvcConfigProfile-FailureTrapEnable
		INTEGER,
	    atmSpvcConfigProfile-FailureNotificationInterval
		INTEGER,
	    atmSpvcConfigProfile-Action-o
		INTEGER
	}

    atmSpvcConfigProfile-Index-o	OBJECT-TYPE
	SYNTAX	INTEGER
	ACCESS	read-only
	STATUS	mandatory
	DESCRIPTION	""
	::= { mibatmSpvcConfigProfileEntry 1 }

    atmSpvcConfigProfile-FailureTrapEnable	OBJECT-TYPE
	SYNTAX	INTEGER {
		    no (1),
		    yes (2)
		}
	ACCESS	read-write
	STATUS	mandatory
	DESCRIPTION	"Allows the generation of traps in response to call failures. By default, this object is set to 'false'."
	::= { mibatmSpvcConfigProfileEntry 2 }

    atmSpvcConfigProfile-FailureNotificationInterval	OBJECT-TYPE
	SYNTAX	INTEGER
	ACCESS	read-write
	STATUS	mandatory
	DESCRIPTION	"The minimum interval between the sending of atmSoftPvcCallFailuresTrap notifications."
	::= { mibatmSpvcConfigProfileEntry 3 }

    atmSpvcConfigProfile-Action-o	OBJECT-TYPE
	SYNTAX	INTEGER {
		    noAction (1),
		    createProfile (2),
		    deleteProfile (3)
		}
	ACCESS	read-write
	STATUS	mandatory
	DESCRIPTION	""
	::= { mibatmSpvcConfigProfileEntry 4 }

END
