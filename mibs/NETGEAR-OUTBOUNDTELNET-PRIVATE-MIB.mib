NETGEAR-OUTBOUNDTELNET-PRIVATE-MIB DEFINITIONS ::= BEGIN

-- NETGEAR OUTBOUND TELNET MIB
-- Copyright LVL7 Systems (2002-2005)  All rights reserved.

-- This SNMP Management Information Specification
-- embodies LVL7 System's confidential and proprietary
-- intellectual property.  LVL7 Systems retains all title
-- and ownership in the Specification including any revisions.

-- This Specification is supplied "AS IS", LVL7 Systems
-- makes no warranty, either expressed or implied,
-- as to the use, operation, condition, or performance of the
-- Specification.



IMPORTS
    MODULE-IDENTITY, OBJECT-TYPE, Integer32               FROM SNMPv2-SMI
    ng7000Switch                                          FROM NETGEAR-REF-MIB;

    agentOutboundTelnetPrivate MODULE-IDENTITY
    LAST-UPDATED "200502231200Z" -- 23 Feb 2005 12:00:00 GMT
    ORGANIZATION "Netgear"
    CONTACT-INFO
       ""
        
    DESCRIPTION
       "The NETGEAR Private MIB for Outbound Telnet"
       
    -- revision history
    REVISION
       "200502231200Z" -- 23 Feb 2005 12:00:00 GMT
   	DESCRIPTION
       "Initial revision."
       
    ::= { ng7000Switch 19 }


     --**************************************************************************************
    -- agentOutboundTelnetGroup -> contains MIB objects displaying various properties of a Outbound Telnet
    --
    --**************************************************************************************

    agentOutboundTelnetGroup       OBJECT IDENTIFIER ::= { agentOutboundTelnetPrivate 1 }

    agentOutboundTelnetAdminMode OBJECT-TYPE
      SYNTAX      INTEGER {
                  enable(1),
                  disable(2)
                  }
      MAX-ACCESS read-write
      STATUS     current
      DESCRIPTION
       " Admin-mode of the Outbound Telnet."
      DEFVAL { enable }
    ::= { agentOutboundTelnetGroup 1 }


    agentOutboundTelnetMaxNoOfSessions OBJECT-TYPE
      SYNTAX     INTEGER (0..5)
      MAX-ACCESS read-write
      STATUS     current
      DESCRIPTION
       " The maximum no. of Outbound Telnet sessions allowed."
      DEFVAL { 5 }
    ::= { agentOutboundTelnetGroup 2 }

    agentOutboundTelnetTimeout OBJECT-TYPE
      SYNTAX     INTEGER (0..160)
      MAX-ACCESS read-write
      STATUS     current
      DESCRIPTION
       " The login inactivity timeout value for Outbound Telnet."
      DEFVAL { 0 }
    ::= { agentOutboundTelnetGroup 3 }
END
