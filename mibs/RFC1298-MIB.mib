-- WinAgents MIB Extraction Wizard
-- Extracted from rfc1298.txt 16.03.2005 20:20:15

RFC1298-MIB DEFINITIONS ::= BEGIN

   IMPORTS
     enterprises         FROM RFC1155-SMI;

     novell              OBJECT IDENTIFIER ::= { enterprises 23 }
     transportDomains    OBJECT IDENTIFIER ::= { novell 7 }

     ipxTransportDomain  OBJECT IDENTIFIER ::= { transportDomains 1 }

   -- Authoritatively names the IPX Transport Domain

   IpxTransportAddress ::= OCTET STRING (SIZE (12))

   -- A textual convention denoting a transport service address in
   -- the ipxTransportDomain.  An IpxTransportAddress is 12 octets
   -- long and comprises 3 fields, each in network-byte (high-low)
   -- order.

   -- The first field is 4 octets long and contains the network
   -- number.

   -- The next field is 6 octets long and contains the physical
   -- address of the node.  Since IPX can run over a variety of
   -- subnet architectures, the physical node address may not
   -- require all 6 octets.  As specified in [2], the physical
   -- node address will occupy the least significant portion of
   -- the field and the most significant octets should be set
   -- to zero.

   -- The last field is 2 octets long and contains the socket
   -- number.

END
