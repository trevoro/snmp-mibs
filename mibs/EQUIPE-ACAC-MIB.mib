EQUIPE-ACAC-MIB DEFINITIONS ::= BEGIN

    --
    -- Equipe ACAC MIB
    --

    IMPORTS
        enterprises
            FROM RFC1155-SMI
        Gauge32, MODULE-IDENTITY, OBJECT-TYPE, Counter32, Counter64
            FROM SNMPv2-SMI
        TEXTUAL-CONVENTION
            FROM SNMPv2-TC
        AtmServiceCategory
            FROM ATM-TC-MIB;

    equipe        OBJECT IDENTIFIER ::= { enterprises 5022 }

    eqAcacMib MODULE-IDENTITY
        LAST-UPDATED "0012270000Z"
        ORGANIZATION ""
        CONTACT-INFO
            "Jas Parmar
            Equipe Communications
            100 Nagog Park
            Acton MA 01720"
        DESCRIPTION
            "This is the Equipe ACAC MIB module."
        ::= { equipe 5 }

--
-- Virtual Interface Table
--

    eqAcacViTable OBJECT-TYPE
        SYNTAX      SEQUENCE OF EqAcacViEntry
        MAX-ACCESS  not-accessible
        STATUS      current
        DESCRIPTION
           "This table contains stats for an ACAC logical port."
        ::= { eqAcacMib 1 }
        
    eqAcacViEntry OBJECT-TYPE
        SYNTAX      EqAcacViEntry
        MAX-ACCESS  not-accessible
        STATUS      current
        DESCRIPTION
                "An ACAC logical port stats entry."
        INDEX    { eqAcacViIfIndex }
        ::= { eqAcacViTable 1 }

    EqAcacViEntry ::=
        SEQUENCE {
            eqAcacViIfIndex
                    INTEGER,
            eqAcacViStartingBw
                    INTEGER,
            eqAcacViConsumedBw
                    Gauge32,
            eqAcacViInConsideredCcts
                    Counter32,
            eqAcacViInRejectedCcts
                    Counter32,
            eqAcacViInActiveCcts
                    Gauge32,
            eqAcacViInReservedCcts
                    Gauge32,
            eqAcacViOutConsideredCcts
                    Counter32,
            eqAcacViOutRejectedCcts
                    Counter32,
            eqAcacViOutActiveCcts
                    Gauge32,
            eqAcacViOutReservedCcts
                    Gauge32
        }

    eqAcacViIfIndex OBJECT-TYPE
        SYNTAX      INTEGER (1..2147483647)
        MAX-ACCESS  read-only
        STATUS      current
        DESCRIPTION
            "The ifIndex for the logical port."
        ::= { eqAcacViEntry 1 }

    eqAcacViStartingBw OBJECT-TYPE
        SYNTAX      INTEGER (1..2147483647)
        MAX-ACCESS  read-only
        STATUS      current
        DESCRIPTION
            "The initial amount of bandwidth allocated to this virtual
            interface (in cells per second)."
        ::= { eqAcacViEntry 2 }

    eqAcacViConsumedBw OBJECT-TYPE
        SYNTAX      Gauge32
        MAX-ACCESS  read-only
        STATUS      current
        DESCRIPTION
            "The amount of bandwidth consumed by existing circuits (in
            cells per second)."
        ::= { eqAcacViEntry 3 }

    eqAcacViInConsideredCcts OBJECT-TYPE
        SYNTAX      Counter32
        MAX-ACCESS  read-only
        STATUS      current
        DESCRIPTION
            "The number of circuits that CAC has been asked to consider
            for admission."
        ::= { eqAcacViEntry 4 }

    eqAcacViInRejectedCcts OBJECT-TYPE
        SYNTAX      Counter32
        MAX-ACCESS  read-only
        STATUS      current
        DESCRIPTION
            "The number of circuits that CAC has been asked to consider
            for admission for which sufficient resources have not been
            available.  Hence the circuit was rejected."
        ::= { eqAcacViEntry 5 }

    eqAcacViInActiveCcts OBJECT-TYPE
        SYNTAX      Gauge32
        MAX-ACCESS  read-only
        STATUS      current
        DESCRIPTION
            "The number of currently active circuits"
        ::= { eqAcacViEntry 6 }

    eqAcacViInReservedCcts OBJECT-TYPE
        SYNTAX      Gauge32
        MAX-ACCESS  read-only
        STATUS      current
        DESCRIPTION
            "The number of circuits that CAC has reserved resources, but
            is waiting for a commit."
        ::= { eqAcacViEntry 7 }

    eqAcacViOutConsideredCcts OBJECT-TYPE
        SYNTAX      Counter32
        MAX-ACCESS  read-only
        STATUS      current
        DESCRIPTION
            "The number of circuits that CAC has been asked to consider
            for admission."
        ::= { eqAcacViEntry 8 }

    eqAcacViOutRejectedCcts OBJECT-TYPE
        SYNTAX      Counter32
        MAX-ACCESS  read-only
        STATUS      current
        DESCRIPTION
            "The number of circuits that CAC has been asked to consider
            for admission for which sufficient resources have not been
            available.  Hence the circuit was rejected."
        ::= { eqAcacViEntry 9 }

    eqAcacViOutActiveCcts OBJECT-TYPE
        SYNTAX      Gauge32
        MAX-ACCESS  read-only
        STATUS      current
        DESCRIPTION
            "The number of currently active circuits."
        ::= { eqAcacViEntry 10 }

    eqAcacViOutReservedCcts OBJECT-TYPE
        SYNTAX      Gauge32
        MAX-ACCESS  read-only
        STATUS      current
        DESCRIPTION
            "The number of circuits that CAC has reserved resources, but
            is waiting for a commit."
        ::= { eqAcacViEntry 11 }


--
-- Virtual Interface Service Category Table
--


    eqAcacViServCatTable OBJECT-TYPE
        SYNTAX      SEQUENCE OF EqAcacViServCatEntry
        MAX-ACCESS  not-accessible
        STATUS      current
        DESCRIPTION
           "This table contains stats per ATM Service Category for an
            ACAC logical port."
        ::= { eqAcacMib 2 }
        
    eqAcacViServCatEntry OBJECT-TYPE
        SYNTAX      EqAcacViServCatEntry
        MAX-ACCESS  not-accessible
        STATUS      current
        DESCRIPTION
                "An ACAC logical port service category stats entry."
        INDEX    { eqAcacViServCatIfIndex, eqAcacViServCatServiceCategory }
        ::= { eqAcacViServCatTable 1 }

    EqAcacViServCatEntry ::=
        SEQUENCE {
            eqAcacViServCatIfIndex
                    INTEGER,
            eqAcacViServCatServiceCategory
                    AtmServiceCategory,
            eqAcacViServCatConsumedBw
                    Gauge32,
            eqAcacViServCatActiveCcts
                    Gauge32
        }

    eqAcacViServCatIfIndex OBJECT-TYPE
        SYNTAX      INTEGER (1..2147483647)
        MAX-ACCESS  read-only
        STATUS      current
        DESCRIPTION
            "The ifIndex for the logical port."
        ::= { eqAcacViServCatEntry 1 }

    eqAcacViServCatServiceCategory OBJECT-TYPE
        SYNTAX      AtmServiceCategory
        MAX-ACCESS  read-only
        STATUS      current
        DESCRIPTION
            "The Service Category that this instance in the table describes."
        ::= { eqAcacViServCatEntry 2 }

    eqAcacViServCatConsumedBw OBJECT-TYPE
        SYNTAX      Gauge32
        MAX-ACCESS  read-only
        STATUS      current
        DESCRIPTION
            "The amount of bandwidth currently considered in use by this
            service category for the purposes of CAC calculations.  Note that
            this does not represent actual traffic utilitization."
        ::= { eqAcacViServCatEntry 3 }

    eqAcacViServCatActiveCcts OBJECT-TYPE
        SYNTAX      Gauge32
        MAX-ACCESS  read-only
        STATUS      current
        DESCRIPTION
            "The number of active circuits for this service category on this
            virtual interface."
        ::= { eqAcacViServCatEntry 4 }
        

END
