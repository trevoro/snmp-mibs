--======================================================
--
-- MIB     : Meritage                Lucent Technologies
--
-- Version: 1.2.3                       26 July 1999
--
-- RCS Id : Yigal N.
--
--======================================================
--
-- Copyright 1999 Lucent Technologies, Ltd.
-- All Rights Reserved.
--
-- Reproduction of this document is authorized on condition
-- that the foregoing copyright notice is included.
--
-- This Lucent Technologies SNMP Management Information Base 
-- Specification embodies Lucent Technologies confidential and
-- proprietary intellectual property.  Lucent Technologies retains all
-- title and ownership in the Specification, including any revisions
--
-- It is Lucent Technologies intent to encourage the widespread use of this
-- Specification in connection with the management of Lucent Technologies
-- products.
-- Lucent Technologies grants vendors, end-users, and other interested parties
-- a non-exclusive license to use this Specification in connection
-- with the management of Lucent Technologies products.
--
-- This Specification is supplied "as is," and Lucent Technologies makes
-- no warranty, either express or implied, as to the use,
-- operation, condition, or performance of the Specification.
--
--======================================================
--
-- RCS
--
-- Version 1.2.3
-- 26 July 1999
-- 1. Add the MIB - meritageClockSourceFraming - Gidi N.
-- 2. Add new enumeration m-ps800-dc (4) to meritageBasePSUType
--
-- Version 1.2.2
-- 21 June 1999
-- 1. Update description of meritageBaseFaultMask - Gidi N.
--
-- Version 1.2.1
-- 9 June 1999
-- 1. Remove the MIB - meritageClockSourcCurrentPort - Gidi N.
-- 2. Change enumeration to freeRunning in meritageClockStatus - Gidi N.
-- 3. Update some descriptions in the meritageClock Group  - Gidi N.
--
-- Version 1.2.0
-- 19 May 1999
-- 1. Add sub-tree meritageClock with 5 new scalars MIB items - Gidi N.
-- 2. Add sub-tree meritageClockSource with a new table - Gidi N.
-- 3. Update the meritageBaseFaultMask with bits 7-12 - Gidi N.
--
-- Version 1.1.0
-- 12 March 1999
-- 1. Add 2 new MIB item: meritageBaseUpBckplnConfiguration
--    meritageBaseUpBckplnConfigurationSymbol - Gidi N.
--
-- Version 1.0.4
-- 18 Jan. 1999
-- 1. Add new enumeration m-ps800(3) to meritageBasePSUType - Yaron N.
--
-- Version 1.0.3
-- 16 Feb. 1998
-- 1. Syntax Error fixed - Alpha.
--
-- Version 1.0.2
-- 29 Sep. 1997
-- 1. Change enumeration notPresent to none
--
-- Version 1.0.1
-- 18 Aug. 1997
-- 1. Change enumeration of notExist to notPresent
-- 2. Change description of meritageBaseFaultMask
--
-- Version 1.0.0
-- 12 Aug. 1997
-- 1. Initial version
--
--======================================================
--
-- Overview :
--
-- The Meritage MIB defines manageable objects used by:
--      Cajun M770 (Meritage 1400)
--
-- The MIB defines manageable objects specific to the Cajun M770.
--
-- The MIB contains the following groups:
--
--  meritageBase	- This group contains basic device info
--			including chassis type, LEDs, Fans, PSUs etc.
--
--  meritageMSPV	- This group contains information about the Supervisor unit.
--
--  meritageGroup	- This group contains information about the modules.
--
--=========================================================

MERITAGE-MIB DEFINITIONS ::= BEGIN

	IMPORTS
               lannet
	FROM GEN-MIB
               DisplayString
	FROM RFC1213-MIB
               OBJECT-TYPE
	FROM RFC-1212;

-- useful types
        
-- MeritageLedColour ::= INTEGER
--	{
--	no-led		(0),    - there is no LED present
--	off		(1),    - LED off
--	green-on	(2),    - LED green
--	green-flashing	(3),    - LED green  flashing
--	red-on		(4),    - LED red
--	red-flashing	(5),    - LED red    flashing
--	yellow-on	(6),    - LED yellow
--	yellow-flashing	(7),    - LED yellow flashing
--	}

-- the MeritageMIB

-- The MERITAGE MIB forms part of the general Lannet MIB as follows:
-- LANNET-MIB { iso org(3) dod(6) internet(1) private(4) enterprises(1) 81 }

	meritage        OBJECT IDENTIFIER ::= { lannet 32 }

-- groups in the MeritageMIB

	meritageBase		OBJECT IDENTIFIER ::= { meritage 1 }
	meritageMSPV		OBJECT IDENTIFIER ::= { meritage 2 }
	meritageGroup		OBJECT IDENTIFIER ::= { meritage 3 }
	meritageClock		OBJECT IDENTIFIER ::= { meritage 4 }
	meritageClockSource	OBJECT IDENTIFIER ::= { meritage 5 }

-- the meritageBase group

meritageBaseLEDs OBJECT-TYPE
	SYNTAX OCTET STRING
	ACCESS read-only
	STATUS mandatory
	DESCRIPTION  
	"Summary of the hub LEDs. The coding of each LED is defined in 
	meritageLedColour 
	Number of bits per LED, currently 8 (1st byte)
	Number of LEDs, currently 8 (2nd byte)
	PS1 LED (3rd byte)
	PS2 LED
	PS3 LED
	Fan1 LED
	Fan2 LED
	MSPV1 LED
	MSPV2 LED
	Eth Sideband LED  (last byte)"
	::= { meritageBase 1 }

meritageBaseTemperatureExceed OBJECT-TYPE
	SYNTAX  INTEGER {
		ok (1),
		exceeded (2),
		notSupported (255)
		}
	ACCESS  read-only
	STATUS  mandatory
	DESCRIPTION
	"Fault condition indicating that the temperature exceeded
	 70 degrees in at least one of the modules in the hub."
	::= { meritageBase 2 }

meritageBaseXswitchConfiguration OBJECT-TYPE
	SYNTAX	INTEGER {
		connected (1),
		separated (2),
		notSupported (255)
		}
	ACCESS	read-only
	STATUS	mandatory
	DESCRIPTION
	"The value of this attribute shows whether the two horizontal
	Xswitches are connected internally to form a single 
	14-slots-wide Xswitch in the Meritage, or not."
	::= { meritageBase 3 }

meritageBaseFaultMask  OBJECT-TYPE  
	SYNTAX    OCTET STRING
	ACCESS      read-only
	STATUS     mandatory
	DESCRIPTION
	"Each bit of this item describes a fault situation in the Meritage hub.
	bit 1: meritageBaseFanActivityStatus.1 = failed (2),
	bit 2: meritageBaseFanActivityStatus.2 = failed (2),
	bit 3: meritageBasePSUActivityStatus.1 = failed(2),
	bit 4: meritageBasePSUActivityStatus.2 = failed(2),
	bit 5: meritageBasePSUActivityStatus.3 = failed(2),
	bit 6: meritageMSPVBackupStatus = failed(2),
	bit 7: scGenSwitchOldVersionModules.1 = null,
	bit 8: scGenSwitchOldVersionModules.2 = null,
	bit 9: scGenSwitchVIDPNonSupportedModules.1 = null,
	bit 10: scGenSwitchVIDPNonSupportedModules.2 = null,
	bit 11: scGenSwitchSTAonSupportedModules.1 = null,
	bit 12: scGenSwitchSTAonSupportedModules.2 = null,
	bit 13: scGenSwitchIDSonSupportedModules.1 = null,
	bit 14: scGenSwitchIDSonSupportedModules.2 = null,
	bit 15: The highest priority source port is not the curent
		source (according to meritageClockCurrentSource),
	bit 16: meritageClockStatus is Not in locked (1)  for more then
		120 seconds AND not all priorities are 0 AND
		meritageClockAdminStatus = enable (1),
	bit 17: meritageClockSourceStatus.1 = failed (2),
	bit 18: meritageClockSourceStatus.2 = failed (2),
	bit 19: meritageClockSourceStatus.3 = failed (2),
	bit 20: meritageClockSourceStatus.4 = failed (2),

	"
	::= { meritageBase 4 }


-- Fans

meritageBaseFanTable	OBJECT-TYPE
	SYNTAX	SEQUENCE OF MeritageBaseFanEntry
	ACCESS	not-accessible
	STATUS	mandatory
	DESCRIPTION
	"Table of attributes for Fan units in the Meritage."
	::= { meritageBase 5 }

meritageBaseFanEntry	OBJECT-TYPE
	SYNTAX	MeritageBaseFanEntry
	ACCESS	not-accessible
	STATUS	mandatory
	DESCRIPTION
	"An entry in the table, containing attributes for a single Fan unit
	in the Meritage."
	INDEX	{ meritageBaseFanId}
	::= { meritageBaseFanTable 1 }

MeritageBaseFanEntry	::=
	SEQUENCE	{
	meritageBaseFanId		INTEGER,
	meritageBaseFanActivityStatus	INTEGER
	}

meritageBaseFanId	OBJECT-TYPE
	SYNTAX	INTEGER  (1..2)
	ACCESS	read-only
	STATUS	mandatory
	DESCRIPTION
	"Fan index for identifying the Fan in the Meritage
	1-left, 2-right."
	::= { meritageBaseFanEntry 1 }

meritageBaseFanActivityStatus	OBJECT-TYPE
	SYNTAX	INTEGER  {
			active (1),
			failed (2),
			none (3)
			}
	ACCESS	read-only
	STATUS	mandatory
	DESCRIPTION
	"This attribute defines the status of the Fan."
	::= { meritageBaseFanEntry 2 }


-- Power Supply Units, PSU

meritageBasePSUTable OBJECT-TYPE
	SYNTAX  SEQUENCE OF MeritageBasePSUEntry
	ACCESS  not-accessible
	STATUS  mandatory
	DESCRIPTION
	"Table of configuration attributes for the Power Supply Units."
	::= { meritageBase 6 } 

meritageBasePSUEntry OBJECT-TYPE
	SYNTAX  MeritageBasePSUEntry
	ACCESS  not-accessible
	STATUS  mandatory
	DESCRIPTION
	"An entry in the table, containing information for a single
	Power Supply Unit." 
	INDEX  { meritageBasePSUId }
	::= { meritageBasePSUTable 1 }

MeritageBasePSUEntry  ::=
	SEQUENCE  {
	meritageBasePSUId			INTEGER,
	meritageBasePSUType			INTEGER,
	meritageBasePSUHWVersion		DisplayString,
	meritageBasePSURatedPower		INTEGER,
	meritageBasePSUActivityStatus		INTEGER
	}

meritageBasePSUId OBJECT-TYPE
	SYNTAX  INTEGER (1..255)
	ACCESS  read-only
	STATUS  mandatory
	DESCRIPTION
	"Index identifying the PSU.1-left, 2-middle, 3-right."
	::= { meritageBasePSUEntry 1 }

meritageBasePSUType	OBJECT-TYPE
	SYNTAX INTEGER {
		m-ps500 (1),
		m-ps1250 (2),
		m-ps800 (3),
		m-ps800-dc (4), 
		notSupported (255)
		}
	ACCESS read-only
	STATUS mandatory
	DESCRIPTION
	"This attribute indicates the PSU type."
	::= { meritageBasePSUEntry 2 }

meritageBasePSUHWVersion	OBJECT-TYPE
	SYNTAX  DisplayString (SIZE(3))
	ACCESS  read-only
	STATUS  mandatory
	DESCRIPTION
	"Hardware version of the PSU. Stored in ASCII format :
	first Byte - hardware major version number
	Second Byte - hardware minor version number (Configuration Symbol)
	last Byte  - hardware debug version number."
	::= { meritageBasePSUEntry 3 }

meritageBasePSURatedPower	OBJECT-TYPE
	SYNTAX	INTEGER
	ACCESS	read-only
	STATUS	mandatory
	DESCRIPTION
	"This attribute indicates the rated power of the PSU in Watts."
	::= { meritageBasePSUEntry 4 }

meritageBasePSUActivityStatus OBJECT-TYPE
	SYNTAX  INTEGER {
		active(1),
		failed(2),
		none(3)
		}
	ACCESS  read-only
	STATUS  mandatory
	DESCRIPTION
	"This attribute defines the status of the PSU:
	 active(1) - indicates that the PSU supplies power to the chassis.
	 failed(2) - indicates PSU failure
	 none(3) - indicates absence of PSU from the configuration."
	::= { meritageBasePSUEntry 5 }

meritageBaseUpBckplnConfiguration OBJECT-TYPE
	SYNTAX	INTEGER {
		singleDomain (1),
		dualDomain (2),
		notInstalled (3),
		notSupported (255)
		}
	ACCESS	read-only
	STATUS	mandatory
	DESCRIPTION
	"Defines whether the Upper Backplane is constructed
	as a single domain (full), as a dual domain (split) or not installed.
	The hardware supports 2 bits for this purpose (A10, B10 MSB).
	single - 10 in the MSB HW registers
	dual - 01 in the MSB HW registers
	notInstalled - 11 in the MSB HW registers"
	::= { meritageBase 7 }

meritageBaseUpBckplnConfigurationSymbol OBJECT-TYPE
	SYNTAX	DisplayString
	ACCESS	read-only
	STATUS	mandatory
	DESCRIPTION
	"Defines the Configuration Symbol of the Upper Backplane
	X.Y - where X & Y are integers:
		1st byte (X) - Major version number
		2nd byte - '.'
		3rd byte (Y) - minor version number
	The hardware supports 2 bits for this purpose (D10, E10 LSB).
	Y will always be 0.
	X will change according to the HW registers.
	00 is CS 1.0, 01 is 2.0, 10 is 3.0, 11 is 4.0.

	If no upper backplane is installed in the chassis, an empty string
	will be returned. "
	::= { meritageBase 8 }


-- the meritageMSPV Group

meritageMSPVBackupStatus	OBJECT-TYPE
	SYNTAX INTEGER {
		dormant (1),
		failed (2),
		none (3),
		notSupported (255)
		}
	ACCESS	read-only
	STATUS	mandatory
	DESCRIPTION
	"This attribute defines the status of the backup M-SPV module
	in the Meritage:
	dormant (1) - indicates that the backup M-SPV is dormant and works ok.
	failed (2) - indicates that the backup M-SPV has failed.
	none (3) - indicates absence of the backup M-SPV from the hub."
	::= { meritageMSPV 1 } 

meritageMSPVMainPosition	OBJECT-TYPE
	SYNTAX INTEGER {
		mMSPV1 (1),
		mMSPV2 (2),
		notSupported (255)
		}
	ACCESS	read-only
	STATUS	mandatory
	DESCRIPTION
	"This attribute defines the position of the main M-SPV module
	in the Meritage:
	MSPV1 (1) - indicates that the main M-SPV is the one on the left slot
	MSPV2 (2) - indicates that the main M-SPV is the one on the right slot."
	::= { meritageMSPV 2 } 


-- the meritageGroup Group

meritageGroupTable OBJECT-TYPE
	SYNTAX SEQUENCE OF  MeritageGroupEntry
	ACCESS not-accessible
	STATUS mandatory
	DESCRIPTION
	"A table containing information about each group in the hub."
	::= { meritageGroup 1 }

meritageGroupEntry OBJECT-TYPE
	SYNTAX MeritageGroupEntry
	ACCESS not-accessible
	STATUS mandatory
	DESCRIPTION
	"An entry containing information about a particular 
	group in the hub."
	INDEX { meritageGroupIndex }
	::= { meritageGroupTable 1 }

MeritageGroupEntry ::=
	SEQUENCE {
	meritageGroupIndex		INTEGER,
	meritageGroupTempExceed	INTEGER,
	meritageGroupLEDsMap	OCTET STRING
	}

meritageGroupIndex OBJECT-TYPE
	SYNTAX INTEGER
	ACCESS read-only
	STATUS mandatory
	DESCRIPTION
	"Index into this table, by group number."
	::= { meritageGroupEntry 1 }

meritageGroupTempExceed	OBJECT-TYPE
	SYNTAX INTEGER {
		ok (1),
		exceeded (2),
		notSupported (255)
		}
	ACCESS	read-only
	STATUS	mandatory
	DESCRIPTION
	"Fault condition indicating that temperature exceeded the threshold
	on the module."
	::= { meritageGroupEntry 2 }

meritageGroupLEDsMap OBJECT-TYPE  
	SYNTAX    OCTET STRING
	ACCESS     read-only
	STATUS     mandatory
	DESCRIPTION
	"The status of all the Group LEDs in the form of a BIT Map.
	The coding of each LED is defined in MeritageLedColour.
	
	The structure of this item:
	Number of bits per LED = A (currently 8 bits) (1st byte)
	Number of Module level LEDs = B (currently 2) (2nd byte)
	Number of Ports = C (currently 12) (3rd byte)
	Number of Functions = D (currently 6) (4th byte)
	
	Module level LEDs (=B bytes)
	Ports LEDs for function #1 (=C bytes)
	Ports LEDs for function #2 (=C bytes)
	Ports LEDs for function #3 (=C bytes)
	...
	Ports LEDs for function #D (=C bytes)

	The length of this item, with the current values, is 78 bytes."
	::= { meritageGroupEntry 3 }


-- the meritageClock Group

meritageClockAdminStatus	OBJECT-TYPE
	SYNTAX INTEGER {
		enable	(1),
		disable	(2)
		}
	ACCESS	read-write
	STATUS	mandatory
	DESCRIPTION
	"enable or disable the clock sync daughter board.
	When disabled, the M-SPS will use its own internal clock."
	::= { meritageClock 1 }



meritageClockReset	OBJECT-TYPE
	SYNTAX INTEGER  {
		on	(1),
		off	(2)
		}
	ACCESS	read-write
	STATUS	mandatory
	DESCRIPTION
	"Setting the value of this attribute to ON causes a reset only to the
	Clock Sync daughter board and not to the M-SPS."
	::= { meritageClock 2 }
meritageClockWTR	OBJECT-TYPE
	SYNTAX	INTEGER
	ACCESS	read-write
	STATUS	mandatory
	DESCRIPTION
	"The value in seconds of  Wait Time to Restore.
	The time the M-SPS software will wait before restoring a healthy higher
	priority timing source as the sync source.
	This is to prevent toggling between two sources if one source is 
	intermittently bad.
	If the WTR is set to infinity, a higher priority source will be active
	only if the current source fails or after reset.
	ranges 10-3600 seconds
	value = 9999 means infinity.
	default value - 20 sec. "
	::= { meritageClock 3 }

meritageClockStatus	OBJECT-TYPE
	
SYNTAX INTEGER {
		locked	(1),
		holdover (2),
		freeRunning (3),
		internal (4)
		}
	ACCESS	read-only
	STATUS	mandatory
	DESCRIPTION
	"The status of the Clock Sync daughter board:
	Locked - locked to the input timing source for more then 8 seconds.
	Holdover - Trying to simulate a clock it was previously locked to.
	FreeRunning - Outputting a timing source derived from none of the sources.
	Internal - Outputting the internal clock, because the clock sync is
		disabled."
	::= { meritageClock 4 }

meritageClockCurrentSource	OBJECT-TYPE
	SYNTAX	DisplayString
	ACCESS	read-only
	STATUS	mandatory
	DESCRIPTION
	"The current clock source being used. This is the outcome of the
	status of the sources and the priority between the sources.
	possible values are:
	ATM A, ATM B, SYNC A, SYNC B, none  (when there is no source,
	i.e. in Holdover, Free Running or Internal).

	A Trap will be sent on change. "
	::= { meritageClock 5 }


-- the meritageClockSource Group Table

meritageClockSourceTable OBJECT-TYPE
	SYNTAX SEQUENCE OF  MeritageClockSourceEntry
	ACCESS not-accessible
	STATUS mandatory
	DESCRIPTION
	"A table containing information about each clock source in the hub."
	::= { meritageClockSource 1 }

meritageClockSourceEntry OBJECT-TYPE
	SYNTAX MeritageClockSourceEntry
	ACCESS not-accessible
	STATUS mandatory
	DESCRIPTION
	"An entry containing information about a particular clock source
	in the hub."
	INDEX { meritageClockSourceIndex }
	::= { meritageClockSourceTable 1 }

MeritageClockSourceEntry ::=
	SEQUENCE {
	meritageClockSourceIndex	INTEGER,
	meritageClockSourceStatus	INTEGER,
	meritageClockSourcePriority	INTEGER,
	meritageClockSourceConfigPort	DisplayString,
	meritageClockSourceFraming	INTEGER 
	}

meritageClockSourceIndex OBJECT-TYPE
	SYNTAX INTEGER
	ACCESS read-only
	STATUS mandatory
	DESCRIPTION
	"Index into this table, by clock source number 1-4.
	1 - ATM A
	2 - ATM B
	3 - SYNC A
	4 - SYNC B "
	::= { meritageClockSourceEntry 1 }

meritageClockSourceStatus	OBJECT-TYPE
	SYNTAX INTEGER {
		ok (1),
		los (2),
		failed (3),
		notSupported (255)
		}
	ACCESS	read-only
	STATUS	mandatory
	DESCRIPTION
	"The status of the source port
	ok - link ok
	los - loss of signal.
	failed -  the source may have a link, but the M-SPS has failed 4 times
		to lock to it. The source will automatically be disabled
		(priority 0).
		The status can exit the failed status only if the user enables
		the source by raising it's priority."
	::= { meritageClockSourceEntry 2 }

meritageClockSourcePriority	OBJECT-TYPE
	SYNTAX	INTEGER (0..4)
	ACCESS	read-write
	STATUS	mandatory
	DESCRIPTION
	"The priority of the source port
	0 - disabled
	1 - lowest
	4 - highest "
	::= { meritageClockSourceEntry 3 }

meritageClockSourceConfigPort	OBJECT-TYPE
	SYNTAX	DisplayString
	ACCESS	read-write
	STATUS	mandatory
	DESCRIPTION
	"The port assigned to drive the Clock Source.
	In the format  X.Y - where X & Y are integers:
	1st byte (X) - Slot number
	2nd byte - (.)
	3rd byte (Y) - Port number	

	The NMS can write values to index 1 and 2 only. Attempt to write a value
	to index 3 and 4 will cause genError.

	The NMS can read the value to see that the set was successful.
		
	For index 1 - for example = 3.1
	For index 2 - for example = 3.2
	For index 3 - value always = 15.1
	For index 4 - value always = 15.2"
	::= { meritageClockSourceEntry 4 }

meritageClockSourceFraming	OBJECT-TYPE
	SYNTAX INTEGER {
		e1-framed  (1),
		e1-unframed (2),
		ds1-sf (3),
		ds1-esf (4),
		notSupported (255)
		}

	ACCESS	read-write
	STATUS	mandatory
	DESCRIPTION
	"The framing mode for the SYNC A SYNC B ports.
	Sources ATM A and ATM will reply with notSupported (255).
	For M-SPS/ER and EB, the values 1 and 2 are relevant.	
	For M-SPS/T, the values 3 and 4 are relevant.
	"
	::= { meritageClockSourceEntry 5 }

END
