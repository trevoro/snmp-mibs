--			Ascend mibdslthresh MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBDSLTHRESH-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibdslThreshProfile  OBJECT IDENTIFIER ::= { configuration 75}

	-- The mibdslThreshProfile table
	--
	-- This table contains parameters for the mibdslThreshProfile profile
	--

    mibdslThreshProfileTable	OBJECT-TYPE
	SYNTAX		SEQUENCE OF MibdslThreshProfileEntry
	ACCESS		not-accessible
	STATUS		mandatory
	DESCRIPTION	"A list of mibdslThreshProfile profile entries."
	::= { mibdslThreshProfile 1 }

    mibdslThreshProfileEntry	OBJECT-TYPE
	SYNTAX		MibdslThreshProfileEntry
	ACCESS		not-accessible
	STATUS		mandatory
	DESCRIPTION	"A mibdslThreshProfile entry containing objects that
			 maps to the parameters of mibdslThreshProfile profile."
	INDEX		{ dslThreshProfile-Name }
	::= { mibdslThreshProfileTable 1 }

    MibdslThreshProfileEntry ::=
	SEQUENCE {
	    dslThreshProfile-Name
		DisplayString,
	    dslThreshProfile-PhysicalAddress-Shelf
		INTEGER,
	    dslThreshProfile-PhysicalAddress-Slot
		INTEGER,
	    dslThreshProfile-PhysicalAddress-ItemNumber
		INTEGER,
	    dslThreshProfile-Enabled
		INTEGER,
	    dslThreshProfile-Atuc15minLofs
		INTEGER,
	    dslThreshProfile-Atuc15minLoss
		INTEGER,
	    dslThreshProfile-Atuc15minLols
		INTEGER,
	    dslThreshProfile-Atuc15minLprs
		INTEGER,
	    dslThreshProfile-Atuc15minEss
		INTEGER,
	    dslThreshProfile-AtucFastRateUp
		INTEGER,
	    dslThreshProfile-AtucInterleaveRateUp
		INTEGER,
	    dslThreshProfile-AtucFastRateDown
		INTEGER,
	    dslThreshProfile-AtucInterleaveRateDown
		INTEGER,
	    dslThreshProfile-AtucInitFailureTrap
		INTEGER,
	    dslThreshProfile-Atur15minLofs
		INTEGER,
	    dslThreshProfile-Atur15minLoss
		INTEGER,
	    dslThreshProfile-Atur15minLprs
		INTEGER,
	    dslThreshProfile-Atur15minEss
		INTEGER,
	    dslThreshProfile-AturFastRateUp
		INTEGER,
	    dslThreshProfile-AturInterleaveRateUp
		INTEGER,
	    dslThreshProfile-AturFastRateDown
		INTEGER,
	    dslThreshProfile-AturInterleaveRateDown
		INTEGER,
	    dslThreshProfile-Action-o
		INTEGER
	}

    dslThreshProfile-Name	OBJECT-TYPE
	SYNTAX	DisplayString
	ACCESS	read-only
	STATUS	mandatory
	DESCRIPTION	"The name consists of a null terminated ascii string supplied by the user."
	::= { mibdslThreshProfileEntry 1 }

    dslThreshProfile-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibdslThreshProfileEntry 2 }

    dslThreshProfile-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibdslThreshProfileEntry 3 }

    dslThreshProfile-PhysicalAddress-ItemNumber	OBJECT-TYPE
	SYNTAX	INTEGER
	ACCESS	read-write
	STATUS	mandatory
	DESCRIPTION	"A number that specifies an addressable entity within the context of shelf and slot."
	::= { mibdslThreshProfileEntry 4 }

    dslThreshProfile-Enabled	OBJECT-TYPE
	SYNTAX	INTEGER {
		    no (1),
		    yes (2)
		}
	ACCESS	read-write
	STATUS	mandatory
	DESCRIPTION	"TRUE if any trap of this line needs to be monitored."
	::= { mibdslThreshProfileEntry 5 }

    dslThreshProfile-Atuc15minLofs	OBJECT-TYPE
	SYNTAX	INTEGER
	ACCESS	read-write
	STATUS	mandatory
	DESCRIPTION	"The number of Loss of Frame Seconds encountered by a DSL interface within any given 15 min. performance data collection period, which causes the SNMP agent to send a trap. One trap will be sent per interval per interface. A value 0 disables the trap."
	::= { mibdslThreshProfileEntry 6 }

    dslThreshProfile-Atuc15minLoss	OBJECT-TYPE
	SYNTAX	INTEGER
	ACCESS	read-write
	STATUS	mandatory
	DESCRIPTION	"The number of Loss of Signal Seconds encountered by a DSL interface within any given 15 min. performance data collection period, which causes the SNMP agent to send a trap. One trap will be sent per interval per interface. A value 0 disables the trap."
	::= { mibdslThreshProfileEntry 7 }

    dslThreshProfile-Atuc15minLols	OBJECT-TYPE
	SYNTAX	INTEGER
	ACCESS	read-write
	STATUS	mandatory
	DESCRIPTION	"The number of Loss of Link Seconds encountered by a DSL interface within any given 15 min. performance data collection period, which causes the SNMP agent to send a trap. One trap will be sent per interval per interface. A value 0 disables the trap."
	::= { mibdslThreshProfileEntry 8 }

    dslThreshProfile-Atuc15minLprs	OBJECT-TYPE
	SYNTAX	INTEGER
	ACCESS	read-write
	STATUS	mandatory
	DESCRIPTION	"The number of Loss of Power Seconds encountered by a DSL interface within any given 15 min. performance data collection period, which causes the SNMP agent to send a trap. One trap will be sent per interval per interface. A value 0 disables the trap."
	::= { mibdslThreshProfileEntry 9 }

    dslThreshProfile-Atuc15minEss	OBJECT-TYPE
	SYNTAX	INTEGER
	ACCESS	read-write
	STATUS	mandatory
	DESCRIPTION	"The number of Errored Seconds encountered by a DSL interface within any given 15 min. performance data collection period, which causes the SNMP agent to send a trap. One trap will be sent per interval per interface. A value 0 disables the trap."
	::= { mibdslThreshProfileEntry 10 }

    dslThreshProfile-AtucFastRateUp	OBJECT-TYPE
	SYNTAX	INTEGER
	ACCESS	read-write
	STATUS	mandatory
	DESCRIPTION	"Applies to Fast channels only. Configured change in rate causing a trap to be sent. A trap is produced when ChanCurrTxRate >= ChanPrevTxRate plus the value of this object. A value 0 disables the trap."
	::= { mibdslThreshProfileEntry 11 }

    dslThreshProfile-AtucInterleaveRateUp	OBJECT-TYPE
	SYNTAX	INTEGER
	ACCESS	read-write
	STATUS	mandatory
	DESCRIPTION	"Applies to Interleave channels only. Configured change in rate causing a trap to be sent. A trap is produced when ChanCurrTxRate >= ChanPrevTxRate plus the value of this object. A value 0 disables the trap."
	::= { mibdslThreshProfileEntry 12 }

    dslThreshProfile-AtucFastRateDown	OBJECT-TYPE
	SYNTAX	INTEGER
	ACCESS	read-write
	STATUS	mandatory
	DESCRIPTION	"Applies to Fast channels only. Configured change in rate causing a trap to be sent. A trap is produced when ChanCurrTxRate <= ChanPrevTxRate minus the value of this object. A value 0 disables the trap."
	::= { mibdslThreshProfileEntry 13 }

    dslThreshProfile-AtucInterleaveRateDown	OBJECT-TYPE
	SYNTAX	INTEGER
	ACCESS	read-write
	STATUS	mandatory
	DESCRIPTION	"Applies to Interleave channels only. Configured change in rate causing a trap to be sent. A trap is produced when ChanCurrTxRate <= ChanPrevTxRate minus the value of this object. A value 0 disables the trap."
	::= { mibdslThreshProfileEntry 14 }

    dslThreshProfile-AtucInitFailureTrap	OBJECT-TYPE
	SYNTAX	INTEGER {
		    enable (2),
		    disable (3)
		}
	ACCESS	read-write
	STATUS	mandatory
	DESCRIPTION	"Enables and disables the InitFailureTrap."
	::= { mibdslThreshProfileEntry 15 }

    dslThreshProfile-Atur15minLofs	OBJECT-TYPE
	SYNTAX	INTEGER
	ACCESS	read-write
	STATUS	mandatory
	DESCRIPTION	"The number of Loss of Frame Seconds encountered by an ADSL interface within any given 15 minute performance data collection period, which causes the SNMP agent to send a adslAturPerfLofsThreshTrap trap. One trap will be sent per interval per interface. A value 0 disables the trap."
	::= { mibdslThreshProfileEntry 17 }

    dslThreshProfile-Atur15minLoss	OBJECT-TYPE
	SYNTAX	INTEGER
	ACCESS	read-write
	STATUS	mandatory
	DESCRIPTION	"The number of Loss of Signal Seconds encountered by an ADSL interface within any given 15 minute performance data collection period, which causes the SNMP agent to send a adslAturPerfLossThreshTrap trap. One trap will be sent per interval per interface. A value 0 disables the trap."
	::= { mibdslThreshProfileEntry 18 }

    dslThreshProfile-Atur15minLprs	OBJECT-TYPE
	SYNTAX	INTEGER
	ACCESS	read-write
	STATUS	mandatory
	DESCRIPTION	"The number of Loss of Power Seconds encountered by an ADSL interface within any given 15 minute performance data collection period, which causes the SNMP agent to send a adslAturPerfLprsThreshTrap trap. One trap will be sent per interval per interface. A value 0 disables the trap."
	::= { mibdslThreshProfileEntry 19 }

    dslThreshProfile-Atur15minEss	OBJECT-TYPE
	SYNTAX	INTEGER
	ACCESS	read-write
	STATUS	mandatory
	DESCRIPTION	"The number of Errored Seconds encountered by an ADSL interface within any given 15 minute performance data collection period, which causes the SNMP agent to send a trap adslAturPerfESsThreshTrap. One trap will be sent per interval per interface. A value 0 disables the trap."
	::= { mibdslThreshProfileEntry 20 }

    dslThreshProfile-AturFastRateUp	OBJECT-TYPE
	SYNTAX	INTEGER
	ACCESS	read-write
	STATUS	mandatory
	DESCRIPTION	"Applies to Fast channels only. Configured change in rate causing a adslAturRateChangeTrap trap to be sent. A trap is produced when ChanCurrTxRate >= ChanPrevTxRate plus the value of this object. A value 0 disables the trap."
	::= { mibdslThreshProfileEntry 21 }

    dslThreshProfile-AturInterleaveRateUp	OBJECT-TYPE
	SYNTAX	INTEGER
	ACCESS	read-write
	STATUS	mandatory
	DESCRIPTION	"Applies to Interleave channels only. Configured change in rate causing a adslAturRateChangeTrap trap to be sent. A trap is produced when ChanCurrTxRate >= ChanPrevTxRate plus the value of this object. A value 0 disables the trap."
	::= { mibdslThreshProfileEntry 22 }

    dslThreshProfile-AturFastRateDown	OBJECT-TYPE
	SYNTAX	INTEGER
	ACCESS	read-write
	STATUS	mandatory
	DESCRIPTION	"Applies to Fast channels only. Configured change in rate causing a adslAturRateChangeTrap trap to be sent. A trap is produced when ChanCurrTxRate <= ChanPrevTxRate minus the value of this object. A value 0 disables the trap."
	::= { mibdslThreshProfileEntry 23 }

    dslThreshProfile-AturInterleaveRateDown	OBJECT-TYPE
	SYNTAX	INTEGER
	ACCESS	read-write
	STATUS	mandatory
	DESCRIPTION	"Applies to Interleave channels only. Configured change in rate causing a adslAturRateChangeTrap trap to be sent. A trap is produced when ChanCurrTxRate <= ChanPrevTxRate minus the value of this object. A value 0 disables the trap."
	::= { mibdslThreshProfileEntry 24 }

    dslThreshProfile-Action-o	OBJECT-TYPE
	SYNTAX	INTEGER {
		    noAction (1),
		    createProfile (2),
		    deleteProfile (3)
		}
	ACCESS	read-write
	STATUS	mandatory
	DESCRIPTION	""
	::= { mibdslThreshProfileEntry 16 }

END
