-- ************************************************************************
-- ciscoWanVismMgcRedunCapabilities MIB
--
-- AGENT-CAPABILITIES mib for CISCO-WAN-MGC-REDUN-MIB in the VISM product
--
-- Copyright(c) 2001 by Cisco Systems,Inc.
--
-- Author: Malathi Anand
-- *****************************************************************
CISCO-WAN-VISM-MGC-REDUN-CAPABILITY DEFINITIONS ::= BEGIN

IMPORTS
        MODULE-IDENTITY,
        Integer32
                FROM SNMPv2-SMI
        AGENT-CAPABILITIES
                FROM SNMPv2-CONF
        ciscoWanAgentCapability
                FROM CISCOWAN-SMI;

ciscoWanVismMgcRedunCapability MODULE-IDENTITY
        LAST-UPDATED    "200108220000Z"
        ORGANIZATION    "Cisco Systems, Inc."
        CONTACT-INFO
                "       Cisco Systems
                        Customer Service

                Postal: 170 W Tasman Drive
                        San Jose, CA  95134
                        USA

                        Tel: +1 800 553-NETS

                E-mail: cs-vism@cisco.com"
        DESCRIPTION
                "The Agent Capabilities for CISCO-WAN-MGC-REDUN-MIB
                "

        REVISION        "                   "
        DESCRIPTION
                "Initial version of this MIB module"
        ::= { ciscoWanAgentCapability 338 }

ciscoWanVismMgcRedunCapV2R00 AGENT-CAPABILITIES
    PRODUCT-RELEASE      "VISM Release2.2"
    STATUS               current
    DESCRIPTION          "CISCO-WAN-VISM-MGC-REDUN-MIB capabilities"

    SUPPORTS CISCO-WAN-MGC-REDUN-MIB 
    INCLUDES { mgcRedundancyGroup,
               mgcRedundancyParamGroup }

    VARIATION   mgcRedundancyGrpEntry
    DESCRIPTION "An MGC cannot be part of more than one MGC
                 Redundancy Group"

    VARIATION   mgcRedundancyGrpNum
    SYNTAX      Integer32(1..8)
    DESCRIPTION "Supports range 1-8 only."

    VARIATION   mgcRedundancyGrpRowStatus
    SYNTAX INTEGER {
                   active(1),
                   createAndGo(4),
                   destroy(6)
                   }
    DESCRIPTION "only supports active, createAndGo and Destroy"
 
    VARIATION   mgcRedundancyGrpPref
    SYNTAX      Integer32(1..8)
    DESCRIPTION "Supports range 1-8 only."

    VARIATION   mgcRedundancyGrpPriority
    SYNTAX      Integer32(0..8)
    DESCRIPTION "Supports range 0-8 only."

    ::= { ciscoWanVismMgcRedunCapability 1 }

END
