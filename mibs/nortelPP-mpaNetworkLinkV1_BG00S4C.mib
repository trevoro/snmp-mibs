Nortel-Magellan-Passport-MpaNetworkLinkMIB
DEFINITIONS ::= BEGIN



IMPORTS

      OBJECT-TYPE
   FROM RFC-1212

      components,
      passportMIBs
   FROM Nortel-Magellan-Passport-UsefulDefinitionsMIB

      Counter32,
      RowPointer,
      DisplayString,
      StorageType,
      RowStatus,
      PassportCounter64,
      InterfaceIndex,
      Gauge32,
      Integer32,
      Unsigned32
   FROM Nortel-Magellan-Passport-StandardTextualConventionsMIB

      AsciiString,
      Hex,
      NonReplicated,
      HexString,
      EnterpriseDateAndTime,
      Link,
      DigitString,
      Unsigned64
   FROM Nortel-Magellan-Passport-TextualConventionsMIB;




-- LAST-UPDATED   "9902010000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     MpaNetworkLink Enterprise MIB."

mpaNetworkLinkMIB OBJECT IDENTIFIER ::= { passportMIBs 119 }










-- MpaNetworkLink/<n>
-- This component defines an instance of the MPA Network Link 
-- (MPANL) service. The component instance value n is a unique 
-- positive integer within a module.

mpanl OBJECT IDENTIFIER ::= { components 123 }



mpanlRowStatusTable OBJECT-TYPE
   SYNTAX     SEQUENCE OF MpanlRowStatusEntry
   ACCESS     not-accessible
   STATUS     mandatory
   DESCRIPTION
     "This entry controls the addition and deletion of 
      mpanl components."
::= { mpanl 1 }

mpanlRowStatusEntry OBJECT-TYPE
   SYNTAX     MpanlRowStatusEntry
   ACCESS     not-accessible
   STATUS     mandatory
   DESCRIPTION
     "A single entry in the table represents a single 
      mpanl component."
   INDEX {
      mpanlIndex }
::= { mpanlRowStatusTable 1 }

MpanlRowStatusEntry ::= SEQUENCE {
   mpanlRowStatus
      RowStatus,
   mpanlComponentName
      DisplayString,
   mpanlStorageType
      StorageType,
   mpanlIndex
      Integer32 }

mpanlRowStatus OBJECT-TYPE
   SYNTAX     RowStatus 
   ACCESS     read-write
   STATUS     mandatory
   DESCRIPTION
     "This variable is used as the basis for SNMP naming of
      mpanl components.
      These components can be added and deleted."
::= { mpanlRowStatusEntry 1 }

mpanlComponentName OBJECT-TYPE
   SYNTAX     DisplayString 
   ACCESS     read-only
   STATUS     mandatory
   DESCRIPTION
     "This variable provides the component's string name for
      use with the ASCII Console Interface"
::= { mpanlRowStatusEntry 2 }

mpanlStorageType OBJECT-TYPE
   SYNTAX     StorageType 
   ACCESS     read-only
   STATUS     mandatory
   DESCRIPTION
     "This variable represents the storage type value for the
      mpanl tables."
::= { mpanlRowStatusEntry 4 }

mpanlIndex OBJECT-TYPE
   SYNTAX     Integer32 (1..65535)
   ACCESS     not-accessible
   STATUS     mandatory
   DESCRIPTION
     "This variable represents the index for the mpanl tables."
::= { mpanlRowStatusEntry 10 }

mpanlCidDataTable OBJECT-TYPE
   SYNTAX     SEQUENCE OF MpanlCidDataEntry
   ACCESS     not-accessible
   STATUS     mandatory
   DESCRIPTION
     "This group contains the attribute for the MPANL component's 
      Customer Identifier (CID). Refer to the attribute description for a 
      detailed explanation of CIDs."
::= { mpanl 10 }

mpanlCidDataEntry OBJECT-TYPE
   SYNTAX     MpanlCidDataEntry
   ACCESS     not-accessible
   STATUS     mandatory
   DESCRIPTION
     "An entry in the mpanlCidDataTable."
   INDEX {
      mpanlIndex }
::= { mpanlCidDataTable 1 }

MpanlCidDataEntry ::= SEQUENCE {
   mpanlCustomerIdentifier
      Unsigned32 }

mpanlCustomerIdentifier OBJECT-TYPE
   SYNTAX     Unsigned32 (0 | 1..8191)
   ACCESS     read-only
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mpanlCidDataEntry 1 }

mpanlProvTable OBJECT-TYPE
   SYNTAX     SEQUENCE OF MpanlProvEntry
   ACCESS     not-accessible
   STATUS     mandatory
   DESCRIPTION
     "This group contains provisionable attributes of the MPANL service."
::= { mpanl 12 }

mpanlProvEntry OBJECT-TYPE
   SYNTAX     MpanlProvEntry
   ACCESS     not-accessible
   STATUS     mandatory
   DESCRIPTION
     "An entry in the mpanlProvTable."
   INDEX {
      mpanlIndex }
::= { mpanlProvTable 1 }

MpanlProvEntry ::= SEQUENCE {
   mpanlCommentText
      AsciiString }

mpanlCommentText OBJECT-TYPE
   SYNTAX     AsciiString (SIZE (0..40))
   ACCESS     read-write
   STATUS     mandatory
   DESCRIPTION
     "This attribute specifies the name the customer wishes to associate 
      with this MPANL interface."
::= { mpanlProvEntry 1 }

mpanlEmissionPriorityQsTable OBJECT-TYPE
   SYNTAX     SEQUENCE OF MpanlEmissionPriorityQsEntry
   ACCESS     not-accessible
   STATUS     mandatory
   DESCRIPTION
     "This group contains the provisionable attribute to specifie the 
      number of Frame Relay egress emission priority queues to be used 
      on that Frame Relay Interface"
::= { mpanl 13 }

mpanlEmissionPriorityQsEntry OBJECT-TYPE
   SYNTAX     MpanlEmissionPriorityQsEntry
   ACCESS     not-accessible
   STATUS     mandatory
   DESCRIPTION
     "An entry in the mpanlEmissionPriorityQsTable."
   INDEX {
      mpanlIndex }
::= { mpanlEmissionPriorityQsTable 1 }

MpanlEmissionPriorityQsEntry ::= SEQUENCE {
   mpanlNumberOfEmissionQs
      Unsigned32 }

mpanlNumberOfEmissionQs OBJECT-TYPE
   SYNTAX     Unsigned32 (2 | 4)
   ACCESS     read-only
   STATUS     mandatory
   DESCRIPTION
     "This attribute specifies the number of egress emission priority 
      queues that will be used for that Frame Relay interface. The 
      possible values of this attribute are 2 or 4:
      For V.35, V.11, HSSI, E1, DS1, E3, DS3 or 8pDS1 the possible 
      values are: 2 (in which case they are hardware queues), or 4 (in 
      which case they are software queues).
      For DS1C, E1C or DS3C the possible values are 2, 4 (in all cases 
      they are software queues)."
   DEFVAL     { 4 }
::= { mpanlEmissionPriorityQsEntry 1 }

mpanlStateTable OBJECT-TYPE
   SYNTAX     SEQUENCE OF MpanlStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mpanl 14 }

mpanlStateEntry OBJECT-TYPE
   SYNTAX     MpanlStateEntry
   ACCESS     not-accessible
   STATUS     mandatory
   DESCRIPTION
     "An entry in the mpanlStateTable."
   INDEX {
      mpanlIndex }
::= { mpanlStateTable 1 }

MpanlStateEntry ::= SEQUENCE {
   mpanlAdminState
      INTEGER,
   mpanlOperationalState
      INTEGER,
   mpanlUsageState
      INTEGER,
   mpanlAvailabilityStatus
      OCTET STRING,
   mpanlProceduralStatus
      OCTET STRING,
   mpanlControlStatus
      OCTET STRING,
   mpanlAlarmStatus
      OCTET STRING,
   mpanlStandbyStatus
      INTEGER,
   mpanlUnknownStatus
      INTEGER }

mpanlAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mpanlStateEntry 1 }

mpanlOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mpanlStateEntry 2 }

mpanlUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mpanlStateEntry 3 }

mpanlAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mpanlStateEntry 4 }

mpanlProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mpanlStateEntry 5 }

mpanlControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mpanlStateEntry 6 }

mpanlAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mpanlStateEntry 7 }

mpanlStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mpanlStateEntry 8 }

mpanlUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mpanlStateEntry 9 }

mpanlStatsTable OBJECT-TYPE
   SYNTAX     SEQUENCE OF MpanlStatsEntry
   ACCESS     not-accessible
   STATUS     mandatory
   DESCRIPTION
     "FrUni/n Statistics
      This group contains the statistics about the operational behavior of 
      the service at the interface level."
::= { mpanl 16 }

mpanlStatsEntry OBJECT-TYPE
   SYNTAX     MpanlStatsEntry
   ACCESS     not-accessible
   STATUS     mandatory
   DESCRIPTION
     "An entry in the mpanlStatsTable."
   INDEX {
      mpanlIndex }
::= { mpanlStatsTable 1 }

MpanlStatsEntry ::= SEQUENCE {
   mpanlLastUnknownDlci
      Unsigned32,
   mpanlUnknownDlciFramesFromIf
      Counter32,
   mpanlInvalidHeaderFramesFromIf
      Counter32 }

mpanlLastUnknownDlci OBJECT-TYPE
   SYNTAX     Unsigned32 (0..1023)
   ACCESS     read-only
   STATUS     mandatory
   DESCRIPTION
     "This attribute identifies the most recent DLCI which user frames 
      were received on for which a DLCI has not been provisioned on the 
      port."
   DEFVAL     { 0 }
::= { mpanlStatsEntry 1 }

mpanlUnknownDlciFramesFromIf OBJECT-TYPE
   SYNTAX     Counter32 
   ACCESS     read-only
   STATUS     mandatory
   DESCRIPTION
     "This attribute contains a count of the number of frames received 
      from the interface with an unknown DLCI (DLCI which is not 
      provisioned). When the maximum is reached the count wraps to 
      zero."
::= { mpanlStatsEntry 2 }

mpanlInvalidHeaderFramesFromIf OBJECT-TYPE
   SYNTAX     Counter32 
   ACCESS     read-only
   STATUS     mandatory
   DESCRIPTION
     "This attribute counts the number of frames received from the 
      interface with an invalid header format. When the maximum is 
      reached the count wraps to zero."
::= { mpanlStatsEntry 3 }

mpanlTrafficStatsTable OBJECT-TYPE
   SYNTAX     SEQUENCE OF MpanlTrafficStatsEntry
   ACCESS     not-accessible
   STATUS     mandatory
   DESCRIPTION
     "This operational group provides the traffic statistics of the service at 
      the interface level. Each attribute type is a non-negative integer 
      which monotonically increases until it reaches a maximum value, at 
      which point it wraps around and starts increasing again from zero."
::= { mpanl 17 }

mpanlTrafficStatsEntry OBJECT-TYPE
   SYNTAX     MpanlTrafficStatsEntry
   ACCESS     not-accessible
   STATUS     mandatory
   DESCRIPTION
     "An entry in the mpanlTrafficStatsTable."
   INDEX {
      mpanlIndex }
::= { mpanlTrafficStatsTable 1 }

MpanlTrafficStatsEntry ::= SEQUENCE {
   mpanlFrmToIf
      Unsigned32,
   mpanlOctetToIf
      Unsigned32,
   mpanlFrmFromIf
      Unsigned32,
   mpanlOctetFromIf
      Unsigned32 }

mpanlFrmToIf OBJECT-TYPE
   SYNTAX     Unsigned32 (0..4294967295)
   ACCESS     read-only
   STATUS     mandatory
   DESCRIPTION
     "This attribute counts frames transmitted to the interface. This count 
      may differ from its framer couterpart because Voice over Frame 
      Relay function may fragment and pack the Frame Relay frames 
      before transmission. When the maximum is reached the count 
      wraps to zero."
::= { mpanlTrafficStatsEntry 1 }

mpanlOctetToIf OBJECT-TYPE
   SYNTAX     Unsigned32 (0..4294967295)
   ACCESS     read-only
   STATUS     mandatory
   DESCRIPTION
     "This attribute counts octets transmitted to the interface. This count 
      may differ from its framer couterpart because Voice over Frame 
      Relay function may fragment and pack the Frame Relay frames 
      before transmission. When the maximum is reached the count 
      wraps to zero."
::= { mpanlTrafficStatsEntry 2 }

mpanlFrmFromIf OBJECT-TYPE
   SYNTAX     Unsigned32 (0..4294967295)
   ACCESS     read-only
   STATUS     mandatory
   DESCRIPTION
     "This attribute counts frames received from the interface. This count 
      may differ from its framer couterpart because Voice over Frame 
      Relay function may fragment and pack the Frame Relay frames 
      before transmission. When the maximum is reached the count 
      wraps to zero."
::= { mpanlTrafficStatsEntry 3 }

mpanlOctetFromIf OBJECT-TYPE
   SYNTAX     Unsigned32 (0..4294967295)
   ACCESS     read-only
   STATUS     mandatory
   DESCRIPTION
     "This attribute counts octets received from the interface. This count 
      may differ from its framer couterpart because Voice over Frame 
      Relay function may fragment and pack the Frame Relay frames 
      before transmission. When the maximum is reached the count 
      wraps to zero."
::= { mpanlTrafficStatsEntry 4 }

mpanlIfEntryTable OBJECT-TYPE
   SYNTAX     SEQUENCE OF MpanlIfEntryEntry
   ACCESS     not-accessible
   STATUS     mandatory
   DESCRIPTION
     "This group contains the provisionable attributes for the ifEntry."
::= { mpanl 23 }

mpanlIfEntryEntry OBJECT-TYPE
   SYNTAX     MpanlIfEntryEntry
   ACCESS     not-accessible
   STATUS     mandatory
   DESCRIPTION
     "An entry in the mpanlIfEntryTable."
   INDEX {
      mpanlIndex }
::= { mpanlIfEntryTable 1 }

MpanlIfEntryEntry ::= SEQUENCE {
   mpanlIfAdminStatus
      INTEGER,
   mpanlIfIndex
      InterfaceIndex }

mpanlIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mpanlIfEntryEntry 1 }

mpanlIfIndex OBJECT-TYPE
   SYNTAX     InterfaceIndex (1..65535)
   ACCESS     read-only
   STATUS     mandatory
   DESCRIPTION
     "This is the index for the IfEntry. Its value is automatically initialized 
      during the provisioning process."
::= { mpanlIfEntryEntry 2 }

mpanlOperStatusTable OBJECT-TYPE
   SYNTAX     SEQUENCE OF MpanlOperStatusEntry
   ACCESS     not-accessible
   STATUS     mandatory
   DESCRIPTION
     "This group includes the Operational Status attribute. This attribute 
      defines the current operational state of this component."
::= { mpanl 24 }

mpanlOperStatusEntry OBJECT-TYPE
   SYNTAX     MpanlOperStatusEntry
   ACCESS     not-accessible
   STATUS     mandatory
   DESCRIPTION
     "An entry in the mpanlOperStatusTable."
   INDEX {
      mpanlIndex }
::= { mpanlOperStatusTable 1 }

MpanlOperStatusEntry ::= SEQUENCE {
   mpanlSnmpOperStatus
      INTEGER }

mpanlSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mpanlOperStatusEntry 1 }

mpanlOperTable OBJECT-TYPE
   SYNTAX     SEQUENCE OF MpanlOperEntry
   ACCESS     not-accessible
   STATUS     mandatory
   DESCRIPTION
     "This group contains miscelleneous operational attributes of the 
      MPANL service."
::= { mpanl 25 }

mpanlOperEntry OBJECT-TYPE
   SYNTAX     MpanlOperEntry
   ACCESS     not-accessible
   STATUS     mandatory
   DESCRIPTION
     "An entry in the mpanlOperTable."
   INDEX {
      mpanlIndex }
::= { mpanlOperTable 1 }

MpanlOperEntry ::= SEQUENCE {
   mpanlRoundTripDelay
      Unsigned32 }

mpanlRoundTripDelay OBJECT-TYPE
   SYNTAX     Unsigned32 (0..10000)
   ACCESS     read-only
   STATUS     mandatory
   DESCRIPTION
     "This attribute indicates the round trip delay of the MPANL 
      interface. The round trip delay measurement is only made when this 
      attribute is displayed. The measured value is rounded up to the next 
      millisecond. 
      
      This attribute has the value 0, if the delay measurement cannot be 
      made."
::= { mpanlOperEntry 1 }

mpanlFrmToIfByQueueTable OBJECT-TYPE
   SYNTAX     SEQUENCE OF MpanlFrmToIfByQueueEntry
   ACCESS     not-accessible
   STATUS     mandatory
   DESCRIPTION
     "This attribute counts the total number of frames transmitted to the 
      interface per egress emission priority queue since the component 
      has been activated. There is potentially a maximum of 4 emission 
      priority queues. The number of available egress queues varies 
      according to the value of the provisionable attribute 
      numberOfEmissionQs. Egress queue 0 has the lowest priority, while 
      egress queue 3 has the highest priority."
::= { mpanl 350 }

mpanlFrmToIfByQueueEntry OBJECT-TYPE
   SYNTAX     MpanlFrmToIfByQueueEntry
   ACCESS     not-accessible
   STATUS     mandatory
   DESCRIPTION
     "An entry in the mpanlFrmToIfByQueueTable."
   INDEX {
      mpanlIndex,
      mpanlFrmToIfByQueueIndex }
::= { mpanlFrmToIfByQueueTable 1 }

MpanlFrmToIfByQueueEntry ::= SEQUENCE {
   mpanlFrmToIfByQueueIndex
      Integer32,
   mpanlFrmToIfByQueueValue
      Unsigned32 }

mpanlFrmToIfByQueueIndex OBJECT-TYPE
   SYNTAX     Integer32 (0..3)
   ACCESS     not-accessible
   STATUS     mandatory
   DESCRIPTION
     "This variable represents the index for the mpanlFrmToIfByQueueTable."
::= { mpanlFrmToIfByQueueEntry 1 }

mpanlFrmToIfByQueueValue OBJECT-TYPE
   SYNTAX     Unsigned32 (0..4294967295)
   ACCESS     read-only
   STATUS     mandatory
   DESCRIPTION
     "This variable represents an individual value for the
      mpanlFrmToIfByQueueTable."
::= { mpanlFrmToIfByQueueEntry 2 }

mpanlOctetToIfByQueueTable OBJECT-TYPE
   SYNTAX     SEQUENCE OF MpanlOctetToIfByQueueEntry
   ACCESS     not-accessible
   STATUS     mandatory
   DESCRIPTION
     "This attribute counts the total number of octets transmitted from the 
      service to the interface per emission priority queue since the 
      component has been activated. There is potentially a maximum of 4 
      emission priority queues. The number of available egress queues 
      varies according to the value of the provisionable attribute 
      numberOfEmissionQs. Egress queue 0 has the lowest priority, while 
      egress queue 3 has the highest priority."
::= { mpanl 351 }

mpanlOctetToIfByQueueEntry OBJECT-TYPE
   SYNTAX     MpanlOctetToIfByQueueEntry
   ACCESS     not-accessible
   STATUS     mandatory
   DESCRIPTION
     "An entry in the mpanlOctetToIfByQueueTable."
   INDEX {
      mpanlIndex,
      mpanlOctetToIfByQueueIndex }
::= { mpanlOctetToIfByQueueTable 1 }

MpanlOctetToIfByQueueEntry ::= SEQUENCE {
   mpanlOctetToIfByQueueIndex
      Integer32,
   mpanlOctetToIfByQueueValue
      Unsigned32 }

mpanlOctetToIfByQueueIndex OBJECT-TYPE
   SYNTAX     Integer32 (0..3)
   ACCESS     not-accessible
   STATUS     mandatory
   DESCRIPTION
     "This variable represents the index for the mpanlOctetToIfByQueueTable."
::= { mpanlOctetToIfByQueueEntry 1 }

mpanlOctetToIfByQueueValue OBJECT-TYPE
   SYNTAX     Unsigned32 (0..4294967295)
   ACCESS     read-only
   STATUS     mandatory
   DESCRIPTION
     "This variable represents an individual value for the
      mpanlOctetToIfByQueueTable."
::= { mpanlOctetToIfByQueueEntry 2 }


-- Mpanl/<n> DataNetworkAddress
-- This component contains the attributes necessary for creating a 
-- virtual circuit. These attributes indicate the default call setup 
-- capabilities for the interface.

mpanlDna OBJECT IDENTIFIER ::= { mpanl 2 }



mpanlDnaRowStatusTable OBJECT-TYPE
   SYNTAX     SEQUENCE OF MpanlDnaRowStatusEntry
   ACCESS     not-accessible
   STATUS     mandatory
   DESCRIPTION
     "This entry controls the addition and deletion of 
      mpanlDna components."
::= { mpanlDna 1 }

mpanlDnaRowStatusEntry OBJECT-TYPE
   SYNTAX     MpanlDnaRowStatusEntry
   ACCESS     not-accessible
   STATUS     mandatory
   DESCRIPTION
     "A single entry in the table represents a single 
      mpanlDna component."
   INDEX {
      mpanlIndex,
      mpanlDnaIndex }
::= { mpanlDnaRowStatusTable 1 }

MpanlDnaRowStatusEntry ::= SEQUENCE {
   mpanlDnaRowStatus
      RowStatus,
   mpanlDnaComponentName
      DisplayString,
   mpanlDnaStorageType
      StorageType,
   mpanlDnaIndex
      NonReplicated }

mpanlDnaRowStatus OBJECT-TYPE
   SYNTAX     RowStatus 
   ACCESS     read-only
   STATUS     mandatory
   DESCRIPTION
     "This variable is used as the basis for SNMP naming of
      mpanlDna components.
      These components cannot be added nor deleted."
::= { mpanlDnaRowStatusEntry 1 }

mpanlDnaComponentName OBJECT-TYPE
   SYNTAX     DisplayString 
   ACCESS     read-only
   STATUS     mandatory
   DESCRIPTION
     "This variable provides the component's string name for
      use with the ASCII Console Interface"
::= { mpanlDnaRowStatusEntry 2 }

mpanlDnaStorageType OBJECT-TYPE
   SYNTAX     StorageType 
   ACCESS     read-only
   STATUS     mandatory
   DESCRIPTION
     "This variable represents the storage type value for the
      mpanlDna tables."
::= { mpanlDnaRowStatusEntry 4 }

mpanlDnaIndex OBJECT-TYPE
   SYNTAX     NonReplicated 
   ACCESS     not-accessible
   STATUS     mandatory
   DESCRIPTION
     "This variable represents the index for the mpanlDna tables."
::= { mpanlDnaRowStatusEntry 10 }

mpanlDnaOutgoingOptionsTable OBJECT-TYPE
   SYNTAX     SEQUENCE OF MpanlDnaOutgoingOptionsEntry
   ACCESS     not-accessible
   STATUS     mandatory
   DESCRIPTION
     "DnaOutOptionsProv group defines call options of a Dna for calls 
      which are made out of the interface represented by Dna. All these 
      options are not used for calls arriving to the interface represented by 
      Dna."
::= { mpanlDna 11 }

mpanlDnaOutgoingOptionsEntry OBJECT-TYPE
   SYNTAX     MpanlDnaOutgoingOptionsEntry
   ACCESS     not-accessible
   STATUS     mandatory
   DESCRIPTION
     "An entry in the mpanlDnaOutgoingOptionsTable."
   INDEX {
      mpanlIndex,
      mpanlDnaIndex }
::= { mpanlDnaOutgoingOptionsTable 1 }

MpanlDnaOutgoingOptionsEntry ::= SEQUENCE {
   mpanlDnaDefaultTransferPriority
      INTEGER }

mpanlDnaDefaultTransferPriority OBJECT-TYPE
   SYNTAX     INTEGER  {
                 n0(0),
                 n1(1),
                 n2(2),
                 n3(3),
                 n4(4),
                 n5(5),
                 n6(6),
                 n7(7),
                 n8(8),
                 n9(9),
                 n10(10),
                 n11(11),
                 n12(12),
                 n13(13),
                 n14(14),
                 n15(15) }
   ACCESS     read-write
   STATUS     mandatory
   DESCRIPTION
     "This attribute specifies the default transfer priority to network for all 
      outgoing calls using this particular Dna.
      
      The transfer priority is a preference configured for an application 
      according to its delay-sensitivity requirement. Frames with higher 
      transfer priority are served by the network before the frames with 
      lower priority. The transfer priority standard is defined to have 16 
      levels from 0 to 15.
      
      Each transfer priority n, where n indicates the transfer priority 
      index, contains a default setting for routing class of service 
      (multimedia, delay or throughput) and frame relay egress queue 
      (depending on the number of supported egress queues on the remote 
      end interface) specified by the routingClassOfService and 
      emissionPriority attributes provisioned in the Mod Frs DprsNet 
      Tpm/n component. The default mapping can be altered by a user if 
      required.
      
      The default defaultTransferPriority is 0."
   DEFVAL     { n0 }
::= { mpanlDnaOutgoingOptionsEntry 18 }

mpanlDnaCallOptionsTable OBJECT-TYPE
   SYNTAX     SEQUENCE OF MpanlDnaCallOptionsEntry
   ACCESS     not-accessible
   STATUS     mandatory
   DESCRIPTION
     "DnaCallOptions group defines additional options for calls not 
      related directly to direction of a call."
::= { mpanlDna 13 }

mpanlDnaCallOptionsEntry OBJECT-TYPE
   SYNTAX     MpanlDnaCallOptionsEntry
   ACCESS     not-accessible
   STATUS     mandatory
   DESCRIPTION
     "An entry in the mpanlDnaCallOptionsTable."
   INDEX {
      mpanlIndex,
      mpanlDnaIndex }
::= { mpanlDnaCallOptionsTable 1 }

MpanlDnaCallOptionsEntry ::= SEQUENCE {
   mpanlDnaAccountClass
      Unsigned32,
   mpanlDnaAccountCollection
      OCTET STRING,
   mpanlDnaServiceExchange
      Unsigned32,
   mpanlDnaEgressAccounting
      INTEGER }

mpanlDnaAccountClass OBJECT-TYPE
   SYNTAX     Unsigned32 (0..255)
   ACCESS     read-write
   STATUS     mandatory
   DESCRIPTION
     "This attribute specifies the accounting class which is reserved for 
      network operations usage. Its value is returned in the accounting 
      record in the local and remote service type attributes. Use of this 
      attribute is decided by network operator.
      This attribute is returned by the local VC in the accounting record 
      for all calls setup using this particular DNA."
   DEFVAL     { 0 }
::= { mpanlDnaCallOptionsEntry 10 }

mpanlDnaAccountCollection OBJECT-TYPE
   SYNTAX     OCTET STRING (SIZE (1))
   ACCESS     read-write
   STATUS     mandatory
   DESCRIPTION
     "This set attribute indicates that accounting records are to be 
      collected by the network for the various reasons: billing, test, study, 
      auditing.  The last of the parameters, force, indicates that 
      accounting records are to be collected irrespective of other 
      collection reasons.  The force option is available for X.75 Gateways 
      only. If none of these reasons are set, then accounting will be 
      suppressed.
      To set a specific accounting collection reason, the reason is entered 
      and the corresponding bit in the structure is set to a value of 1. To 
      turn off a specific accounting collection reason, the reason is 
      entered preceeded with the '^' character, and the corresponding bit 
      in the structure is set to a value of 0.
      The bit placement for the accounting collection reasons is as 
      follows:
      Bit 0  - Bill
      Bit 1  - Test
      Bit 2  - Study
      Bit 3  - Audit
      Bit 4  - Force

      Description of bits:
      bill(0)
      test(1)
      study(2)
      audit(3)
      force(4)"
   DEFVAL     { '80'H }
::= { mpanlDnaCallOptionsEntry 11 }

mpanlDnaServiceExchange OBJECT-TYPE
   SYNTAX     Unsigned32 (0..255)
   ACCESS     read-write
   STATUS     mandatory
   DESCRIPTION
     "This attribute is an arbitrary number, Data Service Exchange, as 
      entered by the network operator and reported in accounting record. 
      It is converted into an internal 8-bit integer value for use in the 
      accounting record as well as in various X.25 and X.75 Tariff 
      utilities."
   DEFVAL     { 0 }
::= { mpanlDnaCallOptionsEntry 12 }

mpanlDnaEgressAccounting OBJECT-TYPE
   SYNTAX     INTEGER  {
                 no(0),
                 yes(1) }
   ACCESS     read-write
   STATUS     mandatory
   DESCRIPTION
     "This attribute specifies if Egress accounting is enabled by the 
      MPANL service. Disabling of Egress accounting means that only 
      segment counts are collected by VC and there are no frame relay 
      counts in accounting records for the MPANL service. Enabling of 
      Egress accounting means that the accounting records for MPANL 
      contain frame relay specific counts."
   DEFVAL     { no }
::= { mpanlDnaCallOptionsEntry 13 }


-- 
-- Mpanl/<n> Framer
-- The Framer component controls link layer framing for application 
-- components sending and receiving data on a link interface. It is also 
-- through Framer, that an application component is associated with a 
-- specific hardware link interface.
-- 
-- The Framer component provides provisionable attributes related to 
-- datapath aspects of the hardware interface (such as crc and frame 
-- length) rather than interface specific attributes (such as modem 
-- leads and clocking) which are associated with specific hardware 
-- components (such as V35/n or DS1/n). The Framer component also 
-- provides a provisionable attribute which binds the application 
-- component to a specific hardware component.
-- 
-- The Framer component contains operational attributes for link 
-- interface datapath statistics (such as frame counts and aborts).
-- 

mpanlFramer OBJECT IDENTIFIER ::= { mpanl 3 }



mpanlFramerRowStatusTable OBJECT-TYPE
   SYNTAX     SEQUENCE OF MpanlFramerRowStatusEntry
   ACCESS     not-accessible
   STATUS     mandatory
   DESCRIPTION
     "This entry controls the addition and deletion of 
      mpanlFramer components."
::= { mpanlFramer 1 }

mpanlFramerRowStatusEntry OBJECT-TYPE
   SYNTAX     MpanlFramerRowStatusEntry
   ACCESS     not-accessible
   STATUS     mandatory
   DESCRIPTION
     "A single entry in the table represents a single 
      mpanlFramer component."
   INDEX {
      mpanlIndex,
      mpanlFramerIndex }
::= { mpanlFramerRowStatusTable 1 }

MpanlFramerRowStatusEntry ::= SEQUENCE {
   mpanlFramerRowStatus
      RowStatus,
   mpanlFramerComponentName
      DisplayString,
   mpanlFramerStorageType
      StorageType,
   mpanlFramerIndex
      NonReplicated }

mpanlFramerRowStatus OBJECT-TYPE
   SYNTAX     RowStatus 
   ACCESS     read-write
   STATUS     mandatory
   DESCRIPTION
     "This variable is used as the basis for SNMP naming of
      mpanlFramer components.
      These components can be added and deleted."
::= { mpanlFramerRowStatusEntry 1 }

mpanlFramerComponentName OBJECT-TYPE
   SYNTAX     DisplayString 
   ACCESS     read-only
   STATUS     mandatory
   DESCRIPTION
     "This variable provides the component's string name for
      use with the ASCII Console Interface"
::= { mpanlFramerRowStatusEntry 2 }

mpanlFramerStorageType OBJECT-TYPE
   SYNTAX     StorageType 
   ACCESS     read-only
   STATUS     mandatory
   DESCRIPTION
     "This variable represents the storage type value for the
      mpanlFramer tables."
::= { mpanlFramerRowStatusEntry 4 }

mpanlFramerIndex OBJECT-TYPE
   SYNTAX     NonReplicated 
   ACCESS     not-accessible
   STATUS     mandatory
   DESCRIPTION
     "This variable represents the index for the mpanlFramer tables."
::= { mpanlFramerRowStatusEntry 10 }

mpanlFramerProvTable OBJECT-TYPE
   SYNTAX     SEQUENCE OF MpanlFramerProvEntry
   ACCESS     not-accessible
   STATUS     mandatory
   DESCRIPTION
     "This group contains the base provisioning data for the Framer 
      component. Application or hardware interface specific provisioning 
      data is contained in other provisionable Framer groups."
::= { mpanlFramer 10 }

mpanlFramerProvEntry OBJECT-TYPE
   SYNTAX     MpanlFramerProvEntry
   ACCESS     not-accessible
   STATUS     mandatory
   DESCRIPTION
     "An entry in the mpanlFramerProvTable."
   INDEX {
      mpanlIndex,
      mpanlFramerIndex }
::= { mpanlFramerProvTable 1 }

MpanlFramerProvEntry ::= SEQUENCE {
   mpanlFramerInterfaceName
      Link }

mpanlFramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { mpanlFramerProvEntry 1 }

mpanlFramerLinkTable OBJECT-TYPE
   SYNTAX     SEQUENCE OF MpanlFramerLinkEntry
   ACCESS     not-accessible
   STATUS     mandatory
   DESCRIPTION
     "This group contains attributes defining the framing of data on the 
      link interface."
::= { mpanlFramer 11 }

mpanlFramerLinkEntry OBJECT-TYPE
   SYNTAX     MpanlFramerLinkEntry
   ACCESS     not-accessible
   STATUS     mandatory
   DESCRIPTION
     "An entry in the mpanlFramerLinkTable."
   INDEX {
      mpanlIndex,
      mpanlFramerIndex }
::= { mpanlFramerLinkTable 1 }

MpanlFramerLinkEntry ::= SEQUENCE {
   mpanlFramerFlagsBetweenFrames
      Unsigned32 }

mpanlFramerFlagsBetweenFrames OBJECT-TYPE
   SYNTAX     Unsigned32 (1..16)
   ACCESS     read-write
   STATUS     mandatory
   DESCRIPTION
     "This attribute defines the number of flags that are inserted between 
      frames sent to the link interface."
   DEFVAL     { 1 }
::= { mpanlFramerLinkEntry 4 }

mpanlFramerStateTable OBJECT-TYPE
   SYNTAX     SEQUENCE OF MpanlFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mpanlFramer 12 }

mpanlFramerStateEntry OBJECT-TYPE
   SYNTAX     MpanlFramerStateEntry
   ACCESS     not-accessible
   STATUS     mandatory
   DESCRIPTION
     "An entry in the mpanlFramerStateTable."
   INDEX {
      mpanlIndex,
      mpanlFramerIndex }
::= { mpanlFramerStateTable 1 }

MpanlFramerStateEntry ::= SEQUENCE {
   mpanlFramerAdminState
      INTEGER,
   mpanlFramerOperationalState
      INTEGER,
   mpanlFramerUsageState
      INTEGER }

mpanlFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mpanlFramerStateEntry 1 }

mpanlFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mpanlFramerStateEntry 2 }

mpanlFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mpanlFramerStateEntry 3 }

mpanlFramerStatsTable OBJECT-TYPE
   SYNTAX     SEQUENCE OF MpanlFramerStatsEntry
   ACCESS     not-accessible
   STATUS     mandatory
   DESCRIPTION
     "This group contains the operational statistics data for a Framer 
      component."
::= { mpanlFramer 13 }

mpanlFramerStatsEntry OBJECT-TYPE
   SYNTAX     MpanlFramerStatsEntry
   ACCESS     not-accessible
   STATUS     mandatory
   DESCRIPTION
     "An entry in the mpanlFramerStatsTable."
   INDEX {
      mpanlIndex,
      mpanlFramerIndex }
::= { mpanlFramerStatsTable 1 }

MpanlFramerStatsEntry ::= SEQUENCE {
   mpanlFramerFrmToIf
      Counter32,
   mpanlFramerFrmFromIf
      Counter32,
   mpanlFramerOctetFromIf
      Counter32,
   mpanlFramerAborts
      Counter32,
   mpanlFramerCrcErrors
      Counter32,
   mpanlFramerLrcErrors
      Counter32,
   mpanlFramerNonOctetErrors
      Counter32,
   mpanlFramerOverruns
      Counter32,
   mpanlFramerUnderruns
      Counter32,
   mpanlFramerLargeFrmErrors
      Counter32,
   mpanlFramerFrmModeErrors
      Counter32 }

mpanlFramerFrmToIf OBJECT-TYPE
   SYNTAX     Counter32 
   ACCESS     read-only
   STATUS     mandatory
   DESCRIPTION
     "The number of frames transmitted to the link interface by Framer.
      
      Note: This does not include the number of frames transmitted 
      directly to the hardware queue, thus bypassing the Framer 
      component."
::= { mpanlFramerStatsEntry 1 }

mpanlFramerFrmFromIf OBJECT-TYPE
   SYNTAX     Counter32 
   ACCESS     read-only
   STATUS     mandatory
   DESCRIPTION
     "The number of frames received from the link interface by Framer."
::= { mpanlFramerStatsEntry 2 }

mpanlFramerOctetFromIf OBJECT-TYPE
   SYNTAX     Counter32 
   ACCESS     read-only
   STATUS     mandatory
   DESCRIPTION
     "The number of bytes received from the link interface by Framer."
::= { mpanlFramerStatsEntry 3 }

mpanlFramerAborts OBJECT-TYPE
   SYNTAX     Counter32 
   ACCESS     read-only
   STATUS     mandatory
   DESCRIPTION
     "This attribute is the total number of aborts received."
::= { mpanlFramerStatsEntry 4 }

mpanlFramerCrcErrors OBJECT-TYPE
   SYNTAX     Counter32 
   ACCESS     read-only
   STATUS     mandatory
   DESCRIPTION
     "This attribute is the total number of frames with CRC errors, 
      occurring in the receive direction from the link."
::= { mpanlFramerStatsEntry 5 }

mpanlFramerLrcErrors OBJECT-TYPE
   SYNTAX     Counter32 
   ACCESS     read-only
   STATUS     mandatory
   DESCRIPTION
     "This attribute is the total number of frames with LRC errors, 
      occurring in the Tx link prior to transmission onto the link."
::= { mpanlFramerStatsEntry 6 }

mpanlFramerNonOctetErrors OBJECT-TYPE
   SYNTAX     Counter32 
   ACCESS     read-only
   STATUS     mandatory
   DESCRIPTION
     "This attribute is the total number of frames that were non octet 
      aligned."
::= { mpanlFramerStatsEntry 7 }

mpanlFramerOverruns OBJECT-TYPE
   SYNTAX     Counter32 
   ACCESS     read-only
   STATUS     mandatory
   DESCRIPTION
     "This attribute is the total number of frames received from the link 
      for which overruns occurred."
::= { mpanlFramerStatsEntry 8 }

mpanlFramerUnderruns OBJECT-TYPE
   SYNTAX     Counter32 
   ACCESS     read-only
   STATUS     mandatory
   DESCRIPTION
     "This attribute is the total number of frames transmitted to the link 
      for which underruns occurred."
::= { mpanlFramerStatsEntry 9 }

mpanlFramerLargeFrmErrors OBJECT-TYPE
   SYNTAX     Counter32 
   ACCESS     read-only
   STATUS     mandatory
   DESCRIPTION
     "This attribute is the total number of frames received which were too 
      large. The frame execeeded the maximumFrameLengthLimit 
      provisioned attribute or it contained more than the 255 block 
      hardware limit."
::= { mpanlFramerStatsEntry 10 }

mpanlFramerFrmModeErrors OBJECT-TYPE
   SYNTAX     Counter32 
   ACCESS     read-only
   STATUS     mandatory
   DESCRIPTION
     "This attribute is the total number of frames detected with framing 
      mode errors. A framingModeError is flagged when frames are 
      inconsistent with the specified framingType, that is when 
      interrupting frames are used while running in hdlc mode."
::= { mpanlFramerStatsEntry 11 }

mpanlFramerUtilTable OBJECT-TYPE
   SYNTAX     SEQUENCE OF MpanlFramerUtilEntry
   ACCESS     not-accessible
   STATUS     mandatory
   DESCRIPTION
     "This group contains the link utilizaiton operational data for a 
      Framer component."
::= { mpanlFramer 14 }

mpanlFramerUtilEntry OBJECT-TYPE
   SYNTAX     MpanlFramerUtilEntry
   ACCESS     not-accessible
   STATUS     mandatory
   DESCRIPTION
     "An entry in the mpanlFramerUtilTable."
   INDEX {
      mpanlIndex,
      mpanlFramerIndex }
::= { mpanlFramerUtilTable 1 }

MpanlFramerUtilEntry ::= SEQUENCE {
   mpanlFramerNormPrioLinkUtilToIf
      Gauge32,
   mpanlFramerNormPrioLinkUtilFromIf
      Gauge32 }

mpanlFramerNormPrioLinkUtilToIf OBJECT-TYPE
   SYNTAX     Gauge32 (0..100)
   ACCESS     read-only
   STATUS     mandatory
   DESCRIPTION
     "This attribute is the utilization of the normal and high priority data 
      traffic (interruptable traffic) sent to the link as a percentage of the 
      available bandwidth on the link. Note that this includes traffic with 
      Transfer Priorities (TP) of 0, 6 and 9 and/or Emission Priority of 2 
      and 3. The utilization is the average for the last minute."
   DEFVAL     { 0 }
::= { mpanlFramerUtilEntry 1 }

mpanlFramerNormPrioLinkUtilFromIf OBJECT-TYPE
   SYNTAX     Gauge32 (0..100)
   ACCESS     read-only
   STATUS     mandatory
   DESCRIPTION
     "This attribute is the utilization of the normal and high priority data 
      traffic (interruptable traffic) received from the link as a percentage 
      of the available bandwidth on the link. Note that this includes traffic 
      with Transfer Priorities (TP) of 0, 6 and 9 and/or Emission Priority 
      of 2 and 3. The utilization is the average for the last minute."
   DEFVAL     { 0 }
::= { mpanlFramerUtilEntry 3 }

-- 
-- *** THIS SUBTREE CURRENTLY NOT IMPLEMENTED ***
-- 

-- Mpanl/<n> PrefixDataNetworkAddress/<npi>,<dna>
-- This component identifies a prefixDNA provided by the MPA DTE 
-- via the the MPANL protocol. It has no attributes because all of the 
-- relevant information is contained in the indices of this component. 
-- The first index is the numbering plan indicator (x121/e164) and the 
-- second index is the prefixDNA digits. 

mpanlPrefixDna OBJECT IDENTIFIER ::= { mpanl 4 }



mpanlPrefixDnaRowStatusTable OBJECT-TYPE
   SYNTAX     SEQUENCE OF MpanlPrefixDnaRowStatusEntry
   ACCESS     not-accessible
   STATUS     mandatory
   DESCRIPTION
     "*** THIS TABLE CURRENTLY NOT IMPLEMENTED ***

      This entry controls the addition and deletion of 
      mpanlPrefixDna components."
::= { mpanlPrefixDna 1 }

mpanlPrefixDnaRowStatusEntry OBJECT-TYPE
   SYNTAX     MpanlPrefixDnaRowStatusEntry
   ACCESS     not-accessible
   STATUS     mandatory
   DESCRIPTION
     "A single entry in the table represents a single 
      mpanlPrefixDna component."
   INDEX {
      mpanlIndex,
      mpanlPrefixDnaNumberingPlanIndicatorIndex,
      mpanlPrefixDnaDataNetworkAddressIndex }
::= { mpanlPrefixDnaRowStatusTable 1 }

MpanlPrefixDnaRowStatusEntry ::= SEQUENCE {
   mpanlPrefixDnaRowStatus
      RowStatus,
   mpanlPrefixDnaComponentName
      DisplayString,
   mpanlPrefixDnaStorageType
      StorageType,
   mpanlPrefixDnaNumberingPlanIndicatorIndex
      INTEGER,
   mpanlPrefixDnaDataNetworkAddressIndex
      DigitString }

mpanlPrefixDnaRowStatus OBJECT-TYPE
   SYNTAX     RowStatus 
   ACCESS     read-only
   STATUS     mandatory
   DESCRIPTION
     "This variable is used as the basis for SNMP naming of
      mpanlPrefixDna components.
      These components cannot be added nor deleted."
::= { mpanlPrefixDnaRowStatusEntry 1 }

mpanlPrefixDnaComponentName OBJECT-TYPE
   SYNTAX     DisplayString 
   ACCESS     read-only
   STATUS     mandatory
   DESCRIPTION
     "This variable provides the component's string name for
      use with the ASCII Console Interface"
::= { mpanlPrefixDnaRowStatusEntry 2 }

mpanlPrefixDnaStorageType OBJECT-TYPE
   SYNTAX     StorageType 
   ACCESS     read-only
   STATUS     mandatory
   DESCRIPTION
     "This variable represents the storage type value for the
      mpanlPrefixDna tables."
::= { mpanlPrefixDnaRowStatusEntry 4 }

mpanlPrefixDnaNumberingPlanIndicatorIndex OBJECT-TYPE
   SYNTAX     INTEGER  {
                 x121(0),
                 e164(1) }
   ACCESS     not-accessible
   STATUS     mandatory
   DESCRIPTION
     "This variable represents an index for the mpanlPrefixDna tables."
::= { mpanlPrefixDnaRowStatusEntry 10 }

mpanlPrefixDnaDataNetworkAddressIndex OBJECT-TYPE
   SYNTAX     DigitString (SIZE (1..15))
   ACCESS     not-accessible
   STATUS     mandatory
   DESCRIPTION
     "This variable represents an index for the mpanlPrefixDna tables."
::= { mpanlPrefixDnaRowStatusEntry 11 }

-- 
-- *** THIS SUBTREE CURRENTLY NOT IMPLEMENTED ***
-- 

-- Mpanl/n DataLinkConnectionIdentifier/n
-- This component is responsible for the Frame Relay U-plane (User-
-- plane) protocol for the specified instance. There can be many 
-- instances of Dlci for each Mpanl. The instance value is used to 
-- identify the logical connection, multiplexed within the physical 
-- channel, with which a frame is associated. All frames carried within 
-- a particular physical channel and having the same DLCI value are 
-- associated with the same logical connection.
-- 
-- A DLCI refers to a switched virtual circuit (SVC) which is created 
-- dynamically through signaling.

mpanlDlci OBJECT IDENTIFIER ::= { mpanl 5 }



mpanlDlciRowStatusTable OBJECT-TYPE
   SYNTAX     SEQUENCE OF MpanlDlciRowStatusEntry
   ACCESS     not-accessible
   STATUS     mandatory
   DESCRIPTION
     "*** THIS TABLE CURRENTLY NOT IMPLEMENTED ***

      This entry controls the addition and deletion of 
      mpanlDlci components."
::= { mpanlDlci 1 }

mpanlDlciRowStatusEntry OBJECT-TYPE
   SYNTAX     MpanlDlciRowStatusEntry
   ACCESS     not-accessible
   STATUS     mandatory
   DESCRIPTION
     "A single entry in the table represents a single 
      mpanlDlci component."
   INDEX {
      mpanlIndex,
      mpanlDlciIndex }
::= { mpanlDlciRowStatusTable 1 }

MpanlDlciRowStatusEntry ::= SEQUENCE {
   mpanlDlciRowStatus
      RowStatus,
   mpanlDlciComponentName
      DisplayString,
   mpanlDlciStorageType
      StorageType,
   mpanlDlciIndex
      Integer32 }

mpanlDlciRowStatus OBJECT-TYPE
   SYNTAX     RowStatus 
   ACCESS     read-only
   STATUS     mandatory
   DESCRIPTION
     "This variable is used as the basis for SNMP naming of
      mpanlDlci components.
      These components cannot be added nor deleted."
::= { mpanlDlciRowStatusEntry 1 }

mpanlDlciComponentName OBJECT-TYPE
   SYNTAX     DisplayString 
   ACCESS     read-only
   STATUS     mandatory
   DESCRIPTION
     "This variable provides the component's string name for
      use with the ASCII Console Interface"
::= { mpanlDlciRowStatusEntry 2 }

mpanlDlciStorageType OBJECT-TYPE
   SYNTAX     StorageType 
   ACCESS     read-only
   STATUS     mandatory
   DESCRIPTION
     "This variable represents the storage type value for the
      mpanlDlci tables."
::= { mpanlDlciRowStatusEntry 4 }

mpanlDlciIndex OBJECT-TYPE
   SYNTAX     Integer32 (17..1007)
   ACCESS     not-accessible
   STATUS     mandatory
   DESCRIPTION
     "This variable represents the index for the mpanlDlci tables."
::= { mpanlDlciRowStatusEntry 10 }

mpanlDlciStateTable OBJECT-TYPE
   SYNTAX     SEQUENCE OF MpanlDlciStateEntry
   ACCESS     not-accessible
   STATUS     mandatory
   DESCRIPTION
     "*** THIS TABLE CURRENTLY NOT IMPLEMENTED ***

      This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mpanlDlci 10 }

mpanlDlciStateEntry OBJECT-TYPE
   SYNTAX     MpanlDlciStateEntry
   ACCESS     not-accessible
   STATUS     mandatory
   DESCRIPTION
     "An entry in the mpanlDlciStateTable."
   INDEX {
      mpanlIndex,
      mpanlDlciIndex }
::= { mpanlDlciStateTable 1 }

MpanlDlciStateEntry ::= SEQUENCE {
   mpanlDlciAdminState
      INTEGER,
   mpanlDlciOperationalState
      INTEGER,
   mpanlDlciUsageState
      INTEGER,
   mpanlDlciAvailabilityStatus
      OCTET STRING,
   mpanlDlciProceduralStatus
      OCTET STRING,
   mpanlDlciControlStatus
      OCTET STRING,
   mpanlDlciAlarmStatus
      OCTET STRING,
   mpanlDlciStandbyStatus
      INTEGER,
   mpanlDlciUnknownStatus
      INTEGER }

mpanlDlciAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mpanlDlciStateEntry 1 }

mpanlDlciOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mpanlDlciStateEntry 2 }

mpanlDlciUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mpanlDlciStateEntry 3 }

mpanlDlciAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mpanlDlciStateEntry 4 }

mpanlDlciProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mpanlDlciStateEntry 5 }

mpanlDlciControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mpanlDlciStateEntry 6 }

mpanlDlciAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mpanlDlciStateEntry 7 }

mpanlDlciStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mpanlDlciStateEntry 8 }

mpanlDlciUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mpanlDlciStateEntry 9 }

mpanlDlciCalldTable OBJECT-TYPE
   SYNTAX     SEQUENCE OF MpanlDlciCalldEntry
   ACCESS     not-accessible
   STATUS     mandatory
   DESCRIPTION
     "*** THIS TABLE CURRENTLY NOT IMPLEMENTED ***

      This group of attributes describes the characteristics of the call such 
      as call type and call state."
::= { mpanlDlci 11 }

mpanlDlciCalldEntry OBJECT-TYPE
   SYNTAX     MpanlDlciCalldEntry
   ACCESS     not-accessible
   STATUS     mandatory
   DESCRIPTION
     "An entry in the mpanlDlciCalldTable."
   INDEX {
      mpanlIndex,
      mpanlDlciIndex }
::= { mpanlDlciCalldTable 1 }

MpanlDlciCalldEntry ::= SEQUENCE {
   mpanlDlciQ933CallState
      INTEGER,
   mpanlDlciQ933CallReference
      Unsigned32 }

mpanlDlciQ933CallState OBJECT-TYPE
   SYNTAX     INTEGER  {
                 null(0),
                 callInitiated(1),
                 outgoingCallProceeding(3),
                 callPresent(6),
                 incomingCallProceeding(9),
                 active(10),
                 disconnectRequest(11),
                 disconnectIndication(12),
                 releaseRequest(19),
                 notApplicable(20) }
   ACCESS     read-only
   STATUS     mandatory
   DESCRIPTION
     "This attribute indicates the Q.933 state of an SVC call. In the 
      description that follows, 'local' refers to the user who has initiated 
      the SETUP request, and 'remote' refers to the user to whom the 
      local user wishes to connect.
      
      State description:
      In the null state, the network has neither received nor sent call setup 
      requests for this DLCI.
      In the callInitiated state, the network has received a SETUP 
      message from the local user.
      In the outgoingCallProceeding state, the network has sent a CALL 
      PROCEEDING message to the local user in response to the SETUP 
      message.
      In the callPresent state, the network has sent a SETUP message to 
      the remote user.
      In the incomingCallProceeding state, the network has received a 
      CALL PROCEEDING message from the remote user in response to 
      a SETUP message.
      In the active state, either the network has sent a CONNECT 
      message to the local user, or the network has received a CONNECT 
      from the remote user.
      In the disconnectRequest state, the network has received a 
      DISCONNECT message from the local user.
      In the disconnectIndication state, the network has sent a 
      DISCONNECT to the local user.
      In the releaseRequest state, the network has sent out a RELEASE 
      message to the local user.
      The notApplicable state indicates that this attribute is meaningless 
      because the DLCI is a PVC."
::= { mpanlDlciCalldEntry 2 }

mpanlDlciQ933CallReference OBJECT-TYPE
   SYNTAX     Unsigned32 (0..32767)
   ACCESS     read-only
   STATUS     mandatory
   DESCRIPTION
     "This attribute indicates the Q.933 call reference number associated 
      with this DLCI."
::= { mpanlDlciCalldEntry 3 }

mpanlDlciSpOpTable OBJECT-TYPE
   SYNTAX     SEQUENCE OF MpanlDlciSpOpEntry
   ACCESS     not-accessible
   STATUS     mandatory
   DESCRIPTION
     "*** THIS TABLE CURRENTLY NOT IMPLEMENTED ***

      This group contains the service parameters specific to this instance 
      of Dlci."
::= { mpanlDlci 12 }

mpanlDlciSpOpEntry OBJECT-TYPE
   SYNTAX     MpanlDlciSpOpEntry
   ACCESS     not-accessible
   STATUS     mandatory
   DESCRIPTION
     "An entry in the mpanlDlciSpOpTable."
   INDEX {
      mpanlIndex,
      mpanlDlciIndex }
::= { mpanlDlciSpOpTable 1 }

MpanlDlciSpOpEntry ::= SEQUENCE {
   mpanlDlciMaximumFrameSize
      Unsigned32,
   mpanlDlciCommittedBurstSize
      Unsigned32,
   mpanlDlciExcessBurstSize
      Unsigned32,
   mpanlDlciAccounting
      INTEGER,
   mpanlDlciEmissionPriorityToIf
      INTEGER,
   mpanlDlciTransferPriToNwk
      Unsigned32,
   mpanlDlciTransferPriFromNwk
      Unsigned32 }

mpanlDlciMaximumFrameSize OBJECT-TYPE
   SYNTAX     Unsigned32 (1..4096)
   ACCESS     read-only
   STATUS     mandatory
   DESCRIPTION
     "This attribute specifies the maximum number of octets which may 
      be included in the information field. The frame relay header and 
      CRC octets are not included in this definition. This attribute 
      corresponds to the dN1 parameter described in the Frame Relay 
      Vendor Forum Specification."
::= { mpanlDlciSpOpEntry 1 }

mpanlDlciCommittedBurstSize OBJECT-TYPE
   SYNTAX     Unsigned32 (0..50000000)
   ACCESS     read-only
   STATUS     mandatory
   DESCRIPTION
     "This attribute indicates the committed burst size (Bc) in bits. bc is 
      the amount of data that a network agrees to transfer under normal 
      conditions over a measurement interval (t). Data marked DE=1 is 
      not accounted for in Bc.
      
      This attribute should be ignored when rateEnforcement is off."
::= { mpanlDlciSpOpEntry 4 }

mpanlDlciExcessBurstSize OBJECT-TYPE
   SYNTAX     Unsigned32 (0..50000000)
   ACCESS     read-only
   STATUS     mandatory
   DESCRIPTION
     "This attribute indicates the excess burst size (Be) in bits. Be is the 
      amount of uncommitted data that the network will attempt to deliver 
      over measurement interval T. Data marked DE=1 by the user or by 
      the network is accounted for here.
      
      This attribute should be ignored when rateEnforcement is off."
::= { mpanlDlciSpOpEntry 5 }

mpanlDlciAccounting OBJECT-TYPE
   SYNTAX     INTEGER  {
                 off(0),
                 on(1) }
   ACCESS     read-only
   STATUS     mandatory
   DESCRIPTION
     "This attribute indicates whether accounting data collection and 
      record generation is turned on at this DLCI. For accounting data 
      collection and record generation to be occur, the accountingOn 
      attribute must be on and at least one of the accountCollection 
      options in the DataNetworkAddress component must be selected."
::= { mpanlDlciSpOpEntry 8 }

mpanlDlciEmissionPriorityToIf OBJECT-TYPE
   SYNTAX     INTEGER (0 | 1 | 2 | 3)
   ACCESS     read-only
   STATUS     mandatory
   DESCRIPTION
     "This attribute indicates the emission priority of frames sent to the 
      interface. A larger value denotes a higher priority."
::= { mpanlDlciSpOpEntry 9 }

mpanlDlciTransferPriToNwk OBJECT-TYPE
   SYNTAX     Unsigned32 (0..15)
   ACCESS     read-only
   STATUS     mandatory
   DESCRIPTION
     "This attribute indicates the priority at which data is transferred to 
      the network.
      
      The transfer priority is a preference configured for an application 
      according to its delay-sensitivity requirement. Frames with higher 
      transfer priority are served by the network before the frames with 
      lower priority. The transfer priority standard is defined to have 16 
      indices from 0 to 15.
      
      Each transfer priority n, where n specifies the transfer priority 
      index, contains a default setting for routing class of service 
      (multimedia, delay or throughput) and frame relay egress queue 
      (depending on the number of supported egress queues on the remote 
      end interface) specified by the routingClassOfService and 
      emissionPriority attributes provisioned in the Mod Frs DprsNet 
      Tpm/n component. The default mapping can be altered by a user if 
      required."
::= { mpanlDlciSpOpEntry 10 }

mpanlDlciTransferPriFromNwk OBJECT-TYPE
   SYNTAX     Unsigned32 (0..15)
   ACCESS     read-only
   STATUS     mandatory
   DESCRIPTION
     "This attribute indicates the priority at which data is transferred from 
      the network.
      
      The transfer priority is a preference configured for an application 
      according to its delay-sensitivity requirement. Frames with higher 
      transfer priority are served by the network before the frames with 
      lower priority. The transfer priority standard is defined to have 16 
      indices from 0 to 15.
      
      Each transfer priority n, where n specifies the transfer priority 
      index, contains a default setting for routing class of service 
      (multimedia, delay or throughput) and frame relay egress queue 
      (depending on the number of supported egress queues on the remote 
      end interface) specified by the routingClassOfService and 
      emissionPriority attributes provisioned in the Mod Frs DprsNet 
      Tpm/n component. The default mapping can be altered by a user if 
      required."
::= { mpanlDlciSpOpEntry 11 }

mpanlDlciStatsTable OBJECT-TYPE
   SYNTAX     SEQUENCE OF MpanlDlciStatsEntry
   ACCESS     not-accessible
   STATUS     mandatory
   DESCRIPTION
     "*** THIS TABLE CURRENTLY NOT IMPLEMENTED ***

      This group contains the operational statistics for the MPANL Data 
      Link Connection Identifier."
::= { mpanlDlci 13 }

mpanlDlciStatsEntry OBJECT-TYPE
   SYNTAX     MpanlDlciStatsEntry
   ACCESS     not-accessible
   STATUS     mandatory
   DESCRIPTION
     "An entry in the mpanlDlciStatsTable."
   INDEX {
      mpanlIndex,
      mpanlDlciIndex }
::= { mpanlDlciStatsTable 1 }

MpanlDlciStatsEntry ::= SEQUENCE {
   mpanlDlciFrmToIf
      Unsigned32,
   mpanlDlciFecnFrmToIf
      Unsigned32,
   mpanlDlciBecnFrmToIf
      Unsigned32,
   mpanlDlciBciToSubnet
      Unsigned32,
   mpanlDlciDeFrmToIf
      Unsigned32,
   mpanlDlciDiscCongestedToIf
      Unsigned32,
   mpanlDlciDiscDeCongestedToIf
      Unsigned32,
   mpanlDlciFrmFromIf
      Unsigned32,
   mpanlDlciFecnFrmFromIf
      Unsigned32,
   mpanlDlciBecnFrmFromIf
      Unsigned32,
   mpanlDlciFciFromSubnet
      Unsigned32,
   mpanlDlciBciFromSubnet
      Unsigned32,
   mpanlDlciDeFrmFromIf
      Unsigned32,
   mpanlDlciExcessFrmFromIf
      Unsigned32,
   mpanlDlciDiscExcessFromIf
      Unsigned32,
   mpanlDlciDiscFrameAbit
      Unsigned32,
   mpanlDlciDiscCongestedFromIf
      Unsigned32,
   mpanlDlciDiscDeCongestedFromIf
      Unsigned32,
   mpanlDlciErrorShortFrmFromIf
      Unsigned32,
   mpanlDlciErrorLongFrmFromIf
      Unsigned32,
   mpanlDlciBecnFrmSetByService
      Unsigned32,
   mpanlDlciBytesToIf
      Unsigned32,
   mpanlDlciDeBytesToIf
      Unsigned32,
   mpanlDlciDiscCongestedToIfBytes
      Unsigned32,
   mpanlDlciDiscDeCongestedToIfBytes
      Unsigned32,
   mpanlDlciBytesFromIf
      Unsigned32,
   mpanlDlciDeBytesFromIf
      Unsigned32,
   mpanlDlciExcessBytesFromIf
      Unsigned32,
   mpanlDlciDiscExcessFromIfBytes
      Unsigned32,
   mpanlDlciDiscByteAbit
      Unsigned32,
   mpanlDlciDiscCongestedFromIfBytes
      Unsigned32,
   mpanlDlciDiscDeCongestedFromIfBytes
      Unsigned32,
   mpanlDlciErrorLongBytesFromIf
      Unsigned32,
   mpanlDlciTransferPriorityToNetwork
      INTEGER,
   mpanlDlciTransferPriorityFromNetwork
      INTEGER }

mpanlDlciFrmToIf OBJECT-TYPE
   SYNTAX     Unsigned32 (0..4294967295)
   ACCESS     read-only
   STATUS     mandatory
   DESCRIPTION
     "This attribute counts the frames sent out the interface. When the 
      maximum count is reached the count wraps to zero."
   DEFVAL     { 0 }
::= { mpanlDlciStatsEntry 1 }

mpanlDlciFecnFrmToIf OBJECT-TYPE
   SYNTAX     Unsigned32 (0..4294967295)
   ACCESS     read-only
   STATUS     mandatory
   DESCRIPTION
     "This attribute counts the frames sent to the interface with the 
      Forward Explicit Congestion Notification (FECN) bit set. When the 
      count reaches maximum it wraps to zero."
   DEFVAL     { 0 }
::= { mpanlDlciStatsEntry 2 }

mpanlDlciBecnFrmToIf OBJECT-TYPE
   SYNTAX     Unsigned32 (0..4294967295)
   ACCESS     read-only
   STATUS     mandatory
   DESCRIPTION
     "This attribute counts the frames sent to the interface with the 
      Backward Explicit Congestion Notification (BECN) bit set. When 
      the count reaches maximum it wraps to zero."
   DEFVAL     { 0 }
::= { mpanlDlciStatsEntry 3 }

mpanlDlciBciToSubnet OBJECT-TYPE
   SYNTAX     Unsigned32 (0..4294967295)
   ACCESS     read-only
   STATUS     mandatory
   DESCRIPTION
     "This attribute counts the frames sent into the network with the 
      Backward Congestion Indication (BCI) bit set. When the count 
      reaches maximum it wraps to zero."
   DEFVAL     { 0 }
::= { mpanlDlciStatsEntry 4 }

mpanlDlciDeFrmToIf OBJECT-TYPE
   SYNTAX     Unsigned32 (0..4294967295)
   ACCESS     read-only
   STATUS     mandatory
   DESCRIPTION
     "This attribute counts the frames sent to the interface with the 
      Discard Eligibility (DE) bit set. When the count reaches maximum 
      it wraps to zero."
   DEFVAL     { 0 }
::= { mpanlDlciStatsEntry 5 }

mpanlDlciDiscCongestedToIf OBJECT-TYPE
   SYNTAX     Unsigned32 (0..4294967295)
   ACCESS     read-only
   STATUS     mandatory
   DESCRIPTION
     "This attribute counts the number of frame discards at the MPANL 
      service due to local congestion in the direction toward the interface. 
      When this count reaches maximum, it wraps to zero."
   DEFVAL     { 0 }
::= { mpanlDlciStatsEntry 6 }

mpanlDlciDiscDeCongestedToIf OBJECT-TYPE
   SYNTAX     Unsigned32 (0..4294967295)
   ACCESS     read-only
   STATUS     mandatory
   DESCRIPTION
     "This attribute counts the number of discarded frames, with the 
      Discard Eligibility (DE) bit set, at the MPANL service, due to local 
      congestion in the direction toward the interface. When this count 
      reaches maximum, it wraps to zero."
   DEFVAL     { 0 }
::= { mpanlDlciStatsEntry 7 }

mpanlDlciFrmFromIf OBJECT-TYPE
   SYNTAX     Unsigned32 (0..4294967295)
   ACCESS     read-only
   STATUS     mandatory
   DESCRIPTION
     "This attribute counts the frames received from the interface. Frames 
      that are discarded due to error or excess are not counted. When the 
      maximum count is reached the count wraps to zero."
   DEFVAL     { 0 }
::= { mpanlDlciStatsEntry 8 }

mpanlDlciFecnFrmFromIf OBJECT-TYPE
   SYNTAX     Unsigned32 (0..4294967295)
   ACCESS     read-only
   STATUS     mandatory
   DESCRIPTION
     "This attribute counts the frames received from the interface with the 
      Forward Explicit Congestion Notification (FECN) bit set. When the 
      count reaches maximum it wraps to zero."
   DEFVAL     { 0 }
::= { mpanlDlciStatsEntry 9 }

mpanlDlciBecnFrmFromIf OBJECT-TYPE
   SYNTAX     Unsigned32 (0..4294967295)
   ACCESS     read-only
   STATUS     mandatory
   DESCRIPTION
     "This attribute counts the frames received from the interface with the 
      Backward Explicit Congestion Notification (BECN) bit set. When 
      the count reaches maximum it wraps to zero."
   DEFVAL     { 0 }
::= { mpanlDlciStatsEntry 10 }

mpanlDlciFciFromSubnet OBJECT-TYPE
   SYNTAX     Unsigned32 (0..4294967295)
   ACCESS     read-only
   STATUS     mandatory
   DESCRIPTION
     "This attribute counts the frames received from the network with the 
      Forward Congestion Indication (FCI) bit set. When the count 
      reaches maximum it wraps to zero."
   DEFVAL     { 0 }
::= { mpanlDlciStatsEntry 11 }

mpanlDlciBciFromSubnet OBJECT-TYPE
   SYNTAX     Unsigned32 (0..4294967295)
   ACCESS     read-only
   STATUS     mandatory
   DESCRIPTION
     "This attribute counts the frames received from the network with the 
      Backward Congestion Indication (BCI) bit set. When the count 
      reaches maximum it wraps to zero."
   DEFVAL     { 0 }
::= { mpanlDlciStatsEntry 12 }

mpanlDlciDeFrmFromIf OBJECT-TYPE
   SYNTAX     Unsigned32 (0..4294967295)
   ACCESS     read-only
   STATUS     mandatory
   DESCRIPTION
     "This attribute counts the frames received from the interface with the 
      Discard Eligibility (DE) bit set. When the count reaches maximum 
      it wraps to zero."
   DEFVAL     { 0 }
::= { mpanlDlciStatsEntry 13 }

mpanlDlciExcessFrmFromIf OBJECT-TYPE
   SYNTAX     Unsigned32 (0..4294967295)
   ACCESS     read-only
   STATUS     mandatory
   DESCRIPTION
     "This attribute counts the frames received from the interface with the 
      Discard Eligibility (DE) bit clear, but subsequently set by the 
      network due to rate enforcement. When the count reaches 
      maximum it wraps to zero."
   DEFVAL     { 0 }
::= { mpanlDlciStatsEntry 14 }

mpanlDlciDiscExcessFromIf OBJECT-TYPE
   SYNTAX     Unsigned32 (0..4294967295)
   ACCESS     read-only
   STATUS     mandatory
   DESCRIPTION
     "This attribute counts the frames which were discarded due to rate 
      enforcement. When the count reaches maximum it wraps to zero."
   DEFVAL     { 0 }
::= { mpanlDlciStatsEntry 15 }

mpanlDlciDiscFrameAbit OBJECT-TYPE
   SYNTAX     Unsigned32 (0..4294967295)
   ACCESS     read-only
   STATUS     mandatory
   DESCRIPTION
     "This attribute counts the number of frame discards at the MPANL 
      Service, due to an inactive PVC status, in the direction toward the 
      network. When this count reaches maximum, it wraps to zero."
   DEFVAL     { 0 }
::= { mpanlDlciStatsEntry 16 }

mpanlDlciDiscCongestedFromIf OBJECT-TYPE
   SYNTAX     Unsigned32 (0..4294967295)
   ACCESS     read-only
   STATUS     mandatory
   DESCRIPTION
     "This attribute counts the number of frame discards at the MPANL 
      service due to local congestion in the direction toward the network. 
      When this count reaches maximum, it wraps to zero."
   DEFVAL     { 0 }
::= { mpanlDlciStatsEntry 17 }

mpanlDlciDiscDeCongestedFromIf OBJECT-TYPE
   SYNTAX     Unsigned32 (0..4294967295)
   ACCESS     read-only
   STATUS     mandatory
   DESCRIPTION
     "This attribute counts the number of discarded frames, with the 
      Discard Eligibility (DE) bit set, at the MPANL service, due to local 
      congestion, in the direction toward the network. When this count 
      reaches maximum, it wraps to zero."
   DEFVAL     { 0 }
::= { mpanlDlciStatsEntry 18 }

mpanlDlciErrorShortFrmFromIf OBJECT-TYPE
   SYNTAX     Unsigned32 (0..4294967295)
   ACCESS     read-only
   STATUS     mandatory
   DESCRIPTION
     "This attribute counts the frames received with 0 octets in the 
      information field. When the count reaches maximum it wraps to 
      zero."
   DEFVAL     { 0 }
::= { mpanlDlciStatsEntry 19 }

mpanlDlciErrorLongFrmFromIf OBJECT-TYPE
   SYNTAX     Unsigned32 (0..4294967295)
   ACCESS     read-only
   STATUS     mandatory
   DESCRIPTION
     "This attribute counts the frames received with number of octets in 
      the information field greater than the subscribed maximum. When 
      the count reaches maximum it wraps to zero. Frames whose lengths 
      are greater than the hardware receive buffer are ignored by the 
      hardware and are therefore not included in this count."
   DEFVAL     { 0 }
::= { mpanlDlciStatsEntry 20 }

mpanlDlciBecnFrmSetByService OBJECT-TYPE
   SYNTAX     Unsigned32 (0..4294967295)
   ACCESS     read-only
   STATUS     mandatory
   DESCRIPTION
     "This attribute counts the number of frames with BECN set by the 
      MPANL service. It is incremented whenever the MPANL service 
      sets BECN on a frame upon detecting local congestion. This count 
      is incremented regardless of whether the frame already bears a set 
      BECN bit since its use is to determine the place of congestion. 
      When the count reaches maximum, it wraps to zero."
   DEFVAL     { 0 }
::= { mpanlDlciStatsEntry 21 }

mpanlDlciBytesToIf OBJECT-TYPE
   SYNTAX     Unsigned32 (0..4294967295)
   ACCESS     read-only
   STATUS     mandatory
   DESCRIPTION
     "This attribute counts the bytes sent out the interface. When the 
      maximum count is reached the count wraps to zero."
   DEFVAL     { 0 }
::= { mpanlDlciStatsEntry 22 }

mpanlDlciDeBytesToIf OBJECT-TYPE
   SYNTAX     Unsigned32 (0..4294967295)
   ACCESS     read-only
   STATUS     mandatory
   DESCRIPTION
     "This attribute counts the bytes sent to the interface with the Discard 
      Eligibility (DE) bit set. When the count reaches maximum it wraps 
      to zero."
   DEFVAL     { 0 }
::= { mpanlDlciStatsEntry 23 }

mpanlDlciDiscCongestedToIfBytes OBJECT-TYPE
   SYNTAX     Unsigned32 (0..4294967295)
   ACCESS     read-only
   STATUS     mandatory
   DESCRIPTION
     "This attribute counts the number of byte discards at the MPANL 
      service due to local congestion in the direction toward the link. 
      When this count reaches maximum, it wraps to zero."
   DEFVAL     { 0 }
::= { mpanlDlciStatsEntry 24 }

mpanlDlciDiscDeCongestedToIfBytes OBJECT-TYPE
   SYNTAX     Unsigned32 (0..4294967295)
   ACCESS     read-only
   STATUS     mandatory
   DESCRIPTION
     "This attribute counts the number of discard eligible (DE=1) byte 
      discards at the MPANL service due to local congestion in the 
      direction toward the link. When the maximum count is reached the 
      count wraps to zero."
   DEFVAL     { 0 }
::= { mpanlDlciStatsEntry 25 }

mpanlDlciBytesFromIf OBJECT-TYPE
   SYNTAX     Unsigned32 (0..4294967295)
   ACCESS     read-only
   STATUS     mandatory
   DESCRIPTION
     "This attribute counts the bytes received from the interface. Bytes 
      that are discarded due to error or excess are not counted. When the 
      maximum count is reached the count wraps to zero."
   DEFVAL     { 0 }
::= { mpanlDlciStatsEntry 26 }

mpanlDlciDeBytesFromIf OBJECT-TYPE
   SYNTAX     Unsigned32 (0..4294967295)
   ACCESS     read-only
   STATUS     mandatory
   DESCRIPTION
     "This attribute counts the bytes received from the interface with the 
      Discard Eligibility (DE) bit set. When the count reaches maximum 
      it wraps to zero."
   DEFVAL     { 0 }
::= { mpanlDlciStatsEntry 27 }

mpanlDlciExcessBytesFromIf OBJECT-TYPE
   SYNTAX     Unsigned32 (0..4294967295)
   ACCESS     read-only
   STATUS     mandatory
   DESCRIPTION
     "This attribute counts the bytes received from the interface with the 
      Discard Eligibility (DE) bit clear, but subsequently set by the 
      network due to rate enforcement. When the count reaches 
      maximum it wraps to zero."
   DEFVAL     { 0 }
::= { mpanlDlciStatsEntry 28 }

mpanlDlciDiscExcessFromIfBytes OBJECT-TYPE
   SYNTAX     Unsigned32 (0..4294967295)
   ACCESS     read-only
   STATUS     mandatory
   DESCRIPTION
     "This attribute counts the bytes which were discarded due to rate 
      enforcement. When the count reaches maximum it wraps to zero."
   DEFVAL     { 0 }
::= { mpanlDlciStatsEntry 29 }

mpanlDlciDiscByteAbit OBJECT-TYPE
   SYNTAX     Unsigned32 (0..4294967295)
   ACCESS     read-only
   STATUS     mandatory
   DESCRIPTION
     "This attribute counts the bytes which were discarded due to aBit 
      turned off."
   DEFVAL     { 0 }
::= { mpanlDlciStatsEntry 30 }

mpanlDlciDiscCongestedFromIfBytes OBJECT-TYPE
   SYNTAX     Unsigned32 (0..4294967295)
   ACCESS     read-only
   STATUS     mandatory
   DESCRIPTION
     "This attribute counts the number of byte discards at the MPANL 
      service due to local congestion in the direction toward the network. 
      When this count reaches maximum, it wraps to zero."
   DEFVAL     { 0 }
::= { mpanlDlciStatsEntry 31 }

mpanlDlciDiscDeCongestedFromIfBytes OBJECT-TYPE
   SYNTAX     Unsigned32 (0..4294967295)
   ACCESS     read-only
   STATUS     mandatory
   DESCRIPTION
     "This attribute counts the number of discard eligible (DE=1) byte 
      discards at the MPANL service due to local congestion in the 
      direction toward the network. When the maximum count is reached 
      the count wraps to zero."
   DEFVAL     { 0 }
::= { mpanlDlciStatsEntry 32 }

mpanlDlciErrorLongBytesFromIf OBJECT-TYPE
   SYNTAX     Unsigned32 (0..4294967295)
   ACCESS     read-only
   STATUS     mandatory
   DESCRIPTION
     "This attribute counts the bytes received with number of octets in the 
      information field greater than the subscribed maximum. When the 
      count reaches maximum it wraps to zero. Bytes whose lengths are 
      greater than the hardware receive buffer are ignored by the 
      hardware and are therefore not included in this count."
   DEFVAL     { 0 }
::= { mpanlDlciStatsEntry 34 }

mpanlDlciTransferPriorityToNetwork OBJECT-TYPE
   SYNTAX     INTEGER  {
                 n0(0),
                 n1(1),
                 n2(2),
                 n3(3),
                 n4(4),
                 n5(5),
                 n6(6),
                 n7(7),
                 n8(8),
                 n9(9),
                 n10(10),
                 n11(11),
                 n12(12),
                 n13(13),
                 n14(14),
                 n15(15) }
   ACCESS     read-only
   STATUS     obsolete
   DESCRIPTION
     "This attribute is obsolete. It is replaced by attribute 
      transferPriorityToNetwork under group 
      FrsNniDataLinkConnectionIdentifierServiceParametersOp."
::= { mpanlDlciStatsEntry 37 }

mpanlDlciTransferPriorityFromNetwork OBJECT-TYPE
   SYNTAX     INTEGER  {
                 n0(0),
                 n1(1),
                 n2(2),
                 n3(3),
                 n4(4),
                 n5(5),
                 n6(6),
                 n7(7),
                 n8(8),
                 n9(9),
                 n10(10),
                 n11(11),
                 n12(12),
                 n13(13),
                 n14(14),
                 n15(15) }
   ACCESS     read-only
   STATUS     obsolete
   DESCRIPTION
     "This attribute is obsolete. It is replaced by attribute 
      transferPriorityFromNetwork under group 
      FrsNniDataLinkConnectionIdentifierServiceParametersOp."
::= { mpanlDlciStatsEntry 38 }

mpanlDlciIntTable OBJECT-TYPE
   SYNTAX     SEQUENCE OF MpanlDlciIntEntry
   ACCESS     not-accessible
   STATUS     mandatory
   DESCRIPTION
     "*** THIS TABLE CURRENTLY NOT IMPLEMENTED ***

      This group contains the operational statistics for the MPANL Data 
      Link Connection Identifier interval data."
::= { mpanlDlci 14 }

mpanlDlciIntEntry OBJECT-TYPE
   SYNTAX     MpanlDlciIntEntry
   ACCESS     not-accessible
   STATUS     mandatory
   DESCRIPTION
     "An entry in the mpanlDlciIntTable."
   INDEX {
      mpanlIndex,
      mpanlDlciIndex }
::= { mpanlDlciIntTable 1 }

MpanlDlciIntEntry ::= SEQUENCE {
   mpanlDlciStartTime
      EnterpriseDateAndTime,
   mpanlDlciTotalIngressBytes
      Unsigned64,
   mpanlDlciTotalEgressBytes
      Unsigned64,
   mpanlDlciEirIngressBytes
      Unsigned64,
   mpanlDlciEirEgressBytes
      Unsigned64,
   mpanlDlciDiscardedBytes
      Unsigned64,
   mpanlDlciTotalIngressSegFrm
      Unsigned32,
   mpanlDlciTotalEgressSegFrm
      Unsigned32,
   mpanlDlciEirIngressSegFrm
      Unsigned32,
   mpanlDlciEirEgressSegFrm
      Unsigned32,
   mpanlDlciDiscardedSegFrm
      Unsigned32,
   mpanlDlciCallReferenceNumber
      Unsigned32,
   mpanlDlciElapsedDifference
      Unsigned32 }

mpanlDlciStartTime OBJECT-TYPE
   SYNTAX     EnterpriseDateAndTime (SIZE (0 | 19))
   ACCESS     read-only
   STATUS     mandatory
   DESCRIPTION
     "This attribute indicates the start time of this interval period. If the 
      Vc spans 12 hour time or time of day change, startTime reflects new 
      time as recorded at 12 hour periods or time of day changes. A new 
      interval period is started each time an accounting record is 
      generated."
::= { mpanlDlciIntEntry 1 }

mpanlDlciTotalIngressBytes OBJECT-TYPE
   SYNTAX     Unsigned64 (SIZE (8))
   ACCESS     read-only
   STATUS     mandatory
   DESCRIPTION
     "This attribute counts the total bytes received from the interface 
      since the start of the interval period. The start of the interval period 
      is captured in the startTime attribute. The count is reset to zero 
      when an accounting record is generated."
::= { mpanlDlciIntEntry 2 }

mpanlDlciTotalEgressBytes OBJECT-TYPE
   SYNTAX     Unsigned64 (SIZE (8))
   ACCESS     read-only
   STATUS     mandatory
   DESCRIPTION
     "This attribute counts the total bytes sent to the interface since the 
      start of the interval period. The start of the interval period is 
      captured in the startTime attribute. The count is reset to zero when 
      an accounting record is generated."
::= { mpanlDlciIntEntry 3 }

mpanlDlciEirIngressBytes OBJECT-TYPE
   SYNTAX     Unsigned64 (SIZE (8))
   ACCESS     read-only
   STATUS     mandatory
   DESCRIPTION
     "This attribute counts the total bytes with the Discard Eligibility 
      (DE) bit set sent to the subnet since the start of the interval period. 
      The start of the interval period is captured in the startTime attribute. 
      The count is reset to zero when an accounting record is generated."
::= { mpanlDlciIntEntry 4 }

mpanlDlciEirEgressBytes OBJECT-TYPE
   SYNTAX     Unsigned64 (SIZE (8))
   ACCESS     read-only
   STATUS     mandatory
   DESCRIPTION
     "This attribute counts the total bytes with the Discard Eligibility 
      (DE) bit set sent to the interface since the start of the interval 
      period. The start of the interval period is captured in the startTime 
      attribute. The count is reset to zero when an accounting record is 
      generated."
::= { mpanlDlciIntEntry 5 }

mpanlDlciDiscardedBytes OBJECT-TYPE
   SYNTAX     Unsigned64 (SIZE (8))
   ACCESS     read-only
   STATUS     mandatory
   DESCRIPTION
     "This attribute counts the total bytes in invalid frames received from 
      the interface and discarded at the DLCI since the start of the interval 
      period. This count is a sum of octets in frames discarded due to the 
      number of octets in the information field greater than the subscribed 
      maximum or equal to 0, due to aBit turned off, or due to rate 
      enforcement. The start of the interval period is captured in the 
      startTime attribute. The count is reset to zero when an accounting 
      record is generated."
::= { mpanlDlciIntEntry 6 }

mpanlDlciTotalIngressSegFrm OBJECT-TYPE
   SYNTAX     Unsigned32 (0..4294967295)
   ACCESS     read-only
   STATUS     mandatory
   DESCRIPTION
     "If the value of the unitsCounted attribute in moduleData component 
      is segments, this attribute counts the total number of segments in 
      frames received from the interface since the start of the interval 
      period. If the value of the unitsCounted attribute in moduleData 
      component is frames, this attribute counts the total number of 
      frames received from the interface since the start of the interval 
      period. The start of the interval period is captured in the startTime 
      attribute. The count is reset to zero when an accounting record is 
      generated."
   DEFVAL     { 0 }
::= { mpanlDlciIntEntry 7 }

mpanlDlciTotalEgressSegFrm OBJECT-TYPE
   SYNTAX     Unsigned32 (0..4294967295)
   ACCESS     read-only
   STATUS     mandatory
   DESCRIPTION
     "If the value of the unitsCounted attribute in moduleData component 
      is segments, this attribute counts the total number of segments in 
      frames sent to the interface since the start of the interval period. If 
      the value of the unitsCounted attribute in moduleData component is 
      frames, this attribute counts the total number of frames sent to the 
      interface since the start of the interval period. The start of the 
      interval period is captured in the startTime attribute. The count is 
      reset to zero when an accounting record is generated."
   DEFVAL     { 0 }
::= { mpanlDlciIntEntry 8 }

mpanlDlciEirIngressSegFrm OBJECT-TYPE
   SYNTAX     Unsigned32 (0..4294967295)
   ACCESS     read-only
   STATUS     mandatory
   DESCRIPTION
     "If the value of the unitsCounted attribute in moduleData component 
      is segments, this attribute counts the number of segments in frames 
      with the Discard Eligibility (DE) bit set sent to the subnet since the 
      start of the interval period. If the value of the unitsCounted attribute 
      in moduleData component is frames, this attribute counts the 
      number of frames with the Discard Eligibility (DE) bit set sent to 
      the subnet since the start of the interval period. The start of the 
      interval period is captured in the startTime attribute. The count is 
      reset to zero when an accounting record is generated."
   DEFVAL     { 0 }
::= { mpanlDlciIntEntry 9 }

mpanlDlciEirEgressSegFrm OBJECT-TYPE
   SYNTAX     Unsigned32 (0..4294967295)
   ACCESS     read-only
   STATUS     mandatory
   DESCRIPTION
     "If the value of the unitsCounted attribute in moduleData component 
      is segments, this attribute counts the number of segments in frames 
      with the Discard Eligibility (DE) bit set sent to the interface since 
      the start of the interval period. If the value of the unitsCounted 
      attribute in moduleData component is frames, this attribute counts 
      the number of frames with the Discard Eligibility (DE) bit set sent 
      to the interface since the start of the interval period. The start of the 
      interval period is captured in the startTime attribute. The count is 
      reset to zero when an accounting record is generated."
   DEFVAL     { 0 }
::= { mpanlDlciIntEntry 10 }

mpanlDlciDiscardedSegFrm OBJECT-TYPE
   SYNTAX     Unsigned32 (0..4294967295)
   ACCESS     read-only
   STATUS     mandatory
   DESCRIPTION
     "If the value of the unitsCounted attribute in moduleData component 
      is segments, this attribute counts the number of segments in invalid 
      frames received from the interface and discarded at the DLCI. If the 
      value of the unitsCounted attribute in moduleData component is 
      frames, this attribute counts the number of invalid frames received 
      from the interface and discarded at the DLCI. Segments of frames 
      are counted since the start of the interval period. The count is reset 
      to zero when an accounting record is generated. The count is a sum 
      of segments in frames or frames discarded due to the number of 
      octets in the information field greater than the subscribed maximum 
      or equal to 0, due to aBit turned off, or due to rate enforcement."
   DEFVAL     { 0 }
::= { mpanlDlciIntEntry 11 }

mpanlDlciCallReferenceNumber OBJECT-TYPE
   SYNTAX     Unsigned32 (0..4294967295)
   ACCESS     read-only
   STATUS     mandatory
   DESCRIPTION
     "This attribute displays the call reference number which is a unique 
      number generated by the switch.The same Call Reference Number 
      is stored in the interval data (accounting record) at both ends of the 
      call. It can be used as one of the attributes in matching duplicate 
      records generated at each end of the call."
   DEFVAL     { 0 }
::= { mpanlDlciIntEntry 17 }

mpanlDlciElapsedDifference OBJECT-TYPE
   SYNTAX     Unsigned32 (0..4294967295)
   ACCESS     read-only
   STATUS     mandatory
   DESCRIPTION
     "This attribute displays the elapsed time representing the period of 
      this interval data. It is elapsed time in 0.1 second increments since 
      the call started."
   DEFVAL     { 0 }
::= { mpanlDlciIntEntry 18 }

mpanlDlciAbitTable OBJECT-TYPE
   SYNTAX     SEQUENCE OF MpanlDlciAbitEntry
   ACCESS     not-accessible
   STATUS     mandatory
   DESCRIPTION
     "*** THIS TABLE CURRENTLY NOT IMPLEMENTED ***

      This group contains the A-Bit status information for this Data Link 
      Connection Identifier.
      
      A-Bit status information is only applicable for SPVCs. For SVCs, 
      the values of attributes under this group are all notApplicable."
::= { mpanlDlci 15 }

mpanlDlciAbitEntry OBJECT-TYPE
   SYNTAX     MpanlDlciAbitEntry
   ACCESS     not-accessible
   STATUS     mandatory
   DESCRIPTION
     "An entry in the mpanlDlciAbitTable."
   INDEX {
      mpanlIndex,
      mpanlDlciIndex }
::= { mpanlDlciAbitTable 1 }

MpanlDlciAbitEntry ::= SEQUENCE {
   mpanlDlciABitStatusToIf
      INTEGER,
   mpanlDlciABitReasonToIf
      INTEGER,
   mpanlDlciABitStatusFromIf
      INTEGER,
   mpanlDlciABitReasonFromIf
      INTEGER,
   mpanlDlciLoopbackState
      INTEGER }

mpanlDlciABitStatusToIf OBJECT-TYPE
   SYNTAX     INTEGER  {
                 inactive(0),
                 active(1),
                 notApplicable(2) }
   ACCESS     read-only
   STATUS     mandatory
   DESCRIPTION
     "This attribute is the most recent A-Bit status sent to the interface. 
      The A-Bit status is originated from the SPVC end point at the 
      remote end of the Passport subnet and it is relayed to the interface 
      by Mpanl. When an inactive setting is sent out, Mpanl will discard 
      any data offered from the interface. When an active setting is sent 
      out, Mpanl will try to relay all data offered from the interface to the 
      other end of the SPVC."
   DEFVAL     { inactive }
::= { mpanlDlciAbitEntry 1 }

mpanlDlciABitReasonToIf OBJECT-TYPE
   SYNTAX     INTEGER  {
                 notApplicable(0),
                 remoteUserSignaled(1),
                 remoteLmiError(3),
                 remoteLinkDown(5),
                 vcDown(6) }
   ACCESS     read-only
   STATUS     mandatory
   DESCRIPTION
     "This attribute provides the reason (if any) for an inactive status to be 
      sent to the interface. This reason is not applicable for an active 
      status.
      
      A-Bit status reason description:
      The A-Bit status reason is notApplicable when the A-Bit status is 
      active.
      The A-Bit status reason is remoteUserSignaled if the SPVC end 
      point originating the A-Bit status has detected that the virtual circuit 
      is down at the remote network through the LMI protocol. The 
      SPVC end point must be running network site LMI protocol for this 
      A-Bit status reason to be sent.
      The A-Bit status reason is remoteLmiError if the LMI protocol is 
      down at the SPVC end point originating this A-Bit status reason.
      The A-Bit status reason is remoteLinkDown if the physical 
      interface is disabled at the SPVC end point originating this A-Bit 
      status reason.
      The A-Bit reason is vcDown if no A-Bit status has been sent to the 
      interface (i.e., no A-Bit status has been relayed)."
   DEFVAL     { vcDown }
::= { mpanlDlciAbitEntry 2 }

mpanlDlciABitStatusFromIf OBJECT-TYPE
   SYNTAX     INTEGER  {
                 inactive(0),
                 active(1),
                 notApplicable(2) }
   ACCESS     read-only
   STATUS     mandatory
   DESCRIPTION
     "This attribute is the most recent A-Bit status received from the 
      interface. It is an indication from the equipment attached to the 
      interface on whether it is ready to accept data. Mpanl relays the A-
      Bit status from interface to the other end of the SPVC. When an 
      inactive setting is received, Mpanl will discard any data offered 
      from the subnet. When an active setting is received, Mpanl will try 
      to relay all data offered from the subnet to the interface."
   DEFVAL     { inactive }
::= { mpanlDlciAbitEntry 3 }

mpanlDlciABitReasonFromIf OBJECT-TYPE
   SYNTAX     INTEGER  {
                 notApplicable(0),
                 remoteUserSignaled(1),
                 remoteLmiError(3),
                 remoteLinkDown(5),
                 vcDown(6) }
   ACCESS     read-only
   STATUS     mandatory
   DESCRIPTION
     "This attribute provides the reason (if any) for an inactive status to be 
      sent to the subnet. This reason is not applicable for an active status.
      
      A-Bit status reason description:
      The A-Bit status reason is notApplicable when the A-Bit status is 
      active.
      The A-Bit status reason is remoteUserSignaled if the SPVC end 
      point originating the A-Bit status has detected that the DLCI is 
      inactive at the remote network through the LMI protocol. The 
      SPVC end point must be running network site LMI protocol for this 
      A-Bit status reason to be sent.
      The A-Bit status reason is remoteLmiError if the LMI protocol is 
      down at the SPVC end point originating this A-Bit status reason.
      The A-Bit status reason is remoteLinkDown if the physical 
      interface is disabled at the SPVC end point originating this A-Bit 
      status reason.
      The A-Bit reason is vcDown if no A-Bit status has been received 
      from the interface (i.e., no A-Bit status has been relayed)."
   DEFVAL     { vcDown }
::= { mpanlDlciAbitEntry 4 }

mpanlDlciLoopbackState OBJECT-TYPE
   SYNTAX     INTEGER  {
                 off(0),
                 on(1) }
   ACCESS     read-only
   STATUS     mandatory
   DESCRIPTION
     "This attribute has the value on when the DLCI is in loopback mode 
      and off otherwise. This loopback command verbs start and stop are 
      used to initiate and terminate the loopback mode for a DLCI. While 
      loopbackState is on, an active A-bit signal will be reliably 
      propagated across the subnet to the remote DLCI."
   DEFVAL     { off }
::= { mpanlDlciAbitEntry 5 }

-- 
-- *** THIS SUBTREE CURRENTLY NOT IMPLEMENTED ***
-- 

-- FrUni/n Dlci/n LoopBack	
-- FrNni/n Dlci/n LoopBack		
-- This component is the data loopback tool for the parent DLCI.

mpanlDlciLb OBJECT IDENTIFIER ::= { mpanlDlci 2 }



mpanlDlciLbRowStatusTable OBJECT-TYPE
   SYNTAX     SEQUENCE OF MpanlDlciLbRowStatusEntry
   ACCESS     not-accessible
   STATUS     mandatory
   DESCRIPTION
     "*** THIS TABLE CURRENTLY NOT IMPLEMENTED ***

      This entry controls the addition and deletion of 
      mpanlDlciLb components."
::= { mpanlDlciLb 1 }

mpanlDlciLbRowStatusEntry OBJECT-TYPE
   SYNTAX     MpanlDlciLbRowStatusEntry
   ACCESS     not-accessible
   STATUS     mandatory
   DESCRIPTION
     "A single entry in the table represents a single 
      mpanlDlciLb component."
   INDEX {
      mpanlIndex,
      mpanlDlciIndex,
      mpanlDlciLbIndex }
::= { mpanlDlciLbRowStatusTable 1 }

MpanlDlciLbRowStatusEntry ::= SEQUENCE {
   mpanlDlciLbRowStatus
      RowStatus,
   mpanlDlciLbComponentName
      DisplayString,
   mpanlDlciLbStorageType
      StorageType,
   mpanlDlciLbIndex
      NonReplicated }

mpanlDlciLbRowStatus OBJECT-TYPE
   SYNTAX     RowStatus 
   ACCESS     read-only
   STATUS     mandatory
   DESCRIPTION
     "This variable is used as the basis for SNMP naming of
      mpanlDlciLb components.
      These components cannot be added nor deleted."
::= { mpanlDlciLbRowStatusEntry 1 }

mpanlDlciLbComponentName OBJECT-TYPE
   SYNTAX     DisplayString 
   ACCESS     read-only
   STATUS     mandatory
   DESCRIPTION
     "This variable provides the component's string name for
      use with the ASCII Console Interface"
::= { mpanlDlciLbRowStatusEntry 2 }

mpanlDlciLbStorageType OBJECT-TYPE
   SYNTAX     StorageType 
   ACCESS     read-only
   STATUS     mandatory
   DESCRIPTION
     "This variable represents the storage type value for the
      mpanlDlciLb tables."
::= { mpanlDlciLbRowStatusEntry 4 }

mpanlDlciLbIndex OBJECT-TYPE
   SYNTAX     NonReplicated 
   ACCESS     not-accessible
   STATUS     mandatory
   DESCRIPTION
     "This variable represents the index for the mpanlDlciLb tables."
::= { mpanlDlciLbRowStatusEntry 10 }

mpanlDlciLbStatsTable OBJECT-TYPE
   SYNTAX     SEQUENCE OF MpanlDlciLbStatsEntry
   ACCESS     not-accessible
   STATUS     mandatory
   DESCRIPTION
     "*** THIS TABLE CURRENTLY NOT IMPLEMENTED ***

      This group contains all the statistics for the data loopback tool."
::= { mpanlDlciLb 10 }

mpanlDlciLbStatsEntry OBJECT-TYPE
   SYNTAX     MpanlDlciLbStatsEntry
   ACCESS     not-accessible
   STATUS     mandatory
   DESCRIPTION
     "An entry in the mpanlDlciLbStatsTable."
   INDEX {
      mpanlIndex,
      mpanlDlciIndex,
      mpanlDlciLbIndex }
::= { mpanlDlciLbStatsTable 1 }

MpanlDlciLbStatsEntry ::= SEQUENCE {
   mpanlDlciLbLocalTotalFrm
      Unsigned32,
   mpanlDlciLbLocalTotalBytes
      Unsigned32,
   mpanlDlciLbLocalFecnFrm
      Unsigned32,
   mpanlDlciLbLocalBecnFrm
      Unsigned32,
   mpanlDlciLbLocalDeFrm
      Unsigned32,
   mpanlDlciLbLocalDeBytes
      Unsigned32,
   mpanlDlciLbRemoteTotalFrm
      Unsigned32,
   mpanlDlciLbRemoteTotalBytes
      Unsigned32,
   mpanlDlciLbRemoteFecnFrm
      Unsigned32,
   mpanlDlciLbRemoteBecnFrm
      Unsigned32,
   mpanlDlciLbRemoteDeFrm
      Unsigned32,
   mpanlDlciLbRemoteDeBytes
      Unsigned32 }

mpanlDlciLbLocalTotalFrm OBJECT-TYPE
   SYNTAX     Unsigned32 (0..4294967295)
   ACCESS     read-only
   STATUS     mandatory
   DESCRIPTION
     "This attribute records the number of frames looped back to the link 
      since loopback was last started."
   DEFVAL     { 0 }
::= { mpanlDlciLbStatsEntry 1 }

mpanlDlciLbLocalTotalBytes OBJECT-TYPE
   SYNTAX     Unsigned32 (0..4294967295)
   ACCESS     read-only
   STATUS     mandatory
   DESCRIPTION
     "This attribute records the number of bytes looped back to the link 
      since loopback mode was started."
   DEFVAL     { 0 }
::= { mpanlDlciLbStatsEntry 2 }

mpanlDlciLbLocalFecnFrm OBJECT-TYPE
   SYNTAX     Unsigned32 (0..4294967295)
   ACCESS     read-only
   STATUS     mandatory
   DESCRIPTION
     "This attribute records the number of frames with the Forward 
      Explicit Congestion Notification (FECN) bit set, looped back to the 
      link since the loopback mode was started."
   DEFVAL     { 0 }
::= { mpanlDlciLbStatsEntry 3 }

mpanlDlciLbLocalBecnFrm OBJECT-TYPE
   SYNTAX     Unsigned32 (0..4294967295)
   ACCESS     read-only
   STATUS     mandatory
   DESCRIPTION
     "This attribute records the number of frames with the Backward 
      Explicit Congestion Notification (BECN) bit set, looped back to the 
      link since the loopback mode was started."
   DEFVAL     { 0 }
::= { mpanlDlciLbStatsEntry 4 }

mpanlDlciLbLocalDeFrm OBJECT-TYPE
   SYNTAX     Unsigned32 (0..4294967295)
   ACCESS     read-only
   STATUS     mandatory
   DESCRIPTION
     "This attribute records the number of frames with the Discard 
      Eligibility (DE) bit set, looped back to the link since the loopback 
      mode was started."
   DEFVAL     { 0 }
::= { mpanlDlciLbStatsEntry 5 }

mpanlDlciLbLocalDeBytes OBJECT-TYPE
   SYNTAX     Unsigned32 (0..4294967295)
   ACCESS     read-only
   STATUS     mandatory
   DESCRIPTION
     "This attribute records the number of bytes in frames with the 
      Discard Eligibility (DE) bit set, looped back to the link since the 
      loopback mode was started."
   DEFVAL     { 0 }
::= { mpanlDlciLbStatsEntry 6 }

mpanlDlciLbRemoteTotalFrm OBJECT-TYPE
   SYNTAX     Unsigned32 (0..4294967295)
   ACCESS     read-only
   STATUS     mandatory
   DESCRIPTION
     "This attribute records the number of frames looped back to the 
      subnet since loopback was last started."
   DEFVAL     { 0 }
::= { mpanlDlciLbStatsEntry 7 }

mpanlDlciLbRemoteTotalBytes OBJECT-TYPE
   SYNTAX     Unsigned32 (0..4294967295)
   ACCESS     read-only
   STATUS     mandatory
   DESCRIPTION
     "This attribute records the number of bytes looped back to the subnet 
      since loopback was last started."
   DEFVAL     { 0 }
::= { mpanlDlciLbStatsEntry 8 }

mpanlDlciLbRemoteFecnFrm OBJECT-TYPE
   SYNTAX     Unsigned32 (0..4294967295)
   ACCESS     read-only
   STATUS     mandatory
   DESCRIPTION
     "This attribute records the number of frames with the Forward 
      Explicit Congestion Notification (FECN) bit set, looped back to the 
      subnet since the loopback mode was started."
   DEFVAL     { 0 }
::= { mpanlDlciLbStatsEntry 9 }

mpanlDlciLbRemoteBecnFrm OBJECT-TYPE
   SYNTAX     Unsigned32 (0..4294967295)
   ACCESS     read-only
   STATUS     mandatory
   DESCRIPTION
     "This attribute records the number of frames with the Backward 
      Explicit Congestion Notification (BECN) bit set, looped back to the 
      subnet since the loopback mode was started."
   DEFVAL     { 0 }
::= { mpanlDlciLbStatsEntry 10 }

mpanlDlciLbRemoteDeFrm OBJECT-TYPE
   SYNTAX     Unsigned32 (0..4294967295)
   ACCESS     read-only
   STATUS     mandatory
   DESCRIPTION
     "This attribute records the number of frames with the Discard 
      Eligibility (DE) bit set, looped back to the subnet since the 
      loopback mode was started."
   DEFVAL     { 0 }
::= { mpanlDlciLbStatsEntry 13 }

mpanlDlciLbRemoteDeBytes OBJECT-TYPE
   SYNTAX     Unsigned32 (0..4294967295)
   ACCESS     read-only
   STATUS     mandatory
   DESCRIPTION
     "This attribute records the number of bytes in frames with the 
      Discard Eligibility (DE) bit set, looped back to the subnet since the 
      loopback mode was started."
   DEFVAL     { 0 }
::= { mpanlDlciLbStatsEntry 14 }

-- 
-- *** THIS SUBTREE CURRENTLY NOT IMPLEMENTED ***
-- 

-- Mpanl/<n> Dlci/<n> Vc
-- This component defines attributes collected by Mpanl/n Dlci/n Vc.

mpanlDlciVc OBJECT IDENTIFIER ::= { mpanlDlci 3 }



mpanlDlciVcRowStatusTable OBJECT-TYPE
   SYNTAX     SEQUENCE OF MpanlDlciVcRowStatusEntry
   ACCESS     not-accessible
   STATUS     mandatory
   DESCRIPTION
     "*** THIS TABLE CURRENTLY NOT IMPLEMENTED ***

      This entry controls the addition and deletion of 
      mpanlDlciVc components."
::= { mpanlDlciVc 1 }

mpanlDlciVcRowStatusEntry OBJECT-TYPE
   SYNTAX     MpanlDlciVcRowStatusEntry
   ACCESS     not-accessible
   STATUS     mandatory
   DESCRIPTION
     "A single entry in the table represents a single 
      mpanlDlciVc component."
   INDEX {
      mpanlIndex,
      mpanlDlciIndex,
      mpanlDlciVcIndex }
::= { mpanlDlciVcRowStatusTable 1 }

MpanlDlciVcRowStatusEntry ::= SEQUENCE {
   mpanlDlciVcRowStatus
      RowStatus,
   mpanlDlciVcComponentName
      DisplayString,
   mpanlDlciVcStorageType
      StorageType,
   mpanlDlciVcIndex
      NonReplicated }

mpanlDlciVcRowStatus OBJECT-TYPE
   SYNTAX     RowStatus 
   ACCESS     read-only
   STATUS     mandatory
   DESCRIPTION
     "This variable is used as the basis for SNMP naming of
      mpanlDlciVc components.
      These components cannot be added nor deleted."
::= { mpanlDlciVcRowStatusEntry 1 }

mpanlDlciVcComponentName OBJECT-TYPE
   SYNTAX     DisplayString 
   ACCESS     read-only
   STATUS     mandatory
   DESCRIPTION
     "This variable provides the component's string name for
      use with the ASCII Console Interface"
::= { mpanlDlciVcRowStatusEntry 2 }

mpanlDlciVcStorageType OBJECT-TYPE
   SYNTAX     StorageType 
   ACCESS     read-only
   STATUS     mandatory
   DESCRIPTION
     "This variable represents the storage type value for the
      mpanlDlciVc tables."
::= { mpanlDlciVcRowStatusEntry 4 }

mpanlDlciVcIndex OBJECT-TYPE
   SYNTAX     NonReplicated 
   ACCESS     not-accessible
   STATUS     mandatory
   DESCRIPTION
     "This variable represents the index for the mpanlDlciVc tables."
::= { mpanlDlciVcRowStatusEntry 10 }

mpanlDlciVcCadTable OBJECT-TYPE
   SYNTAX     SEQUENCE OF MpanlDlciVcCadEntry
   ACCESS     not-accessible
   STATUS     mandatory
   DESCRIPTION
     "*** THIS TABLE CURRENTLY NOT IMPLEMENTED ***

      This group represents operational call data related to Frame Relay 
      Vc. It can be displayed only for Frame Relay Vc which is created by 
      application."
::= { mpanlDlciVc 10 }

mpanlDlciVcCadEntry OBJECT-TYPE
   SYNTAX     MpanlDlciVcCadEntry
   ACCESS     not-accessible
   STATUS     mandatory
   DESCRIPTION
     "An entry in the mpanlDlciVcCadTable."
   INDEX {
      mpanlIndex,
      mpanlDlciIndex,
      mpanlDlciVcIndex }
::= { mpanlDlciVcCadTable 1 }

MpanlDlciVcCadEntry ::= SEQUENCE {
   mpanlDlciVcType
      INTEGER,
   mpanlDlciVcState
      INTEGER,
   mpanlDlciVcPreviousState
      INTEGER,
   mpanlDlciVcDiagnosticCode
      Unsigned32,
   mpanlDlciVcPreviousDiagnosticCode
      Unsigned32,
   mpanlDlciVcCalledNpi
      INTEGER,
   mpanlDlciVcCalledDna
      DigitString,
   mpanlDlciVcCalledLcn
      Unsigned32,
   mpanlDlciVcCallingNpi
      INTEGER,
   mpanlDlciVcCallingDna
      DigitString,
   mpanlDlciVcCallingLcn
      Unsigned32,
   mpanlDlciVcAccountingEnabled
      INTEGER,
   mpanlDlciVcFastSelectCall
      INTEGER,
   mpanlDlciVcPathReliability
      INTEGER,
   mpanlDlciVcAccountingEnd
      INTEGER,
   mpanlDlciVcPriority
      INTEGER,
   mpanlDlciVcSegmentSize
      Unsigned32,
   mpanlDlciVcMaxSubnetPktSize
      Unsigned32,
   mpanlDlciVcRcosToNetwork
      INTEGER,
   mpanlDlciVcRcosFromNetwork
      INTEGER,
   mpanlDlciVcEmissionPriorityToNetwork
      INTEGER,
   mpanlDlciVcEmissionPriorityFromNetwork
      INTEGER,
   mpanlDlciVcDataPath
      AsciiString }

mpanlDlciVcType OBJECT-TYPE
   SYNTAX     INTEGER  {
                 svc(0),
                 pvc(1),
                 spvc(2) }
   ACCESS     read-only
   STATUS     mandatory
   DESCRIPTION
     "This attribute displays the type of call, pvc,svc or spvc."
::= { mpanlDlciVcCadEntry 1 }

mpanlDlciVcState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the state of call control. P5 state is not 
      supported but is listed for completness. Transitions from one state to 
      another take very short time. state most often displayed is 
      dataTransferP4."
::= { mpanlDlciVcCadEntry 2 }

mpanlDlciVcPreviousState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the previous state of call control. This is a 
      valuable field to determine how the processing is progressing."
::= { mpanlDlciVcCadEntry 3 }

mpanlDlciVcDiagnosticCode OBJECT-TYPE
   SYNTAX     Unsigned32 (0..255)
   ACCESS     read-only
   STATUS     mandatory
   DESCRIPTION
     "This attribute displays the internal substate of call control. It is used 
      to further refine state of call processing."
::= { mpanlDlciVcCadEntry 4 }

mpanlDlciVcPreviousDiagnosticCode OBJECT-TYPE
   SYNTAX     Unsigned32 (0..255)
   ACCESS     read-only
   STATUS     mandatory
   DESCRIPTION
     "This attribute displays the internal substate of call control. It is used 
      to further refine state of call processing."
::= { mpanlDlciVcCadEntry 5 }

mpanlDlciVcCalledNpi OBJECT-TYPE
   SYNTAX     INTEGER  {
                 x121(0),
                 e164(1) }
   ACCESS     read-only
   STATUS     mandatory
   DESCRIPTION
     "This attribute displays the Numbering Plan Indicator (NPI) of the 
      called end."
::= { mpanlDlciVcCadEntry 6 }

mpanlDlciVcCalledDna OBJECT-TYPE
   SYNTAX     DigitString (SIZE (1..15))
   ACCESS     read-only
   STATUS     mandatory
   DESCRIPTION
     "This attribute displays the Data Network Address (Dna) of the 
      called (destination) DTE to which this call is sent. This address if 
      defined at recieving end will complete Vc connection."
::= { mpanlDlciVcCadEntry 7 }

mpanlDlciVcCalledLcn OBJECT-TYPE
   SYNTAX     Unsigned32 (1..65535)
   ACCESS     read-only
   STATUS     mandatory
   DESCRIPTION
     "This attribute displays the Logical Channel Number of the called 
      end. It is valid only after both ends of Vc exchanged relevant 
      information."
::= { mpanlDlciVcCadEntry 8 }

mpanlDlciVcCallingNpi OBJECT-TYPE
   SYNTAX     INTEGER  {
                 x121(0),
                 e164(1) }
   ACCESS     read-only
   STATUS     mandatory
   DESCRIPTION
     "This attribute displays the Numbering Plan Indicator (NPI) of the 
      calling end."
::= { mpanlDlciVcCadEntry 9 }

mpanlDlciVcCallingDna OBJECT-TYPE
   SYNTAX     DigitString (SIZE (1..15))
   ACCESS     read-only
   STATUS     mandatory
   DESCRIPTION
     "This attribute displays the Data Network Address (Dna) of the 
      calling end."
::= { mpanlDlciVcCadEntry 10 }

mpanlDlciVcCallingLcn OBJECT-TYPE
   SYNTAX     Unsigned32 (1..65535)
   ACCESS     read-only
   STATUS     mandatory
   DESCRIPTION
     "This attribute displays the Logical Channel Number of the calling 
      end."
::= { mpanlDlciVcCadEntry 11 }

mpanlDlciVcAccountingEnabled OBJECT-TYPE
   SYNTAX     INTEGER  {
                 yes(0),
                 no(1) }
   ACCESS     read-only
   STATUS     mandatory
   DESCRIPTION
     "This attribute indicates that this optional section of accounting 
      record is suppressed or permitted. If accountingEnabled is yes, 
      conditions for generation of accounting record were met. These 
      conditions include billing options, vc recovery conditions and 
      Module wide accounting data options."
::= { mpanlDlciVcCadEntry 12 }

mpanlDlciVcFastSelectCall OBJECT-TYPE
   SYNTAX     INTEGER  {
                 no(0),
                 yes(1) }
   ACCESS     read-only
   STATUS     mandatory
   DESCRIPTION
     "This attribute displays that this is a fast select call."
::= { mpanlDlciVcCadEntry 13 }

mpanlDlciVcPathReliability OBJECT-TYPE
   SYNTAX     INTEGER  {
                 high(0),
                 normal(1) }
   ACCESS     read-only
   STATUS     mandatory
   DESCRIPTION
     "This attribute displays the path reliability."
::= { mpanlDlciVcCadEntry 19 }

mpanlDlciVcAccountingEnd OBJECT-TYPE
   SYNTAX     INTEGER  {
                 callingEnd(0),
                 calledEnd(1) }
   ACCESS     read-only
   STATUS     mandatory
   DESCRIPTION
     "This attribute indicates if this end should generate an accounting 
      record. Normally, callingEnd is the end to generate an accounting 
      record."
::= { mpanlDlciVcCadEntry 20 }

mpanlDlciVcPriority OBJECT-TYPE
   SYNTAX     INTEGER  {
                 normal(0),
                 high(1) }
   ACCESS     read-only
   STATUS     mandatory
   DESCRIPTION
     "This attribute displays whether the call is a normal or a high 
      priority call."
::= { mpanlDlciVcCadEntry 21 }

mpanlDlciVcSegmentSize OBJECT-TYPE
   SYNTAX     Unsigned32 (0..4096)
   ACCESS     read-only
   STATUS     mandatory
   DESCRIPTION
     "This attribute displays the segment size (in bytes) used on the call. 
      It is used to calculate the number of segments transmitted and 
      received."
::= { mpanlDlciVcCadEntry 22 }

mpanlDlciVcMaxSubnetPktSize OBJECT-TYPE
   SYNTAX     Unsigned32 (0..4096)
   ACCESS     read-only
   STATUS     mandatory
   DESCRIPTION
     "This attribute indicates the maximum packet size allowed on the Vc."
::= { mpanlDlciVcCadEntry 27 }

mpanlDlciVcRcosToNetwork OBJECT-TYPE
   SYNTAX     INTEGER  {
                 throughput(0),
                 delay(1),
                 multimedia(2) }
   ACCESS     read-only
   STATUS     mandatory
   DESCRIPTION
     "This attribute indicates the routing metric routing class of service to
      the network."
::= { mpanlDlciVcCadEntry 28 }

mpanlDlciVcRcosFromNetwork OBJECT-TYPE
   SYNTAX     INTEGER  {
                 throughput(0),
                 delay(1),
                 multimedia(2) }
   ACCESS     read-only
   STATUS     mandatory
   DESCRIPTION
     "This attribute displays the routing metric Routing Class of Service 
      from the Network."
::= { mpanlDlciVcCadEntry 29 }

mpanlDlciVcEmissionPriorityToNetwork OBJECT-TYPE
   SYNTAX     INTEGER  {
                 normal(0),
                 high(1),
                 interrupting(2) }
   ACCESS     read-only
   STATUS     mandatory
   DESCRIPTION
     "This attribute displays the network internal emission priotity to the 
      network."
::= { mpanlDlciVcCadEntry 30 }

mpanlDlciVcEmissionPriorityFromNetwork OBJECT-TYPE
   SYNTAX     INTEGER  {
                 normal(0),
                 high(1),
                 interrupting(2) }
   ACCESS     read-only
   STATUS     mandatory
   DESCRIPTION
     "This attribute displays the network internal emission priotity from 
      the network."
::= { mpanlDlciVcCadEntry 31 }

mpanlDlciVcDataPath OBJECT-TYPE
   SYNTAX     AsciiString (SIZE (0..32))
   ACCESS     read-only
   STATUS     mandatory
   DESCRIPTION
     "This attribute indicates the data path used by the connection. The 
      data path is provisioned in Dna and DirectCall components. The 
      displayed value of this attribute can be different from the 
      provisioned value.
      
      If the connection is using dprsOnly data path, the string 
      dprsOnly is displayed. (dynamic packet routing system)
      
      If the connection is using dprsMcsOnly data path, the string 
      dprsMcsOnly is displayed.
      
      If the connection is using dprsMcsFirst data path, the string 
      dprsMcsFirst is displayed."
::= { mpanlDlciVcCadEntry 32 }

mpanlDlciVcIntdTable OBJECT-TYPE
   SYNTAX     SEQUENCE OF MpanlDlciVcIntdEntry
   ACCESS     not-accessible
   STATUS     mandatory
   DESCRIPTION
     "*** THIS TABLE CURRENTLY NOT IMPLEMENTED ***

      This group defines display of interval data collected by Vc. Data in 
      this group is variable and may depend on time when this display 
      command is issued."
::= { mpanlDlciVc 11 }

mpanlDlciVcIntdEntry OBJECT-TYPE
   SYNTAX     MpanlDlciVcIntdEntry
   ACCESS     not-accessible
   STATUS     mandatory
   DESCRIPTION
     "An entry in the mpanlDlciVcIntdTable."
   INDEX {
      mpanlIndex,
      mpanlDlciIndex,
      mpanlDlciVcIndex }
::= { mpanlDlciVcIntdTable 1 }

MpanlDlciVcIntdEntry ::= SEQUENCE {
   mpanlDlciVcCallReferenceNumber
      Hex,
   mpanlDlciVcElapsedTimeTillNow
      Unsigned32,
   mpanlDlciVcSegmentsRx
      Unsigned32,
   mpanlDlciVcSegmentsSent
      Unsigned32,
   mpanlDlciVcStartTime
      EnterpriseDateAndTime }

mpanlDlciVcCallReferenceNumber OBJECT-TYPE
   SYNTAX     Hex (0..16777215)
   ACCESS     read-only
   STATUS     mandatory
   DESCRIPTION
     "This attribute displays the call reference number which is a unique 
      number generated by the switch.The same Call Reference Number 
      is stored in the interval data (accounting record) at both ends of the 
      call. It can be used as one of the attributes in matching duplicate 
      records generated at each end of the call."
::= { mpanlDlciVcIntdEntry 1 }

mpanlDlciVcElapsedTimeTillNow OBJECT-TYPE
   SYNTAX     Unsigned32 (0..16777215)
   ACCESS     read-only
   STATUS     mandatory
   DESCRIPTION
     "This attribute displays the elapsed time representing the period of 
      this interval data. It is elapsed time in 0.1 second increments since 
      Vc started."
::= { mpanlDlciVcIntdEntry 2 }

mpanlDlciVcSegmentsRx OBJECT-TYPE
   SYNTAX     Unsigned32 (0..16777215)
   ACCESS     read-only
   STATUS     mandatory
   DESCRIPTION
     "This attribute displays the number of segments received at the time 
      command was issued. This is the segment received count 
      maintained by accounting at each end of the Vc. This counter is 
      updated only when the packet cannot be successfully delivered out 
      of the sink Vc and to the sink AP Conditions in which packets may 
      be discarded by the sink Vc include: missing packets due to subnet 
      discards, segmentation protocol violations due to subnet discard, 
      duplicated and out-of-ranged packets and packets that arrive while 
      Vc is in path recovery state."
::= { mpanlDlciVcIntdEntry 3 }

mpanlDlciVcSegmentsSent OBJECT-TYPE
   SYNTAX     Unsigned32 (0..16777215)
   ACCESS     read-only
   STATUS     mandatory
   DESCRIPTION
     "This attribute displays the number of segments sent at the time 
      command was issued. This is the segment sent count maintained by 
      accounting at the source Vc. Vc only counts packets that Vc thinks 
      can be delivered successfully into the subnet. In reality, these 
      packets may be dropped by trunking, for instance. This counter is 
      not updated when splitting fails, when Vc is in a path recovery state, 
      when packet forwarding fails to forward this packet and when 
      subsequent packets have to be discarded as we want to minimize the 
      chance of out-of-sequence and do not intentionally send out-of-
      sequenced packets into the subnet."
::= { mpanlDlciVcIntdEntry 4 }

mpanlDlciVcStartTime OBJECT-TYPE
   SYNTAX     EnterpriseDateAndTime (SIZE (0 | 19))
   ACCESS     read-only
   STATUS     mandatory
   DESCRIPTION
     "This attribute displays the start time of this interval period. If Vc 
      spans 12 hour time or time of day change startTime reflects new 
      time as recorded at 12 hour periods or time of day changes."
::= { mpanlDlciVcIntdEntry 5 }

mpanlDlciVcFrdTable OBJECT-TYPE
   SYNTAX     SEQUENCE OF MpanlDlciVcFrdEntry
   ACCESS     not-accessible
   STATUS     mandatory
   DESCRIPTION
     "*** THIS TABLE CURRENTLY NOT IMPLEMENTED ***

      This group defines Frame Relay attributes collected by Frame Relay 
      Vc.
      The purpose of Vc attributes is to aid end users and verification 
      people to understand the Vc internal behavior. This is particularly 
      useful when the network has experienced abnormality and we want 
      to isolate problems and pinpoint trouble spots. 
      Attributes are collected on a per Vc basis. Until a need is identified, 
      statistics are not collected at a processor level. Each attribute is 
      stored in a 32 bit field and is initialized to zero when a Vc enters 
      into the data transfer state. When a PVC is disconnected and then 
      connected again, the attributes will be reset. Attributes cannot be 
      reset through other methods. 
      Frame Relay Vc uses a best effort data packet delivery protocol and 
      a different packet segmentation and combination methods from the 
      General Vc. The Frame Relay Vc uses the same call setup and 
      control mechanism (e.g. the support of non-flow control data 
      packets) as in a General Vc. Most General Vc statistics and internal 
      variables are used in a Frame Relay Vc and are displayed by 
      software developers"
::= { mpanlDlciVc 12 }

mpanlDlciVcFrdEntry OBJECT-TYPE
   SYNTAX     MpanlDlciVcFrdEntry
   ACCESS     not-accessible
   STATUS     mandatory
   DESCRIPTION
     "An entry in the mpanlDlciVcFrdTable."
   INDEX {
      mpanlIndex,
      mpanlDlciIndex,
      mpanlDlciVcIndex }
::= { mpanlDlciVcFrdTable 1 }

MpanlDlciVcFrdEntry ::= SEQUENCE {
   mpanlDlciVcFrmCongestedToSubnet
      Unsigned32,
   mpanlDlciVcCannotForwardToSubnet
      Unsigned32,
   mpanlDlciVcNotDataXferToSubnet
      Unsigned32,
   mpanlDlciVcOutOfRangeFrmFromSubnet
      Unsigned32,
   mpanlDlciVcCombErrorsFromSubnet
      Unsigned32,
   mpanlDlciVcDuplicatesFromSubnet
      Unsigned32,
   mpanlDlciVcNotDataXferFromSubnet
      Unsigned32,
   mpanlDlciVcFrmLossTimeouts
      Unsigned32,
   mpanlDlciVcOoSeqByteCntExceeded
      Unsigned32,
   mpanlDlciVcPeakOoSeqPktCount
      Unsigned32,
   mpanlDlciVcPeakOoSeqFrmForwarded
      Unsigned32,
   mpanlDlciVcSendSequenceNumber
      Unsigned32,
   mpanlDlciVcPktRetryTimeouts
      Unsigned32,
   mpanlDlciVcPeakRetryQueueSize
      Unsigned32,
   mpanlDlciVcSubnetRecoveries
      Unsigned32,
   mpanlDlciVcOoSeqPktCntExceeded
      Unsigned32,
   mpanlDlciVcPeakOoSeqByteCount
      Unsigned32 }

mpanlDlciVcFrmCongestedToSubnet OBJECT-TYPE
   SYNTAX     Unsigned32 (0..5000)
   ACCESS     read-only
   STATUS     mandatory
   DESCRIPTION
     "This attribute displays the number of frames from link discarded 
      due to lack of resources. It keeps track of the number of frames 
      from link that have to be discarded. The discard reasons include 
      insufficient memory for splitting the frame into smaller subnet 
      packet size."
::= { mpanlDlciVcFrdEntry 2 }

mpanlDlciVcCannotForwardToSubnet OBJECT-TYPE
   SYNTAX     Unsigned32 (0..5000)
   ACCESS     read-only
   STATUS     mandatory
   DESCRIPTION
     "This attribute displays the number of discarded packets that can not 
      be forwarded into the subnet because of subnet congestion.
      Number of frames from link discarded due to failure in forwarding 
      a packet from Vc into the subnet.- This attribute is increased when 
      packet forwarding fails to forward a packet into the subnet. If a 
      frame is split into multiple subnet packets and a partial packet has 
      to be discarded, all subsequent partial packets that have not yet been 
      delivered to the subnet will be discarded as well."
::= { mpanlDlciVcFrdEntry 3 }

mpanlDlciVcNotDataXferToSubnet OBJECT-TYPE
   SYNTAX     Unsigned32 (0..5000)
   ACCESS     read-only
   STATUS     mandatory
   DESCRIPTION
     "This attribute records the number of frames from link discarded 
      when the Vc tries to recover from internal path failure."
::= { mpanlDlciVcFrdEntry 4 }

mpanlDlciVcOutOfRangeFrmFromSubnet OBJECT-TYPE
   SYNTAX     Unsigned32 (0..5000)
   ACCESS     read-only
   STATUS     mandatory
   DESCRIPTION
     "This attribute displays the number of frames from subnet discarded 
      due to out of sequence range for arriving too late."
::= { mpanlDlciVcFrdEntry 5 }

mpanlDlciVcCombErrorsFromSubnet OBJECT-TYPE
   SYNTAX     Unsigned32 (0..5000)
   ACCESS     read-only
   STATUS     mandatory
   DESCRIPTION
     "This attribute records the number of subnet packets discarded at the 
      sink Vc due to the Vc segmentation and combination protocol error. 
      Usually, this occurs when the subnet discards packets and thus this 
      statistics can be used to guest the number of subnet packets that are 
      not delivered to the Vc. It cannot be used as an actual measure 
      because some subnet packets may have been delivered to Vc but 
      have to be discarded because these are partial packets to a frame in 
      which some other partial packets have not been properly delivered 
      to Vc"
::= { mpanlDlciVcFrdEntry 6 }

mpanlDlciVcDuplicatesFromSubnet OBJECT-TYPE
   SYNTAX     Unsigned32 (0..5000)
   ACCESS     read-only
   STATUS     mandatory
   DESCRIPTION
     "This attribute displays the number of subnet packets discarded due 
      to duplication. Although packets are not retransmitted by the Frame 
      Relay Vc, it is possible for the subnet to retransmit packets. When 
      packets are out-of-sequenced and copies of the same packets arrive, 
      then this attribute is increased."
::= { mpanlDlciVcFrdEntry 7 }

mpanlDlciVcNotDataXferFromSubnet OBJECT-TYPE
   SYNTAX     Unsigned32 (0..5000)
   ACCESS     read-only
   STATUS     mandatory
   DESCRIPTION
     "This attribute displays the number of subnet packets discarded when 
      data transfer is suspended in Vc recovery."
::= { mpanlDlciVcFrdEntry 8 }

mpanlDlciVcFrmLossTimeouts OBJECT-TYPE
   SYNTAX     Unsigned32 (0..5000)
   ACCESS     read-only
   STATUS     mandatory
   DESCRIPTION
     "This attribute displays the number of lost frame timer expiries.
      When this count is excessive, the network is very congested and 
      packets have been discarded in the subnet."
::= { mpanlDlciVcFrdEntry 9 }

mpanlDlciVcOoSeqByteCntExceeded OBJECT-TYPE
   SYNTAX     Unsigned32 (0..5000)
   ACCESS     read-only
   STATUS     mandatory
   DESCRIPTION
     "This attribute displays the number times that the out of sequence 
      byte threshold is exceeded. When the threshold is exceeded, this 
      condition is treated as if the loss frame timer has expired and all 
      frames queued at the sink Vc are delivered to the AP. We need to 
      keep this count to examine if the threshold is engineered properly. 
      This should be used in conjunction with the peak value of out-of-
      sequenced queue and the number of times the loss frame timer has 
      expired. This count should be relatively small when compared with 
      loss frame timer expiry count."
::= { mpanlDlciVcFrdEntry 10 }

mpanlDlciVcPeakOoSeqPktCount OBJECT-TYPE
   SYNTAX     Unsigned32 (0..5000)
   ACCESS     read-only
   STATUS     mandatory
   DESCRIPTION
     "This attribute displays the frame relay peak packet count of the out 
      of sequence queue. This attribute records the maximum queue 
      length of the out-of-sequenced queue. The counter can be used to 
      deduce the message buffer requirement on a Vc."
::= { mpanlDlciVcFrdEntry 11 }

mpanlDlciVcPeakOoSeqFrmForwarded OBJECT-TYPE
   SYNTAX     Unsigned32 (0..5000)
   ACCESS     read-only
   STATUS     mandatory
   DESCRIPTION
     "This attribute displays the frame relay peak size of the 
      sequence packet queue. The subnet may deliver packets out-of-
      sequenced. These packets are then queued in an out-of-sequenced 
      queue, waiting for a packet with the expected sequence number to 
      come. When that packet arrives, this attribute records the maximum 
      number of packets that were out-of-sequenced, but now have 
      become in-sequenced. The statistics is used to measure expected 
      queue size due to normal subnet packet disorder (not due to subnet 
      packet discard). Current implementation also uses this statistics to 
      set a maximum size for the out-of-sequenced queue."
::= { mpanlDlciVcFrdEntry 12 }

mpanlDlciVcSendSequenceNumber OBJECT-TYPE
   SYNTAX     Unsigned32 (0..5000)
   ACCESS     read-only
   STATUS     mandatory
   DESCRIPTION
     "This attribute displays the Vc internal packet's send sequence 
      number. Note that a 'packet' in this context, may be either a user 
      data packet, or an OAM frame."
::= { mpanlDlciVcFrdEntry 13 }

mpanlDlciVcPktRetryTimeouts OBJECT-TYPE
   SYNTAX     Unsigned32 (0..5000)
   ACCESS     read-only
   STATUS     mandatory
   DESCRIPTION
     "This attribute displays the number of packets which have 
      retransmission time-outs. When this count is excessive, the network 
      is very congested and packets have been discarded in the subnet."
::= { mpanlDlciVcFrdEntry 15 }

mpanlDlciVcPeakRetryQueueSize OBJECT-TYPE
   SYNTAX     Unsigned32 (0..5000)
   ACCESS     read-only
   STATUS     mandatory
   DESCRIPTION
     "This attribute displays the peak size of retransmission queue.
      This attribute is used as an indicator of the acknowledgment 
      behavior across the subnet. Records the largest body of 
      unacknowledged packets."
::= { mpanlDlciVcFrdEntry 16 }

mpanlDlciVcSubnetRecoveries OBJECT-TYPE
   SYNTAX     Unsigned32 (0..5000)
   ACCESS     read-only
   STATUS     mandatory
   DESCRIPTION
     "This attribute displays the number of successful Vc recovery 
      attempts."
::= { mpanlDlciVcFrdEntry 17 }

mpanlDlciVcOoSeqPktCntExceeded OBJECT-TYPE
   SYNTAX     Unsigned32 (0..255)
   ACCESS     read-only
   STATUS     mandatory
   DESCRIPTION
     "This attribute displays the number times that the out of sequence 
      packet threshold is exceeded. When the threshold is exceeded, this 
      condition is treated as if the loss frame timer has expired and all 
      frames queued at the sink Vc are delivered to the AP. We need to 
      keep this count to examine if the threshold is engineered properly. 
      This should be used in conjunction with the peak value of out-of-
      sequenced queue and the number of times the loss frame timer has 
      expired. This count should be relatively small when compared with 
      loss frame timer expiry count."
::= { mpanlDlciVcFrdEntry 19 }

mpanlDlciVcPeakOoSeqByteCount OBJECT-TYPE
   SYNTAX     Unsigned32 (0..50000)
   ACCESS     read-only
   STATUS     mandatory
   DESCRIPTION
     "This attribute displays the frame relay peak byte count of the out of 
      sequence queue. This attribute records the maximum queue length 
      of the out-of-sequenced queue. The counter can be used to deduce 
      the message buffer requirement on a Vc."
::= { mpanlDlciVcFrdEntry 20 }

mpanlDlciVcDmepTable OBJECT-TYPE
   SYNTAX     SEQUENCE OF MpanlDlciVcDmepEntry
   ACCESS     not-accessible
   STATUS     mandatory
   DESCRIPTION
     "*** THIS TABLE CURRENTLY NOT IMPLEMENTED ***

      This attribute displays the data path used by the connection. Data 
      path is provisioned in Dna and DirectCall components.
      
      If the connection is using dprsOnly data path, this attribute is 
      empty.
      
      If the connection is using dprsMcsOnly or dprsMcsFirst data path, 
      this attribute displays component name of the dprsMcsEndPoint."
::= { mpanlDlciVc 417 }

mpanlDlciVcDmepEntry OBJECT-TYPE
   SYNTAX     MpanlDlciVcDmepEntry
   ACCESS     not-accessible
   STATUS     mandatory
   DESCRIPTION
     "An entry in the mpanlDlciVcDmepTable."
   INDEX {
      mpanlIndex,
      mpanlDlciIndex,
      mpanlDlciVcIndex,
      mpanlDlciVcDmepValue }
::= { mpanlDlciVcDmepTable 1 }

MpanlDlciVcDmepEntry ::= SEQUENCE {
   mpanlDlciVcDmepValue
      RowPointer }

mpanlDlciVcDmepValue OBJECT-TYPE
   SYNTAX     RowPointer 
   ACCESS     read-only
   STATUS     mandatory
   DESCRIPTION
     "This variable represents both the value and the index for the
      mpanlDlciVcDmepTable."
::= { mpanlDlciVcDmepEntry 1 }

-- 
-- *** THIS SUBTREE CURRENTLY NOT IMPLEMENTED ***
-- 

-- Mpanl/n Dlci/m LCo
-- This component contains all of the operation attributes for a Path 
-- Oriented Logical Connection.

mpanlDlciLCo OBJECT IDENTIFIER ::= { mpanlDlci 4 }



mpanlDlciLCoRowStatusTable OBJECT-TYPE
   SYNTAX     SEQUENCE OF MpanlDlciLCoRowStatusEntry
   ACCESS     not-accessible
   STATUS     mandatory
   DESCRIPTION
     "*** THIS TABLE CURRENTLY NOT IMPLEMENTED ***

      This entry controls the addition and deletion of 
      mpanlDlciLCo components."
::= { mpanlDlciLCo 1 }

mpanlDlciLCoRowStatusEntry OBJECT-TYPE
   SYNTAX     MpanlDlciLCoRowStatusEntry
   ACCESS     not-accessible
   STATUS     mandatory
   DESCRIPTION
     "A single entry in the table represents a single 
      mpanlDlciLCo component."
   INDEX {
      mpanlIndex,
      mpanlDlciIndex,
      mpanlDlciLCoIndex }
::= { mpanlDlciLCoRowStatusTable 1 }

MpanlDlciLCoRowStatusEntry ::= SEQUENCE {
   mpanlDlciLCoRowStatus
      RowStatus,
   mpanlDlciLCoComponentName
      DisplayString,
   mpanlDlciLCoStorageType
      StorageType,
   mpanlDlciLCoIndex
      NonReplicated }

mpanlDlciLCoRowStatus OBJECT-TYPE
   SYNTAX     RowStatus 
   ACCESS     read-only
   STATUS     mandatory
   DESCRIPTION
     "This variable is used as the basis for SNMP naming of
      mpanlDlciLCo components.
      These components cannot be added nor deleted."
::= { mpanlDlciLCoRowStatusEntry 1 }

mpanlDlciLCoComponentName OBJECT-TYPE
   SYNTAX     DisplayString 
   ACCESS     read-only
   STATUS     mandatory
   DESCRIPTION
     "This variable provides the component's string name for
      use with the ASCII Console Interface"
::= { mpanlDlciLCoRowStatusEntry 2 }

mpanlDlciLCoStorageType OBJECT-TYPE
   SYNTAX     StorageType 
   ACCESS     read-only
   STATUS     mandatory
   DESCRIPTION
     "This variable represents the storage type value for the
      mpanlDlciLCo tables."
::= { mpanlDlciLCoRowStatusEntry 4 }

mpanlDlciLCoIndex OBJECT-TYPE
   SYNTAX     NonReplicated 
   ACCESS     not-accessible
   STATUS     mandatory
   DESCRIPTION
     "This variable represents the index for the mpanlDlciLCo tables."
::= { mpanlDlciLCoRowStatusEntry 10 }

mpanlDlciLCoPathDataTable OBJECT-TYPE
   SYNTAX     SEQUENCE OF MpanlDlciLCoPathDataEntry
   ACCESS     not-accessible
   STATUS     mandatory
   DESCRIPTION
     "*** THIS TABLE CURRENTLY NOT IMPLEMENTED ***

      This group contains all operational attributes for the path oriented 
      LCo."
::= { mpanlDlciLCo 10 }

mpanlDlciLCoPathDataEntry OBJECT-TYPE
   SYNTAX     MpanlDlciLCoPathDataEntry
   ACCESS     not-accessible
   STATUS     mandatory
   DESCRIPTION
     "An entry in the mpanlDlciLCoPathDataTable."
   INDEX {
      mpanlIndex,
      mpanlDlciIndex,
      mpanlDlciLCoIndex }
::= { mpanlDlciLCoPathDataTable 1 }

MpanlDlciLCoPathDataEntry ::= SEQUENCE {
   mpanlDlciLCoState
      INTEGER,
   mpanlDlciLCoEnd
      INTEGER,
   mpanlDlciLCoCostMetric
      Unsigned32,
   mpanlDlciLCoDelayMetric
      Unsigned32,
   mpanlDlciLCoRoundTripDelay
      Unsigned32,
   mpanlDlciLCoSetupPriority
      Unsigned32,
   mpanlDlciLCoHoldingPriority
      Unsigned32,
   mpanlDlciLCoRequiredTxBandwidth
      Gauge32,
   mpanlDlciLCoRequiredRxBandwidth
      Gauge32,
   mpanlDlciLCoRequiredTrafficType
      INTEGER,
   mpanlDlciLCoPermittedTrunkTypes
      OCTET STRING,
   mpanlDlciLCoRequiredSecurity
      Unsigned32,
   mpanlDlciLCoRequiredCustomerParameter
      Unsigned32,
   mpanlDlciLCoEmissionPriority
      Unsigned32,
   mpanlDlciLCoDiscardPriority
      Unsigned32,
   mpanlDlciLCoRetryCount
      Unsigned32,
   mpanlDlciLCoPathFailureCount
      Unsigned32,
   mpanlDlciLCoReasonForNoRoute
      INTEGER,
   mpanlDlciLCoLastTearDownReason
      INTEGER,
   mpanlDlciLCoPathFailureAction
      INTEGER,
   mpanlDlciLCoBumpPreference
      INTEGER,
   mpanlDlciLCoOptimization
      INTEGER,
   mpanlDlciLCoPathUpDateTime
      EnterpriseDateAndTime }

mpanlDlciLCoState OBJECT-TYPE
   SYNTAX     INTEGER  {
                 pathDown(0),
                 selectingRoute(1),
                 connecting(2),
                 pathUp(3),
                 pathDownRetrying(4) }
   ACCESS     read-only
   STATUS     mandatory
   DESCRIPTION
     "This attribute reflects the current state of the connection. The 
      pathDown state indicates that the application has not yet signalled 
      for a path. The selectingRoute state occurs when a request has been 
      sent to the route selector and it has not yet responded. The 
      connectingState occurs while a path is being established. The 
      pathUp state is the normal operational state of a path. The 
      pathDownRetrying state indicates a path that attempted route 
      selection but received no route and is now waiting to retry route 
      selection again."
::= { mpanlDlciLCoPathDataEntry 1 }

mpanlDlciLCoEnd OBJECT-TYPE
   SYNTAX     INTEGER  {
                 calling(0),
                 called(1) }
   ACCESS     read-only
   STATUS     mandatory
   DESCRIPTION
     "This attribute identifies whether this is the calling or called end of 
      the path."
::= { mpanlDlciLCoPathDataEntry 3 }

mpanlDlciLCoCostMetric OBJECT-TYPE
   SYNTAX     Unsigned32 (0..65535)
   ACCESS     read-only
   STATUS     mandatory
   DESCRIPTION
     "This attribute gives the route's total cost metric. It is calculated as 
      the sum of the cost metric of all trunks in the path at the time the 
      connection was established. The cost metric of a trunk is defined by 
      the trunkCost attribute of the Trunk component. The costMetric for 
      an LCo that is originated and terminated on the same module is 0."
::= { mpanlDlciLCoPathDataEntry 4 }

mpanlDlciLCoDelayMetric OBJECT-TYPE
   SYNTAX     Unsigned32 (0..100000)
   ACCESS     read-only
   STATUS     mandatory
   DESCRIPTION
     "This attribute gives the total delay of the route as the one way delay 
      for a 512 byte packet. It is calculated as the sum of the delays of all 
      trunks in the path stored in topology at the time the connection was 
      established. The delay for an LCo that is originated and terminated 
      on the same module is 0."
::= { mpanlDlciLCoPathDataEntry 5 }

mpanlDlciLCoRoundTripDelay OBJECT-TYPE
   SYNTAX     Unsigned32 (0..200000)
   ACCESS     read-only
   STATUS     mandatory
   DESCRIPTION
     "This attribute contains the time taken for a packet (cell) of 44 bytes 
      to be transmitted to the remote LCo and return to this LCo. The 
      number reported is given in milliseconds to the nearest millisecond. 
      A value of one millisecond is reported if the time is less than 1 
      millisecond even though the delay may be less than 1 millisecond 
      when the LCo is originated and terminated on the same module."
::= { mpanlDlciLCoPathDataEntry 6 }

mpanlDlciLCoSetupPriority OBJECT-TYPE
   SYNTAX     Unsigned32 (0..4)
   ACCESS     read-only
   STATUS     mandatory
   DESCRIPTION
     "This attribute gives the priority at which the current path is 
      established. Zero is the highest priority and four is the lowest. The 
      holdingPriority, a complementary attribute of this component, 
      indicates the priority a path maintains once it is established."
::= { mpanlDlciLCoPathDataEntry 7 }

mpanlDlciLCoHoldingPriority OBJECT-TYPE
   SYNTAX     Unsigned32 (0..4)
   ACCESS     read-only
   STATUS     mandatory
   DESCRIPTION
     "This attribute gives the priority at which a path holds its current 
      path once the path is established. Zero is the highest priority and 
      four is the lowest. The setupPriority, a complementary attribute, 
      indicates the priority of a path at establishment time."
::= { mpanlDlciLCoPathDataEntry 8 }

mpanlDlciLCoRequiredTxBandwidth OBJECT-TYPE
   SYNTAX     Gauge32 (0..2048000)
   ACCESS     read-only
   STATUS     mandatory
   DESCRIPTION
     "This attribute gives the actual bandwidth (in bits per second) 
      reserved by this path on each of the trunks of its route. This attribute 
      represents the bandwidth for traffic outgoing to the remote end 
      point. The originating end of the connection determines this value."
::= { mpanlDlciLCoPathDataEntry 9 }

mpanlDlciLCoRequiredRxBandwidth OBJECT-TYPE
   SYNTAX     Gauge32 (0..2048000)
   ACCESS     read-only
   STATUS     mandatory
   DESCRIPTION
     "This attribute gives the actual bandwidth (in bits per second) 
      reserved by this path on each of trunks of its route. This attribute 
      represents the bandwidth for traffic incoming from the remote end 
      point. The originating end of the connection determines this value"
::= { mpanlDlciLCoPathDataEntry 10 }

mpanlDlciLCoRequiredTrafficType OBJECT-TYPE
   SYNTAX     INTEGER  {
                 voice(0),
                 data(1),
                 video(2),
                 trafficType1(3),
                 trafficType2(4),
                 trafficType3(5),
                 trafficType4(6),
                 trafficType5(7) }
   ACCESS     read-only
   STATUS     mandatory
   DESCRIPTION
     "This operational attribute indicates the type of traffic transmitted 
      over the path. There are eight possible traffic types, and the path can 
      transmit only one of them. The originating end of the connection 
      determines the type. These are arbitrary designations for traffic 
      type. The voice, data and video traffic types are defined, and five 
      other arbitrary traffic types can be defined by the network 
      administration. This attribute is used in the route selection process 
      to restrict the route to trunks that support this traffic type. The 
      supportedTrafficType trunk attribute lists all the types of traffic 
      allowed on the trunk. For example, if requiredTrafficType is 
      specified as trafficType1 then only trunks that include trafficType1 
      in supportedTrafficType, will be candidates for this connection."
::= { mpanlDlciLCoPathDataEntry 11 }

mpanlDlciLCoPermittedTrunkTypes OBJECT-TYPE
   SYNTAX     OCTET STRING (SIZE (1))
   ACCESS     read-only
   STATUS     mandatory
   DESCRIPTION
     "This operational attribute lists up to eight types of trunk that can be 
      used on the route. The originating end of the connection determines 
      the types. The terrestrial and satellite trunk types have been 
      defined, leaving six remaining arbitrary types that can be defined by 
      the network administration. The trunk's type is indicated in the 
      trunkType attribute of the Trunk component. When selecting a 
      route, PORS only chooses trunks whose trunkType are in the 
      permittedTrunkTypes for the path.

      Description of bits:
      terrestrial(0)
      satellite(1)
      trunkType1(2)
      trunkType2(3)
      trunkType3(4)
      trunkType4(5)
      trunkType5(6)
      trunkType6(7)"
::= { mpanlDlciLCoPathDataEntry 12 }

mpanlDlciLCoRequiredSecurity OBJECT-TYPE
   SYNTAX     Unsigned32 (0..7)
   ACCESS     read-only
   STATUS     mandatory
   DESCRIPTION
     "This attribute indicates the required minimum level of security of 
      the trunks on the route. Zero represents the most secure and seven 
      represents the least secure. The trunk's security is indicated by the 
      trunkSecurity attribute of the Trunk component, and has values 
      identical in range and meaning to the requiredSecurity attribute. 
      PORS ensures that any route selected does not contain a trunk 
      whose trunkSecurity attribute is numerically greater than the 
      requiredSecurity."
::= { mpanlDlciLCoPathDataEntry 13 }

mpanlDlciLCoRequiredCustomerParameter OBJECT-TYPE
   SYNTAX     Unsigned32 (0..7)
   ACCESS     read-only
   STATUS     mandatory
   DESCRIPTION
     "This attribute indicates the allowed customer defined parameter of 
      the trunks on the route.The originating end of the connection 
      determines the customer defined parameter. Its value, a number 
      from zero to seven, is chosen by a network administration to have a 
      meaning specific to their network, thus allowing them to customize 
      the use of their trunks. A complementary trunk attribute, 
      customerParameter, also has a value from zero to seven. The route 
      selection process does not consider trunks whose 
      customerParameter is greater than the requiredCustomerParameter 
      of the path."
::= { mpanlDlciLCoPathDataEntry 14 }

mpanlDlciLCoEmissionPriority OBJECT-TYPE
   SYNTAX     Unsigned32 (0..2)
   ACCESS     read-only
   STATUS     mandatory
   DESCRIPTION
     "This attribute indicates the urgency with which packets on the path 
      are emitted by the trunks on the route. The originating end of the 
      connection selects the emissionPriority. EmissionPriority of zero 
      indicates the highest emission priority, while two indicates the 
      lowest emission priority. Packets with a higher emissionPriority (or 
      numerically less) are serviced and sent out before the packets of 
      lower emissionPriority (or numerically higher)."
::= { mpanlDlciLCoPathDataEntry 15 }

mpanlDlciLCoDiscardPriority OBJECT-TYPE
   SYNTAX     Unsigned32 (1..3)
   ACCESS     read-only
   STATUS     mandatory
   DESCRIPTION
     "This attribute indicates the importance of the packets on the 
      path.The originating end of the connection sets discardPriority. One 
      is used for paths carrying the most important traffic, and three is 
      used for paths carrying the least important traffic. Packets with 
      lower discardPriority(numerically lower) are discarded after 
      packets with a higher discardPriority(numerically higher)."
::= { mpanlDlciLCoPathDataEntry 16 }

mpanlDlciLCoRetryCount OBJECT-TYPE
   SYNTAX     Unsigned32 (0..255)
   ACCESS     read-only
   STATUS     mandatory
   DESCRIPTION
     "This attribute is the count of the number of times the path chosen 
      during route selection could not be instantiated. This count should 
      be three or below if the network is performing adequately. A high 
      value indicates that the route selection is often performed using an 
      out-of-date view of available network bandwidth and/or topology.
      This attribute will only increase at the calling end of the connection.
      This attribute is reset each time a path reconnects and stops 
      counting when it reaches its maximum value."
::= { mpanlDlciLCoPathDataEntry 18 }

mpanlDlciLCoPathFailureCount OBJECT-TYPE
   SYNTAX     Unsigned32 (0..65535)
   ACCESS     read-only
   STATUS     mandatory
   DESCRIPTION
     "This attribute is the count of the number of times the path has 
      successfully reconnected. It is set to zero the first time the path is 
      up. If a path fails anytime after connecting, this count will be 
      incremented when the path is up again. Failed route requests do not 
      count in this statistic. See retryCount(rcount) - page 78. This 
      attribute stops counting at its maximum value."
::= { mpanlDlciLCoPathDataEntry 19 }

mpanlDlciLCoReasonForNoRoute OBJECT-TYPE
   SYNTAX     INTEGER  {
                 none(0),
                 destinationNameTooLong(1),
                 destinationNotSpecified(2),
                 unknownDestinationName(3),
                 incorrectDestination(4),
                 incorrectDestinationEndPoint(5),
                 unknownSource(6),
                 unknownDestination(7),
                 sameNode(8),
                 routeCostTooMuch(9),
                 routesDelayTooLong(10),
                 attributesNotMet(11),
                 anError(12),
                 attributeProfileProblem(13),
                 manualPathIndexProblem(14) }
   ACCESS     read-only
   STATUS     mandatory
   DESCRIPTION
     "This attribute is the route selection's reasonForNoRoute and 
      provides a brief reason for which a route was not selected. The 
      reasons are essentially self-explanatory."
   DEFVAL     { none }
::= { mpanlDlciLCoPathDataEntry 20 }

mpanlDlciLCoLastTearDownReason OBJECT-TYPE
   SYNTAX     INTEGER  {
                 none(0),
                 normalShutDown(1),
                 insufficientTxLcOrBandwidth(2),
                 insufficientRxLcOrBandwidth(3),
                 trunkFailure(4),
                 trunkCardFailure(5),
                 operatorForced(6),
                 lostLcnClash(7),
                 networkCongestion(8),
                 trunkNotFound(9),
                 farEndNotFound(10),
                 wrongModuleReached(11),
                 farEndBusy(12),
                 callLoopedBack(13),
                 unknownReason(14),
                 farEndNotReady(15),
                 remoteNameMismatch(16),
                 serviceTypeMismatch(17),
                 reconnectFromFarEnd(18),
                 bumped(19),
                 accessCardFailure(20),
                 optimized(21),
                 overrideRemoteName(22) }
   ACCESS     read-only
   STATUS     mandatory
   DESCRIPTION
     "This attribute reflects the last tear down reason for a connection 
      (LCo). In many cases this displays the reason for a momentary 
      service interruption. This attribute applies to the last path failure 
      only. If a path is no longer up, this may indicate why the path has 
      failed. In many cases an alarm will also be generated with more 
      specific information. The following is a brief description of the 
      reasons:
      none - This path has no information for the teardown. 
      normalShutDown - This path has gone down due to normal call 
      termination.
      insufficientTxLcOrBandwidth - At present there is either no 
      available bandwidth or logical channel numbers available on one or 
      more of the trunks for this path in the transmit direction.
      insufficientRxLcOrBandwidth - At present there is either no 
      available bandwidth or logical channel numbers available on one or 
      more of the trunks for this path in the receive direction.
      trunkFailure- A trunk on the path has failed or has gone down due 
      to a provisioning change of a critical attribute.
      trunkCardFailure- A trunk FP card has failed along the path.
      accessCardFailure- The FP on which the peer access service was 
      running has failed.
      operatorForced- The path has terminated due to the operator 
      locking a trunk along the path.
      lostLcnClash- The path has terminated because the PAs at both 
      ends of an intermediate trunk have allocated the same LC to 
      different calls. When this happens both calls must go down and then 
      try to come up again a fraction of a second later (effectively 
      ensuring that they will now be assigned different LCs). It is normal 
      to get the odd clash especially when the PA's usedLC is 
      approaching the PA's maxLC.
      networkCongestion - The path has failed due to control information 
      being lost and not recoverable.
      trunkNotFound - Occurs on a manual path usually. Check for 
      trunks not up or names provisioned incorrectly.
      farEndNotFound - The far end is not provisioned or is not up. 
      Check remote Name.
      wrongModuleReached - This may occur on a manual path. Check 
      provisioning for correct trunk and service names. For a normal 
      path, the network Topology may be changing. Check remote 
      provisioned DNA.
      farEndBusy - The far end has been reached but it is busy. Check 
      remote provisioned DNA and remote end provisioning.
      unknownReason - The failure was not resolved.
      farEndNotReady - The remote end was reached but the connection 
      was refused due to the remote end not being enabled.
      serviceTypeMismatch - The remote service type does not match 
      this service type. Check provisioning.
      reconnectFromFarEnd - The remote end re-established this 
      connection. Check the remote end lastTearDownReason to 
      determine the real reason.
      bumped - Another call bumped this path from a trunk to get 
      bandwidth (or an LC) which it required to come up. This other path 
      had a higher setupPriority than this path's holdingPriority, hence it 
      was allowed to steal the bandwidth (or LC) from this path.
      optimized - This call has been rerouted due to the optimization 
      feature. The call is still active; this just indicates why the path 
      changed."
   DEFVAL     { none }
::= { mpanlDlciLCoPathDataEntry 21 }

mpanlDlciLCoPathFailureAction OBJECT-TYPE
   SYNTAX     INTEGER  {
                 disconnectConnection(0),
                 reRoutePath(1) }
   ACCESS     read-only
   STATUS     mandatory
   DESCRIPTION
     "This attribute displays whether the application is set to tolerate a 
      momentary interruption of a path while a new path is selected. If 
      disconnectConnection is displayed, the application is informed as 
      soon as possible about a failure by disconnection. If the attribute 
      displays reRoutePath, the path may attempt an immediate reroute, 
      provided the failure is a recoverable failure. If rerouting fails the 
      application is informed of the failure. 
      With this option set to reRoutePath the LCo may wait up to 30 
      seconds before informing the service of complete disconnection in 
      order to allow both ends to attempt to reconnect. All pathTypes 
      respect this attribute. Also, on a manualPath with both ends 
      provisioned with independent paths (at least with respect to the 
      failure) this option will have the desired effect that the path is 
      rerouted without complete disconnection at both ends."
::= { mpanlDlciLCoPathDataEntry 22 }

mpanlDlciLCoBumpPreference OBJECT-TYPE
   SYNTAX     INTEGER  {
                 bumpWhenNecessary(0),
                 bumpToObtainBestRoute(1) }
   ACCESS     read-only
   STATUS     mandatory
   DESCRIPTION
     "This attribute specifies when bumping will occur during the route 
      selection process. Bumping may occur when necessary or always. It 
      will be necessary for a connection to bump if there is not enough 
      resources for the connection to be established and these resources 
      are occupied by a connection whose holdingPriority is lower 
      (numerically higher) than the connection's setupPriority. A 
      connection may also always bump in order to obtain the best route."
::= { mpanlDlciLCoPathDataEntry 23 }

mpanlDlciLCoOptimization OBJECT-TYPE
   SYNTAX     INTEGER  {
                 disabled(0),
                 enabled(1) }
   ACCESS     read-only
   STATUS     mandatory
   DESCRIPTION
     "This attribute is used to specify whether this connection should 
      attempt to optimize its path when requested by the routing PORS 
      component. Every path is as optimal as it can be when it is 
      established, but as network traffic patterns and configurations 
      change this path may no longer be as optimal as it could be. The 
      PORS connection manager on a module requests circuits to 
      optimize at the optimization interval."
::= { mpanlDlciLCoPathDataEntry 24 }

mpanlDlciLCoPathUpDateTime OBJECT-TYPE
   SYNTAX     EnterpriseDateAndTime (SIZE (0 | 19))
   ACCESS     read-only
   STATUS     mandatory
   DESCRIPTION
     "This is the time stamp when the current path was established or 
      reestablished."
::= { mpanlDlciLCoPathDataEntry 25 }

mpanlDlciLCoStatsTable OBJECT-TYPE
   SYNTAX     SEQUENCE OF MpanlDlciLCoStatsEntry
   ACCESS     not-accessible
   STATUS     mandatory
   DESCRIPTION
     "*** THIS TABLE CURRENTLY NOT IMPLEMENTED ***

      This group contains the operational statistics attributes for the path 
      oriented LCo."
::= { mpanlDlciLCo 11 }

mpanlDlciLCoStatsEntry OBJECT-TYPE
   SYNTAX     MpanlDlciLCoStatsEntry
   ACCESS     not-accessible
   STATUS     mandatory
   DESCRIPTION
     "An entry in the mpanlDlciLCoStatsTable."
   INDEX {
      mpanlIndex,
      mpanlDlciIndex,
      mpanlDlciLCoIndex }
::= { mpanlDlciLCoStatsTable 1 }

MpanlDlciLCoStatsEntry ::= SEQUENCE {
   mpanlDlciLCoPktsToNetwork
      PassportCounter64,
   mpanlDlciLCoBytesToNetwork
      PassportCounter64,
   mpanlDlciLCoPktsFromNetwork
      PassportCounter64,
   mpanlDlciLCoBytesFromNetwork
      PassportCounter64 }

mpanlDlciLCoPktsToNetwork OBJECT-TYPE
   SYNTAX     PassportCounter64 
   ACCESS     read-only
   STATUS     mandatory
   DESCRIPTION
     "This attribute counts the number of packets transmitted to the 
      network over this Logical Connection."
::= { mpanlDlciLCoStatsEntry 1 }

mpanlDlciLCoBytesToNetwork OBJECT-TYPE
   SYNTAX     PassportCounter64 
   ACCESS     read-only
   STATUS     mandatory
   DESCRIPTION
     "This attribute counts the number of bytes sent to the network over 
      this Logical Connection."
::= { mpanlDlciLCoStatsEntry 2 }

mpanlDlciLCoPktsFromNetwork OBJECT-TYPE
   SYNTAX     PassportCounter64 
   ACCESS     read-only
   STATUS     mandatory
   DESCRIPTION
     "This attribute counts the number of packets received from the 
      remote LCo via the network. This attribute wraps to 0."
::= { mpanlDlciLCoStatsEntry 3 }

mpanlDlciLCoBytesFromNetwork OBJECT-TYPE
   SYNTAX     PassportCounter64 
   ACCESS     read-only
   STATUS     mandatory
   DESCRIPTION
     "This attribute counts the number of bytes received from the remote 
      LCo via the network. This attribute wraps to 0."
::= { mpanlDlciLCoStatsEntry 4 }

mpanlDlciLCoCallDataTable OBJECT-TYPE
   SYNTAX     SEQUENCE OF MpanlDlciLCoCallDataEntry
   ACCESS     not-accessible
   STATUS     mandatory
   DESCRIPTION
     "*** THIS TABLE CURRENTLY NOT IMPLEMENTED ***

      This group contains all operational attributes for the path oriented 
      LCo."
::= { mpanlDlciLCo 12 }

mpanlDlciLCoCallDataEntry OBJECT-TYPE
   SYNTAX     MpanlDlciLCoCallDataEntry
   ACCESS     not-accessible
   STATUS     mandatory
   DESCRIPTION
     "An entry in the mpanlDlciLCoCallDataTable."
   INDEX {
      mpanlIndex,
      mpanlDlciIndex,
      mpanlDlciLCoIndex }
::= { mpanlDlciLCoCallDataTable 1 }

MpanlDlciLCoCallDataEntry ::= SEQUENCE {
   mpanlDlciLCoCallingNpi
      INTEGER,
   mpanlDlciLCoCallingDna
      DigitString,
   mpanlDlciLCoElapsedTimeTillNow
      Unsigned32,
   mpanlDlciLCoCallReferenceNumber
      Hex,
   mpanlDlciLCoCalledNpi
      INTEGER,
   mpanlDlciLCoCalledDna
      DigitString }

mpanlDlciLCoCallingNpi OBJECT-TYPE
   SYNTAX     INTEGER  {
                 x121(0),
                 e164(1) }
   ACCESS     read-only
   STATUS     mandatory
   DESCRIPTION
     "This attribute displays the Numbering Plan Indicator (NPI) of the 
      calling end."
   DEFVAL     { x121 }
::= { mpanlDlciLCoCallDataEntry 27 }

mpanlDlciLCoCallingDna OBJECT-TYPE
   SYNTAX     DigitString (SIZE (0..15))
   ACCESS     read-only
   STATUS     mandatory
   DESCRIPTION
     "This attribute displays the Data Network Address (DNA) of the 
      calling end."
::= { mpanlDlciLCoCallDataEntry 28 }

mpanlDlciLCoElapsedTimeTillNow OBJECT-TYPE
   SYNTAX     Unsigned32 (0..16777215)
   ACCESS     read-only
   STATUS     mandatory
   DESCRIPTION
     "This attribute displays the total duration in tenths of miliseconds 
      that a connection has been up for a call."
::= { mpanlDlciLCoCallDataEntry 30 }

mpanlDlciLCoCallReferenceNumber OBJECT-TYPE
   SYNTAX     Hex (0..16777215)
   ACCESS     read-only
   STATUS     mandatory
   DESCRIPTION
     "This attribute displays the call reference number which is a unique 
      number generated by the switch.The same Call Reference Number 
      is stored in the interval data (accounting record) at both ends of the 
      call. It can be used as one of the attributes in matching duplicate 
      records generated at each end of the call."
::= { mpanlDlciLCoCallDataEntry 31 }

mpanlDlciLCoCalledNpi OBJECT-TYPE
   SYNTAX     INTEGER  {
                 x121(0),
                 e164(1) }
   ACCESS     read-only
   STATUS     mandatory
   DESCRIPTION
     "This attribute indicates the Numbering Plan Indicator (NPI) of the 
      called end."
   DEFVAL     { x121 }
::= { mpanlDlciLCoCallDataEntry 33 }

mpanlDlciLCoCalledDna OBJECT-TYPE
   SYNTAX     DigitString (SIZE (0..15))
   ACCESS     read-only
   STATUS     mandatory
   DESCRIPTION
     "This attribute indicates the Data Network Address (DNA) of the 
      called (destination) DTE to which this call is sent. This address if 
      defined at the receiving end will complete the logical connection."
::= { mpanlDlciLCoCallDataEntry 34 }

mpanlDlciLCoPathTable OBJECT-TYPE
   SYNTAX     SEQUENCE OF MpanlDlciLCoPathEntry
   ACCESS     not-accessible
   STATUS     mandatory
   DESCRIPTION
     "*** THIS TABLE CURRENTLY NOT IMPLEMENTED ***

      This attribute contains the trunk component names over which the 
      path has been instantiated and the remote end point name 
      terminating the path."
::= { mpanlDlciLCo 401 }

mpanlDlciLCoPathEntry OBJECT-TYPE
   SYNTAX     MpanlDlciLCoPathEntry
   ACCESS     not-accessible
   STATUS     mandatory
   DESCRIPTION
     "An entry in the mpanlDlciLCoPathTable."
   INDEX {
      mpanlIndex,
      mpanlDlciIndex,
      mpanlDlciLCoIndex,
      mpanlDlciLCoPathValue }
::= { mpanlDlciLCoPathTable 1 }

MpanlDlciLCoPathEntry ::= SEQUENCE {
   mpanlDlciLCoPathValue
      AsciiString }

mpanlDlciLCoPathValue OBJECT-TYPE
   SYNTAX     AsciiString (SIZE (0..40))
   ACCESS     read-only
   STATUS     mandatory
   DESCRIPTION
     "This variable represents both the value and the index for the
      mpanlDlciLCoPathTable."
::= { mpanlDlciLCoPathEntry 1 }

-- 
-- *** THIS SUBTREE CURRENTLY NOT IMPLEMENTED ***
-- 

-- Mpanl/n Dlci/n JunctorVc
-- This component extends the GVC connectivity across MPANL. It 
-- allows applications in a Legacy Data Module (LDM) subnet to 
-- establish GVC connections with applications in the Magellan 
-- subnet.

mpanlDlciJvc OBJECT IDENTIFIER ::= { mpanlDlci 5 }



mpanlDlciJvcRowStatusTable OBJECT-TYPE
   SYNTAX     SEQUENCE OF MpanlDlciJvcRowStatusEntry
   ACCESS     not-accessible
   STATUS     mandatory
   DESCRIPTION
     "*** THIS TABLE CURRENTLY NOT IMPLEMENTED ***

      This entry controls the addition and deletion of 
      mpanlDlciJvc components."
::= { mpanlDlciJvc 1 }

mpanlDlciJvcRowStatusEntry OBJECT-TYPE
   SYNTAX     MpanlDlciJvcRowStatusEntry
   ACCESS     not-accessible
   STATUS     mandatory
   DESCRIPTION
     "A single entry in the table represents a single 
      mpanlDlciJvc component."
   INDEX {
      mpanlIndex,
      mpanlDlciIndex,
      mpanlDlciJvcIndex }
::= { mpanlDlciJvcRowStatusTable 1 }

MpanlDlciJvcRowStatusEntry ::= SEQUENCE {
   mpanlDlciJvcRowStatus
      RowStatus,
   mpanlDlciJvcComponentName
      DisplayString,
   mpanlDlciJvcStorageType
      StorageType,
   mpanlDlciJvcIndex
      NonReplicated }

mpanlDlciJvcRowStatus OBJECT-TYPE
   SYNTAX     RowStatus 
   ACCESS     read-only
   STATUS     mandatory
   DESCRIPTION
     "This variable is used as the basis for SNMP naming of
      mpanlDlciJvc components.
      These components cannot be added nor deleted."
::= { mpanlDlciJvcRowStatusEntry 1 }

mpanlDlciJvcComponentName OBJECT-TYPE
   SYNTAX     DisplayString 
   ACCESS     read-only
   STATUS     mandatory
   DESCRIPTION
     "This variable provides the component's string name for
      use with the ASCII Console Interface"
::= { mpanlDlciJvcRowStatusEntry 2 }

mpanlDlciJvcStorageType OBJECT-TYPE
   SYNTAX     StorageType 
   ACCESS     read-only
   STATUS     mandatory
   DESCRIPTION
     "This variable represents the storage type value for the
      mpanlDlciJvc tables."
::= { mpanlDlciJvcRowStatusEntry 4 }

mpanlDlciJvcIndex OBJECT-TYPE
   SYNTAX     NonReplicated 
   ACCESS     not-accessible
   STATUS     mandatory
   DESCRIPTION
     "This variable represents the index for the mpanlDlciJvc tables."
::= { mpanlDlciJvcRowStatusEntry 10 }

mpanlDlciJvcOperTable OBJECT-TYPE
   SYNTAX     SEQUENCE OF MpanlDlciJvcOperEntry
   ACCESS     not-accessible
   STATUS     mandatory
   DESCRIPTION
     "*** THIS TABLE CURRENTLY NOT IMPLEMENTED ***

      This group contains the operational attributes of the Jvc component."
::= { mpanlDlciJvc 10 }

mpanlDlciJvcOperEntry OBJECT-TYPE
   SYNTAX     MpanlDlciJvcOperEntry
   ACCESS     not-accessible
   STATUS     mandatory
   DESCRIPTION
     "An entry in the mpanlDlciJvcOperTable."
   INDEX {
      mpanlIndex,
      mpanlDlciIndex,
      mpanlDlciJvcIndex }
::= { mpanlDlciJvcOperTable 1 }

MpanlDlciJvcOperEntry ::= SEQUENCE {
   mpanlDlciJvcCurrentState
      INTEGER,
   mpanlDlciJvcPreviousState
      INTEGER,
   mpanlDlciJvcCallingNpi
      INTEGER,
   mpanlDlciJvcCallingAddress
      DigitString,
   mpanlDlciJvcCallingLcn
      Unsigned32,
   mpanlDlciJvcCalledNpi
      INTEGER,
   mpanlDlciJvcCalledAddress
      DigitString,
   mpanlDlciJvcCalledLcn
      Unsigned32 }

mpanlDlciJvcCurrentState OBJECT-TYPE
   SYNTAX     INTEGER  {
                 null(0),
                 callRequest(1),
                 callIndication(2),
                 callBlockPresent(3),
                 active(4),
                 discInitiated(5),
                 discPktPresent(6),
                 callDisconnected(7),
                 callTerminated(8) }
   ACCESS     read-only
   STATUS     mandatory
   DESCRIPTION
     "This attribute indicates the current state of the JVC process.
      The state can be one of:
      null:	 waiting for an incoming call or a call request from MPANL,
      callRequest: waiting for the call connected from MPANL,
      callIndication: waiting for the call packet from MPANL,
      callBlockPresent: waiting for the Raccept packet from the subnet,
      active: relaying packets between the subnet and MPANL,
      discInitiated: not used by the DCE JVC,
      discPktPresent: not used by the DCE JVC,
      callDisconnected: waiting for the termination request from 
      MPANL,
      callTerminated: waiting for the termination by MPANL."
::= { mpanlDlciJvcOperEntry 1 }

mpanlDlciJvcPreviousState OBJECT-TYPE
   SYNTAX     INTEGER  {
                 null(0),
                 callRequest(1),
                 callIndication(2),
                 callBlockPresent(3),
                 active(4),
                 discInitiated(5),
                 discPktPresent(6),
                 callDisconnected(7),
                 callTerminated(8) }
   ACCESS     read-only
   STATUS     mandatory
   DESCRIPTION
     "This attribute indicates the previous state of the JVC process.
      The state can be one of:
      null:	 waiting for an incoming call or a call request from MPANL,
      callRequest: waiting for the call connected from MPANL,
      callIndication: waiting for the call packet from MPANL,
      callBlockPresent: waiting for the Raccept packet from the subnet,
      active: relaying packets between the subnet and MPANL,
      discInitiated: not used by the DCE JVC,
      discPktPresent: not used by the DCE JVC,
      callDisconnected: waiting for the termination request from 
      MPANL,
      callTerminated: waiting for the termination by MPANL."
::= { mpanlDlciJvcOperEntry 2 }

mpanlDlciJvcCallingNpi OBJECT-TYPE
   SYNTAX     INTEGER  {
                 x121(0),
                 e164(1) }
   ACCESS     read-only
   STATUS     mandatory
   DESCRIPTION
     "This attribute contains the numbering plan indicator of the calling 
      address. This attribute value is retrieved from the call packet."
::= { mpanlDlciJvcOperEntry 6 }

mpanlDlciJvcCallingAddress OBJECT-TYPE
   SYNTAX     DigitString (SIZE (1..15))
   ACCESS     read-only
   STATUS     mandatory
   DESCRIPTION
     "This attribute contains the calling DataNetworkAddress of the 
      interface. It includes the DNIC (first 4 digits) for X.121, and the CC 
      (Country Code) for the E.164 address of the calling end. The 
      maximum length of this attribute is 15 digits. This attribute value is 
      retrieved from the call packet."
::= { mpanlDlciJvcOperEntry 7 }

mpanlDlciJvcCallingLcn OBJECT-TYPE
   SYNTAX     Unsigned32 (1..4095)
   ACCESS     read-only
   STATUS     mandatory
   DESCRIPTION
     "This attribute contains the calling LCN (logical channel number) of 
      the interface. This number is assigned to the call request at the 
      calling end. This attribute value is retrieved from the call packet."
::= { mpanlDlciJvcOperEntry 8 }

mpanlDlciJvcCalledNpi OBJECT-TYPE
   SYNTAX     INTEGER  {
                 x121(0),
                 e164(1) }
   ACCESS     read-only
   STATUS     mandatory
   DESCRIPTION
     "This attribute contains the numbering plan indicator of the called 
      address. This attribute value is retrieved from the call packet."
::= { mpanlDlciJvcOperEntry 9 }

mpanlDlciJvcCalledAddress OBJECT-TYPE
   SYNTAX     DigitString (SIZE (1..15))
   ACCESS     read-only
   STATUS     mandatory
   DESCRIPTION
     "This attribute contains the called DataNetworkAddress of the 
      interface. It includes the DNIC (first 4 digits) for X.121, and the CC 
      (Country Code) for the E.164 address of the called end. The 
      maximum length of this attribute is 15 digits. This attribute value is 
      retrieved from the Raccept packet."
::= { mpanlDlciJvcOperEntry 10 }

mpanlDlciJvcCalledLcn OBJECT-TYPE
   SYNTAX     Unsigned32 (1..4095)
   ACCESS     read-only
   STATUS     mandatory
   DESCRIPTION
     "This attribute contains the called LCN (logical channel number) of 
      the interface. This number is assigned to the call request at the 
      called end. This attribute value is retrieved from the Raccept packet."
::= { mpanlDlciJvcOperEntry 11 }

mpanlDlciJvcStatTable OBJECT-TYPE
   SYNTAX     SEQUENCE OF MpanlDlciJvcStatEntry
   ACCESS     not-accessible
   STATUS     mandatory
   DESCRIPTION
     "*** THIS TABLE CURRENTLY NOT IMPLEMENTED ***

      This group contains the statistics collected by the Jvc component."
::= { mpanlDlciJvc 11 }

mpanlDlciJvcStatEntry OBJECT-TYPE
   SYNTAX     MpanlDlciJvcStatEntry
   ACCESS     not-accessible
   STATUS     mandatory
   DESCRIPTION
     "An entry in the mpanlDlciJvcStatTable."
   INDEX {
      mpanlIndex,
      mpanlDlciIndex,
      mpanlDlciJvcIndex }
::= { mpanlDlciJvcStatTable 1 }

MpanlDlciJvcStatEntry ::= SEQUENCE {
   mpanlDlciJvcPacketsFromSubnet
      Unsigned32,
   mpanlDlciJvcPacketsToSubnet
      Unsigned32,
   mpanlDlciJvcPacketsDiscarded
      Unsigned32,
   mpanlDlciJvcProtocolErrors
      Unsigned32 }

mpanlDlciJvcPacketsFromSubnet OBJECT-TYPE
   SYNTAX     Unsigned32 (0..4294967295)
   ACCESS     read-only
   STATUS     mandatory
   DESCRIPTION
     "This attribute counts all packets including control packets received 
      from the subnet. This number reflects also the packets sent to the 
      MPANL process since the JVC does not drop or generate packets in 
      this direction.The value of this attribute wraps to 0 when the 
      maximum value is reached."
::= { mpanlDlciJvcStatEntry 1 }

mpanlDlciJvcPacketsToSubnet OBJECT-TYPE
   SYNTAX     Unsigned32 (0..4294967295)
   ACCESS     read-only
   STATUS     mandatory
   DESCRIPTION
     "This attribute counts all packets including control packets sent into 
      the subnet. This number includes Renew Call Timer Packets that are 
      generated by the JVC. The value of this attribute wraps to 0 when 
      the maximum value is reached."
::= { mpanlDlciJvcStatEntry 2 }

mpanlDlciJvcPacketsDiscarded OBJECT-TYPE
   SYNTAX     Unsigned32 (0..4294967295)
   ACCESS     read-only
   STATUS     mandatory
   DESCRIPTION
     "This attribute counts discarded packets that can not be forwarded 
      into the subnet because of subnet congestion. This attribute is 
      increased when packet forwarding fails to forward a packet into the 
      subnet."
::= { mpanlDlciJvcStatEntry 3 }

mpanlDlciJvcProtocolErrors OBJECT-TYPE
   SYNTAX     Unsigned32 (0..4294967295)
   ACCESS     read-only
   STATUS     mandatory
   DESCRIPTION
     "This attribute counts the number of protocol errors detected by the 
      JVC in both the MPANL and the subnet directions. A protocol error 
      is counted in the following cases:
      - reception of a packet from MPANL while waiting for a Raccept 
      packet from the subnet,
      - reception of a packet from the subnet following a call packet and 
      before the callAccepted is received from MPANL,
      - reception of a packet from the subnet or from MPANL that is 
      shorter than the subnet header.
      The value of this attribute wraps to 0 when the maximum value is 
      reached."
::= { mpanlDlciJvcStatEntry 4 }


-- Mpanl/<n> Signaling
-- This component defines the Q.933 and Q.922 (LAPF) parameters 
-- for Frame Relay switched virtual circuits at the Mpanl interface.

mpanlSig OBJECT IDENTIFIER ::= { mpanl 6 }



mpanlSigRowStatusTable OBJECT-TYPE
   SYNTAX     SEQUENCE OF MpanlSigRowStatusEntry
   ACCESS     not-accessible
   STATUS     mandatory
   DESCRIPTION
     "This entry controls the addition and deletion of 
      mpanlSig components."
::= { mpanlSig 1 }

mpanlSigRowStatusEntry OBJECT-TYPE
   SYNTAX     MpanlSigRowStatusEntry
   ACCESS     not-accessible
   STATUS     mandatory
   DESCRIPTION
     "A single entry in the table represents a single 
      mpanlSig component."
   INDEX {
      mpanlIndex,
      mpanlSigIndex }
::= { mpanlSigRowStatusTable 1 }

MpanlSigRowStatusEntry ::= SEQUENCE {
   mpanlSigRowStatus
      RowStatus,
   mpanlSigComponentName
      DisplayString,
   mpanlSigStorageType
      StorageType,
   mpanlSigIndex
      NonReplicated }

mpanlSigRowStatus OBJECT-TYPE
   SYNTAX     RowStatus 
   ACCESS     read-only
   STATUS     mandatory
   DESCRIPTION
     "This variable is used as the basis for SNMP naming of
      mpanlSig components.
      These components cannot be added nor deleted."
::= { mpanlSigRowStatusEntry 1 }

mpanlSigComponentName OBJECT-TYPE
   SYNTAX     DisplayString 
   ACCESS     read-only
   STATUS     mandatory
   DESCRIPTION
     "This variable provides the component's string name for
      use with the ASCII Console Interface"
::= { mpanlSigRowStatusEntry 2 }

mpanlSigStorageType OBJECT-TYPE
   SYNTAX     StorageType 
   ACCESS     read-only
   STATUS     mandatory
   DESCRIPTION
     "This variable represents the storage type value for the
      mpanlSig tables."
::= { mpanlSigRowStatusEntry 4 }

mpanlSigIndex OBJECT-TYPE
   SYNTAX     NonReplicated 
   ACCESS     not-accessible
   STATUS     mandatory
   DESCRIPTION
     "This variable represents the index for the mpanlSig tables."
::= { mpanlSigRowStatusEntry 10 }

mpanlSigSysParmsTable OBJECT-TYPE
   SYNTAX     SEQUENCE OF MpanlSigSysParmsEntry
   ACCESS     not-accessible
   STATUS     mandatory
   DESCRIPTION
     "This group contains the provisionable Q.933 system parameters."
::= { mpanlSig 13 }

mpanlSigSysParmsEntry OBJECT-TYPE
   SYNTAX     MpanlSigSysParmsEntry
   ACCESS     not-accessible
   STATUS     mandatory
   DESCRIPTION
     "An entry in the mpanlSigSysParmsTable."
   INDEX {
      mpanlIndex,
      mpanlSigIndex }
::= { mpanlSigSysParmsTable 1 }

MpanlSigSysParmsEntry ::= SEQUENCE {
   mpanlSigCallSetupTimer
      Unsigned32,
   mpanlSigDisconnectTimer
      Unsigned32,
   mpanlSigReleaseTimer
      Unsigned32,
   mpanlSigCallProceedingTimer
      Unsigned32,
   mpanlSigNetworkType
      INTEGER }

mpanlSigCallSetupTimer OBJECT-TYPE
   SYNTAX     Unsigned32 (1..255)
   ACCESS     read-write
   STATUS     mandatory
   DESCRIPTION
     "This attribute specifies the time the network will wait for a response 
      to the SETUP message sent to the called user. Upon timer expiry, 
      the SETUP message is retransmitted. The second expiry of this 
      timer causes the call to be cleared. This value is specified in 
      seconds."
   DEFVAL     { 4 }
::= { mpanlSigSysParmsEntry 1 }

mpanlSigDisconnectTimer OBJECT-TYPE
   SYNTAX     Unsigned32 (1..255)
   ACCESS     read-write
   STATUS     mandatory
   DESCRIPTION
     "This attribute specifies the time the network will wait for a response 
      to the DISCONNECT message sent to the user. Upon timer expiry, 
      the RELEASE message is sent. This value is specified in seconds."
   DEFVAL     { 30 }
::= { mpanlSigSysParmsEntry 2 }

mpanlSigReleaseTimer OBJECT-TYPE
   SYNTAX     Unsigned32 (1..255)
   ACCESS     read-write
   STATUS     mandatory
   DESCRIPTION
     "This attribute specifies the time the network will wait for a response 
      to the RELEASE message sent to the user. Upon timer expiry, the 
      RELEASE message is retransmitted. The second expiry of the timer 
      causes the call to be released. This value is specified in seconds."
   DEFVAL     { 4 }
::= { mpanlSigSysParmsEntry 3 }

mpanlSigCallProceedingTimer OBJECT-TYPE
   SYNTAX     Unsigned32 (1..255)
   ACCESS     read-write
   STATUS     mandatory
   DESCRIPTION
     "This attribute specifies the time the network will wait for the 
      CONNECT message from the called user after the network has 
      received the optional CALL PROCEEDING message from the 
      called user. Upon timer expiry, the call is cleared. This value is 
      specified in seconds."
   DEFVAL     { 10 }
::= { mpanlSigSysParmsEntry 4 }

mpanlSigNetworkType OBJECT-TYPE
   SYNTAX     INTEGER  {
                 private(1),
                 public(2) }
   ACCESS     read-write
   STATUS     mandatory
   DESCRIPTION
     "This attribute specifies whether this Frame Relay service is running 
      on a public or a private network. This value is used solely in 
      populating applicable information elements within those Q.933 
      messages that require a public or private network indication."
   DEFVAL     { private }
::= { mpanlSigSysParmsEntry 5 }

mpanlSigLapfSysTable OBJECT-TYPE
   SYNTAX     SEQUENCE OF MpanlSigLapfSysEntry
   ACCESS     not-accessible
   STATUS     mandatory
   DESCRIPTION
     "This group contains the provisionable attributes for the SVC data 
      link layer. The data link layer is governed primarily through ITU 
      specification Q.922, and operates over DLCI 0.."
::= { mpanlSig 14 }

mpanlSigLapfSysEntry OBJECT-TYPE
   SYNTAX     MpanlSigLapfSysEntry
   ACCESS     not-accessible
   STATUS     mandatory
   DESCRIPTION
     "An entry in the mpanlSigLapfSysTable."
   INDEX {
      mpanlIndex,
      mpanlSigIndex }
::= { mpanlSigLapfSysTable 1 }

MpanlSigLapfSysEntry ::= SEQUENCE {
   mpanlSigWindowSize
      Unsigned32,
   mpanlSigRetransmitLimit
      Unsigned32,
   mpanlSigAckTimer
      Unsigned32,
   mpanlSigAckDelayTimer
      Unsigned32,
   mpanlSigIdleProbeTimer
      Unsigned32 }

mpanlSigWindowSize OBJECT-TYPE
   SYNTAX     Unsigned32 (1..127)
   ACCESS     read-write
   STATUS     mandatory
   DESCRIPTION
     "This attribute specifies the window size. This is the maximum 
      number of unacknowledged sequenced frames that may be 
      outstanding from or to this interface at any one time."
   DEFVAL     { 7 }
::= { mpanlSigLapfSysEntry 2 }

mpanlSigRetransmitLimit OBJECT-TYPE
   SYNTAX     Unsigned32 (0..20)
   ACCESS     read-write
   STATUS     mandatory
   DESCRIPTION
     "This attribute specifies the number of times a frame can be 
      retransmitted by the SVC data link layer before appropriate 
      recovery action is taken."
   DEFVAL     { 3 }
::= { mpanlSigLapfSysEntry 3 }

mpanlSigAckTimer OBJECT-TYPE
   SYNTAX     Unsigned32 (1000..10000)
   ACCESS     read-write
   STATUS     mandatory
   DESCRIPTION
     "This attribute specifies the period in milliseconds that the network 
      will wait for an acknowledgment to a sent frame. The value set for 
      ackTimer must be less than the value set for idleProbeTimer."
   DEFVAL     { 1500 }
::= { mpanlSigLapfSysEntry 4 }

mpanlSigAckDelayTimer OBJECT-TYPE
   SYNTAX     Unsigned32 (0..10000)
   ACCESS     read-write
   STATUS     mandatory
   DESCRIPTION
     "This attribute specifies the maximum period in milliseconds that the 
      network will wait before sending an acknowledgment for a received 
      in-sequence I-frame. A value of 0 means there will be no delay in 
      acknowledgment."
   DEFVAL     { 0 }
::= { mpanlSigLapfSysEntry 5 }

mpanlSigIdleProbeTimer OBJECT-TYPE
   SYNTAX     Unsigned32 (1000..65535000)
   ACCESS     read-write
   STATUS     mandatory
   DESCRIPTION
     "This attribute specifies the time period in milliseconds the link will 
      be permitted to remain idle (that is, no frames are exchanged on the 
      data link). Upon expiry of this timer, the network's side link layer 
      polls its peer for status. The value set for idleProbeTimer must be 
      greater than the value set for ackTimer."
   DEFVAL     { 30000 }
::= { mpanlSigLapfSysEntry 6 }

mpanlSigSvcaccTable OBJECT-TYPE
   SYNTAX     SEQUENCE OF MpanlSigSvcaccEntry
   ACCESS     not-accessible
   STATUS     mandatory
   DESCRIPTION
     "This group contains the provisionable attribute to define the 
      defaultAccounting attribute.."
::= { mpanlSig 15 }

mpanlSigSvcaccEntry OBJECT-TYPE
   SYNTAX     MpanlSigSvcaccEntry
   ACCESS     not-accessible
   STATUS     mandatory
   DESCRIPTION
     "An entry in the mpanlSigSvcaccTable."
   INDEX {
      mpanlIndex,
      mpanlSigIndex }
::= { mpanlSigSvcaccTable 1 }

MpanlSigSvcaccEntry ::= SEQUENCE {
   mpanlSigDefaultAccounting
      INTEGER }

mpanlSigDefaultAccounting OBJECT-TYPE
   SYNTAX     INTEGER  {
                 off(0),
                 on(1) }
   ACCESS     read-write
   STATUS     mandatory
   DESCRIPTION
     "This attribute specifies whether accounting data collection and 
      record generation is turned on at this DLCI. For accounting data 
      collection and record generation to be turned on, the 
      defaultAccounting bit and at least one of the accountCollection 
      bits in the FrsDataNetworkAddress component must be set to on."
   DEFVAL     { on }
::= { mpanlSigSvcaccEntry 1 }

mpanlSigStateTable OBJECT-TYPE
   SYNTAX     SEQUENCE OF MpanlSigStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mpanlSig 16 }

mpanlSigStateEntry OBJECT-TYPE
   SYNTAX     MpanlSigStateEntry
   ACCESS     not-accessible
   STATUS     mandatory
   DESCRIPTION
     "An entry in the mpanlSigStateTable."
   INDEX {
      mpanlIndex,
      mpanlSigIndex }
::= { mpanlSigStateTable 1 }

MpanlSigStateEntry ::= SEQUENCE {
   mpanlSigAdminState
      INTEGER,
   mpanlSigOperationalState
      INTEGER,
   mpanlSigUsageState
      INTEGER }

mpanlSigAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mpanlSigStateEntry 1 }

mpanlSigOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mpanlSigStateEntry 2 }

mpanlSigUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mpanlSigStateEntry 3 }

mpanlSigStatsTable OBJECT-TYPE
   SYNTAX     SEQUENCE OF MpanlSigStatsEntry
   ACCESS     not-accessible
   STATUS     mandatory
   DESCRIPTION
     "This group contains the statistics related to the SVC signaling layer 
      at the interface level."
::= { mpanlSig 17 }

mpanlSigStatsEntry OBJECT-TYPE
   SYNTAX     MpanlSigStatsEntry
   ACCESS     not-accessible
   STATUS     mandatory
   DESCRIPTION
     "An entry in the mpanlSigStatsTable."
   INDEX {
      mpanlIndex,
      mpanlSigIndex }
::= { mpanlSigStatsTable 1 }

MpanlSigStatsEntry ::= SEQUENCE {
   mpanlSigCurrentNumberOfSvcCalls
      Unsigned32,
   mpanlSigInCalls
      Counter32,
   mpanlSigInCallsRefused
      Counter32,
   mpanlSigOutCalls
      Counter32,
   mpanlSigOutCallsFailed
      Counter32,
   mpanlSigProtocolErrors
      Counter32,
   mpanlSigQualityOfServiceNotAvailable
      Counter32,
   mpanlSigSetupTimeout
      Counter32,
   mpanlSigLastCauseInStatusMsgReceived
      Unsigned32,
   mpanlSigLastStateInStatusMsgReceived
      INTEGER,
   mpanlSigLastDlciReceivedStatus
      Unsigned32,
   mpanlSigLastQ933StateReceivedStatus
      INTEGER,
   mpanlSigLastTimeMsgBlockCongested
      EnterpriseDateAndTime,
   mpanlSigLastDlciWithMsgBlockCongestion
      Unsigned32 }

mpanlSigCurrentNumberOfSvcCalls OBJECT-TYPE
   SYNTAX     Unsigned32 (0..991)
   ACCESS     read-only
   STATUS     mandatory
   DESCRIPTION
     "This attribute shows the number of Frame Relay SVCs currently 
      existing on this interface."
::= { mpanlSigStatsEntry 1 }

mpanlSigInCalls OBJECT-TYPE
   SYNTAX     Counter32 
   ACCESS     read-only
   STATUS     mandatory
   DESCRIPTION
     "This attribute indicates the current number of incoming SVCs on 
      this interface (that is,  the number of SVCs for which this interface 
      represents the destination end of the call)."
::= { mpanlSigStatsEntry 4 }

mpanlSigInCallsRefused OBJECT-TYPE
   SYNTAX     Counter32 
   ACCESS     read-only
   STATUS     mandatory
   DESCRIPTION
     "This attribute counts the number of incoming SVC call requests that 
      are rejected by either this interface or by the called user. When this 
      count reaches maximum, it wraps to zero."
::= { mpanlSigStatsEntry 5 }

mpanlSigOutCalls OBJECT-TYPE
   SYNTAX     Counter32 
   ACCESS     read-only
   STATUS     mandatory
   DESCRIPTION
     "This attribute shows the current number of outgoing SVCs on this 
      interface (that is,  the number of SVCs for which this interface 
      represents the source end of the call)."
::= { mpanlSigStatsEntry 6 }

mpanlSigOutCallsFailed OBJECT-TYPE
   SYNTAX     Counter32 
   ACCESS     read-only
   STATUS     mandatory
   DESCRIPTION
     "This attribute counts the number of outgoing SVC call requests that 
      are rejected by either this interface, or by the network side of the 
      destination end, or by the called user. When this count reaches 
      maximum, it wraps to zero."
::= { mpanlSigStatsEntry 7 }

mpanlSigProtocolErrors OBJECT-TYPE
   SYNTAX     Counter32 
   ACCESS     read-only
   STATUS     mandatory
   DESCRIPTION
     "This attribute counts the number of times a Q.933 protocol error has 
      occurred. Any one of the following events constitutes a protocol 
      error:
      1. In the user-signaled Link Layer Core Parameters IE within the
      SETUP or CONNECT messages, Cir, Bc and Be are all zero;
      2. In the user-signaled Link Layer Core Parameters IE within the
      SETUP or CONNECT messages, Cir is zero but Bc is 
      non-zero, or Bc is zero but Cir is non-zero;
      3. In the user-signaled Link Layer Core Parameters IE within the
      SETUP or CONNECT messages, the minimum acceptable Cir
      is greater than Cir;
      4. At the destination end, any of the destination to source direction 
      link layer core parameters has been increased in the 
      CONNECT message from the called user;
      5. At the destination end, the destination to source direction Cir
      in the CONNECT message is smaller than the corresponding 
      minimum acceptable Cir signaled to the called user;
      6. At the source end, any of the source to destination direction 
      link layer core parameters in the CONNECT message from the 
      destination end has been increased;
      7. At the source end, the source to destination direction Cir, after
      negotiation, is smaller than the corresponding minimum
      acceptable Cir;
      8. The network has received a STATUS message from the user
      with an incompatible Q.933 state.	
      
      When this count reaches maximum, it wraps to zero."
::= { mpanlSigStatsEntry 8 }

mpanlSigQualityOfServiceNotAvailable OBJECT-TYPE
   SYNTAX     Counter32 
   ACCESS     read-only
   STATUS     mandatory
   DESCRIPTION
     "This attribute counts the number of incoming and outgoing SVCs 
      that are rejected because the quality of service requested cannot be 
      met by the network. When this count reaches maximum, it wraps to 
      zero."
::= { mpanlSigStatsEntry 9 }

mpanlSigSetupTimeout OBJECT-TYPE
   SYNTAX     Counter32 
   ACCESS     read-only
   STATUS     mandatory
   DESCRIPTION
     "This attribute counts the number of times the T303 setup timer has 
      expired. When this count reaches maximum, it wraps to zero."
::= { mpanlSigStatsEntry 10 }

mpanlSigLastCauseInStatusMsgReceived OBJECT-TYPE
   SYNTAX     Unsigned32 (0..255)
   ACCESS     read-only
   STATUS     mandatory
   DESCRIPTION
     "This attribute shows the cause value in the last received user's 
      STATUS message to an existing call. The DLCI to which this 
      STATUS message applies is specified in the lastDlciReceivedStatus 
      attribute.
      
      The initial value of this attribute is 0 which means that no STATUS 
      message has been received for an existing call."
::= { mpanlSigStatsEntry 11 }

mpanlSigLastStateInStatusMsgReceived OBJECT-TYPE
   SYNTAX     INTEGER  {
                 null(0),
                 callInitiated(1),
                 n2(2),
                 outgoingCallProceeding(3),
                 n4(4),
                 n5(5),
                 callPresent(6),
                 n7(7),
                 n8(8),
                 incomingCallProceeding(9),
                 active(10),
                 disconnectRequest(11),
                 disconnectIndication(12),
                 n13(13),
                 n14(14),
                 n15(15),
                 n16(16),
                 n17(17),
                 n18(18),
                 releaseRequest(19),
                 notApplicable(20),
                 n21(21),
                 n22(22),
                 n23(23),
                 n24(24),
                 n25(25),
                 n26(26),
                 n27(27),
                 n28(28),
                 n29(29),
                 n30(30),
                 n31(31),
                 n32(32),
                 n33(33),
                 n34(34),
                 n35(35),
                 n36(36),
                 n37(37),
                 n38(38),
                 n39(39),
                 n40(40),
                 n41(41),
                 n42(42),
                 n43(43),
                 n44(44),
                 n45(45),
                 n46(46),
                 n47(47),
                 n48(48),
                 n49(49),
                 n50(50),
                 n51(51),
                 n52(52),
                 n53(53),
                 n54(54),
                 n55(55),
                 n56(56),
                 n57(57),
                 n58(58),
                 n59(59),
                 n60(60),
                 n61(61),
                 n62(62),
                 n63(63) }
   ACCESS     read-only
   STATUS     mandatory
   DESCRIPTION
     "This attribute shows the state value in the last received user's 
      STATUS message to an existing call. The DLCI to which this 
      STATUS message applies is specified in the lastDlciReceivedStatus 
      attribute.
      
      The initial value of this attribute is notApplicable."
::= { mpanlSigStatsEntry 12 }

mpanlSigLastDlciReceivedStatus OBJECT-TYPE
   SYNTAX     Unsigned32 (0 | 17..1007)
   ACCESS     read-only
   STATUS     mandatory
   DESCRIPTION
     "This attribute shows the value of the DLCI that has most recently 
      received a STATUS message from the user.
      
      The initial value of this attribute is 0."
::= { mpanlSigStatsEntry 13 }

mpanlSigLastQ933StateReceivedStatus OBJECT-TYPE
   SYNTAX     INTEGER  {
                 null(0),
                 callInitiated(1),
                 outgoingCallProceeding(3),
                 callPresent(6),
                 incomingCallProceeding(9),
                 active(10),
                 disconnectRequest(11),
                 disconnectIndication(12),
                 releaseRequest(19),
                 notApplicable(20) }
   ACCESS     read-only
   STATUS     mandatory
   DESCRIPTION
     "This attribute shows the network Q.933 state of the DLCI that has 
      most recently received a STATUS message from the user. The DLCI 
      to which this STATUS message applies is specified in the 
      lastDlciReceivedStatus attribute.
      
      The initial value of this attribute is notApplicable."
::= { mpanlSigStatsEntry 14 }

mpanlSigLastTimeMsgBlockCongested OBJECT-TYPE
   SYNTAX     EnterpriseDateAndTime (SIZE (0 | 16))
   ACCESS     read-only
   STATUS     mandatory
   DESCRIPTION
     "This attribute displays the most recent time that an SVC DLCI has 
      failed to get a message block due to message block congestion. 
      Exceptional behavior can occur due to this. The DLCI that has most 
      recently encountered this is indicated by the 
      lastDlciWithMsgBlockCongestion attribute. However, all SVC 
      DLCIs may be affected.
      
      The initial value of this attribute is 0000-00-00 00:00."
::= { mpanlSigStatsEntry 15 }

mpanlSigLastDlciWithMsgBlockCongestion OBJECT-TYPE
   SYNTAX     Unsigned32 (0 | 16..1007)
   ACCESS     read-only
   STATUS     mandatory
   DESCRIPTION
     "This attribute shows the value of the DLCI that has most recently 
      failed to get a message block due to message block congestion.
      
      The initial value of this attribute is 0."
::= { mpanlSigStatsEntry 16 }

mpanlSigLapfStatusTable OBJECT-TYPE
   SYNTAX     SEQUENCE OF MpanlSigLapfStatusEntry
   ACCESS     not-accessible
   STATUS     mandatory
   DESCRIPTION
     "This group contains the Q.922 SVC data link layer status."
::= { mpanlSig 18 }

mpanlSigLapfStatusEntry OBJECT-TYPE
   SYNTAX     MpanlSigLapfStatusEntry
   ACCESS     not-accessible
   STATUS     mandatory
   DESCRIPTION
     "An entry in the mpanlSigLapfStatusTable."
   INDEX {
      mpanlIndex,
      mpanlSigIndex }
::= { mpanlSigLapfStatusTable 1 }

MpanlSigLapfStatusEntry ::= SEQUENCE {
   mpanlSigCurrentState
      INTEGER,
   mpanlSigLastStateChangeReason
      INTEGER,
   mpanlSigFrmrReceive
      HexString,
   mpanlSigCurrentQueueSize
      Counter32 }

mpanlSigCurrentState OBJECT-TYPE
   SYNTAX     INTEGER  {
                 disconnected(1),
                 linkSetup(2),
                 disconnectRequest(4),
                 informationTransfer(5),
                 waitingAck(7) }
   ACCESS     read-only
   STATUS     mandatory
   DESCRIPTION
     "This attribute shows the current state of the SVC data link layer 
      interface."
::= { mpanlSigLapfStatusEntry 1 }

mpanlSigLastStateChangeReason OBJECT-TYPE
   SYNTAX     INTEGER  {
                 notStarted(1),
                 abmeEntered(3),
                 abmeReset(5),
                 dmReceived(6),
                 dmSent(7),
                 discReceived(8),
                 discSent(9),
                 frmrReceived(10),
                 n200RetranTimeOut(12),
                 other(13) }
   ACCESS     read-only
   STATUS     mandatory
   DESCRIPTION
     "This attribute shows the reason for the most recent state change.
      notStarted - this is the default state after SVC data link has just been 
      created.
      abmeEntered - SVC data link has entered Asynchronous Balanced 
      Mode after SABME or UA has been received.
      abmeReset - the data link has been reset.
      dmReceived - DM response received.
      dmSent - DM sent.
      discReceived - DISC response received.
      discSent - DISC sent.
      frmrReceived - FRMR received.
      n200RetranTimeOut - retransmitLimit has been exceeded.
      other - unspecified state change reasons. The most likely reason for 
      this is the transition from state waitingAck to state 
      informationTransfer."
::= { mpanlSigLapfStatusEntry 2 }

mpanlSigFrmrReceive OBJECT-TYPE
   SYNTAX     HexString (SIZE (0..8))
   ACCESS     read-only
   STATUS     mandatory
   DESCRIPTION
     "This attribute shows the information field of the FRMR most 
      recently received."
::= { mpanlSigLapfStatusEntry 3 }

mpanlSigCurrentQueueSize OBJECT-TYPE
   SYNTAX     Counter32 
   ACCESS     read-only
   STATUS     mandatory
   DESCRIPTION
     "This attribute shows the current number of frames in the SVC data 
      link layer transmit queue."
::= { mpanlSigLapfStatusEntry 4 }

mpanlSigLapfStatsTable OBJECT-TYPE
   SYNTAX     SEQUENCE OF MpanlSigLapfStatsEntry
   ACCESS     not-accessible
   STATUS     mandatory
   DESCRIPTION
     "This group contains the statistics for the SVC data link layer."
::= { mpanlSig 19 }

mpanlSigLapfStatsEntry OBJECT-TYPE
   SYNTAX     MpanlSigLapfStatsEntry
   ACCESS     not-accessible
   STATUS     mandatory
   DESCRIPTION
     "An entry in the mpanlSigLapfStatsTable."
   INDEX {
      mpanlIndex,
      mpanlSigIndex }
::= { mpanlSigLapfStatsTable 1 }

MpanlSigLapfStatsEntry ::= SEQUENCE {
   mpanlSigStateChange
      Counter32,
   mpanlSigRemoteBusy
      Counter32,
   mpanlSigReceiveRejectFrame
      Counter32,
   mpanlSigAckTimeout
      Counter32,
   mpanlSigIFramesTransmitted
      Counter32,
   mpanlSigIFramesTxDiscarded
      Counter32,
   mpanlSigIFramesReceived
      Counter32,
   mpanlSigIFramesRcvdDiscarded
      Counter32 }

mpanlSigStateChange OBJECT-TYPE
   SYNTAX     Counter32 
   ACCESS     read-only
   STATUS     mandatory
   DESCRIPTION
     "This attribute counts the number of times the SVC data link layer 
      interface has changed state. Frequent state changes may indicate a 
      problem with the line quality. While the data link layer is in 
      informationTransfer state, this counter will increment on each 
      expiry of idleProbeTimer as its state goes from 
      informationTransfer to waitingAck and back. When this count 
      reaches maximum, it wraps to zero."
::= { mpanlSigLapfStatsEntry 1 }

mpanlSigRemoteBusy OBJECT-TYPE
   SYNTAX     Counter32 
   ACCESS     read-only
   STATUS     mandatory
   DESCRIPTION
     "This attribute counts the number of times transmission of an I-frame 
      was unsuccessful due to a perceived remote busy condition 
      (window closed or remote busy). When this count reaches 
      maximum, it wraps to zero."
::= { mpanlSigLapfStatsEntry 2 }

mpanlSigReceiveRejectFrame OBJECT-TYPE
   SYNTAX     Counter32 
   ACCESS     read-only
   STATUS     mandatory
   DESCRIPTION
     "This attribute counts the number of REJ frames received by the 
      interface. When this count reaches maximum, it wraps to zero."
::= { mpanlSigLapfStatsEntry 3 }

mpanlSigAckTimeout OBJECT-TYPE
   SYNTAX     Counter32 
   ACCESS     read-only
   STATUS     mandatory
   DESCRIPTION
     "This attribute counts the number of times the ackTimer has expired. 
      Frequent increments of this counter indicate a problem at the link or 
      improper values have been chosen for ackTimer and ackDelayTimer 
      between the local and remote sides. When this count reaches 
      maximum, it wraps to zero."
::= { mpanlSigLapfStatsEntry 4 }

mpanlSigIFramesTransmitted OBJECT-TYPE
   SYNTAX     Counter32 
   ACCESS     read-only
   STATUS     mandatory
   DESCRIPTION
     "This attribute counts the number of SVC I-frames transmitted to the 
      interface on DLCI 0. An I-frame may be counted more than once if 
      there are retransmissions at the SVC data link layer. When this 
      count reaches maximum, it wraps to zero."
::= { mpanlSigLapfStatsEntry 5 }

mpanlSigIFramesTxDiscarded OBJECT-TYPE
   SYNTAX     Counter32 
   ACCESS     read-only
   STATUS     mandatory
   DESCRIPTION
     "This attribute counts the number of SVC I-frames that are bound for 
      the link but have been discarded. Discard reasons may be one of the 
      following:
      1.	the frame length is beyond allow limit.
      2.	the SVC data link layer is in disconnected state.
      3. 	the transmit queue has been purged because the queue length 
      has reached the reset threshold.
      4.	the transmit queue or the queue waiting for acknowledgment
      has been 			purged because the link cannot be re-established.
      
      When this count reaches maximum, it wraps to zero."
::= { mpanlSigLapfStatsEntry 6 }

mpanlSigIFramesReceived OBJECT-TYPE
   SYNTAX     Counter32 
   ACCESS     read-only
   STATUS     mandatory
   DESCRIPTION
     "This attribute counts the number of SVC I-frames received from the 
      interface. When this count reaches maximum, it wraps to zero."
::= { mpanlSigLapfStatsEntry 7 }

mpanlSigIFramesRcvdDiscarded OBJECT-TYPE
   SYNTAX     Counter32 
   ACCESS     read-only
   STATUS     mandatory
   DESCRIPTION
     "This attribute counts the number of SVC I-frames received but have 
      been discarded. The discard reasons are:
      1.	 incorrect frame size
      2. frame is out of sequence
      3. frame received while the network side of the SVC data link
      layer is not in the informationTransfer or waitingAck state.
      
      When this count reaches maximum, it wraps to zero."
::= { mpanlSigLapfStatsEntry 8 }


-- Mpanl/<n> SignalingMpanl
-- 
-- This component contains attributes relating to the MPANL 
-- signaling DLCI at the MPANL interface. This includes operational 
-- Q.922 (LAPF) information for this DLCI.

mpanlSigMpanl OBJECT IDENTIFIER ::= { mpanl 7 }



mpanlSigMpanlRowStatusTable OBJECT-TYPE
   SYNTAX     SEQUENCE OF MpanlSigMpanlRowStatusEntry
   ACCESS     not-accessible
   STATUS     mandatory
   DESCRIPTION
     "This entry controls the addition and deletion of 
      mpanlSigMpanl components."
::= { mpanlSigMpanl 1 }

mpanlSigMpanlRowStatusEntry OBJECT-TYPE
   SYNTAX     MpanlSigMpanlRowStatusEntry
   ACCESS     not-accessible
   STATUS     mandatory
   DESCRIPTION
     "A single entry in the table represents a single 
      mpanlSigMpanl component."
   INDEX {
      mpanlIndex,
      mpanlSigMpanlIndex }
::= { mpanlSigMpanlRowStatusTable 1 }

MpanlSigMpanlRowStatusEntry ::= SEQUENCE {
   mpanlSigMpanlRowStatus
      RowStatus,
   mpanlSigMpanlComponentName
      DisplayString,
   mpanlSigMpanlStorageType
      StorageType,
   mpanlSigMpanlIndex
      NonReplicated }

mpanlSigMpanlRowStatus OBJECT-TYPE
   SYNTAX     RowStatus 
   ACCESS     read-only
   STATUS     mandatory
   DESCRIPTION
     "This variable is used as the basis for SNMP naming of
      mpanlSigMpanl components.
      These components cannot be added nor deleted."
::= { mpanlSigMpanlRowStatusEntry 1 }

mpanlSigMpanlComponentName OBJECT-TYPE
   SYNTAX     DisplayString 
   ACCESS     read-only
   STATUS     mandatory
   DESCRIPTION
     "This variable provides the component's string name for
      use with the ASCII Console Interface"
::= { mpanlSigMpanlRowStatusEntry 2 }

mpanlSigMpanlStorageType OBJECT-TYPE
   SYNTAX     StorageType 
   ACCESS     read-only
   STATUS     mandatory
   DESCRIPTION
     "This variable represents the storage type value for the
      mpanlSigMpanl tables."
::= { mpanlSigMpanlRowStatusEntry 4 }

mpanlSigMpanlIndex OBJECT-TYPE
   SYNTAX     NonReplicated 
   ACCESS     not-accessible
   STATUS     mandatory
   DESCRIPTION
     "This variable represents the index for the mpanlSigMpanl tables."
::= { mpanlSigMpanlRowStatusEntry 10 }

mpanlSigMpanlStateTable OBJECT-TYPE
   SYNTAX     SEQUENCE OF MpanlSigMpanlStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mpanlSigMpanl 10 }

mpanlSigMpanlStateEntry OBJECT-TYPE
   SYNTAX     MpanlSigMpanlStateEntry
   ACCESS     not-accessible
   STATUS     mandatory
   DESCRIPTION
     "An entry in the mpanlSigMpanlStateTable."
   INDEX {
      mpanlIndex,
      mpanlSigMpanlIndex }
::= { mpanlSigMpanlStateTable 1 }

MpanlSigMpanlStateEntry ::= SEQUENCE {
   mpanlSigMpanlAdminState
      INTEGER,
   mpanlSigMpanlOperationalState
      INTEGER,
   mpanlSigMpanlUsageState
      INTEGER }

mpanlSigMpanlAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mpanlSigMpanlStateEntry 1 }

mpanlSigMpanlOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mpanlSigMpanlStateEntry 2 }

mpanlSigMpanlUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mpanlSigMpanlStateEntry 3 }

mpanlSigMpanlProfileTable OBJECT-TYPE
   SYNTAX     SEQUENCE OF MpanlSigMpanlProfileEntry
   ACCESS     not-accessible
   STATUS     mandatory
   DESCRIPTION
     "This group contains attributes which are populated by the 
      information received from the MPA in the Profile Association 
      command of the MPANL protocol."
::= { mpanlSigMpanl 11 }

mpanlSigMpanlProfileEntry OBJECT-TYPE
   SYNTAX     MpanlSigMpanlProfileEntry
   ACCESS     not-accessible
   STATUS     mandatory
   DESCRIPTION
     "An entry in the mpanlSigMpanlProfileTable."
   INDEX {
      mpanlIndex,
      mpanlSigMpanlIndex }
::= { mpanlSigMpanlProfileTable 1 }

MpanlSigMpanlProfileEntry ::= SEQUENCE {
   mpanlSigMpanlDteCustomerId
      Unsigned32,
   mpanlSigMpanlDteNodeId
      Unsigned32,
   mpanlSigMpanlDteComponentName
      AsciiString,
   mpanlSigMpanlHighestDlci
      Unsigned32 }

mpanlSigMpanlDteCustomerId OBJECT-TYPE
   SYNTAX     Unsigned32 (0 | 1..8191)
   ACCESS     read-only
   STATUS     mandatory
   DESCRIPTION
     "This attribute indicates the Customer ID of the MPA connected to 
      this Mpanl interface."
::= { mpanlSigMpanlProfileEntry 1 }

mpanlSigMpanlDteNodeId OBJECT-TYPE
   SYNTAX     Unsigned32 (1..4095)
   ACCESS     read-only
   STATUS     mandatory
   DESCRIPTION
     "This attribute indicates the nodeId that uniquely identifies the MPA 
      connected to this Mpanl interface."
::= { mpanlSigMpanlProfileEntry 2 }

mpanlSigMpanlDteComponentName OBJECT-TYPE
   SYNTAX     AsciiString (SIZE (1..255))
   ACCESS     read-only
   STATUS     mandatory
   DESCRIPTION
     "This attribute indicates the component name provided by the MPA 
      connected to this MPANL interface."
::= { mpanlSigMpanlProfileEntry 3 }

mpanlSigMpanlHighestDlci OBJECT-TYPE
   SYNTAX     Unsigned32 (0 | 17..1007)
   ACCESS     read-only
   STATUS     mandatory
   DESCRIPTION
     "This gives the highest DLCI that the Mpanl interface will assign to 
      an SVC. This value is populated by information provided in the 
      DLCI Range Information Element of the MPANL Profile 
      Association command received from the MPA."
::= { mpanlSigMpanlProfileEntry 4 }

mpanlSigMpanlStatsTable OBJECT-TYPE
   SYNTAX     SEQUENCE OF MpanlSigMpanlStatsEntry
   ACCESS     not-accessible
   STATUS     mandatory
   DESCRIPTION
     "This group contains the statistics related to the Mpanl signaling 
      layer at the interface level."
::= { mpanlSigMpanl 12 }

mpanlSigMpanlStatsEntry OBJECT-TYPE
   SYNTAX     MpanlSigMpanlStatsEntry
   ACCESS     not-accessible
   STATUS     mandatory
   DESCRIPTION
     "An entry in the mpanlSigMpanlStatsTable."
   INDEX {
      mpanlIndex,
      mpanlSigMpanlIndex }
::= { mpanlSigMpanlStatsTable 1 }

MpanlSigMpanlStatsEntry ::= SEQUENCE {
   mpanlSigMpanlProtocolErrors
      Counter32,
   mpanlSigMpanlSap0CommandsRx
      Counter32,
   mpanlSigMpanlSap0CommandsTx
      Counter32,
   mpanlSigMpanlSapXCommandsRx
      Counter32,
   mpanlSigMpanlSapXCommandsTx
      Counter32 }

mpanlSigMpanlProtocolErrors OBJECT-TYPE
   SYNTAX     Counter32 
   ACCESS     read-only
   STATUS     mandatory
   DESCRIPTION
     "This attribute counts the number of times an Mpanl protocol error 
      has occurred. Any one of the following events constitutes a protocol 
      error:
      1. DNA association before profile association.
      2. Mandatory IE absent in SAPcommands.
      3. Invalid length of IE/sub-info fields in SAP command.
      When this count reaches maximum, it wraps to zero."
::= { mpanlSigMpanlStatsEntry 1 }

mpanlSigMpanlSap0CommandsRx OBJECT-TYPE
   SYNTAX     Counter32 
   ACCESS     read-only
   STATUS     mandatory
   DESCRIPTION
     "This attribute counts the number of SAP-0 commands received on 
      the MPANL DLCI 16. This counter wraps to zero."
::= { mpanlSigMpanlStatsEntry 2 }

mpanlSigMpanlSap0CommandsTx OBJECT-TYPE
   SYNTAX     Counter32 
   ACCESS     read-only
   STATUS     mandatory
   DESCRIPTION
     "This attribute counts the number of SAP-0 commands sent on the 
      MPANL DLCI 16. This counter wraps to zero."
::= { mpanlSigMpanlStatsEntry 3 }

mpanlSigMpanlSapXCommandsRx OBJECT-TYPE
   SYNTAX     Counter32 
   ACCESS     read-only
   STATUS     mandatory
   DESCRIPTION
     "This attribute counts the number of SAP-X commands received on 
      the MPANL DLCI 16. This counter wraps to zero."
::= { mpanlSigMpanlStatsEntry 4 }

mpanlSigMpanlSapXCommandsTx OBJECT-TYPE
   SYNTAX     Counter32 
   ACCESS     read-only
   STATUS     mandatory
   DESCRIPTION
     "This attribute counts the number of SAP-X commands sent on the 
      MPANL DLCI 16. This counter wraps to zero."
::= { mpanlSigMpanlStatsEntry 5 }

mpanlSigMpanlLapfStatusTable OBJECT-TYPE
   SYNTAX     SEQUENCE OF MpanlSigMpanlLapfStatusEntry
   ACCESS     not-accessible
   STATUS     mandatory
   DESCRIPTION
     "This group contains the Q.922 SVC data link layer status."
::= { mpanlSigMpanl 13 }

mpanlSigMpanlLapfStatusEntry OBJECT-TYPE
   SYNTAX     MpanlSigMpanlLapfStatusEntry
   ACCESS     not-accessible
   STATUS     mandatory
   DESCRIPTION
     "An entry in the mpanlSigMpanlLapfStatusTable."
   INDEX {
      mpanlIndex,
      mpanlSigMpanlIndex }
::= { mpanlSigMpanlLapfStatusTable 1 }

MpanlSigMpanlLapfStatusEntry ::= SEQUENCE {
   mpanlSigMpanlCurrentState
      INTEGER,
   mpanlSigMpanlLastStateChangeReason
      INTEGER,
   mpanlSigMpanlFrmrReceive
      HexString,
   mpanlSigMpanlCurrentQueueSize
      Counter32 }

mpanlSigMpanlCurrentState OBJECT-TYPE
   SYNTAX     INTEGER  {
                 disconnected(1),
                 linkSetup(2),
                 disconnectRequest(4),
                 informationTransfer(5),
                 waitingAck(7) }
   ACCESS     read-only
   STATUS     mandatory
   DESCRIPTION
     "This attribute shows the current state of the SVC data link layer 
      interface."
::= { mpanlSigMpanlLapfStatusEntry 1 }

mpanlSigMpanlLastStateChangeReason OBJECT-TYPE
   SYNTAX     INTEGER  {
                 notStarted(1),
                 abmeEntered(3),
                 abmeReset(5),
                 dmReceived(6),
                 dmSent(7),
                 discReceived(8),
                 discSent(9),
                 frmrReceived(10),
                 n200RetranTimeOut(12),
                 other(13) }
   ACCESS     read-only
   STATUS     mandatory
   DESCRIPTION
     "This attribute shows the reason for the most recent state change.
      notStarted - this is the default state after SVC data link has just been 
      created.
      abmeEntered - SVC data link has entered Asynchronous Balanced 
      Mode after SABME or UA has been received.
      abmeReset - the data link has been reset.
      dmReceived - DM response received.
      dmSent - DM sent.
      discReceived - DISC response received.
      discSent - DISC sent.
      frmrReceived - FRMR received.
      n200RetranTimeOut - retransmitLimit has been exceeded.
      other - unspecified state change reasons. The most likely reason for 
      this is the transition from state waitingAck to state 
      informationTransfer."
::= { mpanlSigMpanlLapfStatusEntry 2 }

mpanlSigMpanlFrmrReceive OBJECT-TYPE
   SYNTAX     HexString (SIZE (0..8))
   ACCESS     read-only
   STATUS     mandatory
   DESCRIPTION
     "This attribute shows the information field of the FRMR most 
      recently received."
::= { mpanlSigMpanlLapfStatusEntry 3 }

mpanlSigMpanlCurrentQueueSize OBJECT-TYPE
   SYNTAX     Counter32 
   ACCESS     read-only
   STATUS     mandatory
   DESCRIPTION
     "This attribute shows the current number of frames in the SVC data 
      link layer transmit queue."
::= { mpanlSigMpanlLapfStatusEntry 4 }

mpanlSigMpanlLapfStatsTable OBJECT-TYPE
   SYNTAX     SEQUENCE OF MpanlSigMpanlLapfStatsEntry
   ACCESS     not-accessible
   STATUS     mandatory
   DESCRIPTION
     "This group contains the statistics for the SVC data link layer."
::= { mpanlSigMpanl 14 }

mpanlSigMpanlLapfStatsEntry OBJECT-TYPE
   SYNTAX     MpanlSigMpanlLapfStatsEntry
   ACCESS     not-accessible
   STATUS     mandatory
   DESCRIPTION
     "An entry in the mpanlSigMpanlLapfStatsTable."
   INDEX {
      mpanlIndex,
      mpanlSigMpanlIndex }
::= { mpanlSigMpanlLapfStatsTable 1 }

MpanlSigMpanlLapfStatsEntry ::= SEQUENCE {
   mpanlSigMpanlStateChange
      Counter32,
   mpanlSigMpanlRemoteBusy
      Counter32,
   mpanlSigMpanlReceiveRejectFrame
      Counter32,
   mpanlSigMpanlAckTimeout
      Counter32,
   mpanlSigMpanlIFramesTransmitted
      Counter32,
   mpanlSigMpanlIFramesTxDiscarded
      Counter32,
   mpanlSigMpanlIFramesReceived
      Counter32,
   mpanlSigMpanlIFramesRcvdDiscarded
      Counter32 }

mpanlSigMpanlStateChange OBJECT-TYPE
   SYNTAX     Counter32 
   ACCESS     read-only
   STATUS     mandatory
   DESCRIPTION
     "This attribute counts the number of times the SVC data link layer 
      interface has changed state. Frequent state changes may indicate a 
      problem with the line quality. While the data link layer is in 
      informationTransfer state, this counter will increment on each 
      expiry of idleProbeTimer as its state goes from 
      informationTransfer to waitingAck and back. When this count 
      reaches maximum, it wraps to zero."
::= { mpanlSigMpanlLapfStatsEntry 1 }

mpanlSigMpanlRemoteBusy OBJECT-TYPE
   SYNTAX     Counter32 
   ACCESS     read-only
   STATUS     mandatory
   DESCRIPTION
     "This attribute counts the number of times transmission of an I-frame 
      was unsuccessful due to a perceived remote busy condition 
      (window closed or remote busy). When this count reaches 
      maximum, it wraps to zero."
::= { mpanlSigMpanlLapfStatsEntry 2 }

mpanlSigMpanlReceiveRejectFrame OBJECT-TYPE
   SYNTAX     Counter32 
   ACCESS     read-only
   STATUS     mandatory
   DESCRIPTION
     "This attribute counts the number of REJ frames received by the 
      interface. When this count reaches maximum, it wraps to zero."
::= { mpanlSigMpanlLapfStatsEntry 3 }

mpanlSigMpanlAckTimeout OBJECT-TYPE
   SYNTAX     Counter32 
   ACCESS     read-only
   STATUS     mandatory
   DESCRIPTION
     "This attribute counts the number of times the ackTimer has expired. 
      Frequent increments of this counter indicate a problem at the link or 
      improper values have been chosen for ackTimer and ackDelayTimer 
      between the local and remote sides. When this count reaches 
      maximum, it wraps to zero."
::= { mpanlSigMpanlLapfStatsEntry 4 }

mpanlSigMpanlIFramesTransmitted OBJECT-TYPE
   SYNTAX     Counter32 
   ACCESS     read-only
   STATUS     mandatory
   DESCRIPTION
     "This attribute counts the number of SVC I-frames transmitted to the 
      interface on DLCI 0. An I-frame may be counted more than once if 
      there are retransmissions at the SVC data link layer. When this 
      count reaches maximum, it wraps to zero."
::= { mpanlSigMpanlLapfStatsEntry 5 }

mpanlSigMpanlIFramesTxDiscarded OBJECT-TYPE
   SYNTAX     Counter32 
   ACCESS     read-only
   STATUS     mandatory
   DESCRIPTION
     "This attribute counts the number of SVC I-frames that are bound for 
      the link but have been discarded. Discard reasons may be one of the 
      following:
      1.	the frame length is beyond allow limit.
      2.	the SVC data link layer is in disconnected state.
      3. 	the transmit queue has been purged because the queue length 
      has reached the reset threshold.
      4.	the transmit queue or the queue waiting for acknowledgment
      has been 			purged because the link cannot be re-established.
      
      When this count reaches maximum, it wraps to zero."
::= { mpanlSigMpanlLapfStatsEntry 6 }

mpanlSigMpanlIFramesReceived OBJECT-TYPE
   SYNTAX     Counter32 
   ACCESS     read-only
   STATUS     mandatory
   DESCRIPTION
     "This attribute counts the number of SVC I-frames received from the 
      interface. When this count reaches maximum, it wraps to zero."
::= { mpanlSigMpanlLapfStatsEntry 7 }

mpanlSigMpanlIFramesRcvdDiscarded OBJECT-TYPE
   SYNTAX     Counter32 
   ACCESS     read-only
   STATUS     mandatory
   DESCRIPTION
     "This attribute counts the number of SVC I-frames received but have 
      been discarded. The discard reasons are:
      1.	 incorrect frame size
      2. frame is out of sequence
      3. frame received while the network side of the SVC data link
      layer is not in the informationTransfer or waitingAck state.
      
      When this count reaches maximum, it wraps to zero."
::= { mpanlSigMpanlLapfStatsEntry 8 }


-- Mpanl/n Lmi
-- This component defines the parameters for implementing the Local 
-- Management Interface protocol.

mpanlLmi OBJECT IDENTIFIER ::= { mpanl 8 }



mpanlLmiRowStatusTable OBJECT-TYPE
   SYNTAX     SEQUENCE OF MpanlLmiRowStatusEntry
   ACCESS     not-accessible
   STATUS     mandatory
   DESCRIPTION
     "This entry controls the addition and deletion of 
      mpanlLmi components."
::= { mpanlLmi 1 }

mpanlLmiRowStatusEntry OBJECT-TYPE
   SYNTAX     MpanlLmiRowStatusEntry
   ACCESS     not-accessible
   STATUS     mandatory
   DESCRIPTION
     "A single entry in the table represents a single 
      mpanlLmi component."
   INDEX {
      mpanlIndex,
      mpanlLmiIndex }
::= { mpanlLmiRowStatusTable 1 }

MpanlLmiRowStatusEntry ::= SEQUENCE {
   mpanlLmiRowStatus
      RowStatus,
   mpanlLmiComponentName
      DisplayString,
   mpanlLmiStorageType
      StorageType,
   mpanlLmiIndex
      NonReplicated }

mpanlLmiRowStatus OBJECT-TYPE
   SYNTAX     RowStatus 
   ACCESS     read-only
   STATUS     mandatory
   DESCRIPTION
     "This variable is used as the basis for SNMP naming of
      mpanlLmi components.
      These components cannot be added nor deleted."
::= { mpanlLmiRowStatusEntry 1 }

mpanlLmiComponentName OBJECT-TYPE
   SYNTAX     DisplayString 
   ACCESS     read-only
   STATUS     mandatory
   DESCRIPTION
     "This variable provides the component's string name for
      use with the ASCII Console Interface"
::= { mpanlLmiRowStatusEntry 2 }

mpanlLmiStorageType OBJECT-TYPE
   SYNTAX     StorageType 
   ACCESS     read-only
   STATUS     mandatory
   DESCRIPTION
     "This variable represents the storage type value for the
      mpanlLmi tables."
::= { mpanlLmiRowStatusEntry 4 }

mpanlLmiIndex OBJECT-TYPE
   SYNTAX     NonReplicated 
   ACCESS     not-accessible
   STATUS     mandatory
   DESCRIPTION
     "This variable represents the index for the mpanlLmi tables."
::= { mpanlLmiRowStatusEntry 10 }

mpanlLmiParmsTable OBJECT-TYPE
   SYNTAX     SEQUENCE OF MpanlLmiParmsEntry
   ACCESS     not-accessible
   STATUS     mandatory
   DESCRIPTION
     "This group contains the provisionable attributes of the Local 
      Management Interface component."
::= { mpanlLmi 10 }

mpanlLmiParmsEntry OBJECT-TYPE
   SYNTAX     MpanlLmiParmsEntry
   ACCESS     not-accessible
   STATUS     mandatory
   DESCRIPTION
     "An entry in the mpanlLmiParmsTable."
   INDEX {
      mpanlIndex,
      mpanlLmiIndex }
::= { mpanlLmiParmsTable 1 }

MpanlLmiParmsEntry ::= SEQUENCE {
   mpanlLmiProcedures
      INTEGER }

mpanlLmiProcedures OBJECT-TYPE
   SYNTAX     INTEGER  {
                 none(0),
                 vendorForum(1),
                 ansi(2),
                 ccitt(3) }
   ACCESS     read-only
   STATUS     mandatory
   DESCRIPTION
     "This attribute selects the procedures to be used for the Local 
      Management Interface. For the MPANL service this attribute is 
      always set to none.
      
      none	:	 no Local Management Interface procedures are running on 
      this interface. This accomodates MPANL user equipment that have 
      not implemented any LMI procedures. The remaining attributes of 
      this group will be ignored.
      
      vendorForum	:	Local Management Interface procedures from the 
      Vendor Forum specification are supported on this interface. DLCI 
      1023 is used for the LMI protocol.
      
      ansi: 	Local Management Interface procedures from the ANSI 
      specification are supported. DLCI 0 is used for the LMI protocol.
      
      ccitt: Local Management Interface procedures from the CCITT 
      specification are supported. DLCI 0 is used for the LMI protocol."
   DEFVAL     { none }
::= { mpanlLmiParmsEntry 1 }

mpanlLmiStateTable OBJECT-TYPE
   SYNTAX     SEQUENCE OF MpanlLmiStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mpanlLmi 12 }

mpanlLmiStateEntry OBJECT-TYPE
   SYNTAX     MpanlLmiStateEntry
   ACCESS     not-accessible
   STATUS     mandatory
   DESCRIPTION
     "An entry in the mpanlLmiStateTable."
   INDEX {
      mpanlIndex,
      mpanlLmiIndex }
::= { mpanlLmiStateTable 1 }

MpanlLmiStateEntry ::= SEQUENCE {
   mpanlLmiAdminState
      INTEGER,
   mpanlLmiOperationalState
      INTEGER,
   mpanlLmiUsageState
      INTEGER }

mpanlLmiAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mpanlLmiStateEntry 1 }

mpanlLmiOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mpanlLmiStateEntry 2 }

mpanlLmiUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mpanlLmiStateEntry 3 }


-- Mpanl/n VoiceOverFrameRelay
-- This component, when provisioned, provides VoFr link layer 
-- framing capability to the containing Mpanl instance.

mpanlVoFr OBJECT IDENTIFIER ::= { mpanl 18 }



mpanlVoFrRowStatusTable OBJECT-TYPE
   SYNTAX     SEQUENCE OF MpanlVoFrRowStatusEntry
   ACCESS     not-accessible
   STATUS     mandatory
   DESCRIPTION
     "This entry controls the addition and deletion of 
      mpanlVoFr components."
::= { mpanlVoFr 1 }

mpanlVoFrRowStatusEntry OBJECT-TYPE
   SYNTAX     MpanlVoFrRowStatusEntry
   ACCESS     not-accessible
   STATUS     mandatory
   DESCRIPTION
     "A single entry in the table represents a single 
      mpanlVoFr component."
   INDEX {
      mpanlIndex,
      mpanlVoFrIndex }
::= { mpanlVoFrRowStatusTable 1 }

MpanlVoFrRowStatusEntry ::= SEQUENCE {
   mpanlVoFrRowStatus
      RowStatus,
   mpanlVoFrComponentName
      DisplayString,
   mpanlVoFrStorageType
      StorageType,
   mpanlVoFrIndex
      NonReplicated }

mpanlVoFrRowStatus OBJECT-TYPE
   SYNTAX     RowStatus 
   ACCESS     read-only
   STATUS     mandatory
   DESCRIPTION
     "This variable is used as the basis for SNMP naming of
      mpanlVoFr components.
      These components cannot be added nor deleted."
::= { mpanlVoFrRowStatusEntry 1 }

mpanlVoFrComponentName OBJECT-TYPE
   SYNTAX     DisplayString 
   ACCESS     read-only
   STATUS     mandatory
   DESCRIPTION
     "This variable provides the component's string name for
      use with the ASCII Console Interface"
::= { mpanlVoFrRowStatusEntry 2 }

mpanlVoFrStorageType OBJECT-TYPE
   SYNTAX     StorageType 
   ACCESS     read-only
   STATUS     mandatory
   DESCRIPTION
     "This variable represents the storage type value for the
      mpanlVoFr tables."
::= { mpanlVoFrRowStatusEntry 4 }

mpanlVoFrIndex OBJECT-TYPE
   SYNTAX     NonReplicated 
   ACCESS     not-accessible
   STATUS     mandatory
   DESCRIPTION
     "This variable represents the index for the mpanlVoFr tables."
::= { mpanlVoFrRowStatusEntry 10 }

mpanlVoFrOperTable OBJECT-TYPE
   SYNTAX     SEQUENCE OF MpanlVoFrOperEntry
   ACCESS     not-accessible
   STATUS     mandatory
   DESCRIPTION
     "This group contains operational attributes of the VoFr component."
::= { mpanlVoFr 10 }

mpanlVoFrOperEntry OBJECT-TYPE
   SYNTAX     MpanlVoFrOperEntry
   ACCESS     not-accessible
   STATUS     mandatory
   DESCRIPTION
     "An entry in the mpanlVoFrOperTable."
   INDEX {
      mpanlIndex,
      mpanlVoFrIndex }
::= { mpanlVoFrOperTable 1 }

MpanlVoFrOperEntry ::= SEQUENCE {
   mpanlVoFrMaximumFrameSize
      Counter32,
   mpanlVoFrTransmitInformationRate
      Counter32 }

mpanlVoFrMaximumFrameSize OBJECT-TYPE
   SYNTAX     Counter32 
   ACCESS     read-only
   STATUS     mandatory
   DESCRIPTION
     "This attribute indicates the maximum size of VoFr frames 
      transmitted to MPA. The size excludes HDLC flags and CRC octets. 
      MPA signals the required value as part of the MPANL initial 
      staging, which is then used to set the value of this attribute. Default 
      value is used before MPANL staging is completed."
::= { mpanlVoFrOperEntry 1 }

mpanlVoFrTransmitInformationRate OBJECT-TYPE
   SYNTAX     Counter32 
   ACCESS     read-only
   STATUS     mandatory
   DESCRIPTION
     "This attribute indicates the maximum information rate towards 
      MPA. Value may change over time, as signalled by MPA. Default 
      value is used before MPANL staging is completed."
::= { mpanlVoFrOperEntry 2 }

mpanlVoFrStatsTable OBJECT-TYPE
   SYNTAX     SEQUENCE OF MpanlVoFrStatsEntry
   ACCESS     not-accessible
   STATUS     mandatory
   DESCRIPTION
     "This group contains statistics attributes of the VoFr component."
::= { mpanlVoFr 11 }

mpanlVoFrStatsEntry OBJECT-TYPE
   SYNTAX     MpanlVoFrStatsEntry
   ACCESS     not-accessible
   STATUS     mandatory
   DESCRIPTION
     "An entry in the mpanlVoFrStatsTable."
   INDEX {
      mpanlIndex,
      mpanlVoFrIndex }
::= { mpanlVoFrStatsTable 1 }

MpanlVoFrStatsEntry ::= SEQUENCE {
   mpanlVoFrFragmentedHighestPriorityFrames
      Counter32,
   mpanlVoFrLostFragmentsFromIf
      Counter32,
   mpanlVoFrProtocolViolationsFromIf
      Counter32 }

mpanlVoFrFragmentedHighestPriorityFrames OBJECT-TYPE
   SYNTAX     Counter32 
   ACCESS     read-only
   STATUS     mandatory
   DESCRIPTION
     "This attribute counts egress frames with the highest priority, which 
      had to be fragmented because they were larger than 
      maximumFrameSize. This could happen when a data call is setup to 
      use the highest emission priority, or MPA is provisioned with too 
      low maximum frame size. When the maximum is reached the count 
      wraps to zero."
::= { mpanlVoFrStatsEntry 1 }

mpanlVoFrLostFragmentsFromIf OBJECT-TYPE
   SYNTAX     Counter32 
   ACCESS     read-only
   STATUS     mandatory
   DESCRIPTION
     "This attribute counts lost VoFr fragments from the interface. 
      Presence of lost fragments indicates a link problem. Note that lost 
      whole frames cannot be detected. When the maximum is reached 
      the count wraps to zero."
::= { mpanlVoFrStatsEntry 5 }

mpanlVoFrProtocolViolationsFromIf OBJECT-TYPE
   SYNTAX     Counter32 
   ACCESS     read-only
   STATUS     mandatory
   DESCRIPTION
     "This attribute counts VoFr protocol violations detected in the data 
      from the interface. When the maximum is reached the count wraps 
      to zero."
::= { mpanlVoFrStatsEntry 6 }


-- Mpanl/n FrMuxSetup
-- This component contains operational attributes for egress traffic 
-- shaping as well as the component name of the FrMux Dlci to which 
-- this Mpanl/n is associated.

mpanlFrMuxSetup OBJECT IDENTIFIER ::= { mpanl 19 }



mpanlFrMuxSetupRowStatusTable OBJECT-TYPE
   SYNTAX     SEQUENCE OF MpanlFrMuxSetupRowStatusEntry
   ACCESS     not-accessible
   STATUS     mandatory
   DESCRIPTION
     "This entry controls the addition and deletion of 
      mpanlFrMuxSetup components."
::= { mpanlFrMuxSetup 1 }

mpanlFrMuxSetupRowStatusEntry OBJECT-TYPE
   SYNTAX     MpanlFrMuxSetupRowStatusEntry
   ACCESS     not-accessible
   STATUS     mandatory
   DESCRIPTION
     "A single entry in the table represents a single 
      mpanlFrMuxSetup component."
   INDEX {
      mpanlIndex,
      mpanlFrMuxSetupIndex }
::= { mpanlFrMuxSetupRowStatusTable 1 }

MpanlFrMuxSetupRowStatusEntry ::= SEQUENCE {
   mpanlFrMuxSetupRowStatus
      RowStatus,
   mpanlFrMuxSetupComponentName
      DisplayString,
   mpanlFrMuxSetupStorageType
      StorageType,
   mpanlFrMuxSetupIndex
      NonReplicated }

mpanlFrMuxSetupRowStatus OBJECT-TYPE
   SYNTAX     RowStatus 
   ACCESS     read-write
   STATUS     mandatory
   DESCRIPTION
     "This variable is used as the basis for SNMP naming of
      mpanlFrMuxSetup components.
      These components can be added and deleted."
::= { mpanlFrMuxSetupRowStatusEntry 1 }

mpanlFrMuxSetupComponentName OBJECT-TYPE
   SYNTAX     DisplayString 
   ACCESS     read-only
   STATUS     mandatory
   DESCRIPTION
     "This variable provides the component's string name for
      use with the ASCII Console Interface"
::= { mpanlFrMuxSetupRowStatusEntry 2 }

mpanlFrMuxSetupStorageType OBJECT-TYPE
   SYNTAX     StorageType 
   ACCESS     read-only
   STATUS     mandatory
   DESCRIPTION
     "This variable represents the storage type value for the
      mpanlFrMuxSetup tables."
::= { mpanlFrMuxSetupRowStatusEntry 4 }

mpanlFrMuxSetupIndex OBJECT-TYPE
   SYNTAX     NonReplicated 
   ACCESS     not-accessible
   STATUS     mandatory
   DESCRIPTION
     "This variable represents the index for the mpanlFrMuxSetup tables."
::= { mpanlFrMuxSetupRowStatusEntry 10 }

mpanlFrMuxSetupOpTable OBJECT-TYPE
   SYNTAX     SEQUENCE OF MpanlFrMuxSetupOpEntry
   ACCESS     not-accessible
   STATUS     mandatory
   DESCRIPTION
     "This group contains the following operational parameters: 
      committedInformationRate of the PVC connection used for 
      tunnelling the MPANL traffic, and the component name of the Dlci 
      which carries the traffic for this MPANL."
::= { mpanlFrMuxSetup 11 }

mpanlFrMuxSetupOpEntry OBJECT-TYPE
   SYNTAX     MpanlFrMuxSetupOpEntry
   ACCESS     not-accessible
   STATUS     mandatory
   DESCRIPTION
     "An entry in the mpanlFrMuxSetupOpTable."
   INDEX {
      mpanlIndex,
      mpanlFrMuxSetupIndex }
::= { mpanlFrMuxSetupOpTable 1 }

MpanlFrMuxSetupOpEntry ::= SEQUENCE {
   mpanlFrMuxSetupCommittedInformationRate
      Unsigned32,
   mpanlFrMuxSetupDlciCompName
      RowPointer }

mpanlFrMuxSetupCommittedInformationRate OBJECT-TYPE
   SYNTAX     Unsigned32 (16000..4294967295)
   ACCESS     read-only
   STATUS     mandatory
   DESCRIPTION
     "This attribute specifies, in bit/s, the committed information rate 
      (CIR) to which the traffic transmitted towards the interface is 
      shaped."
   DEFVAL     { 16000 }
::= { mpanlFrMuxSetupOpEntry 1 }

mpanlFrMuxSetupDlciCompName OBJECT-TYPE
   SYNTAX     RowPointer 
   ACCESS     read-only
   STATUS     mandatory
   DESCRIPTION
     "This attribute specifies the component name of the Dlci with which 
      the application using this FrMuxSetup component is associated. The 
      name is a string FrMux/n Dlci/m. For a PVC this is the same 
      component name as provisioned under the subcomponent 
      FrMuxPvcSetup."
::= { mpanlFrMuxSetupOpEntry 2 }


-- Mpanl/n FrMuxSetup PvcSetup
-- This component contains provisionable attributes for setting up a 
-- Dlci associated with the application using this component. The Dlci 
-- is of a PVC type. 

mpanlFrMuxSetupPvcSetup OBJECT IDENTIFIER ::= { mpanlFrMuxSetup 2 }



mpanlFrMuxSetupPvcSetupRowStatusTable OBJECT-TYPE
   SYNTAX     SEQUENCE OF MpanlFrMuxSetupPvcSetupRowStatusEntry
   ACCESS     not-accessible
   STATUS     mandatory
   DESCRIPTION
     "This entry controls the addition and deletion of 
      mpanlFrMuxSetupPvcSetup components."
::= { mpanlFrMuxSetupPvcSetup 1 }

mpanlFrMuxSetupPvcSetupRowStatusEntry OBJECT-TYPE
   SYNTAX     MpanlFrMuxSetupPvcSetupRowStatusEntry
   ACCESS     not-accessible
   STATUS     mandatory
   DESCRIPTION
     "A single entry in the table represents a single 
      mpanlFrMuxSetupPvcSetup component."
   INDEX {
      mpanlIndex,
      mpanlFrMuxSetupIndex,
      mpanlFrMuxSetupPvcSetupIndex }
::= { mpanlFrMuxSetupPvcSetupRowStatusTable 1 }

MpanlFrMuxSetupPvcSetupRowStatusEntry ::= SEQUENCE {
   mpanlFrMuxSetupPvcSetupRowStatus
      RowStatus,
   mpanlFrMuxSetupPvcSetupComponentName
      DisplayString,
   mpanlFrMuxSetupPvcSetupStorageType
      StorageType,
   mpanlFrMuxSetupPvcSetupIndex
      NonReplicated }

mpanlFrMuxSetupPvcSetupRowStatus OBJECT-TYPE
   SYNTAX     RowStatus 
   ACCESS     read-only
   STATUS     mandatory
   DESCRIPTION
     "This variable is used as the basis for SNMP naming of
      mpanlFrMuxSetupPvcSetup components.
      These components cannot be added nor deleted."
::= { mpanlFrMuxSetupPvcSetupRowStatusEntry 1 }

mpanlFrMuxSetupPvcSetupComponentName OBJECT-TYPE
   SYNTAX     DisplayString 
   ACCESS     read-only
   STATUS     mandatory
   DESCRIPTION
     "This variable provides the component's string name for
      use with the ASCII Console Interface"
::= { mpanlFrMuxSetupPvcSetupRowStatusEntry 2 }

mpanlFrMuxSetupPvcSetupStorageType OBJECT-TYPE
   SYNTAX     StorageType 
   ACCESS     read-only
   STATUS     mandatory
   DESCRIPTION
     "This variable represents the storage type value for the
      mpanlFrMuxSetupPvcSetup tables."
::= { mpanlFrMuxSetupPvcSetupRowStatusEntry 4 }

mpanlFrMuxSetupPvcSetupIndex OBJECT-TYPE
   SYNTAX     NonReplicated 
   ACCESS     not-accessible
   STATUS     mandatory
   DESCRIPTION
     "This variable represents the index for the mpanlFrMuxSetupPvcSetup tables."
::= { mpanlFrMuxSetupPvcSetupRowStatusEntry 10 }

mpanlFrMuxSetupPvcSetupProvTable OBJECT-TYPE
   SYNTAX     SEQUENCE OF MpanlFrMuxSetupPvcSetupProvEntry
   ACCESS     not-accessible
   STATUS     mandatory
   DESCRIPTION
     "This group contains provisionable attributes for setting up a Dlci 
      associated with the application using the FrMuxSetup component. 
      The Dlci is of the PVC type."
::= { mpanlFrMuxSetupPvcSetup 10 }

mpanlFrMuxSetupPvcSetupProvEntry OBJECT-TYPE
   SYNTAX     MpanlFrMuxSetupPvcSetupProvEntry
   ACCESS     not-accessible
   STATUS     mandatory
   DESCRIPTION
     "An entry in the mpanlFrMuxSetupPvcSetupProvTable."
   INDEX {
      mpanlIndex,
      mpanlFrMuxSetupIndex,
      mpanlFrMuxSetupPvcSetupIndex }
::= { mpanlFrMuxSetupPvcSetupProvTable 1 }

MpanlFrMuxSetupPvcSetupProvEntry ::= SEQUENCE {
   mpanlFrMuxSetupPvcSetupDlciName
      Link }

mpanlFrMuxSetupPvcSetupDlciName OBJECT-TYPE
   SYNTAX     Link 
   ACCESS     read-write
   STATUS     mandatory
   DESCRIPTION
     "This attribute is the link to the Dlci which is associated with the 
      application using the FrMuxSetup component."
::= { mpanlFrMuxSetupPvcSetupProvEntry 1 }


-- Mpanl/n Isdn
-- This component defines the parameters associated with the ISDN B-
-- Channel interface. Adding this component makes the Mpanl
-- behave as an ISDN access to the MPA.

mpanlIsdn OBJECT IDENTIFIER ::= { mpanl 22 }



mpanlIsdnRowStatusTable OBJECT-TYPE
   SYNTAX     SEQUENCE OF MpanlIsdnRowStatusEntry
   ACCESS     not-accessible
   STATUS     mandatory
   DESCRIPTION
     "This entry controls the addition and deletion of 
      mpanlIsdn components."
::= { mpanlIsdn 1 }

mpanlIsdnRowStatusEntry OBJECT-TYPE
   SYNTAX     MpanlIsdnRowStatusEntry
   ACCESS     not-accessible
   STATUS     mandatory
   DESCRIPTION
     "A single entry in the table represents a single 
      mpanlIsdn component."
   INDEX {
      mpanlIndex,
      mpanlIsdnIndex }
::= { mpanlIsdnRowStatusTable 1 }

MpanlIsdnRowStatusEntry ::= SEQUENCE {
   mpanlIsdnRowStatus
      RowStatus,
   mpanlIsdnComponentName
      DisplayString,
   mpanlIsdnStorageType
      StorageType,
   mpanlIsdnIndex
      NonReplicated }

mpanlIsdnRowStatus OBJECT-TYPE
   SYNTAX     RowStatus 
   ACCESS     read-write
   STATUS     mandatory
   DESCRIPTION
     "This variable is used as the basis for SNMP naming of
      mpanlIsdn components.
      These components can be added and deleted."
::= { mpanlIsdnRowStatusEntry 1 }

mpanlIsdnComponentName OBJECT-TYPE
   SYNTAX     DisplayString 
   ACCESS     read-only
   STATUS     mandatory
   DESCRIPTION
     "This variable provides the component's string name for
      use with the ASCII Console Interface"
::= { mpanlIsdnRowStatusEntry 2 }

mpanlIsdnStorageType OBJECT-TYPE
   SYNTAX     StorageType 
   ACCESS     read-only
   STATUS     mandatory
   DESCRIPTION
     "This variable represents the storage type value for the
      mpanlIsdn tables."
::= { mpanlIsdnRowStatusEntry 4 }

mpanlIsdnIndex OBJECT-TYPE
   SYNTAX     NonReplicated 
   ACCESS     not-accessible
   STATUS     mandatory
   DESCRIPTION
     "This variable represents the index for the mpanlIsdn tables."
::= { mpanlIsdnRowStatusEntry 10 }

mpanlIsdnProvTable OBJECT-TYPE
   SYNTAX     SEQUENCE OF MpanlIsdnProvEntry
   ACCESS     not-accessible
   STATUS     mandatory
   DESCRIPTION
     "This group contains the provisionable attributes of the Isdn 
      component."
::= { mpanlIsdn 11 }

mpanlIsdnProvEntry OBJECT-TYPE
   SYNTAX     MpanlIsdnProvEntry
   ACCESS     not-accessible
   STATUS     mandatory
   DESCRIPTION
     "An entry in the mpanlIsdnProvTable."
   INDEX {
      mpanlIndex,
      mpanlIsdnIndex }
::= { mpanlIsdnProvTable 1 }

MpanlIsdnProvEntry ::= SEQUENCE {
   mpanlIsdnT320
      Unsigned32,
   mpanlIsdnAddressSignalling
      INTEGER }

mpanlIsdnT320 OBJECT-TYPE
   SYNTAX     Unsigned32 (0..255)
   ACCESS     read-write
   STATUS     mandatory
   DESCRIPTION
     "This attribute specifies the waiting time for a silent 
      B-Channel (no active VCs associated with the Mpanl) to be 
      disconnected and made available. Default is 60 seconds. 0 means 
      t320 will never timeout."
   DEFVAL     { 60 }
::= { mpanlIsdnProvEntry 1 }

mpanlIsdnAddressSignalling OBJECT-TYPE
   SYNTAX     INTEGER  {
                 isdnDna(0),
                 normalBehavior(1) }
   ACCESS     read-write
   STATUS     mandatory
   DESCRIPTION
     "This attribute defines whether the ISDN Calling Party Number is to 
      be signalled to the remote DTE during an SVC call establishment. 
      Otherwise, no changes to the current behavior of SVC call 
      establishement (i.e., Passport Dna is used in the calling party 
      number information element)."
   DEFVAL     { normalBehavior }
::= { mpanlIsdnProvEntry 2 }

mpanlIsdnOperTable OBJECT-TYPE
   SYNTAX     SEQUENCE OF MpanlIsdnOperEntry
   ACCESS     not-accessible
   STATUS     mandatory
   DESCRIPTION
     "This group contains the operational attributes of the Isdn 
      component."
::= { mpanlIsdn 12 }

mpanlIsdnOperEntry OBJECT-TYPE
   SYNTAX     MpanlIsdnOperEntry
   ACCESS     not-accessible
   STATUS     mandatory
   DESCRIPTION
     "An entry in the mpanlIsdnOperTable."
   INDEX {
      mpanlIndex,
      mpanlIsdnIndex }
::= { mpanlIsdnOperTable 1 }

MpanlIsdnOperEntry ::= SEQUENCE {
   mpanlIsdnDataSigChan
      INTEGER,
   mpanlIsdnBChannelState
      INTEGER,
   mpanlIsdnLastUsedCgpn
      DigitString,
   mpanlIsdnBChanIntState
      INTEGER,
   mpanlIsdnActiveVirtualCircuitsCount
      Counter32 }

mpanlIsdnDataSigChan OBJECT-TYPE
   SYNTAX     INTEGER (1..255)
   ACCESS     read-only
   STATUS     mandatory
   DESCRIPTION
     "This attribute indicates the instance number of the dataSigChan 
      component controlling the allocation of this Mpanl Isdn component."
::= { mpanlIsdnOperEntry 1 }

mpanlIsdnBChannelState OBJECT-TYPE
   SYNTAX     INTEGER  {
                 idle(0),
                 busy(1),
                 disabled(2) }
   ACCESS     read-only
   STATUS     mandatory
   DESCRIPTION
     "This attribute indicates the state of the B-Channel. If the value is 
      idle it means that no VCs are connected and this B-Channel is 
      available. If the value is busy it means this B-Channel has been 
      allocated and is not available. If the value is disabled it means the 
      application interface or the port is locked or disabled."
::= { mpanlIsdnOperEntry 2 }

mpanlIsdnLastUsedCgpn OBJECT-TYPE
   SYNTAX     DigitString (SIZE (0..15))
   ACCESS     read-only
   STATUS     mandatory
   DESCRIPTION
     "This attribute indicates the calling party number currently using
      the B-Channel. When the B-Channel is free, the null string is 
      displayed."
::= { mpanlIsdnOperEntry 3 }

mpanlIsdnBChanIntState OBJECT-TYPE
   SYNTAX     INTEGER  {
                 isdnInit(0),
                 waitAccEnable(1),
                 waitLnsResponse(2),
                 waitFramerData(3),
                 enabling(4),
                 waitAccRegAck(5),
                 up(6),
                 down(7),
                 releasing(8) }
   ACCESS     read-only
   STATUS     mandatory
   DESCRIPTION
     "Debug information"
::= { mpanlIsdnOperEntry 4 }

mpanlIsdnActiveVirtualCircuitsCount OBJECT-TYPE
   SYNTAX     Counter32 
   ACCESS     read-only
   STATUS     mandatory
   DESCRIPTION
     "Current number of virtual circuits (switched and permanent) in data 
      transfer."
::= { mpanlIsdnOperEntry 5 }




-- 
-- Version and Compliance statements
-- 



-- Object-Group Statement:
-- A list of all current accessible leaf objects.

-- OBJECTS { mpanlDlciJvcCalledAddress,
--           mpanlDlciAlarmStatus,
--           mpanlDlciVcPriority,
--           mpanlDlciVcPathReliability,
--           mpanlDlciVcCannotForwardToSubnet,
--           mpanlDlciAccounting,
--           mpanlSigMpanlFrmrReceive,
--           mpanlAvailabilityStatus,
--           mpanlVoFrMaximumFrameSize,
--           mpanlDlciVcCallReferenceNumber,
--           mpanlDlciFciFromSubnet,
--           mpanlSigMpanlSap0CommandsRx,
--           mpanlVoFrRowStatus,
--           mpanlSigAckDelayTimer,
--           mpanlSigCurrentState,
--           mpanlRoundTripDelay,
--           mpanlDlciElapsedDifference,
--           mpanlDnaRowStatus,
--           mpanlDlciDiscCongestedToIfBytes,
--           mpanlSigProtocolErrors,
--           mpanlSigLastDlciReceivedStatus,
--           mpanlFramerFlagsBetweenFrames,
--           mpanlDlciLbRowStatus,
--           mpanlSigMpanlDteCustomerId,
--           mpanlDlciLCoSetupPriority,
--           mpanlSigAckTimer,
--           mpanlDlciDiscDeCongestedToIf,
--           mpanlDlciTransferPriToNwk,
--           mpanlDnaComponentName,
--           mpanlOctetFromIf,
--           mpanlDnaServiceExchange,
--           mpanlDlciVcStorageType,
--           mpanlDlciLCoRowStatus,
--           mpanlDlciLCoRequiredTrafficType,
--           mpanlIsdnStorageType,
--           mpanlDlciFecnFrmToIf,
--           mpanlSigLastTimeMsgBlockCongested,
--           mpanlDlciLCoPathUpDateTime,
--           mpanlDlciABitStatusFromIf,
--           mpanlDlciLCoCostMetric,
--           mpanlDlciLCoCallReferenceNumber,
--           mpanlDlciLbRemoteFecnFrm,
--           mpanlDlciLCoBumpPreference,
--           mpanlSigLastStateInStatusMsgReceived,
--           mpanlDlciDiscardedBytes,
--           mpanlDlciVcElapsedTimeTillNow,
--           mpanlDlciComponentName,
--           mpanlProceduralStatus,
--           mpanlSigIFramesTxDiscarded,
--           mpanlOctetToIfByQueueValue,
--           mpanlSigOutCallsFailed,
--           mpanlDlciJvcPreviousState,
--           mpanlDlciABitReasonFromIf,
--           mpanlDlciJvcPacketsToSubnet,
--           mpanlFramerComponentName,
--           mpanlDlciLbLocalDeBytes,
--           mpanlLmiAdminState,
--           mpanlDlciDeBytesFromIf,
--           mpanlDlciEirIngressSegFrm,
--           mpanlIfAdminStatus,
--           mpanlDlciDiscCongestedFromIf,
--           mpanlDlciLbLocalDeFrm,
--           mpanlDlciDeFrmFromIf,
--           mpanlDlciVcPreviousDiagnosticCode,
--           mpanlFrmToIf,
--           mpanlDlciVcEmissionPriorityFromNetwork,
--           mpanlSigCurrentQueueSize,
--           mpanlDlciLCoReasonForNoRoute,
--           mpanlVoFrFragmentedHighestPriorityFrames,
--           mpanlDlciLCoLastTearDownReason,
--           mpanlSigQualityOfServiceNotAvailable,
--           mpanlDlciLCoRequiredSecurity,
--           mpanlFramerLrcErrors,
--           mpanlDlciVcCallingDna,
--           mpanlDlciExcessBytesFromIf,
--           mpanlIsdnBChannelState,
--           mpanlDlciVcPeakOoSeqFrmForwarded,
--           mpanlDlciVcFrmCongestedToSubnet,
--           mpanlDlciExcessFrmFromIf,
--           mpanlSigMpanlRemoteBusy,
--           mpanlDlciJvcCalledLcn,
--           mpanlSigMpanlIFramesTxDiscarded,
--           mpanlSigMpanlRowStatus,
--           mpanlDlciLbLocalTotalFrm,
--           mpanlDlciAvailabilityStatus,
--           mpanlSigComponentName,
--           mpanlSigIFramesRcvdDiscarded,
--           mpanlDlciLbRemoteTotalBytes,
--           mpanlDlciBytesFromIf,
--           mpanlDlciBecnFrmToIf,
--           mpanlDlciLCoRoundTripDelay,
--           mpanlDlciVcNotDataXferFromSubnet,
--           mpanlDlciLbRemoteTotalFrm,
--           mpanlDlciFrmFromIf,
--           mpanlComponentName,
--           mpanlDlciLbRemoteBecnFrm,
--           mpanlCommentText,
--           mpanlIsdnBChanIntState,
--           mpanlDlciLCoEnd,
--           mpanlLmiComponentName,
--           mpanlSigSetupTimeout,
--           mpanlLastUnknownDlci,
--           mpanlFramerFrmFromIf,
--           mpanlDlciVcRcosFromNetwork,
--           mpanlDlciLCoHoldingPriority,
--           mpanlUnknownStatus,
--           mpanlStandbyStatus,
--           mpanlLmiProcedures,
--           mpanlDlciLCoPathFailureAction,
--           mpanlDlciVcDuplicatesFromSubnet,
--           mpanlStorageType,
--           mpanlDlciControlStatus,
--           mpanlSigLastStateChangeReason,
--           mpanlSigMpanlDteNodeId,
--           mpanlSigRetransmitLimit,
--           mpanlDlciJvcProtocolErrors,
--           mpanlDlciLCoPktsFromNetwork,
--           mpanlDlciTotalIngressSegFrm,
--           mpanlDlciQ933CallState,
--           mpanlDlciJvcPacketsDiscarded,
--           mpanlSigAckTimeout,
--           mpanlDlciRowStatus,
--           mpanlDlciJvcCallingAddress,
--           mpanlDlciVcOoSeqByteCntExceeded,
--           mpanlFrMuxSetupPvcSetupComponentName,
--           mpanlFramerRowStatus,
--           mpanlDlciErrorLongBytesFromIf,
--           mpanlAdminState,
--           mpanlDlciVcPktRetryTimeouts,
--           mpanlDlciMaximumFrameSize,
--           mpanlDlciErrorLongFrmFromIf,
--           mpanlDlciVcCalledDna,
--           mpanlDlciUsageState,
--           mpanlOctetToIf,
--           mpanlDlciVcAccountingEnd,
--           mpanlCustomerIdentifier,
--           mpanlSigMpanlOperationalState,
--           mpanlSigInCalls,
--           mpanlFrMuxSetupRowStatus,
--           mpanlFramerUsageState,
--           mpanlSigMpanlReceiveRejectFrame,
--           mpanlDlciVcSubnetRecoveries,
--           mpanlFramerNormPrioLinkUtilFromIf,
--           mpanlDlciTotalEgressSegFrm,
--           mpanlSigAdminState,
--           mpanlFrMuxSetupStorageType,
--           mpanlSigWindowSize,
--           mpanlDlciOperationalState,
--           mpanlDlciBciFromSubnet,
--           mpanlFramerInterfaceName,
--           mpanlDlciDiscExcessFromIfBytes,
--           mpanlDlciVcSegmentSize,
--           mpanlDlciLoopbackState,
--           mpanlUnknownDlciFramesFromIf,
--           mpanlSigUsageState,
--           mpanlFramerOperationalState,
--           mpanlFrMuxSetupComponentName,
--           mpanlSigFrmrReceive,
--           mpanlVoFrProtocolViolationsFromIf,
--           mpanlFrMuxSetupPvcSetupDlciName,
--           mpanlDlciVcFastSelectCall,
--           mpanlFramerFrmModeErrors,
--           mpanlDlciVcCalledLcn,
--           mpanlDlciLCoRequiredCustomerParameter,
--           mpanlDlciEirEgressSegFrm,
--           mpanlDlciJvcCallingLcn,
--           mpanlIsdnComponentName,
--           mpanlDlciVcComponentName,
--           mpanlSigDefaultAccounting,
--           mpanlDlciBecnFrmSetByService,
--           mpanlDlciVcMaxSubnetPktSize,
--           mpanlPrefixDnaStorageType,
--           mpanlSigCallProceedingTimer,
--           mpanlIsdnDataSigChan,
--           mpanlDnaStorageType,
--           mpanlDlciVcOutOfRangeFrmFromSubnet,
--           mpanlDlciStartTime,
--           mpanlLmiRowStatus,
--           mpanlDlciLbStorageType,
--           mpanlFramerAborts,
--           mpanlDlciBecnFrmFromIf,
--           mpanlDlciABitStatusToIf,
--           mpanlDlciEmissionPriorityToIf,
--           mpanlDlciVcType,
--           mpanlDlciVcSendSequenceNumber,
--           mpanlSigMpanlSapXCommandsTx,
--           mpanlDlciLCoPathFailureCount,
--           mpanlDlciJvcCurrentState,
--           mpanlSigReceiveRejectFrame,
--           mpanlIsdnRowStatus,
--           mpanlLmiUsageState,
--           mpanlSigOperationalState,
--           mpanlDnaEgressAccounting,
--           mpanlDlciLCoCalledDna,
--           mpanlAlarmStatus,
--           mpanlDlciABitReasonToIf,
--           mpanlDlciLCoStorageType,
--           mpanlSigMpanlUsageState,
--           mpanlSigMpanlAckTimeout,
--           mpanlDlciDiscFrameAbit,
--           mpanlVoFrStorageType,
--           mpanlFrMuxSetupPvcSetupRowStatus,
--           mpanlDlciBciToSubnet,
--           mpanlDlciDiscCongestedToIf,
--           mpanlSigRemoteBusy,
--           mpanlDlciDeFrmToIf,
--           mpanlDlciLCoOptimization,
--           mpanlDlciLbRemoteDeBytes,
--           mpanlDlciVcEmissionPriorityToNetwork,
--           mpanlDlciLCoElapsedTimeTillNow,
--           mpanlSigNetworkType,
--           mpanlDlciVcPeakOoSeqByteCount,
--           mpanlFramerOctetFromIf,
--           mpanlDlciLbRemoteDeFrm,
--           mpanlDlciDiscDeCongestedFromIfBytes,
--           mpanlDlciDiscByteAbit,
--           mpanlLmiOperationalState,
--           mpanlDlciTotalIngressBytes,
--           mpanlDlciProceduralStatus,
--           mpanlVoFrLostFragmentsFromIf,
--           mpanlSigMpanlCurrentState,
--           mpanlSigInCallsRefused,
--           mpanlFramerOverruns,
--           mpanlDlciLCoRetryCount,
--           mpanlDlciLCoEmissionPriority,
--           mpanlDlciJvcCalledNpi,
--           mpanlDlciVcCalledNpi,
--           mpanlSigCurrentNumberOfSvcCalls,
--           mpanlDlciTotalEgressBytes,
--           mpanlDlciBytesToIf,
--           mpanlSigLastDlciWithMsgBlockCongestion,
--           mpanlIsdnAddressSignalling,
--           mpanlNumberOfEmissionQs,
--           mpanlSigDisconnectTimer,
--           mpanlDlciFrmToIf,
--           mpanlSigMpanlCurrentQueueSize,
--           mpanlSigMpanlIFramesRcvdDiscarded,
--           mpanlDlciLCoCallingDna,
--           mpanlDlciVcAccountingEnabled,
--           mpanlDlciVcRowStatus,
--           mpanlDlciLCoDiscardPriority,
--           mpanlDlciVcPeakOoSeqPktCount,
--           mpanlDlciDiscCongestedFromIfBytes,
--           mpanlSigStateChange,
--           mpanlFramerCrcErrors,
--           mpanlFramerFrmToIf,
--           mpanlDlciVcRcosToNetwork,
--           mpanlDlciEirIngressBytes,
--           mpanlSigMpanlHighestDlci,
--           mpanlDlciVcNotDataXferToSubnet,
--           mpanlSigMpanlSapXCommandsRx,
--           mpanlDlciTransferPriFromNwk,
--           mpanlPrefixDnaComponentName,
--           mpanlSigMpanlSap0CommandsTx,
--           mpanlDlciLCoPktsToNetwork,
--           mpanlDlciJvcComponentName,
--           mpanlDlciVcCombErrorsFromSubnet,
--           mpanlSigMpanlStateChange,
--           mpanlSigIFramesReceived,
--           mpanlDlciEirEgressBytes,
--           mpanlInvalidHeaderFramesFromIf,
--           mpanlDlciLbLocalFecnFrm,
--           mpanlDlciJvcStorageType,
--           mpanlDlciFecnFrmFromIf,
--           mpanlDlciVcSegmentsRx,
--           mpanlSigMpanlProtocolErrors,
--           mpanlFrMuxSetupDlciCompName,
--           mpanlSigReleaseTimer,
--           mpanlSigStorageType,
--           mpanlDnaDefaultTransferPriority,
--           mpanlIsdnT320,
--           mpanlDlciLCoRequiredTxBandwidth,
--           mpanlSigMpanlDteComponentName,
--           mpanlDlciUnknownStatus,
--           mpanlDlciStandbyStatus,
--           mpanlSigIdleProbeTimer,
--           mpanlDlciLCoBytesFromNetwork,
--           mpanlSigMpanlIFramesReceived,
--           mpanlDlciStorageType,
--           mpanlDlciVcDmepValue,
--           mpanlIfIndex,
--           mpanlFramerNormPrioLinkUtilToIf,
--           mpanlDlciVcDataPath,
--           mpanlDlciLCoCalledNpi,
--           mpanlSigOutCalls,
--           mpanlFramerStorageType,
--           mpanlSigMpanlLastStateChangeReason,
--           mpanlDlciErrorShortFrmFromIf,
--           mpanlFrmFromIf,
--           mpanlDlciCommittedBurstSize,
--           mpanlDlciVcStartTime,
--           mpanlDlciQ933CallReference,
--           mpanlDlciAdminState,
--           mpanlSigMpanlStorageType,
--           mpanlDlciVcDiagnosticCode,
--           mpanlDlciLCoRequiredRxBandwidth,
--           mpanlSigMpanlComponentName,
--           mpanlDlciLCoPermittedTrunkTypes,
--           mpanlDlciVcCallingNpi,
--           mpanlLmiStorageType,
--           mpanlIsdnLastUsedCgpn,
--           mpanlFramerAdminState,
--           mpanlDlciVcCallingLcn,
--           mpanlDlciCallReferenceNumber,
--           mpanlDnaAccountClass,
--           mpanlFrMuxSetupCommittedInformationRate,
--           mpanlDlciLbLocalTotalBytes,
--           mpanlControlStatus,
--           mpanlFramerLargeFrmErrors,
--           mpanlFrmToIfByQueueValue,
--           mpanlDlciLbComponentName,
--           mpanlDlciDiscardedSegFrm,
--           mpanlVoFrTransmitInformationRate,
--           mpanlDlciLCoDelayMetric,
--           mpanlDlciLbLocalBecnFrm,
--           mpanlDlciVcState,
--           mpanlRowStatus,
--           mpanlSnmpOperStatus,
--           mpanlDlciVcFrmLossTimeouts,
--           mpanlDlciVcSegmentsSent,
--           mpanlDlciJvcRowStatus,
--           mpanlFramerNonOctetErrors,
--           mpanlSigRowStatus,
--           mpanlDlciLCoComponentName,
--           mpanlDlciVcPreviousState,
--           mpanlVoFrComponentName,
--           mpanlPrefixDnaRowStatus,
--           mpanlSigCallSetupTimer,
--           mpanlDlciVcOoSeqPktCntExceeded,
--           mpanlDlciVcPeakRetryQueueSize,
--           mpanlDlciDeBytesToIf,
--           mpanlUsageState,
--           mpanlDlciLCoCallingNpi,
--           mpanlFramerUnderruns,
--           mpanlSigIFramesTransmitted,
--           mpanlIsdnActiveVirtualCircuitsCount,
--           mpanlDlciLCoBytesToNetwork,
--           mpanlDlciDiscExcessFromIf,
--           mpanlDlciExcessBurstSize,
--           mpanlSigLastCauseInStatusMsgReceived,
--           mpanlDlciDiscDeCongestedFromIf,
--           mpanlOperationalState,
--           mpanlDlciLCoPathValue,
--           mpanlSigLastQ933StateReceivedStatus,
--           mpanlDlciDiscDeCongestedToIfBytes,
--           mpanlDlciJvcCallingNpi,
--           mpanlDnaAccountCollection,
--           mpanlSigMpanlIFramesTransmitted,
--           mpanlDlciLCoState,
--           mpanlSigMpanlAdminState,
--           mpanlDlciJvcPacketsFromSubnet,
--           mpanlFrMuxSetupPvcSetupStorageType }
-- STATUS  mandatory
-- DESCRIPTION
--   "A list of all current accessible leaf objects."

mpaNetworkLinkGroup OBJECT IDENTIFIER ::= { mpaNetworkLinkMIB 1 }
mpaNetworkLinkGroupBE OBJECT IDENTIFIER ::= { mpaNetworkLinkGroup 5 }
mpaNetworkLinkGroupBE01 OBJECT IDENTIFIER ::= { mpaNetworkLinkGroupBE 2 }
mpaNetworkLinkGroupBE01A OBJECT IDENTIFIER ::= { mpaNetworkLinkGroupBE01 2 }



-- Agent-Capabilities Statement:

-- PRODUCT-RELEASE "Passport Release 7.0 MpaNetworkLink."
-- STATUS          mandatory
-- DESCRIPTION     "MpaNetworkLink MIB: MIB Version BE01A,
--                  Software Version BG00S4C."
-- SUPPORTS        Nortel-Magellan-Passport-MpaNetworkLinkMIB
--    INCLUDES     { mpaNetworkLinkGroupBE01A }

mpaNetworkLinkCapabilities OBJECT IDENTIFIER ::= { mpaNetworkLinkMIB 3 }
mpaNetworkLinkCapabilitiesBE OBJECT IDENTIFIER ::= { mpaNetworkLinkCapabilities 5 }
mpaNetworkLinkCapabilitiesBE01 OBJECT IDENTIFIER ::= { mpaNetworkLinkCapabilitiesBE 2 }
mpaNetworkLinkCapabilitiesBE01A OBJECT IDENTIFIER ::= { mpaNetworkLinkCapabilitiesBE01 2 }





END
