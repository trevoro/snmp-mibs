-- This mib serves to aproximate various objects until we
-- go entirely V2.

STOP-GAP-V2 DEFINITIONS ::= BEGIN

RowStatus ::= INTEGER { active(1), notInService(2) }

TestAndIncr ::= INTEGER (0..2147483647)  

-- PhysAddress ::= OCTET STRING

-- DisplayString ::= OCTET STRING

END
