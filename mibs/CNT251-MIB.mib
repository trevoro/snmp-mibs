--
--	Computer Network Technology, Corp.
--		6000 Nathan Lane North 
--		Plymouth, Minnesota  55442
--
--		  phone:  (763) 268-6000
--		    fax:  (763) 268-6800
--		support:  1-800-NET-TECH
--		  email:  cnt.com
--
--
--	MIB Version:     2.8
--	Product Family:  CNT Zeus(2) Config(5) SystemProbe(1) 
--
-- +------------+ if you change this mib, you increment the version number.
-- | Attention! | Also, this MIB is supported by the configuration subagent,
-- +------------+ and that agent must also be compiled with this mib version.
-- Ver.2.8: Added tm(17) to SysChassisType
--          Added cnt2SysOsVersion
--          Added gigabitEthernet
--          Added tm(17) type

CNT251-MIB DEFINITIONS ::= BEGIN

	IMPORTS
		Counter FROM RFC1065-SMI
		OBJECT-TYPE
			FROM RFC-1212
			DisplayString FROM RFC1213-MIB
		cnt2CfgSystemProbe
			FROM CNT25-MIB;

---   	cnt			OBJECT IDENTIFIER ::= { enterprises 333 }
---   	cnt2			OBJECT IDENTIFIER ::= { cnt 2 }
---   	cnt2Config		OBJECT IDENTIFIER ::= { cnt2 5 }
---   	cnt2CfgSystemProbe	OBJECT IDENTIFIER ::= { cnt2Config 1 }

	cnt2SysChassisType OBJECT-TYPE
		SYNTAX  INTEGER {
				slot-2(2),	-- two slots
				slot-6(6),	-- six slots
				slot-12(12),	-- twelve slots
				osg(13),	-- osg 
				usg(14),	-- usg 
				usd6(15),	-- usd six slots 
				usd12(16),	-- usd twelve slots 
				tm(17)		-- tm box 
			
			}
		ACCESS  read-only
		STATUS  mandatory
		DESCRIPTION
			"The chassis type for this network node."
		::= { cnt2CfgSystemProbe 1 }

	cnt2SysZachCardType OBJECT-TYPE
		SYNTAX  INTEGER { 
				not-present(1),
				rs232(2)
			}
		ACCESS  read-only
		STATUS  mandatory
		DESCRIPTION
			"TBD."
		::= { cnt2CfgSystemProbe 2 }

	cnt2SysHmbFirmwareRevision OBJECT-TYPE
		SYNTAX  INTEGER
		ACCESS  read-only
		STATUS  mandatory
		DESCRIPTION
			"The Hardware Monitor Board (HMB) firmware
			revision level."
		::= { cnt2CfgSystemProbe 3 }

	cnt2SysScnrcVersion OBJECT-TYPE
		SYNTAX  INTEGER
		ACCESS  read-only
		STATUS  mandatory
		DESCRIPTION
			"The version of the Lattice chip set on the HMB."
		::= { cnt2CfgSystemProbe 4 }

	cnt2SysDatPresent OBJECT-TYPE
		SYNTAX  INTEGER {
				yes(1),
				no(2)
			}
		ACCESS  read-only
		STATUS  mandatory
		DESCRIPTION
			"Indicates whether this node contains a tape
			drive."
		::= { cnt2CfgSystemProbe 5 }

	cnt2SysCdRomPresent OBJECT-TYPE
		SYNTAX  INTEGER {
				yes(1),
				no(2)
			}
		ACCESS  read-only
		STATUS  mandatory
		DESCRIPTION
			"Indicates whether this node contains a CD-ROM
			drive."
		::= { cnt2CfgSystemProbe 6 }

	cnt2SysProbeDateTime OBJECT-TYPE
		SYNTAX  DisplayString
		ACCESS  read-only
		STATUS  mandatory
		DESCRIPTION
			"The date and time the system probe file was
			built/modified.  It is a string in the form
			mm/dd/yy hh:mm:ss local time.  hh is expressed
			as 00-23."
		::= { cnt2CfgSystemProbe 7 }

	cnt2SysSlotCount OBJECT-TYPE
		SYNTAX  INTEGER
		ACCESS  read-only
		STATUS  mandatory
		DESCRIPTION
			"The number of available slots on this
			network node of which application processors
			or i/o processors can occupy."
		::= { cnt2CfgSystemProbe 8 }

	cnt2SysPowerSupplyTable OBJECT-TYPE
		SYNTAX  SEQUENCE OF Cnt2SysPowerSupplyEntry
		ACCESS  not-accessible
		STATUS  mandatory
		DESCRIPTION
			"A list of entries ..."
		::= { cnt2CfgSystemProbe 9 }

	cnt2SysPowerSupplyEntry OBJECT-TYPE
		SYNTAX  Cnt2SysPowerSupplyEntry
		ACCESS  not-accessible
		STATUS  mandatory
		DESCRIPTION
			"An individual power supply entry."
		INDEX { cnt2SysPowerSupplyIndex }
		::= { cnt2SysPowerSupplyTable 1 }

	Cnt2SysPowerSupplyEntry ::= SEQUENCE {
		cnt2SysPowerSupplyIndex
			INTEGER,
		cnt2SysPowerSupplyPresent
			INTEGER
	}

	cnt2SysPowerSupplyIndex OBJECT-TYPE
		SYNTAX  INTEGER
		ACCESS  read-only
		STATUS  mandatory
		DESCRIPTION
			"The relative index for this power supply."
		::= { cnt2SysPowerSupplyEntry 1 }

	cnt2SysPowerSupplyPresent OBJECT-TYPE
		SYNTAX  INTEGER {
				yes(1),
				no(2)
			}
		ACCESS  read-only
		STATUS  mandatory
		DESCRIPTION
			"An indication if a power supply is in
			this network node."
		::= { cnt2SysPowerSupplyEntry 2 }

	cnt2SysFanTable OBJECT-TYPE
		SYNTAX  SEQUENCE OF Cnt2SysFanEntry
		ACCESS  not-accessible
		STATUS  mandatory
		DESCRIPTION
			"A list of entries ..."
		::= { cnt2CfgSystemProbe 10 }

	cnt2SysFanEntry OBJECT-TYPE
		SYNTAX  Cnt2SysFanEntry
		ACCESS  not-accessible
		STATUS  mandatory
		DESCRIPTION
			"An individual power supply fan entry."
		INDEX { cnt2SysFanIndex }
		::= { cnt2SysFanTable 1 }

	Cnt2SysFanEntry ::= SEQUENCE {
		cnt2SysFanIndex
			INTEGER,
		cnt2SysFanPresent
			INTEGER
	}

	cnt2SysFanIndex OBJECT-TYPE
		SYNTAX  INTEGER
		ACCESS  read-only
		STATUS  mandatory
		DESCRIPTION
			"The relative index for this power supply fan."
		::= { cnt2SysFanEntry 1 }

	cnt2SysFanPresent OBJECT-TYPE
		SYNTAX  INTEGER {
				yes(1),
				no(2)
			}
		ACCESS  read-only
		STATUS  mandatory
		DESCRIPTION
			"An indication if a power supply fan is
			operational in this network node."
		::= { cnt2SysFanEntry 2 }

	cnt2SysAdapterTable OBJECT-TYPE
		SYNTAX  SEQUENCE OF Cnt2SysAdapterEntry
		ACCESS  not-accessible
		STATUS  mandatory
		DESCRIPTION
			"A list of entries ..."
		::= { cnt2CfgSystemProbe 11 }

	cnt2SysAdapterEntry OBJECT-TYPE
		SYNTAX  Cnt2SysAdapterEntry
		ACCESS  not-accessible
		STATUS  mandatory
		DESCRIPTION
			"An individual adapter entry."
		INDEX { cnt2SysAdapterIndex }
		::= { cnt2SysAdapterTable 1 }

	Cnt2SysAdapterEntry ::= SEQUENCE {
		cnt2SysAdapterIndex
			INTEGER,
		cnt2SysAdapterType
			INTEGER,
		cnt2SysAdapterName
			INTEGER,
		cnt2SysAdapterPartNumber
			INTEGER,
		cnt2SysAdapterSerialNumber
			DisplayString,
		cnt2SysAdapterHostId
			DisplayString,
		cnt2SysAdapterBoardRevision
			DisplayString,
		cnt2SysAdapterFirmwareMajorRevision
			INTEGER,
		cnt2SysAdapterFirmwareMinorRevision
			INTEGER,
		cnt2SysAdapterHostName
			DisplayString,
		cnt2SysAdapterOsName
			DisplayString,
		cnt2SysAdapterOsMajorVersion
			INTEGER,
		cnt2SysAdapterOsMinorVersion
			INTEGER,
		cnt2SysAdapterServiceMonitorStatus
			INTEGER
	}

	cnt2SysAdapterIndex OBJECT-TYPE
		SYNTAX  INTEGER
		ACCESS  read-only
		STATUS  mandatory
		DESCRIPTION
			"The relative index for this adapter."
		::= { cnt2SysAdapterEntry 1 }

	cnt2SysAdapterType OBJECT-TYPE
		SYNTAX  INTEGER {
				unknown(1),	-- not yet determined
				absent(2),	-- determined to be missing
				sparc(3),
				escon(4),
				ppc(5)
			}
		ACCESS  read-only
		STATUS  mandatory
		DESCRIPTION
			"the type of adapter in this slot."
		::= { cnt2SysAdapterEntry 2 }

	cnt2SysAdapterName OBJECT-TYPE
		SYNTAX  INTEGER {
				absent(1),	-- determined to be missing
				unknown(2),	-- not yet determined
				zsp1(3),
				zen1(4),
				zap1(5),
				zsp2(6),
				zen2(7),
				zap2(8),
				zen3(9),
				usg1(10),
				usg2(11),
				zap3(12),
				zap4(13),
				zen4(14),
				o1x1(15)
			}
		ACCESS  read-only
		STATUS  mandatory
		DESCRIPTION
			"the name of the adapter in this slot."
		::= { cnt2SysAdapterEntry 3 }

	cnt2SysAdapterPartNumber OBJECT-TYPE
		SYNTAX  INTEGER
		ACCESS  read-only
		STATUS  mandatory
		DESCRIPTION
			"The part number of the adapter in this slot."
		::= { cnt2SysAdapterEntry 4 }

	cnt2SysAdapterSerialNumber OBJECT-TYPE
		SYNTAX  DisplayString
		ACCESS  read-only
		STATUS  mandatory
		DESCRIPTION
			"The serial number of the adapter in this slot."
		::= { cnt2SysAdapterEntry 5 }

	cnt2SysAdapterHostId OBJECT-TYPE
		SYNTAX  DisplayString
		ACCESS  read-only
		STATUS  mandatory
		DESCRIPTION
			"Any host identifier assigned by the operating
                        system vendor.  For example, Solaris uses a host
                        identifier."
		::= { cnt2SysAdapterEntry 6 }

	cnt2SysAdapterBoardRevision OBJECT-TYPE
		SYNTAX  DisplayString
		ACCESS  read-only
		STATUS  mandatory
		DESCRIPTION
			"The board revision of the adapter in this slot."
		::= { cnt2SysAdapterEntry 7 }

	cnt2SysAdapterFirmwareMajorRevision OBJECT-TYPE
		SYNTAX  INTEGER
		ACCESS  read-only
		STATUS  mandatory
		DESCRIPTION
			"The major revision of the firmware on the
			adapter in this slot."
		::= { cnt2SysAdapterEntry 8 }

	cnt2SysAdapterFirmwareMinorRevision OBJECT-TYPE
		SYNTAX  INTEGER
		ACCESS  read-only
		STATUS  mandatory
		DESCRIPTION
			"The minor revision of the firmware on the
			adapter in this slot."
		::= { cnt2SysAdapterEntry 9 }

	cnt2SysAdapterHostName OBJECT-TYPE
		SYNTAX  DisplayString
		ACCESS  read-only
		STATUS  mandatory
		DESCRIPTION
			"The node name of the adapter in this slot."
		::= { cnt2SysAdapterEntry 10 }

	cnt2SysAdapterOsName OBJECT-TYPE
		SYNTAX  DisplayString
		ACCESS  read-only
		STATUS  mandatory
		DESCRIPTION
			"The operating system name running on the
			adapter in this slot."
		::= { cnt2SysAdapterEntry 11 }

	cnt2SysAdapterOsMajorVersion OBJECT-TYPE
		SYNTAX  INTEGER
		ACCESS  read-only
		STATUS  mandatory
		DESCRIPTION
			"The operating system major version running
			on the adapter in this slot."
		::= { cnt2SysAdapterEntry 12 }

	cnt2SysAdapterOsMinorVersion OBJECT-TYPE
		SYNTAX  INTEGER
		ACCESS  read-only
		STATUS  mandatory
		DESCRIPTION
			"The operating system minor version running
			on the adapter in this slot."
		::= { cnt2SysAdapterEntry 13 }

	cnt2SysAdapterServiceMonitorStatus OBJECT-TYPE
		SYNTAX  INTEGER {
				none(1),      -- this adapter cannot be a SM
				primary(2),
				secondary(3)
			}
		ACCESS  read-only
		STATUS  mandatory
		DESCRIPTION
			"Indicates the status of the Service Monitor
                        software for the adapter in this slot."
		::= { cnt2SysAdapterEntry 14 }

	cnt2SysBusTable OBJECT-TYPE
		SYNTAX  SEQUENCE OF Cnt2SysBusEntry
		ACCESS  not-accessible
		STATUS  mandatory
		DESCRIPTION
			"A list of entries ..."
		::= { cnt2CfgSystemProbe 12 }

	cnt2SysBusEntry OBJECT-TYPE
		SYNTAX  Cnt2SysBusEntry
		ACCESS  not-accessible
		STATUS  mandatory
		DESCRIPTION
			"An individual bus entry."
		INDEX { cnt2SysBusAdapterIndex, cnt2SysBusIndex }
		::= { cnt2SysBusTable 1 }

	Cnt2SysBusEntry ::= SEQUENCE {
		cnt2SysBusAdapterIndex
			INTEGER,
		cnt2SysBusIndex
			INTEGER,
		cnt2SysBusType
			INTEGER
	}

	cnt2SysBusAdapterIndex OBJECT-TYPE
		SYNTAX  INTEGER
		ACCESS  read-only
		STATUS  mandatory
		DESCRIPTION
			"The same as cnt2SysAdapterIndex:  the relative
			index for this adapter."
		::= { cnt2SysBusEntry 1 }

	cnt2SysBusIndex OBJECT-TYPE
		SYNTAX  INTEGER
		ACCESS  read-only
		STATUS  mandatory
		DESCRIPTION
			"The relative index for a bus on the adapter
			in this slot."
		::= { cnt2SysBusEntry 2 }

	cnt2SysBusType OBJECT-TYPE
		SYNTAX  INTEGER {
				unknown(1),	-- can't be determined
				sbus(2),
				pci(3),
				vme(4)
			}
		ACCESS  read-only
		STATUS  mandatory
		DESCRIPTION
			"A type of bus on the adapter in this slot."
		::= { cnt2SysBusEntry 3 }

	cnt2SysCardTable OBJECT-TYPE
		SYNTAX  SEQUENCE OF Cnt2SysCardEntry
		ACCESS  not-accessible
		STATUS  mandatory
		DESCRIPTION
			"A list of entries ..."
		::= { cnt2CfgSystemProbe 13 }

	cnt2SysCardEntry OBJECT-TYPE
		SYNTAX  Cnt2SysCardEntry
		ACCESS  not-accessible
		STATUS  mandatory
		DESCRIPTION
			"An individual card entry."
		INDEX { cnt2SysCardAdapterIndex, cnt2SysCardBusIndex,
			cnt2SysCardIndex }
		::= { cnt2SysCardTable 1 }

	Cnt2SysCardEntry ::= SEQUENCE {
		cnt2SysCardAdapterIndex
			INTEGER,
		cnt2SysCardBusIndex
			INTEGER,
		cnt2SysCardIndex
			INTEGER,
		cnt2SysCardFunction
			INTEGER,
		cnt2SysCardFirmwareMajorRevision
			INTEGER,
		cnt2SysCardFirmwareMinorRevision
			INTEGER,
		cnt2SysCardVendorOctetString
			DisplayString,
		cnt2SysCardVendorDisplayString
			DisplayString
	}

	cnt2SysCardAdapterIndex OBJECT-TYPE
		SYNTAX  INTEGER
		ACCESS  read-only
		STATUS  mandatory
		DESCRIPTION
			"The same as cnt2SysAdapterIndex:  the relative
			index for this adapter."
		::= { cnt2SysCardEntry 1 }

	cnt2SysCardBusIndex OBJECT-TYPE
		SYNTAX  INTEGER
		ACCESS  read-only
		STATUS  mandatory
		DESCRIPTION
			"The same as cnt2SysBusIndex:  the relative
			index for a bus on this adapter."
		::= { cnt2SysCardEntry 2 }

	cnt2SysCardIndex OBJECT-TYPE
		SYNTAX  INTEGER
		ACCESS  read-only
		STATUS  mandatory
		DESCRIPTION
			"The relative index for this card on the adapter
			in this slot."
		::= { cnt2SysCardEntry 3 }

	cnt2SysCardFunction OBJECT-TYPE
		SYNTAX  INTEGER {
				unknown(1),	-- can't be determined
				interface(2),
				compression(3)
			}
		ACCESS  read-only
		STATUS  mandatory
		DESCRIPTION
			"The function of this card for the adapter in
                        this slot."
		::= { cnt2SysCardEntry 4 }

	cnt2SysCardFirmwareMajorRevision OBJECT-TYPE
		SYNTAX  INTEGER
		ACCESS  read-only
		STATUS  mandatory
		DESCRIPTION
			"The major revision of the firmware on the card
			in this slot."
		::= { cnt2SysCardEntry 5 }

	cnt2SysCardFirmwareMinorRevision OBJECT-TYPE
		SYNTAX  INTEGER
		ACCESS  read-only
		STATUS  mandatory
		DESCRIPTION
			"The minor revision of the firmware on the card
			in this slot."
		::= { cnt2SysCardEntry 6 }

	cnt2SysCardVendorOctetString OBJECT-TYPE
		SYNTAX  DisplayString
		ACCESS  read-only
		STATUS  mandatory
		DESCRIPTION
			"Any octet string used for identification or
                         other purposes that may be readable from the
                         card in this slot."
		::= { cnt2SysCardEntry 7 }

	cnt2SysCardVendorDisplayString OBJECT-TYPE
		SYNTAX  DisplayString
		ACCESS  read-only
		STATUS  mandatory
		DESCRIPTION
			"Any display string used for identification or
                         other purposes that may be readable from the
                         card in this slot."
		::= { cnt2SysCardEntry 8 }

	cnt2SysIfTable OBJECT-TYPE
		SYNTAX  SEQUENCE OF Cnt2SysIfEntry
		ACCESS  not-accessible
		STATUS  mandatory
		DESCRIPTION
			"A list of entries ..."
		::= { cnt2CfgSystemProbe 14 }

	cnt2SysIfEntry OBJECT-TYPE
		SYNTAX  Cnt2SysIfEntry
		ACCESS  not-accessible
		STATUS  mandatory
		DESCRIPTION
			"An individual card entry."
		INDEX { cnt2SysIfAdapterIndex, cnt2SysIfBusIndex,
			cnt2SysIfIndex }
		::= { cnt2SysIfTable 1 }

	Cnt2SysIfEntry ::= SEQUENCE {
		cnt2SysIfAdapterIndex
			INTEGER,
		cnt2SysIfBusIndex
			INTEGER,
		cnt2SysIfIndex
			INTEGER,
		cnt2SysIfType
			INTEGER,
		cnt2SysIfCardIndex
			INTEGER,
		cnt2SysIfName
			DisplayString,
		cnt2SysIfConnector
			INTEGER,
		cnt2SysIfSnmpIndex
			INTEGER
	}

	cnt2SysIfAdapterIndex OBJECT-TYPE
		SYNTAX  INTEGER
		ACCESS  read-only
		STATUS  mandatory
		DESCRIPTION
			"The same as cnt2SysAdapterIndex:  the relative
			index for this adapter."
		::= { cnt2SysIfEntry 1 }

	cnt2SysIfBusIndex OBJECT-TYPE
		SYNTAX  INTEGER
		ACCESS  read-only
		STATUS  mandatory
		DESCRIPTION
			"The same as cnt2SysBusIndex:  the relative
			index for a bus on this adapter."
		::= { cnt2SysIfEntry 2 }

	cnt2SysIfIndex OBJECT-TYPE
		SYNTAX  INTEGER
		ACCESS  read-only
		STATUS  mandatory
		DESCRIPTION
			"The relative index for this interface on the
                        adapter in this slot."
		::= { cnt2SysIfEntry 3 }

	cnt2SysIfType OBJECT-TYPE
		SYNTAX  INTEGER {
				unknown(1),	-- can't be determined
				ethernetCsmacd(2),
				async(3),
				escon(4),
				atm(5),
				fibreChannel(6),
				scsi-2(7),
				scsi-3(8),
				ds3(9),
				fddi(10),
				fastEther(11),
				isdn(12),
				gigabitEthernet(13)
			}
		ACCESS  read-only
		STATUS  mandatory
		DESCRIPTION
			"The type of interface on the adapter in
                        this slot."
		::= { cnt2SysIfEntry 4 }

	cnt2SysIfCardIndex OBJECT-TYPE
		SYNTAX  INTEGER
		ACCESS  read-only
		STATUS  mandatory
		DESCRIPTION
			"The card index on which this interface resides.
                         The card index is relative to the bus.  If the
                         interface is native to the adapter, this value
                         is 0."
		::= { cnt2SysIfEntry 5 }

	cnt2SysIfName OBJECT-TYPE
		SYNTAX  DisplayString
		ACCESS  read-only
		STATUS  mandatory
		DESCRIPTION
			"The adapter-unique name of this interface.
                        It may be the name assigned by the operating system,
                        the name of the device driver, or a description
                        assigned by configuration."
		::= { cnt2SysIfEntry 6 }

	cnt2SysIfConnector OBJECT-TYPE
		SYNTAX  INTEGER {
                                absent(1),
                                unknown(2),       -- cannot be determined
                                micro-d15(3),     -- Sparc Ethernet
                                scsi-2(4),        -- Sparc on-board SCSI
                                scsi-3(5),        -- PPC io-board SCSI
                                sc-duplex(6),     -- Sparc Sbus ATM
                                rj45(7),          -- Sparc Sbus Serial
                                bnc(8),           -- PPC Ethernet
                                hssdc(9),         -- Fibre Channel
                                rsd-duplex(10)    -- Escon
                }
		ACCESS  read-only
		STATUS  mandatory
		DESCRIPTION
			"The connector type used for this interface."
		::= { cnt2SysIfEntry 7 }

	cnt2SysIfSnmpIndex OBJECT-TYPE
		SYNTAX  INTEGER
		ACCESS  read-only
		STATUS  mandatory
		DESCRIPTION
			"The SNMP MIB-2 interface index assigned to
                         this interface."
		::= { cnt2SysIfEntry 8 }

	cnt2SysSerialNumber OBJECT-TYPE
		SYNTAX  DisplayString
		ACCESS  read-only
		STATUS  mandatory
		DESCRIPTION
			"The chassis serial number shown on the tag
			on the outside of this system."
		::= { cnt2CfgSystemProbe 15 }

	cnt2SysOsVersion OBJECT-TYPE
		SYNTAX  DisplayString
		ACCESS  read-only
		STATUS  mandatory
		DESCRIPTION
			"The Software Nucleus OS version of this system."
		::= { cnt2CfgSystemProbe 16 }

	END
