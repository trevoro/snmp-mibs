-- ----------------------------------------------------------------------
--
-- netcom.mib
--
-- ----------------------------------------------------------------------

NETCOM-MIB DEFINITIONS ::= BEGIN



-- {{{ Imports
--	OBJECT-TYPE, Counter32, Unsigned32,

IMPORTS
	OBJECT-TYPE
		FROM SNMPv2-SMI
        TRAP-TYPE
                FROM RFC-1215
        DisplayString
                FROM RFC1213-MIB
        OBJECT-TYPE
                FROM RFC-1212
	MODULE-COMPLIANCE, OBJECT-GROUP
		FROM SNMPv2-CONF
	TEXTUAL-CONVENTION
		FROM SNMPv2-TC
	enterprises FROM RFC1155-SMI
	;

-- }}}



sinetica   OBJECT IDENTIFIER ::= { enterprises 3711 }



netcom          OBJECT IDENTIFIER ::= { sinetica 7 }
netcom1         OBJECT IDENTIFIER ::= { netcom 1 }
netcomObjects   OBJECT IDENTIFIER ::= { netcom1 1 }


-- {{{ netcomObjects  

netcomEnvironment   OBJECT IDENTIFIER ::= { netcomObjects 1  }
netcomContact       OBJECT IDENTIFIER ::= { netcomObjects 2  }

-- }}}
-- {{{ netcomEnvironment group    

netcomEnvHumidity        OBJECT IDENTIFIER ::= { netcomEnvironment 1 }
netcomEnvTemperature     OBJECT IDENTIFIER ::= { netcomEnvironment 2 }

-- }}}
-- {{{ netcomEnvHumidity

netcomEnvHumidityEnableMonitoring  OBJECT-TYPE
    SYNTAX    INTEGER (0..1)
    ACCESS    read-write
    STATUS    mandatory
    DESCRIPTION
        "Setting to one enables monitoring of Humidity"
    ::= { netcomEnvHumidity 1 }

netcomEnvCurrentHumidity  OBJECT-TYPE
    SYNTAX    INTEGER (0..1000)
    ACCESS    read-only
    STATUS    mandatory
    DESCRIPTION
        "The current humidity reading in 0.1%"
    ::= { netcomEnvHumidity 2 }

netcomEnvHumidityLowerThreshold  OBJECT-TYPE
    SYNTAX    INTEGER (0..1000)
    ACCESS    read-write
    STATUS    mandatory
    DESCRIPTION
        "The Lower humidity threshold in 0.1%"
    ::= { netcomEnvHumidity 3 }

netcomEnvHumidityUpperThreshold  OBJECT-TYPE
    SYNTAX    INTEGER (0..1000)
    ACCESS    read-write
    STATUS    mandatory
    DESCRIPTION
        "The Upper humidity threshold in 0.1%"
    ::= { netcomEnvHumidity 4 }

netcomEnvHumidityCalibrationOffset  OBJECT-TYPE
    SYNTAX    INTEGER (-100..100)
    ACCESS    read-write
    STATUS    mandatory
    DESCRIPTION
        "Calibration offset in 0.1%"	
    ::= { netcomEnvHumidity 5 }

netcomLowHumidity              TRAP-TYPE
    ENTERPRISE netcomEnvHumidity
    VARIABLES { netcomEnvCurrentHumidity }
    DESCRIPTION
        "The NetCom-th unit is below the low humidity threshold."
    ::= 21

netcomHighHumidity             TRAP-TYPE
    ENTERPRISE netcomEnvHumidity
    VARIABLES { netcomEnvCurrentHumidity }
    DESCRIPTION
        "The NetCom-th unit is above the high humidity threshold."
    ::= 22

netcomHumidityReturnToNormal   TRAP-TYPE
    ENTERPRISE netcomEnvHumidity
    VARIABLES { netcomEnvCurrentHumidity }
    DESCRIPTION
        "The NetCom-th unit has returned to normal humidity"
    ::= 23

-- }}}
-- {{{ netcomEnvTemperature

netcomEnvTemperatureEnableMonitoring  OBJECT-TYPE
    SYNTAX    INTEGER (0..1)
    ACCESS    read-write
    STATUS    mandatory
    DESCRIPTION
        "Setting to one enables monitoring of Temperature"
    ::= { netcomEnvTemperature 1 }

netcomEnvCurrentTemperature  OBJECT-TYPE
    SYNTAX    INTEGER (-200..1000)
    ACCESS    read-only
    STATUS    mandatory
    DESCRIPTION
        "The current temperature reading in 0.1%"
    ::= { netcomEnvTemperature 2 }

netcomEnvTemperatureLowerThreshold  OBJECT-TYPE
    SYNTAX    INTEGER (-200..1000)
    ACCESS    read-write
    STATUS    mandatory
    DESCRIPTION
        "The Lower temperature threshold in 0.1 degrees"
    ::= { netcomEnvTemperature 3 }

netcomEnvTemperatureUpperThreshold  OBJECT-TYPE
    SYNTAX    INTEGER (-200..1000)
    ACCESS    read-write
    STATUS    mandatory
    DESCRIPTION
        "The Upper temperature threshold in 0.1 degrees"
    ::= { netcomEnvTemperature 4 }

netcomEnvTemperatureCalibrationOffset  OBJECT-TYPE
    SYNTAX    INTEGER (-100..100)
    ACCESS    read-write
    STATUS    mandatory
    DESCRIPTION
        "Calibration offset in 0.1 degrees"	
    ::= { netcomEnvTemperature 5 }

netcomLowTemperature            TRAP-TYPE
    ENTERPRISE netcomEnvTemperature
    VARIABLES { netcomEnvCurrentTemperature }
    DESCRIPTION
        "The NetCom-th unit is below the lower temperature threshold."
    ::= 31

netcomHighTemperature           TRAP-TYPE
    ENTERPRISE netcomEnvTemperature
    VARIABLES { netcomEnvCurrentTemperature }
    DESCRIPTION
        "The NetCom-th unit is above the high temperature threshold."
    ::= 32

netcomTemperatureReturnToNormal   TRAP-TYPE
    ENTERPRISE netcomEnvTemperature
    VARIABLES { netcomEnvCurrentTemperature }
    DESCRIPTION
        "The NetCom-th unit has returned to normal temperature"
    ::= 33

-- }}}

-- {{{ netcomContact group    

netcomContactEnable  OBJECT-TYPE
    SYNTAX    INTEGER (0..1)
    ACCESS    read-write
    STATUS    mandatory
    DESCRIPTION
        "Setting to one enables monitoring of contacts"
    ::= { netcomContact 1 }

netcomContactNormalStates    OBJECT IDENTIFIER ::= { netcomContact 2  }
netcomContactCurrentStates    OBJECT IDENTIFIER ::= { netcomContact 3  }

-- {{{ netcomContactNormalStates group

netcomContact1NormalState  OBJECT-TYPE
    SYNTAX    INTEGER (0..1)
    ACCESS    read-write
    STATUS    mandatory
    DESCRIPTION
        "Set to 0 for normally open condition, 1 for normally closed"
    ::= { netcomContactNormalStates 1 }

netcomContact2NormalState  OBJECT-TYPE
    SYNTAX    INTEGER (0..1)
    ACCESS    read-write
    STATUS    mandatory
    DESCRIPTION
        "Set to 0 for normally open condition, 1 for normally closed"
    ::= { netcomContactNormalStates 2 }

netcomContact3NormalState  OBJECT-TYPE
    SYNTAX    INTEGER (0..1)
    ACCESS    read-write
    STATUS    mandatory
    DESCRIPTION
        "Set to 0 for normally open condition, 1 for normally closed"
    ::= { netcomContactNormalStates 3 }

netcomContact4NormalState  OBJECT-TYPE
    SYNTAX    INTEGER (0..1)
    ACCESS    read-write
    STATUS    mandatory
    DESCRIPTION
        "Set to 0 for normally open condition, 1 for normally closed"
    ::= { netcomContactNormalStates 4 }

netcomContact5NormalState  OBJECT-TYPE
    SYNTAX    INTEGER (0..1)
    ACCESS    read-write
    STATUS    mandatory
    DESCRIPTION
        "Set to 0 for normally open condition, 1 for normally closed"
    ::= { netcomContactNormalStates 5 }

netcomContact6NormalState  OBJECT-TYPE
    SYNTAX    INTEGER (0..1)
    ACCESS    read-write
    STATUS    mandatory
    DESCRIPTION
        "Set to 0 for normally open condition, 1 for normally closed"
    ::= { netcomContactNormalStates 6 }

netcomContact7NormalState  OBJECT-TYPE
    SYNTAX    INTEGER (0..1)
    ACCESS    read-write
    STATUS    mandatory
    DESCRIPTION
        "Set to 0 for normally open condition, 1 for normally closed"
    ::= { netcomContactNormalStates 7 }

-- }}}

-- {{{ netcomContactCurrentStates group

netcomContact1CurrentState  OBJECT-TYPE
    SYNTAX    INTEGER (0..1)
    ACCESS    read-only
    STATUS    mandatory
    DESCRIPTION
        "The current state of the contact"
    ::= { netcomContactCurrentStates 1 }

netcomContact2CurrentState  OBJECT-TYPE
    SYNTAX    INTEGER (0..1)
    ACCESS    read-only
    STATUS    mandatory
    DESCRIPTION
        "The current state of the contact"
    ::= { netcomContactCurrentStates 2 }

netcomContact3CurrentState  OBJECT-TYPE
    SYNTAX    INTEGER (0..1)
    ACCESS    read-only
    STATUS    mandatory
    DESCRIPTION
        "The current state of the contact"
    ::= { netcomContactCurrentStates 3 }

netcomContact4CurrentState  OBJECT-TYPE
    SYNTAX    INTEGER (0..1)
    ACCESS    read-only
    STATUS    mandatory
    DESCRIPTION
        "The current state of the contact"
    ::= { netcomContactCurrentStates 4 }

netcomContact5CurrentState  OBJECT-TYPE
    SYNTAX    INTEGER (0..1)
    ACCESS    read-only
    STATUS    mandatory
    DESCRIPTION
        "The current state of the contact"
    ::= { netcomContactCurrentStates 5 }

netcomContact6CurrentState  OBJECT-TYPE
    SYNTAX    INTEGER (0..1)
    ACCESS    read-only
    STATUS    mandatory
    DESCRIPTION
        "The current state of the contact"
    ::= { netcomContactCurrentStates 6 }

netcomContact7CurrentState  OBJECT-TYPE
    SYNTAX    INTEGER (0..1)
    ACCESS    read-only
    STATUS    mandatory
    DESCRIPTION
        "The current state of the contact"
    ::= { netcomContactCurrentStates 7 }

-- }}}

netcomContact1NonNormal              TRAP-TYPE
    ENTERPRISE netcomContact
    DESCRIPTION
        "The NetCom has detected a non-normal state on contact 1"
    ::= 1

netcomContact1ReturnToNormal         TRAP-TYPE
    ENTERPRISE netcomContact
    DESCRIPTION
        "The NetCom has detected a return to normal state on contact 1"
    ::= 11

netcomContact2NonNormal              TRAP-TYPE
    ENTERPRISE netcomContact
    DESCRIPTION
        "The NetCom has detected a non-normal state on contact 2"
    ::= 2

netcomContact2ReturnToNormal         TRAP-TYPE
    ENTERPRISE netcomContact
    DESCRIPTION
        "The NetCom has detected a return to normal state on contact 2"
    ::= 12

netcomContact3NonNormal              TRAP-TYPE
    ENTERPRISE netcomContact
    DESCRIPTION
        "The NetCom has detected a non-normal state on contact 3"
    ::= 3

netcomContact3ReturnToNormal         TRAP-TYPE
    ENTERPRISE netcomContact
    DESCRIPTION
        "The NetCom has detected a return to normal state on contact 3"
    ::= 13

netcomContact4NonNormal              TRAP-TYPE
    ENTERPRISE netcomContact
    DESCRIPTION
        "The NetCom has detected a non-normal state on contact 4"
    ::= 4

netcomContact4ReturnToNormal         TRAP-TYPE
    ENTERPRISE netcomContact
    DESCRIPTION
        "The NetCom has detected a return to normal state on contact 4"
    ::= 14

netcomContact5NonNormal              TRAP-TYPE
    ENTERPRISE netcomContact
    DESCRIPTION
        "The NetCom has detected a non-normal state on contact 5"
    ::= 5

netcomContact5ReturnToNormal         TRAP-TYPE
    ENTERPRISE netcomContact
    DESCRIPTION
        "The NetCom has detected a return to normal state on contact 5"
    ::= 15

netcomContact6NonNormal              TRAP-TYPE
    ENTERPRISE netcomContact
    DESCRIPTION
        "The NetCom has detected a non-normal state on contact 6"
    ::= 6

netcomContact6ReturnToNormal         TRAP-TYPE
    ENTERPRISE netcomContact
    DESCRIPTION
        "The NetCom has detected a return to normal state on contact 6"
    ::= 16

netcomContact7NonNormal              TRAP-TYPE
    ENTERPRISE netcomContact
    DESCRIPTION
        "The NetCom has detected a non-normal state on contact 7"
    ::= 7

netcomContact7ReturnToNormal         TRAP-TYPE
    ENTERPRISE netcomContact
    DESCRIPTION
        "The NetCom has detected a return to normal state on contact 7"
    ::= 17
-- }}}


END
