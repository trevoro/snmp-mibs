--------------------------------------------------------------------------      
-- #condInclude "rs.inc"
-- #condInclude "rfc2851.inc"
RIVERSTONE-DHCP-MIB DEFINITIONS ::= BEGIN

--  This module provides authoritative definitions for Riverstone
--  enterprise-specific SNMP API to manage Riverstone Switch
--  DHCP feature.
--
--  This module will be extended, as required.

IMPORTS
    Integer32, OBJECT-TYPE, MODULE-IDENTITY, OBJECT-IDENTITY
        FROM SNMPv2-SMI
    DisplayString, TEXTUAL-CONVENTION, TruthValue
        FROM SNMPv2-TC
    MODULE-COMPLIANCE, OBJECT-GROUP
        FROM SNMPv2-CONF
    InetAddressType, InetAddress
        FROM INET-ADDRESS-MIB           -- RFC2851
    riverstoneMibs 
       FROM RIVERSTONE-SMI-MIB;

rsDhcpMIB MODULE-IDENTITY  
    LAST-UPDATED "200209100000Z"  -- Sept. 10, 2002
    ORGANIZATION "Riverstone Networks Inc."
    CONTACT-INFO
    "Riverstone Networks, Inc
     5200 Great America Parkway
     Santa Clara, CA 95054
     (408) 878-6500
     nms-eng@riverstonenet.com
     http://www.riverstonenet.com"

    DESCRIPTION
         "This mib module defines an SNMP API to manage Riverstone 
          switch DHCP feature"
    REVISION     "200209100000Z"
    DESCRIPTION
       "Added number of clients statistcs objects"

      ::= { riverstoneMibs 50 }



--Textual Conventions
  RsErrorCode ::= TEXTUAL-CONVENTION
       STATUS       current
       DESCRIPTION
        "A unique value, greater than zero defining the operation
         completion status."
       SYNTAX       INTEGER {
                      noStatus(1),
                      timeout(2),
                      networkError(3),
                      noSpace(4),
		      invalidConfig(5),
                      commandCompleted(6),
	              internalError(7),
                      tftpServerError(8)
                }



  rsDhcpNotifications   OBJECT-IDENTITY
      STATUS current
      DESCRIPTION 
        "Group for dhcp  related Notifications"

      ::= { rsDhcpMIB 0 }


   rsDhcpLeaseFileGroup   OBJECT-IDENTITY
      STATUS current
      DESCRIPTION 
        "Group for dhcp  lease file upload"

       ::= { rsDhcpMIB 5}

   rsDhcpConfigGroup   OBJECT-IDENTITY
       STATUS current
       DESCRIPTION 
        "Dhcp config group"

       ::= { rsDhcpMIB 10 }

   rsDhcpStatisticsGroup   OBJECT-IDENTITY
       STATUS current
       DESCRIPTION 
        "Dhcp statistics group"

       ::= { rsDhcpMIB 15 }


--MIB definition dhcp file transfer 

   rsDhcpLeaseFileTransferOp  OBJECT-TYPE
       SYNTAX      INTEGER {
                      noop(1),
                      sendLeaseFileToAgent(2),
                      receiveLeaseFileFromAgent(3)
                   }	
       MAX-ACCESS  read-write
       STATUS      current
       DESCRIPTION
	"Transfer operation to be performed. DHCP lease files are 
         ASCII NVT text files.
	
        Send operations use tftp to transfer a file from the manager 
        to agent. Receive operations use tftp to transfer the file
        from the agent to the manager. Default value is no operation
        or noop."
       ::= { rsDhcpLeaseFileGroup 1 }

rsDhcpLeaseFileManagerAddressType  OBJECT-TYPE
       SYNTAX      InetAddressType
       MAX-ACCESS  read-write
       STATUS      current
       DESCRIPTION
	"Specifies the type of IP address of the Manager to be used by
         the agent for rsDhcpLeaseFileTransferOp operations."
       DEFVAL { ipv4 } --ipv4(1)
       ::= { rsDhcpLeaseFileGroup 2 }

   rsDhcpLeaseFileManagerAddress  OBJECT-TYPE
       SYNTAX      InetAddress
       MAX-ACCESS  read-write
       STATUS      current
       DESCRIPTION
	"The IP address of the Manager to be used by the agent for
         rsDhcpLeaseFileTransferOp operations. Address must be a 
         unicast address that is reachable from the agent and no 
         firewalls/acls preventing tftp datagrams from being
         transferred. The address type is determined by the object
         value of rsDhcpLeaseFileManagerAddressType. A value for 
         this object MUST be set prior to setting
         rsDhcpLeaseFileActivateTransfer to TRUE."
       ::= { rsDhcpLeaseFileGroup 3 }

   
   rsDhcpLeaseFileFileName  OBJECT-TYPE
       SYNTAX      DisplayString
       MAX-ACCESS  read-write
       STATUS      current
       DESCRIPTION
	"The file name to be retrieved from the tftp server at 
         host dhcpLeaseFileManagerAddress or to be written to. Default
         value is blank. Length of filename string must not exceed 255
         alpha-numeric characters, no spaces in filenames."
       ::= { rsDhcpLeaseFileGroup 4 }

   rsDhcpLeaseFileActivateTransfer  OBJECT-TYPE
       SYNTAX  TruthValue
       MAX-ACCESS  read-write
       STATUS      current
       DESCRIPTION
	"Activate the file transfer operation with a value of True(1) or 
         stop it with False(2). Poll rsDhcpLeaseFileTransferStatus for
         current status. Default value is False. rsDhcpLeaseFileFileName,
         rsDhcpLeaseFileManagerAddress and rsDhcpLeaseFileTransferOp
         must be valid prior to setting this object to True. "
       ::= { rsDhcpLeaseFileGroup 5 }


    rsDhcpLeaseFileTransferStatus  OBJECT-TYPE
       SYNTAX      INTEGER {
                      idle(1),
                      sending(2),
                      receiving(3),
                      transferComplete(4),
		      error(5)
                   }	
       MAX-ACCESS  read-only
       STATUS      current
       DESCRIPTION
	"The current status of the transfer task. Default state is idle. 
         sending indicates a file transfer (agent->mgr) in progress. 
         receiving indicates sending a file from Manager to agent. 
         transferComplete indicates a successful transfer. error indicates
         a failed transfer. See rsDhcpLeaseFileLastError to diagnose why
         the transfer failed."
       ::= { rsDhcpLeaseFileGroup 6 }

   rsDhcpLeaseFileLastError  OBJECT-TYPE
       SYNTAX      RsErrorCode
       MAX-ACCESS  read-only
       STATUS      current
       DESCRIPTION
	"A reason code for the last transfer operation. Poll this value
         when doing sets against dhcpLeaseFileActivateFile  obtain status."
       ::= { rsDhcpLeaseFileGroup 7 }

   rsDhcpLeaseFileLastErrorReason  OBJECT-TYPE
       SYNTAX      DisplayString
       MAX-ACCESS  read-only
       STATUS      current
       DESCRIPTION
	"A string representation of dhcpLeaseFileLastError which may 
         contain additional details."
       ::= { rsDhcpLeaseFileGroup 8 }

   rsDhcpMaxClientsAllowed OBJECT-TYPE
       SYNTAX      Integer32
       MAX-ACCESS  read-only
       STATUS      current
       DESCRIPTION
	"Maximum number of DHCP clients allowed per system"
       ::= { rsDhcpStatisticsGroup 1 }


   rsDhcpNumberOfClients OBJECT-TYPE
       SYNTAX      Integer32
       MAX-ACCESS  read-only
       STATUS      current
       DESCRIPTION
	"Current number of DHCP clients connected"
       ::= { rsDhcpStatisticsGroup 2 }


-- Conformance statements
   rsDhcpConformance OBJECT IDENTIFIER ::= { rsDhcpMIB 3 }
   rsDhcpCompliances OBJECT IDENTIFIER ::= { rsDhcpConformance 1 }
   rsDhcpGroups      OBJECT IDENTIFIER ::= { rsDhcpConformance 2 }
 
   rsDhcpCompliance MODULE-COMPLIANCE
    STATUS  current
    DESCRIPTION
         "The compliance statement for SNMP entities which implement
         the dhcp management and config objects for RS "
    MODULE  -- this module
        MANDATORY-GROUPS { rsDhcpGroup1, rsDhcpGroup2 }
       ::= { rsDhcpCompliances 1 }

-- MIB groupings
-- Grouping for rsDhcpLeaseFileGroup
 
   rsDhcpGroup1    OBJECT-GROUP
    OBJECTS {
      rsDhcpLeaseFileTransferOp,
      rsDhcpLeaseFileManagerAddressType,
      rsDhcpLeaseFileManagerAddress,
      rsDhcpLeaseFileFileName,
      rsDhcpLeaseFileActivateTransfer,
      rsDhcpLeaseFileTransferStatus,
      rsDhcpLeaseFileLastError,
      rsDhcpLeaseFileLastErrorReason
    }
    STATUS  current
    DESCRIPTION
            "The collection of objects which are used to represent 
             version 1.0 of DHCP MIB"
       ::= { rsDhcpGroups 1 }

-- Grouping for rsDhcpLeaseFileGroup
 
   rsDhcpGroup2    OBJECT-GROUP
    OBJECTS {

        rsDhcpMaxClientsAllowed ,
        rsDhcpNumberOfClients 
    }
    STATUS  current
    DESCRIPTION
            "The collection of objects which are used to represent 
             version 1.1 of DHCP MIB"
       ::= { rsDhcpGroups 2 }

END
