Nortel-Magellan-Passport-VirtualRouterMIB
DEFINITIONS ::= BEGIN



IMPORTS

      OBJECT-TYPE
   FROM RFC-1212

      components,
      passportMIBs
   FROM Nortel-Magellan-Passport-UsefulDefinitionsMIB

      Counter32,
      RowPointer,
      DisplayString,
      StorageType,
      RowStatus,
      InterfaceIndex,
      Gauge32,
      Integer32,
      Unsigned32
   FROM Nortel-Magellan-Passport-StandardTextualConventionsMIB

      AsciiString,
      NonReplicated,
      HexString,
      Link,
      AsciiStringIndex,
      IntegerSequence
   FROM Nortel-Magellan-Passport-TextualConventionsMIB;




-- LAST-UPDATED   "9906090000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     VirtualRouter Enterprise MIB."

virtualRouterMIB OBJECT IDENTIFIER ::= { passportMIBs 26 }










-- Vr/<string>
-- The VirtualRouter component represents an instance of a Router on the 
-- platform. Vr provides a mechanism to segregate router traffic and 
-- maintenance activities based on a logical separation of ports into 
-- separate VirtualRouters.

vr OBJECT IDENTIFIER ::= { components 100 }



vrRowStatusTable OBJECT-TYPE
   SYNTAX     SEQUENCE OF VrRowStatusEntry
   ACCESS     not-accessible
   STATUS     mandatory
   DESCRIPTION
     "This entry controls the addition and deletion of 
      vr components."
::= { vr 1 }

vrRowStatusEntry OBJECT-TYPE
   SYNTAX     VrRowStatusEntry
   ACCESS     not-accessible
   STATUS     mandatory
   DESCRIPTION
     "A single entry in the table represents a single 
      vr component."
   INDEX {
      vrIndex }
::= { vrRowStatusTable 1 }

VrRowStatusEntry ::= SEQUENCE {
   vrRowStatus
      RowStatus,
   vrComponentName
      DisplayString,
   vrStorageType
      StorageType,
   vrIndex
      AsciiStringIndex }

vrRowStatus OBJECT-TYPE
   SYNTAX     RowStatus 
   ACCESS     read-write
   STATUS     mandatory
   DESCRIPTION
     "This variable is used as the basis for SNMP naming of
      vr components.
      These components can be added and deleted."
::= { vrRowStatusEntry 1 }

vrComponentName OBJECT-TYPE
   SYNTAX     DisplayString 
   ACCESS     read-only
   STATUS     mandatory
   DESCRIPTION
     "This variable provides the component's string name for
      use with the ASCII Console Interface"
::= { vrRowStatusEntry 2 }

vrStorageType OBJECT-TYPE
   SYNTAX     StorageType 
   ACCESS     read-only
   STATUS     mandatory
   DESCRIPTION
     "This variable represents the storage type value for the
      vr tables."
::= { vrRowStatusEntry 4 }

vrIndex OBJECT-TYPE
   SYNTAX     AsciiStringIndex (SIZE (1..8))
   ACCESS     not-accessible
   STATUS     mandatory
   DESCRIPTION
     "This variable represents the index for the vr tables."
::= { vrRowStatusEntry 10 }

vrAdminContorlTable OBJECT-TYPE
   SYNTAX     SEQUENCE OF VrAdminContorlEntry
   ACCESS     not-accessible
   STATUS     mandatory
   DESCRIPTION
     "This group includes the Administrative Control attribute. This 
      attribute defines the current administrative state of this component."
::= { vr 100 }

vrAdminContorlEntry OBJECT-TYPE
   SYNTAX     VrAdminContorlEntry
   ACCESS     not-accessible
   STATUS     mandatory
   DESCRIPTION
     "An entry in the vrAdminContorlTable."
   INDEX {
      vrIndex }
::= { vrAdminContorlTable 1 }

VrAdminContorlEntry ::= SEQUENCE {
   vrSnmpAdminStatus
      INTEGER,
   vrManagementAccess
      INTEGER,
   vrVirtualPrivateIntranetIdentifier
      INTEGER }

vrSnmpAdminStatus OBJECT-TYPE
   SYNTAX     INTEGER  {
                 up(1),
                 down(2),
                 testing(3) }
   ACCESS     read-write
   STATUS     mandatory
   DESCRIPTION
     "This sets the desired state of this VirtualRouter. The up state   
      indicates the Vr is operational. The down state indicates the Vr is 
      not operational.  
      The down state is only valid when the managementAccess attribute 
      is disabled. Testing is an invalid state for the Vr."
   DEFVAL     { up }
::= { vrAdminContorlEntry 1 }

vrManagementAccess OBJECT-TYPE
   SYNTAX     INTEGER  {
                 disabled(0),
                 enabled(1) }
   ACCESS     read-write
   STATUS     mandatory
   DESCRIPTION
     "This attributes defines the routing capabilities of this Virtual Router
      and controls the tcp access into that Vr.  
      External access is only permitted through the Vr that has this     
      attribute enabled. 
      The attribute allows the following subcomponents to be
      provisioned: Ipx, Bridging, Sna, Sres, NetSentry, and Snmp.
      Exactly one Vr must have this attribute enabled.  
      The first provisioned Vr will have the attribute enabled by default.  
      Subsequent Vrs will have the attribute disabled."
::= { vrAdminContorlEntry 2 }

vrVirtualPrivateIntranetIdentifier OBJECT-TYPE
   SYNTAX     INTEGER (1..255)
   ACCESS     read-write
   STATUS     mandatory
   DESCRIPTION
     "Identifies the Virtual  Private Intranet (VPI) associated with this 
      Virtual Router. The vpiId must be unique for each VR on a    
      Passport and ach interconnected VR must have the same vpiId."
::= { vrAdminContorlEntry 3 }

vrCidDataTable OBJECT-TYPE
   SYNTAX     SEQUENCE OF VrCidDataEntry
   ACCESS     not-accessible
   STATUS     mandatory
   DESCRIPTION
     "This group contains the attribute for a component's Customer 
      Identifier (CID). Refer to the attribute description for a detailed 
      explanation of CIDs."
::= { vr 101 }

vrCidDataEntry OBJECT-TYPE
   SYNTAX     VrCidDataEntry
   ACCESS     not-accessible
   STATUS     mandatory
   DESCRIPTION
     "An entry in the vrCidDataTable."
   INDEX {
      vrIndex }
::= { vrCidDataTable 1 }

VrCidDataEntry ::= SEQUENCE {
   vrCustomerIdentifier
      Unsigned32 }

vrCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { vrCidDataEntry 1 }

vrOperStatusTable OBJECT-TYPE
   SYNTAX     SEQUENCE OF VrOperStatusEntry
   ACCESS     not-accessible
   STATUS     mandatory
   DESCRIPTION
     "This group includes the Operational Status attribute. This attribute 
      defines the current operational state of this component."
::= { vr 103 }

vrOperStatusEntry OBJECT-TYPE
   SYNTAX     VrOperStatusEntry
   ACCESS     not-accessible
   STATUS     mandatory
   DESCRIPTION
     "An entry in the vrOperStatusTable."
   INDEX {
      vrIndex }
::= { vrOperStatusTable 1 }

VrOperStatusEntry ::= SEQUENCE {
   vrSnmpOperStatus
      INTEGER }

vrSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { vrOperStatusEntry 1 }

vrStateTable OBJECT-TYPE
   SYNTAX     SEQUENCE OF VrStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { vr 104 }

vrStateEntry OBJECT-TYPE
   SYNTAX     VrStateEntry
   ACCESS     not-accessible
   STATUS     mandatory
   DESCRIPTION
     "An entry in the vrStateTable."
   INDEX {
      vrIndex }
::= { vrStateTable 1 }

VrStateEntry ::= SEQUENCE {
   vrAdminState
      INTEGER,
   vrOperationalState
      INTEGER,
   vrUsageState
      INTEGER }

vrAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { vrStateEntry 1 }

vrOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { vrStateEntry 2 }

vrUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { vrStateEntry 3 }

vrIfNumberOperTable OBJECT-TYPE
   SYNTAX     SEQUENCE OF VrIfNumberOperEntry
   ACCESS     not-accessible
   STATUS     mandatory
   DESCRIPTION
     "This group contains the ifNumber attribute."
::= { vr 105 }

vrIfNumberOperEntry OBJECT-TYPE
   SYNTAX     VrIfNumberOperEntry
   ACCESS     not-accessible
   STATUS     mandatory
   DESCRIPTION
     "An entry in the vrIfNumberOperTable."
   INDEX {
      vrIndex }
::= { vrIfNumberOperTable 1 }

VrIfNumberOperEntry ::= SEQUENCE {
   vrIfNumber
      Unsigned32 }

vrIfNumber OBJECT-TYPE
   SYNTAX     Unsigned32 (0..65535)
   ACCESS     read-only
   STATUS     mandatory
   DESCRIPTION
     "This attribute defines the number of IfEntries in the IfTable."
::= { vrIfNumberOperEntry 1 }


-- Vr/<string> Mm
-- The MemoryManagement component provides a mechanism which 
-- controls and monitors Dynamic Memory usage within a VirtualRouter. 
-- Upper layer protocols and other Vr subcomponents memory usage can 
-- be enforced using the provisioned attributes of this component.

vrMm OBJECT IDENTIFIER ::= { vr 2 }



vrMmRowStatusTable OBJECT-TYPE
   SYNTAX     SEQUENCE OF VrMmRowStatusEntry
   ACCESS     not-accessible
   STATUS     mandatory
   DESCRIPTION
     "This entry controls the addition and deletion of 
      vrMm components."
::= { vrMm 1 }

vrMmRowStatusEntry OBJECT-TYPE
   SYNTAX     VrMmRowStatusEntry
   ACCESS     not-accessible
   STATUS     mandatory
   DESCRIPTION
     "A single entry in the table represents a single 
      vrMm component."
   INDEX {
      vrIndex,
      vrMmIndex }
::= { vrMmRowStatusTable 1 }

VrMmRowStatusEntry ::= SEQUENCE {
   vrMmRowStatus
      RowStatus,
   vrMmComponentName
      DisplayString,
   vrMmStorageType
      StorageType,
   vrMmIndex
      NonReplicated }

vrMmRowStatus OBJECT-TYPE
   SYNTAX     RowStatus 
   ACCESS     read-only
   STATUS     mandatory
   DESCRIPTION
     "This variable is used as the basis for SNMP naming of
      vrMm components.
      These components cannot be added nor deleted."
::= { vrMmRowStatusEntry 1 }

vrMmComponentName OBJECT-TYPE
   SYNTAX     DisplayString 
   ACCESS     read-only
   STATUS     mandatory
   DESCRIPTION
     "This variable provides the component's string name for
      use with the ASCII Console Interface"
::= { vrMmRowStatusEntry 2 }

vrMmStorageType OBJECT-TYPE
   SYNTAX     StorageType 
   ACCESS     read-only
   STATUS     mandatory
   DESCRIPTION
     "This variable represents the storage type value for the
      vrMm tables."
::= { vrMmRowStatusEntry 4 }

vrMmIndex OBJECT-TYPE
   SYNTAX     NonReplicated 
   ACCESS     not-accessible
   STATUS     mandatory
   DESCRIPTION
     "This variable represents the index for the vrMm tables."
::= { vrMmRowStatusEntry 10 }

vrMmProvTable OBJECT-TYPE
   SYNTAX     SEQUENCE OF VrMmProvEntry
   ACCESS     not-accessible
   STATUS     mandatory
   DESCRIPTION
     "The group includes all provisioned attributes for the 
      MemoryManagement component."
::= { vrMm 10 }

vrMmProvEntry OBJECT-TYPE
   SYNTAX     VrMmProvEntry
   ACCESS     not-accessible
   STATUS     mandatory
   DESCRIPTION
     "An entry in the vrMmProvTable."
   INDEX {
      vrIndex,
      vrMmIndex }
::= { vrMmProvTable 1 }

VrMmProvEntry ::= SEQUENCE {
   vrMmVrMaxHeapSpace
      Unsigned32,
   vrMmIpMaxHeapSpace
      Unsigned32,
   vrMmIpxMaxHeapSpace
      Unsigned32,
   vrMmBridgingMaxHeapSpace
      Unsigned32,
   vrMmNetSentryMaxHeapSpace
      Unsigned32,
   vrMmSresMaxHeapSpace
      Unsigned32,
   vrMmSnaMaxHeapSpace
      Unsigned32 }

vrMmVrMaxHeapSpace OBJECT-TYPE
   SYNTAX     Unsigned32 (0..100)
   ACCESS     read-write
   STATUS     mandatory
   DESCRIPTION
     "The maximum percentage of the total system heap space that is 
      allowed for use by this Virtual Router. Memory allocation for this 
      VR which attempts to exceed this limit will fail causing a shut down 
      of the requesting process."
   DEFVAL     { 100 }
::= { vrMmProvEntry 1 }

vrMmIpMaxHeapSpace OBJECT-TYPE
   SYNTAX     Unsigned32 (0..100)
   ACCESS     read-write
   STATUS     mandatory
   DESCRIPTION
     "The maximum percentage of this VR's dynamic memory which can be 
      allocated to this VR's IP. An attempt to allocate memory in excess of 
      this limit forces IP to shut down."
   DEFVAL     { 100 }
::= { vrMmProvEntry 2 }

vrMmIpxMaxHeapSpace OBJECT-TYPE
   SYNTAX     Unsigned32 (0..100)
   ACCESS     read-write
   STATUS     mandatory
   DESCRIPTION
     "The maximum percentage of this VR's dynamic memory which can be 
      allocated to this VR's IPX. An attempt to allocate memory in excess of 
      this limit forces IPX to shut down."
   DEFVAL     { 100 }
::= { vrMmProvEntry 3 }

vrMmBridgingMaxHeapSpace OBJECT-TYPE
   SYNTAX     Unsigned32 (0..100)
   ACCESS     read-write
   STATUS     mandatory
   DESCRIPTION
     "The maximum percentage of this VR's dynamic memory which can be 
      allocated to this VR's Bridging. An attempt to allocate memory in 
      excess of this limit forces Bridging to shut down."
   DEFVAL     { 100 }
::= { vrMmProvEntry 6 }

vrMmNetSentryMaxHeapSpace OBJECT-TYPE
   SYNTAX     Unsigned32 (0..100)
   ACCESS     read-write
   STATUS     mandatory
   DESCRIPTION
     "The maximum percentage of this VR's dynamic memory which can be 
      allocated to this VR's NetSentry. An attempt to allocate memory in 
      excess of this limit forces NetSentry to shut down."
   DEFVAL     { 100 }
::= { vrMmProvEntry 7 }

vrMmSresMaxHeapSpace OBJECT-TYPE
   SYNTAX     Unsigned32 (0..100)
   ACCESS     read-write
   STATUS     mandatory
   DESCRIPTION
     "The maximum percentage of this VR's dynamic memory which can 
      be allocated to this VR's SourceRouteEndStation. An attempt to 
      allocate memory in excess of this limit forces 
      SourceRouteEndStation to shut down."
   DEFVAL     { 100 }
::= { vrMmProvEntry 8 }

vrMmSnaMaxHeapSpace OBJECT-TYPE
   SYNTAX     Unsigned32 (0..100)
   ACCESS     read-write
   STATUS     mandatory
   DESCRIPTION
     "The maximum percentage of this VR's dynamic memory which can 
      be allocated to this VR's SNA. An attempt to allocate memory in 
      excess of this limit forces SNA to shut down."
   DEFVAL     { 100 }
::= { vrMmProvEntry 9 }

vrMmOperTable OBJECT-TYPE
   SYNTAX     SEQUENCE OF VrMmOperEntry
   ACCESS     not-accessible
   STATUS     mandatory
   DESCRIPTION
     "The group includes all operational attributes for the 
      MemoryManagement component."
::= { vrMm 11 }

vrMmOperEntry OBJECT-TYPE
   SYNTAX     VrMmOperEntry
   ACCESS     not-accessible
   STATUS     mandatory
   DESCRIPTION
     "An entry in the vrMmOperTable."
   INDEX {
      vrIndex,
      vrMmIndex }
::= { vrMmOperTable 1 }

VrMmOperEntry ::= SEQUENCE {
   vrMmVrHeapSpaceBytesAllocated
      Unsigned32,
   vrMmVrHeapSpaceAllocated
      Unsigned32,
   vrMmIpHeapSpaceAllocated
      Unsigned32,
   vrMmIpxHeapSpaceAllocated
      Unsigned32,
   vrMmBridgingHeapSpaceAllocated
      Unsigned32,
   vrMmNetSentryHeapSpaceAllocated
      Unsigned32,
   vrMmSresHeapSpaceAllocated
      Unsigned32,
   vrMmSnaHeapSpaceAllocated
      Unsigned32 }

vrMmVrHeapSpaceBytesAllocated OBJECT-TYPE
   SYNTAX     Unsigned32 (0..4294967295)
   ACCESS     read-only
   STATUS     mandatory
   DESCRIPTION
     "The number of bytes of system dynamic memory which has been 
      allocated by this Virtual Router."
::= { vrMmOperEntry 1 }

vrMmVrHeapSpaceAllocated OBJECT-TYPE
   SYNTAX     Unsigned32 (0..100)
   ACCESS     read-only
   STATUS     mandatory
   DESCRIPTION
     "The percentage of system dynamic memory which is currently allocated 
      to this Virtual Router."
::= { vrMmOperEntry 2 }

vrMmIpHeapSpaceAllocated OBJECT-TYPE
   SYNTAX     Unsigned32 (0..100)
   ACCESS     read-only
   STATUS     mandatory
   DESCRIPTION
     "The percentage of this Virtual Router's dynamic memory which is 
      currently allocated to this Virtual Router's IP."
::= { vrMmOperEntry 3 }

vrMmIpxHeapSpaceAllocated OBJECT-TYPE
   SYNTAX     Unsigned32 (0..100)
   ACCESS     read-only
   STATUS     mandatory
   DESCRIPTION
     "The percentage of this Virtual Router's dynamic memory which is 
      currently allocated to this Virtual Router's IPX."
   DEFVAL     { 100 }
::= { vrMmOperEntry 4 }

vrMmBridgingHeapSpaceAllocated OBJECT-TYPE
   SYNTAX     Unsigned32 (0..100)
   ACCESS     read-only
   STATUS     mandatory
   DESCRIPTION
     "The percentage of this Virtual Router's dynamic memory which is 
      currently allocated to this Virtual Router's Bridging."
::= { vrMmOperEntry 7 }

vrMmNetSentryHeapSpaceAllocated OBJECT-TYPE
   SYNTAX     Unsigned32 (0..100)
   ACCESS     read-only
   STATUS     mandatory
   DESCRIPTION
     "The percentage of this Virtual Router's dynamic memory which is 
      currently allocated to this Virtual Router's NetSentry."
::= { vrMmOperEntry 8 }

vrMmSresHeapSpaceAllocated OBJECT-TYPE
   SYNTAX     Unsigned32 (0..100)
   ACCESS     read-only
   STATUS     mandatory
   DESCRIPTION
     "The percentage of this Virtual Router's dynamic memory which is 
      currently allocated to this Virtual Router's Source Route End Station."
::= { vrMmOperEntry 9 }

vrMmSnaHeapSpaceAllocated OBJECT-TYPE
   SYNTAX     Unsigned32 (0..100)
   ACCESS     read-only
   STATUS     mandatory
   DESCRIPTION
     "The percentage of this Virtual Router's dynamic memory which is 
      currently allocated to this Virtual Router's SNA."
::= { vrMmOperEntry 10 }


-- Vr/<string> Pp/<string>
-- This component represents a logical interface to the network. 
-- Protocol Ports are associated with physical or logical media via a 
-- linkage attribute. Protocol Ports allow for individual upper layer 
-- protocols to be enabled or disabled. 

vrPp OBJECT IDENTIFIER ::= { vr 3 }



vrPpRowStatusTable OBJECT-TYPE
   SYNTAX     SEQUENCE OF VrPpRowStatusEntry
   ACCESS     not-accessible
   STATUS     mandatory
   DESCRIPTION
     "This entry controls the addition and deletion of 
      vrPp components."
::= { vrPp 1 }

vrPpRowStatusEntry OBJECT-TYPE
   SYNTAX     VrPpRowStatusEntry
   ACCESS     not-accessible
   STATUS     mandatory
   DESCRIPTION
     "A single entry in the table represents a single 
      vrPp component."
   INDEX {
      vrIndex,
      vrPpIndex }
::= { vrPpRowStatusTable 1 }

VrPpRowStatusEntry ::= SEQUENCE {
   vrPpRowStatus
      RowStatus,
   vrPpComponentName
      DisplayString,
   vrPpStorageType
      StorageType,
   vrPpIndex
      AsciiStringIndex }

vrPpRowStatus OBJECT-TYPE
   SYNTAX     RowStatus 
   ACCESS     read-write
   STATUS     mandatory
   DESCRIPTION
     "This variable is used as the basis for SNMP naming of
      vrPp components.
      These components can be added and deleted."
::= { vrPpRowStatusEntry 1 }

vrPpComponentName OBJECT-TYPE
   SYNTAX     DisplayString 
   ACCESS     read-only
   STATUS     mandatory
   DESCRIPTION
     "This variable provides the component's string name for
      use with the ASCII Console Interface"
::= { vrPpRowStatusEntry 2 }

vrPpStorageType OBJECT-TYPE
   SYNTAX     StorageType 
   ACCESS     read-only
   STATUS     mandatory
   DESCRIPTION
     "This variable represents the storage type value for the
      vrPp tables."
::= { vrPpRowStatusEntry 4 }

vrPpIndex OBJECT-TYPE
   SYNTAX     AsciiStringIndex (SIZE (1..20))
   ACCESS     not-accessible
   STATUS     mandatory
   DESCRIPTION
     "This variable represents the index for the vrPp tables."
::= { vrPpRowStatusEntry 10 }

vrPpAdminControlTable OBJECT-TYPE
   SYNTAX     SEQUENCE OF VrPpAdminControlEntry
   ACCESS     not-accessible
   STATUS     mandatory
   DESCRIPTION
     "This group includes the Administrative Control attribute. This 
      attribute defines the current administrative state of this component."
::= { vrPp 100 }

vrPpAdminControlEntry OBJECT-TYPE
   SYNTAX     VrPpAdminControlEntry
   ACCESS     not-accessible
   STATUS     mandatory
   DESCRIPTION
     "An entry in the vrPpAdminControlTable."
   INDEX {
      vrIndex,
      vrPpIndex }
::= { vrPpAdminControlTable 1 }

VrPpAdminControlEntry ::= SEQUENCE {
   vrPpSnmpAdminStatus
      INTEGER }

vrPpSnmpAdminStatus OBJECT-TYPE
   SYNTAX     INTEGER  {
                 up(1),
                 down(2),
                 testing(3) }
   ACCESS     read-write
   STATUS     mandatory
   DESCRIPTION
     "The desired state of the interface. The up state indicates the 
      interface is operational and packet forwarding is allowed. The down 
      state indicates the interface is not operational and packet forwarding 
      is unavailable. The testing state indicates that no operational 
      packets can be passed."
   DEFVAL     { up }
::= { vrPpAdminControlEntry 1 }

vrPpProvTable OBJECT-TYPE
   SYNTAX     SEQUENCE OF VrPpProvEntry
   ACCESS     not-accessible
   STATUS     mandatory
   DESCRIPTION
     "This group includes provisioned attributes specific to the ProtocolPort 
      component."
::= { vrPp 101 }

vrPpProvEntry OBJECT-TYPE
   SYNTAX     VrPpProvEntry
   ACCESS     not-accessible
   STATUS     mandatory
   DESCRIPTION
     "An entry in the vrPpProvTable."
   INDEX {
      vrIndex,
      vrPpIndex }
::= { vrPpProvTable 1 }

VrPpProvEntry ::= SEQUENCE {
   vrPpLinkToMedia
      Link }

vrPpLinkToMedia OBJECT-TYPE
   SYNTAX     Link 
   ACCESS     read-write
   STATUS     mandatory
   DESCRIPTION
     "This attribute defines the Media Application which this Protocol Port is 
      using as an interface to the network."
::= { vrPpProvEntry 1 }

vrPpOperStatusTable OBJECT-TYPE
   SYNTAX     SEQUENCE OF VrPpOperStatusEntry
   ACCESS     not-accessible
   STATUS     mandatory
   DESCRIPTION
     "This group includes the Operational Status attribute. This attribute 
      defines the current operational state of this component."
::= { vrPp 102 }

vrPpOperStatusEntry OBJECT-TYPE
   SYNTAX     VrPpOperStatusEntry
   ACCESS     not-accessible
   STATUS     mandatory
   DESCRIPTION
     "An entry in the vrPpOperStatusTable."
   INDEX {
      vrIndex,
      vrPpIndex }
::= { vrPpOperStatusTable 1 }

VrPpOperStatusEntry ::= SEQUENCE {
   vrPpSnmpOperStatus
      INTEGER }

vrPpSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { vrPpOperStatusEntry 1 }

vrPpStateTable OBJECT-TYPE
   SYNTAX     SEQUENCE OF VrPpStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { vrPp 103 }

vrPpStateEntry OBJECT-TYPE
   SYNTAX     VrPpStateEntry
   ACCESS     not-accessible
   STATUS     mandatory
   DESCRIPTION
     "An entry in the vrPpStateTable."
   INDEX {
      vrIndex,
      vrPpIndex }
::= { vrPpStateTable 1 }

VrPpStateEntry ::= SEQUENCE {
   vrPpAdminState
      INTEGER,
   vrPpOperationalState
      INTEGER,
   vrPpUsageState
      INTEGER }

vrPpAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { vrPpStateEntry 1 }

vrPpOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { vrPpStateEntry 2 }

vrPpUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { vrPpStateEntry 3 }

vrPpOperTable OBJECT-TYPE
   SYNTAX     SEQUENCE OF VrPpOperEntry
   ACCESS     not-accessible
   STATUS     mandatory
   DESCRIPTION
     "This group includes operational attributes specific to the ProtocolPort 
      component."
::= { vrPp 104 }

vrPpOperEntry OBJECT-TYPE
   SYNTAX     VrPpOperEntry
   ACCESS     not-accessible
   STATUS     mandatory
   DESCRIPTION
     "An entry in the vrPpOperTable."
   INDEX {
      vrIndex,
      vrPpIndex }
::= { vrPpOperTable 1 }

VrPpOperEntry ::= SEQUENCE {
   vrPpIfIndex
      InterfaceIndex }

vrPpIfIndex OBJECT-TYPE
   SYNTAX     InterfaceIndex (1..65535)
   ACCESS     read-only
   STATUS     mandatory
   DESCRIPTION
     "This represents the SNMP ifIndex which is associated with this PP. This 
      ifIndex can be used to extract detailed information about the PP from 
      the ifTable."
::= { vrPpOperEntry 1 }

vrPpNbmaAddressTable OBJECT-TYPE
   SYNTAX     SEQUENCE OF VrPpNbmaAddressEntry
   ACCESS     not-accessible
   STATUS     mandatory
   DESCRIPTION
     "This group contains the operational attributes of the ProtocolPort 
      component specific to NHRP."
::= { vrPp 105 }

vrPpNbmaAddressEntry OBJECT-TYPE
   SYNTAX     VrPpNbmaAddressEntry
   ACCESS     not-accessible
   STATUS     mandatory
   DESCRIPTION
     "An entry in the vrPpNbmaAddressTable."
   INDEX {
      vrIndex,
      vrPpIndex }
::= { vrPpNbmaAddressTable 1 }

VrPpNbmaAddressEntry ::= SEQUENCE {
   vrPpAtmAddress
      HexString }

vrPpAtmAddress OBJECT-TYPE
   SYNTAX     HexString (SIZE (0..20))
   ACCESS     read-only
   STATUS     mandatory
   DESCRIPTION
     "This attribute indicates the ATM address which is associated with 
      this protocol port. NHRP uses this address to establish shortcut 
      connections. This attribute is not displayed if NHRP is not 
      provisioned on this protocol port."
::= { vrPpNbmaAddressEntry 1 }

-- 
-- *** THIS SUBTREE CURRENTLY NOT IMPLEMENTED ***
-- 

-- Vr/<string> IfTableEntry/n
-- Each instance of this component represents one row in the IfTable 
-- as defined in rfc1213. One entry will exist for each ProtocolPort 
-- defined under this VirtualRouter. If this is the management Vr, an 
-- entry also exists for each physical interface defined. 

vrIfTableEntry OBJECT IDENTIFIER ::= { vr 10 }



vrIfTableEntryRowStatusTable OBJECT-TYPE
   SYNTAX     SEQUENCE OF VrIfTableEntryRowStatusEntry
   ACCESS     not-accessible
   STATUS     mandatory
   DESCRIPTION
     "*** THIS TABLE CURRENTLY NOT IMPLEMENTED ***

      This entry controls the addition and deletion of 
      vrIfTableEntry components."
::= { vrIfTableEntry 1 }

vrIfTableEntryRowStatusEntry OBJECT-TYPE
   SYNTAX     VrIfTableEntryRowStatusEntry
   ACCESS     not-accessible
   STATUS     mandatory
   DESCRIPTION
     "A single entry in the table represents a single 
      vrIfTableEntry component."
   INDEX {
      vrIndex,
      vrIfTableEntryIndex }
::= { vrIfTableEntryRowStatusTable 1 }

VrIfTableEntryRowStatusEntry ::= SEQUENCE {
   vrIfTableEntryRowStatus
      RowStatus,
   vrIfTableEntryComponentName
      DisplayString,
   vrIfTableEntryStorageType
      StorageType,
   vrIfTableEntryIndex
      Integer32 }

vrIfTableEntryRowStatus OBJECT-TYPE
   SYNTAX     RowStatus 
   ACCESS     read-only
   STATUS     mandatory
   DESCRIPTION
     "This variable is used as the basis for SNMP naming of
      vrIfTableEntry components.
      These components cannot be added nor deleted."
::= { vrIfTableEntryRowStatusEntry 1 }

vrIfTableEntryComponentName OBJECT-TYPE
   SYNTAX     DisplayString 
   ACCESS     read-only
   STATUS     mandatory
   DESCRIPTION
     "This variable provides the component's string name for
      use with the ASCII Console Interface"
::= { vrIfTableEntryRowStatusEntry 2 }

vrIfTableEntryStorageType OBJECT-TYPE
   SYNTAX     StorageType 
   ACCESS     read-only
   STATUS     mandatory
   DESCRIPTION
     "This variable represents the storage type value for the
      vrIfTableEntry tables."
::= { vrIfTableEntryRowStatusEntry 4 }

vrIfTableEntryIndex OBJECT-TYPE
   SYNTAX     Integer32 (1..65535)
   ACCESS     not-accessible
   STATUS     mandatory
   DESCRIPTION
     "This variable represents the index for the vrIfTableEntry tables."
::= { vrIfTableEntryRowStatusEntry 10 }

vrIfTableEntryIftTable OBJECT-TYPE
   SYNTAX     SEQUENCE OF VrIfTableEntryIftEntry
   ACCESS     not-accessible
   STATUS     mandatory
   DESCRIPTION
     "*** THIS TABLE CURRENTLY NOT IMPLEMENTED ***

      This group represents the SNMP interface table entry."
::= { vrIfTableEntry 10 }

vrIfTableEntryIftEntry OBJECT-TYPE
   SYNTAX     VrIfTableEntryIftEntry
   ACCESS     not-accessible
   STATUS     mandatory
   DESCRIPTION
     "An entry in the vrIfTableEntryIftTable."
   INDEX {
      vrIndex,
      vrIfTableEntryIndex }
::= { vrIfTableEntryIftTable 1 }

VrIfTableEntryIftEntry ::= SEQUENCE {
   vrIfTableEntryIfAdminStatus
      INTEGER,
   vrIfTableEntryIfOperStatus
      INTEGER,
   vrIfTableEntryIfLastChange
      Unsigned32,
   vrIfTableEntryIfInOctets
      Counter32,
   vrIfTableEntryIfOutOctets
      Counter32,
   vrIfTableEntryIfInDiscards
      Counter32,
   vrIfTableEntryIfOutDiscards
      Counter32,
   vrIfTableEntryIfInErrors
      Counter32,
   vrIfTableEntryIfOutErrors
      Counter32,
   vrIfTableEntryIfInUcastPkts
      Counter32,
   vrIfTableEntryIfOutUcastPkts
      Counter32,
   vrIfTableEntryIfInNuCastPkts
      Counter32,
   vrIfTableEntryIfOutNuCastPkts
      Counter32,
   vrIfTableEntryIfInUnknownProtos
      Counter32,
   vrIfTableEntryIfOutQlength
      Gauge32,
   vrIfTableEntryIfDescription
      AsciiString,
   vrIfTableEntryIfType
      INTEGER,
   vrIfTableEntryIfMtu
      Unsigned32,
   vrIfTableEntryIfSpeed
      Unsigned32,
   vrIfTableEntryIfPhysicalAddress
      AsciiString,
   vrIfTableEntryIfSpecific
      IntegerSequence }

vrIfTableEntryIfAdminStatus OBJECT-TYPE
   SYNTAX     INTEGER  {
                 up(1),
                 down(2),
                 testing(3) }
   ACCESS     read-only
   STATUS     mandatory
   DESCRIPTION
     "The down state indicates the interface is not operational. The testing 
      state indicates that no operational packets can be passed."
   DEFVAL     { up }
::= { vrIfTableEntryIftEntry 2 }

vrIfTableEntryIfOperStatus OBJECT-TYPE
   SYNTAX     INTEGER  {
                 up(1),
                 down(2),
                 testing(3) }
   ACCESS     read-only
   STATUS     mandatory
   DESCRIPTION
     "This attribute provides the current operational status of the 
      interface. The testing state indicates that no operational packets can 
      be passed."
   DEFVAL     { down }
::= { vrIfTableEntryIftEntry 3 }

vrIfTableEntryIfLastChange OBJECT-TYPE
   SYNTAX     Unsigned32 (0..4294967295)
   ACCESS     read-only
   STATUS     mandatory
   DESCRIPTION
     "The value of sysUpTime at the time the interface entered its current 
      operational state. If the current state was entered prior to the last re- 
      initialization of the local network management subsystem, then this 
      object contains a zero value."
::= { vrIfTableEntryIftEntry 4 }

vrIfTableEntryIfInOctets OBJECT-TYPE
   SYNTAX     Counter32 
   ACCESS     read-only
   STATUS     mandatory
   DESCRIPTION
     "The total number of octets received on the interface, including 
      framing characters."
::= { vrIfTableEntryIftEntry 5 }

vrIfTableEntryIfOutOctets OBJECT-TYPE
   SYNTAX     Counter32 
   ACCESS     read-only
   STATUS     mandatory
   DESCRIPTION
     "The total number of octets transmitted out the interface, including 
      framing characters"
::= { vrIfTableEntryIftEntry 6 }

vrIfTableEntryIfInDiscards OBJECT-TYPE
   SYNTAX     Counter32 
   ACCESS     read-only
   STATUS     mandatory
   DESCRIPTION
     "The number of inbound packets which were chosen to be discarded 
      even though no errors had been detected to prevent their being 
      deliverable to a higher layer protocol. One possible reason for 
      discarding such a packet could be to free up buffer space."
::= { vrIfTableEntryIftEntry 7 }

vrIfTableEntryIfOutDiscards OBJECT-TYPE
   SYNTAX     Counter32 
   ACCESS     read-only
   STATUS     mandatory
   DESCRIPTION
     "The number of outbound packets which were chosen to be 
      discarded even though no errors had been detected to prevent their 
      being transmitted. One possible reason for discarding such a packet 
      could be to free up buffer space."
::= { vrIfTableEntryIftEntry 8 }

vrIfTableEntryIfInErrors OBJECT-TYPE
   SYNTAX     Counter32 
   ACCESS     read-only
   STATUS     mandatory
   DESCRIPTION
     "The number of inbound packet that contained errors preventing 
      them from being deliverable to a higher layer protocol."
::= { vrIfTableEntryIftEntry 9 }

vrIfTableEntryIfOutErrors OBJECT-TYPE
   SYNTAX     Counter32 
   ACCESS     read-only
   STATUS     mandatory
   DESCRIPTION
     "The number of outbound packets that could not be transmitted because 
      of errors."
::= { vrIfTableEntryIftEntry 10 }

vrIfTableEntryIfInUcastPkts OBJECT-TYPE
   SYNTAX     Counter32 
   ACCESS     read-only
   STATUS     mandatory
   DESCRIPTION
     "The number of subnetwork-unicast packets delivered to a higher-layer 
      protocol."
::= { vrIfTableEntryIftEntry 11 }

vrIfTableEntryIfOutUcastPkts OBJECT-TYPE
   SYNTAX     Counter32 
   ACCESS     read-only
   STATUS     mandatory
   DESCRIPTION
     "The total number of packets that higher level protocols requested be 
      transmitted to a subnetwork-unicast address, including those that 
      were discarded or not sent."
::= { vrIfTableEntryIftEntry 12 }

vrIfTableEntryIfInNuCastPkts OBJECT-TYPE
   SYNTAX     Counter32 
   ACCESS     read-only
   STATUS     mandatory
   DESCRIPTION
     "The number of non-unicast (i.e., subnetwork- broadcast or 
      subnetwork-multicast) packets delivered to a higher-layer protocol."
::= { vrIfTableEntryIftEntry 13 }

vrIfTableEntryIfOutNuCastPkts OBJECT-TYPE
   SYNTAX     Counter32 
   ACCESS     read-only
   STATUS     mandatory
   DESCRIPTION
     "The total number of packets that higher level protocols request be 
      transmitted to a non-unicast address, including those that were 
      discarded or not sent."
::= { vrIfTableEntryIftEntry 14 }

vrIfTableEntryIfInUnknownProtos OBJECT-TYPE
   SYNTAX     Counter32 
   ACCESS     read-only
   STATUS     mandatory
   DESCRIPTION
     "The number of packets received via the interface which were 
      discarded because of an unknown or unsupported protocol."
::= { vrIfTableEntryIftEntry 15 }

vrIfTableEntryIfOutQlength OBJECT-TYPE
   SYNTAX     Gauge32 (0..4294967295)
   ACCESS     read-only
   STATUS     mandatory
   DESCRIPTION
     "The length of the output packet queue (in packets)"
::= { vrIfTableEntryIftEntry 16 }

vrIfTableEntryIfDescription OBJECT-TYPE
   SYNTAX     AsciiString (SIZE (0..255))
   ACCESS     read-only
   STATUS     mandatory
   DESCRIPTION
     "A textual string containing information about the interface. This 
      string includes the name of the manufacturer, the product name and 
      the version of the hardware interface."
::= { vrIfTableEntryIftEntry 17 }

vrIfTableEntryIfType OBJECT-TYPE
   SYNTAX     INTEGER  {
                 other(1),
                 ddnX25(4),
                 rfc877x25(5),
                 ethernetCsmacd(6),
                 ethernet8023(7),
                 tokenBus8024(8),
                 tokenring8025(9),
                 man802(10),
                 starLan(11),
                 hyperChannel(14),
                 fddi(15),
                 lapb(16),
                 sdlc(17),
                 ds1(18),
                 e1(19),
                 basicIsdn(20),
                 primaryIsdn(21),
                 propPointToPointSerial(22),
                 ppp(23),
                 ds3(30),
                 smds(31),
                 frameRelay(32),
                 frameRelayService(44),
                 v35(45),
                 hssi(46),
                 aflane8023(59),
                 aflane8025(60),
                 v11(64),
                 atmMpeVcEncap(1039),
                 atmMpeLlcEncap(1040),
                 ilsForwarder(1041),
                 ipTunnel(1042),
                 virtualMedia(1043) }
   ACCESS     read-only
   STATUS     mandatory
   DESCRIPTION
     "The type of interface, distinguished according to the physical/link 
      protocol(s) immediately below the network layer in the protocol 
      stack"
::= { vrIfTableEntryIftEntry 18 }

vrIfTableEntryIfMtu OBJECT-TYPE
   SYNTAX     Unsigned32 (0..4294967295)
   ACCESS     read-only
   STATUS     mandatory
   DESCRIPTION
     "The size of the largest datagram which can be sent/received on the 
      interface, specified in octets. For interfaces that are used for 
      transmitting network datagrams, this is the size of the largest 
      network datagram that can be sent on the interface."
::= { vrIfTableEntryIftEntry 19 }

vrIfTableEntryIfSpeed OBJECT-TYPE
   SYNTAX     Unsigned32 (0..4294967295)
   ACCESS     read-only
   STATUS     mandatory
   DESCRIPTION
     "An estimate of the interface's current bandwidth in bits per second. 
      For interfaces which do not vary in bandwidth or for those where no 
      accurate estimation can be made, this object should contain the 
      nominal bandwidth."
::= { vrIfTableEntryIftEntry 20 }

vrIfTableEntryIfPhysicalAddress OBJECT-TYPE
   SYNTAX     AsciiString (SIZE (0..17))
   ACCESS     read-only
   STATUS     mandatory
   DESCRIPTION
     "The interface's address at the protocol layer immediately `below' the 
      network layer in the protocol stack.  For interfaces which do not 
      have such an address (e.g., a serial line), this object should be an 
      octet string of zero length."
::= { vrIfTableEntryIftEntry 21 }

vrIfTableEntryIfSpecific OBJECT-TYPE
   SYNTAX     IntegerSequence 
   ACCESS     read-only
   STATUS     mandatory
   DESCRIPTION
     "A reference to MIB definitions specific to the particular media 
      being used to realize the interface. For example, if the interface is 
      realized by an ethernet, then the value of this object refers to a 
      document defining objects specific to ethernet.  If this information is 
      not present, its value should be set to the OBJECT IDENTIFIER 
      0.0, which is a syntactically valid object identifier, and any 
      conformant implementation of ASN.1 and BER must be able to 
      generate and recognize this value."
::= { vrIfTableEntryIftEntry 22 }

vrIfTableEntryAdditionalInfoTable OBJECT-TYPE
   SYNTAX     SEQUENCE OF VrIfTableEntryAdditionalInfoEntry
   ACCESS     not-accessible
   STATUS     mandatory
   DESCRIPTION
     "*** THIS TABLE CURRENTLY NOT IMPLEMENTED ***

      This group contains additional information associated with this 
      ifEntry."
::= { vrIfTableEntry 11 }

vrIfTableEntryAdditionalInfoEntry OBJECT-TYPE
   SYNTAX     VrIfTableEntryAdditionalInfoEntry
   ACCESS     not-accessible
   STATUS     mandatory
   DESCRIPTION
     "An entry in the vrIfTableEntryAdditionalInfoTable."
   INDEX {
      vrIndex,
      vrIfTableEntryIndex }
::= { vrIfTableEntryAdditionalInfoTable 1 }

VrIfTableEntryAdditionalInfoEntry ::= SEQUENCE {
   vrIfTableEntryStdComponentName
      RowPointer }

vrIfTableEntryStdComponentName OBJECT-TYPE
   SYNTAX     RowPointer 
   ACCESS     read-only
   STATUS     mandatory
   DESCRIPTION
     "This attribute provides a component name associated with this 
      ifEntry. This component is the source of the data stored in this 
      entry. More data may be determined about this entry by looking at 
      the component associated with this component name."
::= { vrIfTableEntryAdditionalInfoEntry 1 }


-- Vr/<string> QosP/< n>
-- For egress traffic of certain media types, this component provides a 
-- mapping from a Class of Service (CoS) index (the instance value of 
-- this component) to specific Quality of Service (QoS) attributes. 
-- QosP/0 corresponding to CoS index of zero (0), is defined at all 
-- times. 
-- 
-- When the packet is to be transmitted from a VNS protocol port, the 
-- CoS of the packet and the associated QualityOfServiceProfile 
-- determine the vnsEmissionPriority and vnsDiscardPriority of the 
-- outgoing packet.

vrQosP OBJECT IDENTIFIER ::= { vr 15 }



vrQosPRowStatusTable OBJECT-TYPE
   SYNTAX     SEQUENCE OF VrQosPRowStatusEntry
   ACCESS     not-accessible
   STATUS     mandatory
   DESCRIPTION
     "This entry controls the addition and deletion of 
      vrQosP components."
::= { vrQosP 1 }

vrQosPRowStatusEntry OBJECT-TYPE
   SYNTAX     VrQosPRowStatusEntry
   ACCESS     not-accessible
   STATUS     mandatory
   DESCRIPTION
     "A single entry in the table represents a single 
      vrQosP component."
   INDEX {
      vrIndex,
      vrQosPIndex }
::= { vrQosPRowStatusTable 1 }

VrQosPRowStatusEntry ::= SEQUENCE {
   vrQosPRowStatus
      RowStatus,
   vrQosPComponentName
      DisplayString,
   vrQosPStorageType
      StorageType,
   vrQosPIndex
      Integer32 }

vrQosPRowStatus OBJECT-TYPE
   SYNTAX     RowStatus 
   ACCESS     read-write
   STATUS     mandatory
   DESCRIPTION
     "This variable is used as the basis for SNMP naming of
      vrQosP components.
      These components can be added and deleted."
::= { vrQosPRowStatusEntry 1 }

vrQosPComponentName OBJECT-TYPE
   SYNTAX     DisplayString 
   ACCESS     read-only
   STATUS     mandatory
   DESCRIPTION
     "This variable provides the component's string name for
      use with the ASCII Console Interface"
::= { vrQosPRowStatusEntry 2 }

vrQosPStorageType OBJECT-TYPE
   SYNTAX     StorageType 
   ACCESS     read-only
   STATUS     mandatory
   DESCRIPTION
     "This variable represents the storage type value for the
      vrQosP tables."
::= { vrQosPRowStatusEntry 4 }

vrQosPIndex OBJECT-TYPE
   SYNTAX     Integer32 (0..3)
   ACCESS     not-accessible
   STATUS     mandatory
   DESCRIPTION
     "This variable represents the index for the vrQosP tables."
::= { vrQosPRowStatusEntry 10 }

vrQosPProvTable OBJECT-TYPE
   SYNTAX     SEQUENCE OF VrQosPProvEntry
   ACCESS     not-accessible
   STATUS     mandatory
   DESCRIPTION
     "This group includes all attributes that can be provisioned to define an 
      InwQualityofServiceProfile instance."
::= { vrQosP 10 }

vrQosPProvEntry OBJECT-TYPE
   SYNTAX     VrQosPProvEntry
   ACCESS     not-accessible
   STATUS     mandatory
   DESCRIPTION
     "An entry in the vrQosPProvTable."
   INDEX {
      vrIndex,
      vrQosPIndex }
::= { vrQosPProvTable 1 }

VrQosPProvEntry ::= SEQUENCE {
   vrQosPVnsDiscardPriority
      Unsigned32,
   vrQosPVnsEmissionPriority
      Unsigned32,
   vrQosPWanEmissionPriority
      Unsigned32 }

vrQosPVnsDiscardPriority OBJECT-TYPE
   SYNTAX     Unsigned32 (1..3)
   ACCESS     read-write
   STATUS     mandatory
   DESCRIPTION
     "This attribute specifies the throughput importance of the packets when 
      forwarded over VNS connections. In times of congestion the discard 
      priority of a packet is used to determine whether the packet should be 
      discarded to reduce the heavy traffic load. Packets with lower discard 
      priority (numerically higher vdp) are more likely to be discarded than 
      packets with higher discard priority (numerically lower vdp). Discard 
      priority one (vdp 1) should be used for the most important traffic, 
      whereas discard priority three (vdp 3) should be used for the least 
      important traffic."
   DEFVAL     { 2 }
::= { vrQosPProvEntry 1 }

vrQosPVnsEmissionPriority OBJECT-TYPE
   SYNTAX     Unsigned32 (1..2)
   ACCESS     read-write
   STATUS     mandatory
   DESCRIPTION
     "This attribute specifies the delay importance of the packets when 
      forwarded over VNS connections. Packets with higher emission 
      priority (vep 1) are transmitted before packets with lower emission 
      priority (vep 2). Delay sensitive packets should be sent with 
      emission priority one (vep 1)."
   DEFVAL     { 2 }
::= { vrQosPProvEntry 2 }

vrQosPWanEmissionPriority OBJECT-TYPE
   SYNTAX     Unsigned32 (1..2)
   ACCESS     read-write
   STATUS     obsolete
   DESCRIPTION
     "This attribute specifies the delay importance of the packets when 
      forwarded over WAN connections. Packets with higher emission 
      priority (wep 1) are transmitted before packets with lower emission 
      priority (wep 2). Delay sensitive packets should be sent with 
      emission priority one (wep 1).	This attribute has been obsoleted and 
      is replaced by emissionPriority attribute under Vr/n Ip Pg/n 
      CosTreatment/n component."
   DEFVAL     { 2 }
::= { vrQosPProvEntry 3 }




-- 
-- Version and Compliance statements
-- 



-- Object-Group Statement:
-- A list of all current accessible leaf objects.

-- OBJECTS { vrSnmpOperStatus,
--           vrIfTableEntryComponentName,
--           vrMmSnaMaxHeapSpace,
--           vrPpLinkToMedia,
--           vrQosPVnsDiscardPriority,
--           vrIfTableEntryIfAdminStatus,
--           vrMmNetSentryHeapSpaceAllocated,
--           vrIfTableEntryIfSpecific,
--           vrIfTableEntryIfLastChange,
--           vrStorageType,
--           vrIfTableEntryRowStatus,
--           vrIfTableEntryIfOutErrors,
--           vrMmBridgingMaxHeapSpace,
--           vrIfTableEntryIfInNuCastPkts,
--           vrMmVrMaxHeapSpace,
--           vrPpSnmpOperStatus,
--           vrIfTableEntryIfOutDiscards,
--           vrPpIfIndex,
--           vrIfTableEntryIfInErrors,
--           vrMmStorageType,
--           vrMmNetSentryMaxHeapSpace,
--           vrIfTableEntryIfOutNuCastPkts,
--           vrMmSresHeapSpaceAllocated,
--           vrIfTableEntryStdComponentName,
--           vrAdminState,
--           vrManagementAccess,
--           vrPpStorageType,
--           vrRowStatus,
--           vrSnmpAdminStatus,
--           vrCustomerIdentifier,
--           vrMmVrHeapSpaceBytesAllocated,
--           vrQosPRowStatus,
--           vrIfTableEntryIfInUnknownProtos,
--           vrIfTableEntryIfOutQlength,
--           vrIfTableEntryIfOutOctets,
--           vrMmSresMaxHeapSpace,
--           vrUsageState,
--           vrPpAdminState,
--           vrMmVrHeapSpaceAllocated,
--           vrComponentName,
--           vrVirtualPrivateIntranetIdentifier,
--           vrMmIpxHeapSpaceAllocated,
--           vrIfTableEntryIfOperStatus,
--           vrQosPComponentName,
--           vrPpRowStatus,
--           vrMmIpHeapSpaceAllocated,
--           vrPpSnmpAdminStatus,
--           vrIfTableEntryIfInUcastPkts,
--           vrIfTableEntryIfType,
--           vrOperationalState,
--           vrIfTableEntryIfSpeed,
--           vrMmComponentName,
--           vrQosPStorageType,
--           vrMmRowStatus,
--           vrIfTableEntryIfDescription,
--           vrPpUsageState,
--           vrMmIpxMaxHeapSpace,
--           vrIfTableEntryStorageType,
--           vrQosPVnsEmissionPriority,
--           vrMmSnaHeapSpaceAllocated,
--           vrPpComponentName,
--           vrMmIpMaxHeapSpace,
--           vrPpAtmAddress,
--           vrIfNumber,
--           vrIfTableEntryIfOutUcastPkts,
--           vrIfTableEntryIfInOctets,
--           vrIfTableEntryIfInDiscards,
--           vrIfTableEntryIfPhysicalAddress,
--           vrPpOperationalState,
--           vrIfTableEntryIfMtu,
--           vrMmBridgingHeapSpaceAllocated }
-- STATUS  mandatory
-- DESCRIPTION
--   "A list of all current accessible leaf objects."

virtualRouterGroup OBJECT IDENTIFIER ::= { virtualRouterMIB 1 }
virtualRouterGroupBE OBJECT IDENTIFIER ::= { virtualRouterGroup 5 }
virtualRouterGroupBE01 OBJECT IDENTIFIER ::= { virtualRouterGroupBE 2 }
virtualRouterGroupBE01A OBJECT IDENTIFIER ::= { virtualRouterGroupBE01 2 }



-- Agent-Capabilities Statement:

-- PRODUCT-RELEASE "Passport Release 7.0 VirtualRouter."
-- STATUS          mandatory
-- DESCRIPTION     "VirtualRouter MIB: MIB Version BE01A,
--                  Software Version BG00S4C."
-- SUPPORTS        Nortel-Magellan-Passport-VirtualRouterMIB
--    INCLUDES     { virtualRouterGroupBE01A }

virtualRouterCapabilities OBJECT IDENTIFIER ::= { virtualRouterMIB 3 }
virtualRouterCapabilitiesBE OBJECT IDENTIFIER ::= { virtualRouterCapabilities 5 }
virtualRouterCapabilitiesBE01 OBJECT IDENTIFIER ::= { virtualRouterCapabilitiesBE 2 }
virtualRouterCapabilitiesBE01A OBJECT IDENTIFIER ::= { virtualRouterCapabilitiesBE01 2 }





END
