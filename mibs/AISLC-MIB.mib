AISLC-MIB DEFINITIONS ::=  BEGIN

-- Applied Innovation SLC MIB definitions

IMPORTS
    MODULE-IDENTITY, OBJECT-TYPE, 
    enterprises, TimeTicks
        FROM SNMPv2-SMI
    DisplayString
        FROM RFC1213-MIB
    DateAndTime, TruthValue
        FROM SNMPv2-TC;


-- group object IDs

aii             OBJECT IDENTIFIER ::= { enterprises 539 }

aiSLC   MODULE-IDENTITY
    LAST-UPDATED "9909141500Z"
    ORGANIZATION "Applied Innovation Incorporated"
    CONTACT-INFO
        "        Engineering MIB Administrator

        Postal:  Applied Innovation Inc.
                 5800 Innovation Drive
                 Dublin, OH 43016

           Tel:  614/798-2000
           Fax:  614/798-1770
        E-mail:  snmp@aiinet.com"
    DESCRIPTION
        "The MIB Module for Smart Line Cards (SLC)"
    ::= { aii 10 }

-- System group for all SLCs

aiSLCSystem     OBJECT IDENTIFIER ::= { aiSLC 1 }

-- System Group

-- Implementation of this group is mandatory for all Applied Innovation
-- Smart Line Cards(SLC's) that support SNMP management


aislcAdminStatus OBJECT-TYPE
        SYNTAX          INTEGER {
                        up(1),
                        boot(2)
                        }
        MAX-ACCESS      read-write
        STATUS          current
        DESCRIPTION
            "Configured boot status of the 
            card.  A write of boot(2)when this 
            object is in up(1) state will 
            cause the SLC to reboot.  Any 
            other write will have no effect.  
            This may not yet be the 
            operational state of the SLC.  
            The current operational state of 
            the SLC is available as 
            aislcOperStatus below."
        ::= { aiSLCSystem 1 }

aislcAdminPush OBJECT-TYPE
        SYNTAX INTEGER {
                ready(1),
                push(2)
               }
        MAX-ACCESS read-write
        STATUS current
        DESCRIPTION
            "A write of push(2) to this object informs the
            SLC that the management station is done with a
            group of related set requests.  The SLC will save
            to novolatile memory any unsaved values.  The use
            of this feature by the management station is 
            OPTIONAL.  The SLC will save to nonvolatile memory
            periodically, and upon the occurence of various
            events, even if the management station never writes
            to this object."
        ::= { aiSLCSystem 2 }

aislcOperBaseport OBJECT-TYPE
        SYNTAX INTEGER(0..255)
        MAX-ACCESS read-only
        STATUS current
        DESCRIPTION
            "The baseport of the SLC.  This 
            is the lowest-numbered 
            backplane Time Division 
            Subchannel assigned to this 
            SLC."
        ::= { aiSLCSystem 3 }

aislcLastConfigTime OBJECT-TYPE
        SYNTAX          TimeTicks
        MAX-ACCESS      read-only
        STATUS          current
        DESCRIPTION
            "The timestamp of the last
            configuration or inventory 
            change in the SLC.  This value 
            should be set to the value of 
            sysUpTime at boot time.  
            Additionaly, this value should
            be updated when a user changes
            the configuration or when any
            new hardware is detected that 
            would effect variables in the 
            supported MIBs."
        ::= { aiSLCSystem 4 }

aislcAdminResetAlarm OBJECT-TYPE
        SYNTAX     INTEGER {
                         normal(1),
                         reset(2),
                         linkdown(3)
                        }
        MAX-ACCESS          read-write
        STATUS          current
        DESCRIPTION
            "A write of reset(2) to this object informs the SLC
            that the management station wishes to reset the board
            alarm level for the SLC to the NORMAL level.  The use
            of this feature by the management station is OPTIONAL.
            The SLC will reset the alarm status of the SLC to a
            normal alarm status.  Used to reset the alarm status
            of the SLC after marking an enabled link that is down
            as dormant.  A get of this object will return the
            current board level alarm state, either normal(1) or
            linkdown(3)."
        ::= { aiSLCSystem 5 }

aislcFirmwareVersion OBJECT-TYPE
        SYNTAX          DisplayString (SIZE (3..11))
        MAX-ACCESS      read-only
        STATUS          current
        DESCRIPTION
            "The version of the firmware currently executing on the 
             SLC.  This is in the format xxx.yyy[.zzz] where xxx, 
             yyy, and zzz are 1 to 3 digit numbers and the third 
             field, zzz, is optional."
        ::= { aiSLCSystem 6 }

aislcProductName OBJECT-TYPE
        SYNTAX          DisplayString (SIZE (3..40))
        MAX-ACCESS      read-only
        STATUS          current
        DESCRIPTION
            "The name of the product, such as AI296 or AI193-FT."
        ::= { aiSLCSystem 7 }

aislcRomIdImageId OBJECT-TYPE
        SYNTAX          DisplayString (SIZE (0..20))
        MAX-ACCESS      read-only
        STATUS          current
        DESCRIPTION
            "The image identifier (ROM ID) string of the firmware 
             currently executing on the SLC."
        ::= { aiSLCSystem 8 }

aislcRomIdTimeDate OBJECT-TYPE
        SYNTAX          DateAndTime
        MAX-ACCESS      read-only
        STATUS          current
        DESCRIPTION
            "This is the image build time and date.  The DateAndTime 
             type is a structured OCTET STRING, defined in v2-tc.my 
             (SNMPv2 Textual Conventions)."
        ::= { aiSLCSystem 9 }

aislcRomIdSelFeatTable OBJECT-TYPE
        SYNTAX SEQUENCE OF AislcRomIdSelFeatTableEntry
        MAX-ACCESS      not-accessible
        STATUS          current
        DESCRIPTION
            "A table of selectable features in this firmware image.  
             If there are no selectable features, this table is 
             empty."
        ::= { aiSLCSystem 10 }

aislcRomIdSelFeatTableEntry OBJECT-TYPE
        SYNTAX          AislcRomIdSelFeatTableEntry
        MAX-ACCESS      not-accessible
        STATUS          current
        DESCRIPTION
            "Information about a particular selectable feature."
	INDEX { aislcRomIdSelFeatName }
        ::= { aislcRomIdSelFeatTable 1 }

AislcRomIdSelFeatTableEntry ::=
        SEQUENCE {
            aislcRomIdSelFeatName     DisplayString,
            aislcRomIdSelFeatEnabled  TruthValue
        }

aislcRomIdSelFeatName OBJECT-TYPE
        SYNTAX          DisplayString
        MAX-ACCESS      read-only
        STATUS          current
        DESCRIPTION
            "The name of the selectable feature for this entry."
        ::= { aislcRomIdSelFeatTableEntry 1 }

aislcRomIdSelFeatEnabled OBJECT-TYPE
        SYNTAX          TruthValue
        MAX-ACCESS      read-only
        STATUS          current
        DESCRIPTION
            "Whether or not this selectable feature is enabled.  The 
             TruthValue syntax defines values of true(1) and 
             false(2)."
        ::= { aislcRomIdSelFeatTableEntry 2 }

END
