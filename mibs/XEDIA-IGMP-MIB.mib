XEDIA-IGMP-MIB DEFINITIONS ::= BEGIN

IMPORTS
    MODULE-IDENTITY, OBJECT-TYPE, Counter32
	  FROM SNMPv2-SMI
    xediaMibs
	FROM XEDIA-REG
    InterfaceIndexOrZero,
    InterfaceIndex                   FROM IF-MIB
    ;

xigmpMIB MODULE-IDENTITY
    LAST-UPDATED "9904151600Z" -- April 15, 1999
    ORGANIZATION "Xedia Corp."
    CONTACT-INFO
          "support@xedia.com"
    DESCRIPTION
            "The Xedia extention MIB module for management of IGMP routers."
    ::= { xediaMibs 33 }

xigmpMIBObjects OBJECT IDENTIFIER ::= { xigmpMIB 1 }

xigmp           OBJECT IDENTIFIER ::= { xigmpMIBObjects 1 }

xigmpInMsgs OBJECT-TYPE
    SYNTAX	Counter32
    MAX-ACCESS  read-only
    STATUS	current
    DESCRIPTION
		"Total number of IGMP messages received"
    ::= { xigmp 1 }

xigmpInErrors OBJECT-TYPE
    SYNTAX	Counter32
    MAX-ACCESS  read-only
    STATUS	current
    DESCRIPTION
		"Total number of malformed IGMP messages received"
    ::= { xigmp 2 }

xigmpInReports OBJECT-TYPE
    SYNTAX	Counter32
    MAX-ACCESS  read-only
    STATUS	current
    DESCRIPTION
		"Total number of IGMP Report messages received"
    ::= { xigmp 3 }

xigmpInV1Reports OBJECT-TYPE
    SYNTAX	Counter32
    MAX-ACCESS  read-only
    STATUS	current
    DESCRIPTION
		"Total number of IGMP V1 Report messages received"
    ::= { xigmp 4 }

xigmpInLeaves OBJECT-TYPE
    SYNTAX	Counter32
    MAX-ACCESS  read-only
    STATUS	current
    DESCRIPTION
		"Total number of IGMP Leave messages received"
    ::= { xigmp 5 }

xigmpInQueries OBJECT-TYPE
    SYNTAX	Counter32
    MAX-ACCESS  read-only
    STATUS	current
    DESCRIPTION
		"Total number of IGMP Query messages received"
    ::= { xigmp 6 }

xigmpInUnknowns OBJECT-TYPE
    SYNTAX	Counter32
    MAX-ACCESS  read-only
    STATUS	current
    DESCRIPTION
		"Total number of IGMP messages of unknown types received"
    ::= { xigmp 7 }

xigmpOutMsgs OBJECT-TYPE
    SYNTAX	Counter32
    MAX-ACCESS  read-only
    STATUS	current
    DESCRIPTION
		"Total number of IGMP messages transmitted by IGMP protocol"
    ::= { xigmp 8 }

xigmpInterfaceTable OBJECT-TYPE
    SYNTAX     SEQUENCE OF XIgmpInterfaceEntry
    MAX-ACCESS not-accessible
    STATUS     current
    DESCRIPTION
            "The (conceptual) table listing the interfaces on which IGMP
            is enabled."
    ::= { xigmp 9 }

xigmpInterfaceEntry OBJECT-TYPE
    SYNTAX     XIgmpInterfaceEntry
    MAX-ACCESS not-accessible
    STATUS     current
    DESCRIPTION
            "An entry (conceptual row) representing an interface on
            which IGMP is enabled."
    INDEX      { xigmpInterfaceIfIndex }
    ::= { xigmpInterfaceTable 1 }

XIgmpInterfaceEntry ::= SEQUENCE {
    xigmpInterfaceIfIndex              InterfaceIndex,
    xigmpInterfaceState                INTEGER
}

xigmpInterfaceIfIndex OBJECT-TYPE
    SYNTAX     InterfaceIndex
    MAX-ACCESS not-accessible
    STATUS     current
    DESCRIPTION
            "The ifIndex value of the interface for which IGMP is
            enabled."
    ::= { xigmpInterfaceEntry 1 }

xigmpInterfaceState OBJECT-TYPE
    SYNTAX     INTEGER { up(1), down(2) }
    MAX-ACCESS read-only
    STATUS     current
    DESCRIPTION
            "The state of the IGMP interface"
    ::= { xigmpInterfaceEntry 2 }

END
