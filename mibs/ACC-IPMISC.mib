ACC-IPMISC DEFINITIONS ::= BEGIN

    IMPORTS
	 OBJECT-TYPE, IpAddress, Gauge, Counter FROM RFC1155-SMI
         accTrapLogSeqNum FROM ACC-SYSTEM
	accBRG, DisplayString, RowStatus, IfIndex, SmdsAddress
             FROM ACC-MIB;

-- Miscellaneous Ip Objects Group
   accIpMisc         OBJECT IDENTIFIER ::= { accBRG 45 }
      -- A new branch is created for IP address assignment/negotiation:
      -- Miscellaneous IP objects
      -- IP address assignment objects
      accIpAssign	OBJECT IDENTIFIER	::= { accIpMisc 1 }
   accIpAssignRangeTable        OBJECT-TYPE
                SYNTAX  SEQUENCE OF AccIpAssignRangeEntry
                ACCESS  not-accessible
                STATUS  mandatory
                DESCRIPTION
                   "Table defining the address ranges which make up
                    the pool from which addresses may be assigned"
                ::= { accIpAssign 1 }
   AccIpAssignRangeEntry ::= SEQUENCE {
                accIpAssignStartAddr    IpAddress,
                accIpAssignEndAddr  IpAddress,
	        accIpAssignAccessPartition DisplayString
                }
    accIpAssignRangeEntry      OBJECT-TYPE
                SYNTAX  AccIpAssignRangeEntry
                ACCESS  not-accessible
                STATUS  mandatory
                DESCRIPTION
                  " A single entry or range in the range table
                    which makes up the address pool."
                INDEX { accIpAssignStartAddr }
                ::= { accIpAssignRangeTable 1 }
      accIpAssignStartAddr		OBJECT-TYPE
      	SYNTAX			IpAddress
      	ACCESS			read-write
      	STATUS			mandatory
      	DESCRIPTION
      	"Start of IP address range to assign"
      ::= { accIpAssignRangeEntry 1 }
      accIpAssignEndAddr		OBJECT-TYPE
      	SYNTAX			IpAddress
      	ACCESS			read-write
      	STATUS			mandatory
      	DESCRIPTION
      	"End of IP address range to assign"
      ::= { accIpAssignRangeEntry 2 }
        accIpAssignAccessPartition OBJECT-TYPE
	    SYNTAX DisplayString --(Size(1..16))
	    ACCESS read-write
	    STATUS obsolete
	    DESCRIPTION
	       "The access partition assigned to this range of addresses.  
	        An IP address in this range can only be assigned to an 
	        interface belonging to the designated partition."
	    ::= { accIpAssignRangeEntry 3 }
      accIpAssignCurrent		OBJECT-TYPE
      	SYNTAX			Gauge
      	ACCESS			read-only
      	STATUS			mandatory
      	DESCRIPTION
      	"Count of currently assigned addresses"
      ::= { accIpAssign 3 }
      accIpAssignAvail		OBJECT-TYPE
      	SYNTAX			Gauge
      	ACCESS			read-only
      	STATUS			mandatory
      	DESCRIPTION
      	"Count of currently unassigned addresses"
      ::= { accIpAssign 4 }
      accIpAssignTotals		OBJECT-TYPE
      	SYNTAX			INTEGER
      	ACCESS			read-only
      	STATUS			mandatory
      	DESCRIPTION
      	"Count of address assignments"
      ::= { accIpAssign 5 }
      accIpAssignReleases		OBJECT-TYPE
      	SYNTAX			Counter
      	ACCESS			read-only
      	STATUS			mandatory
      	DESCRIPTION
      	"Count of address releases"
      ::= { accIpAssign 6 }
      accIpAssignFailures		OBJECT-TYPE
      	SYNTAX			Counter
      	ACCESS			read-only
      	STATUS			mandatory
      	DESCRIPTION
      	"Count of address assignments that have failed due to lack of
      	 addresses in pool"
      ::= { accIpAssign 7 }
      accIpAssignAssignments               OBJECT-TYPE
        SYNTAX                  Counter
        ACCESS                  read-only
        STATUS                  mandatory
        DESCRIPTION
        "The number address assignments that have been made from the 
         addresses in pool"
      ::= { accIpAssign 8 }
      accIpAssignLasts               OBJECT-TYPE
        SYNTAX                  IpAddress
        ACCESS                  read-only
        STATUS                  mandatory
        DESCRIPTION
        "The last address assigned from the address pool"
      ::= { accIpAssign 9 }
      -- IP Negotiated Address Table
      accIpNegAddrTable		OBJECT-TYPE
      	SYNTAX			SEQUENCE OF AccIpNegAddrEntry
      	ACCESS			not-accessible
      	STATUS			mandatory
      	DESCRIPTION
      	"Table containing currently assigned &amp; negotiated addresses."
      ::= { accIpMisc 2 }
      accIpNegAddrEntry		OBJECT-TYPE
      	SYNTAX			AccIpNegAddrEntry
      	ACCESS			not-accessible
      	STATUS			mandatory
      	DESCRIPTION
      	"Table entry for currently assigned &amp; negotiated addresses."
        INDEX { accIpNegIfIndex }
      ::= { accIpNegAddrTable 1 }
      AccIpNegAddrEntry ::= SEQUENCE {
      		accIpNegIfIndex	INTEGER,
      		accIpNegType	INTEGER,
      		accIpNegAddr	IpAddress,
	        accIpNegAccessPartition DisplayString
      		}
      accIpNegIfIndex		OBJECT-TYPE
      	SYNTAX			INTEGER
      	ACCESS			read-only
      	STATUS			mandatory
      	DESCRIPTION
      	"The ifIndex for the interface that has negotiated/assigned the
      	 network entry"
      ::= { accIpNegAddrEntry 1 }
      accIpNegType		OBJECT-TYPE
      	SYNTAX			INTEGER {
      				configured (1),
      				assigned (2),
      				user (3)
      			}
      	ACCESS			read-only
      	STATUS			mandatory
      	DESCRIPTION
      	"The type of the negotiated entry"
      ::= { accIpNegAddrEntry 2 }
      accIpNegAddr		OBJECT-TYPE
      	SYNTAX			IpAddress
      	ACCESS			read-only
      	STATUS			mandatory
      	DESCRIPTION
      	" The assigned or negotiated address"
      ::= { accIpNegAddrEntry 3 }
	accIpNegAccessPartition OBJECT-TYPE
	    SYNTAX DisplayString --(Size(1..16))
	    ACCESS read-only
	    STATUS obsolete
	    DESCRIPTION
	       "The access partition associated with the range this IP 
	        address was assigned from."
	    ::= { accIpNegAddrEntry 4 }

END
