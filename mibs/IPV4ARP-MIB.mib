IPV4ARP-MIB

   --FORCE-INCLUDE <mib.h>
   --FORCE-INCLUDE <snmpdefs.h>
   --FORCE-INCLUDE <snmpstat.h>
   --FORCE-INCLUDE "mibproto.h"
 
   DEFINITIONS ::= BEGIN

	IMPORTS
		MODULE-IDENTITY, OBJECT-TYPE, Integer32,IpAddress
			FROM SNMPv2-SMI
		RowStatus
			FROM SNMPv2-TC
		MacAddress
			FROM SNMPv2-TC
		apIpv4Arp
			FROM APENT-MIB;


    ipv4ArpMib MODULE-IDENTITY
	   LAST-UPDATED "9711242000Z" -- Mon November 24 20:00:00 EST 1997
	   ORGANIZATION "ArrowPoint Communications Inc."
	   CONTACT-INFO
	   "Postal:               ArrowPoint Communications Inc.
				                 50 Nagog Park
				                 Acton, Massachusetts 01720
	   Tel:                   +1 978-206-3000  option 1
	   E-Mail:                support@arrowpoint.com"
       DESCRIPTION
	"This MIB module describes the ArrowPoint enterprise
	 MIB support for IPv4 ARP"
      ::= { apIpv4Arp 1}


--arrowpoint
-- apmgmt
--  ipv4Ext
--   apIpv4Arp
--     apIpv4ArpAddressMax
--     apIpv4ArpResponseWait
--     apIpv4ArpFlushTime
--     apIpv4StaticArpTable
--     apIpv4ArpTable

-- global ARP configuration information.

apIpv4ArpAddressMax OBJECT-TYPE
	SYNTAX      Integer32 (1..256)
	MAX-ACCESS  read-write
	STATUS      current
	DESCRIPTION
	       "Maximum number of addresses that can be simultaneously resolved
            on one board."
	DEFVAL {64}
	::= {apIpv4Arp 2}

apIpv4ArpResponseWait OBJECT-TYPE
	SYNTAX      Integer32 (5..30)
	MAX-ACCESS  read-write
	STATUS      current
	DESCRIPTION
	       "Amount of time in seconds to wait for an ARP response"
	DEFVAL {5}
	::= {apIpv4Arp 3}

apIpv4ArpFlushTime OBJECT-TYPE
	SYNTAX      Integer32 (60..86401)
	MAX-ACCESS  read-write
	STATUS      current
	DESCRIPTION
	       "Amount of time in seconds a resolved address is held in the ARP
            cache.  Default is 4 hours.  86401 is a special value that
            means 'no timeout'."
	DEFVAL {14400}
	::= {apIpv4Arp 4}

-- configured static ARP table

apIpv4StaticArpTable OBJECT-TYPE
	SYNTAX      SEQUENCE OF ApIpv4StaticArpEntry
	MAX-ACCESS  not-accessible
	STATUS      current
	DESCRIPTION
		"A Table of static ARP entries"
	::= {apIpv4Arp 5}

apIpv4StaticArpEntry OBJECT-TYPE
	SYNTAX      ApIpv4StaticArpEntry
	MAX-ACCESS  not-accessible
	STATUS      current
	DESCRIPTION
	       " "
	INDEX  {apIpv4ArpIpAddress}
	::= {apIpv4StaticArpTable 1}

ApIpv4StaticArpEntry ::=
	SEQUENCE {
	       apIpv4StaticArpIpAddress            IpAddress,
	       apIpv4StaticArpMacAddress           MacAddress,
           apIpv4StaticArpStatus               RowStatus,
	       apIpv4StaticArpIfIndex              Integer32
		 }

apIpv4StaticArpIpAddress OBJECT-TYPE
	SYNTAX      IpAddress
	MAX-ACCESS  read-only
	STATUS      current
	DESCRIPTION
	       "IP address for static mapping."
	::= {apIpv4StaticArpEntry 1}

apIpv4StaticArpMacAddress OBJECT-TYPE
	SYNTAX      MacAddress
	MAX-ACCESS  read-create
	STATUS      current
	DESCRIPTION
	       "MAC address for static mapping."
	::= {apIpv4StaticArpEntry 2}

apIpv4StaticArpStatus OBJECT-TYPE
	SYNTAX      RowStatus
	MAX-ACCESS  read-create
	STATUS      current
	DESCRIPTION
	       "(fill in later)"
	::= {apIpv4StaticArpEntry 3}

apIpv4StaticArpIfIndex OBJECT-TYPE
	SYNTAX      Integer32 (1..'7fffffff'h)
	MAX-ACCESS  read-create
	STATUS      current
	DESCRIPTION
	       "The ifIndex on which this ARP address is configured."
	::= {apIpv4StaticArpEntry 4}

-- ARP resolution table

apIpv4ArpTable OBJECT-TYPE
	SYNTAX      SEQUENCE OF ApIpv4ArpEntry
	MAX-ACCESS  not-accessible
	STATUS      current
	DESCRIPTION
		"A Table of hosts resolved by ARP"
	::= {apIpv4Arp 6}

apIpv4ArpEntry OBJECT-TYPE
	SYNTAX      ApIpv4ArpEntry
	MAX-ACCESS  not-accessible
	STATUS      current
	DESCRIPTION
	       " "
	INDEX  {apIpv4ArpIpAddress}
	::= {apIpv4ArpTable 1}

ApIpv4ArpEntry ::=
	SEQUENCE {
	       apIpv4ArpIpAddress            IpAddress,
	       apIpv4ArpMacAddress           MacAddress,
	       apIpv4ArpResolutionType       INTEGER,
	       apIpv4ArpSlotLearned          INTEGER,
	       apIpv4ArpPortLearned          INTEGER
		 }

apIpv4ArpIpAddress OBJECT-TYPE
	SYNTAX      IpAddress
	MAX-ACCESS  read-only
	STATUS      current
	DESCRIPTION
	       "IP host address."
	::= {apIpv4ArpEntry 1}

apIpv4ArpMacAddress OBJECT-TYPE
	SYNTAX      MacAddress
	MAX-ACCESS  read-only
	STATUS      current
	DESCRIPTION
	       "MAC address for host."
	::= {apIpv4ArpEntry 2}

apIpv4ArpResolutionType OBJECT-TYPE
	SYNTAX      INTEGER {
			    dynamic (1),  -- resolved dynamically via ARP
			    static (2)    -- configured
			    } 
	MAX-ACCESS  read-only
	STATUS      current
	DESCRIPTION
	       "Method by which the address was resolved."
	::= {apIpv4ArpEntry 3}

apIpv4ArpSlotLearned OBJECT-TYPE
	SYNTAX      INTEGER 
	MAX-ACCESS  read-only
	STATUS      current
	DESCRIPTION
	       "Physical slot on which this ARP address was learned."
	::= {apIpv4ArpEntry 4}

apIpv4ArpPortLearned OBJECT-TYPE
	SYNTAX      INTEGER 
	MAX-ACCESS  read-only
	STATUS      current
	DESCRIPTION
	       "Physical port on which this ARP address was learned."
	::= {apIpv4ArpEntry 5}

END
