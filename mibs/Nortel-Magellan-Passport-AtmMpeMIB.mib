Nortel-Magellan-Passport-AtmMpeMIB
DEFINITIONS ::= BEGIN



IMPORTS

      OBJECT-TYPE
   FROM RFC-1212

      components,
      passportMIBs
   FROM Nortel-Magellan-Passport-UsefulDefinitionsMIB

      Counter32,
      DisplayString,
      StorageType,
      RowStatus,
      InterfaceIndex,
      Integer32,
      Unsigned32
   FROM Nortel-Magellan-Passport-StandardTextualConventionsMIB

      Link
   FROM Nortel-Magellan-Passport-TextualConventionsMIB;




-- LAST-UPDATED   "9702280000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     AtmMpe Enterprise MIB."

atmMpeMIB OBJECT IDENTIFIER ::= { passportMIBs 65 }










-- AtmMpe/n
-- This component represents a logical interface between the Virtual 
-- Router and an ATM media (AtmIf). Multiprotocol Encapsulation as 
-- specified in RFC1483 is used to transfer higher-layer protocol data 
-- across virtual channels in an ATM network. AtmMpes provide a 
-- means to associate multiple ATM virtual channel connections with a 
-- single VirtualRouter ProtocolPort. The AtmMpe component is 
-- associated with a ProtocolPort via a linkage attribute and virtual 
-- channel connections via a linkage attribute in each AtmConnection 
-- subcomponent.

atmMpe OBJECT IDENTIFIER ::= { components 118 }



atmMpeRowStatusTable OBJECT-TYPE
   SYNTAX     SEQUENCE OF AtmMpeRowStatusEntry
   ACCESS     not-accessible
   STATUS     mandatory
   DESCRIPTION
     "This entry controls the addition and deletion of 
      atmMpe components."
::= { atmMpe 1 }

atmMpeRowStatusEntry OBJECT-TYPE
   SYNTAX     AtmMpeRowStatusEntry
   ACCESS     not-accessible
   STATUS     mandatory
   DESCRIPTION
     "A single entry in the table represents a single 
      atmMpe component."
   INDEX {
      atmMpeIndex }
::= { atmMpeRowStatusTable 1 }

AtmMpeRowStatusEntry ::= SEQUENCE {
   atmMpeRowStatus
      RowStatus,
   atmMpeComponentName
      DisplayString,
   atmMpeStorageType
      StorageType,
   atmMpeIndex
      Integer32 }

atmMpeRowStatus OBJECT-TYPE
   SYNTAX     RowStatus 
   ACCESS     read-write
   STATUS     mandatory
   DESCRIPTION
     "This variable is used as the basis for SNMP naming of
      atmMpe components.
      These components can be added and deleted."
::= { atmMpeRowStatusEntry 1 }

atmMpeComponentName OBJECT-TYPE
   SYNTAX     DisplayString 
   ACCESS     read-only
   STATUS     mandatory
   DESCRIPTION
     "This variable provides the component's string name for
      use with the ASCII Console Interface"
::= { atmMpeRowStatusEntry 2 }

atmMpeStorageType OBJECT-TYPE
   SYNTAX     StorageType 
   ACCESS     read-only
   STATUS     mandatory
   DESCRIPTION
     "This variable represents the storage type value for the
      atmMpe tables."
::= { atmMpeRowStatusEntry 4 }

atmMpeIndex OBJECT-TYPE
   SYNTAX     Integer32 (0..255)
   ACCESS     not-accessible
   STATUS     mandatory
   DESCRIPTION
     "This variable represents the index for the atmMpe tables."
::= { atmMpeRowStatusEntry 10 }

atmMpeCidDataTable OBJECT-TYPE
   SYNTAX     SEQUENCE OF AtmMpeCidDataEntry
   ACCESS     not-accessible
   STATUS     mandatory
   DESCRIPTION
     "This group contains the attribute for a component's Customer 
      Identifier (CID). Refer to the attribute description for a detailed 
      explanation of CIDs."
::= { atmMpe 10 }

atmMpeCidDataEntry OBJECT-TYPE
   SYNTAX     AtmMpeCidDataEntry
   ACCESS     not-accessible
   STATUS     mandatory
   DESCRIPTION
     "An entry in the atmMpeCidDataTable."
   INDEX {
      atmMpeIndex }
::= { atmMpeCidDataTable 1 }

AtmMpeCidDataEntry ::= SEQUENCE {
   atmMpeCustomerIdentifier
      Unsigned32 }

atmMpeCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { atmMpeCidDataEntry 1 }

atmMpeIfEntryTable OBJECT-TYPE
   SYNTAX     SEQUENCE OF AtmMpeIfEntryEntry
   ACCESS     not-accessible
   STATUS     mandatory
   DESCRIPTION
     "This group contains the provisionable attributes for the ifEntry."
::= { atmMpe 11 }

atmMpeIfEntryEntry OBJECT-TYPE
   SYNTAX     AtmMpeIfEntryEntry
   ACCESS     not-accessible
   STATUS     mandatory
   DESCRIPTION
     "An entry in the atmMpeIfEntryTable."
   INDEX {
      atmMpeIndex }
::= { atmMpeIfEntryTable 1 }

AtmMpeIfEntryEntry ::= SEQUENCE {
   atmMpeIfAdminStatus
      INTEGER,
   atmMpeIfIndex
      InterfaceIndex }

atmMpeIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { atmMpeIfEntryEntry 1 }

atmMpeIfIndex OBJECT-TYPE
   SYNTAX     InterfaceIndex (1..65535)
   ACCESS     read-only
   STATUS     mandatory
   DESCRIPTION
     "This is the index for the IfEntry. Its value is automatically initialized 
      during the provisioning process."
::= { atmMpeIfEntryEntry 2 }

atmMpeProvTable OBJECT-TYPE
   SYNTAX     SEQUENCE OF AtmMpeProvEntry
   ACCESS     not-accessible
   STATUS     mandatory
   DESCRIPTION
     "This group contains the provisioned attributes for the AtmMpe 
      component."
::= { atmMpe 12 }

atmMpeProvEntry OBJECT-TYPE
   SYNTAX     AtmMpeProvEntry
   ACCESS     not-accessible
   STATUS     mandatory
   DESCRIPTION
     "An entry in the atmMpeProvTable."
   INDEX {
      atmMpeIndex }
::= { atmMpeProvTable 1 }

AtmMpeProvEntry ::= SEQUENCE {
   atmMpeMaxTransmissionUnit
      Unsigned32,
   atmMpeEncapType
      INTEGER,
   atmMpeIlsForwarder
      Link }

atmMpeMaxTransmissionUnit OBJECT-TYPE
   SYNTAX     Unsigned32 (256..9188)
   ACCESS     read-write
   STATUS     mandatory
   DESCRIPTION
     "This attribute sets the size of the largest datagram which can be sent 
      on the interface. This includes the size of the Logical Link Control 
      header (if applicable) as well as the protocol data unit."
   DEFVAL     { 9188 }
::= { atmMpeProvEntry 1 }

atmMpeEncapType OBJECT-TYPE
   SYNTAX     INTEGER  {
                 llcEncap(1),
                 ipVcEncap(2),
                 ipxVcEncap(3) }
   ACCESS     read-write
   STATUS     mandatory
   DESCRIPTION
     "This attribute specifies the rfc1483 encapsulation type to be used for 
      the AtmConnections under this AtmMpe. Specifying llcEncap 
      allows multiplexing of multiple protocols over the VCCs. The 
      protocol of the carried PDU will be identified by an IEEE 802.2 
      Logical Link Control header. If Bridging or Inverse ARP is to be 
      carried over a VCC, llcEncap must be used. Specifying ipVcEncap 
      or ipxVcEncap indicates that all the VCCs (i.e. AtmConnections) 
      under an AtmMpe component will use VC based multiplexing and 
      will carry IP or IPX PDUs only. Thus an IpxPort cannot be 
      provisioned under a protocol port linked to an AtmMpe component 
      with encapsulation type of ipVcEncap. Similarly, an IpPort cannot 
      be provisioned under a protocol port linked to an AtmMpe 
      component with encapsulation type of ipxVcEncap."
   DEFVAL     { llcEncap }
::= { atmMpeProvEntry 2 }

atmMpeIlsForwarder OBJECT-TYPE
   SYNTAX     Link 
   ACCESS     read-write
   STATUS     mandatory
   DESCRIPTION
     "This attribute specifies the IlsForwarder component this AtmMpe 
      component is using."
::= { atmMpeProvEntry 3 }

atmMpeMediaProvTable OBJECT-TYPE
   SYNTAX     SEQUENCE OF AtmMpeMediaProvEntry
   ACCESS     not-accessible
   STATUS     mandatory
   DESCRIPTION
     "This group contains the base provisioning data for the Atm Mpe 
      component."
::= { atmMpe 13 }

atmMpeMediaProvEntry OBJECT-TYPE
   SYNTAX     AtmMpeMediaProvEntry
   ACCESS     not-accessible
   STATUS     mandatory
   DESCRIPTION
     "An entry in the atmMpeMediaProvTable."
   INDEX {
      atmMpeIndex }
::= { atmMpeMediaProvTable 1 }

AtmMpeMediaProvEntry ::= SEQUENCE {
   atmMpeLinkToProtocolPort
      Link }

atmMpeLinkToProtocolPort OBJECT-TYPE
   SYNTAX     Link 
   ACCESS     read-write
   STATUS     mandatory
   DESCRIPTION
     "This attribute contains a protocol port component name. The 
      attribute associates an AtmMpe application with a protocol port."
::= { atmMpeMediaProvEntry 1 }

atmMpeStateTable OBJECT-TYPE
   SYNTAX     SEQUENCE OF AtmMpeStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { atmMpe 14 }

atmMpeStateEntry OBJECT-TYPE
   SYNTAX     AtmMpeStateEntry
   ACCESS     not-accessible
   STATUS     mandatory
   DESCRIPTION
     "An entry in the atmMpeStateTable."
   INDEX {
      atmMpeIndex }
::= { atmMpeStateTable 1 }

AtmMpeStateEntry ::= SEQUENCE {
   atmMpeAdminState
      INTEGER,
   atmMpeOperationalState
      INTEGER,
   atmMpeUsageState
      INTEGER }

atmMpeAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { atmMpeStateEntry 1 }

atmMpeOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { atmMpeStateEntry 2 }

atmMpeUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { atmMpeStateEntry 3 }

atmMpeOperStatusTable OBJECT-TYPE
   SYNTAX     SEQUENCE OF AtmMpeOperStatusEntry
   ACCESS     not-accessible
   STATUS     mandatory
   DESCRIPTION
     "This group includes the Operational Status attribute. This attribute 
      defines the current operational state of this component."
::= { atmMpe 15 }

atmMpeOperStatusEntry OBJECT-TYPE
   SYNTAX     AtmMpeOperStatusEntry
   ACCESS     not-accessible
   STATUS     mandatory
   DESCRIPTION
     "An entry in the atmMpeOperStatusTable."
   INDEX {
      atmMpeIndex }
::= { atmMpeOperStatusTable 1 }

AtmMpeOperStatusEntry ::= SEQUENCE {
   atmMpeSnmpOperStatus
      INTEGER }

atmMpeSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { atmMpeOperStatusEntry 1 }


-- AtmMpe/n Ac/n
-- This component represents a virtual channel through which 
-- internetworking frames will be transported using rfc1483 
-- encapsulation. The AtmConnection component contains OSI state 
-- information, frame based statistics, and the linkage to an ATM 
-- virtual channel connection. This component's instance value is used 
-- by higher-layer protocols when referring to a specific ATM 
-- connection.

atmMpeAc OBJECT IDENTIFIER ::= { atmMpe 2 }



atmMpeAcRowStatusTable OBJECT-TYPE
   SYNTAX     SEQUENCE OF AtmMpeAcRowStatusEntry
   ACCESS     not-accessible
   STATUS     mandatory
   DESCRIPTION
     "This entry controls the addition and deletion of 
      atmMpeAc components."
::= { atmMpeAc 1 }

atmMpeAcRowStatusEntry OBJECT-TYPE
   SYNTAX     AtmMpeAcRowStatusEntry
   ACCESS     not-accessible
   STATUS     mandatory
   DESCRIPTION
     "A single entry in the table represents a single 
      atmMpeAc component."
   INDEX {
      atmMpeIndex,
      atmMpeAcIndex }
::= { atmMpeAcRowStatusTable 1 }

AtmMpeAcRowStatusEntry ::= SEQUENCE {
   atmMpeAcRowStatus
      RowStatus,
   atmMpeAcComponentName
      DisplayString,
   atmMpeAcStorageType
      StorageType,
   atmMpeAcIndex
      Integer32 }

atmMpeAcRowStatus OBJECT-TYPE
   SYNTAX     RowStatus 
   ACCESS     read-write
   STATUS     mandatory
   DESCRIPTION
     "This variable is used as the basis for SNMP naming of
      atmMpeAc components.
      These components can be added and deleted."
::= { atmMpeAcRowStatusEntry 1 }

atmMpeAcComponentName OBJECT-TYPE
   SYNTAX     DisplayString 
   ACCESS     read-only
   STATUS     mandatory
   DESCRIPTION
     "This variable provides the component's string name for
      use with the ASCII Console Interface"
::= { atmMpeAcRowStatusEntry 2 }

atmMpeAcStorageType OBJECT-TYPE
   SYNTAX     StorageType 
   ACCESS     read-only
   STATUS     mandatory
   DESCRIPTION
     "This variable represents the storage type value for the
      atmMpeAc tables."
::= { atmMpeAcRowStatusEntry 4 }

atmMpeAcIndex OBJECT-TYPE
   SYNTAX     Integer32 (1..255)
   ACCESS     not-accessible
   STATUS     mandatory
   DESCRIPTION
     "This variable represents the index for the atmMpeAc tables."
::= { atmMpeAcRowStatusEntry 10 }

atmMpeAcProvTable OBJECT-TYPE
   SYNTAX     SEQUENCE OF AtmMpeAcProvEntry
   ACCESS     not-accessible
   STATUS     mandatory
   DESCRIPTION
     "This group contains the provisioned attributes for the 
      AtmConnection component."
::= { atmMpeAc 10 }

atmMpeAcProvEntry OBJECT-TYPE
   SYNTAX     AtmMpeAcProvEntry
   ACCESS     not-accessible
   STATUS     mandatory
   DESCRIPTION
     "An entry in the atmMpeAcProvTable."
   INDEX {
      atmMpeIndex,
      atmMpeAcIndex }
::= { atmMpeAcProvTable 1 }

AtmMpeAcProvEntry ::= SEQUENCE {
   atmMpeAcAtmConnection
      Link,
   atmMpeAcIpCoS
      Unsigned32 }

atmMpeAcAtmConnection OBJECT-TYPE
   SYNTAX     Link 
   ACCESS     read-write
   STATUS     mandatory
   DESCRIPTION
     "This attribute specifies the Atm nailed up endpoint, AtmIf/n Vcc/
      vpi.vci Nep, that this connection is associated with."
::= { atmMpeAcProvEntry 1 }

atmMpeAcIpCoS OBJECT-TYPE
   SYNTAX     Unsigned32 (0..3)
   ACCESS     read-write
   STATUS     mandatory
   DESCRIPTION
     "This attribute specifies the Class of Service (CoS) given to each 
      packet received on an ATM connection.
      
      The initial CoS given to a packet may be overridden when the 
      cosPolicyAssignment attribute is defined on either the IpPort 
      component of the ProtocolPort linked to the ATM MPE or the Ip 
      component of the protocol port's VirtualRouter.
      
      When a packet is to be transmitted on an ATM MPE protocol port 
      where multiple connections are available for the packet's next hop, 
      the packet is forwarded on the connection where the ipCos value 
      matches the CoS of the packet. When the packets' CoS does not 
      match the ipCos value of any of the available connections, the 
      packet is forwarded using next lowest CoS; failing this, the packet 
      is forwarded using the next highest CoS."
   DEFVAL     { 0 }
::= { atmMpeAcProvEntry 2 }

atmMpeAcStateTable OBJECT-TYPE
   SYNTAX     SEQUENCE OF AtmMpeAcStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { atmMpeAc 11 }

atmMpeAcStateEntry OBJECT-TYPE
   SYNTAX     AtmMpeAcStateEntry
   ACCESS     not-accessible
   STATUS     mandatory
   DESCRIPTION
     "An entry in the atmMpeAcStateTable."
   INDEX {
      atmMpeIndex,
      atmMpeAcIndex }
::= { atmMpeAcStateTable 1 }

AtmMpeAcStateEntry ::= SEQUENCE {
   atmMpeAcAdminState
      INTEGER,
   atmMpeAcOperationalState
      INTEGER,
   atmMpeAcUsageState
      INTEGER }

atmMpeAcAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { atmMpeAcStateEntry 1 }

atmMpeAcOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { atmMpeAcStateEntry 2 }

atmMpeAcUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { atmMpeAcStateEntry 3 }

atmMpeAcOperTable OBJECT-TYPE
   SYNTAX     SEQUENCE OF AtmMpeAcOperEntry
   ACCESS     not-accessible
   STATUS     mandatory
   DESCRIPTION
     "This group contains the operational attributes for the 
      AtmConnection component."
::= { atmMpeAc 12 }

atmMpeAcOperEntry OBJECT-TYPE
   SYNTAX     AtmMpeAcOperEntry
   ACCESS     not-accessible
   STATUS     mandatory
   DESCRIPTION
     "An entry in the atmMpeAcOperTable."
   INDEX {
      atmMpeIndex,
      atmMpeAcIndex }
::= { atmMpeAcOperTable 1 }

AtmMpeAcOperEntry ::= SEQUENCE {
   atmMpeAcSpeed
      Counter32 }

atmMpeAcSpeed OBJECT-TYPE
   SYNTAX     Counter32 
   ACCESS     read-only
   STATUS     mandatory
   DESCRIPTION
     "This attribute indicates the approximate bit rate for the connection. 
      The bit rate is determined from the cell rate provisioned for the Vcc 
      linked to this connection. The cell rate is multiplied by 53 bytes per 
      cell and 8 bits per byte to obtain the bit rate. The ifSpeed of the 
      entry in the ifTable corresponding to the AtmMpe component is the 
      lowest speed of all the connections associated with the AtmMpe 
      component."
::= { atmMpeAcOperEntry 1 }

atmMpeAcStatsTable OBJECT-TYPE
   SYNTAX     SEQUENCE OF AtmMpeAcStatsEntry
   ACCESS     not-accessible
   STATUS     mandatory
   DESCRIPTION
     "This group contains the frame based statistics maintained for the 
      AtmConnection component. For cell based statistics, see the Vcc 
      component."
::= { atmMpeAc 13 }

atmMpeAcStatsEntry OBJECT-TYPE
   SYNTAX     AtmMpeAcStatsEntry
   ACCESS     not-accessible
   STATUS     mandatory
   DESCRIPTION
     "An entry in the atmMpeAcStatsTable."
   INDEX {
      atmMpeIndex,
      atmMpeAcIndex }
::= { atmMpeAcStatsTable 1 }

AtmMpeAcStatsEntry ::= SEQUENCE {
   atmMpeAcOutPackets
      Counter32,
   atmMpeAcOutOctets
      Counter32,
   atmMpeAcOutDiscards
      Counter32,
   atmMpeAcInPackets
      Counter32,
   atmMpeAcInOctets
      Counter32,
   atmMpeAcInUnknownProtos
      Counter32,
   atmMpeAcInErrors
      Counter32 }

atmMpeAcOutPackets OBJECT-TYPE
   SYNTAX     Counter32 
   ACCESS     read-only
   STATUS     mandatory
   DESCRIPTION
     "This attribute counts the total number of packets sent on this 
      connection. This counter will wrap around to 0 when it exceeds its 
      maximum count."
::= { atmMpeAcStatsEntry 1 }

atmMpeAcOutOctets OBJECT-TYPE
   SYNTAX     Counter32 
   ACCESS     read-only
   STATUS     mandatory
   DESCRIPTION
     "This attribute counts the total number of octets sent on this 
      connection. This counter will wrap around to 0 when it exceeds its 
      maximum count.
      DESCRIPTION"
::= { atmMpeAcStatsEntry 2 }

atmMpeAcOutDiscards OBJECT-TYPE
   SYNTAX     Counter32 
   ACCESS     read-only
   STATUS     mandatory
   DESCRIPTION
     "This attribute counts the total number of packets which were 
      supposed to be sent on this connection but were discarded due to 
      congestion or the connection being down. This counter will wrap 
      around to 0 when it exceeds its maximum count.
      DESCRIPTION"
::= { atmMpeAcStatsEntry 3 }

atmMpeAcInPackets OBJECT-TYPE
   SYNTAX     Counter32 
   ACCESS     read-only
   STATUS     mandatory
   DESCRIPTION
     "This attribute counts the total number of packets received on this 
      connection. This counter will wrap around to 0 when it exceeds its 
      maximum count.
      DESCRIPTION"
::= { atmMpeAcStatsEntry 4 }

atmMpeAcInOctets OBJECT-TYPE
   SYNTAX     Counter32 
   ACCESS     read-only
   STATUS     mandatory
   DESCRIPTION
     "The attribute counts the total number of octets received on this 
      connection. This counter will wrap around to 0 when it exceeds its 
      maximum count.
      DESCRIPTION"
::= { atmMpeAcStatsEntry 5 }

atmMpeAcInUnknownProtos OBJECT-TYPE
   SYNTAX     Counter32 
   ACCESS     read-only
   STATUS     mandatory
   DESCRIPTION
     "This attribute counts the total number of packets received on this 
      connection which were discarded because they contained an 
      unknown or unsupported protocol (includes packets received for 
      protocols not currently bound to the associated ProtocolPort 
      component). This counter will wrap around to 0 when it exceeds its 
      maximum count.
      DESCRIPTION"
::= { atmMpeAcStatsEntry 6 }

atmMpeAcInErrors OBJECT-TYPE
   SYNTAX     Counter32 
   ACCESS     read-only
   STATUS     mandatory
   DESCRIPTION
     "This attribute counts the total number of packets received on the 
      connection which contained errors preventing them from being 
      delivered to a higher-layer protocol (includes short frames). This 
      counter will wrap around to 0 when it exceeds its maximum count.
      DESCRIPTION"
::= { atmMpeAcStatsEntry 7 }




-- 
-- Version and Compliance statements
-- 



-- Object-Group Statement:
-- A list of all current accessible leaf objects.

-- OBJECTS { atmMpeAcOutPackets,
--           atmMpeMaxTransmissionUnit,
--           atmMpeAcSpeed,
--           atmMpeOperationalState,
--           atmMpeAcOutDiscards,
--           atmMpeAcAdminState,
--           atmMpeIfAdminStatus,
--           atmMpeAcInErrors,
--           atmMpeAcIpCoS,
--           atmMpeAcAtmConnection,
--           atmMpeAcRowStatus,
--           atmMpeAdminState,
--           atmMpeLinkToProtocolPort,
--           atmMpeAcInOctets,
--           atmMpeRowStatus,
--           atmMpeComponentName,
--           atmMpeAcInPackets,
--           atmMpeCustomerIdentifier,
--           atmMpeAcUsageState,
--           atmMpeEncapType,
--           atmMpeAcOutOctets,
--           atmMpeSnmpOperStatus,
--           atmMpeIfIndex,
--           atmMpeUsageState,
--           atmMpeAcStorageType,
--           atmMpeIlsForwarder,
--           atmMpeAcOperationalState,
--           atmMpeAcComponentName,
--           atmMpeAcInUnknownProtos,
--           atmMpeStorageType }
-- STATUS  mandatory
-- DESCRIPTION
--   "A list of all current accessible leaf objects."

atmMpeGroup OBJECT IDENTIFIER ::= { atmMpeMIB 1 }
atmMpeGroupBD OBJECT IDENTIFIER ::= { atmMpeGroup 4 }
atmMpeGroupBD00 OBJECT IDENTIFIER ::= { atmMpeGroupBD 1 }
atmMpeGroupBD00A OBJECT IDENTIFIER ::= { atmMpeGroupBD00 2 }



-- Agent-Capabilities Statement:

-- PRODUCT-RELEASE "Passport Release 7.0 AtmMpe."
-- STATUS          mandatory
-- DESCRIPTION     "AtmMpe MIB: MIB Version BD00A,
--                  Software Version BG00S4C."
-- SUPPORTS        Nortel-Magellan-Passport-AtmMpeMIB
--    INCLUDES     { atmMpeGroupBD00A }

atmMpeCapabilities OBJECT IDENTIFIER ::= { atmMpeMIB 3 }
atmMpeCapabilitiesBD OBJECT IDENTIFIER ::= { atmMpeCapabilities 4 }
atmMpeCapabilitiesBD00 OBJECT IDENTIFIER ::= { atmMpeCapabilitiesBD 1 }
atmMpeCapabilitiesBD00A OBJECT IDENTIFIER ::= { atmMpeCapabilitiesBD00 2 }





END
