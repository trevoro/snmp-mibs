AISLCSYSCFG-MIB DEFINITIONS ::= BEGIN

IMPORTS
	MODULE-IDENTITY, OBJECT-TYPE, enterprises
			FROM SNMPv2-SMI
	TruthValue, DisplayString
			FROM SNMPv2-TC
	IpAddress
			FROM RFC1155-SMI;

	PositiveInteger    ::= INTEGER (1..2147483647)

	aii OBJECT IDENTIFIER ::= {enterprises 539}

aiSLCSysCfg MODULE-IDENTITY
	LAST-UPDATED "0006200500Z"
	ORGANIZATION "Applied Innovation Inc."
	CONTACT-INFO "Engineering MIB Administrator
					Postal: Applied Innovation Inc.
									5800 Innovation Drive
															Dublin, Ohio 43017-3271

											Tel:    614-798-2000
											Fax:    614-798-1770
											Email:  snmp@aiinet.com"
	DESCRIPTION "MIB module for SLC system parameters."
	::= {aii 21}

--=========================================================================

aislcscSystemPrompt OBJECT-TYPE
	SYNTAX		DisplayString (SIZE (0..80))
	MAX-ACCESS	read-write
	STATUS		current
	DESCRIPTION
		"Prompt for login shells.
		Maximum length is 80 characters."
	::= {aiSLCSysCfg 1}

--=========================================================================

aislcscShellMinLogLevel OBJECT-TYPE
	SYNTAX		INTEGER (0..9)
	MAX-ACCESS	read-write
	STATUS		current
	DESCRIPTION
		"Minimum message severity which will be logged
		to a shell connection."
	::= {aiSLCSysCfg 2}

--=========================================================================

aislcscFtpPort OBJECT-TYPE
	SYNTAX		INTEGER (1..65535)
	MAX-ACCESS	read-write
	STATUS		current
	DESCRIPTION	"TCP port for accepting FTP connections."
	::= {aiSLCSysCfg 3}

aislcscTelnetPort OBJECT-TYPE
	SYNTAX		INTEGER (1..65535)
	MAX-ACCESS	read-write
	STATUS		current
	DESCRIPTION	"TCP port for accepting Telnet connections."
	::= {aiSLCSysCfg 4}

--=========================================================================

aiSLCSysCfgManagerTable OBJECT-TYPE
	SYNTAX		SEQUENCE OF AISLCSysCfgManagerEntry
				MAX-ACCESS	not-accessible
	STATUS		current
	DESCRIPTION
		"Table of IP addresses to which SNMP traps will be sent,
		indexed by an integer."
	::= {aiSLCSysCfg 5}

aiSLCSysCfgManagerEntry OBJECT-TYPE
	SYNTAX		AISLCSysCfgManagerEntry
	MAX-ACCESS	not-accessible
	STATUS		current
	DESCRIPTION	"Entry of aiSLCSysCfgManagerTable."
	INDEX		{aislcscManagerIndex}
	::= {aiSLCSysCfgManagerTable 1}

AISLCSysCfgManagerEntry ::= SEQUENCE {
	aislcscManagerIndex	PositiveInteger,
	aislcscManagerAddress	IpAddress,
	aislcscManagerTrapPort  INTEGER
}

aislcscManagerIndex OBJECT-TYPE
	SYNTAX		PositiveInteger
	MAX-ACCESS	read-only
	STATUS		current
	DESCRIPTION	"Index into this table of SNMP managers."
	::= {aiSLCSysCfgManagerEntry 1}

aislcscManagerAddress OBJECT-TYPE
	SYNTAX		IpAddress
	MAX-ACCESS	read-write
	STATUS		current
	DESCRIPTION
		"SNMP manager IP address.  0.0.0.0 indicates an unused entry."
	::= {aiSLCSysCfgManagerEntry 2}

aislcscManagerTrapPort OBJECT-TYPE
	SYNTAX		INTEGER (1..65535)
	MAX-ACCESS	read-write
	STATUS		current
	DESCRIPTION	"SNMP manager trap port destination number."
	::= {aiSLCSysCfgManagerEntry 3}

--=========================================================================

aislcscReadCommunity OBJECT-TYPE
	SYNTAX		DisplayString (SIZE (0..32))
	MAX-ACCESS	read-write
	STATUS		current
	DESCRIPTION	"SNMP community string for read-only access."
	::= {aiSLCSysCfg 6}

aislcscWriteCommunity OBJECT-TYPE
	SYNTAX		DisplayString (SIZE (0..32))
	MAX-ACCESS	read-write
	STATUS		current
	DESCRIPTION	"SNMP community string for read-write access."
	::= {aiSLCSysCfg 7}

--=========================================================================

aislcsctl1SourceID OBJECT-TYPE
	SYNTAX		DisplayString (SIZE (0..20))
	MAX-ACCESS	read-write
	STATUS		current
	DESCRIPTION
		"TL1 source identifier.
		 Maximum length is 20 characters."
	::= {aiSLCSysCfg 8}

aislcsctl1LogonRequired OBJECT-TYPE
	SYNTAX		TruthValue
	MAX-ACCESS	read-write
	STATUS		current
	DESCRIPTION
		"Indicates whether or not an ACT-USER command
		is required for TL1 access."
	::= {aiSLCSysCfg 9}

aislcsctl1NumBadLogons OBJECT-TYPE
	SYNTAX		PositiveInteger
	MAX-ACCESS	read-only
	STATUS		current
	DESCRIPTION
		"The number of failed TL1 logons that have occurred
		since the last successful logon."
	::= {aiSLCSysCfg 10}

--=========================================================================

aislcscExtProbeStatus OBJECT-TYPE
	SYNTAX		INTEGER { available(1), unavailable(2) }
	MAX-ACCESS	read-only
	STATUS		current
	DESCRIPTION
		"This is the state of the external temperature probe.
		It is either available or unavailable."
	::= {aiSLCSysCfg 11}

aislcscExtLowThreshCelsius OBJECT-TYPE
	SYNTAX		INTEGER (-54..124)
	UNITS		"degrees Celsius"
	MAX-ACCESS	read-write
	STATUS		current
	DESCRIPTION
		"The lower threshold for the external temperature probe,
		in degrees Celsius.  When the temperature drops below this
		value, an SNMP trap is sent."
	::= {aiSLCSysCfg 12}

aislcscExtHighThreshCelsius OBJECT-TYPE
	SYNTAX		INTEGER (-54..124)
	UNITS		"degrees Celsius"
	MAX-ACCESS	read-write
	STATUS		current
	DESCRIPTION
		"The upper threshold for the external temperature probe,
		in degrees Celsius.  When the temperature rises above this
		value, an SNMP trap is sent."
	::= {aiSLCSysCfg 13}

aislcscExtTempCelsius OBJECT-TYPE
	SYNTAX		INTEGER (-55..125)
	UNITS		"degrees Celsius"
	MAX-ACCESS	read-only
	STATUS		current
	DESCRIPTION	"The current external temperature (Celsius)."
	::= {aiSLCSysCfg 14}

aislcscIntProbeStatus OBJECT-TYPE
	SYNTAX		INTEGER { available(1), unavailable(2) }
	MAX-ACCESS	read-only
	STATUS		current
	DESCRIPTION
		"This is the state of the internal temperature probe.
		It is either available or unavailable."
	::= {aiSLCSysCfg 15}

aislcscIntLowThreshCelsius OBJECT-TYPE
	SYNTAX		INTEGER (-54..124)
	UNITS		"degrees Celsius"
	MAX-ACCESS	read-write
	STATUS		current
	DESCRIPTION
		"The lower threshold for the internal temperature probe,
		in degrees Celsius.  When the temperature drops below this
		value, an SNMP trap is sent."
	::= {aiSLCSysCfg 16}

aislcscIntHighThreshCelsius OBJECT-TYPE
	SYNTAX		INTEGER (-54..124)
	UNITS		"degrees Celsius"
	MAX-ACCESS	read-write
	STATUS		current
	DESCRIPTION
		"The upper threshold for the internal temperature probe,
		in degrees Celsius.  When the temperature rises above this
		value, an SNMP trap is sent."
	::= {aiSLCSysCfg 17}

aislcscIntTempCelsius OBJECT-TYPE
	SYNTAX		INTEGER (-55..125)
	UNITS		"degrees Celsius"
	MAX-ACCESS	read-only
	STATUS		current
	DESCRIPTION	"The current internal temperature (Celsius)."
	::= {aiSLCSysCfg 18}

aislcscExceededThresholdValue OBJECT-TYPE
	SYNTAX		INTEGER (-55..125)
	UNITS		"degrees Celsius"
	MAX-ACCESS	read-only
	STATUS		current
	DESCRIPTION	"The temperature sent with the last trap (Celsius)."
	::= {aiSLCSysCfg 19}

--=========================================================================

aiSLCSysCfgKeepAliveTable OBJECT-TYPE
	SYNTAX		SEQUENCE OF AISLCSysCfgKeepAliveEntry
				MAX-ACCESS	not-accessible
	STATUS		current
	DESCRIPTION
		"Table of IP addresses which will be pinged periodically."
	::= {aiSLCSysCfg 20}

aiSLCSysCfgKeepAliveEntry OBJECT-TYPE
	SYNTAX		AISLCSysCfgKeepAliveEntry
	MAX-ACCESS	not-accessible
	STATUS		current
	DESCRIPTION	"Entry of aiSLCSysCfgKeepAliveTable."
	INDEX		{aislcscKeepAliveIndex}
	::= {aiSLCSysCfgKeepAliveTable 1}

AISLCSysCfgKeepAliveEntry ::= SEQUENCE {
	aislcscKeepAliveIndex		PositiveInteger,
	aislcscKeepAliveAddress		IpAddress,
	aislcscKeepAliveInterval	INTEGER,
	aislcscKeepAliveWarningText	DisplayString,
	aislcscKeepAliveOKText		DisplayString,
	aislcscKeepAliveCommStat	INTEGER
}

aislcscKeepAliveIndex OBJECT-TYPE
	SYNTAX		PositiveInteger
	MAX-ACCESS	read-only
	STATUS		current
	DESCRIPTION	"Index into this table."
	::= {aiSLCSysCfgKeepAliveEntry 1}

aislcscKeepAliveAddress OBJECT-TYPE
	SYNTAX		IpAddress
	MAX-ACCESS	read-write
	STATUS		current
	DESCRIPTION
		"IP address of network element to ping.
		0.0.0.0 indicates an unused entry."
	::= {aiSLCSysCfgKeepAliveEntry 2}

aislcscKeepAliveInterval OBJECT-TYPE
	SYNTAX		INTEGER (5..600)
	UNITS		"seconds"
	MAX-ACCESS	read-write
	STATUS		current
	DESCRIPTION
		"Time between successive pings of the network element.
		Allowable values are 5 to 600 seconds."
	::= {aiSLCSysCfgKeepAliveEntry 3}

aislcscKeepAliveWarningText OBJECT-TYPE
	SYNTAX		DisplayString (SIZE (0..64))
	MAX-ACCESS	read-write
	STATUS		current
	DESCRIPTION
		"Message sent in SNMP trap when the network element stops
		responding to pings.
		Maximum length is 64 characters."
	::= {aiSLCSysCfgKeepAliveEntry 4}

aislcscKeepAliveOKText OBJECT-TYPE
	SYNTAX		DisplayString (SIZE (0..64))
	MAX-ACCESS	read-write
	STATUS		current
	DESCRIPTION
		"Message sent in SNMP trap when the network element begins
		responding to pings after a period of unresponsiveness.
		Maximum length is 64 characters."
	::= {aiSLCSysCfgKeepAliveEntry 5}

aislcscKeepAliveCommStat OBJECT-TYPE
	SYNTAX		INTEGER { disabled(1), ok(2), lost(3) }
	MAX-ACCESS	read-only
	STATUS		current
	DESCRIPTION
		"Determines the current communication status between the
		system and the target equipment. If the target equipment
		does not respond to pings, this object will be set to lost(3).
		This object will be set to disabled(1) if no IP address is
		configured."
	::= {aiSLCSysCfgKeepAliveEntry 6}

--=========================================================================

aislcscActiveConfigName OBJECT-TYPE
	SYNTAX		DisplayString (SIZE (0..255))
	MAX-ACCESS	read-write
	STATUS		current
	DESCRIPTION
		"Name of the active configuration file.
		Maximum length is 255 characters; additional restrictions
		are system-dependent."
	::= {aiSLCSysCfg 21}

aislcscActiveConfigCRC OBJECT-TYPE
	SYNTAX		INTEGER (0..'ffffffff'h)
	MAX-ACCESS	read-only
	STATUS		current
	DESCRIPTION
		"32-bit CRC of the active configuration file."
	::= {aiSLCSysCfg 22}

aislcscSoftwareUpdateName OBJECT-TYPE
	SYNTAX		DisplayString (SIZE (0..255))
	MAX-ACCESS      read-write
	STATUS		current
	DESCRIPTION
		"To update the system software, set this object to the name of
		the new image file, and monitor aislcscSoftwareUpdateStatus
		until it changes to ok(1) or error(3).  If the update succeeds,
		the new software will be used after the system is rebooted.

		Maximum length is 255 characters; additional restrictions are
		system-dependent."
	::= {aiSLCSysCfg 23}

aislcscSoftwareUpdateStatus OBJECT-TYPE
	SYNTAX		INTEGER {
				ready(1),
				inProgress(2),
				ok(3),
				error(4)
			}
	MAX-ACCESS	read-write
	STATUS		current
	DESCRIPTION
		"See aislcscSoftwareUpdateName for a description of how to
		use this object.
		
		ready(1)      -- ready to update software (read-write)
		inProgress(2) -- update is in progress (read-only)
		ok(3)         -- update completed successfully (read-only)
		error(4)      -- update failed (read-only)"
	::= {aiSLCSysCfg 24}

aislcscResetSystem OBJECT-TYPE
	SYNTAX		INTEGER { none(1), coldStart(2) }
	MAX-ACCESS	read-write
	STATUS		current
	DESCRIPTION
		"When read, this object is always none(1).
		Setting none(1) has no effect.
		Setting coldStart(2) reboots the system."
	::= {aiSLCSysCfg 25}

--=========================================================================

aislcscDiscPowerSupplyStatus OBJECT-TYPE
		SYNTAX      INTEGER {okay(1), trouble(2)}
		MAX-ACCESS  read-only
		STATUS      current
		DESCRIPTION
				"Status of the power supply.  okay(1) or trouble(2).
				When the SLC is booted, this indicates okay(1) until
				the software determines the correct status."
		::= {aiSLCSysCfg 26}
aislcsc48VSupplyAStatus OBJECT-TYPE
		SYNTAX      INTEGER {okay(1), underVoltage(2), overVoltage(3)}
		MAX-ACCESS  read-only
		STATUS      current
		DESCRIPTION
				"Status of the 'A' 48V power supply."
		::= {aiSLCSysCfg 27}
aislcsc48VSupplyBStatus OBJECT-TYPE
		SYNTAX      INTEGER {okay(1), underVoltage(2), overVoltage(3)}
		MAX-ACCESS  read-only
		STATUS      current
		DESCRIPTION
				"Status of the 'B' 48V power supply."
		::= {aiSLCSysCfg 28}
aislcscFanStatus OBJECT-TYPE
		SYNTAX      INTEGER {okay(1), fail(2)}
		MAX-ACCESS  read-only
		STATUS      current
		DESCRIPTION
				"Status of the fan unit."
		::= {aiSLCSysCfg 29}

--=========================================================================

aislcscMib2ReadCommunity OBJECT-TYPE
		SYNTAX		DisplayString (SIZE (0..32))
		MAX-ACCESS	read-write
		STATUS		current
		DESCRIPTION	"SNMP community string for read-only access with mib-2 view."
		::= {aiSLCSysCfg 30}

--=========================================================================

aislcscOverallAlarmSeverity OBJECT-TYPE
	SYNTAX		INTEGER (0..7)
	MAX-ACCESS	read-write
	STATUS		current
	DESCRIPTION
		"Current overall alarm severity (0-7).  This value can be set at the
		user's discretion, but will be overwritten when the next alarm is
		generated."
	::= {aiSLCSysCfg 31}

--=========================================================================

-- Date and time Group
aislcSysCfgTime    OBJECT IDENTIFIER ::= {aiSLCSysCfg 32}

aislcscTimeZone OBJECT-TYPE
		SYNTAX              DisplayString (SIZE (4..6))
		MAX-ACCESS          read-write
		STATUS              current
		DESCRIPTION	"The current Time Zone of the system in the following format: 
		<+|->HH:MM, where HH is the number of hours and MM is the 
		number of minutes. <+/-> specifies the East/West direction. 
		For example, EDT would be displayed as: -05:00 "
		::= {aislcSysCfgTime 1}

aislcscDayLightSaving OBJECT-TYPE
		SYNTAX              INTEGER { disabled (1), enabled (2) }
		MAX-ACCESS          read-write
		STATUS              current
		DESCRIPTION	"Indicates whether Daylight saving is enabled."
		::= {aislcSysCfgTime 2}

aislcscSntpPoll OBJECT-TYPE
		SYNTAX              INTEGER { disabled (1), enabled (2) }
		MAX-ACCESS          read-write
		STATUS              current
		DESCRIPTION	"Indicates whether the SNTP client is enabled on this system."
		::= {aislcSysCfgTime 3}

aislcscNtpServerAddr1 OBJECT-TYPE
		SYNTAX              IpAddress
		MAX-ACCESS          read-write
		STATUS              current
		DESCRIPTION	"IP address of the primary NTP Server"
		::= {aislcSysCfgTime 4}

aislcscNtpServerAddr2 OBJECT-TYPE
		SYNTAX              IpAddress
		MAX-ACCESS          read-write
		STATUS              current
		DESCRIPTION	"IP address of the secondary NTP Server"
		::= {aislcSysCfgTime 5}

aislcscSntpPollInterval OBJECT-TYPE
		SYNTAX              INTEGER (1..9999)
		MAX-ACCESS          read-write
		STATUS              current
		DESCRIPTION	"SNTP poll interval in minutes"
		::= {aislcSysCfgTime 6}

--=========================================================================

aislcscStandaloneStatus OBJECT-TYPE
		SYNTAX      INTEGER {standalone(1), nonStandalone(2)}
		MAX-ACCESS  read-only
		STATUS      current
		DESCRIPTION
				"standalone(1):
						The card is operating standalone (no external CLC).
				nonStandalone(2):
						The card is operating as a line card with a CLC."
		::= {aiSLCSysCfg 33}
--=========================================================================

aislcscShellPromptTimeout OBJECT-TYPE
	SYNTAX		INTEGER (0..10000)
	UNITS		"minutes"
	MAX-ACCESS	read-write
	STATUS		current
	DESCRIPTION
		"Time in minutes before an idle shell is automatically closed.
		0 indicates no timeout."
	::= {aiSLCSysCfg 34}

--=========================================================================

aislcscDestMenuBreakSeq OBJECT-TYPE
	SYNTAX		DisplayString (SIZE (0..80))
	MAX-ACCESS	read-write
	STATUS		current
	DESCRIPTION
		"Sequence of characters to exit a connection made from 
	the destination menu."
	::= {aiSLCSysCfg 35}

END
