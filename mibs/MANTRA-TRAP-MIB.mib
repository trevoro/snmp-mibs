MANTRA-TRAP-MIB DEFINITIONS ::= BEGIN
IMPORTS
    enterprises, Counter
        FROM RFC1155-SMI
    OBJECT-TYPE
        FROM RFC-1212
    DisplayString
        FROM RFC1213-MIB
    NOTIFICATION-TYPE, MODULE-IDENTITY, ObjectName, Integer32, Counter32, snmpModules
        FROM SNMPv2-SMI
    unknownDeviceTrapContents, domain, group, name, runStatus,  pepName, devName, host, port, file, oldFile, newFile, reason, snName, myHost, myPort, mateHost, matePort, minutes, result, sbProducerHost, sbProducerPort, deviceType
        FROM AGGREGATED-EXT-MIB
    TruthValue, DisplayString, TestAndIncr, TimeStamp, RowStatus
        FROM SNMPv2-TC;

	lucent		    OBJECT IDENTIFIER  ::=  {  enterprises  1751  }
	products	    OBJECT IDENTIFIER  ::=  {  lucent  1  }
	softSwitch  	OBJECT IDENTIFIER  ::=  {  products 1198  }

	mantraTraps	MODULE-IDENTITY    
        LAST-UPDATED "240701"
        ORGANIZATION "Lucent Technologies"   
        CONTACT-INFO 
                ""    
        DESCRIPTION
                "The MIB module for entities implementing the xxxx
                protocol."  

    ::=  { softSwitch 0 }

	-- 
	-- the traps area.
	-- these are some of the traps that can be raised by the Admin
	-- module
	-- 

	lssProcessUnstartable NOTIFICATION-TYPE
	    OBJECTS  { deviceType, domain, group, name, host, port, runStatus }
        STATUS current
	    DESCRIPTION
		"Indicates a certain domain:group:process cannot be
		started even after several attempts.  Variables are:
		1)   deviceType - this is either CC, H323, SS7 or
		     EBGen (the various modules in SARAS)
		2-4) domain:group:name - these three variables comprise
		     the fully qualified name of the process (for start/
		     stop snmp-commands)
		5)   host - the hostname on which this process was to be
		     run.
		6)   port - the port on which this process was exposing
		     its health information.
		7)   runStatus - the current run-state in which the
		     process is (likely to be 1).  See moduleSummary for
		     more explanation of runStatus.
		Severity: CRITICAL"
	    ::= { mantraTraps 0 }

	lssProcessCreated NOTIFICATION-TYPE
	    OBJECTS  { deviceType, domain, group, name, host, port, runStatus }
        STATUS current  
	    DESCRIPTION
		"Indicates a certain domain:group:process was
		successfully created/re-started.  Variables are same 
		as the above trap:
		1)   deviceType - this is either CC, H323, SS7 or
		     EBGen (the various modules in SARAS)
		2-4) domain:group:name - these three variables comprise
		     the fully qualified name of the process (for start/
		     stop snmp-commands)
		5)   host - the hostname on which this process was to be
		     run.
		6)   port - the port on which this process was exposing
		     its health information. 
		7)   runStatus - the current run-state in which the
		     process is.  See moduleSummary for more explanation
		     of runStatus.
		Severity: INFO"
	    ::=  { mantraTraps 1 }

	lssProcessDied NOTIFICATION-TYPE
	    OBJECTS  { deviceType, domain, group, name, host, port, runStatus }
        STATUS current
	    DESCRIPTION
		"Indicates a certain domain:group:process died.
		1)   deviceType - this is either CC, H323, SS7 or
		     EBGen (the various modules in SARAS)
		2-4) domain:group:name - these three variables comprise
		     the fully qualified name of the process (for start/
		     stop snmp-commands)
		5)   host - the hostname on which this process was to be
		     run.
		6)   port - the port on which this process was exposing
		     its health information. 
		7)   runStatus - the current run-state in which the
		     process is.   See moduleSummary for more explanation
		     of runStatus.
		Severity: MAJOR"
	    ::=  { mantraTraps 2 }

	lssProcessKilled NOTIFICATION-TYPE
	    OBJECTS  { deviceType, domain, group, name, host, port, runStatus }
        STATUS current
	    DESCRIPTION
		"Indicates a certain domain:group:process was taken
		down manually in response to an snmp-set on mantraReboot, 
		or processStop variable.  Variables are exactly same as
		in the processDied trap:
		1)   deviceType - this is either CC, H323, SS7 or
		     EBGen (the various modules in SARAS)
		2-4) domain:group:name - these three variables comprise
		     the fully qualified name of the process (for start/
		     stop snmp-commands)
		5)   host - the hostname on which this process was to be
		     run.
		6)   port - the port on which this process was exposing
		     its health information. 
		7)   runStatus - the current run-state in which the
		     process is.  See moduleSummary for more explanation 
		     of runStatus.
		Severity: MAJOR"
	    ::=  { mantraTraps 3 }

	lssProcessStateChange NOTIFICATION-TYPE
	    OBJECTS  { deviceType, domain, group, name, host, port, runStatus }
        STATUS current
	    DESCRIPTION
		"Indicates a change of status in a process.  Usually 
		sent to indicate if a process that was inactive, took 
		over for an earlier active process that died.
		Variables are exactly same as all other traps:
		1)   deviceType - this is either CC, H323, SS7 or
		     EBGen (the various modules in SARAS)
		2-4) domain:group:name - these three variables comprise
		     the fully qualified name of the process (for start/
		     stop snmp-commands)
		5)   host - the hostname on which this process was to be
		     run.
		6)   port - the port on which this process was exposing
		     its health information. 
		7)   runStatus - the current run-state in which the
		     process is.  See moduleSummary for more explanation 
		     of runStatus.
		Severity: MAJOR"
	    ::=  { mantraTraps 4 } 

	lssInternalError NOTIFICATION-TYPE
	    OBJECTS  { unknownDeviceTrapContents }
        STATUS current 
	    DESCRIPTION
		"An event is sent up as lssInternalError, 
		if there is an error in formatting, and event
		construction does not succeed.
		The variables are:
		1) unknownDeviceTrapContents - a string representing 
		   the event text as the pep received it.
		Severity: MAJOR"
	    ::= { mantraTraps  5 }

	lssElementSuccessfulConnection NOTIFICATION-TYPE
	    OBJECTS  { pepName, devName, host, port, file }
        STATUS current
	    DESCRIPTION
		"Indicates that the pep was sucessfully able to 
		connect to the source of events specified in its
		config.
		The variables are:
		1)   pepName - this is the name of the PEP who
		     is raising the event
		2)   devName - this is the logical name of the 
		     device this pep is connected to
		3-4) host:port - these two identify the device 
		     that was mounted by the pep
		5)   file - this is the file name used internally
 		     start-up event, mainly.  
		Severity: INFO"
	    ::= { mantraTraps  6 }

	lssElementFileUnReadable NOTIFICATION-TYPE
	    OBJECTS  { pepName, devName, host, port, file }
        STATUS current
	    DESCRIPTION
		"Indicates that the pep's connection exists to the
		device, but the file named in the trap is not 
		readable.
		The variables are:
		1)   pepName - this is the name of the PEP who
		     is raising the event
		2)   devName - this is the logical name of the 
		     device this pep is connected to
		3-4) host:port - these two identify the device 
		     that was mounted by the pep
		5)   file - this is the file name used internally
		Severity: MAJOR"
	    ::= { mantraTraps  7 }

	lssElementDisconnect NOTIFICATION-TYPE
	    OBJECTS  { pepName, devName, host, port, file }
        STATUS current
	    DESCRIPTION
		"Indicates that the pep's connection to the source
		of events was severed.  This could either be because 
		device process died, or because there is a network outage.
		The variables are:
		1)   pepName - this is the name of the PEP who
		     is raising the event
		2)   devName - this is the logical name of the 
		     device this pep is connected to
		3-4) host:port - these two identify the device 
		     that was mounted by the pep
		5)   file - this is the file name used internally
		Severity: MAJOR"
	    ::= { mantraTraps  8 }

	lssElementUnReachable NOTIFICATION-TYPE
	    OBJECTS  { pepName, devName, host, port, file, minutes }
        STATUS current
	    DESCRIPTION
		"Indicates that the pep's connection to the device 
		has not been up for some time now, indicated in 
		minutes.
		The variables are:
		1)   pepName - this is the name of the PEP who
		     is raising the event
		2)   devName - this is the logical name of the 
		     device this pep is connected to
		3-4) host, port - these two identify the device 
		     that was mounted by the pep
		5)   file - this is the file name used internally
		     minutes - the time in minutes for which the 
		     connection to the device has not been up.
		Severity: MAJOR"
	    ::= { mantraTraps  9 }

	logFileChanged NOTIFICATION-TYPE
	    OBJECTS  { oldFile, newFile, result, reason }
        STATUS current
	    DESCRIPTION
		"Indicates that a log-file-change attempt is successful or 
		failure.
		The variables are:
		1)   oldFile - this is the name of the old file which
		     was to be changed.
		2)   newFile - this is the new log file name 
		3)   result  - this indicates 'success' or failure of
		     logFileChange attempt.
		4)   reason - this describes the reason when log file change
		     has failed.
		Severity: INFO"
	    ::= { mantraTraps  10 }

	lssFTMateConnect NOTIFICATION-TYPE
	    OBJECTS  { snName, myHost, myPort, mateHost, matePort }
        STATUS current
	    DESCRIPTION
		"Indicates that this ServiceNode was sucessfully able to 
		connect to its redundant mate. This event is usually raised
		by the Backup mate who is responsible for monitoring its
		respective Primary.
		The variables are:
		1)   snName - this is the name of the ServiceNode who
		     is raising the event. 
		2-3)   myHost:myPort - these identify the host and port of the
		     ServiceNode raising the event.
		4-5) mateHost:matePort - these identify the host and port
		     of the mate to which this ServiceNode connected.
		Severity: INFO"
	    ::= { mantraTraps  11 }

	lssFTMateDisconnect NOTIFICATION-TYPE
	    OBJECTS  { snName, myHost, myPort, mateHost, matePort }
        STATUS current
	    DESCRIPTION
		"Indicates that this ServiceNode has lost connection 
		to its redundant mate due to either process or host failure. 
		This event is usually raised by the Backup mate who is
		monitoring its 	respective Primary. Connection will be
		established upon recovery of the mate.
		The variables are:
		1)   snName - this is the name of the ServiceNode who
		     is raising the event
		2-3)   myHost:myPort - these identify the host and port of the
		     ServiceNode raising the event.
		4-5) mateHost:matePort - these identify the host and port
		     of the mate to which this ServiceNode lost connection.

		Severity: MAJOR"
	    ::= { mantraTraps  12 }

	sbProducerUnreachable NOTIFICATION-TYPE
	    OBJECTS  { pepName, devName, sbProducerHost, sbProducerPort }
        STATUS current
	    DESCRIPTION
		"Indicates that this Socket Based Producer is not reachable by the Policy 
		Enforcement Point.  
		The variables are:
		1)   pepName - this is the name of the Policy Enforcement Point (PEP)  who
		     is raising the event
		2)   devName: Device which is unreachable
		3)   SBProducerHost: Host where the Socket Based event producer is on.
		4)   SBProducerPort: Port where the Socket Based event producer is running on.

		Severity: MAJOR"
	    ::= { mantraTraps  13 }

	sbProducerConnected NOTIFICATION-TYPE
	    OBJECTS  { pepName, devName, sbProducerHost, sbProducerPort }
        STATUS current
	    DESCRIPTION
		"Indicates that this Socket Based Producer has connected to the Policy 
		Enforcement Point (PEP).  
		The variables are:
		1)   pepName - this is the name of the Policy Enforcement Point (PEP)  who
		     is raising the event
		2)   devName: Device which is unreachable
		3)   SBProducerHost: Host where the Socket Based event producer is on.
		4)   SBProducerPort: Port where the Socket Based event producer is running on.

		Severity: MAJOR"
	    ::= { mantraTraps  14 }

	sbProducerRegistered NOTIFICATION-TYPE
	    OBJECTS  { pepName, devName, sbProducerHost, sbProducerPort }
        STATUS current
	    DESCRIPTION
		"Indicates that this Socket Based Producer has registered with the Policy 
		Enforcement Point (PEP).  
		The variables are:
		1)   pepName - this is the name of the Policy Enforcement Point (PEP)  who
		     is raising the event
		2)   devName: Device which is unreachable
		3)   SBProducerHost: Host where the Socket Based event producer is on.
		4)   SBProducerPort: Port where the Socket Based event producer is running on.

		Severity: INFO"
	    ::= { mantraTraps  15 }

	sbProducerDisconnected NOTIFICATION-TYPE
	    OBJECTS  { pepName, devName, sbProducerHost, sbProducerPort }
        STATUS current
	    DESCRIPTION
		"Indicates that this Socket Based Producer has disconnected from the Policy 
		Enforcement Point (PEP).  
		The variables are:
		1)   pepName - this is the name of the Policy Enforcement Point (PEP)  who
		     is raising the event
		2)   devName: Device which is unreachable
		3)   SBProducerHost: Host where the Socket Based event producer is on.
		4)   SBProducerPort: Port where the Socket Based event producer is running on.

		Severity: INFO"
	    ::= { mantraTraps  16 }

	sbProducerCannotRegister NOTIFICATION-TYPE
	    OBJECTS  { pepName, devName, sbProducerHost, sbProducerPort }
        STATUS current
	    DESCRIPTION
		"Indicates that this Socket Based Producer cannot register to the Policy 
		Enforcement Point (PEP).  
		The variables are:
		1)   pepName - this is the name of the Policy Enforcement Point (PEP)  who
		     is raising the event
		2)   devName: Device which is unreachable
		3)   SBProducerHost: Host where the Socket Based event producer is on.
		4)   SBProducerPort: Port where the Socket Based event producer is running on.

		Severity: INFO"
	    ::= { mantraTraps  17 }

	sbProducerCannotDisconnect NOTIFICATION-TYPE
	    OBJECTS  { pepName, devName, sbProducerHost, sbProducerPort }
        STATUS current
	    DESCRIPTION
		"Indicates that this Socket Based Producer cannot disconenct  from  the Policy 
		Enforcement Point (PEP).  
		The variables are:
		1)   pepName - this is the name of the Policy Enforcement Point (PEP)  who
		     is raising the event
		2)   devName: Device which is unreachable
		3)   SBProducerHost: Host where the Socket Based event producer is on.
		4)   SBProducerPort: Port where the Socket Based event producer is running on.

		Severity: INFO"
	    ::= { mantraTraps  18 }

END
