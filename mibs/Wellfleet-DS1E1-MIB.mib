Wellfleet-DS1E1-MIB DEFINITIONS ::= BEGIN

-- Created by mdl2asn version 3.1
-- Creation date: Wed Aug 30 16:40:04 EDT 1995


    IMPORTS

      Counter, Gauge, TimeTicks
        FROM RFC1155-SMI
      OBJECT-TYPE
        FROM RFC-1212
      DisplayString
        FROM RFC1213-MIB
      wfMcT1Group, wfDs1E1Group
        FROM Wellfleet-COMMON-MIB;


    wfDs1E1ModuleTable OBJECT-TYPE
        SYNTAX	SEQUENCE OF WfDs1E1ModuleEntry
        ACCESS	not-accessible
        STATUS	mandatory
        DESCRIPTION
                "This file describes the MIBS for managing the Multichannel T1 and E1
                link modules.

                 DS1E1 MOD record - Contains DS1E1 module Configuration parameters"
        ::= { wfDs1E1Group 1 }

    wfDs1E1ModuleEntry OBJECT-TYPE
        SYNTAX	WfDs1E1ModuleEntry
        ACCESS	not-accessible
        STATUS	mandatory
        DESCRIPTION
                "An entry in the DS1E1 Base table"
        INDEX	{ wfDs1E1ModuleSlot,
    		  wfDs1E1ModuleModule }
        ::= { wfDs1E1ModuleTable 1 }

    WfDs1E1ModuleEntry ::= SEQUENCE {
    	    wfDs1E1ModuleDelete
    		INTEGER,
    	    wfDs1E1ModuleSlot
    		INTEGER,
    	    wfDs1E1ModuleModule
    		INTEGER,
    	    wfDs1E1ModulePrimaryClock
    		INTEGER,
    	    wfDs1E1ModuleSecondaryClock
    		INTEGER,
    	    wfDs1E1ModuleCurrentClock
    		INTEGER,
    	    wfDs1E1ModuleExtClockOperational
    		INTEGER,
    	    wfDs1E1ModuleLoop1ClockOperational
    		INTEGER,
    	    wfDs1E1ModuleLoop2ClockOperational
		INTEGER,
	    wfDs1E1ModuleLoop3ClockOperational
		INTEGER,
	    wfDs1E1ModuleLoop4ClockOperational
    		INTEGER,
            wfDs1E1ModuleCfgTxBufferUseCredits
    		INTEGER,
    	    wfDs1E1ModuleCfgRxBufferUseCredits
    		INTEGER,
            wfDs1E1ModuleTxBufferUseCredits
    		INTEGER,
    	    wfDs1E1ModuleRxBufferUseCredits
    		INTEGER
        }

    wfDs1E1ModuleDelete OBJECT-TYPE
        SYNTAX	INTEGER {
    		    created(1),
    		    deleted(2)
    		}
        ACCESS	read-write
        STATUS	mandatory
        DESCRIPTION
                "Create/Delete parameter"
        DEFVAL	{ created }
        ::= { wfDs1E1ModuleEntry 1 }

    wfDs1E1ModuleSlot OBJECT-TYPE
        SYNTAX	INTEGER
        ACCESS	read-only
        STATUS	mandatory
        DESCRIPTION
                "Instance ID slot, filled in by driver"
        ::= { wfDs1E1ModuleEntry 2 }

    wfDs1E1ModuleModule OBJECT-TYPE
        SYNTAX	INTEGER
        ACCESS	read-only
        STATUS	mandatory
        DESCRIPTION
                "Instance ID slot, filled in by driver"
        ::= { wfDs1E1ModuleEntry 3 }

    wfDs1E1ModulePrimaryClock OBJECT-TYPE
        SYNTAX	INTEGER {
    		    external(1),
    		    loop1(2),
    		    loop2(3),
    		    internal(4),
		    loop3(5),
		    loop4(6)
    		}
        ACCESS	read-write
        STATUS	mandatory
        DESCRIPTION
                "Specifies the primary source for transmit timing. Both ports use the same
                transmit timing source.  The options for timing source are internal timing
                source, loop timing from either port and an external timing source."
        DEFVAL	{ loop1 }
        ::= { wfDs1E1ModuleEntry 4 }

    wfDs1E1ModuleSecondaryClock OBJECT-TYPE
        SYNTAX	INTEGER {
    		    external(1),
    		    loop1(2),
    		    loop2(3),
    		    internal(4),
		    loop3(5),
		    loop4(6)
    		}
        ACCESS	read-write
        STATUS	mandatory
        DESCRIPTION
                "Specifies the secondary source for transmit timing. During normal operation
                transmit timing is derived from the primary timing source. If the primary
                timing source fails, the software switches to secondary timing source."
        DEFVAL	{ internal }
        ::= { wfDs1E1ModuleEntry 5 }

    wfDs1E1ModuleCurrentClock OBJECT-TYPE
        SYNTAX	INTEGER {
    		    external(1),
    		    loop1(2),
    		    loop2(3),
    		    internal(4),
		    loop3(5),
		    loop4(6)
    		}
        ACCESS	read-only
        STATUS	mandatory
        DESCRIPTION
                "Indicates the clock source currently in use"
        ::= { wfDs1E1ModuleEntry 6 }

    wfDs1E1ModuleExtClockOperational OBJECT-TYPE
        SYNTAX	INTEGER {
    		    present(1),
    		    notpresent(2)
    		}
        ACCESS	read-only
        STATUS	mandatory
        DESCRIPTION
                "Indicates whether the External clock is operational"
        DEFVAL	{ present }
        ::= { wfDs1E1ModuleEntry 7 }

    wfDs1E1ModuleLoop1ClockOperational OBJECT-TYPE
        SYNTAX	INTEGER {
    		    present(1),
    		    notpresent(2)
    		}
        ACCESS	read-only
        STATUS	mandatory
        DESCRIPTION
                "Indicates whether the timing source from port 1 is operational"
        DEFVAL	{ present }
        ::= { wfDs1E1ModuleEntry 8 }

    wfDs1E1ModuleLoop2ClockOperational OBJECT-TYPE
        SYNTAX	INTEGER {
    		    present(1),
    		    notpresent(2)
    		}
        ACCESS	read-only
        STATUS	mandatory
        DESCRIPTION
                "Indicates whether the timing source from port 2 is operational"
        DEFVAL	{ present }
        ::= { wfDs1E1ModuleEntry 9 }

    wfDs1E1ModuleLoop3ClockOperational OBJECT-TYPE
	SYNTAX	INTEGER {
		    present(1),
		    notpresent(2)
		}
	ACCESS	read-only
	STATUS	mandatory
	DESCRIPTION
		"Indicates whether the timing source from port 3 is operational"
	DEFVAL	{ present }
	::= { wfDs1E1ModuleEntry 10 }

    wfDs1E1ModuleLoop4ClockOperational OBJECT-TYPE
	SYNTAX	INTEGER {
		    present(1),
		    notpresent(2)
		}
	ACCESS	read-only
	STATUS	mandatory
	DESCRIPTION
		"Indicates whether the timing source from port 4 is operational"
	DEFVAL	{ present }
	::= { wfDs1E1ModuleEntry 11 }

    wfDs1E1ModuleCfgTxBufferUseCredits OBJECT-TYPE
        SYNTAX	INTEGER(0..512)
        ACCESS	read-write
        STATUS	mandatory
        DESCRIPTION
               "Configured Transmit Buffer Credits. Values other than zero over-ride
                the router selected values. A value of zero has a special meaning.
                Zero causes router based default values to be used.  All values are
                accepted.  Care should be taken not to set this to a value which is
                much greater than the default.  The default can be read out of the
                wfDs1E1ModuleTxBufferUseCredits attribute when the router is 
                running with this attribute set to zero.  Sets to this attribute
                may take up to one minute to take effect."
        ::= { wfDs1E1ModuleEntry 12 }
    wfDs1E1ModuleCfgRxBufferUseCredits OBJECT-TYPE
        SYNTAX	INTEGER(0..512)
        ACCESS	read-write
        STATUS	mandatory
        DESCRIPTION
                "Configured Receive Buffer Credits. Values other than zero over-ride
                the router selected values. A value of zero has a special meaning.
                Zero cuases router based default values to be used. Values larger
                than the compiled ring size are truncated to the compiled ring
                size.  Sets to this attribute may take up to one minute to take
                effect."
        ::= { wfDs1E1ModuleEntry 13 }
     wfDs1E1ModuleTxBufferUseCredits OBJECT-TYPE
        SYNTAX	INTEGER
        ACCESS	read-only
        STATUS	mandatory
        DESCRIPTION
               "Current Transmit Buffers available for use by module"
        ::= { wfDs1E1ModuleEntry 14 }
        
    wfDs1E1ModuleRxBufferUseCredits OBJECT-TYPE
        SYNTAX	INTEGER
        ACCESS	read-only
        STATUS	mandatory
        DESCRIPTION
                "Current Receive Buffers available for use by module"
        ::= { wfDs1E1ModuleEntry 15 }


    wfDs1E1PortMapTable OBJECT-TYPE
        SYNTAX	SEQUENCE OF WfDs1E1PortMapEntry
        ACCESS	not-accessible
        STATUS	mandatory
        DESCRIPTION
                "DS1E1  port map record - Used by the driver to identify the LineNumber
                for the Port. The only table indexed by slot.connector. Its purpose is
                to map slot.connector to a PortLineNumber."
        ::= { wfDs1E1Group 2 }

    wfDs1E1PortMapEntry OBJECT-TYPE
        SYNTAX	WfDs1E1PortMapEntry
        ACCESS	not-accessible
        STATUS	mandatory
        DESCRIPTION
                "An entry in the DS1E1 port table"
        INDEX	{ wfDs1E1PortMapSlot,
    		  wfDs1E1PortMapConnector }
        ::= { wfDs1E1PortMapTable 1 }

    WfDs1E1PortMapEntry ::= SEQUENCE {
    	    wfDs1E1PortMapDelete
    		INTEGER,
    	    wfDs1E1PortMapSlot
    		INTEGER,
    	    wfDs1E1PortMapConnector
    		INTEGER,
    	    wfDs1E1PortMapLineNumber
    		INTEGER,
    	    wfDs1E1PortMapDslId
    		INTEGER
        }

    wfDs1E1PortMapDelete OBJECT-TYPE
        SYNTAX	INTEGER {
    		    created(1),
    		    deleted(2)
    		}
        ACCESS	read-write
        STATUS	mandatory
        DESCRIPTION
                "Create/Delete parameter"
        DEFVAL	{ created }
        ::= { wfDs1E1PortMapEntry 1 }

    wfDs1E1PortMapSlot OBJECT-TYPE
        SYNTAX	INTEGER
        ACCESS	read-only
        STATUS	mandatory
        DESCRIPTION
                "Instance ID Slot, filled in by driver"
        ::= { wfDs1E1PortMapEntry 2 }

    wfDs1E1PortMapConnector OBJECT-TYPE
        SYNTAX	INTEGER
        ACCESS	read-only
        STATUS	mandatory
        DESCRIPTION
                "Instance ID Connector, filled in by driver"
        ::= { wfDs1E1PortMapEntry 3 }

    wfDs1E1PortMapLineNumber OBJECT-TYPE
        SYNTAX	INTEGER
        ACCESS	read-write
        STATUS	mandatory
        DESCRIPTION
                "LineNumber off of which all other MIB instances are indexed."
        ::= { wfDs1E1PortMapEntry 4 }

    wfDs1E1PortMapDslId OBJECT-TYPE
        SYNTAX	INTEGER
        ACCESS	read-only
        STATUS	mandatory
        DESCRIPTION
                "When this T1/E1 interface is configured for Primary Rate ISDN (PRI) this
                attribute provides the ID of this Digital Subscriber Loop (DSL) interface.
                Each T1 or E1 PRI interface on a particular slot is assigned a unique DSL
                ID."
        ::= { wfDs1E1PortMapEntry 5 }

    wfDs1E1PortTable OBJECT-TYPE
        SYNTAX	SEQUENCE OF WfDs1E1PortEntry
        ACCESS	not-accessible
        STATUS	mandatory
        DESCRIPTION
                "DS1E1  port record - Contains MUNICH32 Configuration parameters
                "
        ::= { wfDs1E1Group 3 }

    wfDs1E1PortEntry OBJECT-TYPE
        SYNTAX	WfDs1E1PortEntry
        ACCESS	not-accessible
        STATUS	mandatory
        DESCRIPTION
                "An entry in the DS1E1 port table"
        INDEX	{ wfDs1E1PortLineNumber }
        ::= { wfDs1E1PortTable 1 }

    WfDs1E1PortEntry ::= SEQUENCE {
    	    wfDs1E1PortDelete
    		INTEGER,
    	    wfDs1E1PortDisable
    		INTEGER,
    	    wfDs1E1PortState
    		INTEGER,
    	    wfDs1E1PortLineNumber
    		INTEGER,
    	    wfDs1E1PortMtu
    		INTEGER,
    	    wfDs1E1PortSignalLevel
    		INTEGER,
    	    wfDs1E1PortSetupAlarmThreshold
    		INTEGER,
    	    wfDs1E1PortClearAlarmThreshold
    		INTEGER,
    	    wfDs1E1PortFdlTargetHdlcAddress
    		INTEGER,
    	    wfDs1E1PortAcceptLoopbackRequest
    		INTEGER,
    	    wfDs1E1PortLoopbackState
    		INTEGER,
    	    wfDs1E1PortBertMode
    		INTEGER,
    	    wfDs1E1PortBertTestPattern
    		INTEGER,
    	    wfDs1E1PortBertSendAlarm
    		INTEGER,
    	    wfDs1E1PortInternationalBit
    		INTEGER,
    	    wfDs1E1PortLineApplication
    		INTEGER,
    	    wfDs1E1PortLoggingEnableMask
		INTEGER,
	    wfDs1E1PortSendPrmCrAddressBit
		INTEGER,
	    wfDs1E1PortAcceptPrmCrAddressBit
    		INTEGER,
	    wfDs1E1PortLineImpedanceOption
    		INTEGER,
	    wfDs1E1PortFdlLoopInterframeFill
    		INTEGER,
            wfDs1E1PortRelayCtrl
               INTEGER,
            wfDs1E1PortRelayStatus
               INTEGER,
	    wfDs1E1PortPrimaryClockSource
               INTEGER,
	    wfDs1E1PortSecondaryClockSource
               INTEGER,
	    wfDs1E1PortCurrentClock
               INTEGER,
	    wfDs1E1PortExtClockOperational
               INTEGER,
    	    wfDs1E1PortTransmitWaveform
    		INTEGER
        }

    wfDs1E1PortDelete OBJECT-TYPE
        SYNTAX	INTEGER {
    		    created(1),
    		    deleted(2)
    		}
        ACCESS	read-write
        STATUS	mandatory
        DESCRIPTION
                "Create/Delete parameter"
        DEFVAL	{ created }
        ::= { wfDs1E1PortEntry 1 }

    wfDs1E1PortDisable OBJECT-TYPE
        SYNTAX	INTEGER {
    		    enabled(1),
    		    disabled(2)
    		}
        ACCESS	read-write
        STATUS	mandatory
        DESCRIPTION
                "Enable/Disable parameter"
        DEFVAL	{ enabled }
        ::= { wfDs1E1PortEntry 2 }

    wfDs1E1PortState OBJECT-TYPE
        SYNTAX	INTEGER {
    		    up(1),
    		    yelalarm(2),
    		    aisalarm(3),
    		    redalarm(4),
    		    loopback(10),
    		    bert(11),
    		    init(15),
    		    notpresent(20)
    		}
        ACCESS	read-only
        STATUS	mandatory
        DESCRIPTION
                "Line Driver state variable"
        DEFVAL	{ notpresent }
        ::= { wfDs1E1PortEntry 3 }

    wfDs1E1PortLineNumber OBJECT-TYPE
        SYNTAX	INTEGER
        ACCESS	read-only
        STATUS	mandatory
        DESCRIPTION
                "LineNumber for this port. This value is assigned at configuration time
                and uniquely identifies this interface.  This LineNumber not equal to
                any of the LineNumbers assigned to the LogicalLines configured through
                this Port."
        ::= { wfDs1E1PortEntry 4 }

    wfDs1E1PortMtu OBJECT-TYPE
        SYNTAX	INTEGER(3..4608)
        ACCESS	read-write
        STATUS	mandatory
        DESCRIPTION
                "MTU parameter. Obsoleted, it is no longer referenced."
        DEFVAL	{ 1600 }
        ::= { wfDs1E1PortEntry 5 }

    wfDs1E1PortSignalLevel OBJECT-TYPE
        SYNTAX	INTEGER {
    		    ds1-minus-15(1),
    		    ds1-minus-7point5(2),
    		    zero-point0(3),
    		    dsx1-plus-point5(4),
    		    dsx1-plus-point8(5),
    		    dsx1-plus-1point1(6),
    		    dsx1-plus-1point5(7)
    		}
        ACCESS	read-write
        STATUS	mandatory
        DESCRIPTION
                "Specifies T1 transmit power level, in terms of DB. They
                translate into cable length as follows:
                0.0dB -> 0-133   ft
                0.5dB -> 133-266 ft
                0.8dB -> 266-399 ft
                1.1dB -> 399-533 ft
                1.5dB -> 533-655 ft"
        DEFVAL	{ zero-point0 }
        ::= { wfDs1E1PortEntry 6 }

    wfDs1E1PortSetupAlarmThreshold OBJECT-TYPE
        SYNTAX	INTEGER(2..10)
        ACCESS	read-write
        STATUS	mandatory
        DESCRIPTION
                "Specifies setup time for performance failure conditions,
                in seconds. When a performance defect is present for greater
                than the time specified by this parameter a performance
                failure is registered and a message is logged."
        DEFVAL	{ 2 }
        ::= { wfDs1E1PortEntry 7 }

    wfDs1E1PortClearAlarmThreshold OBJECT-TYPE
        SYNTAX	INTEGER(2..10)
        ACCESS	read-write
        STATUS	mandatory
        DESCRIPTION
                "Specifies clear time for performance failure conditions,
                in seconds. When a performance failure condition has been
                cleared for greater than the time specified by this parameter
                then the failure cleared condition is registered and a
                message is logged."
        DEFVAL	{ 2 }
        ::= { wfDs1E1PortEntry 8 }

    wfDs1E1PortFdlTargetHdlcAddress OBJECT-TYPE
        SYNTAX	INTEGER {
    		    az(1),
    		    by(2)
    		}
        ACCESS	read-write
        STATUS	mandatory
        DESCRIPTION
                "Selects between the two FDL target address modes. This determines
                whether the near-end FDL will respond to HDLC address AZ or
                BY in the FDL messages received from the far-end."
        DEFVAL	{ by }
        ::= { wfDs1E1PortEntry 9 }

    wfDs1E1PortAcceptLoopbackRequest OBJECT-TYPE
        SYNTAX	INTEGER {
    		    enabled(1),
    		    disabled(2)
    		}
        ACCESS	read-write
        STATUS	mandatory
        DESCRIPTION
                "The DS1E1 link module is capable of detecting loop up and loop down
                codes received from the far end. This parameter enables and disables
                loop up/down code detection circuitry.  If enabled,  this interface
                will accept and comply with a request to go into loopback mode from
                a far end device."
        DEFVAL	{ enabled }
        ::= { wfDs1E1PortEntry 10 }

    wfDs1E1PortLoopbackState OBJECT-TYPE
        SYNTAX	INTEGER {
    		    noloop(1),
    		    mgrreqpayloadloop(2),
    		    mgrreqlineloop(3),
    		    netreqpayloadloop(4),
    		    netreqlineloop(5),
    		    otherloop(6)
    		}
        ACCESS	read-only
        STATUS	mandatory
        DESCRIPTION
                "Indicates the current loopback state of this interface. The interface
                can be in one the following states:

                 Payload Loopback
                 Line Loopback
                 no loopback

                Payload or Line loopback modes can be initiated by either of two methods:

                Manager requested Loopback (MGRREQPAYLOADLOOP or MGRREQLINELOOP) is
                initiated by the Manager of this device.

                Network requested Loopback (NETREQPAYLOADLOOP or NETREQLINELOOP) is
                initiated by this interface receiving an in-band request on the network
                from the far end device."
        DEFVAL	{ noloop }
        ::= { wfDs1E1PortEntry 11 }

    wfDs1E1PortBertMode OBJECT-TYPE
        SYNTAX	INTEGER {
    		    enabled(1),
    		    disabled(2)
    		}
        ACCESS	read-write
        STATUS	mandatory
        DESCRIPTION
                "An option to generate and analyze specific test patterns
                is provided in BERT mode of operation. Only one port
                can be in BERT mode at a time. This attribute selects
                normal or BERT mode of operation"
        DEFVAL	{ disabled }
        ::= { wfDs1E1PortEntry 12 }

    wfDs1E1PortBertTestPattern OBJECT-TYPE
        SYNTAX	INTEGER {
    		    zeros(1),
    		    ones(2),
    		    qrss(3),
    		    two15(4),
    		    two15-inv(5),
    		    two20(6),
    		    two23(7),
    		    two23-inv(8)
    		}
        ACCESS	read-write
        STATUS	mandatory
        DESCRIPTION
                "When a port is in BERT mode, it is capable of generating
                a set of known patterns. This paramater selects between those
                patterns"
        DEFVAL	{ ones }
        ::= { wfDs1E1PortEntry 13 }

    wfDs1E1PortBertSendAlarm OBJECT-TYPE
        SYNTAX	INTEGER {
    		    ais-alarm(1),
    		    yellow-alarm(2),
    		    disabled(3)
    		}
        ACCESS	read-write
        STATUS	mandatory
        DESCRIPTION
                "Specifies a Alarm Indication Signal (AIS) (Blue Alarm) or yellow alarm to
                be transmitted while in BERT mode."
        DEFVAL	{ disabled }
        ::= { wfDs1E1PortEntry 14 }

    wfDs1E1PortInternationalBit OBJECT-TYPE
        SYNTAX	INTEGER {
    		    enabled(1),
    		    disabled(2)
    		}
        ACCESS	read-write
        STATUS	mandatory
        DESCRIPTION
                "Specifies if the International bit should be set in
                the E1 frame"
        DEFVAL	{ disabled }
        ::= { wfDs1E1PortEntry 15 }

    wfDs1E1PortLineApplication OBJECT-TYPE
        SYNTAX	INTEGER {
    		    nonpri(1),
    		    pri(2),
    		    mixed(3),
		    frswpri(4)
    		}
        ACCESS	read-write
        STATUS	mandatory
        DESCRIPTION
                "Specifies the application that the LogicalLines of this Port will provide.
                NONPRI indicates that all of the LogicalLines will have a permanent Cct
                number and will not be used to dial to varying destinations.  PRI
                indicates that some or all of the ds0s of this port will be used for switched
                Ccts using ISDN. MIXED indicates that some of the ds0s are being used for
                switched Ccts using ISDN and some are being used for non PRI permanent
                connections for other applications such as leased lines or Frame Relay."
        DEFVAL	{ nonpri }
        ::= { wfDs1E1PortEntry 16 }

    wfDs1E1PortLoggingEnableMask OBJECT-TYPE
        SYNTAX	INTEGER
        ACCESS	read-write
        STATUS	mandatory
        DESCRIPTION
                "Specifies which catagories of extended event log messages are enabled for
                logging.  Current bit definitions are:

                     bit 31                       bit 0
                     +--------------------------------+
                     |                                |
                     +--------------------------------+

                     bit0      ISDN PRI debug messages
                     bit1-31   reserved"
        ::= { wfDs1E1PortEntry 17 }

    wfDs1E1PortSendPrmCrAddressBit OBJECT-TYPE
	SYNTAX	INTEGER {
		    prm-ci(1),
		    prm-carrier(2)
		}
	ACCESS	read-write
	STATUS	mandatory
	DESCRIPTION
		"Specifies the Performance message as originating from either a
		Carrier or Customer Installation (CI).  As the performance
		message is sent out the FDL, the PRM Opening Address C/R bit
		is either set (Carrier) or cleared (CI).  This feature is only
		supported by the QMCT1."
	DEFVAL	{ prm-ci }
	::= { wfDs1E1PortEntry 18 }

    wfDs1E1PortAcceptPrmCrAddressBit OBJECT-TYPE
	SYNTAX	INTEGER {
		    prm-ci(1),
		    prm-carrier(2)
		}
	ACCESS	read-write
	STATUS	mandatory
	DESCRIPTION
		"Accepts only Performance messages originating from either a
		Carrier or Customer Installation (CI), as determined below.
		The PRM Opening Address C/R bit is read upon receiving a
		performance message.  If the Performance message does not
		originate from the expected source, it is discarded.  This
		feature is only supported by the QMCT1."
	DEFVAL	{ prm-ci }
	::= { wfDs1E1PortEntry 19 }

    wfDs1E1PortLineImpedanceOption OBJECT-TYPE
        SYNTAX  INTEGER {
                    rj45-120-ohms(1),
                    bnc-75-ohms(2)
                }
        ACCESS  read-write
        STATUS  mandatory
        DESCRIPTION
                "Supports user selectible Line Impedance option for ASN MCE1
		Net Modules."
        DEFVAL  { rj45-120-ohms }
        ::= { wfDs1E1PortEntry 20 }

    wfDs1E1PortFdlLoopInterframeFill OBJECT-TYPE
        SYNTAX  INTEGER {
                    mark(1),
                    loop-retention(2)
                }
        ACCESS  read-write
        STATUS  mandatory
        DESCRIPTION
                "Enables the Loop Retention Interframe Time Fill for
		the FDL after sending Loop Up Code.  Also enables the
		detection of the Loop Retention Code when placed into
		Line or Payload loopback by the remote end."
        DEFVAL  { mark }
        ::= { wfDs1E1PortEntry 21 }

    wfDs1E1PortRelayCtrl OBJECT-TYPE
         SYNTAX  INTEGER {
                     loop(1),
                     no-loop(2)
                 }
         ACCESS  read-write
         STATUS  mandatory
         DESCRIPTION
                "The Relay on the QMCT1 will always be placed into
                loopback for the following conditions:
                    1. Power Up
                    2. Reboot
                    3. Hardware Reset Button
                    4. System CRASH
                However, when altering QMCT1 Port or Module MIBs' attributes
                with a restart characteristic, the state of the Relay will
                be controlled by this MIB attribute.  When set to loop (1),
                the Relay will go into loopback as the Port/Module is
                re-initialized.  The Relay will come out of loopback as the
                Port/Module re-initialization is complete.  When set to
                noLoop (2), the Relay will remain in its present state as
                the Port/Module is re-initialized."
         DEFVAL  { loop }
         ::= { wfDs1E1PortEntry 22 }

    wfDs1E1PortRelayStatus OBJECT-TYPE
         SYNTAX  INTEGER {
                     loop(1),
                     noLoop(2)
                 }
         ACCESS  read-only
         STATUS  mandatory
         DESCRIPTION
                "This attribute indicates the current state of the Relay
                on the QMCT1.  When set to loop (1), the Relay is currently
                looping data from the Rx path onto the Tx path.  When set
                to noLoop (2), the Rx path and Tx path are connected to the
                Framer.  Note that the Framer may be placed into loopback
                without affecting this attribute."
         DEFVAL  { loop }
         ::= { wfDs1E1PortEntry 23 }

    wfDs1E1PortPrimaryClockSource OBJECT-TYPE
        SYNTAX  INTEGER {
                    internal(1),
                    external(2),
                    loop(3)
                }
        ACCESS  read-write
        STATUS  mandatory
        DESCRIPTION
                "Selects the Primary source of the Tx Clock for the DS1/E1
                interface"
        DEFVAL { loop }
        ::= { wfDs1E1PortEntry 24 }

    wfDs1E1PortSecondaryClockSource OBJECT-TYPE
        SYNTAX  INTEGER {
                    internal(1),
                    external(2),
                    loop(3)
                }
        ACCESS  read-write
        STATUS  mandatory
        DESCRIPTION
                "Selects the Secondary source of the Tx Clock for the DS1/E1
                interface"
        DEFVAL { internal }
        ::= { wfDs1E1PortEntry 25 }

    wfDs1E1PortCurrentClock OBJECT-TYPE
        SYNTAX  INTEGER {
                    internal(1),
                    external(2),
                    loop(3)
                }
        ACCESS  read-only
        STATUS  mandatory
        DESCRIPTION
                "Indicates the clock source currently in use by the DS1"
        DEFVAL  { loop }
        ::= { wfDs1E1PortEntry 26 }

    wfDs1E1PortExtClockOperational OBJECT-TYPE
        SYNTAX  INTEGER {
                    present(1),
                    notpresent(2)
                }
        ACCESS  read-only
        STATUS  mandatory
        DESCRIPTION
                "Indicates whether the External clock is operational"
        DEFVAL  { notpresent }
        ::= { wfDs1E1PortEntry 27 }

    wfDs1E1PortTransmitWaveform OBJECT-TYPE
        SYNTAX	INTEGER {
    		    long-haul-0point0(1),
    		    long-haul-7point5(2),
    		    long-haul-15point0(3),
    		    long-haul-22point5(4),
    		    short-haul-0to110(5),
    		    short-haul-110to220(6),
    		    short-haul-220to330(7),
                    short-haul-330to440(8),
                    short-haul-440to550(9),
                    short-haul-550to660(10)
    		}
        ACCESS	read-write
        STATUS	mandatory
        DESCRIPTION
                "Specifies T1 transmit waveform settings.  Legal values are:

                long haul (LBO 0.0dB)
                long haul (LBO 7.5dB)
                long haul (LBO 15.0dB)
                long haul (LBO 22.5dB)

                short haul (0-110 ft)
                short haul (110-220 ft)
                short haul (220-330 ft)
                short haul (330-440 ft)
                short haul (440-550 ft)
                short haul (550-660 ft)

                Note that this attribute is not supported by all T1 interfaces.
                For those interfaces that DO NOT support this attribute, the
                wfDs1E1PortSignalLevel attribute is used instead."
        DEFVAL	{ short-haul-0to110 }
        ::= { wfDs1E1PortEntry 28 }


    wfDs1E1ConfigTable OBJECT-TYPE
        SYNTAX	SEQUENCE OF WfDs1E1ConfigEntry
        ACCESS	not-accessible
        STATUS	mandatory
        DESCRIPTION
                "DS1E1 Configuration Table. This is a copy of the dsx1ConfigTable found
                in RFC1406. The table is indexed with PortLineNumber instead of ifIndex,
                however."
        ::= { wfDs1E1Group 4 }

    wfDs1E1ConfigEntry OBJECT-TYPE
        SYNTAX	WfDs1E1ConfigEntry
        ACCESS	not-accessible
        STATUS	mandatory
        DESCRIPTION
                "An entry in the DS1E1 config table"
        INDEX	{ wfDs1E1ConfigPortLineNumber }
        ::= { wfDs1E1ConfigTable 1 }

    WfDs1E1ConfigEntry ::= SEQUENCE {
    	    wfDs1E1ConfigDelete
    		INTEGER,
    	    wfDs1E1ConfigPortLineNumber
    		INTEGER,
    	    wfDs1E1ConfigIfIndex
    		INTEGER,
    	    wfDs1E1ConfigTimeElapsed
    		INTEGER,
    	    wfDs1E1ConfigValidIntervals
    		INTEGER,
    	    wfDs1E1ConfigLineType
    		INTEGER,
    	    wfDs1E1ConfigLineCoding
    		INTEGER,
    	    wfDs1E1ConfigSendCode
    		INTEGER,
    	    wfDs1E1ConfigCircuitIdentifier
    		DisplayString,
    	    wfDs1E1ConfigLoopbackConfig
    		INTEGER,
    	    wfDs1E1ConfigLineStatus
    		INTEGER,
    	    wfDs1E1ConfigSignalMode
    		INTEGER,
    	    wfDs1E1ConfigTransmitClockSource
    		INTEGER,
    	    wfDs1E1ConfigFdl
    		INTEGER
        }

    wfDs1E1ConfigDelete OBJECT-TYPE
        SYNTAX	INTEGER {
    		    created(1),
    		    deleted(2)
    		}
        ACCESS	read-write
        STATUS	mandatory
        DESCRIPTION
                "Create/Delete attribute"
        DEFVAL	{ created }
        ::= { wfDs1E1ConfigEntry 1 }

    wfDs1E1ConfigPortLineNumber OBJECT-TYPE
        SYNTAX	INTEGER
        ACCESS	read-only
        STATUS	mandatory
        DESCRIPTION
                "The index ID for this record. It is the line number assigned to a port
                in the wfDs1E1PortMapEntry for a port.connector pair. Its channel field
                should be 0."
        ::= { wfDs1E1ConfigEntry 2 }

    wfDs1E1ConfigIfIndex OBJECT-TYPE
        SYNTAX	INTEGER
        ACCESS	read-only
        STATUS	mandatory
        DESCRIPTION
                "Currently this is the sames as wfDs1E1LinePortIndex"
        ::= { wfDs1E1ConfigEntry 3 }

    wfDs1E1ConfigTimeElapsed OBJECT-TYPE
        SYNTAX	INTEGER
        ACCESS	read-only
        STATUS	mandatory
        DESCRIPTION
                "The number of seconds that have elapsed since the beginning of the
                current error-measurement period. Only relevant when the
                wfDs1E1ConfigLineType is ESF and the wfDs1E1ConfigFdl is AT&T 54016."
        ::= { wfDs1E1ConfigEntry 4 }

    wfDs1E1ConfigValidIntervals OBJECT-TYPE
        SYNTAX	INTEGER
        ACCESS	read-only
        STATUS	mandatory
        DESCRIPTION
                "The number of previous intervals for which valid data was collected. The
                value will be 96 unless the interface was brought on-line within the last
                24 hours, in which case the value will be the number of complete 15 minute
                intervals the since interface has been online. Only relevant when the
                wfDs1E1ConfigLineType is ESF and the wfDs1E1ConfigFdl is AT&T 54016."
        ::= { wfDs1E1ConfigEntry 5 }

    wfDs1E1ConfigLineType OBJECT-TYPE
        SYNTAX	INTEGER {
    		    unframedt1(1),
    		    esf(2),
    		    sf(3),
    		    e1(4),
    		    e1crc(5),
    		    e1mf(6),
    		    e1crcmf(7),
    		    unframede1(8)
    		}
        ACCESS	read-write
        STATUS	mandatory
        DESCRIPTION
                "This attribute is used to configure the line framing type to match
                the carrier's framing. SF and ESF are T1 framing types and the main
                differences between the two are the number of frames in a superframe
                and the use of the f-bit. The E1, E1CRC, E1MF, and E1CRCMF are used
                for E1 lines."
        DEFVAL	{ esf }
        ::= { wfDs1E1ConfigEntry 6 }

    wfDs1E1ConfigLineCoding OBJECT-TYPE
        SYNTAX	INTEGER {
    		    jbzs(1),
    		    b8zs(2),
    		    hdb3(3),
    		    zbtsi(4),
    		    ami(5)
    		}
        ACCESS	read-write
        STATUS	mandatory
        DESCRIPTION
                "This variable describes the variety of Zero Code Suppression used on the
                link, which in turn affects a number of its characteristics. It should
                be set to match the carrier.

                AMI (alternate mark inversion) refers to a mode wherein no zero code
                suppression is present and the line encoding does not solve the problem
                directly.  In  this application, the higher layer must provide data
                which meets or exceeds the pulse density  requirements, such as inverting
                HDLC data. This could be used for T1 or E1 lines.

                B8ZS refers to the use of a specified pattern of normal bits and bipolar
                violations which are used to replace a sequence of eight zero bits. This
                can be used on T1 lines while HDB3 provides similar functionality for
                E1 links."
        DEFVAL	{ b8zs }
        ::= { wfDs1E1ConfigEntry 7 }

    wfDs1E1ConfigSendCode OBJECT-TYPE
        SYNTAX	INTEGER {
    		    sendnocode(1),
    		    sendlinecode(2),
    		    sendpayloadcode(3),
    		    sendresetcode(4),
    		    sendqrs(5),
    		    send511pattern(6),
    		    send3in24pattern(7),
    		    sendothertestpattern(8)
    		}
        ACCESS	read-only
        STATUS	mandatory
        DESCRIPTION
                "This variable is currently read-only and it indicates what type of code is
                being sent across the DS1 interface by the device.  The values mean:

                  SENDNOCODE - sending looped or normal data

                  SENDLINECODE - sending a request for a line loopback

                  SENDPAYLOADCODE - sending a request for a payload loopback

                  SENDRESETCODE - sending a loopback termination request

                  SENDQRS - sending a Quasi-Random Signal (QRS) test pattern

                  SEND511PATTERN - sending a 511 bit fixed test pattern

                  SEND3IN24PATTERN - sending a fixed test pattern of 3 bits set in 24

                  SENDOTHERTESTPATTERN - sending a test pattern other than those
                                         described by this object"
        DEFVAL	{ sendnocode }
        ::= { wfDs1E1ConfigEntry 8 }

    wfDs1E1ConfigCircuitIdentifier OBJECT-TYPE
        SYNTAX	DisplayString
        ACCESS	read-write
        STATUS	mandatory
        DESCRIPTION
                "This attribute is not used and appears here as a place holder only. If it
                was implemented then it would contain the transmission vendor's circuit
                identifier, for the purpose of facilitating troubleshooting."
        ::= { wfDs1E1ConfigEntry 9 }

    wfDs1E1ConfigLoopbackConfig OBJECT-TYPE
        SYNTAX	INTEGER {
    		    noloop(1),
    		    payloadloop(2),
    		    lineloop(3)
    		}
        ACCESS	read-write
        STATUS	mandatory
        DESCRIPTION
                "This variable represents the loopback configuration of the DS1 interface.
                The value NOLOOP indicates the port is not in loopback. The value
                PAYLOADLOOP indicates the port is in payload loopback which means that
                data is looped back after it goes through the framer. The value LINELOOP
                indicates the port is in line loopback which means that data is looped
                back before the framer."
        DEFVAL	{ noloop }
        ::= { wfDs1E1ConfigEntry 10 }

    wfDs1E1ConfigLineStatus OBJECT-TYPE
        SYNTAX	INTEGER {
    		    noalarm(1),
    		    rcvfarendlof(2),
    		    xmtfarendlof(4),
    		    rcvais(8),
    		    xmtais(16),
    		    lossofframe(32),
    		    lossofsignal(64),
    		    loopbackstate(128),
    		    t16ais(256),
    		    rcvfarendlomf(512),
    		    xmtfarendlomf(1024),
    		    rcvtestcode(2048),
    		    otherfailure(4096)
    		}
        ACCESS	read-only
        STATUS	mandatory
        DESCRIPTION
                "This variable is a bit-map which indicates the Line Status of the
                interface.  It contains loopback, failure, received 'alarm'  and
                transmitted 'alarm' information.

                The bit definition as as follows with bit #0 being the LSB.

                bit  0  NOALARM - No alarm present, set only when none of the other bits are.
                     1  RCVFARENDLOF - Far end LOF (a.k.a., Yellow Alarm)
                     2  XMTFARENDLOF - Near end sending LOF Indication
                     3  RCVAIS - Far end sending AIS
                     4  XMTAIS - Near end sending AIS
                     5  LOSSOFFRAME - Near end LOF (a.k.a., Red Alarm)
                     6  LOSSOFSIGNAL - Near end Loss Of Signal
                     7  LOOPBACKSTATE - Near end is looped
                     8  T16AIS - E1 only, TS16 AIS
                     9  RCVFARENDLOMF - E1 only, Far End Sending TS16 LOMF
                    10  XMTFARENDLOMF - E1 only, Near End Sending TS16 LOMF
                    11  RCVTESTCODE -  Near End detects a test code
                    12  OTHERFAILURE - any line status not defined here'
                 "
        DEFVAL	{ noalarm }
        ::= { wfDs1E1ConfigEntry 11 }

    wfDs1E1ConfigSignalMode OBJECT-TYPE
        SYNTAX	INTEGER {
    		    none(1),
    		    robbedbit(2),
    		    bitoriented(3),
    		    messageoriented(4)
    		}
        ACCESS	read-only
        STATUS	mandatory
        DESCRIPTION
                "This attribute is not implemented and exists here only as a place holder."
        DEFVAL	{ none }
        ::= { wfDs1E1ConfigEntry 12 }

    wfDs1E1ConfigTransmitClockSource OBJECT-TYPE
        SYNTAX	INTEGER {
    		    looptiming(1),
    		    localtiming(2),
    		    throughtiming(3)
    		}
        ACCESS	read-only
        STATUS	mandatory
        DESCRIPTION
                "The source of Tranmit Clock. LOOPTIMING indicates that the recovered
                receive clock is used as the transmit clock. LOCALTIMING indicates that
                a local clock source is used. Either the internal clock or the external
                clock through the extra connector on the board.  THROUGHTIMING indicates
                that recovered receive clock from another interface is used as the
                transmit clock."
        ::= { wfDs1E1ConfigEntry 13 }

    wfDs1E1ConfigFdl OBJECT-TYPE
        SYNTAX	INTEGER {
    		    ansi403(2),
    		    att54016(4),
    		    none(8)
    		}
        ACCESS	read-write
        STATUS	mandatory
        DESCRIPTION
                "This attribute is used to configure the type facilities data link (FDL).
                The ANSI403 configures the port to use the FDL exchange described in
                the ANSI T1 403 specification. ATT54016 is used to configure the port
                for the for the FDL exchange listed in the AT&T 54016 document. NONE
                is used when no FDL is desired. The FDL can only be used when the line
                type is ESF."
        DEFVAL	{ ansi403 }
        ::= { wfDs1E1ConfigEntry 14 }

    wfDs1E1ActionTable OBJECT-TYPE
        SYNTAX	SEQUENCE OF WfDs1E1ActionEntry
        ACCESS	not-accessible
        STATUS	mandatory
        DESCRIPTION
                "DS1E1 configuration Action record - Contains MUNICH32 and Framer
                write only Configuration parameters"
        ::= { wfDs1E1Group 5 }

    wfDs1E1ActionEntry OBJECT-TYPE
        SYNTAX	WfDs1E1ActionEntry
        ACCESS	not-accessible
        STATUS	mandatory
        DESCRIPTION
                "An entry in the DS1E1 Config table"
        INDEX	{ wfDs1E1ActionPortLineNumber }
        ::= { wfDs1E1ActionTable 1 }

    WfDs1E1ActionEntry ::= SEQUENCE {
    	    wfDs1E1ActionPortLineNumber
    		INTEGER,
    	    wfDs1E1ActionBertReset
    		INTEGER,
    	    wfDs1E1ActionBertErrorInsert
    		INTEGER,
    	    wfDs1E1ActionSendLoopCode
    		INTEGER,
    	    wfDs1E1ActionSendFdlLoopbackCode
		INTEGER,
	    wfDs1E1ActionSendLoopUpFractionalCode
		INTEGER,
	    wfDs1E1ActionSendLoopDownFractionalCode
		INTEGER,
	    wfDs1E1ActionClearFractionalLoopState
    		INTEGER,
	    wfDs1E1ActionClearFdlStats
		INTEGER,
	    wfDs1E1ActionClearCurrentStats
    		INTEGER,
	    wfDs1E1ActionClearFarEndCurrentStats
    		INTEGER,
	    wfDs1E1ActionClearDayCurrentStats
    		INTEGER,
	    wfDs1E1ActionClearFarEndDayCurrentStats
    		INTEGER,
	    wfDs1E1ActionClearIntervalStats
    		INTEGER,
	    wfDs1E1ActionClearFarEndIntervalStats
    		INTEGER
        }

    wfDs1E1ActionPortLineNumber OBJECT-TYPE
        SYNTAX	INTEGER
        ACCESS	read-only
        STATUS	mandatory
        DESCRIPTION
                "Instance ID LineNumber, filled in by driver"
        ::= { wfDs1E1ActionEntry 1 }

    wfDs1E1ActionBertReset OBJECT-TYPE
        SYNTAX	INTEGER {
    		    reset(1),
    		    noaction(21)
    		}
        ACCESS	read-write
        STATUS	mandatory
        DESCRIPTION
                "Reset counters on BERT device"
        DEFVAL	{ noaction }
        ::= { wfDs1E1ActionEntry 2 }

    wfDs1E1ActionBertErrorInsert OBJECT-TYPE
        SYNTAX	INTEGER {
    		    oneerror(1),
    		    errorperthousand(2),
    		    errorpermillion(3),
    		    disable(4),
    		    noaction(21)
    		}
        ACCESS	read-write
        STATUS	mandatory
        DESCRIPTION
                "Indicates that an error be injected into the transmitted data
                stream while in BERT mode."
        DEFVAL	{ noaction }
        ::= { wfDs1E1ActionEntry 3 }

    wfDs1E1ActionSendLoopCode OBJECT-TYPE
        SYNTAX	INTEGER {
    		    loopup(1),
    		    loopdown(2),
    		    noaction(21)
    		}
        ACCESS	read-write
        STATUS	mandatory
        DESCRIPTION
                "Selects a  Loop Up/Down code to be sent to the remote end"
        DEFVAL	{ noaction }
        ::= { wfDs1E1ActionEntry 4 }

    wfDs1E1ActionSendFdlLoopbackCode OBJECT-TYPE
        SYNTAX	INTEGER {
    		    lineloopci(1),
    		    lineloopia(2),
    		    lineloopib(3),
    		    deactivatell(4),
    		    payloadloop(5),
    		    deactivatepl(6),
    		    deactivateall(7),
    		    noaction(21)
    		}
        ACCESS	read-write
        STATUS	mandatory
        DESCRIPTION
                "Selects an FDL code to be sent to the remote end."
        DEFVAL	{ noaction }
        ::= { wfDs1E1ActionEntry 5 }

    wfDs1E1ActionSendLoopUpFractionalCode OBJECT-TYPE
	SYNTAX	INTEGER {
		    noaction(33)
		}
	ACCESS	read-write
	STATUS	mandatory
	DESCRIPTION
		"Selects Fractional Loop Up code to be sent to the remote end.
		Value passed through this attribute is the Logical Line number
		(1 through 24).  This feature is only supported by the QMCT1."
	DEFVAL	{ noaction }
	::= { wfDs1E1ActionEntry 6 }

    wfDs1E1ActionSendLoopDownFractionalCode OBJECT-TYPE
	SYNTAX	INTEGER {
		    noaction(33)
		}
	ACCESS	read-write
	STATUS	mandatory
	DESCRIPTION
		"Selects Fractional Loop Down code to be sent to the remote
		end. Value passed through this attribute is the Logical Line
		number (1 through 24).  This feature is only supported by the
		QMCT1."
	DEFVAL	{ noaction }
	::= { wfDs1E1ActionEntry 7 }

    wfDs1E1ActionClearFractionalLoopState OBJECT-TYPE
	SYNTAX	INTEGER {
		    noaction(33)
		}
	ACCESS	read-write
	STATUS	mandatory
	DESCRIPTION
		"Removes any Logical Line left in hardware Fractional T1
		loopback state.  The Logical Line number is passed as an
		argument.  This feature is only supported by the QMCT1."
	DEFVAL	{ noaction }
	::= { wfDs1E1ActionEntry 8 }

    wfDs1E1ActionClearFdlStats OBJECT-TYPE
	SYNTAX	INTEGER {
		    clrStats(1),
		    noaction(2)
		}
	ACCESS	read-write
	STATUS	mandatory
	DESCRIPTION
		"Clears this port's FDL Statistics.  This feature is only
		supported by the QMCT1."
	DEFVAL	{ noaction }
	::= { wfDs1E1ActionEntry 9 }

    wfDs1E1ActionClearCurrentStats OBJECT-TYPE
	SYNTAX	INTEGER {
		    clrStats(1),
		    noaction(2)
		}
	ACCESS	read-write
	STATUS	mandatory
	DESCRIPTION
		"Clears this port's Current 15 minute Statistics."
	DEFVAL	{ noaction }
	::= { wfDs1E1ActionEntry 10 }

    wfDs1E1ActionClearFarEndCurrentStats OBJECT-TYPE
	SYNTAX	INTEGER {
		    clrStats(1),
		    noaction(2)
		}
	ACCESS	read-write
	STATUS	mandatory
	DESCRIPTION
		"Clears this port's Far End, Current 15 minute Statistics."
	DEFVAL	{ noaction }
	::= { wfDs1E1ActionEntry 11 }

    wfDs1E1ActionClearDayCurrentStats OBJECT-TYPE
	SYNTAX	INTEGER {
		    clrStats(1),
		    noaction(2)
		}
	ACCESS	read-write
	STATUS	mandatory
	DESCRIPTION
		"Clears this port's Current Day Statistics."
	DEFVAL	{ noaction }
	::= { wfDs1E1ActionEntry 12 }

    wfDs1E1ActionClearFarEndDayCurrentStats OBJECT-TYPE
	SYNTAX	INTEGER {
		    clrStats(1),
		    noaction(2)
		}
	ACCESS	read-write
	STATUS	mandatory
	DESCRIPTION
		"Clears this port's Far End, Current Day Statistics."
	DEFVAL	{ noaction }
	::= { wfDs1E1ActionEntry 13 }

    wfDs1E1ActionClearIntervalStats OBJECT-TYPE
	SYNTAX	INTEGER {
		    clrStats(1),
		    noaction(2)
		}
	ACCESS	read-write
	STATUS	mandatory
	DESCRIPTION
		"Clears All Interval Statistics (15 minute and day) of this port."
	DEFVAL	{ noaction }
	::= { wfDs1E1ActionEntry 14 }

    wfDs1E1ActionClearFarEndIntervalStats OBJECT-TYPE
	SYNTAX	INTEGER {
		    clrStats(1),
		    noaction(2)
		}
	ACCESS	read-write
	STATUS	mandatory
	DESCRIPTION
		"Clears All Far End Interval Statistics (15 minute and day) of this port."
	DEFVAL	{ noaction }
	::= { wfDs1E1ActionEntry 15 }


    wfLogicalLineTable OBJECT-TYPE
        SYNTAX	SEQUENCE OF WfLogicalLineEntry
        ACCESS	not-accessible
        STATUS	mandatory
        DESCRIPTION
                "LogicalLine record - Contains configuration parameters and
                statistics for MUNICH32 which are LogicalLine specific."
        ::= { wfDs1E1Group 6 }

    wfLogicalLineEntry OBJECT-TYPE
        SYNTAX	WfLogicalLineEntry
        ACCESS	not-accessible
        STATUS	mandatory
        DESCRIPTION
                "An entry in the LOGICAL_LINE table"
        INDEX	{ wfLogicalLinePortLineNumber,
    		  wfLogicalLineIndex }
        ::= { wfLogicalLineTable 1 }

    WfLogicalLineEntry ::= SEQUENCE {
    	    wfLogicalLineDelete
    		INTEGER,
    	    wfLogicalLineDisable
    		INTEGER,
    	    wfLogicalLineState
    		INTEGER,
    	    wfLogicalLinePortLineNumber
    		INTEGER,
    	    wfLogicalLineIndex
    		INTEGER,
    	    wfLogicalLineCct
    		INTEGER,
    	    wfLogicalLineLineNumber
    		INTEGER,
    	    wfLogicalLineBofl
    		INTEGER,
    	    wfLogicalLineBoflTmo
    		INTEGER,
    	    wfLogicalLineFractionalLoopback
    		INTEGER,
    	    wfLogicalLineTimeSlotAssignment
    		DisplayString,
    	    wfLogicalLineMtu
    		INTEGER,
    	    wfLogicalLineMadr
    		OCTET STRING,
    	    wfLogicalLineWanProtocol
    		INTEGER,
    	    wfLogicalLineHdlcService
    		INTEGER,
    	    wfLogicalLineLocalHdlcAddress
    		INTEGER,
    	    wfLogicalLineRemoteHdlcAddress
    		INTEGER,
    	    wfLogicalLineRateAdaption
    		INTEGER,
    	    wfLogicalLineIFTF
    		INTEGER,
    	    wfLogicalLineCRCSize
    		INTEGER,
    	    wfLogicalLineRxOctets
    		Counter,
    	    wfLogicalLineRxFrames
    		Counter,
    	    wfLogicalLineTxOctets
    		Counter,
    	    wfLogicalLineTxFrames
    		Counter,
    	    wfLogicalLineRxErrors
    		Counter,
    	    wfLogicalLineTxErrors
    		Counter,
    	    wfLogicalLineLackRxResources
    		Counter,
    	    wfLogicalLineLackTxResources
    		Counter,
    	    wfLogicalLineTxUnderflows
    		Counter,
    	    wfLogicalLineRxOverflows
    		Counter,
    	    wfLogicalLineRxNullFrames
    		Counter,
    	    wfLogicalLineRxShortFrames
    		Counter,
    	    wfLogicalLineRxLossSyncs
    		Counter,
    	    wfLogicalLineRxCRCErrors
    		Counter,
    	    wfLogicalLineRxNonOctetBits
    		Counter,
    	    wfLogicalLineRxLongFrames
    		Counter,
    	    wfLogicalLineRxAbortFrames
    		Counter,
    	    wfLogicalLineRxDescOverflows
    		Counter,
    	    wfLogicalLineRxReplenMisses
    		Counter,
    	    wfLogicalLineRxIFCs
    		Counter,
    	    wfLogicalLineRxDropPackets
    		Counter,
    	    wfLogicalLineCfgTxQueueLength
    		INTEGER,
    	    wfLogicalLineCfgRxQueueLength
    		INTEGER,
    	    wfLogicalLineTxQueueLength
    		INTEGER,
    	    wfLogicalLineRxQueueLength
    		INTEGER,
    	    wfLogicalLineTxQueueEmpties
    		Counter,
    	    wfLogicalLineRxIntProcs
    		Counter,
    	    wfLogicalLineTxIntProcs
    		Counter,
    	    wfLogicalLineRxPktCorruptions
    		Counter,
    	    wfLogicalLineTurboBofl
    		INTEGER,
    	    wfLogicalLineBoflNum
    		INTEGER,
    	    wfLogicalLineBoflLen
    		INTEGER,
    	    wfLogicalLineOutQLen
    		Gauge,
    	    wfLogicalLineLastChange
    		TimeTicks,
    	    wfLogicalLineCfgMtu
    		INTEGER,
    	    wfLogicalLineRemoteLpbkDetection
    		INTEGER,
    	    wfLogicalLineLastState
    		INTEGER,
    	    wfLogicalLineRxIdles
    		Counter,
    	    wfLogicalLineRole
    		INTEGER,
    	    wfLogicalLineActiveCct
    		INTEGER,
    	    wfLogicalLineActualRateAdaption
		INTEGER,
	    wfLogicalLineBertMode
		INTEGER,
	    wfLogicalLineBertTestPattern
		INTEGER,
	    wfLogicalLineAcceptFracLoopCode
    		INTEGER,
            wfLogicalLineDS0AStatus
    		INTEGER,
            wfLogicalLineNRZIEnable
    		INTEGER,
            wfLogicalLineNRZIType
    		INTEGER
        }

    wfLogicalLineDelete OBJECT-TYPE
        SYNTAX	INTEGER {
    		    created(1),
    		    deleted(2)
    		}
        ACCESS	read-write
        STATUS	mandatory
        DESCRIPTION
                "Create/Delete parameter"
        DEFVAL	{ created }
        ::= { wfLogicalLineEntry 1 }

    wfLogicalLineDisable OBJECT-TYPE
        SYNTAX	INTEGER {
    		    enabled(1),
    		    disabled(2)
    		}
        ACCESS	read-write
        STATUS	mandatory
        DESCRIPTION
                "Enable/Disable parameter"
        DEFVAL	{ enabled }
        ::= { wfLogicalLineEntry 2 }

    wfLogicalLineState OBJECT-TYPE
        SYNTAX	INTEGER {
    		    up(1),
    		    down(2),
    		    init(3),
    		    lmiwait(4),
    		    loopback(5),
    		    linedieing(6),
    		    linedead(7),
    		    remoteloop(8),
    		    remotedeaf(9),
		    bert(10),
		    hwfrac(11),
		    priWait(12),
		    lineloopbofltest(19),
    		    notpresent(20)
    		}
        ACCESS	read-only
        STATUS	mandatory
        DESCRIPTION
                "Line Driver state variable"
        DEFVAL	{ notpresent }
        ::= { wfLogicalLineEntry 3 }

    wfLogicalLinePortLineNumber OBJECT-TYPE
        SYNTAX	INTEGER
        ACCESS	read-only
        STATUS	mandatory
        DESCRIPTION
                "Instance ID PortLineNumber, filled in by driver"
        ::= { wfLogicalLineEntry 4 }

    wfLogicalLineIndex OBJECT-TYPE
        SYNTAX	INTEGER
        ACCESS	read-only
        STATUS	mandatory
        DESCRIPTION
                "Index for this line instance, filled in by driver.
                The index corresponds to the position of the
                circuit, from 1 to 31, on the port."
        ::= { wfLogicalLineEntry 5 }

    wfLogicalLineCct OBJECT-TYPE
        SYNTAX	INTEGER
        ACCESS	read-write
        STATUS	mandatory
        DESCRIPTION
                "Circuit number for this line instance"
        ::= { wfLogicalLineEntry 6 }

    wfLogicalLineLineNumber OBJECT-TYPE
        SYNTAX	INTEGER
        ACCESS	read-write
        STATUS	mandatory
        DESCRIPTION
                "LineNumber for this logical line instance. This is the same line number
                contained in the PORT_TABLE with the channel field nonzero."
        ::= { wfLogicalLineEntry 7 }

    wfLogicalLineBofl OBJECT-TYPE
        SYNTAX	INTEGER {
    		    enabled(1),
    		    disabled(2)
    		}
        ACCESS	read-write
        STATUS	mandatory
        DESCRIPTION
                "Selects Breath of Life (BOFL) parameter. If selected, a BOFL
                packet is sent out on the wire as often as specifies by the
                wfLogicalLineBoflTmo parameter"
        DEFVAL	{ enabled }
        ::= { wfLogicalLineEntry 8 }

    wfLogicalLineBoflTmo OBJECT-TYPE
        SYNTAX	INTEGER(1..60)
        ACCESS	read-write
        STATUS	mandatory
        DESCRIPTION
                "Indicates the time-period between BOFL packets"
        DEFVAL	{ 5 }
        ::= { wfLogicalLineEntry 9 }

    wfLogicalLineFractionalLoopback OBJECT-TYPE
        SYNTAX	INTEGER {
    		    enabled(1),
    		    disabled(2)
    		}
        ACCESS	read-write
        STATUS	mandatory
        DESCRIPTION
                "Any Logical Line on this T1/E1 port is capable of being put into
                loopback, i.e. data coming into that circuit from the wire is
                mirrorred back onto the wire. This parameter enables or
                disables this loopback feature on any circuit."
        DEFVAL	{ disabled }
        ::= { wfLogicalLineEntry 10 }

    wfLogicalLineTimeSlotAssignment OBJECT-TYPE
        SYNTAX	DisplayString
        ACCESS	read-only
        STATUS	mandatory
        DESCRIPTION
                "Lists the time-slots which constitute this channel. Read only attribute
                that contains a  list of time-slots from 1 to 31 used by the channel"
        ::= { wfLogicalLineEntry 11 }

    wfLogicalLineMtu OBJECT-TYPE
        SYNTAX	INTEGER
        ACCESS	read-only
        STATUS	mandatory
        DESCRIPTION
                "Contains the largest frame size that can be received by the logical line.
                Anything larger than the MTU will be discarded. In all cases except when
                the wfLogicalLineWanProtocol is LAPB, this value will be the same as
                wfLogicalLineCfgMtu. In the LAPB case it will be twice wfLogicalLineCfgMtu
                with a maximum of 4608."
        ::= { wfLogicalLineEntry 12 }

    wfLogicalLineMadr OBJECT-TYPE
        SYNTAX	OCTET STRING
        ACCESS	read-only
        STATUS	mandatory
        DESCRIPTION
                "Line MAC address, fixed - line driver fills in from the 48 bit
                address stored in the serial number prom."
        ::= { wfLogicalLineEntry 13 }

    wfLogicalLineWanProtocol OBJECT-TYPE
        SYNTAX	INTEGER {
    		    standard(1),
    		    passthru(2),
    		    ppp(3),
    		    smds(4),
    		    framerelay(5),
    		    x25(6),
    		    switch(7),
    		    sw(8),
    		    atm(9),
    		    lapb(10),
                    sdlc(11)
    		}
        ACCESS	read-write
        STATUS	mandatory
        DESCRIPTION
                "WAN protocol selection is provided via this parameter. The
                supported protocols can be selected per circuit."
        DEFVAL	{ standard }
        ::= { wfLogicalLineEntry 14 }

    wfLogicalLineHdlcService OBJECT-TYPE
        SYNTAX	INTEGER {
    		    transparent(1),
    		    llc1(2)
    		}
        ACCESS	read-write
        STATUS	mandatory
        DESCRIPTION
                "HDLC Service type for this line. Transparent is raw HDLC mode, LLC1 will
                prefix the HDLC address and control fields to the frame."
        DEFVAL	{ llc1 }
        ::= { wfLogicalLineEntry 15 }

    wfLogicalLineLocalHdlcAddress OBJECT-TYPE
        SYNTAX	INTEGER {
    		    dce(1),
    		    dte(3),
    		    seven(7)
    		}
        ACCESS	read-write
        STATUS	mandatory
        DESCRIPTION
                "This attribute is only used if the Wan protocol is Wellfleet Standard
                Proprietary Point to Point.  This attribute is unused for other Wan
                protocols.

                The local HDLC address can take on values between 1 and 7. The default is
                7.  1 is refered to as DCE.  3 is refered to DTE.  All others are refered
                to as EXPLICIT.  EXPLICIT indicates that the user has explicitely selected
                the address."
        DEFVAL	{ seven }
        ::= { wfLogicalLineEntry 16 }

    wfLogicalLineRemoteHdlcAddress OBJECT-TYPE
        SYNTAX	INTEGER {
    		    dce(1),
    		    dte(3),
    		    seven(7)
    		}
        ACCESS	read-write
        STATUS	mandatory
        DESCRIPTION
                "This attribute is only used if the Wan protocol is Wellfleet Standard
                Proprietary Point to Point.  This attribute is unused for other Wan
                protocols.

                The remote HDLC address can take on values between 1 and 7. The default is
                7.  1 is refered to as DCE.  3 is refered to DTE.  All others are refered
                to as EXPLICIT.  EXPLICIT indicates that the user has explicitely selected
                the address."
        DEFVAL	{ seven }
        ::= { wfLogicalLineEntry 17 }

    wfLogicalLineRateAdaption OBJECT-TYPE
        SYNTAX	INTEGER {
    		    adaption-64k(1),
    		    adaption-56kmsb(2),
    		    adaption-56klsb(3),
    		    adaption-9dot6k(4),          
    		    adaption-19dot2k(5)          
    		}
        ACCESS	read-write
        STATUS	mandatory
        DESCRIPTION
                "Determines the number of bits and their bit positions
                within the time-slot. 64k selection uses all 8 bits in
                the time-slot. The two 56k selections use 7 of the 8
                bits in the time-slot. 56k_MSB does not use the most
                significant bit and 56k_LSB does not use the least
                significant bit in the time-slot.  If 
                the logical line is configured for DS0-A operation, rate 
                adaptions of 9.6 Kbps and 19.2 Kbps may be configured."
        DEFVAL	{ adaption-56klsb }
        ::= { wfLogicalLineEntry 18 }

    wfLogicalLineIFTF OBJECT-TYPE
        SYNTAX	INTEGER {
    		    flags(1),
    		    idles(2)
    		}
        ACCESS	read-write
        STATUS	mandatory
        DESCRIPTION
                "Determines the Interframe time fill character to be
                transmitted by the MUNICH. In case of IFTF_FLAGS, 0x7E
                is sent and in case of IFTF_IDLES 0xff is sent as the
                interframe timefill characters."
        DEFVAL	{ flags }
        ::= { wfLogicalLineEntry 19 }

    wfLogicalLineCRCSize OBJECT-TYPE
        SYNTAX	INTEGER {
    		    crc-32(1),
    		    crc-16(2)
    		}
        ACCESS	read-write
        STATUS	mandatory
        DESCRIPTION
                "Determines the CRC Size. When CRC32 is selected a 32 bit
                CRC is appended to the frame being transmitted and a 32
                bit CRC check is performed on the received frame. When
                CRC16 is selected, a 16 bit CRC is appended to the
                transmitted frame and a 16 bit CRC is performed. on the
                received frame."
        DEFVAL	{ crc-16 }
        ::= { wfLogicalLineEntry 20 }

    wfLogicalLineRxOctets OBJECT-TYPE
        SYNTAX	Counter
        ACCESS	read-only
        STATUS	mandatory
        DESCRIPTION
                "Number of octets received without error"
        ::= { wfLogicalLineEntry 21 }

    wfLogicalLineRxFrames OBJECT-TYPE
        SYNTAX	Counter
        ACCESS	read-only
        STATUS	mandatory
        DESCRIPTION
                "Number of frames received without error"
        ::= { wfLogicalLineEntry 22 }

    wfLogicalLineTxOctets OBJECT-TYPE
        SYNTAX	Counter
        ACCESS	read-only
        STATUS	mandatory
        DESCRIPTION
                "Number of octets transmitted without error"
        ::= { wfLogicalLineEntry 23 }

    wfLogicalLineTxFrames OBJECT-TYPE
        SYNTAX	Counter
        ACCESS	read-only
        STATUS	mandatory
        DESCRIPTION
                "Number of frames transmitted without error"
        ::= { wfLogicalLineEntry 24 }

    wfLogicalLineRxErrors OBJECT-TYPE
        SYNTAX	Counter
        ACCESS	read-only
        STATUS	mandatory
        DESCRIPTION
                "Number of receive errors"
        ::= { wfLogicalLineEntry 25 }

    wfLogicalLineTxErrors OBJECT-TYPE
        SYNTAX	Counter
        ACCESS	read-only
        STATUS	mandatory
        DESCRIPTION
                "Number of transmission errors"
        ::= { wfLogicalLineEntry 26 }

    wfLogicalLineLackRxResources OBJECT-TYPE
        SYNTAX	Counter
        ACCESS	read-only
        STATUS	mandatory
        DESCRIPTION
                "Number of Rx frames dropped due to lack of buffer resources"
        ::= { wfLogicalLineEntry 27 }

    wfLogicalLineLackTxResources OBJECT-TYPE
        SYNTAX	Counter
        ACCESS	read-only
        STATUS	mandatory
        DESCRIPTION
                "Number of Tx frames dropped due to lack of system resources"
        ::= { wfLogicalLineEntry 28 }

    wfLogicalLineTxUnderflows OBJECT-TYPE
        SYNTAX	Counter
        ACCESS	read-only
        STATUS	mandatory
        DESCRIPTION
                "Number of Tx frames dropped due to Transmit underflow"
        ::= { wfLogicalLineEntry 29 }

    wfLogicalLineRxOverflows OBJECT-TYPE
        SYNTAX	Counter
        ACCESS	read-only
        STATUS	mandatory
        DESCRIPTION
                "Number of Rx frames dropped due to Receive overflow"
        ::= { wfLogicalLineEntry 30 }

    wfLogicalLineRxNullFrames OBJECT-TYPE
        SYNTAX	Counter
        ACCESS	read-only
        STATUS	mandatory
        DESCRIPTION
                "Number of short frames received (with no data bytes)"
        ::= { wfLogicalLineEntry 31 }

    wfLogicalLineRxShortFrames OBJECT-TYPE
        SYNTAX	Counter
        ACCESS	read-only
        STATUS	mandatory
        DESCRIPTION
                "Number of short frames received whose length is either 1 or 2 data bytes."
        ::= { wfLogicalLineEntry 32 }

    wfLogicalLineRxLossSyncs OBJECT-TYPE
        SYNTAX	Counter
        ACCESS	read-only
        STATUS	mandatory
        DESCRIPTION
                "Loss of synchronization on receiver"
        ::= { wfLogicalLineEntry 33 }

    wfLogicalLineRxCRCErrors OBJECT-TYPE
        SYNTAX	Counter
        ACCESS	read-only
        STATUS	mandatory
        DESCRIPTION
                "CRC error received"
        ::= { wfLogicalLineEntry 34 }

    wfLogicalLineRxNonOctetBits OBJECT-TYPE
        SYNTAX	Counter
        ACCESS	read-only
        STATUS	mandatory
        DESCRIPTION
                "Non-Octet bits received in frame"
        ::= { wfLogicalLineEntry 35 }

    wfLogicalLineRxLongFrames OBJECT-TYPE
        SYNTAX	Counter
        ACCESS	read-only
        STATUS	mandatory
        DESCRIPTION
                "Frame longer than MFL received"
        ::= { wfLogicalLineEntry 36 }

    wfLogicalLineRxAbortFrames OBJECT-TYPE
        SYNTAX	Counter
        ACCESS	read-only
        STATUS	mandatory
        DESCRIPTION
                "Aborted frame received"
        ::= { wfLogicalLineEntry 37 }

    wfLogicalLineRxDescOverflows OBJECT-TYPE
        SYNTAX	Counter
        ACCESS	read-only
        STATUS	mandatory
        DESCRIPTION
                "Receive overflow on chip buffer"
        ::= { wfLogicalLineEntry 38 }

    wfLogicalLineRxReplenMisses OBJECT-TYPE
        SYNTAX	Counter
        ACCESS	read-only
        STATUS	mandatory
        DESCRIPTION
                "Count of number of packet buffer misses while attempting to
                replenish driver receive ring"
        ::= { wfLogicalLineEntry 39 }

    wfLogicalLineRxIFCs OBJECT-TYPE
        SYNTAX	Counter
        ACCESS	read-only
        STATUS	mandatory
        DESCRIPTION
                "Number of times the device detects a change of interframe time-fill
                between incomming frames."
        ::= { wfLogicalLineEntry 40 }

    wfLogicalLineRxDropPackets OBJECT-TYPE
        SYNTAX	Counter
        ACCESS	read-only
        STATUS	mandatory
        DESCRIPTION
                "Number of packets dropped after reception"
        ::= { wfLogicalLineEntry 41 }

    wfLogicalLineCfgTxQueueLength OBJECT-TYPE
        SYNTAX	INTEGER(0..512)
        ACCESS	read-write
        STATUS	mandatory
        DESCRIPTION
                "Configured Transmit Queue Length. Values other than zero over-ride
                the router selected values. A value of zero has a special meaning.
                Zero causes router based default values to be used.  All values are
                accepted.  Care should be taken not to set this to a value which is
                much greater than the default.  The default can be read out of the
                wfLoigcalLineTxQueueLength attribute when the router is running with
                this attribute set to zero.  Sets to this attribute may take up to
                one minute to take effect."
        ::= { wfLogicalLineEntry 42 }

    wfLogicalLineCfgRxQueueLength OBJECT-TYPE
        SYNTAX	INTEGER(0..512)
        ACCESS	read-write
        STATUS	mandatory
        DESCRIPTION
                "Configured Receive Queue Length. Values other than zero over-ride
                the router selected values. A value of zero has a special meaning.
                Zero cuases router based default values to be used. Values larger
                than the compiled ring size are truncated to the compiled ring
                size.  Sets to this attribute may take up to one minute to take effect."
        ::= { wfLogicalLineEntry 43 }

    wfLogicalLineTxQueueLength OBJECT-TYPE
        SYNTAX	INTEGER
        ACCESS	read-only
        STATUS	mandatory
        DESCRIPTION
                "Current hardware transmit queue length"
        ::= { wfLogicalLineEntry 44 }

    wfLogicalLineRxQueueLength OBJECT-TYPE
        SYNTAX	INTEGER
        ACCESS	read-only
        STATUS	mandatory
        DESCRIPTION
                "Current Receive queue length"
        ::= { wfLogicalLineEntry 45 }

    wfLogicalLineTxQueueEmpties OBJECT-TYPE
        SYNTAX	Counter
        ACCESS	read-only
        STATUS	mandatory
        DESCRIPTION
                "The number of times the transmit ring is found
                empty when transmitting packets"
        ::= { wfLogicalLineEntry 46 }

    wfLogicalLineRxIntProcs OBJECT-TYPE
        SYNTAX	Counter
        ACCESS	read-only
        STATUS	mandatory
        DESCRIPTION
                "DEBUG paramete - Receive Interrupt processing count"
        ::= { wfLogicalLineEntry 47 }

    wfLogicalLineTxIntProcs OBJECT-TYPE
        SYNTAX	Counter
        ACCESS	read-only
        STATUS	mandatory
        DESCRIPTION
                "DEBUG parameter - Tx interrupt processing count"
        ::= { wfLogicalLineEntry 48 }

    wfLogicalLineRxPktCorruptions OBJECT-TYPE
        SYNTAX	Counter
        ACCESS	read-only
        STATUS	mandatory
        DESCRIPTION
                "DEBUG parameter - Corruption check on receive"
        ::= { wfLogicalLineEntry 49 }

    wfLogicalLineTurboBofl OBJECT-TYPE
        SYNTAX	INTEGER {
    		    enabled(1),
    		    disabled(2)
    		}
        ACCESS	read-write
        STATUS	mandatory
        DESCRIPTION
                "DEBUG parameter - Turbo bofl enabled or disabled"
        DEFVAL	{ disabled }
        ::= { wfLogicalLineEntry 50 }

    wfLogicalLineBoflNum OBJECT-TYPE
        SYNTAX	INTEGER(1..127)
        ACCESS	read-write
        STATUS	mandatory
        DESCRIPTION
                "DEBUG parameter - Number of breath of life packets per breath
                of life"
        DEFVAL	{ 1 }
        ::= { wfLogicalLineEntry 51 }

    wfLogicalLineBoflLen OBJECT-TYPE
        SYNTAX	INTEGER(22..4450)
        ACCESS	read-write
        STATUS	mandatory
        DESCRIPTION
                "DEBUG parameter - breath of life packet length"
        DEFVAL	{ 200 }
        ::= { wfLogicalLineEntry 52 }

    wfLogicalLineOutQLen OBJECT-TYPE
        SYNTAX	Gauge
        ACCESS	read-only
        STATUS	mandatory
        DESCRIPTION
                "The instantaneous current length of the output packet queue (in packets)."
        ::= { wfLogicalLineEntry 53 }

    wfLogicalLineLastChange OBJECT-TYPE
        SYNTAX	TimeTicks
        ACCESS	read-only
        STATUS	mandatory
        DESCRIPTION
                "The value of SysUpTime at the time the interface entered it's current
                operational state (UP state).  SysUpTime is defined as the time (in
                hundredths of a second) since the network management portion of the
                system was last re-initialized.  Usually the time since boot."
        ::= { wfLogicalLineEntry 54 }

    wfLogicalLineCfgMtu OBJECT-TYPE
        SYNTAX	INTEGER(3..4608)
        ACCESS	read-write
        STATUS	mandatory
        DESCRIPTION
                "Specifies the largest frame size that can be received by the logical line.
                Anything larger than the MTU will be discarded."
        DEFVAL	{ 1600 }
        ::= { wfLogicalLineEntry 55 }

    wfLogicalLineRemoteLpbkDetection OBJECT-TYPE
        SYNTAX	INTEGER {
    		    enabled(1),
    		    disabled(2)
    		}
        ACCESS	read-write
        STATUS	mandatory
        DESCRIPTION
                "This attribute enables Remote Loopback Detection. When enabled along with
                wfLogicalLineBofl,  the device driver will detect when it is receiving its
                own BOFL packets and will bring the interface down assuming that somewhere
                down stream the link has been put into loopback. "
        DEFVAL	{ disabled }
        ::= { wfLogicalLineEntry 56 }

    wfLogicalLineLastState OBJECT-TYPE
        SYNTAX	INTEGER {
    		    up(1),
    		    down(2),
    		    init(3),
    		    lmiwait(4),
    		    loopback(5),
    		    linedieing(6),
    		    linedead(7),
    		    remoteloop(8),
    		    remotedeaf(9),
		    bert(10),
		    hwfrac(11),
		    priWait(12),
    		    notpresent(20)
    		}
        ACCESS	read-only
        STATUS	mandatory
        DESCRIPTION
                "The state which the Logical Line driver was in prior to the most recent
                re-initialization."
        ::= { wfLogicalLineEntry 57 }

    wfLogicalLineRxIdles OBJECT-TYPE
        SYNTAX	Counter
        ACCESS	read-only
        STATUS	mandatory
        DESCRIPTION
                "Number of received frames followed by ShortFrame errors reported by the
                hardware.  ShortFrame errors imediately after received frames actually
                indicates an Idle (all 1s) interframe time fill.  One ShortFrame is
                allowed per received frame without incrementing wfLogicalLineRxErrors
                or wfLogicalLineRxShortFrames.  Additional ShortFrames will not increment
                wfLogicalLineRxIdles but will increment both wfLogicalLineRxErrors and
                wfLogicalLineRxShortFrames."
        ::= { wfLogicalLineEntry 58 }

    wfLogicalLineRole OBJECT-TYPE
        SYNTAX	INTEGER {
    		    syncconnect(1),
    		    dchannel(2),
    		    bchannel(3)
    		}
        ACCESS	read-write
        STATUS	mandatory
        DESCRIPTION
                "Specifies the role of this Logical Line. This attribute directs the Logical
                Line to be either a normal permanent synchronous connection,  a Primary Rate
                ISDN 'D' channel or a Primary Rate ISDN 'B' channel."
        DEFVAL	{ syncconnect }
        ::= { wfLogicalLineEntry 59 }

    wfLogicalLineActiveCct OBJECT-TYPE
        SYNTAX	INTEGER
        ACCESS	read-only
        STATUS	mandatory
        DESCRIPTION
                "Active CCT number for this LogicalLine. Used in ISDN PRI to indicate the
                CCT of the current call in progress."
        ::= { wfLogicalLineEntry 60 }

    wfLogicalLineActualRateAdaption OBJECT-TYPE
        SYNTAX	INTEGER {
    		    adaption64k(1),
    		    adaption56kmsb(2),
    		    adaption56klsb(3),
    		    adaption9dot6k(4),          
    		    adaption19dot2k(5)          
    		}
        ACCESS	read-only
        STATUS	mandatory
        DESCRIPTION
                "Indicates the current Rate Adaption in use. This may differ from the
                configured Rate Adaption in ISDN PRI applications.  This attribute indicates
                the number of bits and their bit positions within the time-slot. 64k
                selection uses all 8 bits in the time-slot. The two 56k selections use 7 of
                the 8 bits in the time-slot. 56k_MSB does not use the most significant bit
                and 56k_LSB does not use the least significant bit in the time-slot.  If 
                the logical line is configured for DS0-A operation, rate adaptions of 
                9.6 Kbps and 19.2 Kbps may be configured."
        ::= { wfLogicalLineEntry 61 }

    wfLogicalLineBertMode OBJECT-TYPE
	SYNTAX	INTEGER {
		    enabled(1),
		    disabled(2)
		}
	ACCESS	read-write
	STATUS	mandatory
	DESCRIPTION
		"Enables BERT testing on a logical line level.  This feature is
		only supported by the QMCT1."
	DEFVAL	{ disabled }
	::= { wfLogicalLineEntry 62 }

    wfLogicalLineBertTestPattern OBJECT-TYPE
	SYNTAX	INTEGER {
		    zeros(1),
		    ones(2),
		    qrss(3),
		    two15(4),
		    two15-inv(5),
		    two20(6),
		    two23(7),
		    two23-inv(8)
		}
	ACCESS	read-write
	STATUS	mandatory
	DESCRIPTION
		"Test pattern for BERT.  This feature is only supported by the
		QMCT1."
	DEFVAL	{ ones }
	::= { wfLogicalLineEntry 63 }

    wfLogicalLineAcceptFracLoopCode OBJECT-TYPE
	SYNTAX	INTEGER {
		    enabled(1),
		    disabled(2)
	}
	ACCESS	read-write
	STATUS	mandatory
	DESCRIPTION
		"Allows logical line to accept Fractional T1 Loop Code.  This
		feature is only supported by the QMCT1."
	DEFVAL	{ enabled }
	::= { wfLogicalLineEntry 64 }


    wfLogicalLineDS0AStatus OBJECT-TYPE
	SYNTAX	INTEGER {
		    enabled(1),
		    disabled(2)
	}
	ACCESS	read-only
	STATUS	mandatory
	DESCRIPTION
		"Indicates logical line set to T1 DS0-A Subrates.  This
		feature is only supported by the QMCT1."
	DEFVAL	{ disabled }
	::= { wfLogicalLineEntry 65 }

    wfLogicalLineNRZIEnable OBJECT-TYPE
	SYNTAX	INTEGER {
		    enabled(1),
		    disabled(2)
	}
	ACCESS	read-write
	STATUS	mandatory
	DESCRIPTION
                "Allows logical line to accept T1 NRZI encoding on logical 
                Line.  This feature is only supported by the QMRT1."
	DEFVAL	{ disabled }
	::= { wfLogicalLineEntry 66 }

    wfLogicalLineNRZIType OBJECT-TYPE
	SYNTAX	INTEGER {
		    space(1),
		    mark(2)
	}
	ACCESS	read-write
	STATUS	mandatory
	DESCRIPTION
                "Defines logical line to T1 NRZI encoding as either Mark or 
                Space on logical Line.  This feature is only supported by the                  QMRT1."
	DEFVAL	{ mark }
	::= { wfLogicalLineEntry 67 }


    wfDs1E1FracTable OBJECT-TYPE
        SYNTAX	SEQUENCE OF WfDs1E1FracEntry
        ACCESS	not-accessible
        STATUS	mandatory
        DESCRIPTION
                "The DS1E1 fractional table identifies for each time-slot, the Logical
                Line to which the time-slot is currently bound."
        ::= { wfDs1E1Group 7 }

    wfDs1E1FracEntry OBJECT-TYPE
        SYNTAX	WfDs1E1FracEntry
        ACCESS	not-accessible
        STATUS	mandatory
        DESCRIPTION
                "An entry in the DS1E1 Fractional Table"
        INDEX	{ wfDs1E1FracPortLineNumber,
    		  wfDs1E1FracNumber }
        ::= { wfDs1E1FracTable 1 }

    WfDs1E1FracEntry ::= SEQUENCE {
    	    wfDs1E1FracDelete
    		INTEGER,
    	    wfDs1E1FracPortLineNumber
    		INTEGER,
    	    wfDs1E1FracNumber
    		INTEGER,
    	    wfDs1E1FracLogicalLineIndex
		INTEGER,
	    wfDs1E1FracActualLogicalLineIndex
    		INTEGER
        }

    wfDs1E1FracDelete OBJECT-TYPE
        SYNTAX	INTEGER {
    		    created(1),
    		    deleted(2)
    		}
        ACCESS	read-write
        STATUS	mandatory
        DESCRIPTION
                "Create/Delete parameter"
        DEFVAL	{ created }
        ::= { wfDs1E1FracEntry 1 }

    wfDs1E1FracPortLineNumber OBJECT-TYPE
        SYNTAX	INTEGER
        ACCESS	read-only
        STATUS	mandatory
        DESCRIPTION
                "Line number with a zero channel number field. Identifies the port"
        ::= { wfDs1E1FracEntry 2 }

    wfDs1E1FracNumber OBJECT-TYPE
        SYNTAX	INTEGER
        ACCESS	read-only
        STATUS	mandatory
        DESCRIPTION
                "The time slot to be assigned"
        ::= { wfDs1E1FracEntry 3 }

    wfDs1E1FracLogicalLineIndex OBJECT-TYPE
        SYNTAX	INTEGER
        ACCESS	read-write
        STATUS	mandatory
        DESCRIPTION
                "This time slot is assigned to the Logical Line identified by this
                attribute."
        ::= { wfDs1E1FracEntry 4 }

    wfDs1E1FracActualLogicalLineIndex OBJECT-TYPE
	SYNTAX	INTEGER
	ACCESS	read-only
	STATUS	mandatory
	DESCRIPTION
		"This time slot can be manipulated by ISDN PRI Multi-Rate service.
		This is the logical line to which the time slot is currently
		allocated."
	::= { wfDs1E1FracEntry 5 }

    wfDs1E1CurrentTable OBJECT-TYPE
        SYNTAX	SEQUENCE OF WfDs1E1CurrentEntry
        ACCESS	not-accessible
        STATUS	mandatory
        DESCRIPTION
                "Current AT&T FDL stats table."
        ::= { wfDs1E1Group 10 }

    wfDs1E1CurrentEntry OBJECT-TYPE
        SYNTAX	WfDs1E1CurrentEntry
        ACCESS	not-accessible
        STATUS	mandatory
        DESCRIPTION
                "An entry in the DS1E1 Current table"
        INDEX	{ wfDs1E1CurrentPortLineNumber }
        ::= { wfDs1E1CurrentTable 1 }

    WfDs1E1CurrentEntry ::= SEQUENCE {
    	    wfDs1E1CurrentPortLineNumber
    		INTEGER,
    	    wfDs1E1CurrentESs
    		Gauge,
    	    wfDs1E1CurrentSESs
    		Gauge,
    	    wfDs1E1CurrentSEFSs
    		Gauge,
    	    wfDs1E1CurrentUASs
    		Gauge,
    	    wfDs1E1CurrentCSSs
    		Gauge,
    	    wfDs1E1CurrentPCVs
    		Gauge,
    	    wfDs1E1CurrentLESs
    		Gauge,
    	    wfDs1E1CurrentBESs
    		Gauge,
    	    wfDs1E1CurrentDMs
    		Gauge,
    	    wfDs1E1CurrentLCVs
    		Gauge,
    	    wfDs1E1CurrentSASs
    		Gauge,
    	    wfDs1E1CurrentAISSs
    		Gauge,
    	    wfDs1E1CurrentFCs
    		Gauge,
    	    wfDs1E1CurrentTimeElapsed
    		INTEGER,
	    wfDs1E1CurrentValidIntervals
		INTEGER,
	    wfDs1E1CurrentValidFlag
		INTEGER
        }

    wfDs1E1CurrentPortLineNumber OBJECT-TYPE
        SYNTAX	INTEGER
        ACCESS	read-only
        STATUS	mandatory
        DESCRIPTION
                "The instance ID that identifies the port. The port line number with a zero
                channel number field as found in the port map table."
        ::= { wfDs1E1CurrentEntry 1 }

    wfDs1E1CurrentESs OBJECT-TYPE
        SYNTAX	Gauge
        ACCESS	read-only
        STATUS	mandatory
        DESCRIPTION
                "The number of Errored Seconds, encountered by a DS1 interface in the
                current 15 minute interval."
        ::= { wfDs1E1CurrentEntry 2 }

    wfDs1E1CurrentSESs OBJECT-TYPE
        SYNTAX	Gauge
        ACCESS	read-only
        STATUS	mandatory
        DESCRIPTION
                "The number of Severely Errored Seconds encountered by a DS1 interface
                in the current 15 minute interval.'"
        ::= { wfDs1E1CurrentEntry 3 }

    wfDs1E1CurrentSEFSs OBJECT-TYPE
        SYNTAX	Gauge
        ACCESS	read-only
        STATUS	mandatory
        DESCRIPTION
                "The number of Severely Errored Framing Seconds encountered  by  a DS1
                interface in the current 15 minute interval."
        ::= { wfDs1E1CurrentEntry 4 }

    wfDs1E1CurrentUASs OBJECT-TYPE
        SYNTAX	Gauge
        ACCESS	read-only
        STATUS	mandatory
        DESCRIPTION
                "The number of Unavailable Seconds encountered by a DS1 interface in the
                current 15 minute interval."
        ::= { wfDs1E1CurrentEntry 5 }

    wfDs1E1CurrentCSSs OBJECT-TYPE
        SYNTAX	Gauge
        ACCESS	read-only
        STATUS	mandatory
        DESCRIPTION
                "The number of Controlled Slip Seconds encountered by a DS1 interface in the
                current 15 minute interval."
        ::= { wfDs1E1CurrentEntry 6 }

    wfDs1E1CurrentPCVs OBJECT-TYPE
        SYNTAX	Gauge
        ACCESS	read-only
        STATUS	mandatory
        DESCRIPTION
                "The number of Path Coding Violations encountered by a DS1 interface in the
                current 15 minute interval."
        ::= { wfDs1E1CurrentEntry 7 }

    wfDs1E1CurrentLESs OBJECT-TYPE
        SYNTAX	Gauge
        ACCESS	read-only
        STATUS	mandatory
        DESCRIPTION
                "The number of Line Errored Seconds encountered by a DS1 interface in the
                current 15 minute interval.'"
        ::= { wfDs1E1CurrentEntry 8 }

    wfDs1E1CurrentBESs OBJECT-TYPE
        SYNTAX	Gauge
        ACCESS	read-only
        STATUS	mandatory
        DESCRIPTION
                "The number of Bursty Errored Seconds (BESs) encountered by a DS1 interface
                in the current 15 minute interval."
        ::= { wfDs1E1CurrentEntry 9 }

    wfDs1E1CurrentDMs OBJECT-TYPE
        SYNTAX	Gauge
        ACCESS	read-only
        STATUS	mandatory
        DESCRIPTION
                "The number of Degraded Minutes (DMs) encountered by a DS1 interface in
                the current 15 minute interval.'"
        ::= { wfDs1E1CurrentEntry 10 }

    wfDs1E1CurrentLCVs OBJECT-TYPE
        SYNTAX	Gauge
        ACCESS	read-only
        STATUS	mandatory
        DESCRIPTION
                "The number of Line Code Violations (LCVs) encountered  by a DS1 interface in
                the current 15  minute interval.'"
        ::= { wfDs1E1CurrentEntry 11 }

    wfDs1E1CurrentSASs OBJECT-TYPE
        SYNTAX	Gauge
        ACCESS	read-only
        STATUS	mandatory
        DESCRIPTION
                "The number of seconds, within the current 15 minute interval,
		containing one or more SEFs or AIS defects."
        ::= { wfDs1E1CurrentEntry 12 }

    wfDs1E1CurrentAISSs OBJECT-TYPE
        SYNTAX	Gauge
        ACCESS	read-only
        STATUS	mandatory
        DESCRIPTION
                "The number of seconds, within the current 15 minute interval,
		 containing one or more AIS defect."
        ::= { wfDs1E1CurrentEntry 13 }

    wfDs1E1CurrentFCs OBJECT-TYPE
        SYNTAX	Gauge
        ACCESS	read-only
        STATUS	mandatory
        DESCRIPTION
                "The number of Path Failure Count error events detected
                in the current 15  minute interval."
        ::= { wfDs1E1CurrentEntry 14 }

    wfDs1E1CurrentTimeElapsed OBJECT-TYPE
        SYNTAX	INTEGER
        ACCESS	read-only
        STATUS	mandatory
        DESCRIPTION
                "The number of seconds that have elapsed since the beginning of the
                current error-measurement period."
        ::= { wfDs1E1CurrentEntry 15 }

    wfDs1E1CurrentValidIntervals OBJECT-TYPE
        SYNTAX	INTEGER
        ACCESS	read-only
        STATUS	mandatory
        DESCRIPTION
                "The number of previous intervals for which valid data was collected. The
                value will be 96 unless the interface was brought on-line within the last
                24 hours, in which case the value will be the number of complete 15 minute
                intervals the since interface has been online."
        ::= { wfDs1E1CurrentEntry 16 }

    wfDs1E1CurrentValidFlag OBJECT-TYPE
        SYNTAX	INTEGER {
    		    valid(1),
    		    invalid(2)
    		}
        ACCESS	read-only
        STATUS	mandatory
        DESCRIPTION
                "Indicates whether this interval reported by the Mib Table is valid or
		invalid."
        DEFVAL	{ valid }
        ::= { wfDs1E1CurrentEntry 17 }


    wfDs1E1IntervalTable OBJECT-TYPE
        SYNTAX	SEQUENCE OF WfDs1E1IntervalEntry
        ACCESS	not-accessible
        STATUS	mandatory
        DESCRIPTION
                "AT&T Interval stats"
        ::= { wfDs1E1Group 11 }

    wfDs1E1IntervalEntry OBJECT-TYPE
        SYNTAX	WfDs1E1IntervalEntry
        ACCESS	not-accessible
        STATUS	mandatory
        DESCRIPTION
                "An entry in the DS1E1 Interval table"
        INDEX	{ wfDs1E1IntervalPortLineNumber,
    		  wfDs1E1IntervalNumber }
        ::= { wfDs1E1IntervalTable 1 }

    WfDs1E1IntervalEntry ::= SEQUENCE {
    	    wfDs1E1IntervalPortLineNumber
    		INTEGER,
    	    wfDs1E1IntervalNumber
    		INTEGER,
    	    wfDs1E1IntervalESs
    		Gauge,
    	    wfDs1E1IntervalSESs
    		Gauge,
    	    wfDs1E1IntervalSEFSs
    		Gauge,
    	    wfDs1E1IntervalUASs
    		Gauge,
    	    wfDs1E1IntervalCSSs
    		Gauge,
    	    wfDs1E1IntervalPCVs
    		Gauge,
    	    wfDs1E1IntervalLESs
    		Gauge,
    	    wfDs1E1IntervalBESs
    		Gauge,
    	    wfDs1E1IntervalDMs
    		Gauge,
    	    wfDs1E1IntervalLCVs
    		Gauge,
    	    wfDs1E1IntervalSASs
    		Gauge,
    	    wfDs1E1IntervalAISSs
    		Gauge,
    	    wfDs1E1IntervalFCs
    		Gauge,
	    wfDs1E1IntervalValidFlag
		INTEGER
        }

    wfDs1E1IntervalPortLineNumber OBJECT-TYPE
        SYNTAX	INTEGER
        ACCESS	read-only
        STATUS	mandatory
        DESCRIPTION
                "The instance ID that identifies the port. The port line number with a zero
                channel number field as found in the port map table."
        ::= { wfDs1E1IntervalEntry 1 }

    wfDs1E1IntervalNumber OBJECT-TYPE
        SYNTAX	INTEGER
        ACCESS	read-only
        STATUS	mandatory
        DESCRIPTION
                "A number between 1 and 96, where 1 is the most recently completed 15 minute
                interval and 96 is the least recently completed 15 minutes  interval (assuming
                that all 96 intervals are valid)."
        ::= { wfDs1E1IntervalEntry 2 }

    wfDs1E1IntervalESs OBJECT-TYPE
        SYNTAX	Gauge
        ACCESS	read-only
        STATUS	mandatory
        DESCRIPTION
                "The number of Errored Seconds, encountered by a DS1 interface in the current
                15 minute interval."
        ::= { wfDs1E1IntervalEntry 3 }

    wfDs1E1IntervalSESs OBJECT-TYPE
        SYNTAX	Gauge
        ACCESS	read-only
        STATUS	mandatory
        DESCRIPTION
                "The number of Severely Errored Seconds encountered by a DS1 interface in one
                of the previous 15 minute intervals."
        ::= { wfDs1E1IntervalEntry 4 }

    wfDs1E1IntervalSEFSs OBJECT-TYPE
        SYNTAX	Gauge
        ACCESS	read-only
        STATUS	mandatory
        DESCRIPTION
                "The number of Severely Errored Framing Seconds encountered by a DS1 interface
                in one of the previous 15 minute intervals."
        ::= { wfDs1E1IntervalEntry 5 }

    wfDs1E1IntervalUASs OBJECT-TYPE
        SYNTAX	Gauge
        ACCESS	read-only
        STATUS	mandatory
        DESCRIPTION
                "The number of Unavailable Seconds encountered by a DS1 interface in one of the
                previous 15 minute intervals."
        ::= { wfDs1E1IntervalEntry 6 }

    wfDs1E1IntervalCSSs OBJECT-TYPE
        SYNTAX	Gauge
        ACCESS	read-only
        STATUS	mandatory
        DESCRIPTION
                "The number of Controlled Slip Seconds encountered by a DS1 interface in one
                of the previous 15 minute intervals."
        ::= { wfDs1E1IntervalEntry 7 }

    wfDs1E1IntervalPCVs OBJECT-TYPE
        SYNTAX	Gauge
        ACCESS	read-only
        STATUS	mandatory
        DESCRIPTION
                "The number of Path Coding Violations encountered by a DS1 interface in one of
                the previous 15 minute intervals."
        ::= { wfDs1E1IntervalEntry 8 }

    wfDs1E1IntervalLESs OBJECT-TYPE
        SYNTAX	Gauge
        ACCESS	read-only
        STATUS	mandatory
        DESCRIPTION
                "The number of Line Errored Seconds encountered by a DS1 interface in one of
                the previous 15 minute intervals."
        ::= { wfDs1E1IntervalEntry 9 }

    wfDs1E1IntervalBESs OBJECT-TYPE
        SYNTAX	Gauge
        ACCESS	read-only
        STATUS	mandatory
        DESCRIPTION
                "The number of Bursty Errored Seconds (BESs) encountered by a DS1 interface in
                one of the previous 15 minute intervals."
        ::= { wfDs1E1IntervalEntry 10 }

    wfDs1E1IntervalDMs OBJECT-TYPE
        SYNTAX	Gauge
        ACCESS	read-only
        STATUS	mandatory
        DESCRIPTION
                "The number of Degraded Minutes (DMs) encountered by a DS1 interface in one of
                the previous 15 minute intervals."
        ::= { wfDs1E1IntervalEntry 11 }

    wfDs1E1IntervalLCVs OBJECT-TYPE
        SYNTAX	Gauge
        ACCESS	read-only
        STATUS	mandatory
        DESCRIPTION
                "The number of Line Code Violations (LCVs) encountered by a DS1 interface in
                one of the previous 15 minute intervals."
        ::= { wfDs1E1IntervalEntry 12 }

    wfDs1E1IntervalSASs OBJECT-TYPE
        SYNTAX	Gauge
        ACCESS	read-only
        STATUS	mandatory
        DESCRIPTION
                "The number of seconds, in one of the previous 15 minute intervals,
		containing one or more SEFs or AIS defects."
        ::= { wfDs1E1IntervalEntry 13 }

    wfDs1E1IntervalAISSs OBJECT-TYPE
        SYNTAX	Gauge
        ACCESS	read-only
        STATUS	mandatory
        DESCRIPTION
                "The number of seconds, in one of the previous 15 minute intervals,
		 containing one or more AIS defect."
        ::= { wfDs1E1IntervalEntry 14 }

    wfDs1E1IntervalFCs OBJECT-TYPE
        SYNTAX	Gauge
        ACCESS	read-only
        STATUS	mandatory
        DESCRIPTION
                "The number of Path Failure Count error events detected
		one of the previous 15 minute intervals."
        ::= { wfDs1E1IntervalEntry 15 }

    wfDs1E1IntervalValidFlag OBJECT-TYPE
        SYNTAX	INTEGER {
    		    valid(1),
    		    invalid(2)
    		}
        ACCESS	read-only
        STATUS	mandatory
        DESCRIPTION
                "Indicates whether this interval reported by the Mib Table is valid or
		invalid."
        DEFVAL	{ valid }
        ::= { wfDs1E1IntervalEntry 16 }


    wfDs1E1TotalTable OBJECT-TYPE
        SYNTAX	SEQUENCE OF WfDs1E1TotalEntry
        ACCESS	not-accessible
        STATUS	mandatory
        DESCRIPTION
                "AT&T Total stats Table"
        ::= { wfDs1E1Group 12 }

    wfDs1E1TotalEntry OBJECT-TYPE
        SYNTAX	WfDs1E1TotalEntry
        ACCESS	not-accessible
        STATUS	mandatory
        DESCRIPTION
                "An entry in the DS1E1 Total table"
        INDEX	{ wfDs1E1TotalPortLineNumber }
        ::= { wfDs1E1TotalTable 1 }

    WfDs1E1TotalEntry ::= SEQUENCE {
    	    wfDs1E1TotalPortLineNumber
    		INTEGER,
    	    wfDs1E1TotalESs
    		Gauge,
    	    wfDs1E1TotalSESs
    		Gauge,
    	    wfDs1E1TotalSEFSs
    		Gauge,
    	    wfDs1E1TotalUASs
    		Gauge,
    	    wfDs1E1TotalCSSs
    		Gauge,
    	    wfDs1E1TotalPCVs
    		Gauge,
    	    wfDs1E1TotalLESs
    		Gauge,
    	    wfDs1E1TotalBESs
    		Gauge,
    	    wfDs1E1TotalDMs
    		Gauge,
    	    wfDs1E1TotalLCVs
    		Gauge,
    	    wfDs1E1TotalSASs
    		Gauge,
    	    wfDs1E1TotalAISSs
    		Gauge,
    	    wfDs1E1TotalFCs
    		Gauge,
	    wfDs1E1TotalValidFlag
		INTEGER
        }

    wfDs1E1TotalPortLineNumber OBJECT-TYPE
        SYNTAX	INTEGER
        ACCESS	read-only
        STATUS	mandatory
        DESCRIPTION
                "The instance ID that identifies the port. The port line number with a zero
                channel number field as found in the port map table."
        ::= { wfDs1E1TotalEntry 1 }

    wfDs1E1TotalESs OBJECT-TYPE
        SYNTAX	Gauge
        ACCESS	read-only
        STATUS	mandatory
        DESCRIPTION
                "The number of Errored Seconds, encountered by a DS1 interface in the current
                15 minute interval."
        ::= { wfDs1E1TotalEntry 2 }

    wfDs1E1TotalSESs OBJECT-TYPE
        SYNTAX	Gauge
        ACCESS	read-only
        STATUS	mandatory
        DESCRIPTION
                "The number of Severely Errored Seconds encountered by a DS1 interface in the
                previous 24-hour interval."
        ::= { wfDs1E1TotalEntry 3 }

    wfDs1E1TotalSEFSs OBJECT-TYPE
        SYNTAX	Gauge
        ACCESS	read-only
        STATUS	mandatory
        DESCRIPTION
                "The number of Severely Errored Framing Seconds encountered by a DS1 interface
                in the previous 24-hour interval."
        ::= { wfDs1E1TotalEntry 4 }

    wfDs1E1TotalUASs OBJECT-TYPE
        SYNTAX	Gauge
        ACCESS	read-only
        STATUS	mandatory
        DESCRIPTION
                "The number of Unavailable Seconds encountered by a DS1 interface in the
                previous 24-hour interval."
        ::= { wfDs1E1TotalEntry 5 }

    wfDs1E1TotalCSSs OBJECT-TYPE
        SYNTAX	Gauge
        ACCESS	read-only
        STATUS	mandatory
        DESCRIPTION
                "The number of Controlled Slip Seconds encountered by a DS1 interface in the
                previous 24-hour interval."
        ::= { wfDs1E1TotalEntry 6 }

    wfDs1E1TotalPCVs OBJECT-TYPE
        SYNTAX	Gauge
        ACCESS	read-only
        STATUS	mandatory
        DESCRIPTION
                "The number of Path Coding Violations encountered by a DS1 interface in the
                previous 24-hour interval."
        ::= { wfDs1E1TotalEntry 7 }

    wfDs1E1TotalLESs OBJECT-TYPE
        SYNTAX	Gauge
        ACCESS	read-only
        STATUS	mandatory
        DESCRIPTION
                "The number of Line Errored Seconds encountered by a DS1 interface in the
                previous 24-hour interval."
        ::= { wfDs1E1TotalEntry 8 }

    wfDs1E1TotalBESs OBJECT-TYPE
        SYNTAX	Gauge
        ACCESS	read-only
        STATUS	mandatory
        DESCRIPTION
                "The number of Bursty Errored Seconds (BESs) encountered by a DS1 interface
                in the previous 24-hour interval."
        ::= { wfDs1E1TotalEntry 9 }

    wfDs1E1TotalDMs OBJECT-TYPE
        SYNTAX	Gauge
        ACCESS	read-only
        STATUS	mandatory
        DESCRIPTION
                "The number of Degraded Minutes (DMs) encountered by a DS1 interface in the
                previous 24-hour interval."
        ::= { wfDs1E1TotalEntry 10 }

    wfDs1E1TotalLCVs OBJECT-TYPE
        SYNTAX	Gauge
        ACCESS	read-only
        STATUS	mandatory
        DESCRIPTION
                "The number of Line Code Violations (LCVs) encountered  by a DS1 interface in
                the previous 24-hour interval."
        ::= { wfDs1E1TotalEntry 11 }

    wfDs1E1TotalSASs OBJECT-TYPE
        SYNTAX	Gauge
        ACCESS	read-only
        STATUS	mandatory
        DESCRIPTION
                "The number of seconds, in the previous 24-hour interval,
		containing one or more SEFs or AIS defects."
        ::= { wfDs1E1TotalEntry 12 }

    wfDs1E1TotalAISSs OBJECT-TYPE
        SYNTAX	Gauge
        ACCESS	read-only
        STATUS	mandatory
        DESCRIPTION
                "The number of seconds, in the previous 24-hour interval,
		 containing one or more AIS defect."
        ::= { wfDs1E1TotalEntry 13 }

    wfDs1E1TotalFCs OBJECT-TYPE
        SYNTAX	Gauge
        ACCESS	read-only
        STATUS	mandatory
        DESCRIPTION
                "The number of Path Failure Count error events detected
		in the previous 24-hour interval."
        ::= { wfDs1E1TotalEntry 14 }

    wfDs1E1TotalValidFlag OBJECT-TYPE
        SYNTAX	INTEGER {
    		    valid(1),
    		    invalid(2)
    		}
        ACCESS	read-only
        STATUS	mandatory
        DESCRIPTION
                "Indicates whether this interval reported by the Mib Table is valid or
		invalid."
        DEFVAL	{ valid }
        ::= { wfDs1E1TotalEntry 15 }


    wfDs1E1AnsiTable OBJECT-TYPE
        SYNTAX	SEQUENCE OF WfDs1E1AnsiEntry
        ACCESS	not-accessible
        STATUS	mandatory
        DESCRIPTION
                "ANSI Statistics line record - This table contains the
                performance parameters for the ANSI register set "
        ::= { wfMcT1Group 13 }

    wfDs1E1AnsiEntry OBJECT-TYPE
        SYNTAX	WfDs1E1AnsiEntry
        ACCESS	not-accessible
        STATUS	mandatory
        DESCRIPTION
                "An entry in the DS1E1 Ansi table"
        INDEX	{ wfDs1E1AnsiPortLineNumber }
        ::= { wfDs1E1AnsiTable 1 }

    WfDs1E1AnsiEntry ::= SEQUENCE {
    	    wfDs1E1AnsiPortLineNumber
    		INTEGER,
    	    wfDs1E1AnsiCRCCounts
    		Counter,
    	    wfDs1E1AnsiBPVCounts
    		Counter,
    	    wfDs1E1AnsiOOFCounts
    		Counter,
    	    wfDs1E1AnsiFECounts
    		Counter,
    	    wfDs1E1AnsiESCounts
    		Counter,
    	    wfDs1E1AnsiSESCounts
    		Counter,
    	    wfDs1E1AnsiUASCounts
    		Counter,
    	    wfDs1E1AnsiPRMR0Counts
    		Counter,
    	    wfDs1E1AnsiPRMR1Counts
    		Counter,
    	    wfDs1E1AnsiPRMR2Counts
    		Counter,
    	    wfDs1E1AnsiPRMR3Counts
    		Counter,
    	    wfDs1E1AnsiPRMESCounts
    		Counter,
    	    wfDs1E1AnsiPRMSESCounts
    		Counter,
    	    wfDs1E1AnsiPRMECounts
    		Counter
        }

    wfDs1E1AnsiPortLineNumber OBJECT-TYPE
        SYNTAX	INTEGER
        ACCESS	read-only
        STATUS	mandatory
        DESCRIPTION
                "Instance ID Slot, filled in by driver"
        ::= { wfDs1E1AnsiEntry 1 }

    wfDs1E1AnsiCRCCounts OBJECT-TYPE
        SYNTAX	Counter
        ACCESS	read-only
        STATUS	mandatory
        DESCRIPTION
                "Counts CRC-6 error events"
        ::= { wfDs1E1AnsiEntry 2 }

    wfDs1E1AnsiBPVCounts OBJECT-TYPE
        SYNTAX	Counter
        ACCESS	read-only
        STATUS	mandatory
        DESCRIPTION
                "Counts bipolar violations"
        ::= { wfDs1E1AnsiEntry 3 }

    wfDs1E1AnsiOOFCounts OBJECT-TYPE
        SYNTAX	Counter
        ACCESS	read-only
        STATUS	mandatory
        DESCRIPTION
                "Counts out-of-frame error events"
        ::= { wfDs1E1AnsiEntry 4 }

    wfDs1E1AnsiFECounts OBJECT-TYPE
        SYNTAX	Counter
        ACCESS	read-only
        STATUS	mandatory
        DESCRIPTION
                "Counts errors in the FPS framing pattern"
        ::= { wfDs1E1AnsiEntry 5 }

    wfDs1E1AnsiESCounts OBJECT-TYPE
        SYNTAX	Counter
        ACCESS	read-only
        STATUS	mandatory
        DESCRIPTION
                "Counts errorred seconds"
        ::= { wfDs1E1AnsiEntry 6 }

    wfDs1E1AnsiSESCounts OBJECT-TYPE
        SYNTAX	Counter
        ACCESS	read-only
        STATUS	mandatory
        DESCRIPTION
                "Counts severly errorred seconds"
        ::= { wfDs1E1AnsiEntry 7 }

    wfDs1E1AnsiUASCounts OBJECT-TYPE
        SYNTAX	Counter
        ACCESS	read-only
        STATUS	mandatory
        DESCRIPTION
                "counts unavailable seconds"
        ::= { wfDs1E1AnsiEntry 8 }

    wfDs1E1AnsiPRMR0Counts OBJECT-TYPE
        SYNTAX	Counter
        ACCESS	read-only
        STATUS	mandatory
        DESCRIPTION
                "Counts PRMs that ewre received in the FDL in
                the last four seconds"
        ::= { wfDs1E1AnsiEntry 9 }

    wfDs1E1AnsiPRMR1Counts OBJECT-TYPE
        SYNTAX	Counter
        ACCESS	read-only
        STATUS	mandatory
        DESCRIPTION
                "Counts PRMs that ewre received in the FDL in
                the last four seconds"
        ::= { wfDs1E1AnsiEntry 10 }

    wfDs1E1AnsiPRMR2Counts OBJECT-TYPE
        SYNTAX	Counter
        ACCESS	read-only
        STATUS	mandatory
        DESCRIPTION
                "Counts PRMs that ewre received in the FDL in
                the last four seconds"
        ::= { wfDs1E1AnsiEntry 11 }

    wfDs1E1AnsiPRMR3Counts OBJECT-TYPE
        SYNTAX	Counter
        ACCESS	read-only
        STATUS	mandatory
        DESCRIPTION
                "Counts PRMs that ewre received in the FDL in
                the last four seconds"
        ::= { wfDs1E1AnsiEntry 12 }

    wfDs1E1AnsiPRMESCounts OBJECT-TYPE
        SYNTAX	Counter
        ACCESS	read-only
        STATUS	mandatory
        DESCRIPTION
                "Counts errorred seconds as reported in the Performance
                report messages"
        ::= { wfDs1E1AnsiEntry 13 }

    wfDs1E1AnsiPRMSESCounts OBJECT-TYPE
        SYNTAX	Counter
        ACCESS	read-only
        STATUS	mandatory
        DESCRIPTION
                "Counts severely errorred seconds as reported in the
                Performance report messages"
        ::= { wfDs1E1AnsiEntry 14 }

    wfDs1E1AnsiPRMECounts OBJECT-TYPE
        SYNTAX	Counter
        ACCESS	read-only
        STATUS	mandatory
        DESCRIPTION
                "Counts Performance report messages that are received
                in error"
        ::= { wfDs1E1AnsiEntry 15 }

    wfDs1E1BertStatsTable OBJECT-TYPE
        SYNTAX	SEQUENCE OF WfDs1E1BertStatsEntry
        ACCESS	not-accessible
        STATUS	mandatory
        DESCRIPTION
                "BERT Counter line record - This table contains the
                statistics for the BERT tester."
        ::= { wfDs1E1Group 14 }

    wfDs1E1BertStatsEntry OBJECT-TYPE
        SYNTAX	WfDs1E1BertStatsEntry
        ACCESS	not-accessible
        STATUS	mandatory
        DESCRIPTION
                "An entry in the DS1E1 Bert Stats table"
        INDEX	{ wfDs1E1BertStatsPortLineNumber }
        ::= { wfDs1E1BertStatsTable 1 }

    WfDs1E1BertStatsEntry ::= SEQUENCE {
    	    wfDs1E1BertStatsPortLineNumber
    		INTEGER,
    	    wfDs1E1BertStatsBitErrors
    		Counter,
    	    wfDs1E1BertStatsBits
    		Counter
        }

    wfDs1E1BertStatsPortLineNumber OBJECT-TYPE
        SYNTAX	INTEGER
        ACCESS	read-only
        STATUS	mandatory
        DESCRIPTION
                "Instance ID Slot, filled in by driver"
        ::= { wfDs1E1BertStatsEntry 1 }

    wfDs1E1BertStatsBitErrors OBJECT-TYPE
        SYNTAX	Counter
        ACCESS	read-only
        STATUS	mandatory
        DESCRIPTION
                "Bit error counter"
        ::= { wfDs1E1BertStatsEntry 2 }

    wfDs1E1BertStatsBits OBJECT-TYPE
        SYNTAX	Counter
        ACCESS	read-only
        STATUS	mandatory
        DESCRIPTION
                "Bit counter"
        ::= { wfDs1E1BertStatsEntry 3 }

    wfDs1E1CurrentFramerStatsTable OBJECT-TYPE
        SYNTAX	SEQUENCE OF WfDs1E1CurrentFramerStatsEntry
        ACCESS	not-accessible
        STATUS	mandatory
        DESCRIPTION
                "Framer stats line record - This table contains the
                statistics for the Framer tester."
        ::= { wfDs1E1Group 15 }

    wfDs1E1CurrentFramerStatsEntry OBJECT-TYPE
        SYNTAX	WfDs1E1CurrentFramerStatsEntry
        ACCESS	not-accessible
        STATUS	mandatory
        DESCRIPTION
                "An entry in the DS1E1 CurrentFramer Stats table"
        INDEX	{ wfDs1E1CurrentFramerStatsPortLineNumber }
        ::= { wfDs1E1CurrentFramerStatsTable 1 }

    WfDs1E1CurrentFramerStatsEntry ::= SEQUENCE {
    	    wfDs1E1CurrentFramerStatsPortLineNumber
    		INTEGER,
    	    wfDs1E1CurrentFramerStatsMediaType
    		INTEGER,
    	    wfDs1E1CurrentFramerStatsBpvCounts
    		Gauge,
    	    wfDs1E1CurrentFramerStatsCrc4Counts
    		Gauge,
    	    wfDs1E1CurrentFramerStatsFebeCounts
    		Gauge,
    	    wfDs1E1CurrentFramerStatsOofCounts
    		Gauge,
    	    wfDs1E1CurrentFramerStatsFeCounts
    		Gauge,
    	    wfDs1E1CurrentFramerStatsLossFrameFailures
    		Gauge,
    	    wfDs1E1CurrentFramerStatsLossSignalFailures
    		Gauge,
    	    wfDs1E1CurrentFramerStatsAlarmIndicationFailures
    		Gauge,
    	    wfDs1E1CurrentFramerStatsRemoteAlarmFailures
    		Gauge
        }

    wfDs1E1CurrentFramerStatsPortLineNumber OBJECT-TYPE
        SYNTAX	INTEGER
        ACCESS	read-only
        STATUS	mandatory
        DESCRIPTION
                "Instance ID Slot, filled in by driver"
        ::= { wfDs1E1CurrentFramerStatsEntry 1 }

    wfDs1E1CurrentFramerStatsMediaType OBJECT-TYPE
        SYNTAX	INTEGER {
    		    t1(1),
    		    e1(2)
    		}
        ACCESS	read-only
        STATUS	mandatory
        DESCRIPTION
                "The media type is either T1 or E1"
        ::= { wfDs1E1CurrentFramerStatsEntry 2 }

    wfDs1E1CurrentFramerStatsBpvCounts OBJECT-TYPE
        SYNTAX	Gauge
        ACCESS	read-only
        STATUS	mandatory
        DESCRIPTION
                "bipolar violations counter"
        ::= { wfDs1E1CurrentFramerStatsEntry 3 }

    wfDs1E1CurrentFramerStatsCrc4Counts OBJECT-TYPE
        SYNTAX	Gauge
        ACCESS	read-only
        STATUS	mandatory
        DESCRIPTION
                "CRC4 error counter"
        ::= { wfDs1E1CurrentFramerStatsEntry 4 }

    wfDs1E1CurrentFramerStatsFebeCounts OBJECT-TYPE
        SYNTAX	Gauge
        ACCESS	read-only
        STATUS	mandatory
        DESCRIPTION
                "Far End Block Error counter"
        ::= { wfDs1E1CurrentFramerStatsEntry 5 }

    wfDs1E1CurrentFramerStatsOofCounts OBJECT-TYPE
        SYNTAX	Gauge
        ACCESS	read-only
        STATUS	mandatory
        DESCRIPTION
                "Out of frame error counts. Out of frame is declared when at least two
                of four (or five) consecutive framing bits are in error."
        ::= { wfDs1E1CurrentFramerStatsEntry 6 }

    wfDs1E1CurrentFramerStatsFeCounts OBJECT-TYPE
        SYNTAX	Gauge
        ACCESS	read-only
        STATUS	mandatory
        DESCRIPTION
                "Framing error counts. In ESF mode this is the number of errored
                superframes while in SF mode it is the number of incorrect framing
                bits."
        ::= { wfDs1E1CurrentFramerStatsEntry 7 }

    wfDs1E1CurrentFramerStatsLossFrameFailures OBJECT-TYPE
        SYNTAX	Gauge
        ACCESS	read-only
        STATUS	mandatory
        DESCRIPTION
                "Loss of frame failures. These occur when an out of frame event or
                carrier loss happens"
        ::= { wfDs1E1CurrentFramerStatsEntry 8 }

    wfDs1E1CurrentFramerStatsLossSignalFailures OBJECT-TYPE
        SYNTAX	Gauge
        ACCESS	read-only
        STATUS	mandatory
        DESCRIPTION
                "Loss of Signal failure happen when receive carrier is lost"
        ::= { wfDs1E1CurrentFramerStatsEntry 9 }

    wfDs1E1CurrentFramerStatsAlarmIndicationFailures OBJECT-TYPE
        SYNTAX	Gauge
        ACCESS	read-only
        STATUS	mandatory
        DESCRIPTION
                "Alarm Indication signal Failures occur when 2 consecutive frames have
                less than 3 zeros (total) in the data stream."
        ::= { wfDs1E1CurrentFramerStatsEntry 10 }

    wfDs1E1CurrentFramerStatsRemoteAlarmFailures OBJECT-TYPE
        SYNTAX	Gauge
        ACCESS	read-only
        STATUS	mandatory
        DESCRIPTION
                "Remote alarm failure happen when the yellow alarm is detected"
        ::= { wfDs1E1CurrentFramerStatsEntry 11 }

    wfDs1E1TotalFramerStatsTable OBJECT-TYPE
        SYNTAX	SEQUENCE OF WfDs1E1TotalFramerStatsEntry
        ACCESS	not-accessible
        STATUS	mandatory
        DESCRIPTION
                "Total framer stats line record - This table contains the
                statistics for the Framer."
        ::= { wfDs1E1Group 16 }

    wfDs1E1TotalFramerStatsEntry OBJECT-TYPE
        SYNTAX	WfDs1E1TotalFramerStatsEntry
        ACCESS	not-accessible
        STATUS	mandatory
        DESCRIPTION
                "An entry in the DS1E1 TotalFramer Stats table"
        INDEX	{ wfDs1E1TotalFramerStatsPortLineNumber }
        ::= { wfDs1E1TotalFramerStatsTable 1 }

    WfDs1E1TotalFramerStatsEntry ::= SEQUENCE {
    	    wfDs1E1TotalFramerStatsPortLineNumber
    		INTEGER,
    	    wfDs1E1TotalFramerStatsMediaType
    		INTEGER,
    	    wfDs1E1TotalFramerStatsValidIntervals
    		Gauge,
    	    wfDs1E1TotalFramerStatsBpvCounts
    		Gauge,
    	    wfDs1E1TotalFramerStatsCrc4Counts
    		Gauge,
    	    wfDs1E1TotalFramerStatsFebeCounts
    		Gauge,
    	    wfDs1E1TotalFramerStatsOofCounts
    		Gauge,
    	    wfDs1E1TotalFramerStatsFeCounts
    		Gauge,
    	    wfDs1E1TotalFramerStatsLossFrameFailures
    		Gauge,
    	    wfDs1E1TotalFramerStatsLossSignalFailures
    		Gauge,
    	    wfDs1E1TotalFramerStatsAlarmIndicationFailures
    		Gauge,
    	    wfDs1E1TotalFramerStatsRemoteAlarmFailures
    		Gauge
        }

    wfDs1E1TotalFramerStatsPortLineNumber OBJECT-TYPE
        SYNTAX	INTEGER
        ACCESS	read-only
        STATUS	mandatory
        DESCRIPTION
                "Instance ID Slot, filled in by driver"
        ::= { wfDs1E1TotalFramerStatsEntry 1 }

    wfDs1E1TotalFramerStatsMediaType OBJECT-TYPE
        SYNTAX	INTEGER {
    		    t1(1),
    		    e1(2)
    		}
        ACCESS	read-only
        STATUS	mandatory
        DESCRIPTION
                "bipolar violations counter"
        ::= { wfDs1E1TotalFramerStatsEntry 2 }

    wfDs1E1TotalFramerStatsValidIntervals OBJECT-TYPE
        SYNTAX	Gauge
        ACCESS	read-only
        STATUS	mandatory
        DESCRIPTION
                "The number of valid 15 minutes intervals in the last 24-hour period"
        ::= { wfDs1E1TotalFramerStatsEntry 3 }

    wfDs1E1TotalFramerStatsBpvCounts OBJECT-TYPE
        SYNTAX	Gauge
        ACCESS	read-only
        STATUS	mandatory
        DESCRIPTION
                "bipolar violations counter"
        ::= { wfDs1E1TotalFramerStatsEntry 4 }

    wfDs1E1TotalFramerStatsCrc4Counts OBJECT-TYPE
        SYNTAX	Gauge
        ACCESS	read-only
        STATUS	mandatory
        DESCRIPTION
                "CRC4 error counter"
        ::= { wfDs1E1TotalFramerStatsEntry 5 }

    wfDs1E1TotalFramerStatsFebeCounts OBJECT-TYPE
        SYNTAX	Gauge
        ACCESS	read-only
        STATUS	mandatory
        DESCRIPTION
                "Far End Block Error counter"
        ::= { wfDs1E1TotalFramerStatsEntry 6 }

    wfDs1E1TotalFramerStatsOofCounts OBJECT-TYPE
        SYNTAX	Gauge
        ACCESS	read-only
        STATUS	mandatory
        DESCRIPTION
                "Out of frame error counts. Out of frame is declared when at least two
                of four (or five) consecutive framing bits are in error."
        ::= { wfDs1E1TotalFramerStatsEntry 7 }

    wfDs1E1TotalFramerStatsFeCounts OBJECT-TYPE
        SYNTAX	Gauge
        ACCESS	read-only
        STATUS	mandatory
        DESCRIPTION
                "Framing error counts. In ESF mode this is the number of errored
                superframes while in SF mode it is the number of incorrect framing
                bits."
        ::= { wfDs1E1TotalFramerStatsEntry 8 }

    wfDs1E1TotalFramerStatsLossFrameFailures OBJECT-TYPE
        SYNTAX	Gauge
        ACCESS	read-only
        STATUS	mandatory
        DESCRIPTION
                "Loss of frame failures. These occur when an out of frame event or
                carrier loss happens"
        ::= { wfDs1E1TotalFramerStatsEntry 9 }

    wfDs1E1TotalFramerStatsLossSignalFailures OBJECT-TYPE
        SYNTAX	Gauge
        ACCESS	read-only
        STATUS	mandatory
        DESCRIPTION
                "Loss of Signal failure happen when receive carrier is lost"
        ::= { wfDs1E1TotalFramerStatsEntry 10 }

    wfDs1E1TotalFramerStatsAlarmIndicationFailures OBJECT-TYPE
        SYNTAX	Gauge
        ACCESS	read-only
        STATUS	mandatory
        DESCRIPTION
                "Alarm Indication signal Failures occur when 2 consecutive frames have
                less than 3 zeros (total) in the data stream."
        ::= { wfDs1E1TotalFramerStatsEntry 11 }

    wfDs1E1TotalFramerStatsRemoteAlarmFailures OBJECT-TYPE
        SYNTAX	Gauge
        ACCESS	read-only
        STATUS	mandatory
        DESCRIPTION
                "Remote alarm failure happen when the yellow alarm is detected"
        ::= { wfDs1E1TotalFramerStatsEntry 12 }

    wfDs1E1IntervalFramerStatsTable OBJECT-TYPE
        SYNTAX	SEQUENCE OF WfDs1E1IntervalFramerStatsEntry
        ACCESS	not-accessible
        STATUS	mandatory
        DESCRIPTION
                "Interval Framer stats line record - This table contains the
                statistics for the Framer."
        ::= { wfDs1E1Group 17 }

    wfDs1E1IntervalFramerStatsEntry OBJECT-TYPE
        SYNTAX	WfDs1E1IntervalFramerStatsEntry
        ACCESS	not-accessible
        STATUS	mandatory
        DESCRIPTION
                "An entry in the DS1E1 IntervalFramer Stats table"
        INDEX	{ wfDs1E1IntervalFramerStatsPortLineNumber,
    		  wfDs1E1IntervalFramerStatsIntervalNumber }
        ::= { wfDs1E1IntervalFramerStatsTable 1 }

    WfDs1E1IntervalFramerStatsEntry ::= SEQUENCE {
    	    wfDs1E1IntervalFramerStatsPortLineNumber
    		INTEGER,
    	    wfDs1E1IntervalFramerStatsIntervalNumber
    		INTEGER,
    	    wfDs1E1IntervalFramerStatsMediaType
    		INTEGER,
    	    wfDs1E1IntervalFramerStatsBpvCounts
    		Gauge,
    	    wfDs1E1IntervalFramerStatsCrc4Counts
    		Gauge,
    	    wfDs1E1IntervalFramerStatsFebeCounts
    		Gauge,
    	    wfDs1E1IntervalFramerStatsOofCounts
    		Gauge,
    	    wfDs1E1IntervalFramerStatsFeCounts
    		Gauge,
    	    wfDs1E1IntervalFramerStatsLossFrameFailures
    		Gauge,
    	    wfDs1E1IntervalFramerStatsLossSignalFailures
    		Gauge,
    	    wfDs1E1IntervalFramerStatsAlarmIndicationFailures
    		Gauge,
    	    wfDs1E1IntervalFramerStatsRemoteAlarmFailures
    		Gauge
        }

    wfDs1E1IntervalFramerStatsPortLineNumber OBJECT-TYPE
        SYNTAX	INTEGER
        ACCESS	read-only
        STATUS	mandatory
        DESCRIPTION
                "Instance ID Slot, filled in by driver"
        ::= { wfDs1E1IntervalFramerStatsEntry 1 }

    wfDs1E1IntervalFramerStatsIntervalNumber OBJECT-TYPE
        SYNTAX	INTEGER
        ACCESS	read-only
        STATUS	mandatory
        DESCRIPTION
                "Instance ID interval number, filled in by driver"
        ::= { wfDs1E1IntervalFramerStatsEntry 2 }

    wfDs1E1IntervalFramerStatsMediaType OBJECT-TYPE
        SYNTAX	INTEGER {
    		    t1(1),
    		    e1(2)
    		}
        ACCESS	read-only
        STATUS	mandatory
        DESCRIPTION
                "Media Type, T1 or E1"
        ::= { wfDs1E1IntervalFramerStatsEntry 3 }

    wfDs1E1IntervalFramerStatsBpvCounts OBJECT-TYPE
        SYNTAX	Gauge
        ACCESS	read-only
        STATUS	mandatory
        DESCRIPTION
                "bipolar violations counter"
        ::= { wfDs1E1IntervalFramerStatsEntry 4 }

    wfDs1E1IntervalFramerStatsCrc4Counts OBJECT-TYPE
        SYNTAX	Gauge
        ACCESS	read-only
        STATUS	mandatory
        DESCRIPTION
                "CRC4 error counter"
        ::= { wfDs1E1IntervalFramerStatsEntry 5 }

    wfDs1E1IntervalFramerStatsFebeCounts OBJECT-TYPE
        SYNTAX	Gauge
        ACCESS	read-only
        STATUS	mandatory
        DESCRIPTION
                "Far End Block Error counter"
        ::= { wfDs1E1IntervalFramerStatsEntry 6 }

    wfDs1E1IntervalFramerStatsOofCounts OBJECT-TYPE
        SYNTAX	Gauge
        ACCESS	read-only
        STATUS	mandatory
        DESCRIPTION
                "Out of frame error counts. Out of frame is declared when at least two
                of four (or five) consecutive framing bits are in error."
        ::= { wfDs1E1IntervalFramerStatsEntry 7 }

    wfDs1E1IntervalFramerStatsFeCounts OBJECT-TYPE
        SYNTAX	Gauge
        ACCESS	read-only
        STATUS	mandatory
        DESCRIPTION
                "Framing error counts. In ESF mode this is the number of errored
                superframes while in SF mode it is the number of incorrect framing
                bits."
        ::= { wfDs1E1IntervalFramerStatsEntry 8 }

    wfDs1E1IntervalFramerStatsLossFrameFailures OBJECT-TYPE
        SYNTAX	Gauge
        ACCESS	read-only
        STATUS	mandatory
        DESCRIPTION
                "Loss of frame failures. These occur when an out of frame event or
                carrier loss happens"
        ::= { wfDs1E1IntervalFramerStatsEntry 9 }

    wfDs1E1IntervalFramerStatsLossSignalFailures OBJECT-TYPE
        SYNTAX	Gauge
        ACCESS	read-only
        STATUS	mandatory
        DESCRIPTION
                "Loss of Signal failure happen when receive carrier is lost"
        ::= { wfDs1E1IntervalFramerStatsEntry 10 }

    wfDs1E1IntervalFramerStatsAlarmIndicationFailures OBJECT-TYPE
        SYNTAX	Gauge
        ACCESS	read-only
        STATUS	mandatory
        DESCRIPTION
                "Alarm Indication signal Failures occur when 2 consecutive frames have
                less than 3 zeros (total) in the data stream."
        ::= { wfDs1E1IntervalFramerStatsEntry 11 }

    wfDs1E1IntervalFramerStatsRemoteAlarmFailures OBJECT-TYPE
        SYNTAX	Gauge
        ACCESS	read-only
        STATUS	mandatory
        DESCRIPTION
                "Remote alarm failure happen when the yellow alarm is detected"
        ::= { wfDs1E1IntervalFramerStatsEntry 12 }

    wfDs1E1ClockTable OBJECT-TYPE
        SYNTAX	SEQUENCE OF WfDs1E1ClockEntry
        ACCESS	not-accessible
        STATUS	mandatory
        DESCRIPTION
                "DS1E1  clock record - Contains Clock parameters supporting
		the QMCT1. "
        ::= { wfDs1E1Group 18 }

    wfDs1E1ClockEntry OBJECT-TYPE
        SYNTAX	WfDs1E1ClockEntry
        ACCESS	not-accessible
        STATUS	mandatory
        DESCRIPTION
                "An entry in the DS1E1 clock table"
        INDEX	{ wfDs1E1ClockPortLineNumber }
        ::= { wfDs1E1ClockTable 1 }

    WfDs1E1ClockEntry ::= SEQUENCE {
    	    wfDs1E1ClockDelete
    		INTEGER,
    	    wfDs1E1ClockPortLineNumber
    		INTEGER,
    	    wfDs1E1ClockPrimaryClock
    		INTEGER,
    	    wfDs1E1ClockSecondaryClock
    		INTEGER,
    	    wfDs1E1ClockCurrentClock
    		INTEGER,
    	    wfDs1E1ClockLoopClockOperational
    		INTEGER,
    	    wfDs1E1ClockExtClockOperational
    		INTEGER
        }

    wfDs1E1ClockDelete OBJECT-TYPE
        SYNTAX	INTEGER {
    		    created(1),
    		    deleted(2)
    		}
        ACCESS	read-write
        STATUS	mandatory
        DESCRIPTION
                "Create/Delete attribute"
        DEFVAL	{ created }
        ::= { wfDs1E1ClockEntry 1 }

    wfDs1E1ClockPortLineNumber OBJECT-TYPE
        SYNTAX	INTEGER
        ACCESS	read-only
        STATUS	mandatory
        DESCRIPTION
                "The index ID for this record. It is the line number assigned
		to a port in the wfDs1E1PortMapEntry for a port.connector pair.
		Its channel field should be 0."
        ::= { wfDs1E1ClockEntry 2 }

    wfDs1E1ClockPrimaryClock OBJECT-TYPE
        SYNTAX	INTEGER {
    		    internal(1),
    		    external(2),
    		    loop1(3),
    		    loop2(4),
		    loop3(5),
		    loop4(6)
    		}
        ACCESS	read-write
        STATUS	mandatory
        DESCRIPTION
                "Specifies the primary source for transmit timing for this
		port.  The options for timing source are internal timing
		source, loop timing from either port and an external timing
		source.  Note that the bit defines are equal to the Timing
		Register bit definitions plus 1."
        DEFVAL	{ internal }
        ::= { wfDs1E1ClockEntry 3 }

    wfDs1E1ClockSecondaryClock OBJECT-TYPE
        SYNTAX	INTEGER {
    		    internal(1),
    		    external(2),
    		    loop1(3),
    		    loop2(4),
		    loop3(5),
		    loop4(6)
    		}
        ACCESS	read-write
        STATUS	mandatory
        DESCRIPTION
                "Specifies the secondary source for transmit timing for this
		port."
        DEFVAL	{ internal }
        ::= { wfDs1E1ClockEntry 4 }

    wfDs1E1ClockCurrentClock OBJECT-TYPE
        SYNTAX	INTEGER {
    		    internal(1),
    		    external(2),
    		    loop1(3),
    		    loop2(4),
		    loop3(5),
		    loop4(6)
    		}
        ACCESS	read-only
        STATUS	mandatory
        DESCRIPTION
                "Specifies the current source for transmit timing for this
		port."
        ::= { wfDs1E1ClockEntry 5 }

    wfDs1E1ClockLoopClockOperational OBJECT-TYPE
        SYNTAX	INTEGER {
    		    present(1),
    		    notpresent(2)
    		}
        ACCESS	read-only
        STATUS	mandatory
        DESCRIPTION
                "Specifies this ports Loop Clock Status, PRESENT (UP) or
		NOTPRESENT (DOWN)."
        DEFVAL	{ present }
        ::= { wfDs1E1ClockEntry 6 }

    wfDs1E1ClockExtClockOperational OBJECT-TYPE
        SYNTAX	INTEGER {
    		    present(1),
    		    notpresent(2)
    		}
        ACCESS	read-only
        STATUS	mandatory
        DESCRIPTION
                "Indicates whether the External clock is operational."
        DEFVAL	{ present }
        ::= { wfDs1E1ClockEntry 7 }




    wfDs1E1LineCfgTable OBJECT-TYPE
        SYNTAX	SEQUENCE OF WfDs1E1LineCfgEntry
        ACCESS	not-accessible
        STATUS	mandatory
        DESCRIPTION
                "Contains configuration parameters for Channel specific
		Fractional T1/E1."
        ::= { wfDs1E1Group 21 }

    wfDs1E1LineCfgEntry OBJECT-TYPE
        SYNTAX	WfDs1E1LineCfgEntry
        ACCESS	not-accessible
        STATUS	mandatory
        DESCRIPTION
                "An entry in the LOGICAL_LINE table"
        INDEX	{ wfDs1E1LineCfgPortLineNumber,
    		  wfDs1E1LineCfgIndex }
        ::= { wfDs1E1LineCfgTable 1 }

    WfDs1E1LineCfgEntry ::= SEQUENCE {
    	    wfDs1E1LineCfgDelete
    		INTEGER,
    	    wfDs1E1LineCfgDisable
    		INTEGER,
    	    wfDs1E1LineCfgState
    		INTEGER,
	    wfDs1E1LineLastChange
    		TimeTicks,
    	    wfDs1E1LineCfgPortLineNumber
    		INTEGER,
    	    wfDs1E1LineCfgIndex
    		INTEGER,
    	    wfDs1E1LineCfgIfIndex
    		INTEGER,
    	    wfDs1E1LineCfgCct
    		INTEGER,
    	    wfDs1E1LineCfgLineNumber
    		INTEGER,
    	    wfDs1E1LineCfgQosServicePkg
    		INTEGER,
    	    wfDs1E1LineCfgTimeSlotAssign
    		INTEGER,
    	    wfDs1E1LineCfgActualTimeSlotAssign
    		DisplayString,
    	    wfDs1E1LineCfgWanProtocol
    		INTEGER,
    	    wfDs1E1LineCfgRateAdaption
    		INTEGER,
    	    wfDs1E1LineCfgIFTF
    		INTEGER,
    	    wfDs1E1LineCfgCRCSize
    		INTEGER,
    	    wfDs1E1LineCfgMtu
    		INTEGER,
	    wfDs1E1LineCfgBertMode
		INTEGER,
	    wfDs1E1LineCfgBertTestPattern
		INTEGER,
    	    wfDs1E1LineCfgFractionalLoopback
    		INTEGER,
	    wfDs1E1LineCfgAcceptFracLoopCode
    		INTEGER,
	    wfDs1E1LineCfgManagerMethod
    		INTEGER
        }

    wfDs1E1LineCfgDelete OBJECT-TYPE
        SYNTAX	INTEGER {
    		    created(1),
    		    deleted(2)
    		}
        ACCESS	read-write
        STATUS	mandatory
        DESCRIPTION
                "Create/Delete parameter"
        DEFVAL	{ created }
        ::= { wfDs1E1LineCfgEntry 1 }

    wfDs1E1LineCfgDisable OBJECT-TYPE
        SYNTAX	INTEGER {
    		    enabled(1),
    		    disabled(2)
    		}
        ACCESS	read-write
        STATUS	mandatory
        DESCRIPTION
                "Enable/Disable parameter"
        DEFVAL	{ enabled }
        ::= { wfDs1E1LineCfgEntry 2 }

    wfDs1E1LineCfgState OBJECT-TYPE
        SYNTAX	INTEGER {
    		    up(1),
    		    down(2),
    		    init(3),
    		    lmiwait(4),
    		    loopback(5),
    		    linedieing(6),
    		    linedead(7),
    		    remoteloop(8),
    		    remotedeaf(9),
		    bert(10),
		    hwfrac(11),
		    priWait(12),
		    quePkgWait(13),
		    queMisCfg(14),
    		    notpresent(20)
    		}
        ACCESS	read-only
        STATUS	mandatory
        DESCRIPTION
                "Line Driver state variable"
        DEFVAL	{ notpresent }
        ::= { wfDs1E1LineCfgEntry 3 }

    wfDs1E1LineLastChange OBJECT-TYPE
        SYNTAX	TimeTicks
        ACCESS	read-only
        STATUS	mandatory
        DESCRIPTION
		"The value of sysUpTime at the time the interface entered
		its current operational state."
        ::= { wfDs1E1LineCfgEntry 4 }

    wfDs1E1LineCfgPortLineNumber OBJECT-TYPE
        SYNTAX	INTEGER
        ACCESS	read-only
        STATUS	mandatory
        DESCRIPTION
                "Instance ID PortLineNumber, filled in by driver"
        ::= { wfDs1E1LineCfgEntry 5 }

    wfDs1E1LineCfgIndex OBJECT-TYPE
        SYNTAX	INTEGER
        ACCESS	read-only
        STATUS	mandatory
        DESCRIPTION
                "Index for this line instance, filled in by driver.
                The index corresponds to the position of the
                circuit on the port."
        ::= { wfDs1E1LineCfgEntry 6 }

    wfDs1E1LineCfgIfIndex OBJECT-TYPE
        SYNTAX	INTEGER
        ACCESS	read-only
        STATUS	mandatory
        DESCRIPTION
                "IfTable Index for this line instance,
		 filled in by driver."
        ::= { wfDs1E1LineCfgEntry 7 }

    wfDs1E1LineCfgCct OBJECT-TYPE
        SYNTAX	INTEGER
        ACCESS	read-write
        STATUS	mandatory
        DESCRIPTION
                "Circuit number for this line instance"
        ::= { wfDs1E1LineCfgEntry 8 }

    wfDs1E1LineCfgLineNumber OBJECT-TYPE
        SYNTAX	INTEGER
        ACCESS	read-write
        STATUS	mandatory
        DESCRIPTION
                "LineNumber for this logical line instance. This is the same line number
                contained in the PORT_TABLE with the channel field nonzero."
        ::= { wfDs1E1LineCfgEntry 9 }

    wfDs1E1LineCfgQosServicePkg OBJECT-TYPE
        SYNTAX	INTEGER
        ACCESS	read-write
        STATUS	mandatory
        DESCRIPTION
                "Queue Service Package to be used for this line"
        DEFVAL	{ 0 }
        ::= { wfDs1E1LineCfgEntry 10 }

    wfDs1E1LineCfgTimeSlotAssign OBJECT-TYPE
        SYNTAX	INTEGER
        ACCESS	read-write
        STATUS	mandatory
        DESCRIPTION
                "Bitmask of timeslot(s) assigned to this line
			MSB == Bit 31, LSB == Bit 0
			TimeSlot 1  == Bit 1
			TimeSlot 24 == Bit 24 (T1)
			TimeSlot 31 == Bit 31 (E1)"
        ::= { wfDs1E1LineCfgEntry 11 }

    wfDs1E1LineCfgActualTimeSlotAssign OBJECT-TYPE
        SYNTAX	DisplayString
        ACCESS	read-only
        STATUS	mandatory
        DESCRIPTION
                "Lists the time-slots which constitute this channel. Read only
		attribute that contains a  list of time-slots from 1 to 31
		used by the channel"
        ::= { wfDs1E1LineCfgEntry 12 }

    wfDs1E1LineCfgWanProtocol OBJECT-TYPE
        SYNTAX	INTEGER {
    		    standard(1),
    		    passthru(2),
    		    ppp(3),
    		    smds(4),
    		    framerelay(5),
    		    x25(6),
    		    switch(7),
    		    sw(8),
    		    atm(9),
    		    lapb(10),
                    sdlc(11)
    		}
        ACCESS	read-write
        STATUS	mandatory
        DESCRIPTION
                "WAN protocol selection is provided via this parameter. The
                supported protocols can be selected per circuit."
        DEFVAL	{ ppp }
        ::= { wfDs1E1LineCfgEntry 13 }

    wfDs1E1LineCfgRateAdaption OBJECT-TYPE
        SYNTAX	INTEGER {
    		    adaption64k(1),
    		    adaption56klsb(3)
    		}
        ACCESS	read-write
        STATUS	mandatory
        DESCRIPTION
                "Determines the number of bits and their bit positions
                within the time-slot. 64k selection uses all 8 bits in
                the time-slot. The two 56k selections use 7 of the 8
                bits in the time-slot. 56k_MSB does not use the most
                significant bit and 56k_LSB does not use the least
                significant bit in the time-slot."
        DEFVAL	{ adaption64k }
        ::= { wfDs1E1LineCfgEntry 14 }

    wfDs1E1LineCfgIFTF OBJECT-TYPE
        SYNTAX	INTEGER {
    		    flags(1),
    		    idles(2)
    		}
        ACCESS	read-write
        STATUS	mandatory
        DESCRIPTION
                "Determines the Interframe time fill character to be
                transmitted by the HDLC Controller. In case of IFTF_FLAGS,
		0x7E is sent and in case of IFTF_IDLES 0xff is sent as the
                interframe timefill characters."
        DEFVAL	{ flags }
        ::= { wfDs1E1LineCfgEntry 15 }

    wfDs1E1LineCfgCRCSize OBJECT-TYPE
        SYNTAX	INTEGER {
    		    crc32(1),
    		    crc16(2)
    		}
        ACCESS	read-write
        STATUS	mandatory
        DESCRIPTION
                "Determines the CRC Size. When CRC32 is selected a 32 bit
                CRC is appended to the frame being transmitted and a 32
                bit CRC check is performed on the received frame. When
                CRC16 is selected, a 16 bit CRC is appended to the
                transmitted frame and a 16 bit CRC is performed. on the
                received frame."
        DEFVAL	{ crc16 }
        ::= { wfDs1E1LineCfgEntry 16 }

    wfDs1E1LineCfgMtu OBJECT-TYPE
        SYNTAX	INTEGER(3..4608)
        ACCESS	read-write
        STATUS	mandatory
        DESCRIPTION
                "Specifies the largest frame size that can be received by the logical line.
                Anything larger than the MTU will be discarded."
        DEFVAL	{ 4608 }
        ::= { wfDs1E1LineCfgEntry 17 }

    wfDs1E1LineCfgBertMode OBJECT-TYPE
	SYNTAX	INTEGER {
		    enabled(1),
		    disabled(2)
		}
	ACCESS	read-write
	STATUS	mandatory
	DESCRIPTION
		"Enables Bit Error Rate Testing (BERT) on a logical line level."
	DEFVAL	{ disabled }
	::= { wfDs1E1LineCfgEntry 18 }

    wfDs1E1LineCfgBertTestPattern OBJECT-TYPE
        SYNTAX	INTEGER {
    		    zeros(1),
    		    ones(2),
    		    qrss(3),
    		    two15(4),
    		    two15-inv(5),
    		    two20(6),
    		    two23(7),
    		    two23-inv(8)
    		}
        ACCESS	read-write
        STATUS	mandatory
        DESCRIPTION
                "When a line is in BERT mode, it is capable of generating
                a set of known patterns. This paramater selects between those
                patterns"
        DEFVAL	{ ones }
        ::= { wfDs1E1LineCfgEntry 19 }

    wfDs1E1LineCfgFractionalLoopback OBJECT-TYPE
        SYNTAX	INTEGER {
    		    enabled(1),
    		    disabled(2)
    		}
        ACCESS	read-write
        STATUS	mandatory
        DESCRIPTION
                "Any Ds1E1 Line on this T1/E1 port is capable of being put into
                loopback through hardware, i.e. data coming into that circuit
		from the wire is mirrorred back onto the wire. This parameter
		enables or disables this loopback feature on any circuit."
        DEFVAL	{ disabled }
        ::= { wfDs1E1LineCfgEntry 20 }

    wfDs1E1LineCfgAcceptFracLoopCode OBJECT-TYPE
	SYNTAX	INTEGER {
		    enabled(1),
		    disabled(2)
	}
	ACCESS	read-write
	STATUS	mandatory
	DESCRIPTION
		"Allows logical line to accept Fractional T1 Loop Code sent
		from a Remote Device."
	DEFVAL	{ enabled }
	::= { wfDs1E1LineCfgEntry 21 }

    wfDs1E1LineCfgManagerMethod OBJECT-TYPE
	SYNTAX	INTEGER {
		    timeslots(1),
		    t1(2)
	}
	ACCESS	read-write
	STATUS	mandatory
	DESCRIPTION
		"This attribute has no affect on the Hardware configuration.
		This attribute is purely for any Network Management Tool
		to determine whether it configured the Logical Line as a
		Clear Channel T1 or as a Fractional T1 with Timeslots."
	DEFVAL	{ timeslots }
	::= { wfDs1E1LineCfgEntry 22 }






    wfDs1E1LineStatTable OBJECT-TYPE
        SYNTAX	SEQUENCE OF WfDs1E1LineStatEntry
        ACCESS	not-accessible
        STATUS	mandatory
        DESCRIPTION
                "Contains statistics for Channel specific Fractional T1/E1."
        ::= { wfDs1E1Group 22 }

    wfDs1E1LineStatEntry OBJECT-TYPE
        SYNTAX	WfDs1E1LineStatEntry
        ACCESS	not-accessible
        STATUS	mandatory
        DESCRIPTION
                "An entry in the LOGICAL_LINE table"
        INDEX	{ wfDs1E1LineStatPortLineNumber,
    		  wfDs1E1LineStatIndex }
        ::= { wfDs1E1LineStatTable 1 }

    WfDs1E1LineStatEntry ::= SEQUENCE {
    	    wfDs1E1LineStatPortLineNumber
    		INTEGER,
    	    wfDs1E1LineStatIndex
    		INTEGER,
    	    wfDs1E1LineStatRxOctets
    		Counter,
    	    wfDs1E1LineStatTxOctets
    		Counter,
    	    wfDs1E1LineStatRxFrames
    		Counter,
    	    wfDs1E1LineStatTxFrames
    		Counter,
    	    wfDs1E1LineStatRxErrors
    		Counter,
    	    wfDs1E1LineStatTxErrors
    		Counter,
    	    wfDs1E1LineStatRxDropPackets
    		Counter,
    	    wfDs1E1LineStatTxDropPackets
    		Counter,
    	    wfDs1E1LineStatTxUnderflows
    		Counter,
    	    wfDs1E1LineStatRxOverflows
    		Counter,
    	    wfDs1E1LineStatRxShortFrames
    		Counter,
    	    wfDs1E1LineStatRxCRCErrors
    		Counter,
    	    wfDs1E1LineStatRxNonOctetBits
    		Counter,
    	    wfDs1E1LineStatRxLongFrames
    		Counter,
    	    wfDs1E1LineStatRxAbortFrames
    		Counter
        }

    wfDs1E1LineStatPortLineNumber OBJECT-TYPE
        SYNTAX	INTEGER
        ACCESS	read-only
        STATUS	mandatory
        DESCRIPTION
                "Instance ID PortLineNumber, filled in by driver"
        ::= { wfDs1E1LineStatEntry 1 }

    wfDs1E1LineStatIndex OBJECT-TYPE
        SYNTAX	INTEGER
        ACCESS	read-only
        STATUS	mandatory
        DESCRIPTION
                "Index for this line instance, filled in by driver.
                The index corresponds to the position of the
                circuit, from 1 to 31, on the port."
        ::= { wfDs1E1LineStatEntry 2 }

    wfDs1E1LineStatRxOctets OBJECT-TYPE
        SYNTAX	Counter
        ACCESS	read-only
        STATUS	mandatory
        DESCRIPTION
                "Number of octets received without error"
        ::= { wfDs1E1LineStatEntry 3 }

    wfDs1E1LineStatTxOctets OBJECT-TYPE
        SYNTAX	Counter
        ACCESS	read-only
        STATUS	mandatory
        DESCRIPTION
                "Number of octets transmitted without error"
        ::= { wfDs1E1LineStatEntry 4 }

    wfDs1E1LineStatRxFrames OBJECT-TYPE
        SYNTAX	Counter
        ACCESS	read-only
        STATUS	mandatory
        DESCRIPTION
                "Number of frames received without error"
        ::= { wfDs1E1LineStatEntry 5 }

    wfDs1E1LineStatTxFrames OBJECT-TYPE
        SYNTAX	Counter
        ACCESS	read-only
        STATUS	mandatory
        DESCRIPTION
                "Number of frames transmitted without error"
        ::= { wfDs1E1LineStatEntry 6 }

    wfDs1E1LineStatRxErrors OBJECT-TYPE
        SYNTAX	Counter
        ACCESS	read-only
        STATUS	mandatory
        DESCRIPTION
                "Number of receive errors"
        ::= { wfDs1E1LineStatEntry 7 }

    wfDs1E1LineStatTxErrors OBJECT-TYPE
        SYNTAX	Counter
        ACCESS	read-only
        STATUS	mandatory
        DESCRIPTION
                "Number of transmission errors"
        ::= { wfDs1E1LineStatEntry 8 }

    wfDs1E1LineStatRxDropPackets OBJECT-TYPE
        SYNTAX	Counter
        ACCESS	read-only
        STATUS	mandatory
        DESCRIPTION
                "Number of Rx frames dropped"
        ::= { wfDs1E1LineStatEntry 9 }

    wfDs1E1LineStatTxDropPackets OBJECT-TYPE
        SYNTAX	Counter
        ACCESS	read-only
        STATUS	mandatory
        DESCRIPTION
                "Number of Tx frames dropped"
        ::= { wfDs1E1LineStatEntry 10 }

    wfDs1E1LineStatTxUnderflows OBJECT-TYPE
        SYNTAX	Counter
        ACCESS	read-only
        STATUS	mandatory
        DESCRIPTION
                "Number of Tx frames dropped due to Transmit underflow"
        ::= { wfDs1E1LineStatEntry 11 }

    wfDs1E1LineStatRxOverflows OBJECT-TYPE
        SYNTAX	Counter
        ACCESS	read-only
        STATUS	mandatory
        DESCRIPTION
                "Number of Rx frames dropped due to Receive overflow"
        ::= { wfDs1E1LineStatEntry 12 }

    wfDs1E1LineStatRxShortFrames OBJECT-TYPE
        SYNTAX	Counter
        ACCESS	read-only
        STATUS	mandatory
        DESCRIPTION
                "Number of short frames received whose length is either 1
		or 2 data bytes."
        ::= { wfDs1E1LineStatEntry 13 }

    wfDs1E1LineStatRxCRCErrors OBJECT-TYPE
        SYNTAX	Counter
        ACCESS	read-only
        STATUS	mandatory
        DESCRIPTION
                "CRC error received"
        ::= { wfDs1E1LineStatEntry 14 }

    wfDs1E1LineStatRxNonOctetBits OBJECT-TYPE
        SYNTAX	Counter
        ACCESS	read-only
        STATUS	mandatory
        DESCRIPTION
                "Non-Octet bits received in frame"
        ::= { wfDs1E1LineStatEntry 15 }

    wfDs1E1LineStatRxLongFrames OBJECT-TYPE
        SYNTAX	Counter
        ACCESS	read-only
        STATUS	mandatory
        DESCRIPTION
                "Frame longer than MFL received"
        ::= { wfDs1E1LineStatEntry 16 }

    wfDs1E1LineStatRxAbortFrames OBJECT-TYPE
        SYNTAX	Counter
        ACCESS	read-only
        STATUS	mandatory
        DESCRIPTION
                "Aborted frame received"
        ::= { wfDs1E1LineStatEntry 17 }


    wfDs1E1DayCurrentTable OBJECT-TYPE
        SYNTAX	SEQUENCE OF WfDs1E1DayCurrentEntry
        ACCESS	not-accessible
        STATUS	mandatory
        DESCRIPTION
                "Current AT&T FDL stats table."
        ::= { wfDs1E1Group 24 }

    wfDs1E1DayCurrentEntry OBJECT-TYPE
        SYNTAX	WfDs1E1DayCurrentEntry
        ACCESS	not-accessible
        STATUS	mandatory
        DESCRIPTION
                "An entry in the DS1E1 Current table"
        INDEX	{ wfDs1E1DayCurrentPortLineNumber }
        ::= { wfDs1E1DayCurrentTable 1 }

    WfDs1E1DayCurrentEntry ::= SEQUENCE {
    	    wfDs1E1DayCurrentPortLineNumber
    		INTEGER,
    	    wfDs1E1DayCurrentESs
    		Gauge,
    	    wfDs1E1DayCurrentSESs
    		Gauge,
    	    wfDs1E1DayCurrentSEFSs
    		Gauge,
    	    wfDs1E1DayCurrentUASs
    		Gauge,
    	    wfDs1E1DayCurrentCSSs
    		Gauge,
    	    wfDs1E1DayCurrentPCVs
    		Gauge,
    	    wfDs1E1DayCurrentLESs
    		Gauge,
    	    wfDs1E1DayCurrentBESs
    		Gauge,
    	    wfDs1E1DayCurrentDMs
    		Gauge,
    	    wfDs1E1DayCurrentLCVs
    		Gauge,
    	    wfDs1E1DayCurrentSASs
    		Gauge,
    	    wfDs1E1DayCurrentAISSs
    		Gauge,
    	    wfDs1E1DayCurrentFCs
    		Gauge,
    	    wfDs1E1DayCurrentTimeElapsed
    		INTEGER,
	    wfDs1E1DayCurrentValidIntervals
		INTEGER,
	    wfDs1E1DayCurrentValidFlag
		INTEGER
        }

    wfDs1E1DayCurrentPortLineNumber OBJECT-TYPE
        SYNTAX	INTEGER
        ACCESS	read-only
        STATUS	mandatory
        DESCRIPTION
                "The instance ID that identifies the port. The port line number with a zero
                channel number field as found in the port map table."
        ::= { wfDs1E1DayCurrentEntry 1 }

    wfDs1E1DayCurrentESs OBJECT-TYPE
        SYNTAX	Gauge
        ACCESS	read-only
        STATUS	mandatory
        DESCRIPTION
                "The number of Errored Seconds, encountered by a DS1 interface in the
                current day interval."
        ::= { wfDs1E1DayCurrentEntry 2 }

    wfDs1E1DayCurrentSESs OBJECT-TYPE
        SYNTAX	Gauge
        ACCESS	read-only
        STATUS	mandatory
        DESCRIPTION
                "The number of Severely Errored Seconds encountered by a DS1 interface
                in the current day interval.'"
        ::= { wfDs1E1DayCurrentEntry 3 }

    wfDs1E1DayCurrentSEFSs OBJECT-TYPE
        SYNTAX	Gauge
        ACCESS	read-only
        STATUS	mandatory
        DESCRIPTION
                "The number of Severely Errored Framing Seconds encountered  by  a DS1
                interface in the current day interval."
        ::= { wfDs1E1DayCurrentEntry 4 }

    wfDs1E1DayCurrentUASs OBJECT-TYPE
        SYNTAX	Gauge
        ACCESS	read-only
        STATUS	mandatory
        DESCRIPTION
                "The number of Unavailable Seconds encountered by a DS1 interface in the
                current day interval."
        ::= { wfDs1E1DayCurrentEntry 5 }

    wfDs1E1DayCurrentCSSs OBJECT-TYPE
        SYNTAX	Gauge
        ACCESS	read-only
        STATUS	mandatory
        DESCRIPTION
                "The number of Controlled Slip Seconds encountered by a DS1 interface in the
                current day interval."
        ::= { wfDs1E1DayCurrentEntry 6 }

    wfDs1E1DayCurrentPCVs OBJECT-TYPE
        SYNTAX	Gauge
        ACCESS	read-only
        STATUS	mandatory
        DESCRIPTION
                "The number of Path Coding Violations encountered by a DS1 interface in the
                current day interval."
        ::= { wfDs1E1DayCurrentEntry 7 }

    wfDs1E1DayCurrentLESs OBJECT-TYPE
        SYNTAX	Gauge
        ACCESS	read-only
        STATUS	mandatory
        DESCRIPTION
                "The number of Line Errored Seconds encountered by a DS1 interface in the
                current day interval.'"
        ::= { wfDs1E1DayCurrentEntry 8 }

    wfDs1E1DayCurrentBESs OBJECT-TYPE
        SYNTAX	Gauge
        ACCESS	read-only
        STATUS	mandatory
        DESCRIPTION
                "The number of Bursty Errored Seconds (BESs) encountered by a DS1 interface
                in the current day interval."
        ::= { wfDs1E1DayCurrentEntry 9 }

    wfDs1E1DayCurrentDMs OBJECT-TYPE
        SYNTAX	Gauge
        ACCESS	read-only
        STATUS	mandatory
        DESCRIPTION
                "The number of Degraded Minutes (DMs) encountered by a DS1 interface in
                the current day interval.'"
        ::= { wfDs1E1DayCurrentEntry 10 }

    wfDs1E1DayCurrentLCVs OBJECT-TYPE
        SYNTAX	Gauge
        ACCESS	read-only
        STATUS	mandatory
        DESCRIPTION
                "The number of Line Code Violations (LCVs) encountered  by a DS1 interface in
                the current day interval.'"
        ::= { wfDs1E1DayCurrentEntry 11 }

    wfDs1E1DayCurrentSASs OBJECT-TYPE
        SYNTAX	Gauge
        ACCESS	read-only
        STATUS	mandatory
        DESCRIPTION
                "The number of seconds, within the current day interval,
		containing one or more SEFs or AIS defects."
        ::= { wfDs1E1DayCurrentEntry 12 }

    wfDs1E1DayCurrentAISSs OBJECT-TYPE
        SYNTAX	Gauge
        ACCESS	read-only
        STATUS	mandatory
        DESCRIPTION
                "The number of seconds, within the current day interval,
		 containing one or more AIS defect."
        ::= { wfDs1E1DayCurrentEntry 13 }

    wfDs1E1DayCurrentFCs OBJECT-TYPE
        SYNTAX	Gauge
        ACCESS	read-only
        STATUS	mandatory
        DESCRIPTION
                "The number of Path Failure Count error events detected
                in the current day interval."
        ::= { wfDs1E1DayCurrentEntry 14 }

    wfDs1E1DayCurrentTimeElapsed OBJECT-TYPE
        SYNTAX	INTEGER
        ACCESS	read-only
        STATUS	mandatory
        DESCRIPTION
                "The number of seconds that have elapsed since the beginning of the
                current error-measurement period."
        ::= { wfDs1E1DayCurrentEntry 15 }

    wfDs1E1DayCurrentValidIntervals OBJECT-TYPE
        SYNTAX	INTEGER
        ACCESS	read-only
        STATUS	mandatory
        DESCRIPTION
                "The number of previous intervals for which valid data was collected. The
                value will be 8 unless the interface was brought on-line within the last
                8 days, in which case the value will be the number of complete day
                intervals the since interface has been online."
        ::= { wfDs1E1DayCurrentEntry 16 }

    wfDs1E1DayCurrentValidFlag OBJECT-TYPE
        SYNTAX	INTEGER {
    		    valid(1),
    		    invalid(2)
    		}
        ACCESS	read-only
        STATUS	mandatory
        DESCRIPTION
                "Indicates whether this interval reported by the Mib Table is valid or
		invalid."
        DEFVAL	{ valid }
        ::= { wfDs1E1DayCurrentEntry 17 }


    wfDs1E1DayIntervalTable OBJECT-TYPE
        SYNTAX	SEQUENCE OF WfDs1E1DayIntervalEntry
        ACCESS	not-accessible
        STATUS	mandatory
        DESCRIPTION
                "AT&T Interval stats"
        ::= { wfDs1E1Group 25 }

    wfDs1E1DayIntervalEntry OBJECT-TYPE
        SYNTAX	WfDs1E1DayIntervalEntry
        ACCESS	not-accessible
        STATUS	mandatory
        DESCRIPTION
                "An entry in the DS1E1 Interval table"
        INDEX	{ wfDs1E1DayIntervalPortLineNumber,
    		  wfDs1E1DayIntervalNumber }
        ::= { wfDs1E1DayIntervalTable 1 }

    WfDs1E1DayIntervalEntry ::= SEQUENCE {
    	    wfDs1E1DayIntervalPortLineNumber
    		INTEGER,
    	    wfDs1E1DayIntervalNumber
    		INTEGER,
    	    wfDs1E1DayIntervalESs
    		Gauge,
    	    wfDs1E1DayIntervalSESs
    		Gauge,
    	    wfDs1E1DayIntervalSEFSs
    		Gauge,
    	    wfDs1E1DayIntervalUASs
    		Gauge,
    	    wfDs1E1DayIntervalCSSs
    		Gauge,
    	    wfDs1E1DayIntervalPCVs
    		Gauge,
    	    wfDs1E1DayIntervalLESs
    		Gauge,
    	    wfDs1E1DayIntervalBESs
    		Gauge,
    	    wfDs1E1DayIntervalDMs
    		Gauge,
    	    wfDs1E1DayIntervalLCVs
    		Gauge,
    	    wfDs1E1DayIntervalSASs
    		Gauge,
    	    wfDs1E1DayIntervalAISSs
    		Gauge,
    	    wfDs1E1DayIntervalFCs
    		Gauge,
	    wfDs1E1DayIntervalValidFlag
		INTEGER
        }

    wfDs1E1DayIntervalPortLineNumber OBJECT-TYPE
        SYNTAX	INTEGER
        ACCESS	read-only
        STATUS	mandatory
        DESCRIPTION
                "The instance ID that identifies the port. The port line number with a zero
                channel number field as found in the port map table."
        ::= { wfDs1E1DayIntervalEntry 1 }

    wfDs1E1DayIntervalNumber OBJECT-TYPE
        SYNTAX	INTEGER
        ACCESS	read-only
        STATUS	mandatory
        DESCRIPTION
                "A number between 1 and 8, where 1 is the most recently completed day
                interval and 8 is the least recently completed day interval (assuming
                that all 8 intervals are valid)."
        ::= { wfDs1E1DayIntervalEntry 2 }

    wfDs1E1DayIntervalESs OBJECT-TYPE
        SYNTAX	Gauge
        ACCESS	read-only
        STATUS	mandatory
        DESCRIPTION
                "The number of Errored Seconds, encountered by a DS1 interface in the current
                day interval."
        ::= { wfDs1E1DayIntervalEntry 3 }

    wfDs1E1DayIntervalSESs OBJECT-TYPE
        SYNTAX	Gauge
        ACCESS	read-only
        STATUS	mandatory
        DESCRIPTION
                "The number of Severely Errored Seconds encountered by a DS1 interface in one
                of the previous day intervals."
        ::= { wfDs1E1DayIntervalEntry 4 }

    wfDs1E1DayIntervalSEFSs OBJECT-TYPE
        SYNTAX	Gauge
        ACCESS	read-only
        STATUS	mandatory
        DESCRIPTION
                "The number of Severely Errored Framing Seconds encountered by a DS1 interface
                in one of the previous day intervals."
        ::= { wfDs1E1DayIntervalEntry 5 }

    wfDs1E1DayIntervalUASs OBJECT-TYPE
        SYNTAX	Gauge
        ACCESS	read-only
        STATUS	mandatory
        DESCRIPTION
                "The number of Unavailable Seconds encountered by a DS1 interface in one of the
                previous day intervals."
        ::= { wfDs1E1DayIntervalEntry 6 }

    wfDs1E1DayIntervalCSSs OBJECT-TYPE
        SYNTAX	Gauge
        ACCESS	read-only
        STATUS	mandatory
        DESCRIPTION
                "The number of Controlled Slip Seconds encountered by a DS1 interface in one
                of the previous day intervals."
        ::= { wfDs1E1DayIntervalEntry 7 }

    wfDs1E1DayIntervalPCVs OBJECT-TYPE
        SYNTAX	Gauge
        ACCESS	read-only
        STATUS	mandatory
        DESCRIPTION
                "The number of Path Coding Violations encountered by a DS1 interface in one of
                the previous day intervals."
        ::= { wfDs1E1DayIntervalEntry 8 }

    wfDs1E1DayIntervalLESs OBJECT-TYPE
        SYNTAX	Gauge
        ACCESS	read-only
        STATUS	mandatory
        DESCRIPTION
                "The number of Line Errored Seconds encountered by a DS1 interface in one of
                the previous day intervals."
        ::= { wfDs1E1DayIntervalEntry 9 }

    wfDs1E1DayIntervalBESs OBJECT-TYPE
        SYNTAX	Gauge
        ACCESS	read-only
        STATUS	mandatory
        DESCRIPTION
                "The number of Bursty Errored Seconds (BESs) encountered by a DS1 interface in
                one of the previous day intervals."
        ::= { wfDs1E1DayIntervalEntry 10 }

    wfDs1E1DayIntervalDMs OBJECT-TYPE
        SYNTAX	Gauge
        ACCESS	read-only
        STATUS	mandatory
        DESCRIPTION
                "The number of Degraded Minutes (DMs) encountered by a DS1 interface in one of
                the previous day intervals."
        ::= { wfDs1E1DayIntervalEntry 11 }

    wfDs1E1DayIntervalLCVs OBJECT-TYPE
        SYNTAX	Gauge
        ACCESS	read-only
        STATUS	mandatory
        DESCRIPTION
                "The number of Line Code Violations (LCVs) encountered by a DS1 interface in
                one of the previous day intervals."
        ::= { wfDs1E1DayIntervalEntry 12 }

    wfDs1E1DayIntervalSASs OBJECT-TYPE
        SYNTAX	Gauge
        ACCESS	read-only
        STATUS	mandatory
        DESCRIPTION
                "The number of seconds, in one of the previous day intervals,
		containing one or more SEFs or AIS defects."
        ::= { wfDs1E1DayIntervalEntry 13 }

    wfDs1E1DayIntervalAISSs OBJECT-TYPE
        SYNTAX	Gauge
        ACCESS	read-only
        STATUS	mandatory
        DESCRIPTION
                "The number of seconds, in one of the previous day intervals,
		 containing one or more AIS defect."
        ::= { wfDs1E1DayIntervalEntry 14 }

    wfDs1E1DayIntervalFCs OBJECT-TYPE
        SYNTAX	Gauge
        ACCESS	read-only
        STATUS	mandatory
        DESCRIPTION
                "The number of Path Failure Count error events detected
		one of the previous day intervals."
        ::= { wfDs1E1DayIntervalEntry 15 }

    wfDs1E1DayIntervalValidFlag OBJECT-TYPE
        SYNTAX	INTEGER {
    		    valid(1),
    		    invalid(2)
    		}
        ACCESS	read-only
        STATUS	mandatory
        DESCRIPTION
                "Indicates whether this interval reported by the Mib Table is valid or
		invalid."
        DEFVAL	{ valid }
        ::= { wfDs1E1DayIntervalEntry 16 }


    wfDs1E1DayTotalTable OBJECT-TYPE
        SYNTAX	SEQUENCE OF WfDs1E1DayTotalEntry
        ACCESS	not-accessible
        STATUS	mandatory
        DESCRIPTION
                "AT&T Total stats Table"
        ::= { wfDs1E1Group 26 }

    wfDs1E1DayTotalEntry OBJECT-TYPE
        SYNTAX	WfDs1E1DayTotalEntry
        ACCESS	not-accessible
        STATUS	mandatory
        DESCRIPTION
                "An entry in the DS1E1 Total table"
        INDEX	{ wfDs1E1DayTotalPortLineNumber }
        ::= { wfDs1E1DayTotalTable 1 }

    WfDs1E1DayTotalEntry ::= SEQUENCE {
    	    wfDs1E1DayTotalPortLineNumber
    		INTEGER,
    	    wfDs1E1DayTotalESs
    		Gauge,
    	    wfDs1E1DayTotalSESs
    		Gauge,
    	    wfDs1E1DayTotalSEFSs
    		Gauge,
    	    wfDs1E1DayTotalUASs
    		Gauge,
    	    wfDs1E1DayTotalCSSs
    		Gauge,
    	    wfDs1E1DayTotalPCVs
    		Gauge,
    	    wfDs1E1DayTotalLESs
    		Gauge,
    	    wfDs1E1DayTotalBESs
    		Gauge,
    	    wfDs1E1DayTotalDMs
    		Gauge,
    	    wfDs1E1DayTotalLCVs
    		Gauge,
    	    wfDs1E1DayTotalSASs
    		Gauge,
    	    wfDs1E1DayTotalAISSs
    		Gauge,
    	    wfDs1E1DayTotalFCs
    		Gauge,
	    wfDs1E1DayTotalValidFlag
		INTEGER
        }

    wfDs1E1DayTotalPortLineNumber OBJECT-TYPE
        SYNTAX	INTEGER
        ACCESS	read-only
        STATUS	mandatory
        DESCRIPTION
                "The instance ID that identifies the port. The port line number with a zero
                channel number field as found in the port map table."
        ::= { wfDs1E1DayTotalEntry 1 }

    wfDs1E1DayTotalESs OBJECT-TYPE
        SYNTAX	Gauge
        ACCESS	read-only
        STATUS	mandatory
        DESCRIPTION
                "The number of Errored Seconds, encountered by a DS1 interface in the 
                previous 8 day interval."
        ::= { wfDs1E1DayTotalEntry 2 }

    wfDs1E1DayTotalSESs OBJECT-TYPE
        SYNTAX	Gauge
        ACCESS	read-only
        STATUS	mandatory
        DESCRIPTION
                "The number of Severely Errored Seconds encountered by a DS1 interface in the
                previous 8 day interval."
        ::= { wfDs1E1DayTotalEntry 3 }

    wfDs1E1DayTotalSEFSs OBJECT-TYPE
        SYNTAX	Gauge
        ACCESS	read-only
        STATUS	mandatory
        DESCRIPTION
                "The number of Severely Errored Framing Seconds encountered by a DS1 interface
                in the previous 8 day interval."
        ::= { wfDs1E1DayTotalEntry 4 }

    wfDs1E1DayTotalUASs OBJECT-TYPE
        SYNTAX	Gauge
        ACCESS	read-only
        STATUS	mandatory
        DESCRIPTION
                "The number of Unavailable Seconds encountered by a DS1 interface in the
                previous 8 day interval."
        ::= { wfDs1E1DayTotalEntry 5 }

    wfDs1E1DayTotalCSSs OBJECT-TYPE
        SYNTAX	Gauge
        ACCESS	read-only
        STATUS	mandatory
        DESCRIPTION
                "The number of Controlled Slip Seconds encountered by a DS1 interface in the
                previous 8 day interval."
        ::= { wfDs1E1DayTotalEntry 6 }

    wfDs1E1DayTotalPCVs OBJECT-TYPE
        SYNTAX	Gauge
        ACCESS	read-only
        STATUS	mandatory
        DESCRIPTION
                "The number of Path Coding Violations encountered by a DS1 interface in the
                previous 8 day interval."
        ::= { wfDs1E1DayTotalEntry 7 }

    wfDs1E1DayTotalLESs OBJECT-TYPE
        SYNTAX	Gauge
        ACCESS	read-only
        STATUS	mandatory
        DESCRIPTION
                "The number of Line Errored Seconds encountered by a DS1 interface in the
                previous 8 day interval."
        ::= { wfDs1E1DayTotalEntry 8 }

    wfDs1E1DayTotalBESs OBJECT-TYPE
        SYNTAX	Gauge
        ACCESS	read-only
        STATUS	mandatory
        DESCRIPTION
                "The number of Bursty Errored Seconds (BESs) encountered by a DS1 interface
                in the previous 8 day interval."
        ::= { wfDs1E1DayTotalEntry 9 }

    wfDs1E1DayTotalDMs OBJECT-TYPE
        SYNTAX	Gauge
        ACCESS	read-only
        STATUS	mandatory
        DESCRIPTION
                "The number of Degraded Minutes (DMs) encountered by a DS1 interface in the
                previous 8 day interval."
        ::= { wfDs1E1DayTotalEntry 10 }

    wfDs1E1DayTotalLCVs OBJECT-TYPE
        SYNTAX	Gauge
        ACCESS	read-only
        STATUS	mandatory
        DESCRIPTION
                "The number of Line Code Violations (LCVs) encountered  by a DS1 interface in
                the previous 8 day interval."
        ::= { wfDs1E1DayTotalEntry 11 }

    wfDs1E1DayTotalSASs OBJECT-TYPE
        SYNTAX	Gauge
        ACCESS	read-only
        STATUS	mandatory
        DESCRIPTION
                "The number of seconds, in the previous 8 day interval,
		containing one or more SEFs or AIS defects."
        ::= { wfDs1E1DayTotalEntry 12 }

    wfDs1E1DayTotalAISSs OBJECT-TYPE
        SYNTAX	Gauge
        ACCESS	read-only
        STATUS	mandatory
        DESCRIPTION
                "The number of seconds, in the previous 8 day interval,
		 containing one or more AIS defect."
        ::= { wfDs1E1DayTotalEntry 13 }

    wfDs1E1DayTotalFCs OBJECT-TYPE
        SYNTAX	Gauge
        ACCESS	read-only
        STATUS	mandatory
        DESCRIPTION
                "The number of Path Failure Count error events detected
		in the previous 8 day interval."
        ::= { wfDs1E1DayTotalEntry 14 }

    wfDs1E1DayTotalValidFlag OBJECT-TYPE
        SYNTAX	INTEGER {
    		    valid(1),
    		    invalid(2)
    		}
        ACCESS	read-only
        STATUS	mandatory
        DESCRIPTION
                "Indicates whether this interval reported by the Mib Table is valid or
		invalid."
        DEFVAL	{ valid }
        ::= { wfDs1E1DayTotalEntry 15 }


    wfDs1E1FarEndCurrentTable OBJECT-TYPE
        SYNTAX	SEQUENCE OF WfDs1E1FarEndCurrentEntry
        ACCESS	not-accessible
        STATUS	mandatory
        DESCRIPTION
                "Current AT&T FDL stats table."
        ::= { wfDs1E1Group 27 }

    wfDs1E1FarEndCurrentEntry OBJECT-TYPE
        SYNTAX	WfDs1E1FarEndCurrentEntry
        ACCESS	not-accessible
        STATUS	mandatory
        DESCRIPTION
                "An entry in the DS1E1 Current table"
        INDEX	{ wfDs1E1FarEndCurrentPortLineNumber }
        ::= { wfDs1E1FarEndCurrentTable 1 }

    WfDs1E1FarEndCurrentEntry ::= SEQUENCE {
    	    wfDs1E1FarEndCurrentPortLineNumber
    		INTEGER,
    	    wfDs1E1FarEndCurrentESs
    		Gauge,
    	    wfDs1E1FarEndCurrentSESs
    		Gauge,
    	    wfDs1E1FarEndCurrentSEFSs
    		Gauge,
    	    wfDs1E1FarEndCurrentUASs
    		Gauge,
    	    wfDs1E1FarEndCurrentCSSs
    		Gauge,
    	    wfDs1E1FarEndCurrentPCVs
    		Gauge,
    	    wfDs1E1FarEndCurrentLESs
    		Gauge,
    	    wfDs1E1FarEndCurrentBESs
    		Gauge,
    	    wfDs1E1FarEndCurrentDMs
    		Gauge,
    	    wfDs1E1FarEndCurrentLCVs
    		Gauge,
    	    wfDs1E1FarEndCurrentSASs
    		Gauge,
    	    wfDs1E1FarEndCurrentAISSs
    		Gauge,
    	    wfDs1E1FarEndCurrentFCs
    		Gauge,
    	    wfDs1E1FarEndCurrentTimeElapsed
    		INTEGER,
	    wfDs1E1FarEndCurrentValidIntervals
		INTEGER,
	    wfDs1E1FarEndCurrentValidFlag
		INTEGER
        }

    wfDs1E1FarEndCurrentPortLineNumber OBJECT-TYPE
        SYNTAX	INTEGER
        ACCESS	read-only
        STATUS	mandatory
        DESCRIPTION
                "The instance ID that identifies the port. The port line number with a zero
                channel number field as found in the port map table."
        ::= { wfDs1E1FarEndCurrentEntry 1 }

    wfDs1E1FarEndCurrentESs OBJECT-TYPE
        SYNTAX	Gauge
        ACCESS	read-only
        STATUS	mandatory
        DESCRIPTION
                "The number of Errored Seconds, encountered by a DS1 interface in the
                current day interval."
        ::= { wfDs1E1FarEndCurrentEntry 2 }

    wfDs1E1FarEndCurrentSESs OBJECT-TYPE
        SYNTAX	Gauge
        ACCESS	read-only
        STATUS	mandatory
        DESCRIPTION
                "The number of Severely Errored Seconds encountered by a DS1 interface
                in the current day interval.'"
        ::= { wfDs1E1FarEndCurrentEntry 3 }

    wfDs1E1FarEndCurrentSEFSs OBJECT-TYPE
        SYNTAX	Gauge
        ACCESS	read-only
        STATUS	mandatory
        DESCRIPTION
                "The number of Severely Errored Framing Seconds encountered  by  a DS1
                interface in the current day interval."
        ::= { wfDs1E1FarEndCurrentEntry 4 }

    wfDs1E1FarEndCurrentUASs OBJECT-TYPE
        SYNTAX	Gauge
        ACCESS	read-only
        STATUS	mandatory
        DESCRIPTION
                "The number of Unavailable Seconds encountered by a DS1 interface in the
                current day interval."
        ::= { wfDs1E1FarEndCurrentEntry 5 }

    wfDs1E1FarEndCurrentCSSs OBJECT-TYPE
        SYNTAX	Gauge
        ACCESS	read-only
        STATUS	mandatory
        DESCRIPTION
                "The number of Controlled Slip Seconds encountered by a DS1 interface in the
                current day interval."
        ::= { wfDs1E1FarEndCurrentEntry 6 }

    wfDs1E1FarEndCurrentPCVs OBJECT-TYPE
        SYNTAX	Gauge
        ACCESS	read-only
        STATUS	mandatory
        DESCRIPTION
                "The number of Path Coding Violations encountered by a DS1 interface in the
                current day interval."
        ::= { wfDs1E1FarEndCurrentEntry 7 }

    wfDs1E1FarEndCurrentLESs OBJECT-TYPE
        SYNTAX	Gauge
        ACCESS	read-only
        STATUS	mandatory
        DESCRIPTION
                "The number of Line Errored Seconds encountered by a DS1 interface in the
                current day interval.'"
        ::= { wfDs1E1FarEndCurrentEntry 8 }

    wfDs1E1FarEndCurrentBESs OBJECT-TYPE
        SYNTAX	Gauge
        ACCESS	read-only
        STATUS	mandatory
        DESCRIPTION
                "The number of Bursty Errored Seconds (BESs) encountered by a DS1 interface
                in the current day interval."
        ::= { wfDs1E1FarEndCurrentEntry 9 }

    wfDs1E1FarEndCurrentDMs OBJECT-TYPE
        SYNTAX	Gauge
        ACCESS	read-only
        STATUS	mandatory
        DESCRIPTION
                "The number of Degraded Minutes (DMs) encountered by a DS1 interface in
                the current day interval.'"
        ::= { wfDs1E1FarEndCurrentEntry 10 }

    wfDs1E1FarEndCurrentLCVs OBJECT-TYPE
        SYNTAX	Gauge
        ACCESS	read-only
        STATUS	mandatory
        DESCRIPTION
                "The number of Line Code Violations (LCVs) encountered  by a DS1 interface in
                the current day interval.'"
        ::= { wfDs1E1FarEndCurrentEntry 11 }

    wfDs1E1FarEndCurrentSASs OBJECT-TYPE
        SYNTAX	Gauge
        ACCESS	read-only
        STATUS	mandatory
        DESCRIPTION
                "The number of seconds, within the current day interval,
		containing one or more SEFs or AIS defects."
        ::= { wfDs1E1FarEndCurrentEntry 12 }

    wfDs1E1FarEndCurrentAISSs OBJECT-TYPE
        SYNTAX	Gauge
        ACCESS	read-only
        STATUS	mandatory
        DESCRIPTION
                "The number of seconds, within the current day interval,
		 containing one or more AIS defect."
        ::= { wfDs1E1FarEndCurrentEntry 13 }

    wfDs1E1FarEndCurrentFCs OBJECT-TYPE
        SYNTAX	Gauge
        ACCESS	read-only
        STATUS	mandatory
        DESCRIPTION
                "The number of Path Failure Count error events detected
                in the current day interval."
        ::= { wfDs1E1FarEndCurrentEntry 14 }

    wfDs1E1FarEndCurrentTimeElapsed OBJECT-TYPE
        SYNTAX	INTEGER
        ACCESS	read-only
        STATUS	mandatory
        DESCRIPTION
                "The number of seconds that have elapsed since the beginning of the
                current error-measurement period."
        ::= { wfDs1E1FarEndCurrentEntry 15 }

    wfDs1E1FarEndCurrentValidIntervals OBJECT-TYPE
        SYNTAX	INTEGER
        ACCESS	read-only
        STATUS	mandatory
        DESCRIPTION
                "The number of previous intervals for which valid data was collected. The
                value will be 8 unless the interface was brought on-line within the last
                8 days, in which case the value will be the number of complete day
                intervals the since interface has been online."
        ::= { wfDs1E1FarEndCurrentEntry 16 }

    wfDs1E1FarEndCurrentValidFlag OBJECT-TYPE
        SYNTAX	INTEGER {
    		    valid(1),
    		    invalid(2)
    		}
        ACCESS	read-only
        STATUS	mandatory
        DESCRIPTION
                "Indicates whether this interval reported by the Mib Table is valid or
		invalid."
        DEFVAL	{ valid }
        ::= { wfDs1E1FarEndCurrentEntry 17 }


    wfDs1E1FarEndIntervalTable OBJECT-TYPE
        SYNTAX	SEQUENCE OF WfDs1E1FarEndIntervalEntry
        ACCESS	not-accessible
        STATUS	mandatory
        DESCRIPTION
                "AT&T Interval stats"
        ::= { wfDs1E1Group 28 }

    wfDs1E1FarEndIntervalEntry OBJECT-TYPE
        SYNTAX	WfDs1E1FarEndIntervalEntry
        ACCESS	not-accessible
        STATUS	mandatory
        DESCRIPTION
                "An entry in the DS1E1 Interval table"
        INDEX	{ wfDs1E1FarEndIntervalPortLineNumber,
    		  wfDs1E1FarEndIntervalNumber }
        ::= { wfDs1E1FarEndIntervalTable 1 }

    WfDs1E1FarEndIntervalEntry ::= SEQUENCE {
    	    wfDs1E1FarEndIntervalPortLineNumber
    		INTEGER,
    	    wfDs1E1FarEndIntervalNumber
    		INTEGER,
    	    wfDs1E1FarEndIntervalESs
    		Gauge,
    	    wfDs1E1FarEndIntervalSESs
    		Gauge,
    	    wfDs1E1FarEndIntervalSEFSs
    		Gauge,
    	    wfDs1E1FarEndIntervalUASs
    		Gauge,
    	    wfDs1E1FarEndIntervalCSSs
    		Gauge,
    	    wfDs1E1FarEndIntervalPCVs
    		Gauge,
    	    wfDs1E1FarEndIntervalLESs
    		Gauge,
    	    wfDs1E1FarEndIntervalBESs
    		Gauge,
    	    wfDs1E1FarEndIntervalDMs
    		Gauge,
    	    wfDs1E1FarEndIntervalLCVs
    		Gauge,
    	    wfDs1E1FarEndIntervalSASs
    		Gauge,
    	    wfDs1E1FarEndIntervalAISSs
    		Gauge,
    	    wfDs1E1FarEndIntervalFCs
    		Gauge,
	    wfDs1E1FarEndIntervalValidFlag
		INTEGER
        }

    wfDs1E1FarEndIntervalPortLineNumber OBJECT-TYPE
        SYNTAX	INTEGER
        ACCESS	read-only
        STATUS	mandatory
        DESCRIPTION
                "The instance ID that identifies the port. The port line number with a zero
                channel number field as found in the port map table."
        ::= { wfDs1E1FarEndIntervalEntry 1 }

    wfDs1E1FarEndIntervalNumber OBJECT-TYPE
        SYNTAX	INTEGER
        ACCESS	read-only
        STATUS	mandatory
        DESCRIPTION
                "A number between 1 and 8, where 1 is the most recently completed day
                interval and 8 is the least recently completed day interval (assuming
                that all 8 intervals are valid)."
        ::= { wfDs1E1FarEndIntervalEntry 2 }

    wfDs1E1FarEndIntervalESs OBJECT-TYPE
        SYNTAX	Gauge
        ACCESS	read-only
        STATUS	mandatory
        DESCRIPTION
                "The number of Errored Seconds, encountered by a DS1 interface in the current
                day interval."
        ::= { wfDs1E1FarEndIntervalEntry 3 }

    wfDs1E1FarEndIntervalSESs OBJECT-TYPE
        SYNTAX	Gauge
        ACCESS	read-only
        STATUS	mandatory
        DESCRIPTION
                "The number of Severely Errored Seconds encountered by a DS1 interface in one
                of the previous day intervals."
        ::= { wfDs1E1FarEndIntervalEntry 4 }

    wfDs1E1FarEndIntervalSEFSs OBJECT-TYPE
        SYNTAX	Gauge
        ACCESS	read-only
        STATUS	mandatory
        DESCRIPTION
                "The number of Severely Errored Framing Seconds encountered by a DS1 interface
                in one of the previous day intervals."
        ::= { wfDs1E1FarEndIntervalEntry 5 }

    wfDs1E1FarEndIntervalUASs OBJECT-TYPE
        SYNTAX	Gauge
        ACCESS	read-only
        STATUS	mandatory
        DESCRIPTION
                "The number of Unavailable Seconds encountered by a DS1 interface in one of the
                previous day intervals."
        ::= { wfDs1E1FarEndIntervalEntry 6 }

    wfDs1E1FarEndIntervalCSSs OBJECT-TYPE
        SYNTAX	Gauge
        ACCESS	read-only
        STATUS	mandatory
        DESCRIPTION
                "The number of Controlled Slip Seconds encountered by a DS1 interface in one
                of the previous day intervals."
        ::= { wfDs1E1FarEndIntervalEntry 7 }

    wfDs1E1FarEndIntervalPCVs OBJECT-TYPE
        SYNTAX	Gauge
        ACCESS	read-only
        STATUS	mandatory
        DESCRIPTION
                "The number of Path Coding Violations encountered by a DS1 interface in one of
                the previous day intervals."
        ::= { wfDs1E1FarEndIntervalEntry 8 }

    wfDs1E1FarEndIntervalLESs OBJECT-TYPE
        SYNTAX	Gauge
        ACCESS	read-only
        STATUS	mandatory
        DESCRIPTION
                "The number of Line Errored Seconds encountered by a DS1 interface in one of
                the previous day intervals."
        ::= { wfDs1E1FarEndIntervalEntry 9 }

    wfDs1E1FarEndIntervalBESs OBJECT-TYPE
        SYNTAX	Gauge
        ACCESS	read-only
        STATUS	mandatory
        DESCRIPTION
                "The number of Bursty Errored Seconds (BESs) encountered by a DS1 interface in
                one of the previous day intervals."
        ::= { wfDs1E1FarEndIntervalEntry 10 }

    wfDs1E1FarEndIntervalDMs OBJECT-TYPE
        SYNTAX	Gauge
        ACCESS	read-only
        STATUS	mandatory
        DESCRIPTION
                "The number of Degraded Minutes (DMs) encountered by a DS1 interface in one of
                the previous day intervals."
        ::= { wfDs1E1FarEndIntervalEntry 11 }

    wfDs1E1FarEndIntervalLCVs OBJECT-TYPE
        SYNTAX	Gauge
        ACCESS	read-only
        STATUS	mandatory
        DESCRIPTION
                "The number of Line Code Violations (LCVs) encountered by a DS1 interface in
                one of the previous day intervals."
        ::= { wfDs1E1FarEndIntervalEntry 12 }

    wfDs1E1FarEndIntervalSASs OBJECT-TYPE
        SYNTAX	Gauge
        ACCESS	read-only
        STATUS	mandatory
        DESCRIPTION
                "The number of seconds, in one of the previous day intervals,
		containing one or more SEFs or AIS defects."
        ::= { wfDs1E1FarEndIntervalEntry 13 }

    wfDs1E1FarEndIntervalAISSs OBJECT-TYPE
        SYNTAX	Gauge
        ACCESS	read-only
        STATUS	mandatory
        DESCRIPTION
                "The number of seconds, in one of the previous day intervals,
		 containing one or more AIS defect."
        ::= { wfDs1E1FarEndIntervalEntry 14 }

    wfDs1E1FarEndIntervalFCs OBJECT-TYPE
        SYNTAX	Gauge
        ACCESS	read-only
        STATUS	mandatory
        DESCRIPTION
                "The number of Path Failure Count error events detected
		one of the previous day intervals."
        ::= { wfDs1E1FarEndIntervalEntry 15 }

    wfDs1E1FarEndIntervalValidFlag OBJECT-TYPE
        SYNTAX	INTEGER {
    		    valid(1),
    		    invalid(2)
    		}
        ACCESS	read-only
        STATUS	mandatory
        DESCRIPTION
                "Indicates whether this interval reported by the Mib Table is valid or
		invalid."
        DEFVAL	{ valid }
        ::= { wfDs1E1FarEndIntervalEntry 16 }


    wfDs1E1FarEndTotalTable OBJECT-TYPE
        SYNTAX	SEQUENCE OF WfDs1E1FarEndTotalEntry
        ACCESS	not-accessible
        STATUS	mandatory
        DESCRIPTION
                "AT&T Total stats Table"
        ::= { wfDs1E1Group 29 }

    wfDs1E1FarEndTotalEntry OBJECT-TYPE
        SYNTAX	WfDs1E1FarEndTotalEntry
        ACCESS	not-accessible
        STATUS	mandatory
        DESCRIPTION
                "An entry in the DS1E1 Total table"
        INDEX	{ wfDs1E1FarEndTotalPortLineNumber }
        ::= { wfDs1E1FarEndTotalTable 1 }

    WfDs1E1FarEndTotalEntry ::= SEQUENCE {
    	    wfDs1E1FarEndTotalPortLineNumber
    		INTEGER,
    	    wfDs1E1FarEndTotalESs
    		Gauge,
    	    wfDs1E1FarEndTotalSESs
    		Gauge,
    	    wfDs1E1FarEndTotalSEFSs
    		Gauge,
    	    wfDs1E1FarEndTotalUASs
    		Gauge,
    	    wfDs1E1FarEndTotalCSSs
    		Gauge,
    	    wfDs1E1FarEndTotalPCVs
    		Gauge,
    	    wfDs1E1FarEndTotalLESs
    		Gauge,
    	    wfDs1E1FarEndTotalBESs
    		Gauge,
    	    wfDs1E1FarEndTotalDMs
    		Gauge,
    	    wfDs1E1FarEndTotalLCVs
    		Gauge,
    	    wfDs1E1FarEndTotalSASs
    		Gauge,
    	    wfDs1E1FarEndTotalAISSs
    		Gauge,
    	    wfDs1E1FarEndTotalFCs
    		Gauge,
	    wfDs1E1FarEndTotalValidFlag
		INTEGER
        }

    wfDs1E1FarEndTotalPortLineNumber OBJECT-TYPE
        SYNTAX	INTEGER
        ACCESS	read-only
        STATUS	mandatory
        DESCRIPTION
                "The instance ID that identifies the port. The port line number with a zero
                channel number field as found in the port map table."
        ::= { wfDs1E1FarEndTotalEntry 1 }

    wfDs1E1FarEndTotalESs OBJECT-TYPE
        SYNTAX	Gauge
        ACCESS	read-only
        STATUS	mandatory
        DESCRIPTION
                "The number of Errored Seconds, encountered by a DS1 interface in the 
                previous 8 day interval."
        ::= { wfDs1E1FarEndTotalEntry 2 }

    wfDs1E1FarEndTotalSESs OBJECT-TYPE
        SYNTAX	Gauge
        ACCESS	read-only
        STATUS	mandatory
        DESCRIPTION
                "The number of Severely Errored Seconds encountered by a DS1 interface in the
                previous 8 day interval."
        ::= { wfDs1E1FarEndTotalEntry 3 }

    wfDs1E1FarEndTotalSEFSs OBJECT-TYPE
        SYNTAX	Gauge
        ACCESS	read-only
        STATUS	mandatory
        DESCRIPTION
                "The number of Severely Errored Framing Seconds encountered by a DS1 interface
                in the previous 8 day interval."
        ::= { wfDs1E1FarEndTotalEntry 4 }

    wfDs1E1FarEndTotalUASs OBJECT-TYPE
        SYNTAX	Gauge
        ACCESS	read-only
        STATUS	mandatory
        DESCRIPTION
                "The number of Unavailable Seconds encountered by a DS1 interface in the
                previous 8 day interval."
        ::= { wfDs1E1FarEndTotalEntry 5 }

    wfDs1E1FarEndTotalCSSs OBJECT-TYPE
        SYNTAX	Gauge
        ACCESS	read-only
        STATUS	mandatory
        DESCRIPTION
                "The number of Controlled Slip Seconds encountered by a DS1 interface in the
                previous 8 day interval."
        ::= { wfDs1E1FarEndTotalEntry 6 }

    wfDs1E1FarEndTotalPCVs OBJECT-TYPE
        SYNTAX	Gauge
        ACCESS	read-only
        STATUS	mandatory
        DESCRIPTION
                "The number of Path Coding Violations encountered by a DS1 interface in the
                previous 8 day interval."
        ::= { wfDs1E1FarEndTotalEntry 7 }

    wfDs1E1FarEndTotalLESs OBJECT-TYPE
        SYNTAX	Gauge
        ACCESS	read-only
        STATUS	mandatory
        DESCRIPTION
                "The number of Line Errored Seconds encountered by a DS1 interface in the
                previous 8 day interval."
        ::= { wfDs1E1FarEndTotalEntry 8 }

    wfDs1E1FarEndTotalBESs OBJECT-TYPE
        SYNTAX	Gauge
        ACCESS	read-only
        STATUS	mandatory
        DESCRIPTION
                "The number of Bursty Errored Seconds (BESs) encountered by a DS1 interface
                in the previous 8 day interval."
        ::= { wfDs1E1FarEndTotalEntry 9 }

    wfDs1E1FarEndTotalDMs OBJECT-TYPE
        SYNTAX	Gauge
        ACCESS	read-only
        STATUS	mandatory
        DESCRIPTION
                "The number of Degraded Minutes (DMs) encountered by a DS1 interface in the
                previous 8 day interval."
        ::= { wfDs1E1FarEndTotalEntry 10 }

    wfDs1E1FarEndTotalLCVs OBJECT-TYPE
        SYNTAX	Gauge
        ACCESS	read-only
        STATUS	mandatory
        DESCRIPTION
                "The number of Line Code Violations (LCVs) encountered  by a DS1 interface in
                the previous 8 day interval."
        ::= { wfDs1E1FarEndTotalEntry 11 }

    wfDs1E1FarEndTotalSASs OBJECT-TYPE
        SYNTAX	Gauge
        ACCESS	read-only
        STATUS	mandatory
        DESCRIPTION
                "The number of seconds, in the previous 8 day interval,
		containing one or more SEFs or AIS defects."
        ::= { wfDs1E1FarEndTotalEntry 12 }

    wfDs1E1FarEndTotalAISSs OBJECT-TYPE
        SYNTAX	Gauge
        ACCESS	read-only
        STATUS	mandatory
        DESCRIPTION
                "The number of seconds, in the previous 8 day interval,
		 containing one or more AIS defect."
        ::= { wfDs1E1FarEndTotalEntry 13 }

    wfDs1E1FarEndTotalFCs OBJECT-TYPE
        SYNTAX	Gauge
        ACCESS	read-only
        STATUS	mandatory
        DESCRIPTION
                "The number of Path Failure Count error events detected
		in the previous 8 day interval."
        ::= { wfDs1E1FarEndTotalEntry 14 }

    wfDs1E1FarEndTotalValidFlag OBJECT-TYPE
        SYNTAX	INTEGER {
    		    valid(1),
    		    invalid(2)
    		}
        ACCESS	read-only
        STATUS	mandatory
        DESCRIPTION
                "Indicates whether this interval reported by the Mib Table is valid or
		invalid."
        DEFVAL	{ valid }
        ::= { wfDs1E1FarEndTotalEntry 15 }


    wfDs1E1FarEndDayCurrentTable OBJECT-TYPE
        SYNTAX	SEQUENCE OF WfDs1E1FarEndDayCurrentEntry
        ACCESS	not-accessible
        STATUS	mandatory
        DESCRIPTION
                "Current AT&T FDL stats table."
        ::= { wfDs1E1Group 30 }

    wfDs1E1FarEndDayCurrentEntry OBJECT-TYPE
        SYNTAX	WfDs1E1FarEndDayCurrentEntry
        ACCESS	not-accessible
        STATUS	mandatory
        DESCRIPTION
                "An entry in the DS1E1 Current table"
        INDEX	{ wfDs1E1FarEndDayCurrentPortLineNumber }
        ::= { wfDs1E1FarEndDayCurrentTable 1 }

    WfDs1E1FarEndDayCurrentEntry ::= SEQUENCE {
    	    wfDs1E1FarEndDayCurrentPortLineNumber
    		INTEGER,
    	    wfDs1E1FarEndDayCurrentESs
    		Gauge,
    	    wfDs1E1FarEndDayCurrentSESs
    		Gauge,
    	    wfDs1E1FarEndDayCurrentSEFSs
    		Gauge,
    	    wfDs1E1FarEndDayCurrentUASs
    		Gauge,
    	    wfDs1E1FarEndDayCurrentCSSs
    		Gauge,
    	    wfDs1E1FarEndDayCurrentPCVs
    		Gauge,
    	    wfDs1E1FarEndDayCurrentLESs
    		Gauge,
    	    wfDs1E1FarEndDayCurrentBESs
    		Gauge,
    	    wfDs1E1FarEndDayCurrentDMs
    		Gauge,
    	    wfDs1E1FarEndDayCurrentLCVs
    		Gauge,
    	    wfDs1E1FarEndDayCurrentSASs
    		Gauge,
    	    wfDs1E1FarEndDayCurrentAISSs
    		Gauge,
    	    wfDs1E1FarEndDayCurrentFCs
    		Gauge,
    	    wfDs1E1FarEndDayCurrentTimeElapsed
    		INTEGER,
	    wfDs1E1FarEndDayCurrentValidIntervals
		INTEGER,
	    wfDs1E1FarEndDayCurrentValidFlag
		INTEGER
        }

    wfDs1E1FarEndDayCurrentPortLineNumber OBJECT-TYPE
        SYNTAX	INTEGER
        ACCESS	read-only
        STATUS	mandatory
        DESCRIPTION
                "The instance ID that identifies the port. The port line number with a zero
                channel number field as found in the port map table."
        ::= { wfDs1E1FarEndDayCurrentEntry 1 }

    wfDs1E1FarEndDayCurrentESs OBJECT-TYPE
        SYNTAX	Gauge
        ACCESS	read-only
        STATUS	mandatory
        DESCRIPTION
                "The number of Errored Seconds, encountered by a DS1 interface in the
                current day interval."
        ::= { wfDs1E1FarEndDayCurrentEntry 2 }

    wfDs1E1FarEndDayCurrentSESs OBJECT-TYPE
        SYNTAX	Gauge
        ACCESS	read-only
        STATUS	mandatory
        DESCRIPTION
                "The number of Severely Errored Seconds encountered by a DS1 interface
                in the current day interval.'"
        ::= { wfDs1E1FarEndDayCurrentEntry 3 }

    wfDs1E1FarEndDayCurrentSEFSs OBJECT-TYPE
        SYNTAX	Gauge
        ACCESS	read-only
        STATUS	mandatory
        DESCRIPTION
                "The number of Severely Errored Framing Seconds encountered  by  a DS1
                interface in the current day interval."
        ::= { wfDs1E1FarEndDayCurrentEntry 4 }

    wfDs1E1FarEndDayCurrentUASs OBJECT-TYPE
        SYNTAX	Gauge
        ACCESS	read-only
        STATUS	mandatory
        DESCRIPTION
                "The number of Unavailable Seconds encountered by a DS1 interface in the
                current day interval."
        ::= { wfDs1E1FarEndDayCurrentEntry 5 }

    wfDs1E1FarEndDayCurrentCSSs OBJECT-TYPE
        SYNTAX	Gauge
        ACCESS	read-only
        STATUS	mandatory
        DESCRIPTION
                "The number of Controlled Slip Seconds encountered by a DS1 interface in the
                current day interval."
        ::= { wfDs1E1FarEndDayCurrentEntry 6 }

    wfDs1E1FarEndDayCurrentPCVs OBJECT-TYPE
        SYNTAX	Gauge
        ACCESS	read-only
        STATUS	mandatory
        DESCRIPTION
                "The number of Path Coding Violations encountered by a DS1 interface in the
                current day interval."
        ::= { wfDs1E1FarEndDayCurrentEntry 7 }

    wfDs1E1FarEndDayCurrentLESs OBJECT-TYPE
        SYNTAX	Gauge
        ACCESS	read-only
        STATUS	mandatory
        DESCRIPTION
                "The number of Line Errored Seconds encountered by a DS1 interface in the
                current day interval.'"
        ::= { wfDs1E1FarEndDayCurrentEntry 8 }

    wfDs1E1FarEndDayCurrentBESs OBJECT-TYPE
        SYNTAX	Gauge
        ACCESS	read-only
        STATUS	mandatory
        DESCRIPTION
                "The number of Bursty Errored Seconds (BESs) encountered by a DS1 interface
                in the current day interval."
        ::= { wfDs1E1FarEndDayCurrentEntry 9 }

    wfDs1E1FarEndDayCurrentDMs OBJECT-TYPE
        SYNTAX	Gauge
        ACCESS	read-only
        STATUS	mandatory
        DESCRIPTION
                "The number of Degraded Minutes (DMs) encountered by a DS1 interface in
                the current day interval.'"
        ::= { wfDs1E1FarEndDayCurrentEntry 10 }

    wfDs1E1FarEndDayCurrentLCVs OBJECT-TYPE
        SYNTAX	Gauge
        ACCESS	read-only
        STATUS	mandatory
        DESCRIPTION
                "The number of Line Code Violations (LCVs) encountered  by a DS1 interface in
                the current day interval.'"
        ::= { wfDs1E1FarEndDayCurrentEntry 11 }

    wfDs1E1FarEndDayCurrentSASs OBJECT-TYPE
        SYNTAX	Gauge
        ACCESS	read-only
        STATUS	mandatory
        DESCRIPTION
                "The number of seconds, within the current day interval,
		containing one or more SEFs or AIS defects."
        ::= { wfDs1E1FarEndDayCurrentEntry 12 }

    wfDs1E1FarEndDayCurrentAISSs OBJECT-TYPE
        SYNTAX	Gauge
        ACCESS	read-only
        STATUS	mandatory
        DESCRIPTION
                "The number of seconds, within the current day interval,
		 containing one or more AIS defect."
        ::= { wfDs1E1FarEndDayCurrentEntry 13 }

    wfDs1E1FarEndDayCurrentFCs OBJECT-TYPE
        SYNTAX	Gauge
        ACCESS	read-only
        STATUS	mandatory
        DESCRIPTION
                "The number of Path Failure Count error events detected
                in the current day interval."
        ::= { wfDs1E1FarEndDayCurrentEntry 14 }

    wfDs1E1FarEndDayCurrentTimeElapsed OBJECT-TYPE
        SYNTAX	INTEGER
        ACCESS	read-only
        STATUS	mandatory
        DESCRIPTION
                "The number of seconds that have elapsed since the beginning of the
                current error-measurement period."
        ::= { wfDs1E1FarEndDayCurrentEntry 15 }

    wfDs1E1FarEndDayCurrentValidIntervals OBJECT-TYPE
        SYNTAX	INTEGER
        ACCESS	read-only
        STATUS	mandatory
        DESCRIPTION
                "The number of previous intervals for which valid data was collected. The
                value will be 8 unless the interface was brought on-line within the last
                8 days, in which case the value will be the number of complete day
                intervals the since interface has been online."
        ::= { wfDs1E1FarEndDayCurrentEntry 16 }

    wfDs1E1FarEndDayCurrentValidFlag OBJECT-TYPE
        SYNTAX	INTEGER {
    		    valid(1),
    		    invalid(2)
    		}
        ACCESS	read-only
        STATUS	mandatory
        DESCRIPTION
                "Indicates whether this interval reported by the Mib Table is valid or
		invalid."
        DEFVAL	{ valid }
        ::= { wfDs1E1FarEndDayCurrentEntry 17 }


    wfDs1E1FarEndDayIntervalTable OBJECT-TYPE
        SYNTAX	SEQUENCE OF WfDs1E1FarEndDayIntervalEntry
        ACCESS	not-accessible
        STATUS	mandatory
        DESCRIPTION
                "AT&T Interval stats"
        ::= { wfDs1E1Group 31 }

    wfDs1E1FarEndDayIntervalEntry OBJECT-TYPE
        SYNTAX	WfDs1E1FarEndDayIntervalEntry
        ACCESS	not-accessible
        STATUS	mandatory
        DESCRIPTION
                "An entry in the DS1E1 Interval table"
        INDEX	{ wfDs1E1FarEndDayIntervalPortLineNumber,
    		  wfDs1E1FarEndDayIntervalNumber }
        ::= { wfDs1E1FarEndDayIntervalTable 1 }

    WfDs1E1FarEndDayIntervalEntry ::= SEQUENCE {
    	    wfDs1E1FarEndDayIntervalPortLineNumber
    		INTEGER,
    	    wfDs1E1FarEndDayIntervalNumber
    		INTEGER,
    	    wfDs1E1FarEndDayIntervalESs
    		Gauge,
    	    wfDs1E1FarEndDayIntervalSESs
    		Gauge,
    	    wfDs1E1FarEndDayIntervalSEFSs
    		Gauge,
    	    wfDs1E1FarEndDayIntervalUASs
    		Gauge,
    	    wfDs1E1FarEndDayIntervalCSSs
    		Gauge,
    	    wfDs1E1FarEndDayIntervalPCVs
    		Gauge,
    	    wfDs1E1FarEndDayIntervalLESs
    		Gauge,
    	    wfDs1E1FarEndDayIntervalBESs
    		Gauge,
    	    wfDs1E1FarEndDayIntervalDMs
    		Gauge,
    	    wfDs1E1FarEndDayIntervalLCVs
    		Gauge,
    	    wfDs1E1FarEndDayIntervalSASs
    		Gauge,
    	    wfDs1E1FarEndDayIntervalAISSs
    		Gauge,
    	    wfDs1E1FarEndDayIntervalFCs
    		Gauge,
	    wfDs1E1FarEndDayIntervalValidFlag
		INTEGER
        }

    wfDs1E1FarEndDayIntervalPortLineNumber OBJECT-TYPE
        SYNTAX	INTEGER
        ACCESS	read-only
        STATUS	mandatory
        DESCRIPTION
                "The instance ID that identifies the port. The port line number with a zero
                channel number field as found in the port map table."
        ::= { wfDs1E1FarEndDayIntervalEntry 1 }

    wfDs1E1FarEndDayIntervalNumber OBJECT-TYPE
        SYNTAX	INTEGER
        ACCESS	read-only
        STATUS	mandatory
        DESCRIPTION
                "A number between 1 and 8, where 1 is the most recently completed day
                interval and 8 is the least recently completed day interval (assuming
                that all 8 intervals are valid)."
        ::= { wfDs1E1FarEndDayIntervalEntry 2 }

    wfDs1E1FarEndDayIntervalESs OBJECT-TYPE
        SYNTAX	Gauge
        ACCESS	read-only
        STATUS	mandatory
        DESCRIPTION
                "The number of Errored Seconds, encountered by a DS1 interface in the current
                day interval."
        ::= { wfDs1E1FarEndDayIntervalEntry 3 }

    wfDs1E1FarEndDayIntervalSESs OBJECT-TYPE
        SYNTAX	Gauge
        ACCESS	read-only
        STATUS	mandatory
        DESCRIPTION
                "The number of Severely Errored Seconds encountered by a DS1 interface in one
                of the previous day intervals."
        ::= { wfDs1E1FarEndDayIntervalEntry 4 }

    wfDs1E1FarEndDayIntervalSEFSs OBJECT-TYPE
        SYNTAX	Gauge
        ACCESS	read-only
        STATUS	mandatory
        DESCRIPTION
                "The number of Severely Errored Framing Seconds encountered by a DS1 interface
                in one of the previous day intervals."
        ::= { wfDs1E1FarEndDayIntervalEntry 5 }

    wfDs1E1FarEndDayIntervalUASs OBJECT-TYPE
        SYNTAX	Gauge
        ACCESS	read-only
        STATUS	mandatory
        DESCRIPTION
                "The number of Unavailable Seconds encountered by a DS1 interface in one of the
                previous day intervals."
        ::= { wfDs1E1FarEndDayIntervalEntry 6 }

    wfDs1E1FarEndDayIntervalCSSs OBJECT-TYPE
        SYNTAX	Gauge
        ACCESS	read-only
        STATUS	mandatory
        DESCRIPTION
                "The number of Controlled Slip Seconds encountered by a DS1 interface in one
                of the previous day intervals."
        ::= { wfDs1E1FarEndDayIntervalEntry 7 }

    wfDs1E1FarEndDayIntervalPCVs OBJECT-TYPE
        SYNTAX	Gauge
        ACCESS	read-only
        STATUS	mandatory
        DESCRIPTION
                "The number of Path Coding Violations encountered by a DS1 interface in one of
                the previous day intervals."
        ::= { wfDs1E1FarEndDayIntervalEntry 8 }

    wfDs1E1FarEndDayIntervalLESs OBJECT-TYPE
        SYNTAX	Gauge
        ACCESS	read-only
        STATUS	mandatory
        DESCRIPTION
                "The number of Line Errored Seconds encountered by a DS1 interface in one of
                the previous day intervals."
        ::= { wfDs1E1FarEndDayIntervalEntry 9 }

    wfDs1E1FarEndDayIntervalBESs OBJECT-TYPE
        SYNTAX	Gauge
        ACCESS	read-only
        STATUS	mandatory
        DESCRIPTION
                "The number of Bursty Errored Seconds (BESs) encountered by a DS1 interface in
                one of the previous day intervals."
        ::= { wfDs1E1FarEndDayIntervalEntry 10 }

    wfDs1E1FarEndDayIntervalDMs OBJECT-TYPE
        SYNTAX	Gauge
        ACCESS	read-only
        STATUS	mandatory
        DESCRIPTION
                "The number of Degraded Minutes (DMs) encountered by a DS1 interface in one of
                the previous day intervals."
        ::= { wfDs1E1FarEndDayIntervalEntry 11 }

    wfDs1E1FarEndDayIntervalLCVs OBJECT-TYPE
        SYNTAX	Gauge
        ACCESS	read-only
        STATUS	mandatory
        DESCRIPTION
                "The number of Line Code Violations (LCVs) encountered by a DS1 interface in
                one of the previous day intervals."
        ::= { wfDs1E1FarEndDayIntervalEntry 12 }

    wfDs1E1FarEndDayIntervalSASs OBJECT-TYPE
        SYNTAX	Gauge
        ACCESS	read-only
        STATUS	mandatory
        DESCRIPTION
                "The number of seconds, in one of the previous day intervals,
		containing one or more SEFs or AIS defects."
        ::= { wfDs1E1FarEndDayIntervalEntry 13 }

    wfDs1E1FarEndDayIntervalAISSs OBJECT-TYPE
        SYNTAX	Gauge
        ACCESS	read-only
        STATUS	mandatory
        DESCRIPTION
                "The number of seconds, in one of the previous day intervals,
		 containing one or more AIS defect."
        ::= { wfDs1E1FarEndDayIntervalEntry 14 }

    wfDs1E1FarEndDayIntervalFCs OBJECT-TYPE
        SYNTAX	Gauge
        ACCESS	read-only
        STATUS	mandatory
        DESCRIPTION
                "The number of Path Failure Count error events detected
		one of the previous day intervals."
        ::= { wfDs1E1FarEndDayIntervalEntry 15 }

    wfDs1E1FarEndDayIntervalValidFlag OBJECT-TYPE
        SYNTAX	INTEGER {
    		    valid(1),
    		    invalid(2)
    		}
        ACCESS	read-only
        STATUS	mandatory
        DESCRIPTION
                "Indicates whether this interval reported by the Mib Table is valid or
		invalid."
        DEFVAL	{ valid }
        ::= { wfDs1E1FarEndDayIntervalEntry 16 }


    wfDs1E1FarEndDayTotalTable OBJECT-TYPE
        SYNTAX	SEQUENCE OF WfDs1E1FarEndDayTotalEntry
        ACCESS	not-accessible
        STATUS	mandatory
        DESCRIPTION
                "AT&T Total stats Table"
        ::= { wfDs1E1Group 32 }

    wfDs1E1FarEndDayTotalEntry OBJECT-TYPE
        SYNTAX	WfDs1E1FarEndDayTotalEntry
        ACCESS	not-accessible
        STATUS	mandatory
        DESCRIPTION
                "An entry in the DS1E1 Total table"
        INDEX	{ wfDs1E1FarEndDayTotalPortLineNumber }
        ::= { wfDs1E1FarEndDayTotalTable 1 }

    WfDs1E1FarEndDayTotalEntry ::= SEQUENCE {
    	    wfDs1E1FarEndDayTotalPortLineNumber
    		INTEGER,
    	    wfDs1E1FarEndDayTotalESs
    		Gauge,
    	    wfDs1E1FarEndDayTotalSESs
    		Gauge,
    	    wfDs1E1FarEndDayTotalSEFSs
    		Gauge,
    	    wfDs1E1FarEndDayTotalUASs
    		Gauge,
    	    wfDs1E1FarEndDayTotalCSSs
    		Gauge,
    	    wfDs1E1FarEndDayTotalPCVs
    		Gauge,
    	    wfDs1E1FarEndDayTotalLESs
    		Gauge,
    	    wfDs1E1FarEndDayTotalBESs
    		Gauge,
    	    wfDs1E1FarEndDayTotalDMs
    		Gauge,
    	    wfDs1E1FarEndDayTotalLCVs
    		Gauge,
    	    wfDs1E1FarEndDayTotalSASs
    		Gauge,
    	    wfDs1E1FarEndDayTotalAISSs
    		Gauge,
    	    wfDs1E1FarEndDayTotalFCs
    		Gauge,
	    wfDs1E1FarEndDayTotalValidFlag
		INTEGER
        }

    wfDs1E1FarEndDayTotalPortLineNumber OBJECT-TYPE
        SYNTAX	INTEGER
        ACCESS	read-only
        STATUS	mandatory
        DESCRIPTION
                "The instance ID that identifies the port. The port line number with a zero
                channel number field as found in the port map table."
        ::= { wfDs1E1FarEndDayTotalEntry 1 }

    wfDs1E1FarEndDayTotalESs OBJECT-TYPE
        SYNTAX	Gauge
        ACCESS	read-only
        STATUS	mandatory
        DESCRIPTION
                "The number of Errored Seconds, encountered by a DS1 interface in the 
                previous 8 day interval."
        ::= { wfDs1E1FarEndDayTotalEntry 2 }

    wfDs1E1FarEndDayTotalSESs OBJECT-TYPE
        SYNTAX	Gauge
        ACCESS	read-only
        STATUS	mandatory
        DESCRIPTION
                "The number of Severely Errored Seconds encountered by a DS1 interface in the
                previous 8 day interval."
        ::= { wfDs1E1FarEndDayTotalEntry 3 }

    wfDs1E1FarEndDayTotalSEFSs OBJECT-TYPE
        SYNTAX	Gauge
        ACCESS	read-only
        STATUS	mandatory
        DESCRIPTION
                "The number of Severely Errored Framing Seconds encountered by a DS1 interface
                in the previous 8 day interval."
        ::= { wfDs1E1FarEndDayTotalEntry 4 }

    wfDs1E1FarEndDayTotalUASs OBJECT-TYPE
        SYNTAX	Gauge
        ACCESS	read-only
        STATUS	mandatory
        DESCRIPTION
                "The number of Unavailable Seconds encountered by a DS1 interface in the
                previous 8 day interval."
        ::= { wfDs1E1FarEndDayTotalEntry 5 }

    wfDs1E1FarEndDayTotalCSSs OBJECT-TYPE
        SYNTAX	Gauge
        ACCESS	read-only
        STATUS	mandatory
        DESCRIPTION
                "The number of Controlled Slip Seconds encountered by a DS1 interface in the
                previous 8 day interval."
        ::= { wfDs1E1FarEndDayTotalEntry 6 }

    wfDs1E1FarEndDayTotalPCVs OBJECT-TYPE
        SYNTAX	Gauge
        ACCESS	read-only
        STATUS	mandatory
        DESCRIPTION
                "The number of Path Coding Violations encountered by a DS1 interface in the
                previous 8 day interval."
        ::= { wfDs1E1FarEndDayTotalEntry 7 }

    wfDs1E1FarEndDayTotalLESs OBJECT-TYPE
        SYNTAX	Gauge
        ACCESS	read-only
        STATUS	mandatory
        DESCRIPTION
                "The number of Line Errored Seconds encountered by a DS1 interface in the
                previous 8 day interval."
        ::= { wfDs1E1FarEndDayTotalEntry 8 }

    wfDs1E1FarEndDayTotalBESs OBJECT-TYPE
        SYNTAX	Gauge
        ACCESS	read-only
        STATUS	mandatory
        DESCRIPTION
                "The number of Bursty Errored Seconds (BESs) encountered by a DS1 interface
                in the previous 8 day interval."
        ::= { wfDs1E1FarEndDayTotalEntry 9 }

    wfDs1E1FarEndDayTotalDMs OBJECT-TYPE
        SYNTAX	Gauge
        ACCESS	read-only
        STATUS	mandatory
        DESCRIPTION
                "The number of Degraded Minutes (DMs) encountered by a DS1 interface in the
                previous 8 day interval."
        ::= { wfDs1E1FarEndDayTotalEntry 10 }

    wfDs1E1FarEndDayTotalLCVs OBJECT-TYPE
        SYNTAX	Gauge
        ACCESS	read-only
        STATUS	mandatory
        DESCRIPTION
                "The number of Line Code Violations (LCVs) encountered  by a DS1 interface in
                the previous 8 day interval."
        ::= { wfDs1E1FarEndDayTotalEntry 11 }

    wfDs1E1FarEndDayTotalSASs OBJECT-TYPE
        SYNTAX	Gauge
        ACCESS	read-only
        STATUS	mandatory
        DESCRIPTION
                "The number of seconds, in the previous 8 day interval,
		containing one or more SEFs or AIS defects."
        ::= { wfDs1E1FarEndDayTotalEntry 12 }

    wfDs1E1FarEndDayTotalAISSs OBJECT-TYPE
        SYNTAX	Gauge
        ACCESS	read-only
        STATUS	mandatory
        DESCRIPTION
                "The number of seconds, in the previous 8 day interval,
		 containing one or more AIS defect."
        ::= { wfDs1E1FarEndDayTotalEntry 13 }

    wfDs1E1FarEndDayTotalFCs OBJECT-TYPE
        SYNTAX	Gauge
        ACCESS	read-only
        STATUS	mandatory
        DESCRIPTION
                "The number of Path Failure Count error events detected
		in the previous 8 day interval."
        ::= { wfDs1E1FarEndDayTotalEntry 14 }

    wfDs1E1FarEndDayTotalValidFlag OBJECT-TYPE
        SYNTAX	INTEGER {
    		    valid(1),
    		    invalid(2)
    		}
        ACCESS	read-only
        STATUS	mandatory
        DESCRIPTION
                "Indicates whether this interval reported by the Mib Table is valid or
		invalid."
        DEFVAL	{ valid }
        ::= { wfDs1E1FarEndDayTotalEntry 15 }



    wfDs1E1ThrAlrtTable OBJECT-TYPE
        SYNTAX	SEQUENCE OF WfDs1E1ThrAlrtEntry
        ACCESS	not-accessible
        STATUS	mandatory
        DESCRIPTION
                "Current statistics Alarm Threshold Crossing table."
        ::= { wfDs1E1Group 33 }

    wfDs1E1ThrAlrtEntry OBJECT-TYPE
        SYNTAX	WfDs1E1ThrAlrtEntry
        ACCESS	not-accessible
        STATUS	mandatory
        DESCRIPTION
                "An entry in the DS1E1 Current table"
        INDEX	{ wfDs1E1ThrAlrtPortLineNumber }
        ::= { wfDs1E1ThrAlrtTable 1 }

    WfDs1E1ThrAlrtEntry ::= SEQUENCE {
    	    wfDs1E1ThrAlrtDelete
    		INTEGER,
    	    wfDs1E1ThrAlrtPortLineNumber
    		INTEGER,
    	    wfDs1E1ThrAlrtESs
    		Gauge,
    	    wfDs1E1ThrAlrtSESs
    		Gauge,
    	    wfDs1E1ThrAlrtSEFSs
    		Gauge,
    	    wfDs1E1ThrAlrtUASs
    		Gauge,
    	    wfDs1E1ThrAlrtCSSs
    		Gauge,
    	    wfDs1E1ThrAlrtPCVs
    		Gauge,
    	    wfDs1E1ThrAlrtLESs
    		Gauge,
    	    wfDs1E1ThrAlrtBESs
    		Gauge,
    	    wfDs1E1ThrAlrtDMs
    		Gauge,
    	    wfDs1E1ThrAlrtLCVs
    		Gauge,
    	    wfDs1E1ThrAlrtSASs
    		Gauge,
    	    wfDs1E1ThrAlrtAISSs
    		Gauge,
    	    wfDs1E1ThrAlrtFCs
    		Gauge
        }

    wfDs1E1ThrAlrtDelete OBJECT-TYPE
        SYNTAX	INTEGER {
    		    created(1),
    		    deleted(2)
    		}
        ACCESS	read-write
        STATUS	mandatory
        DESCRIPTION
                "Create/Delete parameter"
        DEFVAL	{ created }
        ::= { wfDs1E1ThrAlrtEntry 1 }

    wfDs1E1ThrAlrtPortLineNumber OBJECT-TYPE
        SYNTAX	INTEGER
        ACCESS	read-only
        STATUS	mandatory
        DESCRIPTION
                "The instance ID that identifies the port."
        ::= { wfDs1E1ThrAlrtEntry 2 }

    wfDs1E1ThrAlrtESs OBJECT-TYPE
        SYNTAX	Gauge
        ACCESS	read-write
        STATUS	mandatory
        DESCRIPTION
                "The number of Errored Seconds which must be received prior to the
		generation of a Threshold Crossing Alert."
        DEFVAL	{ 65 }
        ::= { wfDs1E1ThrAlrtEntry 3 }

    wfDs1E1ThrAlrtSESs OBJECT-TYPE
        SYNTAX	Gauge
        ACCESS	read-write
        STATUS	mandatory
        DESCRIPTION
                "The number of Severely Errored Seconds which must be received prior
		to the generation of a Threshold Crossing Alert."
        DEFVAL	{ 10 }
        ::= { wfDs1E1ThrAlrtEntry 4 }

    wfDs1E1ThrAlrtSEFSs OBJECT-TYPE
        SYNTAX	Gauge
        ACCESS	read-write
        STATUS	mandatory
        DESCRIPTION
                "The number of Severely Errored Framing Seconds which must be received
		prior to the generation of a Threshold Crossing Alert."
        DEFVAL	{ 0 }
        ::= { wfDs1E1ThrAlrtEntry 5 }

    wfDs1E1ThrAlrtUASs OBJECT-TYPE
        SYNTAX	Gauge
        ACCESS	read-write
        STATUS	mandatory
        DESCRIPTION
                "The number of Unavailable Seconds which must be received prior to the
		generation of a Threshold Crossing Alert."
        DEFVAL	{ 10 }
        ::= { wfDs1E1ThrAlrtEntry 6 }

    wfDs1E1ThrAlrtCSSs OBJECT-TYPE
        SYNTAX	Gauge
        ACCESS	read-write
        STATUS	mandatory
        DESCRIPTION
                "The number of Controlled Slip Seconds which must be received prior to the
		generation of a Threshold Crossing Alert."
        DEFVAL	{ 1 }
        ::= { wfDs1E1ThrAlrtEntry 7 }

    wfDs1E1ThrAlrtPCVs OBJECT-TYPE
        SYNTAX	Gauge
        ACCESS	read-write
        STATUS	mandatory
        DESCRIPTION
                "The number of Path Coding Violations which must be received prior to the
		generation of a Threshold Crossing Alert."
        DEFVAL	{ 13296 }
        ::= { wfDs1E1ThrAlrtEntry 8 }

    wfDs1E1ThrAlrtLESs OBJECT-TYPE
        SYNTAX	Gauge
        ACCESS	read-write
        STATUS	mandatory
        DESCRIPTION
                "The number of Line Errored Seconds which must be received prior to the
		generation of a Threshold Crossing Alert."
        DEFVAL	{ 65 }
        ::= { wfDs1E1ThrAlrtEntry 9 }

    wfDs1E1ThrAlrtBESs OBJECT-TYPE
        SYNTAX	Gauge
        ACCESS	read-write
        STATUS	mandatory
        DESCRIPTION
                "The number of Bursty Errored Seconds which must be received prior to the
		generation of a Threshold Crossing Alert."
        DEFVAL	{ 0 }
        ::= { wfDs1E1ThrAlrtEntry 10 }

    wfDs1E1ThrAlrtDMs OBJECT-TYPE
        SYNTAX	Gauge
        ACCESS	read-write
        STATUS	mandatory
        DESCRIPTION
                "The number of Degraded Minutes which must be received prior to the
		generation of a Threshold Crossing Alert."
        DEFVAL	{ 0 }
        ::= { wfDs1E1ThrAlrtEntry 11 }

    wfDs1E1ThrAlrtLCVs OBJECT-TYPE
        SYNTAX	Gauge
        ACCESS	read-write
        STATUS	mandatory
        DESCRIPTION
                "The number of Line Code Violations which must be received prior to the
		generation of a Threshold Crossing Alert."
        DEFVAL	{ 13340 }
        ::= { wfDs1E1ThrAlrtEntry 12 }

    wfDs1E1ThrAlrtSASs OBJECT-TYPE
        SYNTAX	Gauge
        ACCESS	read-write
        STATUS	mandatory
        DESCRIPTION
                "The number of SEF/AIS Seconds which must be received prior to the
		generation of a Threshold Crossing Alert."
        DEFVAL	{ 2 }
        ::= { wfDs1E1ThrAlrtEntry 13 }

    wfDs1E1ThrAlrtAISSs OBJECT-TYPE
        SYNTAX	Gauge
        ACCESS	read-write
        STATUS	mandatory
        DESCRIPTION
                "The number of AIS defect Seconds which must be received prior to the
		generation of a Threshold Crossing Alert."
        DEFVAL	{ 0 }
        ::= { wfDs1E1ThrAlrtEntry 14 }

    wfDs1E1ThrAlrtFCs OBJECT-TYPE
        SYNTAX	Gauge
        ACCESS	read-write
        STATUS	mandatory
        DESCRIPTION
                "The number of Path Failure Counts which must be received prior to the
		generation of a Threshold Crossing Alert."
        DEFVAL	{ 0 }
        ::= { wfDs1E1ThrAlrtEntry 15 }



    wfDs1E1DayThrAlrtTable OBJECT-TYPE
        SYNTAX	SEQUENCE OF WfDs1E1DayThrAlrtEntry
        ACCESS	not-accessible
        STATUS	mandatory
        DESCRIPTION
                "Current Day statistics Alarm Threshold Crossing table."
        ::= { wfDs1E1Group 34 }

    wfDs1E1DayThrAlrtEntry OBJECT-TYPE
        SYNTAX	WfDs1E1DayThrAlrtEntry
        ACCESS	not-accessible
        STATUS	mandatory
        DESCRIPTION
                "An entry in the DS1E1 ThrAlrt table"
        INDEX	{ wfDs1E1DayThrAlrtPortLineNumber }
        ::= { wfDs1E1DayThrAlrtTable 1 }

    WfDs1E1DayThrAlrtEntry ::= SEQUENCE {
    	    wfDs1E1DayThrAlrtDelete
    		INTEGER,
    	    wfDs1E1DayThrAlrtPortLineNumber
    		INTEGER,
    	    wfDs1E1DayThrAlrtESs
    		Gauge,
    	    wfDs1E1DayThrAlrtSESs
    		Gauge,
    	    wfDs1E1DayThrAlrtSEFSs
    		Gauge,
    	    wfDs1E1DayThrAlrtUASs
    		Gauge,
    	    wfDs1E1DayThrAlrtCSSs
    		Gauge,
    	    wfDs1E1DayThrAlrtPCVs
    		Gauge,
    	    wfDs1E1DayThrAlrtLESs
    		Gauge,
    	    wfDs1E1DayThrAlrtBESs
    		Gauge,
    	    wfDs1E1DayThrAlrtDMs
    		Gauge,
    	    wfDs1E1DayThrAlrtLCVs
    		Gauge,
    	    wfDs1E1DayThrAlrtSASs
    		Gauge,
    	    wfDs1E1DayThrAlrtAISSs
    		Gauge,
    	    wfDs1E1DayThrAlrtFCs
    		Gauge
        }

    wfDs1E1DayThrAlrtDelete OBJECT-TYPE
        SYNTAX	INTEGER {
    		    created(1),
    		    deleted(2)
    		}
        ACCESS	read-write
        STATUS	mandatory
        DESCRIPTION
                "Create/Delete parameter"
        DEFVAL	{ created }
        ::= { wfDs1E1DayThrAlrtEntry 1 }

    wfDs1E1DayThrAlrtPortLineNumber OBJECT-TYPE
        SYNTAX	INTEGER
        ACCESS	read-only
        STATUS	mandatory
        DESCRIPTION
                "The instance ID that identifies the port."
        ::= { wfDs1E1DayThrAlrtEntry 2 }

    wfDs1E1DayThrAlrtESs OBJECT-TYPE
        SYNTAX	Gauge
        ACCESS	read-write
        STATUS	mandatory
        DESCRIPTION
                "The number of Errored Seconds which must be received prior to the
		generation of a Threshold Crossing Alert."
        DEFVAL	{ 648 }
        ::= { wfDs1E1DayThrAlrtEntry 3 }

    wfDs1E1DayThrAlrtSESs OBJECT-TYPE
        SYNTAX	Gauge
        ACCESS	read-write
        STATUS	mandatory
        DESCRIPTION
                "The number of Severely Errored Seconds which must be received prior
		to the generation of a Threshold Crossing Alert."
        DEFVAL	{ 100 }
        ::= { wfDs1E1DayThrAlrtEntry 4 }

    wfDs1E1DayThrAlrtSEFSs OBJECT-TYPE
        SYNTAX	Gauge
        ACCESS	read-write
        STATUS	mandatory
        DESCRIPTION
                "The number of Severely Errored Framing Seconds which must be received
		prior to the generation of a Threshold Crossing Alert."
        DEFVAL	{ 0 }
        ::= { wfDs1E1DayThrAlrtEntry 5 }

    wfDs1E1DayThrAlrtUASs OBJECT-TYPE
        SYNTAX	Gauge
        ACCESS	read-write
        STATUS	mandatory
        DESCRIPTION
                "The number of Unavailable Seconds which must be received prior to the
		generation of a Threshold Crossing Alert."
        DEFVAL	{ 10 }
        ::= { wfDs1E1DayThrAlrtEntry 6 }

    wfDs1E1DayThrAlrtCSSs OBJECT-TYPE
        SYNTAX	Gauge
        ACCESS	read-write
        STATUS	mandatory
        DESCRIPTION
                "The number of Controlled Slip Seconds which must be received prior to the
		generation of a Threshold Crossing Alert."
        DEFVAL	{ 4 }
        ::= { wfDs1E1DayThrAlrtEntry 7 }

    wfDs1E1DayThrAlrtPCVs OBJECT-TYPE
        SYNTAX	Gauge
        ACCESS	read-write
        STATUS	mandatory
        DESCRIPTION
                "The number of Path Coding Violations which must be received prior to the
		generation of a Threshold Crossing Alert."
        DEFVAL	{ 132960 }
        ::= { wfDs1E1DayThrAlrtEntry 8 }

    wfDs1E1DayThrAlrtLESs OBJECT-TYPE
        SYNTAX	Gauge
        ACCESS	read-write
        STATUS	mandatory
        DESCRIPTION
                "The number of Line Errored Seconds which must be received prior to the
		generation of a Threshold Crossing Alert."
        DEFVAL	{ 648 }
        ::= { wfDs1E1DayThrAlrtEntry 9 }

    wfDs1E1DayThrAlrtBESs OBJECT-TYPE
        SYNTAX	Gauge
        ACCESS	read-write
        STATUS	mandatory
        DESCRIPTION
                "The number of Bursty Errored Seconds which must be received prior to the
		generation of a Threshold Crossing Alert."
        DEFVAL	{ 0 }
        ::= { wfDs1E1DayThrAlrtEntry 10 }

    wfDs1E1DayThrAlrtDMs OBJECT-TYPE
        SYNTAX	Gauge
        ACCESS	read-write
        STATUS	mandatory
        DESCRIPTION
                "The number of Degraded Minutes which must be received prior to the
		generation of a Threshold Crossing Alert."
        DEFVAL	{ 0 }
        ::= { wfDs1E1DayThrAlrtEntry 11 }

    wfDs1E1DayThrAlrtLCVs OBJECT-TYPE
        SYNTAX	Gauge
        ACCESS	read-write
        STATUS	mandatory
        DESCRIPTION
                "The number of Line Code Violations which must be received prior to the
		generation of a Threshold Crossing Alert."
        DEFVAL	{ 133400 }
        ::= { wfDs1E1DayThrAlrtEntry 12 }

    wfDs1E1DayThrAlrtSASs OBJECT-TYPE
        SYNTAX	Gauge
        ACCESS	read-write
        STATUS	mandatory
        DESCRIPTION
                "The number of SEF/AIS Seconds which must be received prior to the
		generation of a Threshold Crossing Alert."
        DEFVAL	{ 17 }
        ::= { wfDs1E1DayThrAlrtEntry 13 }

    wfDs1E1DayThrAlrtAISSs OBJECT-TYPE
        SYNTAX	Gauge
        ACCESS	read-write
        STATUS	mandatory
        DESCRIPTION
                "The number of AIS defect Seconds which must be received prior to the
		generation of a Threshold Crossing Alert."
        DEFVAL	{ 0 }
        ::= { wfDs1E1DayThrAlrtEntry 14 }

    wfDs1E1DayThrAlrtFCs OBJECT-TYPE
        SYNTAX	Gauge
        ACCESS	read-write
        STATUS	mandatory
        DESCRIPTION
                "The number of Path Failure Counts which must be received prior to the
		generation of a Threshold Crossing Alert."
        DEFVAL	{ 0 }
        ::= { wfDs1E1DayThrAlrtEntry 15 }



    wfDs1E1FarEndThrAlrtTable OBJECT-TYPE
        SYNTAX	SEQUENCE OF WfDs1E1FarEndThrAlrtEntry
        ACCESS	not-accessible
        STATUS	mandatory
        DESCRIPTION
                "Current Far End statistics Alarm Threshold Crossing table."
        ::= { wfDs1E1Group 35 }

    wfDs1E1FarEndThrAlrtEntry OBJECT-TYPE
        SYNTAX	WfDs1E1FarEndThrAlrtEntry
        ACCESS	not-accessible
        STATUS	mandatory
        DESCRIPTION
                "An entry in the DS1E1 ThrAlrt table"
        INDEX	{ wfDs1E1FarEndThrAlrtPortLineNumber }
        ::= { wfDs1E1FarEndThrAlrtTable 1 }

    WfDs1E1FarEndThrAlrtEntry ::= SEQUENCE {
    	    wfDs1E1FarEndThrAlrtDelete
    		INTEGER,
    	    wfDs1E1FarEndThrAlrtPortLineNumber
    		INTEGER,
    	    wfDs1E1FarEndThrAlrtESs
    		Gauge,
    	    wfDs1E1FarEndThrAlrtSESs
    		Gauge,
    	    wfDs1E1FarEndThrAlrtSEFSs
    		Gauge,
    	    wfDs1E1FarEndThrAlrtUASs
    		Gauge,
    	    wfDs1E1FarEndThrAlrtCSSs
    		Gauge,
    	    wfDs1E1FarEndThrAlrtPCVs
    		Gauge,
    	    wfDs1E1FarEndThrAlrtLESs
    		Gauge,
    	    wfDs1E1FarEndThrAlrtBESs
    		Gauge,
    	    wfDs1E1FarEndThrAlrtDMs
    		Gauge,
    	    wfDs1E1FarEndThrAlrtLCVs
    		Gauge,
    	    wfDs1E1FarEndThrAlrtSASs
    		Gauge,
    	    wfDs1E1FarEndThrAlrtAISSs
    		Gauge,
    	    wfDs1E1FarEndThrAlrtFCs
    		Gauge
        }

    wfDs1E1FarEndThrAlrtDelete OBJECT-TYPE
        SYNTAX	INTEGER {
    		    created(1),
    		    deleted(2)
    		}
        ACCESS	read-write
        STATUS	mandatory
        DESCRIPTION
                "Create/Delete parameter"
        DEFVAL	{ created }
        ::= { wfDs1E1FarEndThrAlrtEntry 1 }

    wfDs1E1FarEndThrAlrtPortLineNumber OBJECT-TYPE
        SYNTAX	INTEGER
        ACCESS	read-only
        STATUS	mandatory
        DESCRIPTION
                "The instance ID that identifies the port."
        ::= { wfDs1E1FarEndThrAlrtEntry 2 }

    wfDs1E1FarEndThrAlrtESs OBJECT-TYPE
        SYNTAX	Gauge
        ACCESS	read-write
        STATUS	mandatory
        DESCRIPTION
                "The number of Errored Seconds which must be received prior to the
		generation of a Threshold Crossing Alert."
        DEFVAL	{ 65 }
        ::= { wfDs1E1FarEndThrAlrtEntry 3 }

    wfDs1E1FarEndThrAlrtSESs OBJECT-TYPE
        SYNTAX	Gauge
        ACCESS	read-write
        STATUS	mandatory
        DESCRIPTION
                "The number of Severely Errored Seconds which must be received prior
		to the generation of a Threshold Crossing Alert."
        DEFVAL	{ 10 }
        ::= { wfDs1E1FarEndThrAlrtEntry 4 }

    wfDs1E1FarEndThrAlrtSEFSs OBJECT-TYPE
        SYNTAX	Gauge
        ACCESS	read-write
        STATUS	mandatory
        DESCRIPTION
                "The number of Severely Errored Framing Seconds which must be received
		prior to the generation of a Threshold Crossing Alert."
        DEFVAL	{ 0 }
        ::= { wfDs1E1FarEndThrAlrtEntry 5 }

    wfDs1E1FarEndThrAlrtUASs OBJECT-TYPE
        SYNTAX	Gauge
        ACCESS	read-write
        STATUS	mandatory
        DESCRIPTION
                "The number of Unavailable Seconds which must be received prior to the
		generation of a Threshold Crossing Alert."
        DEFVAL	{ 10 }
        ::= { wfDs1E1FarEndThrAlrtEntry 6 }

    wfDs1E1FarEndThrAlrtCSSs OBJECT-TYPE
        SYNTAX	Gauge
        ACCESS	read-write
        STATUS	mandatory
        DESCRIPTION
                "The number of Controlled Slip Seconds which must be received prior to the
		generation of a Threshold Crossing Alert."
        DEFVAL	{ 1 }
        ::= { wfDs1E1FarEndThrAlrtEntry 7 }

    wfDs1E1FarEndThrAlrtPCVs OBJECT-TYPE
        SYNTAX	Gauge
        ACCESS	read-write
        STATUS	mandatory
        DESCRIPTION
                "The number of Path Coding Violations which must be received prior to the
		generation of a Threshold Crossing Alert."
        DEFVAL	{ 13296 }
        ::= { wfDs1E1FarEndThrAlrtEntry 8 }

    wfDs1E1FarEndThrAlrtLESs OBJECT-TYPE
        SYNTAX	Gauge
        ACCESS	read-write
        STATUS	mandatory
        DESCRIPTION
                "The number of Line Errored Seconds which must be received prior to the
		generation of a Threshold Crossing Alert."
        DEFVAL	{ 65 }
        ::= { wfDs1E1FarEndThrAlrtEntry 9 }

    wfDs1E1FarEndThrAlrtBESs OBJECT-TYPE
        SYNTAX	Gauge
        ACCESS	read-write
        STATUS	mandatory
        DESCRIPTION
                "The number of Bursty Errored Seconds which must be received prior to the
		generation of a Threshold Crossing Alert."
        DEFVAL	{ 0 }
        ::= { wfDs1E1FarEndThrAlrtEntry 10 }

    wfDs1E1FarEndThrAlrtDMs OBJECT-TYPE
        SYNTAX	Gauge
        ACCESS	read-write
        STATUS	mandatory
        DESCRIPTION
                "The number of Degraded Minutes which must be received prior to the
		generation of a Threshold Crossing Alert."
        DEFVAL	{ 0 }
        ::= { wfDs1E1FarEndThrAlrtEntry 11 }

    wfDs1E1FarEndThrAlrtLCVs OBJECT-TYPE
        SYNTAX	Gauge
        ACCESS	read-write
        STATUS	mandatory
        DESCRIPTION
                "The number of Line Code Violations which must be received prior to the
		generation of a Threshold Crossing Alert."
        DEFVAL	{ 13340 }
        ::= { wfDs1E1FarEndThrAlrtEntry 12 }

    wfDs1E1FarEndThrAlrtSASs OBJECT-TYPE
        SYNTAX	Gauge
        ACCESS	read-write
        STATUS	mandatory
        DESCRIPTION
                "The number of SEF/AIS Seconds which must be received prior to the
		generation of a Threshold Crossing Alert."
        DEFVAL	{ 2 }
        ::= { wfDs1E1FarEndThrAlrtEntry 13 }

    wfDs1E1FarEndThrAlrtAISSs OBJECT-TYPE
        SYNTAX	Gauge
        ACCESS	read-write
        STATUS	mandatory
        DESCRIPTION
                "The number of AIS defect Seconds which must be received prior to the
		generation of a Threshold Crossing Alert."
        DEFVAL	{ 0 }
        ::= { wfDs1E1FarEndThrAlrtEntry 14 }

    wfDs1E1FarEndThrAlrtFCs OBJECT-TYPE
        SYNTAX	Gauge
        ACCESS	read-write
        STATUS	mandatory
        DESCRIPTION
                "The number of Path Failure Counts which must be received prior to the
		generation of a Threshold Crossing Alert."
        DEFVAL	{ 0 }
        ::= { wfDs1E1FarEndThrAlrtEntry 15 }




    wfDs1E1FarEndDayThrAlrtTable OBJECT-TYPE
        SYNTAX	SEQUENCE OF WfDs1E1FarEndDayThrAlrtEntry
        ACCESS	not-accessible
        STATUS	mandatory
        DESCRIPTION
                "Current Far End Day statistics Alarm Threshold Crossing table."
        ::= { wfDs1E1Group 36 }

    wfDs1E1FarEndDayThrAlrtEntry OBJECT-TYPE
        SYNTAX	WfDs1E1FarEndDayThrAlrtEntry
        ACCESS	not-accessible
        STATUS	mandatory
        DESCRIPTION
                "An entry in the DS1E1 ThrAlrt table"
        INDEX	{ wfDs1E1FarEndDayThrAlrtPortLineNumber }
        ::= { wfDs1E1FarEndDayThrAlrtTable 1 }

    WfDs1E1FarEndDayThrAlrtEntry ::= SEQUENCE {
    	    wfDs1E1FarEndDayThrAlrtDelete
    		INTEGER,
    	    wfDs1E1FarEndDayThrAlrtPortLineNumber
    		INTEGER,
    	    wfDs1E1FarEndDayThrAlrtESs
    		Gauge,
    	    wfDs1E1FarEndDayThrAlrtSESs
    		Gauge,
    	    wfDs1E1FarEndDayThrAlrtSEFSs
    		Gauge,
    	    wfDs1E1FarEndDayThrAlrtUASs
    		Gauge,
    	    wfDs1E1FarEndDayThrAlrtCSSs
    		Gauge,
    	    wfDs1E1FarEndDayThrAlrtPCVs
    		Gauge,
    	    wfDs1E1FarEndDayThrAlrtLESs
    		Gauge,
    	    wfDs1E1FarEndDayThrAlrtBESs
    		Gauge,
    	    wfDs1E1FarEndDayThrAlrtDMs
    		Gauge,
    	    wfDs1E1FarEndDayThrAlrtLCVs
    		Gauge,
    	    wfDs1E1FarEndDayThrAlrtSASs
    		Gauge,
    	    wfDs1E1FarEndDayThrAlrtAISSs
    		Gauge,
    	    wfDs1E1FarEndDayThrAlrtFCs
    		Gauge
        }

    wfDs1E1FarEndDayThrAlrtDelete OBJECT-TYPE
        SYNTAX	INTEGER {
    		    created(1),
    		    deleted(2)
    		}
        ACCESS	read-write
        STATUS	mandatory
        DESCRIPTION
                "Create/Delete parameter"
        DEFVAL	{ created }
        ::= { wfDs1E1FarEndDayThrAlrtEntry 1 }

    wfDs1E1FarEndDayThrAlrtPortLineNumber OBJECT-TYPE
        SYNTAX	INTEGER
        ACCESS	read-only
        STATUS	mandatory
        DESCRIPTION
                "The instance ID that identifies the port."
        ::= { wfDs1E1FarEndDayThrAlrtEntry 2 }

    wfDs1E1FarEndDayThrAlrtESs OBJECT-TYPE
        SYNTAX	Gauge
        ACCESS	read-write
        STATUS	mandatory
        DESCRIPTION
                "The number of Errored Seconds which must be received prior to the
		generation of a Threshold Crossing Alert."
        DEFVAL	{ 648 }
        ::= { wfDs1E1FarEndDayThrAlrtEntry 3 }

    wfDs1E1FarEndDayThrAlrtSESs OBJECT-TYPE
        SYNTAX	Gauge
        ACCESS	read-write
        STATUS	mandatory
        DESCRIPTION
                "The number of Severely Errored Seconds which must be received prior
		to the generation of a Threshold Crossing Alert."
        DEFVAL	{ 100 }
        ::= { wfDs1E1FarEndDayThrAlrtEntry 4 }

    wfDs1E1FarEndDayThrAlrtSEFSs OBJECT-TYPE
        SYNTAX	Gauge
        ACCESS	read-write
        STATUS	mandatory
        DESCRIPTION
                "The number of Severely Errored Seconds which must be received
		prior to the generation of a Threshold Crossing Alert."
        DEFVAL	{ 0 }
        ::= { wfDs1E1FarEndDayThrAlrtEntry 5 }

    wfDs1E1FarEndDayThrAlrtUASs OBJECT-TYPE
        SYNTAX	Gauge
        ACCESS	read-write
        STATUS	mandatory
        DESCRIPTION
                "The number of Unavailable Seconds which must be received prior to the
		generation of a Threshold Crossing Alert."
        DEFVAL	{ 10 }
        ::= { wfDs1E1FarEndDayThrAlrtEntry 6 }

    wfDs1E1FarEndDayThrAlrtCSSs OBJECT-TYPE
        SYNTAX	Gauge
        ACCESS	read-write
        STATUS	mandatory
        DESCRIPTION
                "The number of Controlled Slip Seconds which must be received prior to the
		generation of a Threshold Crossing Alert."
        DEFVAL	{ 4 }
        ::= { wfDs1E1FarEndDayThrAlrtEntry 7 }

    wfDs1E1FarEndDayThrAlrtPCVs OBJECT-TYPE
        SYNTAX	Gauge
        ACCESS	read-write
        STATUS	mandatory
        DESCRIPTION
                "The number of Path Coding Violations which must be received prior to the
		generation of a Threshold Crossing Alert."
        DEFVAL	{ 132960 }
        ::= { wfDs1E1FarEndDayThrAlrtEntry 8 }

    wfDs1E1FarEndDayThrAlrtLESs OBJECT-TYPE
        SYNTAX	Gauge
        ACCESS	read-write
        STATUS	mandatory
        DESCRIPTION
                "The number of Line Errored Seconds which must be received prior to the
		generation of a Threshold Crossing Alert."
        DEFVAL	{ 648 }
        ::= { wfDs1E1FarEndDayThrAlrtEntry 9 }

    wfDs1E1FarEndDayThrAlrtBESs OBJECT-TYPE
        SYNTAX	Gauge
        ACCESS	read-write
        STATUS	mandatory
        DESCRIPTION
                "The number of Bursty Errored Seconds which must be received prior to the
		generation of a Threshold Crossing Alert."
        DEFVAL	{ 0 }
        ::= { wfDs1E1FarEndDayThrAlrtEntry 10 }

    wfDs1E1FarEndDayThrAlrtDMs OBJECT-TYPE
        SYNTAX	Gauge
        ACCESS	read-write
        STATUS	mandatory
        DESCRIPTION
                "The number of Degraded Minutes which must be received prior to the
		generation of a Threshold Crossing Alert."
        DEFVAL	{ 0 }
        ::= { wfDs1E1FarEndDayThrAlrtEntry 11 }

    wfDs1E1FarEndDayThrAlrtLCVs OBJECT-TYPE
        SYNTAX	Gauge
        ACCESS	read-write
        STATUS	mandatory
        DESCRIPTION
                "The number of Line Code Violations which must be received prior to the
		generation of a Threshold Crossing Alert."
        DEFVAL	{ 133400 }
        ::= { wfDs1E1FarEndDayThrAlrtEntry 12 }

    wfDs1E1FarEndDayThrAlrtSASs OBJECT-TYPE
        SYNTAX	Gauge
        ACCESS	read-write
        STATUS	mandatory
        DESCRIPTION
                "The number of SEF/AIS Seconds which must be received prior to the
		generation of a Threshold Crossing Alert."
        DEFVAL	{ 17 }
        ::= { wfDs1E1FarEndDayThrAlrtEntry 13 }

    wfDs1E1FarEndDayThrAlrtAISSs OBJECT-TYPE
        SYNTAX	Gauge
        ACCESS	read-write
        STATUS	mandatory
        DESCRIPTION
                "The number of AIS defect Seconds which must be received prior to the
		generation of a Threshold Crossing Alert."
        DEFVAL	{ 0 }
        ::= { wfDs1E1FarEndDayThrAlrtEntry 14 }

    wfDs1E1FarEndDayThrAlrtFCs OBJECT-TYPE
        SYNTAX	Gauge
        ACCESS	read-write
        STATUS	mandatory
        DESCRIPTION
                "The number of Path Failure Counts which must be received prior to the
		generation of a Threshold Crossing Alert."
        DEFVAL	{ 0 }
        ::= { wfDs1E1FarEndDayThrAlrtEntry 15 }


    wfDs1E1LineQueStatTable OBJECT-TYPE
        SYNTAX	SEQUENCE OF WfDs1E1LineQueStatEntry
        ACCESS	not-accessible
        STATUS	mandatory
        DESCRIPTION
                "This file describes the MIBS for getting Line Queue Stats"
        ::= { wfDs1E1Group 20 }

    wfDs1E1LineQueStatEntry OBJECT-TYPE
        SYNTAX	WfDs1E1LineQueStatEntry
        ACCESS	not-accessible
        STATUS	mandatory
        DESCRIPTION
                "An entry in the Queue Base table"
        INDEX	{ wfDs1E1LineQueStatPortLineNumber,
        	  wfDs1E1LineQueStatLineIndex,
        	  wfDs1E1LineQueStatQueueIndex }
        ::= { wfDs1E1LineQueStatTable 1 }

    WfDs1E1LineQueStatEntry ::= SEQUENCE {
    	    wfDs1E1LineQueStatPortLineNumber
    		INTEGER,
    	    wfDs1E1LineQueStatLineIndex
    		INTEGER,
    	    wfDs1E1LineQueStatQueueIndex
    		INTEGER,
    	    wfDs1E1LineQueStatTxOctets
    		Counter,
    	    wfDs1E1LineQueStatTxPackets
    		Counter,
    	    wfDs1E1LineQueStatTxDrops
    		Counter
        }


    wfDs1E1LineQueStatPortLineNumber OBJECT-TYPE
        SYNTAX  INTEGER
        ACCESS  read-only
        STATUS  mandatory
        DESCRIPTION
                "Instance ID PortLineNumber"
        ::= { wfDs1E1LineQueStatEntry 1 }

    wfDs1E1LineQueStatLineIndex OBJECT-TYPE
        SYNTAX  INTEGER
        ACCESS  read-only
        STATUS  mandatory
        DESCRIPTION
                "Instance Line Number"
        ::= { wfDs1E1LineQueStatEntry 2 }

    wfDs1E1LineQueStatQueueIndex OBJECT-TYPE
        SYNTAX  INTEGER
        ACCESS  read-only
        STATUS  mandatory
        DESCRIPTION
                "Queue Index, matches that of wfQosServPkgQueCfgQueueIndex or
		 one for best effort."
        ::= { wfDs1E1LineQueStatEntry 3 }

    wfDs1E1LineQueStatTxOctets OBJECT-TYPE
        SYNTAX  Counter
        ACCESS  read-only
        STATUS  mandatory
        DESCRIPTION
                "Number of Transmit Octets received by the Queue without error"
        ::= { wfDs1E1LineQueStatEntry 4 }

    wfDs1E1LineQueStatTxPackets OBJECT-TYPE
        SYNTAX  Counter
        ACCESS  read-only
        STATUS  mandatory
        DESCRIPTION
                "Number of Transmit Packets received by the Queue without error"
        ::= { wfDs1E1LineQueStatEntry 5 }

    wfDs1E1LineQueStatTxDrops OBJECT-TYPE
        SYNTAX  Counter
        ACCESS  read-only
        STATUS  mandatory
        DESCRIPTION
                "Number of Transmit Packets Dropped by the Queue"
        ::= { wfDs1E1LineQueStatEntry 6 }



    END  -- Wellfleet-DS1E1-MIB
