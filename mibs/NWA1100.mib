--
-- NWA1100.my
-- MIB generated by MG-SOFT Visual MIB Builder Version 5.0  Build 250
-- Thursday, May 15, 2008 at 08:41:38
--

-- 
-- 

	NWA1100 DEFINITIONS ::= BEGIN
 
		IMPORTS
			ifIndex			
				FROM RFC1213-MIB			
			OBJECT-GROUP			
				FROM SNMPv2-CONF			
			enterprises, Integer32, OBJECT-TYPE, MODULE-IDENTITY			
				FROM SNMPv2-SMI			
			DisplayString, MacAddress, TruthValue			
				FROM SNMPv2-TC;
	
	
		-- 1.3.6.1.4.1.890.1.9
		nwa1100 MODULE-IDENTITY 
			LAST-UPDATED "200804011303Z"		-- April 01, 2008 at 13:03 GMT
			ORGANIZATION 
				" "
			CONTACT-INFO 
				" "
			DESCRIPTION 
				"nwa1100"
			::= { nwaSeries 9 }

		
	
	
--
-- Node definitions
--
	
		-- 1.3.6.1.4.1.890
		zyxel OBJECT IDENTIFIER ::= { enterprises 890 }

		
		-- 1.3.6.1.4.1.890.1
		nwaSeries OBJECT IDENTIFIER ::= { zyxel 1 }

		
--  Common information and firmware/configuration upload/download.
-- 
		-- 1.3.6.1.4.1.890.1.9.1
		pwCommon OBJECT IDENTIFIER ::= { nwa1100 1 }

		
		-- 1.3.6.1.4.1.890.1.9.1.1
		pwSwVersion OBJECT-TYPE
			SYNTAX DisplayString
			MAX-ACCESS read-only
			STATUS current
			DESCRIPTION
				"Current software version."
			::= { pwCommon 1 }

		
		-- 1.3.6.1.4.1.890.1.9.1.8
		pwSystemReboot OBJECT-TYPE
			SYNTAX INTEGER
				{
				no(0),
				yes(1)
				}
			MAX-ACCESS read-write
			STATUS current
			DESCRIPTION
				"System reboot.
				1=reboot."
			::= { pwCommon 8 }

		
		-- 1.3.6.1.4.1.890.1.9.1.10
		pwCPUUsage OBJECT-TYPE
			SYNTAX DisplayString
			MAX-ACCESS read-only
			STATUS current
			DESCRIPTION
				"Display the CPU usage information."
			::= { pwCommon 10 }

		
		-- 1.3.6.1.4.1.890.1.9.1.11
		pwMemoryUsage OBJECT-TYPE
			SYNTAX DisplayString
			MAX-ACCESS read-only
			STATUS current
			DESCRIPTION
				"Display the memory usage information."
			::= { pwCommon 11 }

		
		-- 1.3.6.1.4.1.890.1.9.1.13
		pwSystemCountry OBJECT-TYPE
			SYNTAX INTEGER
				{
				australia(36),
				austria(40),
				canada(124),
				china(156),
				taiwan(158),
				denmark(208),
				finland(246),
				france(250),
				germany(276),
				hongKong(344),
				iceland(352),
				india(356),
				india5825GHz5885GHz(357),
				ireland(372),
				italy(380),
				japan(392),
				liechtenstein(438),
				luxembourg(442),
				netherlands(528),
				newZealand(554),
				norway(578),
				portugal(620),
				singapore(702),
				spain(724),
				sweden(752),
				switzerland(756),
				unitedKingdom(826),
				unitedStates(840)
				}
			MAX-ACCESS read-only
			STATUS current
			DESCRIPTION
				"The country code setting of wlan."
			::= { pwCommon 13 }

		
		-- 1.3.6.1.4.1.890.1.9.1.14
		pwStationCount OBJECT-TYPE
			SYNTAX INTEGER (0..32)
			MAX-ACCESS read-only
			STATUS current
			DESCRIPTION
				"Number of associated stations."
			::= { pwCommon 14 }

		
		-- 1.3.6.1.4.1.890.1.9.1.15
		pwPassword OBJECT-TYPE
			SYNTAX DisplayString (SIZE (3..19))
			MAX-ACCESS read-write
			STATUS current
			DESCRIPTION
				"Change system password."
			::= { pwCommon 15 }

		
		-- 1.3.6.1.4.1.890.1.9.1.16
		pwCurrentChannel OBJECT-TYPE
			SYNTAX INTEGER (1..14)
			MAX-ACCESS read-only
			STATUS current
			DESCRIPTION
				"Current operating Channel."
			::= { pwCommon 16 }

		
		-- 1.3.6.1.4.1.890.1.9.3
		pwStation OBJECT IDENTIFIER ::= { nwa1100 3 }

		
		-- 1.3.6.1.4.1.890.1.9.3.2
		pwStationTable OBJECT-TYPE
			SYNTAX SEQUENCE OF PwStationEntry
			MAX-ACCESS not-accessible
			STATUS current
			DESCRIPTION
				"This table lists the associated stations."
			::= { pwStation 2 }

		
		-- 1.3.6.1.4.1.890.1.9.3.2.1
		pwStationEntry OBJECT-TYPE
			SYNTAX PwStationEntry
			MAX-ACCESS not-accessible
			STATUS current
			DESCRIPTION
				"An entry describing the station information."
			INDEX { pwStationIndex }
			::= { pwStationTable 1 }

		
		PwStationEntry ::=
			SEQUENCE { 
				pwStationIndex
					Integer32,
				pwStationMacAddress
					MacAddress,
				pwStationAssociateTime
					DisplayString,
				pwStationSSID
					DisplayString,
				pwStationStatus
					INTEGER
			 }

		-- 1.3.6.1.4.1.890.1.9.3.2.1.1
		pwStationIndex OBJECT-TYPE
			SYNTAX Integer32 (1..32)
			MAX-ACCESS read-only
			STATUS current
			DESCRIPTION
				"Index of station table."
			::= { pwStationEntry 1 }

		
		-- 1.3.6.1.4.1.890.1.9.3.2.1.2
		pwStationMacAddress OBJECT-TYPE
			SYNTAX MacAddress
			MAX-ACCESS read-only
			STATUS current
			DESCRIPTION
				"Mac Address of the associated entry."
			::= { pwStationEntry 2 }

		
		-- 1.3.6.1.4.1.890.1.9.3.2.1.3
		pwStationAssociateTime OBJECT-TYPE
			SYNTAX DisplayString
			MAX-ACCESS read-only
			STATUS current
			DESCRIPTION
				"Associated time."
			::= { pwStationEntry 3 }

		
		-- 1.3.6.1.4.1.890.1.9.3.2.1.4
		pwStationSSID OBJECT-TYPE
			SYNTAX DisplayString
			MAX-ACCESS read-only
			STATUS current
			DESCRIPTION
				"Associated ssid."
			::= { pwStationEntry 4 }

		
		-- 1.3.6.1.4.1.890.1.9.3.2.1.5
		pwStationStatus OBJECT-TYPE
			SYNTAX INTEGER
				{
				init(0),
				scanning(1),
				authenticating(2),
				associating(3),
				associated(4)
				}
			MAX-ACCESS read-only
			STATUS current
			DESCRIPTION
				"Status of the associated entry."
			::= { pwStationEntry 5 }

		
		-- 1.3.6.1.4.1.890.1.9.5
		pwWlanControl OBJECT IDENTIFIER ::= { nwa1100 5 }

		
		-- 1.3.6.1.4.1.890.1.9.5.1
		pwWlanControlTable OBJECT-TYPE
			SYNTAX SEQUENCE OF PwWlanControlEntry
			MAX-ACCESS not-accessible
			STATUS current
			DESCRIPTION
				"This table lists WLAN control information.
				Use chipIndex as the index of each entry."
			::= { pwWlanControl 1 }

		
		-- 1.3.6.1.4.1.890.1.9.5.1.1
		pwWlanControlEntry OBJECT-TYPE
			SYNTAX PwWlanControlEntry
			MAX-ACCESS not-accessible
			STATUS current
			DESCRIPTION
				"An entry describing WLAN control information for each chip."
			INDEX { pwWlanChipIndex }
			::= { pwWlanControlTable 1 }

		
		PwWlanControlEntry ::=
			SEQUENCE { 
				pwWlanMode
					INTEGER,
				pwWlanChipIndex
					Integer32,
				pwWlanSupportedChannel
					DisplayString,
				pwWlanChannel
					INTEGER,
				pwWlanTxPower
					INTEGER,
				pwAutoChannelSelection
					TruthValue
			 }

		-- 1.3.6.1.4.1.890.1.9.5.1.1.1
		pwWlanMode OBJECT-TYPE
			SYNTAX INTEGER
				{
				auto(0),
				dot11b(2),
				dot11g(3)
				}
			MAX-ACCESS read-write
			STATUS current
			DESCRIPTION
				"Wlan radio mode."
			::= { pwWlanControlEntry 1 }

		
		-- 1.3.6.1.4.1.890.1.9.5.1.1.2
		pwWlanChipIndex OBJECT-TYPE
			SYNTAX Integer32 (1)
			MAX-ACCESS read-only
			STATUS current
			DESCRIPTION
				"Chip Index"
			::= { pwWlanControlEntry 2 }

		
		-- 1.3.6.1.4.1.890.1.9.5.1.1.3
		pwWlanSupportedChannel OBJECT-TYPE
			SYNTAX DisplayString (SIZE (0..64))
			MAX-ACCESS read-only
			STATUS current
			DESCRIPTION
				"Wlan supported channels in this regulatory domain."
			::= { pwWlanControlEntry 3 }

		
		-- 1.3.6.1.4.1.890.1.9.5.1.1.4
		pwWlanChannel OBJECT-TYPE
			SYNTAX INTEGER (1..14)
			MAX-ACCESS read-write
			STATUS current
			DESCRIPTION
				"Control of wlan channel."
			::= { pwWlanControlEntry 4 }

		
		-- 1.3.6.1.4.1.890.1.9.5.1.1.5
		pwWlanTxPower OBJECT-TYPE
			SYNTAX INTEGER
				{
				full(0),
				half(1),
				quarter(2),
				eighth(3),
				min(4)
				}
			MAX-ACCESS read-write
			STATUS current
			DESCRIPTION
				"Control of wlan output power."
			::= { pwWlanControlEntry 5 }

		
		-- 1.3.6.1.4.1.890.1.9.5.1.1.6
		pwAutoChannelSelection OBJECT-TYPE
			SYNTAX TruthValue
			MAX-ACCESS read-write
			STATUS current
			DESCRIPTION
				"Enable/Disable Auto Channel Selection."
			::= { pwWlanControlEntry 6 }

		
		-- 1.3.6.1.4.1.890.1.9.9
		nwa1100Conformance OBJECT IDENTIFIER ::= { nwa1100 9 }

		
		-- 1.3.6.1.4.1.890.1.9.9.1
		nwa1100Groups OBJECT IDENTIFIER ::= { nwa1100Conformance 1 }

		
		-- 1.3.6.1.4.1.890.1.9.9.1.1
		nwa1100pwCommon OBJECT-GROUP
			OBJECTS { pwSwVersion, pwSystemReboot, pwCPUUsage, pwMemoryUsage, pwSystemCountry, 
				pwStationCount, pwPassword, pwCurrentChannel }
			STATUS current
			DESCRIPTION 
				"nwa1100pwCommon Group"
			::= { nwa1100Groups 1 }

		
		-- 1.3.6.1.4.1.890.1.9.9.1.2
		nwa1100pwStation OBJECT-GROUP
			OBJECTS { pwStationIndex, pwStationMacAddress, pwStationAssociateTime, pwStationSSID, pwStationStatus
				 }
			STATUS current
			DESCRIPTION 
				"nwa1100pwStation Group"
			::= { nwa1100Groups 2 }

		
		-- 1.3.6.1.4.1.890.1.9.9.1.3
		nwa1100WlanControl OBJECT-GROUP
			OBJECTS { pwWlanMode, pwWlanChipIndex, pwWlanSupportedChannel, pwWlanChannel, pwWlanTxPower, 
				pwAutoChannelSelection }
			STATUS current
			DESCRIPTION 
				"nwa1100pwWlanControl Group"
			::= { nwa1100Groups 3 }

		
	
	END

--
-- NWA1100.my
--
