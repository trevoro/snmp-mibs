CXT1E1-MIB DEFINITIONS ::= BEGIN


IMPORTS
   OBJECT-TYPE         FROM RFC-1212
	TimeTicks           FROM RFC1155-SMI
	cxT1E1              FROM CXProduct-SMI;

--   This module uses the extended OBJECT-TYPE macro as defined
--   in RFC 1212. This is the MIB module for the T1E1 objects.

--  The T1E1 Configuration Table


t1e1CfgTable             OBJECT-TYPE
		SYNTAX    SEQUENCE OF T1e1CfgEntry      
		ACCESS    not-accessible
		STATUS    mandatory
		DESCRIPTION
"The T1/E1 configuration table."
		::= { cxT1E1 10 }


t1e1CfgEntry             OBJECT-TYPE
		SYNTAX    T1e1CfgEntry
		ACCESS    not-accessible
		STATUS    mandatory
		DESCRIPTION
"An entry in the T1/E1 configuration table."
		INDEX { t1e1CfgLinkIndex }
		::= { t1e1CfgTable 1 }



T1e1CfgEntry   ::=
		SEQUENCE {
-- Parameters
			t1e1CfgLinkIndex              INTEGER,

			t1e1CfgDebounce               INTEGER,
			t1e1CfgJitterAttenuator       INTEGER,
			t1e1CfgSyncCriteria           INTEGER,
			t1e1CfgT1RxEqualizerGainLimit INTEGER,
			t1e1CfgT1RxLevel              INTEGER,
			t1e1CfgT1FrameAlignmentChange TimeTicks,
			t1e1CfgT1JitterAttenuatorTrip TimeTicks
			}

t1e1CfgLinkIndex             OBJECT-TYPE
		SYNTAX    INTEGER (1..2)
		ACCESS    read-only
		STATUS    mandatory
		DESCRIPTION
"Identifies the physical port with the T1/E1 (t1e1) interface.

Range of Values: 1 - 2

Default Value: None

Configuration Changed: administrative"
		::= { t1e1CfgEntry 1 }


t1e1CfgDebounce          OBJECT-TYPE
	SYNTAX    INTEGER (1..255)
		ACCESS    read-write
		STATUS    mandatory
		DESCRIPTION
"Specifies the number of loops needed for debouncing.

Warning: This is a Private Mode activity that should only be
performed by or under the direct supervision of qualified
personnel.

Range of Values: 1 - 255

Default Value: 2

Configuration Changed: administrative"
		DEFVAL { 2 }
		::= { t1e1CfgEntry 10 }



t1e1CfgJitterAttenuator       OBJECT-TYPE
	SYNTAX    INTEGER { t1e1NoJitterAttenuator (1),
					t1e1RxAttenuator32Bits (2),
					t1e1RxAttenuator128Bits (3),
					t1e1TxAttenuator32Bits (4),
					t1e1TxAttenuator128Bits (5)
			}
		ACCESS    read-write
		STATUS    mandatory
		DESCRIPTION
"Defines the position and buffer depth of the Jitter Attenuator 
when the Attenuator is enabled.

Warning: This is a Private Mode activity that should only be
performed by or under the direct supervision of qualified
personnel.

Options:
t1e1NoJitterAttenuator (1)

t1e1RxAttenuator32Bits (2)

t1e1RxAttenuator128Bits (3)

t1e1TxAttenuator32Bits (4)

t1e1TxAttenuator128Bits (5)

Default Value: t1e1NoJitterAttenuator (1)

Configuration Changed: administrative"
		DEFVAL { t1e1NoJitterAttenuator }
		::= { t1e1CfgEntry  11 }


t1e1CfgSyncCriteria      OBJECT-TYPE
	SYNTAX    INTEGER (1..2)
		ACCESS    read-write
		STATUS    mandatory
		DESCRIPTION
"Determines the criteria used for Synchronisation.

Options:
In D4 framing mode, 1 = search for Ft pattern, the search
for Fs pattern and 2=cross couple Ft and Fs pattern.

In ESF framing mode, 1 = search for FPS pattern only.

In ESF framing mode, 2 = search for FPS and verify with CRC6.

Warning: This is a Private Mode activity that should only be
performed by or under the direct supervision of qualified
personnel.

Default Value: 1

Configuration Changed: administrative"
		DEFVAL { 1 }
		::= { t1e1CfgEntry  12 }

t1e1CfgT1RxEqualizerGainLimit OBJECT-TYPE
	SYNTAX    INTEGER { t1e1EGLLow (1),
                                        t1e1EGLHigh (2)
			}
		ACCESS    read-write
		STATUS    mandatory
		DESCRIPTION
"Program the receiver sensitivity.

Warning: This is a Private Mode activity that should only be
performed by or under the direct supervision of qualified
personnel.

Options:
t1e1EGLLow (1): Program a low sensitivity of -30 dB. This is 
recommended for most applications.

t1e1EGLHigh (2): Program a high sensitivity of -36 dB. This
setting could be required for particular applications, however,
with this level of sensitivity the receiver will be more
susceptible to crosstalk and the receiver's jitter tolerance
will suffer.

Default Value: t1e1EGLLow (1)

Configuration Changed: administrative"
		DEFVAL { t1e1EGLLow }
		::= { t1e1CfgEntry  13 }


t1e1CfgT1RxLevel         OBJECT-TYPE
	SYNTAX    INTEGER (1..4)
		ACCESS    read-only
		STATUS    mandatory
		DESCRIPTION
"Indicates in real-time a range of received signal levels.

Options:
1: +2.0 to -7.5 dB

2: -7.5 to -15.0 dB

3: -15.0 to -22.5 dB

4: less than -22.5 dB "
		::= { t1e1CfgEntry  50 }

t1e1CfgT1FrameAlignmentChange OBJECT-TYPE
	SYNTAX    TimeTicks
		ACCESS    read-only
		STATUS    mandatory
		DESCRIPTION
"Indicates the most recent time at which a resynchronization resulted in a 
change of frame or multiframe alignment. If no such event has occurred 
since system startup, then the value will be zero."
		::= { t1e1CfgEntry  51 }


t1e1CfgT1JitterAttenuatorTrip OBJECT-TYPE
	SYNTAX    TimeTicks
		ACCESS    read-only
		STATUS    mandatory
		DESCRIPTION
"Indicates the most recent time that the jitter attenuator FIFO
reached within 4-bits of it's limit on this line interface. If
no such event has occurred since system startup, then the value
will be zero."
		::= { t1e1CfgEntry  52 }



END
