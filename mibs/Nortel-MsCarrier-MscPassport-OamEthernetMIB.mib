Nortel-MsCarrier-MscPassport-OamEthernetMIB
DEFINITIONS ::= BEGIN



IMPORTS

      OBJECT-TYPE
   FROM RFC-1212

      mscPassportMIBs
   FROM Nortel-MsCarrier-MscPassport-UsefulDefinitionsMIB

      Counter32,
      DisplayString,
      StorageType,
      RowStatus,
      InterfaceIndex,
      Integer32,
      MacAddress,
      Unsigned32
   FROM Nortel-MsCarrier-MscPassport-StandardTextualConventionsMIB

      AsciiString,
      NonReplicated,
      Link
   FROM Nortel-MsCarrier-MscPassport-TextualConventionsMIB

      mscLpIndex,
      mscLp
   FROM Nortel-MsCarrier-MscPassport-LogicalProcessorMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     OamEthernet Enterprise MIB."

oamEthernetMIB OBJECT IDENTIFIER ::= { mscPassportMIBs 79 }










-- Lp/0 OamEthernet
-- This component represents an Ethernet port on the control 
-- processor. Only one instance of this component may be created 
-- corresponding to the one hardware port on the control processor. 
-- This port is designed specifically and exclusively for Passport 
-- Operations, Administration and Maintenance purposes; any other 
-- use of this port is unsupported and not advised.

mscLpOamEnet OBJECT IDENTIFIER ::= { mscLp 27 }



mscLpOamEnetRowStatusTable OBJECT-TYPE
   SYNTAX     SEQUENCE OF MscLpOamEnetRowStatusEntry
   ACCESS     not-accessible
   STATUS     mandatory
   DESCRIPTION
     "This entry controls the addition and deletion of 
      mscLpOamEnet components."
::= { mscLpOamEnet 1 }

mscLpOamEnetRowStatusEntry OBJECT-TYPE
   SYNTAX     MscLpOamEnetRowStatusEntry
   ACCESS     not-accessible
   STATUS     mandatory
   DESCRIPTION
     "A single entry in the table represents a single 
      mscLpOamEnet component."
   INDEX {
      mscLpIndex,
      mscLpOamEnetIndex }
::= { mscLpOamEnetRowStatusTable 1 }

MscLpOamEnetRowStatusEntry ::= SEQUENCE {
   mscLpOamEnetRowStatus
      RowStatus,
   mscLpOamEnetComponentName
      DisplayString,
   mscLpOamEnetStorageType
      StorageType,
   mscLpOamEnetIndex
      Integer32 }

mscLpOamEnetRowStatus OBJECT-TYPE
   SYNTAX     RowStatus 
   ACCESS     read-write
   STATUS     mandatory
   DESCRIPTION
     "This variable is used as the basis for SNMP naming of
      mscLpOamEnet components.
      These components can be added and deleted."
::= { mscLpOamEnetRowStatusEntry 1 }

mscLpOamEnetComponentName OBJECT-TYPE
   SYNTAX     DisplayString 
   ACCESS     read-only
   STATUS     mandatory
   DESCRIPTION
     "This variable provides the component's string name for
      use with the ASCII Console Interface"
::= { mscLpOamEnetRowStatusEntry 2 }

mscLpOamEnetStorageType OBJECT-TYPE
   SYNTAX     StorageType 
   ACCESS     read-only
   STATUS     mandatory
   DESCRIPTION
     "This variable represents the storage type value for the
      mscLpOamEnet tables."
::= { mscLpOamEnetRowStatusEntry 4 }

mscLpOamEnetIndex OBJECT-TYPE
   SYNTAX     Integer32 (0..0)
   ACCESS     not-accessible
   STATUS     mandatory
   DESCRIPTION
     "This variable represents the index for the mscLpOamEnet tables."
::= { mscLpOamEnetRowStatusEntry 10 }

mscLpOamEnetCidDataTable OBJECT-TYPE
   SYNTAX     SEQUENCE OF MscLpOamEnetCidDataEntry
   ACCESS     not-accessible
   STATUS     mandatory
   DESCRIPTION
     "This group contains the attribute for a component's Customer 
      Identifier (CID). Refer to the attribute description for a detailed 
      explanation of CIDs."
::= { mscLpOamEnet 10 }

mscLpOamEnetCidDataEntry OBJECT-TYPE
   SYNTAX     MscLpOamEnetCidDataEntry
   ACCESS     not-accessible
   STATUS     mandatory
   DESCRIPTION
     "An entry in the mscLpOamEnetCidDataTable."
   INDEX {
      mscLpIndex,
      mscLpOamEnetIndex }
::= { mscLpOamEnetCidDataTable 1 }

MscLpOamEnetCidDataEntry ::= SEQUENCE {
   mscLpOamEnetCustomerIdentifier
      Unsigned32 }

mscLpOamEnetCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscLpOamEnetCidDataEntry 1 }

mscLpOamEnetIfEntryTable OBJECT-TYPE
   SYNTAX     SEQUENCE OF MscLpOamEnetIfEntryEntry
   ACCESS     not-accessible
   STATUS     mandatory
   DESCRIPTION
     "This group contains the provisionable attributes for the ifEntry."
::= { mscLpOamEnet 11 }

mscLpOamEnetIfEntryEntry OBJECT-TYPE
   SYNTAX     MscLpOamEnetIfEntryEntry
   ACCESS     not-accessible
   STATUS     mandatory
   DESCRIPTION
     "An entry in the mscLpOamEnetIfEntryTable."
   INDEX {
      mscLpIndex,
      mscLpOamEnetIndex }
::= { mscLpOamEnetIfEntryTable 1 }

MscLpOamEnetIfEntryEntry ::= SEQUENCE {
   mscLpOamEnetIfAdminStatus
      INTEGER,
   mscLpOamEnetIfIndex
      InterfaceIndex }

mscLpOamEnetIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscLpOamEnetIfEntryEntry 1 }

mscLpOamEnetIfIndex OBJECT-TYPE
   SYNTAX     InterfaceIndex (1..65535)
   ACCESS     read-only
   STATUS     mandatory
   DESCRIPTION
     "This is the index for the IfEntry. Its value is automatically initialized 
      during the provisioning process."
::= { mscLpOamEnetIfEntryEntry 2 }

mscLpOamEnetProvTable OBJECT-TYPE
   SYNTAX     SEQUENCE OF MscLpOamEnetProvEntry
   ACCESS     not-accessible
   STATUS     mandatory
   DESCRIPTION
     "This group contains provisioned attributes for the OamEthernet 
      component."
::= { mscLpOamEnet 12 }

mscLpOamEnetProvEntry OBJECT-TYPE
   SYNTAX     MscLpOamEnetProvEntry
   ACCESS     not-accessible
   STATUS     mandatory
   DESCRIPTION
     "An entry in the mscLpOamEnetProvTable."
   INDEX {
      mscLpIndex,
      mscLpOamEnetIndex }
::= { mscLpOamEnetProvTable 1 }

MscLpOamEnetProvEntry ::= SEQUENCE {
   mscLpOamEnetApplicationFramerName
      Link,
   mscLpOamEnetSwitchoverOnFailure
      INTEGER,
   mscLpOamEnetExtendedStatistics
      INTEGER }

mscLpOamEnetApplicationFramerName OBJECT-TYPE
   SYNTAX     Link 
   ACCESS     read-write
   STATUS     mandatory
   DESCRIPTION
     "This attribute specifies which Lan Application is running on this 
      port."
::= { mscLpOamEnetProvEntry 1 }

mscLpOamEnetSwitchoverOnFailure OBJECT-TYPE
   SYNTAX     INTEGER  {
                 enabled(1),
                 disabled(2) }
   ACCESS     read-write
   STATUS     mandatory
   DESCRIPTION
     "This attribute specifies if a CP switchover event should occur if a 
      port or link failure is detected by the initial test process or if a 
      steady state link failure is observed.
      
      This attribute can be set to one of the following values:
      enabled: This value indicates that a switchover will take place if a 
      port or link failure is detected.
      
      disabled: This value indicates that a switchover will not take place 
      if a port or link failure is detected."
   DEFVAL     { enabled }
::= { mscLpOamEnetProvEntry 3 }

mscLpOamEnetExtendedStatistics OBJECT-TYPE
   SYNTAX     INTEGER  {
                 enabled(1),
                 disabled(2) }
   ACCESS     read-write
   STATUS     mandatory
   DESCRIPTION
     "This attribute specifies if extended statistics are to be collected for 
      the OamEthernet component.
      
      The extended statistics include: singleCollisionFrames, 
      multipleCollisionFrames, lateCollisions, excessiveCollisions, 
      carrierSenseErrors, and clearToSendSignalLoss. These statistics all 
      require extra processing to gather and store which may have a 
      negative impact on the overall performance of the OAM Ethernet 
      port.
      
      If extendedStatistics is set to disabled, then these particular 
      statistical attributes will be suppressed from display operations."
   DEFVAL     { disabled }
::= { mscLpOamEnetProvEntry 4 }

mscLpOamEnetAdminInfoTable OBJECT-TYPE
   SYNTAX     SEQUENCE OF MscLpOamEnetAdminInfoEntry
   ACCESS     not-accessible
   STATUS     mandatory
   DESCRIPTION
     "This group contains the attributes pertaining to the vendor of the 
      equipment."
::= { mscLpOamEnet 13 }

mscLpOamEnetAdminInfoEntry OBJECT-TYPE
   SYNTAX     MscLpOamEnetAdminInfoEntry
   ACCESS     not-accessible
   STATUS     mandatory
   DESCRIPTION
     "An entry in the mscLpOamEnetAdminInfoTable."
   INDEX {
      mscLpIndex,
      mscLpOamEnetIndex }
::= { mscLpOamEnetAdminInfoTable 1 }

MscLpOamEnetAdminInfoEntry ::= SEQUENCE {
   mscLpOamEnetVendor
      AsciiString,
   mscLpOamEnetCommentText
      AsciiString }

mscLpOamEnetVendor OBJECT-TYPE
   SYNTAX     AsciiString (SIZE (0..20))
   ACCESS     read-write
   STATUS     mandatory
   DESCRIPTION
     "This is the name of the vendor supplying the facility."
::= { mscLpOamEnetAdminInfoEntry 1 }

mscLpOamEnetCommentText OBJECT-TYPE
   SYNTAX     AsciiString (SIZE (0..60))
   ACCESS     read-write
   STATUS     mandatory
   DESCRIPTION
     "Any miscellaneous text about the facility."
::= { mscLpOamEnetAdminInfoEntry 2 }

mscLpOamEnetStateTable OBJECT-TYPE
   SYNTAX     SEQUENCE OF MscLpOamEnetStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscLpOamEnet 15 }

mscLpOamEnetStateEntry OBJECT-TYPE
   SYNTAX     MscLpOamEnetStateEntry
   ACCESS     not-accessible
   STATUS     mandatory
   DESCRIPTION
     "An entry in the mscLpOamEnetStateTable."
   INDEX {
      mscLpIndex,
      mscLpOamEnetIndex }
::= { mscLpOamEnetStateTable 1 }

MscLpOamEnetStateEntry ::= SEQUENCE {
   mscLpOamEnetAdminState
      INTEGER,
   mscLpOamEnetOperationalState
      INTEGER,
   mscLpOamEnetUsageState
      INTEGER }

mscLpOamEnetAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscLpOamEnetStateEntry 1 }

mscLpOamEnetOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscLpOamEnetStateEntry 2 }

mscLpOamEnetUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscLpOamEnetStateEntry 3 }

mscLpOamEnetOperStatusTable OBJECT-TYPE
   SYNTAX     SEQUENCE OF MscLpOamEnetOperStatusEntry
   ACCESS     not-accessible
   STATUS     mandatory
   DESCRIPTION
     "This group includes the Operational Status attribute. This attribute 
      defines the current operational state of this component."
::= { mscLpOamEnet 16 }

mscLpOamEnetOperStatusEntry OBJECT-TYPE
   SYNTAX     MscLpOamEnetOperStatusEntry
   ACCESS     not-accessible
   STATUS     mandatory
   DESCRIPTION
     "An entry in the mscLpOamEnetOperStatusTable."
   INDEX {
      mscLpIndex,
      mscLpOamEnetIndex }
::= { mscLpOamEnetOperStatusTable 1 }

MscLpOamEnetOperStatusEntry ::= SEQUENCE {
   mscLpOamEnetSnmpOperStatus
      INTEGER }

mscLpOamEnetSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscLpOamEnetOperStatusEntry 1 }

mscLpOamEnetOperTable OBJECT-TYPE
   SYNTAX     SEQUENCE OF MscLpOamEnetOperEntry
   ACCESS     not-accessible
   STATUS     mandatory
   DESCRIPTION
     "This group contains the operational attributes of the OamEthernet 
      component."
::= { mscLpOamEnet 17 }

mscLpOamEnetOperEntry OBJECT-TYPE
   SYNTAX     MscLpOamEnetOperEntry
   ACCESS     not-accessible
   STATUS     mandatory
   DESCRIPTION
     "An entry in the mscLpOamEnetOperTable."
   INDEX {
      mscLpIndex,
      mscLpOamEnetIndex }
::= { mscLpOamEnetOperTable 1 }

MscLpOamEnetOperEntry ::= SEQUENCE {
   mscLpOamEnetMacAddress
      MacAddress,
   mscLpOamEnetActiveStatus
      INTEGER,
   mscLpOamEnetStandbyStatus
      INTEGER }

mscLpOamEnetMacAddress OBJECT-TYPE
   SYNTAX     MacAddress (SIZE (6))
   ACCESS     read-only
   STATUS     mandatory
   DESCRIPTION
     "This attribute indicates the medium access controller (MAC) 
      address automatically assigned to the OAM Ethernet port by the 
      system. The MAC address is displayed in canonical format."
::= { mscLpOamEnetOperEntry 1 }

mscLpOamEnetActiveStatus OBJECT-TYPE
   SYNTAX     INTEGER  {
                 available(1),
                 notAvailable(2) }
   ACCESS     read-only
   STATUS     mandatory
   DESCRIPTION
     "This attribute indicates the status of the Oam Ethernet port on the 
      active CP."
::= { mscLpOamEnetOperEntry 2 }

mscLpOamEnetStandbyStatus OBJECT-TYPE
   SYNTAX     INTEGER  {
                 available(1),
                 notAvailable(2) }
   ACCESS     read-only
   STATUS     mandatory
   DESCRIPTION
     "This attribute indicates the status of the Oam Ethernet port on the 
      standby CP."
::= { mscLpOamEnetOperEntry 3 }

mscLpOamEnetOamEnetStatsTable OBJECT-TYPE
   SYNTAX     SEQUENCE OF MscLpOamEnetOamEnetStatsEntry
   ACCESS     not-accessible
   STATUS     mandatory
   DESCRIPTION
     "This group contains statistical attributes for the		 OamEthernet 
      component."
::= { mscLpOamEnet 18 }

mscLpOamEnetOamEnetStatsEntry OBJECT-TYPE
   SYNTAX     MscLpOamEnetOamEnetStatsEntry
   ACCESS     not-accessible
   STATUS     mandatory
   DESCRIPTION
     "An entry in the mscLpOamEnetOamEnetStatsTable."
   INDEX {
      mscLpIndex,
      mscLpOamEnetIndex }
::= { mscLpOamEnetOamEnetStatsTable 1 }

MscLpOamEnetOamEnetStatsEntry ::= SEQUENCE {
   mscLpOamEnetClearToSendSignalLoss
      Counter32,
   mscLpOamEnetFrameTooShort
      Counter32,
   mscLpOamEnetNumberOfRxCollisions
      Counter32,
   mscLpOamEnetLackOfResourcesDiscards
      Counter32,
   mscLpOamEnetOverrunErrors
      Counter32 }

mscLpOamEnetClearToSendSignalLoss OBJECT-TYPE
   SYNTAX     Counter32 
   ACCESS     read-only
   STATUS     mandatory
   DESCRIPTION
     "This attribute indicates the number of times that the clear to send 
      signal was lost when attempting to transmit a frame. This counter 
      wraps to zero when it exceeds its maximum value.
      
      This attribute is only active if the extendedStatistics attribute is 
      enabled."
::= { mscLpOamEnetOamEnetStatsEntry 14 }

mscLpOamEnetFrameTooShort OBJECT-TYPE
   SYNTAX     Counter32 
   ACCESS     read-only
   STATUS     mandatory
   DESCRIPTION
     "This attribute indicates the number of frames received whose length 
      is less than the allowed minimum frame length. This counter wraps 
      to zero when it exceeds its maximum value."
::= { mscLpOamEnetOamEnetStatsEntry 15 }

mscLpOamEnetNumberOfRxCollisions OBJECT-TYPE
   SYNTAX     Counter32 
   ACCESS     read-only
   STATUS     mandatory
   DESCRIPTION
     "This attribute indicates the number of collisions detected during 
      reception. This counter wraps to zero when it exceeds its maximum 
      value."
::= { mscLpOamEnetOamEnetStatsEntry 17 }

mscLpOamEnetLackOfResourcesDiscards OBJECT-TYPE
   SYNTAX     Counter32 
   ACCESS     read-only
   STATUS     mandatory
   DESCRIPTION
     "This attribute indicates the number of good frames discarded 
      because of a lack of resources available to contain them on the 
      system. This counter wraps to zero when it exceeds its maximum 
      value."
::= { mscLpOamEnetOamEnetStatsEntry 18 }

mscLpOamEnetOverrunErrors OBJECT-TYPE
   SYNTAX     Counter32 
   ACCESS     read-only
   STATUS     mandatory
   DESCRIPTION
     "This attribute indicates the number of frames known to be lost 
      because the local system bus was not available. This counter wraps 
      to zero when it exceeds its maximum value."
::= { mscLpOamEnetOamEnetStatsEntry 19 }

mscLpOamEnetStatsTable OBJECT-TYPE
   SYNTAX     SEQUENCE OF MscLpOamEnetStatsEntry
   ACCESS     not-accessible
   STATUS     mandatory
   DESCRIPTION
     "This group contains statistical attributes for the		 Ethernet component."
::= { mscLpOamEnet 19 }

mscLpOamEnetStatsEntry OBJECT-TYPE
   SYNTAX     MscLpOamEnetStatsEntry
   ACCESS     not-accessible
   STATUS     mandatory
   DESCRIPTION
     "An entry in the mscLpOamEnetStatsTable."
   INDEX {
      mscLpIndex,
      mscLpOamEnetIndex }
::= { mscLpOamEnetStatsTable 1 }

MscLpOamEnetStatsEntry ::= SEQUENCE {
   mscLpOamEnetAlignmentErrors
      Counter32,
   mscLpOamEnetFcsErrors
      Counter32,
   mscLpOamEnetSingleCollisionFrames
      Counter32,
   mscLpOamEnetMultipleCollisionFrames
      Counter32,
   mscLpOamEnetSqeTestErrors
      Counter32,
   mscLpOamEnetDeferredTransmissions
      Counter32,
   mscLpOamEnetLateCollisions
      Counter32,
   mscLpOamEnetExcessiveCollisions
      Counter32,
   mscLpOamEnetMacTransmitErrors
      Counter32,
   mscLpOamEnetCarrierSenseErrors
      Counter32,
   mscLpOamEnetFrameTooLongs
      Counter32,
   mscLpOamEnetMacReceiveErrors
      Counter32 }

mscLpOamEnetAlignmentErrors OBJECT-TYPE
   SYNTAX     Counter32 
   ACCESS     read-only
   STATUS     mandatory
   DESCRIPTION
     "The alignmentErrors counter indicates the number of frames received 
      which were not an integral number of octets in length. Frames will be 
      checked for alignmentErrors before they are checked for Frame Check 
      Sequence (FCS) errors. If there is an alignment error, the error will only 
      be counted here and not in fcsErrors. This counter wraps around after it 
      exceeds its maximum value."
::= { mscLpOamEnetStatsEntry 2 }

mscLpOamEnetFcsErrors OBJECT-TYPE
   SYNTAX     Counter32 
   ACCESS     read-only
   STATUS     mandatory
   DESCRIPTION
     "The fcsErrors, Frame Check Sequence (FCS) error, counter indicates the 
      number of frames received which were an integral number of octets in 
      length and did not pass the FCS check. This counter wraps around after 
      it exceeds its maximum value."
::= { mscLpOamEnetStatsEntry 3 }

mscLpOamEnetSingleCollisionFrames OBJECT-TYPE
   SYNTAX     Counter32 
   ACCESS     read-only
   STATUS     mandatory
   DESCRIPTION
     "The singleCollisionFrames counter indicates the number of frames 
      successfully transmitted which experienced exactly one collision. This 
      counter wraps around after it exceeds its maximum value."
::= { mscLpOamEnetStatsEntry 4 }

mscLpOamEnetMultipleCollisionFrames OBJECT-TYPE
   SYNTAX     Counter32 
   ACCESS     read-only
   STATUS     mandatory
   DESCRIPTION
     "The multipleCollisionFrames counter indicates the number of frames 
      successfully transmitted which experienced more than one collision. 
      This counter wraps around after it exceeds its maximum value."
::= { mscLpOamEnetStatsEntry 5 }

mscLpOamEnetSqeTestErrors OBJECT-TYPE
   SYNTAX     Counter32 
   ACCESS     read-only
   STATUS     mandatory
   DESCRIPTION
     "The sqeTestErrors, Signal Quality Error (SQE) Test errors, counter 
      indicates the number of times the 'SQE Test Error' message has been 
      generated for the station. This counter wraps around after it exceeds its 
      maximum value."
::= { mscLpOamEnetStatsEntry 6 }

mscLpOamEnetDeferredTransmissions OBJECT-TYPE
   SYNTAX     Counter32 
   ACCESS     read-only
   STATUS     mandatory
   DESCRIPTION
     "The deferredTransmissions counter indicates the number of frames 
      which experienced a transmission delay because the medium was busy. 
      This counter wraps around after it exceeds its maximum value."
::= { mscLpOamEnetStatsEntry 7 }

mscLpOamEnetLateCollisions OBJECT-TYPE
   SYNTAX     Counter32 
   ACCESS     read-only
   STATUS     mandatory
   DESCRIPTION
     "The lateCollisions counter indicates the number of times a collision was 
      detected later than 512 bit-times into the transmission of a packet. This 
      counter wraps around after it exceeds its maximum value."
::= { mscLpOamEnetStatsEntry 8 }

mscLpOamEnetExcessiveCollisions OBJECT-TYPE
   SYNTAX     Counter32 
   ACCESS     read-only
   STATUS     mandatory
   DESCRIPTION
     "The excessiveCollisions counter indicates the number of frames which 
      failed to get transmitted due to excessive collisions. This counter wraps 
      around after it exceeds its maximum value."
::= { mscLpOamEnetStatsEntry 9 }

mscLpOamEnetMacTransmitErrors OBJECT-TYPE
   SYNTAX     Counter32 
   ACCESS     read-only
   STATUS     mandatory
   DESCRIPTION
     "The Medium Access Controller (MAC) transmit error counter indicates 
      the number of times that a transmission failed due to internal MAC 
      transmit errors. This counter wraps around after it exceeds its maximum 
      value."
::= { mscLpOamEnetStatsEntry 10 }

mscLpOamEnetCarrierSenseErrors OBJECT-TYPE
   SYNTAX     Counter32 
   ACCESS     read-only
   STATUS     mandatory
   DESCRIPTION
     "The carrier sense error counter indicates the number of times that the 
      carrier sense condition was lost or never asserted when attempting to 
      transmit a frame. This counter wraps around after it exceeds its 
      maximum value."
::= { mscLpOamEnetStatsEntry 11 }

mscLpOamEnetFrameTooLongs OBJECT-TYPE
   SYNTAX     Counter32 
   ACCESS     read-only
   STATUS     mandatory
   DESCRIPTION
     "The frame too long counter indicates the number of frames received 
      which exceeded the maximum frame size. This counter wraps around 
      after it exceeds its maximum value."
::= { mscLpOamEnetStatsEntry 12 }

mscLpOamEnetMacReceiveErrors OBJECT-TYPE
   SYNTAX     Counter32 
   ACCESS     read-only
   STATUS     mandatory
   DESCRIPTION
     "The Medium Access Controller (MAC) receive error counter indicates 
      the number of times a receive failed due to internal MAC receive errors. 
      This counter wraps around after it exceeds its maximum value."
::= { mscLpOamEnetStatsEntry 13 }


-- Lp/0 OamEthernet Test
-- The Test component appears only for 10BaseT OAM Ethernet ports 
-- on the CP. It is used to run the port test for the OAM Ethernet port.

mscLpOamEnetTest OBJECT IDENTIFIER ::= { mscLpOamEnet 2 }



mscLpOamEnetTestRowStatusTable OBJECT-TYPE
   SYNTAX     SEQUENCE OF MscLpOamEnetTestRowStatusEntry
   ACCESS     not-accessible
   STATUS     mandatory
   DESCRIPTION
     "This entry controls the addition and deletion of 
      mscLpOamEnetTest components."
::= { mscLpOamEnetTest 1 }

mscLpOamEnetTestRowStatusEntry OBJECT-TYPE
   SYNTAX     MscLpOamEnetTestRowStatusEntry
   ACCESS     not-accessible
   STATUS     mandatory
   DESCRIPTION
     "A single entry in the table represents a single 
      mscLpOamEnetTest component."
   INDEX {
      mscLpIndex,
      mscLpOamEnetIndex,
      mscLpOamEnetTestIndex }
::= { mscLpOamEnetTestRowStatusTable 1 }

MscLpOamEnetTestRowStatusEntry ::= SEQUENCE {
   mscLpOamEnetTestRowStatus
      RowStatus,
   mscLpOamEnetTestComponentName
      DisplayString,
   mscLpOamEnetTestStorageType
      StorageType,
   mscLpOamEnetTestIndex
      NonReplicated }

mscLpOamEnetTestRowStatus OBJECT-TYPE
   SYNTAX     RowStatus 
   ACCESS     read-only
   STATUS     mandatory
   DESCRIPTION
     "This variable is used as the basis for SNMP naming of
      mscLpOamEnetTest components.
      These components cannot be added nor deleted."
::= { mscLpOamEnetTestRowStatusEntry 1 }

mscLpOamEnetTestComponentName OBJECT-TYPE
   SYNTAX     DisplayString 
   ACCESS     read-only
   STATUS     mandatory
   DESCRIPTION
     "This variable provides the component's string name for
      use with the ASCII Console Interface"
::= { mscLpOamEnetTestRowStatusEntry 2 }

mscLpOamEnetTestStorageType OBJECT-TYPE
   SYNTAX     StorageType 
   ACCESS     read-only
   STATUS     mandatory
   DESCRIPTION
     "This variable represents the storage type value for the
      mscLpOamEnetTest tables."
::= { mscLpOamEnetTestRowStatusEntry 4 }

mscLpOamEnetTestIndex OBJECT-TYPE
   SYNTAX     NonReplicated 
   ACCESS     not-accessible
   STATUS     mandatory
   DESCRIPTION
     "This variable represents the index for the mscLpOamEnetTest tables."
::= { mscLpOamEnetTestRowStatusEntry 10 }

mscLpOamEnetTestOperTable OBJECT-TYPE
   SYNTAX     SEQUENCE OF MscLpOamEnetTestOperEntry
   ACCESS     not-accessible
   STATUS     mandatory
   DESCRIPTION
     "This group contains the operational data for the Test component."
::= { mscLpOamEnetTest 10 }

mscLpOamEnetTestOperEntry OBJECT-TYPE
   SYNTAX     MscLpOamEnetTestOperEntry
   ACCESS     not-accessible
   STATUS     mandatory
   DESCRIPTION
     "An entry in the mscLpOamEnetTestOperTable."
   INDEX {
      mscLpIndex,
      mscLpOamEnetIndex,
      mscLpOamEnetTestIndex }
::= { mscLpOamEnetTestOperTable 1 }

MscLpOamEnetTestOperEntry ::= SEQUENCE {
   mscLpOamEnetTestType
      INTEGER }

mscLpOamEnetTestType OBJECT-TYPE
   SYNTAX     INTEGER  {
                 hardwareLogic(0),
                 configuration(1),
                 memoryMap(2),
                 tdr(3) }
   ACCESS     read-write
   STATUS     mandatory
   DESCRIPTION
     "This attribute is the type of test to be run. The four types of tests 
      available are: the port hardware logic test, the configure and dump 
      memory registers test, the memory mapping test and the Time 
      Domain Reflectometry (TDR) test.
      
      The possible values of this attribute are:
      hardwareLogic: this test checks the port hardware controller for 
      logic errors in some of the on-chip counters and shift registers.
      
      configuration: this test configures the memory registers of the 
      hardware controller in a predetermined way and then dumps the 
      registers and checks their contents for errors.
      
      memoryMap: this test does an extensive test of the memory 
      structures used by the OAM Ethernet port to verify that they are 
      configured correctly and are error-free.
      
      tdr: this test is used to detect and locate cable faults caused by either 
      a short or an open circuit on the coaxial cable."
::= { mscLpOamEnetTestOperEntry 1 }

mscLpOamEnetTestResultsTable OBJECT-TYPE
   SYNTAX     SEQUENCE OF MscLpOamEnetTestResultsEntry
   ACCESS     not-accessible
   STATUS     mandatory
   DESCRIPTION
     "This group contains all the statistics related attributes of the Test 
      component."
::= { mscLpOamEnetTest 11 }

mscLpOamEnetTestResultsEntry OBJECT-TYPE
   SYNTAX     MscLpOamEnetTestResultsEntry
   ACCESS     not-accessible
   STATUS     mandatory
   DESCRIPTION
     "An entry in the mscLpOamEnetTestResultsTable."
   INDEX {
      mscLpIndex,
      mscLpOamEnetIndex,
      mscLpOamEnetTestIndex }
::= { mscLpOamEnetTestResultsTable 1 }

MscLpOamEnetTestResultsEntry ::= SEQUENCE {
   mscLpOamEnetTestCauseOfTermination
      INTEGER,
   mscLpOamEnetTestTestResult
      INTEGER }

mscLpOamEnetTestCauseOfTermination OBJECT-TYPE
   SYNTAX     INTEGER  {
                 testTimeExpired(0),
                 stoppedByOperator(1),
                 unknown(2),
                 neverStarted(3),
                 testRunning(4),
                 testComplete(5) }
   ACCESS     read-only
   STATUS     mandatory
   DESCRIPTION
     "This attribute records the reason why the test terminated.
      
      The possible values of this attribute are:
      testTimeExpired: this value indicates the time allotted for the test to 
      run has expired which caused the test terminate. If the port is locked 
      without the forever option then it will remain locked for only five 
      minutes before being automatically unlocked. If the port unlocks 
      itself after five minutes while the test is running then this attribute 
      will be set to testTimeExpired. If the forever option is used then the 
      test will run until completion, failure, or a Stop command.
      
      stoppedByOperator: this value indicates that the test was terminated 
      when an operator issued a Stop command.
      
      unknown: this value indicates that the test terminated for an 
      unknown reason.
      
      neverStarted: this value indicates that the test never started because 
      the port could not be locked or because there is a hardware failure 
      preventing the tests from running.
      
      testRunning: this value indicates that the test is currently running.
      
      testComplete: this value indicates that the test completed normally."
   DEFVAL     { neverStarted }
::= { mscLpOamEnetTestResultsEntry 1 }

mscLpOamEnetTestTestResult OBJECT-TYPE
   SYNTAX     INTEGER  {
                 neverRun(0),
                 fail(1),
                 pass(2),
                 running(3) }
   ACCESS     read-only
   STATUS     mandatory
   DESCRIPTION
     "This attribute records the result of last port test executed on the 
      OAM Ethernet port. The result can be one of the following values.
      pass: the test passed
      fail: the test failed
      neverRun: the test has not been run
      running: the test is running"
::= { mscLpOamEnetTestResultsEntry 2 }




-- 
-- Version and Compliance statements
-- 



-- Object-Group Statement:
-- A list of all current accessible leaf objects.

-- OBJECTS { mscLpOamEnetLackOfResourcesDiscards,
--           mscLpOamEnetTestType,
--           mscLpOamEnetIfAdminStatus,
--           mscLpOamEnetMultipleCollisionFrames,
--           mscLpOamEnetActiveStatus,
--           mscLpOamEnetAdminState,
--           mscLpOamEnetDeferredTransmissions,
--           mscLpOamEnetCarrierSenseErrors,
--           mscLpOamEnetFrameTooShort,
--           mscLpOamEnetApplicationFramerName,
--           mscLpOamEnetRowStatus,
--           mscLpOamEnetTestComponentName,
--           mscLpOamEnetTestStorageType,
--           mscLpOamEnetMacAddress,
--           mscLpOamEnetCustomerIdentifier,
--           mscLpOamEnetExtendedStatistics,
--           mscLpOamEnetTestTestResult,
--           mscLpOamEnetSwitchoverOnFailure,
--           mscLpOamEnetVendor,
--           mscLpOamEnetOverrunErrors,
--           mscLpOamEnetClearToSendSignalLoss,
--           mscLpOamEnetCommentText,
--           mscLpOamEnetIfIndex,
--           mscLpOamEnetSingleCollisionFrames,
--           mscLpOamEnetUsageState,
--           mscLpOamEnetMacReceiveErrors,
--           mscLpOamEnetTestRowStatus,
--           mscLpOamEnetLateCollisions,
--           mscLpOamEnetMacTransmitErrors,
--           mscLpOamEnetComponentName,
--           mscLpOamEnetStandbyStatus,
--           mscLpOamEnetFrameTooLongs,
--           mscLpOamEnetStorageType,
--           mscLpOamEnetAlignmentErrors,
--           mscLpOamEnetTestCauseOfTermination,
--           mscLpOamEnetSqeTestErrors,
--           mscLpOamEnetSnmpOperStatus,
--           mscLpOamEnetExcessiveCollisions,
--           mscLpOamEnetNumberOfRxCollisions,
--           mscLpOamEnetOperationalState,
--           mscLpOamEnetFcsErrors }
-- STATUS  mandatory
-- DESCRIPTION
--   "A list of all current accessible leaf objects."

oamEthernetGroup OBJECT IDENTIFIER ::= { oamEthernetMIB 1 }
oamEthernetGroupCA OBJECT IDENTIFIER ::= { oamEthernetGroup 1 }
oamEthernetGroupCA02 OBJECT IDENTIFIER ::= { oamEthernetGroupCA 3 }
oamEthernetGroupCA02A OBJECT IDENTIFIER ::= { oamEthernetGroupCA02 2 }



-- Agent-Capabilities Statement:

-- PRODUCT-RELEASE "MscPassport Release 1.2 OamEthernet."
-- STATUS          mandatory
-- DESCRIPTION     "Carrier Passport OamEthernet MIB: MIB Version CA02A,
--                  Software Version CA02S9C."
-- SUPPORTS        Nortel-MsCarrier-MscPassport-OamEthernetMIB
--    INCLUDES     { oamEthernetGroupCA02A }

oamEthernetCapabilities OBJECT IDENTIFIER ::= { oamEthernetMIB 3 }
oamEthernetCapabilitiesCA OBJECT IDENTIFIER ::= { oamEthernetCapabilities 1 }
oamEthernetCapabilitiesCA02 OBJECT IDENTIFIER ::= { oamEthernetCapabilitiesCA 3 }
oamEthernetCapabilitiesCA02A OBJECT IDENTIFIER ::= { oamEthernetCapabilitiesCA02 2 }





END
