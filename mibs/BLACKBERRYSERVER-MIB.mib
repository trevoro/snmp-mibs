BLACKBERRYSERVER-MIB DEFINITIONS ::= BEGIN
        --IMPORTS
               --enterprises FROM SNMPv2-SMI;
             --  MODULE-IDENTITY, OBJECT-TYPE, TRAP-TYPE, enterprises
        --FROM RFC-1215;


      IMPORTS
          MODULE-IDENTITY, OBJECT-TYPE, enterprises
              FROM SNMPv2-SMI 
          TRAP-TYPE 
              FROM RFC-1215
	      DisplayString
              FROM RFC1213-MIB;
              
--              RIM
--                      FROM RIM-MIB;

        rim OBJECT IDENTIFIER ::= { enterprises 3530}
        blackBerryServer OBJECT IDENTIFIER ::= {rim 5}     
        besTrapVariables OBJECT IDENTIFIER ::= {blackBerryServer 9}

--
-- GET: Global Stats Counters for the first instance of BlackBerry Server.
-- These values are kept for backward compatibility with 
-- BlackBerry Server MIB version 1
--

        version OBJECT-TYPE
                SYNTAX INTEGER
                ACCESS read-only
                STATUS mandatory
                DESCRIPTION
                "Version number of the BlackBerryServer MIB."
                ::= {blackBerryServer 1}

        besTotMsgsPending OBJECT-TYPE
                SYNTAX INTEGER
                ACCESS read-only
                STATUS mandatory
                DESCRIPTION
                "Total number of messages queued for delivery to handhelds."
                ::= {blackBerryServer 2}

        besTotMsgsSent OBJECT-TYPE
                SYNTAX INTEGER
                ACCESS read-only
                STATUS mandatory
                DESCRIPTION
                "Total number of messages sent from handhelds."
                ::= {blackBerryServer 3}

        besTotMsgsRecvd OBJECT-TYPE
                SYNTAX INTEGER
                ACCESS read-only
                STATUS mandatory
                DESCRIPTION
                "Total number of messages delivered to handhelds."
                ::= {blackBerryServer 4}

        besTotMsgsXpired OBJECT-TYPE
                SYNTAX INTEGER
                ACCESS read-only
                STATUS mandatory
                DESCRIPTION
                "Total number of messages that have expired."
                ::= {blackBerryServer 5}

        besTotMsgsFiltered OBJECT-TYPE
                SYNTAX INTEGER
                ACCESS read-only
                STATUS mandatory
                DESCRIPTION
                "Total number of messages that have been filtered."
                ::= {blackBerryServer 6}

        besTotMsgsSentPerMin OBJECT-TYPE
                SYNTAX INTEGER
                ACCESS read-only
                STATUS mandatory
                DESCRIPTION
                "Total number of messages sent from handhelds per min."
                ::= {blackBerryServer 7}

        besTotMsgsRecvdPerMin OBJECT-TYPE
                SYNTAX INTEGER
                ACCESS read-only
                STATUS mandatory
                DESCRIPTION
                "Total number of messages delivered to handhelds per min."
                ::= {blackBerryServer 8}

--------------------------------------------------
      -- BlackBerry Server MIB version 2 --
--------------------------------------------------
      
  besNumServerInfoAvailable OBJECT-TYPE
      SYNTAX  INTEGER
      ACCESS  read-only
      STATUS  mandatory
      DESCRIPTION
           "The number of BlackBerry Servers installed on this system, information
           for which is exposed and currently available via SNMP."
      ::= { blackBerryServer 15 }

                
  --
  -- Configuration table (20)
  --

  besConfigTable OBJECT-TYPE
      SYNTAX SEQUENCE OF BesConfigEntry
      ACCESS not-accessible
      STATUS mandatory
      DESCRIPTION
           "This table represents Configuration container for BlackBerry Servers 
           running on the system."          
      ::= { blackBerryServer 20 }

  besConfigEntry OBJECT-TYPE
      SYNTAX BesConfigEntry
      ACCESS not-accessible
      STATUS mandatory
      DESCRIPTION
           "besSrvConfigTable entries."                
      INDEX  { besConfigServerInstance }
      ::= { besConfigTable 1 }

  BesConfigEntry ::=
      SEQUENCE {
          besConfigServerInstance
              INTEGER,
          besConfigServerName   
              DisplayString,
          besConfigVersionString  
              DisplayString,
          besConfigReleaseMaj      
              INTEGER,
          besConfigReleaseMin
              INTEGER,
          besConfigReleaseServicePack
              INTEGER,
          besConfigReleaseBuild
              INTEGER,
          besConfigLicenceTotal
              INTEGER,
          besConfigLicenceUsed
              INTEGER,
          besConfigLicenceRemaining
              INTEGER,
          besConfigServerUID
              DisplayString,
          besConfigSystemAttendant
              DisplayString,
          besConfigSRPHost            
              DisplayString,
          besConfigSRPPort
              INTEGER,
          besConfigAutoBCCEnabled
              INTEGER,
          besConfigAutoBCCAddress
              DisplayString,
          besConfigForceSaveInSentEnabled
              INTEGER,
          besConfigWirelessEmailRecoEnabled
              INTEGER
      }

  besConfigServerInstance OBJECT-TYPE
      SYNTAX INTEGER
      ACCESS read-only
      STATUS mandatory
      DESCRIPTION
              "BlackBerry Server instance number (1..n)."      
      ::= { besConfigEntry 1 }

  besConfigServerName OBJECT-TYPE
      SYNTAX DisplayString
      ACCESS read-only
      STATUS mandatory
      DESCRIPTION
              "BlackBerry Server name."      
      ::= { besConfigEntry 2 }

  besConfigVersionString OBJECT-TYPE
      SYNTAX DisplayString
      ACCESS read-only
      STATUS mandatory
      DESCRIPTION
              "BlackBerry Server version information."      
      ::= { besConfigEntry 10 }
  
  besConfigReleaseMaj OBJECT-TYPE
      SYNTAX INTEGER
      ACCESS read-only
      STATUS mandatory
      DESCRIPTION
              "Major release."      
      ::= { besConfigEntry 11 }
  
  besConfigReleaseMin OBJECT-TYPE
      SYNTAX INTEGER
      ACCESS read-only
      STATUS mandatory
      DESCRIPTION
              "Minor release."      
      ::= { besConfigEntry 12 }
  
  besConfigReleaseServicePack OBJECT-TYPE
      SYNTAX INTEGER
      ACCESS read-only
      STATUS mandatory
      DESCRIPTION
              "Service Pack release."      
      ::= { besConfigEntry 13 }
  
  besConfigReleaseBuild OBJECT-TYPE
      SYNTAX INTEGER
      ACCESS read-only
      STATUS mandatory
      DESCRIPTION
              "Build number."      
      ::= { besConfigEntry 14 }
  
  besConfigLicenceTotal OBJECT-TYPE
      SYNTAX INTEGER
      ACCESS read-only
      STATUS mandatory
      DESCRIPTION
              "Total number of licences installed on the server."      
      ::= { besConfigEntry 20 }
  
  besConfigLicenceUsed OBJECT-TYPE
      SYNTAX INTEGER
      ACCESS read-only
      STATUS mandatory
      DESCRIPTION
              "Total number of licences in use currently."      
      ::= { besConfigEntry 21 }

  besConfigLicenceRemaining OBJECT-TYPE
      SYNTAX INTEGER
      ACCESS read-only
      STATUS mandatory
      DESCRIPTION
              "Total number of licences remaining for use."      
      ::= { besConfigEntry 22 }
      
  besConfigServerUID OBJECT-TYPE
      SYNTAX DisplayString
      ACCESS read-only
      STATUS mandatory
      DESCRIPTION
              "UID of this BlackBerry Server instance."      
      ::= { besConfigEntry 30 }
      
  besConfigSystemAttendant OBJECT-TYPE
      SYNTAX DisplayString
      ACCESS read-only
      STATUS mandatory
      DESCRIPTION
              "System Attendant configured."      
      ::= { besConfigEntry 40 }
      
  besConfigSRPHost OBJECT-TYPE
      SYNTAX DisplayString
      ACCESS read-only
      STATUS mandatory
      DESCRIPTION
              "SRP Host configured."      
      ::= { besConfigEntry 50 }
      
  besConfigSRPPort OBJECT-TYPE
      SYNTAX INTEGER
      ACCESS read-only
      STATUS mandatory
      DESCRIPTION
              "SRP Port configured."      
      ::= { besConfigEntry 51 }
      
  besConfigAutoBCCEnabled OBJECT-TYPE
      SYNTAX INTEGER {enabled(1),disabled(0)}
      ACCESS read-only
      STATUS mandatory
      DESCRIPTION
              "Is the AutoBCC function enabled? 1 - yes, 0 - no."      
      ::= { besConfigEntry 60 }
      
  besConfigAutoBCCAddress OBJECT-TYPE
      SYNTAX DisplayString
      ACCESS read-only
      STATUS mandatory
      DESCRIPTION
              "If AutoBCC function enabled, address it is configured to send to.
              Empty if not enabled."
      ::= { besConfigEntry 61 }
      
  besConfigForceSaveInSentEnabled OBJECT-TYPE
      SYNTAX INTEGER {enabled(1),disabled(0)}
      ACCESS read-only
      STATUS mandatory
      DESCRIPTION
              "Is the Force Save in Sent function enabled?  Applies to BlackBerry Enterprise Server for Lotus Domino only."
      ::= { besConfigEntry 70 }
      
  besConfigWirelessEmailRecoEnabled OBJECT-TYPE
      SYNTAX INTEGER {enabled(1),disabled(0)}
      ACCESS read-only
      STATUS mandatory
      DESCRIPTION
              "Is the Wireless Email Reco enabled?"
      ::= { besConfigEntry 80 }


  --
  -- System health table (25) 
  --
  
  besSysHealthTable OBJECT-TYPE
      SYNTAX SEQUENCE OF BesSysHealthEntry
      ACCESS not-accessible
      STATUS mandatory
      DESCRIPTION
           "This table represents System Health container for BlackBerry Servers 
           running on the system."          
      ::= { blackBerryServer 25 }

  besSysHealthEntry OBJECT-TYPE
      SYNTAX BesSysHealthEntry
      ACCESS not-accessible
      STATUS mandatory
      DESCRIPTION
           "besSysHealthTable entries."                
      INDEX  { besSysHealthServerInstance }
      ::= { besSysHealthTable 1 }

  BesSysHealthEntry ::=
      SEQUENCE {
          besSysHealthServerInstance   
              INTEGER,
          besSysHealthSrpConnectedState
              INTEGER,
          besSysHealthSrpLastConnectDate
              DisplayString,
          besSysHealthSrpReconnectSuccess
              INTEGER,
          besSysHealthSrpReconnectsFail
              INTEGER,
          besSysHealthSrpTotalSecNotConnected
              INTEGER,
          besSysHealthSrpLastErrorText
              DisplayString,
          besSysHealthSrpLastErrorTime
              DisplayString,
          besSysHealthMsgTotalProc
              INTEGER,
          besSysHealthMsgToHandheld
              INTEGER,
          besSysHealthMsgFromHandheld
              INTEGER,
          besSysHealthMsgFilteredByUser
              INTEGER,
          besSysHealthMsgFilteredByGlobal
              INTEGER,
          besSysHealthMsgPending
              INTEGER,
          besSysHealthMsgExpired
              INTEGER,
          besSysHealthMsgErrors
              INTEGER,
          besSysHealthMsgMoreRequests
              INTEGER,
          besSysHealthCalUsersOTACEnabled
              INTEGER,
          besSysHealthCalEventToHandheld
              INTEGER,
          besSysHealthCalEventFromHandheld
              INTEGER,
          besSysHealthWERUsersEnabled
              INTEGER,
          besSysHealthWERRequestsToHandheld
              INTEGER,
          besSysHealthWERRequestsFromHandheld
              INTEGER,
          besSysHealthMdsDeviceConnections
              INTEGER,
          besSysHealthMdsPushConnections
              INTEGER,
          besSysHealthMdsTotalBytesFromDevices
              INTEGER,
          besSysHealthMdsMaxPacketSizeFromDevice
              INTEGER,
          besSysHealthMdsAvgPacketSizeFromDevice
              INTEGER,
          besSysHealthMdsTotalBytesToDevice
              INTEGER,
          besSysHealthMdsMaxPacketSizeToDevice
              INTEGER,
          besSysHealthMdsAvgPacketSizeToDevice
              INTEGER,
          besSysHealthMdsRefusedPackets
              INTEGER,
          besSysHealthMdsInvalidPackets
              INTEGER,
          besSysHealthMdsConnectionSuccess
              INTEGER,
          besSysHealthMdsConnectionFailure
              INTEGER,
          besSysHealthMdsConnectionTruncated
              INTEGER,
          besSysHealthV1MsgsPending
              INTEGER,
          besSysHealthV1TotalMsgsSent
              INTEGER,
          besSysHealthV1TotalMsgsReceived
              INTEGER,
          besSysHealthV1TotalMsgsExpired
              INTEGER,
          besSysHealthV1TotalMsgsFiltered
              INTEGER,
          besSysHealthV1MsgsSentPerMin
              INTEGER,
          besSysHealthV1MsgsRecvdPerMin
              INTEGER,
          besSysHealthV1SRPConnectState
              INTEGER
      }

  besSysHealthServerInstance OBJECT-TYPE
      SYNTAX INTEGER
      ACCESS read-only
      STATUS mandatory
      DESCRIPTION
              "BlackBerry Server instance number (1..n)."
      ::= { besSysHealthEntry 1 }

  besSysHealthSrpConnectedState OBJECT-TYPE
      SYNTAX INTEGER
      ACCESS read-only
      STATUS mandatory
      DESCRIPTION
              "Is the BlackBerry Server connected to the SRP Host?"
      ::= { besSysHealthEntry 10 }

  besSysHealthSrpLastConnectDate OBJECT-TYPE
      SYNTAX DisplayString
      ACCESS read-only
      STATUS mandatory
      DESCRIPTION
              "Datetime of last successful connection to the SRP Host."
      ::= { besSysHealthEntry 11 }

  besSysHealthSrpReconnectSuccess OBJECT-TYPE
      SYNTAX INTEGER
      ACCESS read-only
      STATUS mandatory
      DESCRIPTION
              "Number of times the BlackBerry Server has successfully
              reconnected to SRP Host since it was started."
      ::= { besSysHealthEntry 12 }

  besSysHealthSrpReconnectsFail OBJECT-TYPE
      SYNTAX INTEGER
      ACCESS read-only
      STATUS mandatory
      DESCRIPTION
              "Number of times the BlackBerry Server has tried, but failed,
              to connect to SRP Host since it was started."
      ::= { besSysHealthEntry 13 }

  besSysHealthSrpTotalSecNotConnected OBJECT-TYPE
      SYNTAX INTEGER
      ACCESS read-only
      STATUS mandatory
      DESCRIPTION
              "Total number of seconds the BlackBerry Server has NOT been
              connected to SRP Host since startup."
      ::= { besSysHealthEntry 14 }

  besSysHealthSrpLastErrorText OBJECT-TYPE
      SYNTAX DisplayString
      ACCESS read-only
      STATUS mandatory
      DESCRIPTION
              "Error text about the last failed connection attempt."
      ::= { besSysHealthEntry 15 }

  besSysHealthSrpLastErrorTime OBJECT-TYPE
      SYNTAX DisplayString
      ACCESS read-only
      STATUS mandatory
      DESCRIPTION
              "Datetime of the last connection error."
      ::= { besSysHealthEntry 16 }
          
  besSysHealthMsgTotalProc OBJECT-TYPE
      SYNTAX INTEGER
      ACCESS read-only
      STATUS mandatory
      DESCRIPTION
              "Total number of messages processed by the BlackBerry
              server since startup. Includes to handheld, from handheld
              and filtered messages."
      ::= { besSysHealthEntry 20 }

  besSysHealthMsgToHandheld OBJECT-TYPE
      SYNTAX INTEGER
      ACCESS read-only
      STATUS mandatory
      DESCRIPTION
              "Total number of messages that passed the filter criteria 
              and were sent out to handhelds."
      ::= { besSysHealthEntry 21 }

  besSysHealthMsgFromHandheld OBJECT-TYPE
      SYNTAX INTEGER
      ACCESS read-only
      STATUS mandatory
      DESCRIPTION
              "Total number of messages sent from handhelds."
      ::= { besSysHealthEntry 22 }

  besSysHealthMsgFilteredByUser OBJECT-TYPE
      SYNTAX INTEGER
      ACCESS read-only
      STATUS mandatory
      DESCRIPTION
              "Total number of messages filtered out by user filter
              settings."
      ::= { besSysHealthEntry 23 }

  besSysHealthMsgFilteredByGlobal OBJECT-TYPE
      SYNTAX INTEGER
      ACCESS read-only
      STATUS mandatory
      DESCRIPTION
              "Total number of messages filtered out by the global
              filter settings."
      ::= { besSysHealthEntry 24 }

  besSysHealthMsgPending OBJECT-TYPE
      SYNTAX INTEGER
      ACCESS read-only
      STATUS mandatory
      DESCRIPTION
              "Total number of messages pending delivery."
      ::= { besSysHealthEntry 25 }

  besSysHealthMsgExpired OBJECT-TYPE
      SYNTAX INTEGER
      ACCESS read-only
      STATUS mandatory
      DESCRIPTION
              "Total number of messages expired."
      ::= { besSysHealthEntry 26 }

  besSysHealthMsgErrors OBJECT-TYPE
      SYNTAX INTEGER
      ACCESS read-only
      STATUS mandatory
      DESCRIPTION
              "Total number of messages that were non-deliverable due to error."
      ::= { besSysHealthEntry 27 }

  besSysHealthMsgMoreRequests OBJECT-TYPE
      SYNTAX INTEGER
      ACCESS read-only
      STATUS mandatory
      DESCRIPTION
              "Total number of MORE requests issued from devices."
      ::= { besSysHealthEntry 28 }

  besSysHealthCalUsersOTACEnabled OBJECT-TYPE
      SYNTAX INTEGER
      ACCESS read-only
      STATUS mandatory
      DESCRIPTION
              "Total number of users enabled for OTA Calendar."
      ::= { besSysHealthEntry 40 }

  besSysHealthCalEventToHandheld OBJECT-TYPE
      SYNTAX INTEGER
      ACCESS read-only
      STATUS mandatory
      DESCRIPTION
              "Total number of calendar events sent to handhelds."
      ::= { besSysHealthEntry 41 }

  besSysHealthCalEventFromHandheld OBJECT-TYPE
      SYNTAX INTEGER
      ACCESS read-only
      STATUS mandatory
      DESCRIPTION
              "Total number of calendar events sent by handhelds."
      ::= { besSysHealthEntry 42 }

  besSysHealthWERUsersEnabled OBJECT-TYPE
      SYNTAX INTEGER
      ACCESS read-only
      STATUS mandatory
      DESCRIPTION
              "Total number of users enabled for Wireless Email Reco."
      ::= { besSysHealthEntry 50 }
              
  besSysHealthWERRequestsToHandheld OBJECT-TYPE
      SYNTAX INTEGER
      ACCESS read-only
      STATUS mandatory
      DESCRIPTION
              "Total number of Wireless Email Reco events sent to handhelds."
      ::= { besSysHealthEntry 51 }

  besSysHealthWERRequestsFromHandheld OBJECT-TYPE
      SYNTAX INTEGER
      ACCESS read-only
      STATUS mandatory
      DESCRIPTION
              "Total number of Wireless Email Reco events sent from handhelds."
      ::= { besSysHealthEntry 52 }

  besSysHealthMdsDeviceConnections OBJECT-TYPE
      SYNTAX INTEGER
      ACCESS read-only
      STATUS mandatory
      DESCRIPTION
              "Number of handheld-initiated connections."
      ::= { besSysHealthEntry 60 }

  besSysHealthMdsPushConnections OBJECT-TYPE
      SYNTAX INTEGER
      ACCESS read-only
      STATUS mandatory
      DESCRIPTION
              "Number of push server connections."
      ::= { besSysHealthEntry 61 }

  besSysHealthMdsTotalBytesFromDevices OBJECT-TYPE
      SYNTAX INTEGER
      ACCESS read-only
      STATUS mandatory
      DESCRIPTION
              "Total data size (in bytes) from device."
      ::= { besSysHealthEntry 62 }

  besSysHealthMdsMaxPacketSizeFromDevice OBJECT-TYPE
      SYNTAX INTEGER
      ACCESS read-only
      STATUS mandatory
      DESCRIPTION
              "Maximum packet data size (in bytes) from device."
      ::= { besSysHealthEntry 63 }

  besSysHealthMdsAvgPacketSizeFromDevice OBJECT-TYPE
      SYNTAX INTEGER
      ACCESS read-only
      STATUS mandatory
      DESCRIPTION
              "Average packet data size (in bytes) from device."
      ::= { besSysHealthEntry 64 }

  besSysHealthMdsTotalBytesToDevice OBJECT-TYPE
      SYNTAX INTEGER
      ACCESS read-only
      STATUS mandatory
      DESCRIPTION
              "Total data size (in bytes) from push."
      ::= { besSysHealthEntry 65 }

  besSysHealthMdsMaxPacketSizeToDevice OBJECT-TYPE
      SYNTAX INTEGER
      ACCESS read-only
      STATUS mandatory
      DESCRIPTION
              "Maximum packet data size (in bytes) from push."
      ::= { besSysHealthEntry 66 }

  besSysHealthMdsAvgPacketSizeToDevice OBJECT-TYPE
      SYNTAX INTEGER
      ACCESS read-only
      STATUS mandatory
      DESCRIPTION
              "Average packet data size (in bytes) from push."
      ::= { besSysHealthEntry 67 }

  besSysHealthMdsRefusedPackets OBJECT-TYPE
      SYNTAX INTEGER
      ACCESS read-only
      STATUS mandatory
      DESCRIPTION
              "Number of packets refused by SRP Host."
      ::= { besSysHealthEntry 68 }

  besSysHealthMdsInvalidPackets OBJECT-TYPE
      SYNTAX INTEGER
      ACCESS read-only
      STATUS mandatory
      DESCRIPTION
              "Number of invalid packets received by MDS."
      ::= { besSysHealthEntry 69 }

  besSysHealthMdsConnectionSuccess OBJECT-TYPE
      SYNTAX INTEGER
      ACCESS read-only
      STATUS mandatory
      DESCRIPTION
              "Number of successful connections initiated
              by MDS to another address/service."
      ::= { besSysHealthEntry 70 }

  besSysHealthMdsConnectionFailure OBJECT-TYPE
      SYNTAX INTEGER
      ACCESS read-only
      STATUS mandatory
      DESCRIPTION
              "Number of failed connections initiated
              by MDS to another address/service."
      ::= { besSysHealthEntry 71 }

  besSysHealthMdsConnectionTruncated OBJECT-TYPE
      SYNTAX INTEGER
      ACCESS read-only
      STATUS mandatory
      DESCRIPTION
              "Number of truncated connections encountered by MDS."
      ::= { besSysHealthEntry 72 }

  --
  -- Global Stats Counters for all instances of BlackBerry Server.
  -- These values are kept for backward compatibility with 
  -- BlackBerry Server MIB version 1
  --

  besSysHealthV1MsgsPending OBJECT-TYPE
      SYNTAX INTEGER
      ACCESS read-only
      STATUS mandatory
      DESCRIPTION
              "Total number of messages queued for delivery to handhelds."
      ::= { besSysHealthEntry 202 }

  besSysHealthV1TotalMsgsSent OBJECT-TYPE
      SYNTAX INTEGER
      ACCESS read-only
      STATUS mandatory
      DESCRIPTION
              "Total number of messages sent from handhelds."
      ::= { besSysHealthEntry 203 }

  besSysHealthV1TotalMsgsReceived OBJECT-TYPE
      SYNTAX INTEGER
      ACCESS read-only
      STATUS mandatory
      DESCRIPTION
              "Total number of messages delivered to handhelds."
      ::= { besSysHealthEntry 204 }

  besSysHealthV1TotalMsgsExpired OBJECT-TYPE
      SYNTAX INTEGER
      ACCESS read-only
      STATUS mandatory
      DESCRIPTION
              "Total number of messages that have expired."
      ::= { besSysHealthEntry 205 }

  besSysHealthV1TotalMsgsFiltered OBJECT-TYPE
      SYNTAX INTEGER
      ACCESS read-only
      STATUS mandatory
      DESCRIPTION
              "Total number of messages that have been filtered."
      ::= { besSysHealthEntry 206 }

  besSysHealthV1MsgsSentPerMin OBJECT-TYPE
      SYNTAX INTEGER
      ACCESS read-only
      STATUS mandatory
      DESCRIPTION
              "Total number of messages sent from handhelds per min."
      ::= { besSysHealthEntry 207 }

  besSysHealthV1MsgsRecvdPerMin OBJECT-TYPE
      SYNTAX INTEGER
      ACCESS read-only
      STATUS mandatory
      DESCRIPTION
              "Total number of messages delivered to handhelds per min."
      ::= { besSysHealthEntry 208 }

  besSysHealthV1SRPConnectState OBJECT-TYPE
      SYNTAX INTEGER {enabled(1),disabled(0)}                
      ACCESS read-only
      STATUS mandatory
      DESCRIPTION
              "Indication of the state of the SRP connection."
      ::= { besSysHealthEntry 209 }
  
  --
  -- Mail server health table (26)
  --

  besMailServerHealthTable OBJECT-TYPE
      SYNTAX SEQUENCE OF BesMailServerHealthEntry
      ACCESS not-accessible
      STATUS mandatory
      DESCRIPTION
               "This table contains the list of mail servers as well as statistics
               and performance values related to each particular mail server. Applies to BlackBerry Enterprise Server for Lotus Domino only."
      ::= { blackBerryServer 26 }

  besMailServerHealthEntry OBJECT-TYPE
      SYNTAX BesMailServerHealthEntry
      ACCESS not-accessible
      STATUS mandatory
      DESCRIPTION
               "Mail Server entries.  The BlackBerry Server instance
			   and Server Health user ID are used as the index value associated 
			   with each row. Applies to BlackBerry Enterprise Server for Lotus Domino only."      
      INDEX  { besMailServerHealthServerInstance, besMailServerHealthServerId }
      ::= { besMailServerHealthTable 1 }

  BesMailServerHealthEntry ::=
      SEQUENCE {
          besMailServerHealthServerInstance        
              INTEGER,
          besMailServerHealthServerId
              INTEGER,
          besMailServerHealthServerName
              DisplayString,
          besMailServerHealthTotalUsers
              INTEGER,
          besMailServerHealthAvgResponceTime10min
              INTEGER,
          besMailServerHealthFailedConn10min
              INTEGER
      }

  besMailServerHealthServerInstance OBJECT-TYPE
      SYNTAX INTEGER
      ACCESS read-only
      STATUS mandatory
      DESCRIPTION
              "Instance id of the BlackBerry Server associated with this row. Applies to BlackBerry Enterprise Server for Lotus Domino only."      
      ::= { besMailServerHealthEntry 1 }

  besMailServerHealthServerId OBJECT-TYPE
      SYNTAX INTEGER
      ACCESS read-only
      STATUS mandatory
      DESCRIPTION
              "Instance id of the Mail Server associated with this row. Applies to BlackBerry Enterprise Server for Lotus Domino only."      
      ::= { besMailServerHealthEntry 2 }

  besMailServerHealthServerName OBJECT-TYPE
      SYNTAX DisplayString
      ACCESS read-only
      STATUS mandatory
      DESCRIPTION
              "Name of the Mail Server associated with this row. Applies to BlackBerry Enterprise Server for Lotus Domino only."      
      ::= { besMailServerHealthEntry 3 }
  
  besMailServerHealthTotalUsers OBJECT-TYPE
      SYNTAX INTEGER
      ACCESS read-only
      STATUS mandatory
      DESCRIPTION
              "Number of users who are homed on this mail server. Applies to BlackBerry Enterprise Server for Lotus Domino only."      
      ::= { besMailServerHealthEntry 10 }

  besMailServerHealthAvgResponceTime10min OBJECT-TYPE
      SYNTAX INTEGER
      ACCESS read-only
      STATUS mandatory
      DESCRIPTION
              "Average responce time (in milliseconds) for operations for users on this mail server in the last 10 minutes. Applies to BlackBerry Enterprise Server for Lotus Domino only."      
      ::= { besMailServerHealthEntry 11 }

  besMailServerHealthFailedConn10min OBJECT-TYPE
      SYNTAX INTEGER
      ACCESS read-only
      STATUS mandatory
      DESCRIPTION
              "Number of failed connection attempts to this mail server in the last 10 minutes. Applies to BlackBerry Enterprise Server for Lotus Domino only."      
      ::= { besMailServerHealthEntry 12 }

  --
  -- User health table (30)
  --

  besUserHealthTable OBJECT-TYPE
      SYNTAX SEQUENCE OF BesUserHealthEntry
      ACCESS not-accessible
      STATUS mandatory
      DESCRIPTION
               "This table contains the list of user configuration, statistics
               and performance values related to each particular user and device
               which are exist for a given BES."
      ::= { blackBerryServer 30 }

  besUserHealthEntry OBJECT-TYPE
      SYNTAX BesUserHealthEntry
      ACCESS not-accessible
      STATUS mandatory
      DESCRIPTION
               "mssqlDbOptionTable entries.  The BlackBerry Server instance
			   and User Health user ID are used as the index value associated 
			   with each row."      
      INDEX  { besUserHealthServerInstance, besUserHealthUserId }
      ::= { besUserHealthTable 1 }

  BesUserHealthEntry ::=
      SEQUENCE {
          besUserHealthServerInstance        
              INTEGER,
          besUserHealthUserId
              INTEGER,
          besUserHealthUserName
              DisplayString,
          besUserHealthLastErrorText
              DisplayString,
          besUserHealthLastErrorTime
              DisplayString,
          besUserHealthDeviceNetwork
              DisplayString,
          besUserHealthDevicePIN
              DisplayString,
          besUserHealthDeviceInCradle
              INTEGER,
          besUserHealthNumRedirectedFolders
              INTEGER,
          besUserHealthSaveInSent
              INTEGER,
          besUserHealthRedirectEnabledOnDesktop
              INTEGER,
          besUserHealthDisableWhileInCradle
              INTEGER,
          besUserHealthFullyConfigured
              INTEGER,
          besUserHealthEnabled
              INTEGER,
          besUserHealthMsgTotalProc
              INTEGER,
          besUserHealthMsgToHandheld
              INTEGER,
          besUserHealthMsgFromHandheld
              INTEGER,
          besUserHealthMsgFiltered
              INTEGER,
          besUserHealthMsgPending
              INTEGER,
          besUserHealthMsgExpired
              INTEGER,
          besUserHealthMsgErrors
              INTEGER,
          besUserHealthMsgMoreRequests
              INTEGER,
          besUserHealthMsgForwardedFromDevice
              INTEGER,
          besUserHealthMsgRepliedToWithText
              INTEGER,
          besUserHealthLastTimeInCradle
              DisplayString,
          besUserHealthLastInteractionWithDevice
              DisplayString,
          besUserHealthLastMessageForwarded
              DisplayString,
          besUserHealthLastKeyDateGenerated
              DisplayString,
          besUserHealthAvgKBForwarded
              INTEGER,
          besUserHealthAvgKBReplyWithText
              INTEGER,
          besUserHealthAvgLatencyInSecLast10Msg
              INTEGER,
          besUserHealthCalOTAEnabled
              INTEGER,
          besUserHealthCalEventToHandheld
              INTEGER,
          besUserHealthCalEventFromHandheld
              INTEGER,
          besUserHealthWirelessEmailRecoEnabled
              INTEGER,
          besUserHealthWERRequestsToHandheld
              INTEGER,
          besUserHealthWERRequestsFromHandheld
              INTEGER
      }

  besUserHealthServerInstance OBJECT-TYPE
      SYNTAX INTEGER
      ACCESS read-only
      STATUS mandatory
      DESCRIPTION
              "Instance id of the BlackBerry Server associated with this row."      
      ::= { besUserHealthEntry 1 }

  besUserHealthUserId OBJECT-TYPE
      SYNTAX INTEGER
      ACCESS read-only
      STATUS mandatory
      DESCRIPTION
              "Instance id of the user associated with this row."      
      ::= { besUserHealthEntry 2 }

  besUserHealthUserName OBJECT-TYPE
      SYNTAX DisplayString
      ACCESS read-only
      STATUS mandatory
      DESCRIPTION
              "User name of the user associated with this row."      
      ::= { besUserHealthEntry 3 }

  besUserHealthLastErrorText OBJECT-TYPE
      SYNTAX DisplayString
      ACCESS read-only
      STATUS mandatory
      DESCRIPTION
              "The last time an operation for this user failed, this 
              is the error text we got back."
      ::= { besUserHealthEntry 10 }

  besUserHealthLastErrorTime OBJECT-TYPE
      SYNTAX DisplayString
      ACCESS read-only
      STATUS mandatory
      DESCRIPTION
              "The datetime of the last error for the user associated 
              with this row."      
      ::= { besUserHealthEntry 11 }

  besUserHealthDeviceNetwork OBJECT-TYPE
      SYNTAX DisplayString
      ACCESS read-only
      STATUS mandatory
      DESCRIPTION
              "Network the device is on for the user associated
              with this row."      
      ::= { besUserHealthEntry 20 }

  besUserHealthDevicePIN OBJECT-TYPE
      SYNTAX DisplayString
      ACCESS read-only
      STATUS mandatory
      DESCRIPTION
              "PIN number of the device for the user associated
              with this row."      
      ::= { besUserHealthEntry 21 }

  besUserHealthDeviceInCradle OBJECT-TYPE
      SYNTAX INTEGER
      ACCESS read-only
      STATUS mandatory
      DESCRIPTION
              "Is the device in cradle?"      
      ::= { besUserHealthEntry 22 }

  besUserHealthNumRedirectedFolders OBJECT-TYPE
      SYNTAX INTEGER
      ACCESS read-only
      STATUS mandatory
      DESCRIPTION
              "Number of redirected folders the user has configed."      
      ::= { besUserHealthEntry 30 }

  besUserHealthSaveInSent OBJECT-TYPE
      SYNTAX INTEGER {enabled(1),disabled(0)}
      ACCESS read-only
      STATUS mandatory
      DESCRIPTION
              "Is 'save in sent' enabled for the user associated
              with this row?"      
      ::= { besUserHealthEntry 31 }

  besUserHealthRedirectEnabledOnDesktop OBJECT-TYPE
      SYNTAX INTEGER {enabled(1),disabled(0)}
      ACCESS read-only
      STATUS mandatory
      DESCRIPTION
              "Is redirection enabled in Desktop Manager for 
              the user associated with this row?"      
      ::= { besUserHealthEntry 32 }

  besUserHealthDisableWhileInCradle OBJECT-TYPE
      SYNTAX INTEGER {enabled(1),disabled(0)}
      ACCESS read-only
      STATUS mandatory
      DESCRIPTION
              "Is the option in Desktop Manager to disable 
              redirection while in the cradle?"
      ::= { besUserHealthEntry 33 }

  besUserHealthFullyConfigured OBJECT-TYPE
      SYNTAX INTEGER
      ACCESS read-only
      STATUS mandatory
      DESCRIPTION
              "Is the Is the device fully configured with
              PIN & encryption key?"
      ::= { besUserHealthEntry 34 }

  besUserHealthEnabled OBJECT-TYPE
      SYNTAX INTEGER
      ACCESS read-only
      STATUS mandatory
      DESCRIPTION
              "Is the user currently enabled?"
      ::= { besUserHealthEntry 35 }

  besUserHealthMsgTotalProc OBJECT-TYPE
      SYNTAX INTEGER
      ACCESS read-only
      STATUS mandatory
      DESCRIPTION
              "Total number of Messages processed by the BES since
              startup for this user. Includes to handheld, from
              handheld and filtered."
      ::= { besUserHealthEntry 40 }

  besUserHealthMsgToHandheld OBJECT-TYPE
      SYNTAX INTEGER
      ACCESS read-only
      STATUS mandatory
      DESCRIPTION
              "Total number of messages that passed the filter
              criteria and were sent out to  the handheld. Messaging
              only (no calendar)."
      ::= { besUserHealthEntry 41 }

  besUserHealthMsgFromHandheld OBJECT-TYPE
      SYNTAX INTEGER
      ACCESS read-only
      STATUS mandatory
      DESCRIPTION
              "Total number of messages sent from handheld. Messaging
              only (no calendar)."
      ::= { besUserHealthEntry 42 }

  besUserHealthMsgFiltered OBJECT-TYPE
      SYNTAX INTEGER
      ACCESS read-only
      STATUS mandatory
      DESCRIPTION
              "Total number of messages filtered out by user filter 
              settings."
      ::= { besUserHealthEntry 43 }

  besUserHealthMsgPending OBJECT-TYPE
      SYNTAX INTEGER
      ACCESS read-only
      STATUS mandatory
      DESCRIPTION
              "Total number of messages pending delivery."
      ::= { besUserHealthEntry 44 }

  besUserHealthMsgExpired OBJECT-TYPE
      SYNTAX INTEGER
      ACCESS read-only
      STATUS mandatory
      DESCRIPTION
              "Total number of messages expired."
      ::= { besUserHealthEntry 45 }

  besUserHealthMsgErrors OBJECT-TYPE
      SYNTAX INTEGER
      ACCESS read-only
      STATUS mandatory
      DESCRIPTION
              "Total number of messages that were non-deliverable
              due to error."
      ::= { besUserHealthEntry 46 }

  besUserHealthMsgMoreRequests OBJECT-TYPE
      SYNTAX INTEGER
      ACCESS read-only
      STATUS mandatory
      DESCRIPTION
              "Total number of MORE requests issued from device."
      ::= { besUserHealthEntry 47 }

  besUserHealthMsgForwardedFromDevice OBJECT-TYPE
      SYNTAX INTEGER
      ACCESS read-only
      STATUS mandatory
      DESCRIPTION
              "Total number of messages the user has forwarded
              from the device."
      ::= { besUserHealthEntry 48 }

  besUserHealthMsgRepliedToWithText OBJECT-TYPE
      SYNTAX INTEGER
      ACCESS read-only
      STATUS mandatory
      DESCRIPTION
              "Total number of messages that were replies-with-text
              from the device."
      ::= { besUserHealthEntry 49 }

  besUserHealthLastTimeInCradle OBJECT-TYPE
      SYNTAX DisplayString
      ACCESS read-only
      STATUS mandatory
      DESCRIPTION
              "Datetime of the last time the user had the device
              in the cradle."
      ::= { besUserHealthEntry 60 }

  besUserHealthLastInteractionWithDevice OBJECT-TYPE
      SYNTAX DisplayString
      ACCESS read-only
      STATUS mandatory
      DESCRIPTION
              "Datetime of the last interaction the BES had with
              the device."
      ::= { besUserHealthEntry 61 }

  besUserHealthLastMessageForwarded OBJECT-TYPE
      SYNTAX DisplayString
      ACCESS read-only
      STATUS mandatory
      DESCRIPTION
              "Datetime of the last message (mail or calendar) that
              was sent to the device."
      ::= { besUserHealthEntry 62 }

  besUserHealthLastKeyDateGenerated OBJECT-TYPE
      SYNTAX DisplayString
      ACCESS read-only
      STATUS mandatory
      DESCRIPTION
              "Datetime of the last time the user generated
              an encryption key."
      ::= { besUserHealthEntry 63 }

  besUserHealthAvgKBForwarded OBJECT-TYPE
      SYNTAX INTEGER
      ACCESS read-only
      STATUS mandatory
      DESCRIPTION
              "Average size of messages forwarded from the device (in kb).
              I.e. if I receive a message with a 5mb attachment and
              forward it from my handheld to another user, this value
              would be 5120kb."
      ::= { besUserHealthEntry 70 }

  besUserHealthAvgKBReplyWithText OBJECT-TYPE
      SYNTAX INTEGER
      ACCESS read-only
      STATUS mandatory
      DESCRIPTION
              "Similar to besUserHealthAvgKBForwarded, but for messages
              that are replies-with-text."
      ::= { besUserHealthEntry 71 }

  besUserHealthAvgLatencyInSecLast10Msg OBJECT-TYPE
      SYNTAX INTEGER
      ACCESS read-only
      STATUS mandatory
      DESCRIPTION
              "For the last 10 messages sent to the handheld, the average
              length of time (in sec) between the message arriving in the
              mail system and a DELIVERED on the device."
      ::= { besUserHealthEntry 72 }

  besUserHealthCalOTAEnabled OBJECT-TYPE
      SYNTAX INTEGER {enabled(1),disabled(0)}
      ACCESS read-only
      STATUS mandatory
      DESCRIPTION
              "Is the user OTAC enabled?"
      ::= { besUserHealthEntry 80 }

  besUserHealthCalEventToHandheld OBJECT-TYPE
      SYNTAX INTEGER
      ACCESS read-only
      STATUS mandatory
      DESCRIPTION
              "Total number of calendar events sent to the device."
      ::= { besUserHealthEntry 81 }

  besUserHealthCalEventFromHandheld OBJECT-TYPE
      SYNTAX INTEGER
      ACCESS read-only
      STATUS mandatory
      DESCRIPTION
              "Total number of calendar events sent from the device."
      ::= { besUserHealthEntry 82 }

  besUserHealthWirelessEmailRecoEnabled OBJECT-TYPE
      SYNTAX INTEGER {enabled(1),disabled(0)}
      ACCESS read-only
      STATUS mandatory
      DESCRIPTION
              "Is the user enabled for Wireless Email Reco?"
      ::= { besUserHealthEntry 90 }

  besUserHealthWERRequestsToHandheld OBJECT-TYPE
      SYNTAX INTEGER
      ACCESS read-only
      STATUS mandatory
      DESCRIPTION
              "Total number of Wireless Email Reco events sent
              to handhelds"
      ::= { besUserHealthEntry 91 }

  besUserHealthWERRequestsFromHandheld OBJECT-TYPE
      SYNTAX INTEGER
      ACCESS read-only
      STATUS mandatory
      DESCRIPTION
              "Total number of Wireless Email Reco events sent
              from handhelds"
      ::= { besUserHealthEntry 92 }



--
-- TRAP: BlackBerryServer Traps
--     
        besSRPConnectState OBJECT-TYPE
                SYNTAX INTEGER {enabled(1),disabled(0)}                
                ACCESS read-only
                STATUS mandatory
                DESCRIPTION 
                "Indication of the state of the SRP connection."
                ::= {besTrapVariables 1}

        besSRPConnectEvent TRAP-TYPE
              ENTERPRISE blackBerryServer   
              VARIABLES  {besSRPConnectState}
              DESCRIPTION "SRPConnect state."
              ::= 1
        
        besHungThreadEvent TRAP-TYPE
              ENTERPRISE blackBerryServer   
              DESCRIPTION "Event related to detection of hung threads 
                          in Exchange BES."
              ::= 3

        besMailServerDownEvent TRAP-TYPE
              ENTERPRISE blackBerryServer   
              DESCRIPTION "Event is generated when more than one user (or one user 
                          if there is only one) gets more than one error connecting 
                          to a particular mail server, and those errors are not 
                          Access Control related."
              ::= 5
       
        besMDStoBESConnectionEvent TRAP-TYPE
              ENTERPRISE blackBerryServer   
              DESCRIPTION "MDS to BES connection state has changed."
              ::= 7
       
        besMDSStartStopEvent TRAP-TYPE
              ENTERPRISE blackBerryServer   
              DESCRIPTION "MDS has started or stopped."
              ::= 11
       
        besMDStoDBConnectionEvent TRAP-TYPE
              ENTERPRISE blackBerryServer   
              DESCRIPTION "MDS to database connection state has changed."
              ::= 13
       
        besCriticalEvent TRAP-TYPE
              ENTERPRISE blackBerryServer   
              DESCRIPTION "Critical event has happened. These are the events normally
                          logged with 1xxxx and 5xxxx event IDs."
              ::= 21
       
END
