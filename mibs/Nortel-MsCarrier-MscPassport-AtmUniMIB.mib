Nortel-MsCarrier-MscPassport-AtmUniMIB
DEFINITIONS ::= BEGIN



IMPORTS

      OBJECT-TYPE
   FROM RFC-1212

      mscPassportMIBs
   FROM Nortel-MsCarrier-MscPassport-UsefulDefinitionsMIB

      Counter32,
      DisplayString,
      StorageType,
      RowStatus,
      Gauge32,
      Integer32,
      Unsigned32
   FROM Nortel-MsCarrier-MscPassport-StandardTextualConventionsMIB

      AsciiString,
      Hex,
      NonReplicated,
      HexString,
      AsciiStringIndex
   FROM Nortel-MsCarrier-MscPassport-TextualConventionsMIB

      mscAtmIf,
      mscAtmIfVptIndex,
      mscAtmIfVpt,
      mscAtmIfIndex
   FROM Nortel-MsCarrier-MscPassport-AtmCoreMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     AtmUni Enterprise MIB."

atmUniMIB OBJECT IDENTIFIER ::= { mscPassportMIBs 69 }










-- AtmIf/n Uni
-- This component represents an ATM UNI interface. If this 
-- component is provisioned the Iisp component can not be 
-- provisioned under that AtmIf component. If this component is 
-- deleted, then all associated Vcc components are deleted.

mscAtmIfUni OBJECT IDENTIFIER ::= { mscAtmIf 6 }



mscAtmIfUniRowStatusTable OBJECT-TYPE
   SYNTAX     SEQUENCE OF MscAtmIfUniRowStatusEntry
   ACCESS     not-accessible
   STATUS     mandatory
   DESCRIPTION
     "This entry controls the addition and deletion of 
      mscAtmIfUni components."
::= { mscAtmIfUni 1 }

mscAtmIfUniRowStatusEntry OBJECT-TYPE
   SYNTAX     MscAtmIfUniRowStatusEntry
   ACCESS     not-accessible
   STATUS     mandatory
   DESCRIPTION
     "A single entry in the table represents a single 
      mscAtmIfUni component."
   INDEX {
      mscAtmIfIndex,
      mscAtmIfUniIndex }
::= { mscAtmIfUniRowStatusTable 1 }

MscAtmIfUniRowStatusEntry ::= SEQUENCE {
   mscAtmIfUniRowStatus
      RowStatus,
   mscAtmIfUniComponentName
      DisplayString,
   mscAtmIfUniStorageType
      StorageType,
   mscAtmIfUniIndex
      NonReplicated }

mscAtmIfUniRowStatus OBJECT-TYPE
   SYNTAX     RowStatus 
   ACCESS     read-write
   STATUS     mandatory
   DESCRIPTION
     "This variable is used as the basis for SNMP naming of
      mscAtmIfUni components.
      These components can be added and deleted."
::= { mscAtmIfUniRowStatusEntry 1 }

mscAtmIfUniComponentName OBJECT-TYPE
   SYNTAX     DisplayString 
   ACCESS     read-only
   STATUS     mandatory
   DESCRIPTION
     "This variable provides the component's string name for
      use with the ASCII Console Interface"
::= { mscAtmIfUniRowStatusEntry 2 }

mscAtmIfUniStorageType OBJECT-TYPE
   SYNTAX     StorageType 
   ACCESS     read-only
   STATUS     mandatory
   DESCRIPTION
     "This variable represents the storage type value for the
      mscAtmIfUni tables."
::= { mscAtmIfUniRowStatusEntry 4 }

mscAtmIfUniIndex OBJECT-TYPE
   SYNTAX     NonReplicated 
   ACCESS     not-accessible
   STATUS     mandatory
   DESCRIPTION
     "This variable represents the index for the mscAtmIfUni tables."
::= { mscAtmIfUniRowStatusEntry 10 }

mscAtmIfUniProvTable OBJECT-TYPE
   SYNTAX     SEQUENCE OF MscAtmIfUniProvEntry
   ACCESS     not-accessible
   STATUS     mandatory
   DESCRIPTION
     "This group contains the provisionable attributes for the Uni 
      component."
::= { mscAtmIfUni 10 }

mscAtmIfUniProvEntry OBJECT-TYPE
   SYNTAX     MscAtmIfUniProvEntry
   ACCESS     not-accessible
   STATUS     mandatory
   DESCRIPTION
     "An entry in the mscAtmIfUniProvTable."
   INDEX {
      mscAtmIfIndex,
      mscAtmIfUniIndex }
::= { mscAtmIfUniProvTable 1 }

MscAtmIfUniProvEntry ::= SEQUENCE {
   mscAtmIfUniVersion
      INTEGER,
   mscAtmIfUniSide
      INTEGER,
   mscAtmIfUniSoftPvcRetryPeriod
      Unsigned32,
   mscAtmIfUniSoftPvpAndPvcRetryPeriod
      Unsigned32,
   mscAtmIfUniSoftPvpAndPvcHoldOffTime
      Unsigned32,
   mscAtmIfUniLoopPrevention
      INTEGER }

mscAtmIfUniVersion OBJECT-TYPE
   SYNTAX     INTEGER  {
                 atmForum30(0),
                 atmForum31(1),
                 atmForum40(5) }
   ACCESS     read-write
   STATUS     mandatory
   DESCRIPTION
     "This attribute specifies which specification the UNI complies with. 
      The options are ATM FORUM 3.0, ATM FORUM 3.1 or ATM 
      FORUM 4.0. If this attribute is changed then all switched Vcc 
      components in this interface are cleared due to the fact that the two 
      versions are incompatible."
   DEFVAL     { atmForum40 }
::= { mscAtmIfUniProvEntry 1 }

mscAtmIfUniSide OBJECT-TYPE
   SYNTAX     INTEGER  {
                 network(0),
                 user(1) }
   ACCESS     read-write
   STATUS     mandatory
   DESCRIPTION
     "This attribute indicates which side the interface is, user or network."
   DEFVAL     { network }
::= { mscAtmIfUniProvEntry 2 }

mscAtmIfUniSoftPvcRetryPeriod OBJECT-TYPE
   SYNTAX     Unsigned32 (20..999999)
   ACCESS     read-write
   STATUS     obsolete
   DESCRIPTION
     "This attribute represents the time in seconds to wait between call set 
      up retries. The resolution is to the nearest 10 seconds. 
      This attribute has been obsoleted and is replaced by the 
      softPvpAndPvcRetryPeriod attribute."
   DEFVAL     { 60 }
::= { mscAtmIfUniProvEntry 3 }

mscAtmIfUniSoftPvpAndPvcRetryPeriod OBJECT-TYPE
   SYNTAX     Unsigned32 (20..999999)
   ACCESS     read-write
   STATUS     mandatory
   DESCRIPTION
     "This attribute represents the time in seconds to wait between soft 
      PVP or soft PVC call setup retries. The resolution is to the nearest 
      10 seconds."
   DEFVAL     { 60 }
::= { mscAtmIfUniProvEntry 4 }

mscAtmIfUniSoftPvpAndPvcHoldOffTime OBJECT-TYPE
   SYNTAX     Unsigned32 (0 | 50..20000)
   ACCESS     read-write
   STATUS     mandatory
   DESCRIPTION
     "This attribute specifies how long to hold off retries following a 
      release or the connection. The resolution is to the nearest 50 ms."
   DEFVAL     { 0 }
::= { mscAtmIfUniProvEntry 5 }

mscAtmIfUniLoopPrevention OBJECT-TYPE
   SYNTAX     INTEGER  {
                 disabled(0),
                 enabled(1) }
   ACCESS     read-write
   STATUS     mandatory
   DESCRIPTION
     "This attribute specifies whether loop prevention is in effect on this 
      interface.
      
      When the value is enabled, incoming calls on this interface cannot 
      be routed back out the same interface.  When the value is disabled, 
      routing of incoming calls back out the same interface is permitted.
      
      The recommended value is enabled.  The value disabled should 
      only be used if routing of incoming calls back out over this interface 
      is actually required.  As an example, the value disabled might be 
      needed if the interface is connected to an end-user multiplexing 
      device which has no routing capability.
      
      Note that setting the value to enabled prevents only routing loops 
      which involve two network nodes."
   DEFVAL     { enabled }
::= { mscAtmIfUniProvEntry 6 }

mscAtmIfUniOperTable OBJECT-TYPE
   SYNTAX     SEQUENCE OF MscAtmIfUniOperEntry
   ACCESS     not-accessible
   STATUS     mandatory
   DESCRIPTION
     "This attribute group contains the operational attributes for the Uni 
      component."
::= { mscAtmIfUni 11 }

mscAtmIfUniOperEntry OBJECT-TYPE
   SYNTAX     MscAtmIfUniOperEntry
   ACCESS     not-accessible
   STATUS     mandatory
   DESCRIPTION
     "An entry in the mscAtmIfUniOperTable."
   INDEX {
      mscAtmIfIndex,
      mscAtmIfUniIndex }
::= { mscAtmIfUniOperTable 1 }

MscAtmIfUniOperEntry ::= SEQUENCE {
   mscAtmIfUniMacAddress
      AsciiString }

mscAtmIfUniMacAddress OBJECT-TYPE
   SYNTAX     AsciiString (SIZE (12))
   ACCESS     read-only
   STATUS     mandatory
   DESCRIPTION
     "This attribute indicates the MAC address of the port, which is used 
      for address registration of the user side as the default ESI."
::= { mscAtmIfUniOperEntry 1 }

mscAtmIfUniAcctOptTable OBJECT-TYPE
   SYNTAX     SEQUENCE OF MscAtmIfUniAcctOptEntry
   ACCESS     not-accessible
   STATUS     mandatory
   DESCRIPTION
     "This group contains the provisionable attributes for accounting."
::= { mscAtmIfUni 12 }

mscAtmIfUniAcctOptEntry OBJECT-TYPE
   SYNTAX     MscAtmIfUniAcctOptEntry
   ACCESS     not-accessible
   STATUS     mandatory
   DESCRIPTION
     "An entry in the mscAtmIfUniAcctOptTable."
   INDEX {
      mscAtmIfIndex,
      mscAtmIfUniIndex }
::= { mscAtmIfUniAcctOptTable 1 }

MscAtmIfUniAcctOptEntry ::= SEQUENCE {
   mscAtmIfUniAccountCollection
      OCTET STRING,
   mscAtmIfUniAccountConnectionType
      INTEGER,
   mscAtmIfUniAccountClass
      Unsigned32,
   mscAtmIfUniServiceExchange
      Unsigned32 }

mscAtmIfUniAccountCollection OBJECT-TYPE
   SYNTAX     OCTET STRING (SIZE (1))
   ACCESS     read-write
   STATUS     mandatory
   DESCRIPTION
     "This attribute is used to turn accounting on or off for SVC and 
      SPVC connections. It also specifies the reason(s) for which 
      accounting data is collected: billing, test, study, audit or force. 
      
      If the set of reasons is not empty then accounting records will be 
      generated by this interface in the following situations:
      - on a TODA changeover if TODA is enabled;
      - every 12 hours (per connection) if TODA is disabled;
      - on every call clear (a call record with final cell counts).
      
      If none of the reasons is present, then accounting will be 
      suppressed.
      
      The reason for collection is recorded in the accounting record, in 
      the attribute callingCollectReason or calledCollectReason as 
      appropriate.

      Description of bits:
      bill(0)
      test(1)
      study(2)
      audit(3)
      force(4)"
::= { mscAtmIfUniAcctOptEntry 1 }

mscAtmIfUniAccountConnectionType OBJECT-TYPE
   SYNTAX     INTEGER  {
                 origTerm(0),
                 intermediate(1) }
   ACCESS     read-write
   STATUS     mandatory
   DESCRIPTION
     "This attribute specifies whether accounting records generated by 
      this interface should be marked as originating, terminating or 
      intermediate. This attribute, in combination with the direction of the 
      call, determines the value of attribute connPointType of the 
      accounting record and may be used by downstream accounting 
      processes to correlate the records.
      
      If the value is origTerm then records generated for incoming calls 
      will be marked as originating and records generated for outgoing 
      calls will be marked as terminating.
      
      If the value is intermediate then records generated for all calls will 
      be marked as intermediate."
   DEFVAL     { origTerm }
::= { mscAtmIfUniAcctOptEntry 2 }

mscAtmIfUniAccountClass OBJECT-TYPE
   SYNTAX     Unsigned32 (0..255)
   ACCESS     read-write
   STATUS     mandatory
   DESCRIPTION
     "This attribute specifies the accounting class associated with the 
      interface. Its meaning is determined by the network operator.
      
      Its value is simply recorded in the accounting records generated by 
      this interface, in the attribute callingServiceType or 
      calledServiceType as appropriate."
   DEFVAL     { 0 }
::= { mscAtmIfUniAcctOptEntry 3 }

mscAtmIfUniServiceExchange OBJECT-TYPE
   SYNTAX     Unsigned32 (0..255)
   ACCESS     read-write
   STATUS     mandatory
   DESCRIPTION
     "This attribute specifies the data service exchange associated with 
      this interface. Its meaning is determined by the network operator.
      
      Its value is simply recorded in the accounting records generated by 
      this interface, in the attribute callingDse or calledDse as 
      appropriate."
   DEFVAL     { 0 }
::= { mscAtmIfUniAcctOptEntry 4 }


-- AtmIf/n Uni Ilmi
-- This component represents the Interim Local Management Interface 
-- (ILMI) protocol on the interface.

mscAtmIfUniIlmi OBJECT IDENTIFIER ::= { mscAtmIfUni 2 }



mscAtmIfUniIlmiRowStatusTable OBJECT-TYPE
   SYNTAX     SEQUENCE OF MscAtmIfUniIlmiRowStatusEntry
   ACCESS     not-accessible
   STATUS     mandatory
   DESCRIPTION
     "This entry controls the addition and deletion of 
      mscAtmIfUniIlmi components."
::= { mscAtmIfUniIlmi 1 }

mscAtmIfUniIlmiRowStatusEntry OBJECT-TYPE
   SYNTAX     MscAtmIfUniIlmiRowStatusEntry
   ACCESS     not-accessible
   STATUS     mandatory
   DESCRIPTION
     "A single entry in the table represents a single 
      mscAtmIfUniIlmi component."
   INDEX {
      mscAtmIfIndex,
      mscAtmIfUniIndex,
      mscAtmIfUniIlmiIndex }
::= { mscAtmIfUniIlmiRowStatusTable 1 }

MscAtmIfUniIlmiRowStatusEntry ::= SEQUENCE {
   mscAtmIfUniIlmiRowStatus
      RowStatus,
   mscAtmIfUniIlmiComponentName
      DisplayString,
   mscAtmIfUniIlmiStorageType
      StorageType,
   mscAtmIfUniIlmiIndex
      NonReplicated }

mscAtmIfUniIlmiRowStatus OBJECT-TYPE
   SYNTAX     RowStatus 
   ACCESS     read-only
   STATUS     mandatory
   DESCRIPTION
     "This variable is used as the basis for SNMP naming of
      mscAtmIfUniIlmi components.
      These components cannot be added nor deleted."
::= { mscAtmIfUniIlmiRowStatusEntry 1 }

mscAtmIfUniIlmiComponentName OBJECT-TYPE
   SYNTAX     DisplayString 
   ACCESS     read-only
   STATUS     mandatory
   DESCRIPTION
     "This variable provides the component's string name for
      use with the ASCII Console Interface"
::= { mscAtmIfUniIlmiRowStatusEntry 2 }

mscAtmIfUniIlmiStorageType OBJECT-TYPE
   SYNTAX     StorageType 
   ACCESS     read-only
   STATUS     mandatory
   DESCRIPTION
     "This variable represents the storage type value for the
      mscAtmIfUniIlmi tables."
::= { mscAtmIfUniIlmiRowStatusEntry 4 }

mscAtmIfUniIlmiIndex OBJECT-TYPE
   SYNTAX     NonReplicated 
   ACCESS     not-accessible
   STATUS     mandatory
   DESCRIPTION
     "This variable represents the index for the mscAtmIfUniIlmi tables."
::= { mscAtmIfUniIlmiRowStatusEntry 10 }

mscAtmIfUniIlmiStateTable OBJECT-TYPE
   SYNTAX     SEQUENCE OF MscAtmIfUniIlmiStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscAtmIfUniIlmi 10 }

mscAtmIfUniIlmiStateEntry OBJECT-TYPE
   SYNTAX     MscAtmIfUniIlmiStateEntry
   ACCESS     not-accessible
   STATUS     mandatory
   DESCRIPTION
     "An entry in the mscAtmIfUniIlmiStateTable."
   INDEX {
      mscAtmIfIndex,
      mscAtmIfUniIndex,
      mscAtmIfUniIlmiIndex }
::= { mscAtmIfUniIlmiStateTable 1 }

MscAtmIfUniIlmiStateEntry ::= SEQUENCE {
   mscAtmIfUniIlmiAdminState
      INTEGER,
   mscAtmIfUniIlmiOperationalState
      INTEGER,
   mscAtmIfUniIlmiUsageState
      INTEGER }

mscAtmIfUniIlmiAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscAtmIfUniIlmiStateEntry 1 }

mscAtmIfUniIlmiOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscAtmIfUniIlmiStateEntry 2 }

mscAtmIfUniIlmiUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscAtmIfUniIlmiStateEntry 3 }

mscAtmIfUniIlmiProvTable OBJECT-TYPE
   SYNTAX     SEQUENCE OF MscAtmIfUniIlmiProvEntry
   ACCESS     not-accessible
   STATUS     mandatory
   DESCRIPTION
     "This attribute group contains the provisionable attributes for the Ilmi 
      component."
::= { mscAtmIfUniIlmi 11 }

mscAtmIfUniIlmiProvEntry OBJECT-TYPE
   SYNTAX     MscAtmIfUniIlmiProvEntry
   ACCESS     not-accessible
   STATUS     mandatory
   DESCRIPTION
     "An entry in the mscAtmIfUniIlmiProvTable."
   INDEX {
      mscAtmIfIndex,
      mscAtmIfUniIndex,
      mscAtmIfUniIlmiIndex }
::= { mscAtmIfUniIlmiProvTable 1 }

MscAtmIfUniIlmiProvEntry ::= SEQUENCE {
   mscAtmIfUniIlmiVci
      Unsigned32,
   mscAtmIfUniIlmiOperatingMode
      INTEGER }

mscAtmIfUniIlmiVci OBJECT-TYPE
   SYNTAX     Unsigned32 (0..65535)
   ACCESS     read-write
   STATUS     mandatory
   DESCRIPTION
     "This attribute identifies the ILMI channel number."
   DEFVAL     { 16 }
::= { mscAtmIfUniIlmiProvEntry 1 }

mscAtmIfUniIlmiOperatingMode OBJECT-TYPE
   SYNTAX     INTEGER  {
                 addressRegEnabled(0),
                 addressRegDisabled(1),
                 ilmiDisabled(2) }
   ACCESS     read-write
   STATUS     mandatory
   DESCRIPTION
     "This attribute is used to enable/disable the ILMI protocol. 
      addressRegEnabled indicates that the ILMI address registration 
      protocol is enabled. addressRegDisabled indicates that the ILMI 
      address registration protocol is disabled. ilmiDisabled indicates that 
      all of ILMI is disabled."
   DEFVAL     { addressRegEnabled }
::= { mscAtmIfUniIlmiProvEntry 2 }

mscAtmIfUniIlmiStatsTable OBJECT-TYPE
   SYNTAX     SEQUENCE OF MscAtmIfUniIlmiStatsEntry
   ACCESS     not-accessible
   STATUS     mandatory
   DESCRIPTION
     "This attribute group contains the statistics for the AtmIlmi 
      component."
::= { mscAtmIfUniIlmi 12 }

mscAtmIfUniIlmiStatsEntry OBJECT-TYPE
   SYNTAX     MscAtmIfUniIlmiStatsEntry
   ACCESS     not-accessible
   STATUS     mandatory
   DESCRIPTION
     "An entry in the mscAtmIfUniIlmiStatsTable."
   INDEX {
      mscAtmIfIndex,
      mscAtmIfUniIndex,
      mscAtmIfUniIlmiIndex }
::= { mscAtmIfUniIlmiStatsTable 1 }

MscAtmIfUniIlmiStatsEntry ::= SEQUENCE {
   mscAtmIfUniIlmiTxPdus
      Counter32,
   mscAtmIfUniIlmiRxPdus
      Counter32,
   mscAtmIfUniIlmiRxBadPdusDiscarded
      Counter32 }

mscAtmIfUniIlmiTxPdus OBJECT-TYPE
   SYNTAX     Counter32 
   ACCESS     read-only
   STATUS     mandatory
   DESCRIPTION
     "This attribute counts the number of transmitted ILMI PDUs. The 
      counter wraps to 0 when the maximum value is exceeded."
::= { mscAtmIfUniIlmiStatsEntry 1 }

mscAtmIfUniIlmiRxPdus OBJECT-TYPE
   SYNTAX     Counter32 
   ACCESS     read-only
   STATUS     mandatory
   DESCRIPTION
     "This attribute counts the total number of received ILMI PDUs.The 
      counter wraps to 0 when the maximum value is exceeded."
::= { mscAtmIfUniIlmiStatsEntry 2 }

mscAtmIfUniIlmiRxBadPdusDiscarded OBJECT-TYPE
   SYNTAX     Counter32 
   ACCESS     read-only
   STATUS     mandatory
   DESCRIPTION
     "This attribute counts the number of received ILMI PDUs that were 
      discarded due to invalid SNMP format. The counter wraps to 0 
      when the maximum value is exceeded."
::= { mscAtmIfUniIlmiStatsEntry 3 }

mscAtmIfUniIlmiPrefixToRegisterTable OBJECT-TYPE
   SYNTAX     SEQUENCE OF MscAtmIfUniIlmiPrefixToRegisterEntry
   ACCESS     not-accessible
   STATUS     mandatory
   DESCRIPTION
     "This attribute is a list of zero or more addresses. If the side attribute 
      in the Uni component is set to user, then this attribute must be 
      empty; if the side attribute is set to network, then this attribute is a 
      list of prefixes.This attribute represents a list of prefix addresses (26 
      digits) that are sent to the user side. If no prefixes are entered, then 
      the nodeAddress attribute in the AtmCallRouter component is used 
      for address registration."
::= { mscAtmIfUniIlmi 287 }

mscAtmIfUniIlmiPrefixToRegisterEntry OBJECT-TYPE
   SYNTAX     MscAtmIfUniIlmiPrefixToRegisterEntry
   ACCESS     not-accessible
   STATUS     mandatory
   DESCRIPTION
     "An entry in the mscAtmIfUniIlmiPrefixToRegisterTable."
   INDEX {
      mscAtmIfIndex,
      mscAtmIfUniIndex,
      mscAtmIfUniIlmiIndex,
      mscAtmIfUniIlmiPrefixToRegisterValue }
::= { mscAtmIfUniIlmiPrefixToRegisterTable 1 }

MscAtmIfUniIlmiPrefixToRegisterEntry ::= SEQUENCE {
   mscAtmIfUniIlmiPrefixToRegisterValue
      AsciiString,
   mscAtmIfUniIlmiPrefixToRegisterRowStatus
      RowStatus }

mscAtmIfUniIlmiPrefixToRegisterValue OBJECT-TYPE
   SYNTAX     AsciiString (SIZE (26))
   ACCESS     read-write
   STATUS     mandatory
   DESCRIPTION
     "This variable represents both the value and the index for the
      mscAtmIfUniIlmiPrefixToRegisterTable."
::= { mscAtmIfUniIlmiPrefixToRegisterEntry 1 }

mscAtmIfUniIlmiPrefixToRegisterRowStatus OBJECT-TYPE
   SYNTAX     RowStatus 
   ACCESS     write-only
   STATUS     mandatory
   DESCRIPTION
     "This variable is used to control the addition and deletion 
      of individual values of the mscAtmIfUniIlmiPrefixToRegisterTable."
::= { mscAtmIfUniIlmiPrefixToRegisterEntry 2 }

mscAtmIfUniIlmiEsiToRegisterTable OBJECT-TYPE
   SYNTAX     SEQUENCE OF MscAtmIfUniIlmiEsiToRegisterEntry
   ACCESS     not-accessible
   STATUS     mandatory
   DESCRIPTION
     "This attribute is a list of zero or more addresses. If the side attribute 
      in the Uni component is set to network, then this attribute must be 
      an empty list; if the side attribute is set to user, then this attribute is 
      a list of end system indicators (ESI) addresses (12 hex digits) that 
      are used to compose addresses to register with the network side."
::= { mscAtmIfUniIlmi 288 }

mscAtmIfUniIlmiEsiToRegisterEntry OBJECT-TYPE
   SYNTAX     MscAtmIfUniIlmiEsiToRegisterEntry
   ACCESS     not-accessible
   STATUS     mandatory
   DESCRIPTION
     "An entry in the mscAtmIfUniIlmiEsiToRegisterTable."
   INDEX {
      mscAtmIfIndex,
      mscAtmIfUniIndex,
      mscAtmIfUniIlmiIndex,
      mscAtmIfUniIlmiEsiToRegisterValue }
::= { mscAtmIfUniIlmiEsiToRegisterTable 1 }

MscAtmIfUniIlmiEsiToRegisterEntry ::= SEQUENCE {
   mscAtmIfUniIlmiEsiToRegisterValue
      AsciiString,
   mscAtmIfUniIlmiEsiToRegisterRowStatus
      RowStatus }

mscAtmIfUniIlmiEsiToRegisterValue OBJECT-TYPE
   SYNTAX     AsciiString (SIZE (12))
   ACCESS     read-write
   STATUS     mandatory
   DESCRIPTION
     "This variable represents both the value and the index for the
      mscAtmIfUniIlmiEsiToRegisterTable."
::= { mscAtmIfUniIlmiEsiToRegisterEntry 1 }

mscAtmIfUniIlmiEsiToRegisterRowStatus OBJECT-TYPE
   SYNTAX     RowStatus 
   ACCESS     write-only
   STATUS     mandatory
   DESCRIPTION
     "This variable is used to control the addition and deletion 
      of individual values of the mscAtmIfUniIlmiEsiToRegisterTable."
::= { mscAtmIfUniIlmiEsiToRegisterEntry 2 }


-- AtmIf/n Iisp Signalling
-- AtmIf/n Uni Signalling
-- AtmIf/n Pnni Signalling
-- AtmIf/n Vpt/m Iisp Signalling
-- AtmIf/n Vpt/m Uni Signalling
-- AtmIf/n Vpt/m Pnni Signalling
-- 
-- This component represents the signalling entities for the interface.

mscAtmIfUniSig OBJECT IDENTIFIER ::= { mscAtmIfUni 3 }



mscAtmIfUniSigRowStatusTable OBJECT-TYPE
   SYNTAX     SEQUENCE OF MscAtmIfUniSigRowStatusEntry
   ACCESS     not-accessible
   STATUS     mandatory
   DESCRIPTION
     "This entry controls the addition and deletion of 
      mscAtmIfUniSig components."
::= { mscAtmIfUniSig 1 }

mscAtmIfUniSigRowStatusEntry OBJECT-TYPE
   SYNTAX     MscAtmIfUniSigRowStatusEntry
   ACCESS     not-accessible
   STATUS     mandatory
   DESCRIPTION
     "A single entry in the table represents a single 
      mscAtmIfUniSig component."
   INDEX {
      mscAtmIfIndex,
      mscAtmIfUniIndex,
      mscAtmIfUniSigIndex }
::= { mscAtmIfUniSigRowStatusTable 1 }

MscAtmIfUniSigRowStatusEntry ::= SEQUENCE {
   mscAtmIfUniSigRowStatus
      RowStatus,
   mscAtmIfUniSigComponentName
      DisplayString,
   mscAtmIfUniSigStorageType
      StorageType,
   mscAtmIfUniSigIndex
      NonReplicated }

mscAtmIfUniSigRowStatus OBJECT-TYPE
   SYNTAX     RowStatus 
   ACCESS     read-only
   STATUS     mandatory
   DESCRIPTION
     "This variable is used as the basis for SNMP naming of
      mscAtmIfUniSig components.
      These components cannot be added nor deleted."
::= { mscAtmIfUniSigRowStatusEntry 1 }

mscAtmIfUniSigComponentName OBJECT-TYPE
   SYNTAX     DisplayString 
   ACCESS     read-only
   STATUS     mandatory
   DESCRIPTION
     "This variable provides the component's string name for
      use with the ASCII Console Interface"
::= { mscAtmIfUniSigRowStatusEntry 2 }

mscAtmIfUniSigStorageType OBJECT-TYPE
   SYNTAX     StorageType 
   ACCESS     read-only
   STATUS     mandatory
   DESCRIPTION
     "This variable represents the storage type value for the
      mscAtmIfUniSig tables."
::= { mscAtmIfUniSigRowStatusEntry 4 }

mscAtmIfUniSigIndex OBJECT-TYPE
   SYNTAX     NonReplicated 
   ACCESS     not-accessible
   STATUS     mandatory
   DESCRIPTION
     "This variable represents the index for the mscAtmIfUniSig tables."
::= { mscAtmIfUniSigRowStatusEntry 10 }

mscAtmIfUniSigProvTable OBJECT-TYPE
   SYNTAX     SEQUENCE OF MscAtmIfUniSigProvEntry
   ACCESS     not-accessible
   STATUS     mandatory
   DESCRIPTION
     "This attribute group contains the provisionable attributes for the 
      Signalling component."
::= { mscAtmIfUniSig 10 }

mscAtmIfUniSigProvEntry OBJECT-TYPE
   SYNTAX     MscAtmIfUniSigProvEntry
   ACCESS     not-accessible
   STATUS     mandatory
   DESCRIPTION
     "An entry in the mscAtmIfUniSigProvTable."
   INDEX {
      mscAtmIfIndex,
      mscAtmIfUniIndex,
      mscAtmIfUniSigIndex }
::= { mscAtmIfUniSigProvTable 1 }

MscAtmIfUniSigProvEntry ::= SEQUENCE {
   mscAtmIfUniSigVci
      Unsigned32,
   mscAtmIfUniSigAddressConversion
      INTEGER,
   mscAtmIfUniSigOperatingMode
      INTEGER }

mscAtmIfUniSigVci OBJECT-TYPE
   SYNTAX     Unsigned32 (0..65535)
   ACCESS     read-write
   STATUS     mandatory
   DESCRIPTION
     "This attribute specifies the signalling channel number."
   DEFVAL     { 5 }
::= { mscAtmIfUniSigProvEntry 1 }

mscAtmIfUniSigAddressConversion OBJECT-TYPE
   SYNTAX     INTEGER  {
                 none(0),
                 nativeE164(1),
                 nsap(2) }
   ACCESS     read-write
   STATUS     mandatory
   DESCRIPTION
     "This attribute specifies the address conversion on the outgoing 
      signalling PDUs. The options are none, nativeE164, or nsap. The 
      none option is the default and if this option is chosen then nothing 
      is done to the address information element (IE) in the outgoing 
      signalling message. If nativeE164 option is chosen, then only 
      NSAP encapsulated E.164 addresses with zeros in the ESI are 
      converted to native E.164 format in the outgoing signalling 
      message. If the NSAP address is not encapsulated E.164 or the ESI 
      field is not zeros and the nativeE164 option is chosen, then the call 
      is cleared. If the nsap option is chosen, then native E.164 addresses 
      are converted to NSAP E.164 with zeros in the ESI field; otherwise 
      the address is in NSAP format and is not changed."
   DEFVAL     { none }
::= { mscAtmIfUniSigProvEntry 2 }

mscAtmIfUniSigOperatingMode OBJECT-TYPE
   SYNTAX     INTEGER  {
                 normal(0),
                 provisionedOnly(1) }
   ACCESS     read-write
   STATUS     mandatory
   DESCRIPTION
     "This attribute specifies the operating mode of the signaling channel. 				
      provisionedOnly indicates that only SPVCs and SPVPs are 
      supported on the interface and SVCs are not supported. This value 
      is permitted only on UNI interfaces.
      normal indicates that SVCs, SPVCs, and SPVPs are supported on 
      the interface."
   DEFVAL     { normal }
::= { mscAtmIfUniSigProvEntry 3 }

mscAtmIfUniSigStateTable OBJECT-TYPE
   SYNTAX     SEQUENCE OF MscAtmIfUniSigStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscAtmIfUniSig 11 }

mscAtmIfUniSigStateEntry OBJECT-TYPE
   SYNTAX     MscAtmIfUniSigStateEntry
   ACCESS     not-accessible
   STATUS     mandatory
   DESCRIPTION
     "An entry in the mscAtmIfUniSigStateTable."
   INDEX {
      mscAtmIfIndex,
      mscAtmIfUniIndex,
      mscAtmIfUniSigIndex }
::= { mscAtmIfUniSigStateTable 1 }

MscAtmIfUniSigStateEntry ::= SEQUENCE {
   mscAtmIfUniSigAdminState
      INTEGER,
   mscAtmIfUniSigOperationalState
      INTEGER,
   mscAtmIfUniSigUsageState
      INTEGER }

mscAtmIfUniSigAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscAtmIfUniSigStateEntry 1 }

mscAtmIfUniSigOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscAtmIfUniSigStateEntry 2 }

mscAtmIfUniSigUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscAtmIfUniSigStateEntry 3 }

mscAtmIfUniSigOperTable OBJECT-TYPE
   SYNTAX     SEQUENCE OF MscAtmIfUniSigOperEntry
   ACCESS     not-accessible
   STATUS     mandatory
   DESCRIPTION
     "This attribute contains the operational attributes for the 
      AtmSignalling component."
::= { mscAtmIfUniSig 12 }

mscAtmIfUniSigOperEntry OBJECT-TYPE
   SYNTAX     MscAtmIfUniSigOperEntry
   ACCESS     not-accessible
   STATUS     mandatory
   DESCRIPTION
     "An entry in the mscAtmIfUniSigOperTable."
   INDEX {
      mscAtmIfIndex,
      mscAtmIfUniIndex,
      mscAtmIfUniSigIndex }
::= { mscAtmIfUniSigOperTable 1 }

MscAtmIfUniSigOperEntry ::= SEQUENCE {
   mscAtmIfUniSigLastTxCauseCode
      Unsigned32,
   mscAtmIfUniSigLastTxDiagCode
      Hex,
   mscAtmIfUniSigLastRxCauseCode
      Unsigned32,
   mscAtmIfUniSigLastRxDiagCode
      Hex }

mscAtmIfUniSigLastTxCauseCode OBJECT-TYPE
   SYNTAX     Unsigned32 (0..255)
   ACCESS     read-only
   STATUS     mandatory
   DESCRIPTION
     "This attribute indicates the cause code in the last transmitted 
      signalling message that contains the CAUSE information element. 
      The cause code is used to describe the reason for generating certain 
      signalling messages."
::= { mscAtmIfUniSigOperEntry 1 }

mscAtmIfUniSigLastTxDiagCode OBJECT-TYPE
   SYNTAX     Hex (0..255)
   ACCESS     read-only
   STATUS     mandatory
   DESCRIPTION
     "This attribute contains the diagnostic code in the last transmitted 
      signalling message. The diagnostic code is contained in the CAUSE 
      information element and identifies an information element type or 
      timer type. The diagnostic code is present only if a procedural error 
      is detected by the signalling protocol. A diagnostic code is always 
      accompanied by the cause code. If there is no failure, this attribute 
      is set to 0."
::= { mscAtmIfUniSigOperEntry 2 }

mscAtmIfUniSigLastRxCauseCode OBJECT-TYPE
   SYNTAX     Unsigned32 (0..255)
   ACCESS     read-only
   STATUS     mandatory
   DESCRIPTION
     "This attribute contains the cause code in the last received signalling 
      message that contains the CAUSE information element. The cause 
      code is used to describe the reason for generating certain signalling 
      messages."
::= { mscAtmIfUniSigOperEntry 3 }

mscAtmIfUniSigLastRxDiagCode OBJECT-TYPE
   SYNTAX     Hex (0..255)
   ACCESS     read-only
   STATUS     mandatory
   DESCRIPTION
     "This attribute contains the diagnostic code in the last received 
      signalling message. The diagnostic code is contained in the CAUSE 
      information element and identifies an information element type or 
      timer type. The diagnostic code is present only if a procedural error 
      is detected by the signalling protocol. A diagnostic code is always 
      accompanied by the cause code. If there is no failure, this attribute 
      is set to 0."
::= { mscAtmIfUniSigOperEntry 4 }

mscAtmIfUniSigStatsTable OBJECT-TYPE
   SYNTAX     SEQUENCE OF MscAtmIfUniSigStatsEntry
   ACCESS     not-accessible
   STATUS     mandatory
   DESCRIPTION
     "This attribute group contains the statistics associated with the 
      AtmSignalling component."
::= { mscAtmIfUniSig 13 }

mscAtmIfUniSigStatsEntry OBJECT-TYPE
   SYNTAX     MscAtmIfUniSigStatsEntry
   ACCESS     not-accessible
   STATUS     mandatory
   DESCRIPTION
     "An entry in the mscAtmIfUniSigStatsTable."
   INDEX {
      mscAtmIfIndex,
      mscAtmIfUniIndex,
      mscAtmIfUniSigIndex }
::= { mscAtmIfUniSigStatsTable 1 }

MscAtmIfUniSigStatsEntry ::= SEQUENCE {
   mscAtmIfUniSigCurrentConnections
      Counter32,
   mscAtmIfUniSigPeakConnections
      Gauge32,
   mscAtmIfUniSigSuccessfulConnections
      Counter32,
   mscAtmIfUniSigFailedConnections
      Counter32,
   mscAtmIfUniSigTxPdus
      Counter32,
   mscAtmIfUniSigRxPdus
      Counter32,
   mscAtmIfUniSigCurrentPmpConnections
      Gauge32,
   mscAtmIfUniSigPeakPmpConnections
      Gauge32,
   mscAtmIfUniSigSuccessfulPmpConnections
      Counter32,
   mscAtmIfUniSigFailedPmpConnections
      Counter32,
   mscAtmIfUniSigNewCurrentConnections
      Gauge32 }

mscAtmIfUniSigCurrentConnections OBJECT-TYPE
   SYNTAX     Counter32 
   ACCESS     read-only
   STATUS     obsolete
   DESCRIPTION
     "This attribute indicates the total number of currently active 
      connections."
::= { mscAtmIfUniSigStatsEntry 1 }

mscAtmIfUniSigPeakConnections OBJECT-TYPE
   SYNTAX     Gauge32 (0..4294967295)
   ACCESS     read-only
   STATUS     mandatory
   DESCRIPTION
     "This attribute indicates the high water mark of active point-to-
      point and point-to-multipoint connections."
::= { mscAtmIfUniSigStatsEntry 2 }

mscAtmIfUniSigSuccessfulConnections OBJECT-TYPE
   SYNTAX     Counter32 
   ACCESS     read-only
   STATUS     mandatory
   DESCRIPTION
     "This attribute counts the total number of switched point-to-
      point and point-to-multipoint connections that were successfully 
      established. The counter wraps to 0 when the maximum value is 
      exceeded."
::= { mscAtmIfUniSigStatsEntry 3 }

mscAtmIfUniSigFailedConnections OBJECT-TYPE
   SYNTAX     Counter32 
   ACCESS     read-only
   STATUS     mandatory
   DESCRIPTION
     "This attribute counts the total number of switched connections that 
      were not successfully established.The counter wraps to 0 when the 
      maximum value is exceeded."
::= { mscAtmIfUniSigStatsEntry 4 }

mscAtmIfUniSigTxPdus OBJECT-TYPE
   SYNTAX     Counter32 
   ACCESS     read-only
   STATUS     mandatory
   DESCRIPTION
     "This attribute counts the number of transmitted signalling 
      PDUs.The counter wraps to 0 when the maximum value is 
      exceeded."
::= { mscAtmIfUniSigStatsEntry 5 }

mscAtmIfUniSigRxPdus OBJECT-TYPE
   SYNTAX     Counter32 
   ACCESS     read-only
   STATUS     mandatory
   DESCRIPTION
     "This attribute counts the number of received signalling PDUs.The 
      counter wraps to 0 when the maximum value is exceeded."
::= { mscAtmIfUniSigStatsEntry 6 }

mscAtmIfUniSigCurrentPmpConnections OBJECT-TYPE
   SYNTAX     Gauge32 (0..4294967295)
   ACCESS     read-only
   STATUS     mandatory
   DESCRIPTION
     "This attribute indicates the number of currently active point-to-
      multipoint connections."
::= { mscAtmIfUniSigStatsEntry 7 }

mscAtmIfUniSigPeakPmpConnections OBJECT-TYPE
   SYNTAX     Gauge32 (0..4294967295)
   ACCESS     read-only
   STATUS     mandatory
   DESCRIPTION
     "This attribute indicates the high water mark of active point-to-
      multipoint connections."
::= { mscAtmIfUniSigStatsEntry 8 }

mscAtmIfUniSigSuccessfulPmpConnections OBJECT-TYPE
   SYNTAX     Counter32 
   ACCESS     read-only
   STATUS     mandatory
   DESCRIPTION
     "This attribute counts the total number of switched point-to-
      multipoint connections that were successfully established. 
      The counter wraps to 0 when the maximum value is 
      exceeded."
::= { mscAtmIfUniSigStatsEntry 9 }

mscAtmIfUniSigFailedPmpConnections OBJECT-TYPE
   SYNTAX     Counter32 
   ACCESS     read-only
   STATUS     mandatory
   DESCRIPTION
     "This attribute counts the number of switched point-to-
      multipoint connections that were not successfully 
      established.The counter wraps to 0 when the maximum value 
      is exceeded."
::= { mscAtmIfUniSigStatsEntry 10 }

mscAtmIfUniSigNewCurrentConnections OBJECT-TYPE
   SYNTAX     Gauge32 (0..4294967295)
   ACCESS     read-only
   STATUS     mandatory
   DESCRIPTION
     "This attribute indicates the total number of currently active point-to-
      point and point-to-multipoint connections."
::= { mscAtmIfUniSigStatsEntry 11 }


-- AtmIf/n Uni Sig VirtualChannelDescriptor
-- AtmIf/n Uni Ilmi VirtualChannelDescriptor
-- AtmIf/n Iisp Sig VirtualChannelDescriptor
-- AtmIf/n Pnni Sig VirtualChannelDescriptor
-- AtmIf/n Pnni Rcc VirtualChannelDescriptor
-- AtmIf/n Vpt/m Uni Sig VirtualChannelDescriptor
-- AtmIf/n Vpt/m Iisp Sig VirtualChannelDescriptor
-- AtmIf/n Vpt/m Pnni Sig VirtualChannelDescriptor
-- AtmIf/n Vpt/m Pnni Rcc VirtualChannelDescriptor
-- 
-- This component contains the provisionable traffic parameters for a 
-- control channel (Sig, Ilmi or Rcc component).

mscAtmIfUniSigVcd OBJECT IDENTIFIER ::= { mscAtmIfUniSig 2 }



mscAtmIfUniSigVcdRowStatusTable OBJECT-TYPE
   SYNTAX     SEQUENCE OF MscAtmIfUniSigVcdRowStatusEntry
   ACCESS     not-accessible
   STATUS     mandatory
   DESCRIPTION
     "This entry controls the addition and deletion of 
      mscAtmIfUniSigVcd components."
::= { mscAtmIfUniSigVcd 1 }

mscAtmIfUniSigVcdRowStatusEntry OBJECT-TYPE
   SYNTAX     MscAtmIfUniSigVcdRowStatusEntry
   ACCESS     not-accessible
   STATUS     mandatory
   DESCRIPTION
     "A single entry in the table represents a single 
      mscAtmIfUniSigVcd component."
   INDEX {
      mscAtmIfIndex,
      mscAtmIfUniIndex,
      mscAtmIfUniSigIndex,
      mscAtmIfUniSigVcdIndex }
::= { mscAtmIfUniSigVcdRowStatusTable 1 }

MscAtmIfUniSigVcdRowStatusEntry ::= SEQUENCE {
   mscAtmIfUniSigVcdRowStatus
      RowStatus,
   mscAtmIfUniSigVcdComponentName
      DisplayString,
   mscAtmIfUniSigVcdStorageType
      StorageType,
   mscAtmIfUniSigVcdIndex
      NonReplicated }

mscAtmIfUniSigVcdRowStatus OBJECT-TYPE
   SYNTAX     RowStatus 
   ACCESS     read-write
   STATUS     mandatory
   DESCRIPTION
     "This variable is used as the basis for SNMP naming of
      mscAtmIfUniSigVcd components.
      These components can be added and deleted."
::= { mscAtmIfUniSigVcdRowStatusEntry 1 }

mscAtmIfUniSigVcdComponentName OBJECT-TYPE
   SYNTAX     DisplayString 
   ACCESS     read-only
   STATUS     mandatory
   DESCRIPTION
     "This variable provides the component's string name for
      use with the ASCII Console Interface"
::= { mscAtmIfUniSigVcdRowStatusEntry 2 }

mscAtmIfUniSigVcdStorageType OBJECT-TYPE
   SYNTAX     StorageType 
   ACCESS     read-only
   STATUS     mandatory
   DESCRIPTION
     "This variable represents the storage type value for the
      mscAtmIfUniSigVcd tables."
::= { mscAtmIfUniSigVcdRowStatusEntry 4 }

mscAtmIfUniSigVcdIndex OBJECT-TYPE
   SYNTAX     NonReplicated 
   ACCESS     not-accessible
   STATUS     mandatory
   DESCRIPTION
     "This variable represents the index for the mscAtmIfUniSigVcd tables."
::= { mscAtmIfUniSigVcdRowStatusEntry 10 }

mscAtmIfUniSigVcdProvTable OBJECT-TYPE
   SYNTAX     SEQUENCE OF MscAtmIfUniSigVcdProvEntry
   ACCESS     not-accessible
   STATUS     mandatory
   DESCRIPTION
     "This group contains the provisionable traffic attributes for a control 
      channel."
::= { mscAtmIfUniSigVcd 10 }

mscAtmIfUniSigVcdProvEntry OBJECT-TYPE
   SYNTAX     MscAtmIfUniSigVcdProvEntry
   ACCESS     not-accessible
   STATUS     mandatory
   DESCRIPTION
     "An entry in the mscAtmIfUniSigVcdProvTable."
   INDEX {
      mscAtmIfIndex,
      mscAtmIfUniIndex,
      mscAtmIfUniSigIndex,
      mscAtmIfUniSigVcdIndex }
::= { mscAtmIfUniSigVcdProvTable 1 }

MscAtmIfUniSigVcdProvEntry ::= SEQUENCE {
   mscAtmIfUniSigVcdTrafficDescType
      INTEGER,
   mscAtmIfUniSigVcdAtmServiceCategory
      INTEGER,
   mscAtmIfUniSigVcdWeight
      Unsigned32,
   mscAtmIfUniSigVcdQosClass
      INTEGER,
   mscAtmIfUniSigVcdTrafficShaping
      INTEGER,
   mscAtmIfUniSigVcdUnshapedTransmitQueueing
      INTEGER,
   mscAtmIfUniSigVcdUsageParameterControl
      INTEGER }

mscAtmIfUniSigVcdTrafficDescType OBJECT-TYPE
   SYNTAX     INTEGER  {
                 n3(3),
                 n6(6),
                 n7(7),
                 n8(8) }
   ACCESS     read-write
   STATUS     mandatory
   DESCRIPTION
     "This attribute specifies the type of traffic management which is 
      applied to both the transmit and receive direction of this connection 
      as defined in the ATM Forum. The trafficDescType determines the 
      number and meaning of the parameters in the trafficDescParm 
      attribute."
   DEFVAL     { n6 }
::= { mscAtmIfUniSigVcdProvEntry 1 }

mscAtmIfUniSigVcdAtmServiceCategory OBJECT-TYPE
   SYNTAX     INTEGER  {
                 unspecifiedBitRate(0),
                 constantBitRate(1),
                 rtVariableBitRate(2),
                 nrtVariableBitRate(3) }
   ACCESS     read-write
   STATUS     mandatory
   DESCRIPTION
     "This attribute specifies the ATM service category for both directions 
      of the connection. 
      
      The constantBitRate service category is intended for real time 
      applications, that is those requiring tightly constrained delay and 
      delay variation, as would be appropriate for voice and video 
      applications. The consistent availability of a fixed quantity of 
      bandwidth is considered appropriate for CBR service. Cells which 
      are delayed beyond the value specified by CellTransfer Delay are 
      assumed to be of significantly reduce value to the application.
      
      The rtVariableBitRate service category is intended for real time 
      applications, that is those requiring tightly constrained delay and 
      delay variation, as would be appropriate for voice and video 
      applications. Sources are expected to transmit at a rate which varies 
      with time. Equivalently, the source can be described as 'bursty'. 
      Cells which are delayed beyond the value specified by CTD are 
      assumed to be of significantly reduced value to the application. Real 
      time VBR service may support statistical multiplexing of real time 
      sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections.
      
      The unspecifiedBitRate service is intended for non-real time 
      applications; that is, those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
   DEFVAL     { rtVariableBitRate }
::= { mscAtmIfUniSigVcdProvEntry 3 }

mscAtmIfUniSigVcdWeight OBJECT-TYPE
   SYNTAX     Unsigned32 (0 | 1..4095 | 65535)
   ACCESS     read-write
   STATUS     mandatory
   DESCRIPTION
     "This attribute specifies an override for the weight of this unshaped 
      connection. This attribute is ignored for shaped connections, for 
      ABR connections, for connections on a CQC-based ATM FP and 
      basic VPTs. 
      
      When the value is set to sameAsCa, the weight is determined by the 
      weight policy attribute under the CA service category component 
      for all but standard VPT VCCs. For standard VPT VCCs, the 
      weight is determined by the VCC's service category, when the value 
      is set to sameAsCa.
      
      When this attribute is set to a value from 1 to 4095, that value is 
      used for the weight policy of this connection relative to other 
      connections. For all but standard VPT VCCs, weight policy 
      determines the proportion of transit cell opportunities which are 
      allocated to this connection, compared to other connections in the 
      same service category. For standard VPT VCCs, weight policy 
      determines the proportion of transmit cell opportunities which are 
      allocated to this connection, compared to other connections 
      associated with the VPT.
      
      When the value is set to upToQueueLimit, the weight policy is 
      limited only by the txQueueLimit.

      VALUES (

      0 = upToQueueLimit

      65535 = sameAsCa

      )"
   DEFVAL     { 65535 }
::= { mscAtmIfUniSigVcdProvEntry 4 }

mscAtmIfUniSigVcdQosClass OBJECT-TYPE
   SYNTAX     INTEGER  {
                 n0(0),
                 n1(1),
                 n2(2),
                 n3(3),
                 n4(4) }
   ACCESS     read-write
   STATUS     mandatory
   DESCRIPTION
     "This attribute specifies the quality of service for both the forward 
      and backward direction for this connection.
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters."
   DEFVAL     { n2 }
::= { mscAtmIfUniSigVcdProvEntry 21 }

mscAtmIfUniSigVcdTrafficShaping OBJECT-TYPE
   SYNTAX     INTEGER  {
                 disabled(1),
                 sameAsCa(2) }
   ACCESS     read-write
   STATUS     mandatory
   DESCRIPTION
     "This attribute specifies whether this connection uses traffic shaping 
      when transmitting traffic to the ATM interface.
      
      When sameAsCa is selected, traffic shaping for this connection is 
      based on the trafficShaping attribute of the connection's service 
      category component under the AtmIf CA. If the service category has 
      traffic shaping enabled, then traffic shaping is enabled for the 
      connection. Note that enabling traffic shaping may have no effect 
      under certain cases. These cases are listed in the description of the 
      trafficShaping operational attribute, which is under the Vcc Tm and 
      Vpc Tm components.
      
      When disabled is selected, traffic shaping for this connection is 
      disabled."
   DEFVAL     { disabled }
::= { mscAtmIfUniSigVcdProvEntry 50 }

mscAtmIfUniSigVcdUnshapedTransmitQueueing OBJECT-TYPE
   SYNTAX     INTEGER  {
                 common(1),
                 sameAsCa(3) }
   ACCESS     read-write
   STATUS     mandatory
   DESCRIPTION
     "This attribute only applies when this connection is unshaped. This 
      attribute specifies the transmit queueing method for this connection 
      if it is unshaped. Refer to the unshapedTransmitQueueing attribute 
      under the AtmIf CA service category subcomponent for more details 
      on the meaning of this attribute. 
      
      When this attribute is set to sameAsCa, the transmit queueing 
      method for the connection is based on the 
      unshapedTransmitQueueing attribute of the connection's service 
      category component under the ConnectionAdministrator. 
      
      When this attribute is set to common, transmit traffic on this 
      unshaped connection is destined for the common queue. 
      
      The value sameAsInterface is for migration from previous software 
      releases, but should no longer be used"
   DEFVAL     { sameAsCa }
::= { mscAtmIfUniSigVcdProvEntry 60 }

mscAtmIfUniSigVcdUsageParameterControl OBJECT-TYPE
   SYNTAX     INTEGER  {
                 disabled(1),
                 sameAsCa(2) }
   ACCESS     read-write
   STATUS     mandatory
   DESCRIPTION
     "This attribute specifies whether this connection enforces usage 
      parameter control when receiving traffic from the ATM interface.
      
      When sameAsCa is selected, UPC for the connection is based on 
      the usageParameterControl attribute of the connection's service 
      category component under the ConnectionAdministrator. If the 
      service category has UPC enabled, then UPC is enabled for the 
      connection. Note that enabling UPC may have no effect under 
      certain cases. These cases are listed in the description of the 
      usageParameterControl operational attribute, which is under the 
      Vcc Tm or Vpc Tm component.
      
      When disabled is selected, UPC for this connection is disabled.
      
      The value sameAsInterface is for migration from previous software 
      releases, but should no longer be used"
   DEFVAL     { disabled }
::= { mscAtmIfUniSigVcdProvEntry 70 }

mscAtmIfUniSigVcdTdpTable OBJECT-TYPE
   SYNTAX     SEQUENCE OF MscAtmIfUniSigVcdTdpEntry
   ACCESS     not-accessible
   STATUS     mandatory
   DESCRIPTION
     "This attribute is a vector of five traffic parameters whose meanings 
      are defined by the trafficDescType attribute. The values of peak cell 
      rate (PCR), sustained cell rate (SCR) and requested shaping rate are 
      expressed in cell/s. Maximum burst size (MBS) is expressed in 
      cells. CDVT is expressed in microseconds. The values of PCR, 
      SCR, MBS and CDVT are used for connection admission control 
      (CAC). The value of CDVT is only used for connections where the 
      atmServiceCategory is constantBitRate. For all other values of 
      atmServiceCategory, CDVT is ignored. The values of PCR, SCR 
      and requested shaping rate are used to determine the actual shaping 
      rate where traffic shaping is enabled.
      
      When trafficDescType is 3, parameter 1 represents the PCR for CLP 
      equal to 0 and 1 traffic; parameter 4 represents the CDVT; and 
      parameter 5 represents the requested shaping rate. A non-zero value 
      in parameter 5 overrides any value in parameter 1. This result is 
      used as the PCR. Parameter 1 must be non-zero. Parameters 2 and 3 
      must be zero.
      
      When trafficDescType is 6, parameter 1 represents the PCR for CLP 
      equal to 0 and 1 traffic; parameter 2 represents the SCR for CLP 
      equal to 0 and 1 traffic; parameter 3 represents the MBS for CLP 
      equal to 0 and 1 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      When trafficDescType is 7, parameter 1 represents the PCR for CLP 
      equal to 0 and 1 traffic; parameter 2 represents the SCR for CLP 
      equal to 0 with cell discard; parameter 3 represents the MBS for 
      CLP equal to 0 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      When trafficDescType is 8, parameter 1 represents the PCR for CLP 
      equal to 0 and 1 traffic; parameter 2 represents the SCR for CLP 
      equal to 0 traffic with cell tagging; parameter 3 represents the MBS 
      for CLP equal to 0 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      Whenever it is valid for PCR to be specified, parameter 5 may also 
      be used to specify a requested shaping rate. A non-zero value in 
      parameter 5 overrides the value in parameter 1 and is used as the 
      peak cell rate in calculations of CAC and shaping rate.
      
      For trafficDescType 3 the traffic is shaped at the next rate less than 
      the PCR. 
      
      For trafficDescType 6, 7, and 8, the traffic is shaped at the highest 
      available rate which is between PCR and SCR. However, if there is 
      no available shaping rate between PCR and SCR, traffic is shaped at 
      the next rate above the PCR."
::= { mscAtmIfUniSigVcd 387 }

mscAtmIfUniSigVcdTdpEntry OBJECT-TYPE
   SYNTAX     MscAtmIfUniSigVcdTdpEntry
   ACCESS     not-accessible
   STATUS     mandatory
   DESCRIPTION
     "An entry in the mscAtmIfUniSigVcdTdpTable."
   INDEX {
      mscAtmIfIndex,
      mscAtmIfUniIndex,
      mscAtmIfUniSigIndex,
      mscAtmIfUniSigVcdIndex,
      mscAtmIfUniSigVcdTdpIndex }
::= { mscAtmIfUniSigVcdTdpTable 1 }

MscAtmIfUniSigVcdTdpEntry ::= SEQUENCE {
   mscAtmIfUniSigVcdTdpIndex
      Integer32,
   mscAtmIfUniSigVcdTdpValue
      Unsigned32 }

mscAtmIfUniSigVcdTdpIndex OBJECT-TYPE
   SYNTAX     Integer32 (1..5)
   ACCESS     not-accessible
   STATUS     mandatory
   DESCRIPTION
     "This variable represents the mscAtmIfUniSigVcdTdpTable
      specific index for the mscAtmIfUniSigVcdTdpTable."
::= { mscAtmIfUniSigVcdTdpEntry 1 }

mscAtmIfUniSigVcdTdpValue OBJECT-TYPE
   SYNTAX     Unsigned32 (0..2147483647)
   ACCESS     read-write
   STATUS     mandatory
   DESCRIPTION
     "This variable represents an individual value for the
      mscAtmIfUniSigVcdTdpTable."
::= { mscAtmIfUniSigVcdTdpEntry 2 }


-- AtmIf/n Iisp Address/address,type
-- AtmIf/n Uni Address/address,type
-- AtmIf/n Pnni Address/address,type
-- AtmIf/n Vpt/m Iisp Address/address,type
-- AtmIf/n Vpt/m Uni Address/address,type
-- AtmIf/n Vpt/m Pnni Address/address,type
-- 
-- This component represents an address (dynamic or static) 
-- associated with the interface. The index is a string of 1 to 40 hex 
-- digits or a single wildcard ('?'), and a type. The type identifies 
-- whether the Address component is for a primary, alternate, 
-- registered, or default address. 
-- 
-- The types primary and alternate are used for provisioned addresses. 
-- The type registered is used for dynamic addresses registered 
-- through ILMI. The type default is used for Soft PVP and Soft PVC 
-- addresses.Virtual interfaces do not have addresses of 
-- type default.
-- 
-- The wildcard is only valid for provisioned addresses. If the address 
-- is a single wildcard, then that indicates that the interface supports 
-- all addresses. If there is no better match, then this interface may be 
-- chosen in the routing. If there is more than one interface with a 
-- single wildcard static address, then the choice is driven through a 
-- round robin algorithm. 
-- 
-- The round robin algorithm tries the primary routes and then the 
-- alternate routes if none of the primary routes succeed.
-- If this node participates in a PNNI hierarchy, then a PnniInfo 
-- subcomponent can be provisioned under the AtmAddress 
-- component to specify the level to which this address will be 
-- advertised.

mscAtmIfUniAddr OBJECT IDENTIFIER ::= { mscAtmIfUni 4 }



mscAtmIfUniAddrRowStatusTable OBJECT-TYPE
   SYNTAX     SEQUENCE OF MscAtmIfUniAddrRowStatusEntry
   ACCESS     not-accessible
   STATUS     mandatory
   DESCRIPTION
     "This entry controls the addition and deletion of 
      mscAtmIfUniAddr components."
::= { mscAtmIfUniAddr 1 }

mscAtmIfUniAddrRowStatusEntry OBJECT-TYPE
   SYNTAX     MscAtmIfUniAddrRowStatusEntry
   ACCESS     not-accessible
   STATUS     mandatory
   DESCRIPTION
     "A single entry in the table represents a single 
      mscAtmIfUniAddr component."
   INDEX {
      mscAtmIfIndex,
      mscAtmIfUniIndex,
      mscAtmIfUniAddrAddressIndex,
      mscAtmIfUniAddrAddressTypeIndex }
::= { mscAtmIfUniAddrRowStatusTable 1 }

MscAtmIfUniAddrRowStatusEntry ::= SEQUENCE {
   mscAtmIfUniAddrRowStatus
      RowStatus,
   mscAtmIfUniAddrComponentName
      DisplayString,
   mscAtmIfUniAddrStorageType
      StorageType,
   mscAtmIfUniAddrAddressIndex
      AsciiStringIndex,
   mscAtmIfUniAddrAddressTypeIndex
      INTEGER }

mscAtmIfUniAddrRowStatus OBJECT-TYPE
   SYNTAX     RowStatus 
   ACCESS     read-write
   STATUS     mandatory
   DESCRIPTION
     "This variable is used as the basis for SNMP naming of
      mscAtmIfUniAddr components.
      These components can be added and deleted."
::= { mscAtmIfUniAddrRowStatusEntry 1 }

mscAtmIfUniAddrComponentName OBJECT-TYPE
   SYNTAX     DisplayString 
   ACCESS     read-only
   STATUS     mandatory
   DESCRIPTION
     "This variable provides the component's string name for
      use with the ASCII Console Interface"
::= { mscAtmIfUniAddrRowStatusEntry 2 }

mscAtmIfUniAddrStorageType OBJECT-TYPE
   SYNTAX     StorageType 
   ACCESS     read-only
   STATUS     mandatory
   DESCRIPTION
     "This variable represents the storage type value for the
      mscAtmIfUniAddr tables."
::= { mscAtmIfUniAddrRowStatusEntry 4 }

mscAtmIfUniAddrAddressIndex OBJECT-TYPE
   SYNTAX     AsciiStringIndex (SIZE (1..40))
   ACCESS     not-accessible
   STATUS     mandatory
   DESCRIPTION
     "This variable represents an index for the mscAtmIfUniAddr tables."
::= { mscAtmIfUniAddrRowStatusEntry 10 }

mscAtmIfUniAddrAddressTypeIndex OBJECT-TYPE
   SYNTAX     INTEGER  {
                 primary(0),
                 alternate(1),
                 registered(2),
                 default(3) }
   ACCESS     not-accessible
   STATUS     mandatory
   DESCRIPTION
     "This variable represents an index for the mscAtmIfUniAddr tables."
::= { mscAtmIfUniAddrRowStatusEntry 11 }

mscAtmIfUniAddrOperTable OBJECT-TYPE
   SYNTAX     SEQUENCE OF MscAtmIfUniAddrOperEntry
   ACCESS     not-accessible
   STATUS     mandatory
   DESCRIPTION
     "This attribute group contains the operational attributes for the 
      Address component."
::= { mscAtmIfUniAddr 10 }

mscAtmIfUniAddrOperEntry OBJECT-TYPE
   SYNTAX     MscAtmIfUniAddrOperEntry
   ACCESS     not-accessible
   STATUS     mandatory
   DESCRIPTION
     "An entry in the mscAtmIfUniAddrOperTable."
   INDEX {
      mscAtmIfIndex,
      mscAtmIfUniIndex,
      mscAtmIfUniAddrAddressIndex,
      mscAtmIfUniAddrAddressTypeIndex }
::= { mscAtmIfUniAddrOperTable 1 }

MscAtmIfUniAddrOperEntry ::= SEQUENCE {
   mscAtmIfUniAddrScope
      INTEGER,
   mscAtmIfUniAddrReachability
      INTEGER }

mscAtmIfUniAddrScope OBJECT-TYPE
   SYNTAX     INTEGER (-1..104)
   ACCESS     read-only
   STATUS     mandatory
   DESCRIPTION
     "This attribute indicates the scope of the ATM address, which is the 
      highest level to which this address will be advertised in the PNNI 
      hierarchy. If no PnniInfo subcomponent has been provisioned, then 
      the scope will default to the level of this node in the PNNI 
      hierarchy. If this node does not participate in a PNNI hierarchy, then 
      this attribute will have the value of -1."
::= { mscAtmIfUniAddrOperEntry 1 }

mscAtmIfUniAddrReachability OBJECT-TYPE
   SYNTAX     INTEGER  {
                 internal(0),
                 exterior(1) }
   ACCESS     read-only
   STATUS     mandatory
   DESCRIPTION
     "This attribute indicates whether the address is internal or exterior. 
      An internal reachable address is an address of a destination that is 
      directly attached to the logical node advertising the address. An 
      exterior reachable address is an address that can be reached 
      through a PNNI routing domain, but which is not located in that 
      PNNI routing domain."
::= { mscAtmIfUniAddrOperEntry 2 }


-- AtmIf/n Iisp Address/address,type TerminateSPvpAndSPvc
-- AtmIf/n Uni Address/address,type TerminateSPvpAndSPvc
-- AtmIf/n Pnni Address/address,type TerminateSPvpAndSPvc
-- AtmIf/n Vpt/m Iisp Address/address,type TerminateSPvpAndSPvc
-- AtmIf/n Vpt/m Uni Address/address,type TerminateSPvpAndSPvc
-- AtmIf/n Vpt/m Pnni Address/address,type TerminateSPvpAndSPvc
-- 
-- The presence of this subcomponent indicates that SPvp and SPvc 
-- call setups terminate at this node if the destination address of the 
-- SPVP or SPVC matches the Address instance.

mscAtmIfUniAddrTermSP OBJECT IDENTIFIER ::= { mscAtmIfUniAddr 2 }



mscAtmIfUniAddrTermSPRowStatusTable OBJECT-TYPE
   SYNTAX     SEQUENCE OF MscAtmIfUniAddrTermSPRowStatusEntry
   ACCESS     not-accessible
   STATUS     mandatory
   DESCRIPTION
     "This entry controls the addition and deletion of 
      mscAtmIfUniAddrTermSP components."
::= { mscAtmIfUniAddrTermSP 1 }

mscAtmIfUniAddrTermSPRowStatusEntry OBJECT-TYPE
   SYNTAX     MscAtmIfUniAddrTermSPRowStatusEntry
   ACCESS     not-accessible
   STATUS     mandatory
   DESCRIPTION
     "A single entry in the table represents a single 
      mscAtmIfUniAddrTermSP component."
   INDEX {
      mscAtmIfIndex,
      mscAtmIfUniIndex,
      mscAtmIfUniAddrAddressIndex,
      mscAtmIfUniAddrAddressTypeIndex,
      mscAtmIfUniAddrTermSPIndex }
::= { mscAtmIfUniAddrTermSPRowStatusTable 1 }

MscAtmIfUniAddrTermSPRowStatusEntry ::= SEQUENCE {
   mscAtmIfUniAddrTermSPRowStatus
      RowStatus,
   mscAtmIfUniAddrTermSPComponentName
      DisplayString,
   mscAtmIfUniAddrTermSPStorageType
      StorageType,
   mscAtmIfUniAddrTermSPIndex
      NonReplicated }

mscAtmIfUniAddrTermSPRowStatus OBJECT-TYPE
   SYNTAX     RowStatus 
   ACCESS     read-write
   STATUS     mandatory
   DESCRIPTION
     "This variable is used as the basis for SNMP naming of
      mscAtmIfUniAddrTermSP components.
      These components can be added and deleted."
::= { mscAtmIfUniAddrTermSPRowStatusEntry 1 }

mscAtmIfUniAddrTermSPComponentName OBJECT-TYPE
   SYNTAX     DisplayString 
   ACCESS     read-only
   STATUS     mandatory
   DESCRIPTION
     "This variable provides the component's string name for
      use with the ASCII Console Interface"
::= { mscAtmIfUniAddrTermSPRowStatusEntry 2 }

mscAtmIfUniAddrTermSPStorageType OBJECT-TYPE
   SYNTAX     StorageType 
   ACCESS     read-only
   STATUS     mandatory
   DESCRIPTION
     "This variable represents the storage type value for the
      mscAtmIfUniAddrTermSP tables."
::= { mscAtmIfUniAddrTermSPRowStatusEntry 4 }

mscAtmIfUniAddrTermSPIndex OBJECT-TYPE
   SYNTAX     NonReplicated 
   ACCESS     not-accessible
   STATUS     mandatory
   DESCRIPTION
     "This variable represents the index for the mscAtmIfUniAddrTermSP tables."
::= { mscAtmIfUniAddrTermSPRowStatusEntry 10 }


-- AtmIf/n Iisp Addr/address,type PnniInfo
-- AtmIf/n Uni Addr/address,type PnniInfo
-- AtmIf/n Pnni Addr/address,type PnniInfo
-- AtmIf/n Vpt/m Iisp Addr/address,type PnniInfo
-- AtmIf/n Vpt/m Uni Addr/address,type PnniInfo
-- AtmIf/n Vpt/m Pnni Addr/address,type PnniInfo
-- 
-- This component contains provisioned information associated with 
-- the ATM address related to PNNI. This component appears only 
-- under provisioned Address components.

mscAtmIfUniAddrPnniInfo OBJECT IDENTIFIER ::= { mscAtmIfUniAddr 3 }



mscAtmIfUniAddrPnniInfoRowStatusTable OBJECT-TYPE
   SYNTAX     SEQUENCE OF MscAtmIfUniAddrPnniInfoRowStatusEntry
   ACCESS     not-accessible
   STATUS     mandatory
   DESCRIPTION
     "This entry controls the addition and deletion of 
      mscAtmIfUniAddrPnniInfo components."
::= { mscAtmIfUniAddrPnniInfo 1 }

mscAtmIfUniAddrPnniInfoRowStatusEntry OBJECT-TYPE
   SYNTAX     MscAtmIfUniAddrPnniInfoRowStatusEntry
   ACCESS     not-accessible
   STATUS     mandatory
   DESCRIPTION
     "A single entry in the table represents a single 
      mscAtmIfUniAddrPnniInfo component."
   INDEX {
      mscAtmIfIndex,
      mscAtmIfUniIndex,
      mscAtmIfUniAddrAddressIndex,
      mscAtmIfUniAddrAddressTypeIndex,
      mscAtmIfUniAddrPnniInfoIndex }
::= { mscAtmIfUniAddrPnniInfoRowStatusTable 1 }

MscAtmIfUniAddrPnniInfoRowStatusEntry ::= SEQUENCE {
   mscAtmIfUniAddrPnniInfoRowStatus
      RowStatus,
   mscAtmIfUniAddrPnniInfoComponentName
      DisplayString,
   mscAtmIfUniAddrPnniInfoStorageType
      StorageType,
   mscAtmIfUniAddrPnniInfoIndex
      NonReplicated }

mscAtmIfUniAddrPnniInfoRowStatus OBJECT-TYPE
   SYNTAX     RowStatus 
   ACCESS     read-write
   STATUS     mandatory
   DESCRIPTION
     "This variable is used as the basis for SNMP naming of
      mscAtmIfUniAddrPnniInfo components.
      These components can be added and deleted."
::= { mscAtmIfUniAddrPnniInfoRowStatusEntry 1 }

mscAtmIfUniAddrPnniInfoComponentName OBJECT-TYPE
   SYNTAX     DisplayString 
   ACCESS     read-only
   STATUS     mandatory
   DESCRIPTION
     "This variable provides the component's string name for
      use with the ASCII Console Interface"
::= { mscAtmIfUniAddrPnniInfoRowStatusEntry 2 }

mscAtmIfUniAddrPnniInfoStorageType OBJECT-TYPE
   SYNTAX     StorageType 
   ACCESS     read-only
   STATUS     mandatory
   DESCRIPTION
     "This variable represents the storage type value for the
      mscAtmIfUniAddrPnniInfo tables."
::= { mscAtmIfUniAddrPnniInfoRowStatusEntry 4 }

mscAtmIfUniAddrPnniInfoIndex OBJECT-TYPE
   SYNTAX     NonReplicated 
   ACCESS     not-accessible
   STATUS     mandatory
   DESCRIPTION
     "This variable represents the index for the mscAtmIfUniAddrPnniInfo tables."
::= { mscAtmIfUniAddrPnniInfoRowStatusEntry 10 }

mscAtmIfUniAddrPnniInfoProvTable OBJECT-TYPE
   SYNTAX     SEQUENCE OF MscAtmIfUniAddrPnniInfoProvEntry
   ACCESS     not-accessible
   STATUS     mandatory
   DESCRIPTION
     "This attribute group contains the provisioned attributes relating to 
      PNNI for a PnniInfo component."
::= { mscAtmIfUniAddrPnniInfo 10 }

mscAtmIfUniAddrPnniInfoProvEntry OBJECT-TYPE
   SYNTAX     MscAtmIfUniAddrPnniInfoProvEntry
   ACCESS     not-accessible
   STATUS     mandatory
   DESCRIPTION
     "An entry in the mscAtmIfUniAddrPnniInfoProvTable."
   INDEX {
      mscAtmIfIndex,
      mscAtmIfUniIndex,
      mscAtmIfUniAddrAddressIndex,
      mscAtmIfUniAddrAddressTypeIndex,
      mscAtmIfUniAddrPnniInfoIndex }
::= { mscAtmIfUniAddrPnniInfoProvTable 1 }

MscAtmIfUniAddrPnniInfoProvEntry ::= SEQUENCE {
   mscAtmIfUniAddrPnniInfoScope
      INTEGER,
   mscAtmIfUniAddrPnniInfoReachability
      INTEGER }

mscAtmIfUniAddrPnniInfoScope OBJECT-TYPE
   SYNTAX     INTEGER (-1..104)
   ACCESS     read-write
   STATUS     mandatory
   DESCRIPTION
     "This attribute specifies the scope of the ATM address, which is the 
      highest level up to which this address will be advertised in the 
      PNNI hierarchy. The scope must be set to a value numerically less 
      than or equal to the level of the lowest level peer group containing 
      this node. Setting the scope to 0 will cause the address to be 
      advertised globally within this PNNI routing domain."
   DEFVAL     { -1 }
::= { mscAtmIfUniAddrPnniInfoProvEntry 1 }

mscAtmIfUniAddrPnniInfoReachability OBJECT-TYPE
   SYNTAX     INTEGER  {
                 internal(0),
                 exterior(1) }
   ACCESS     read-write
   STATUS     mandatory
   DESCRIPTION
     "This attribute indicates whether the address is internal or exterior. 
      An internal reachable address is an address of a destination that is 
      directly attached to the logical node advertising the address. An 
      exterior reachable address is an address that can be reached 
      through a PNNI routing domain, but which is not located in that 
      PNNI routing domain."
   DEFVAL     { internal }
::= { mscAtmIfUniAddrPnniInfoProvEntry 2 }


-- AtmIf/n Uni CallingAddressScreening
-- AtmIf/n Iisp CallingAddressScreening
-- This component represents the screening of incoming ATM SVC 
-- call requests against provisioned ATM calling addresses (that is, 
-- screening SVC calls coming from specific addresses). If this 
-- component is not provisioned, all call requests are accepted and no 
-- calling address screening takes place. 

mscAtmIfUniCallingAScr OBJECT IDENTIFIER ::= { mscAtmIfUni 5 }



mscAtmIfUniCallingAScrRowStatusTable OBJECT-TYPE
   SYNTAX     SEQUENCE OF MscAtmIfUniCallingAScrRowStatusEntry
   ACCESS     not-accessible
   STATUS     mandatory
   DESCRIPTION
     "This entry controls the addition and deletion of 
      mscAtmIfUniCallingAScr components."
::= { mscAtmIfUniCallingAScr 1 }

mscAtmIfUniCallingAScrRowStatusEntry OBJECT-TYPE
   SYNTAX     MscAtmIfUniCallingAScrRowStatusEntry
   ACCESS     not-accessible
   STATUS     mandatory
   DESCRIPTION
     "A single entry in the table represents a single 
      mscAtmIfUniCallingAScr component."
   INDEX {
      mscAtmIfIndex,
      mscAtmIfUniIndex,
      mscAtmIfUniCallingAScrIndex }
::= { mscAtmIfUniCallingAScrRowStatusTable 1 }

MscAtmIfUniCallingAScrRowStatusEntry ::= SEQUENCE {
   mscAtmIfUniCallingAScrRowStatus
      RowStatus,
   mscAtmIfUniCallingAScrComponentName
      DisplayString,
   mscAtmIfUniCallingAScrStorageType
      StorageType,
   mscAtmIfUniCallingAScrIndex
      NonReplicated }

mscAtmIfUniCallingAScrRowStatus OBJECT-TYPE
   SYNTAX     RowStatus 
   ACCESS     read-write
   STATUS     mandatory
   DESCRIPTION
     "This variable is used as the basis for SNMP naming of
      mscAtmIfUniCallingAScr components.
      These components can be added and deleted."
::= { mscAtmIfUniCallingAScrRowStatusEntry 1 }

mscAtmIfUniCallingAScrComponentName OBJECT-TYPE
   SYNTAX     DisplayString 
   ACCESS     read-only
   STATUS     mandatory
   DESCRIPTION
     "This variable provides the component's string name for
      use with the ASCII Console Interface"
::= { mscAtmIfUniCallingAScrRowStatusEntry 2 }

mscAtmIfUniCallingAScrStorageType OBJECT-TYPE
   SYNTAX     StorageType 
   ACCESS     read-only
   STATUS     mandatory
   DESCRIPTION
     "This variable represents the storage type value for the
      mscAtmIfUniCallingAScr tables."
::= { mscAtmIfUniCallingAScrRowStatusEntry 4 }

mscAtmIfUniCallingAScrIndex OBJECT-TYPE
   SYNTAX     NonReplicated 
   ACCESS     not-accessible
   STATUS     mandatory
   DESCRIPTION
     "This variable represents the index for the mscAtmIfUniCallingAScr tables."
::= { mscAtmIfUniCallingAScrRowStatusEntry 10 }

mscAtmIfUniCallingAScrProvTable OBJECT-TYPE
   SYNTAX     SEQUENCE OF MscAtmIfUniCallingAScrProvEntry
   ACCESS     not-accessible
   STATUS     mandatory
   DESCRIPTION
     "This attribute group contains the provisionable attributes for the 
      CallingAScr component."
::= { mscAtmIfUniCallingAScr 10 }

mscAtmIfUniCallingAScrProvEntry OBJECT-TYPE
   SYNTAX     MscAtmIfUniCallingAScrProvEntry
   ACCESS     not-accessible
   STATUS     mandatory
   DESCRIPTION
     "An entry in the mscAtmIfUniCallingAScrProvTable."
   INDEX {
      mscAtmIfIndex,
      mscAtmIfUniIndex,
      mscAtmIfUniCallingAScrIndex }
::= { mscAtmIfUniCallingAScrProvTable 1 }

MscAtmIfUniCallingAScrProvEntry ::= SEQUENCE {
   mscAtmIfUniCallingAScrAdminStatus
      INTEGER,
   mscAtmIfUniCallingAScrDefaultInsertionAddress
      HexString }

mscAtmIfUniCallingAScrAdminStatus OBJECT-TYPE
   SYNTAX     INTEGER  {
                 enabled(0),
                 disabled(1) }
   ACCESS     read-write
   STATUS     mandatory
   DESCRIPTION
     "This attribute specifies whether the calling address screening feature 
      is enabled or disabled. 
      
      If enabled, incoming SVC calls are screened against provisioned 
      addresses. If enabled and the calling address in the ATM SVC call 
      request is provisioned to be accepted, the call is accepted or rejected 
      according to the action specified for that address. If the value is 
      enabled, and the calling address in the address request is not 
      provisioned, the call is rejected
      
      If the value is disabled, no calling address screening is performed."
   DEFVAL     { disabled }
::= { mscAtmIfUniCallingAScrProvEntry 1 }

mscAtmIfUniCallingAScrDefaultInsertionAddress OBJECT-TYPE
   SYNTAX     HexString (SIZE (0..20))
   ACCESS     read-write
   STATUS     mandatory
   DESCRIPTION
     "This attribute specifies the address to be inserted into the SVC 
      connection request if adminStatus is enabled and the connection 
      request does not contain a calling address. If the adminStatus 
      attribute is enabled and this attribute is empty, all incoming SVC 
      calls which do not contain a calling address are rejected."
   DEFVAL     { ''H }  -- ""
::= { mscAtmIfUniCallingAScrProvEntry 2 }

mscAtmIfUniCallingAScrStatTable OBJECT-TYPE
   SYNTAX     SEQUENCE OF MscAtmIfUniCallingAScrStatEntry
   ACCESS     not-accessible
   STATUS     mandatory
   DESCRIPTION
     "This attribute group contains statistics related to the incoming SVC 
      call requests received while the adminStatus attribute is set to 
      enabled."
::= { mscAtmIfUniCallingAScr 11 }

mscAtmIfUniCallingAScrStatEntry OBJECT-TYPE
   SYNTAX     MscAtmIfUniCallingAScrStatEntry
   ACCESS     not-accessible
   STATUS     mandatory
   DESCRIPTION
     "An entry in the mscAtmIfUniCallingAScrStatTable."
   INDEX {
      mscAtmIfIndex,
      mscAtmIfUniIndex,
      mscAtmIfUniCallingAScrIndex }
::= { mscAtmIfUniCallingAScrStatTable 1 }

MscAtmIfUniCallingAScrStatEntry ::= SEQUENCE {
   mscAtmIfUniCallingAScrAcceptedCalls
      Counter32,
   mscAtmIfUniCallingAScrRejectedCalls
      Counter32,
   mscAtmIfUniCallingAScrUnmatchedCalls
      Counter32 }

mscAtmIfUniCallingAScrAcceptedCalls OBJECT-TYPE
   SYNTAX     Counter32 
   ACCESS     read-only
   STATUS     mandatory
   DESCRIPTION
     "This attribute counts the incoming SVC calls which were accepted 
      because the address specified in the call request matched a 
      provisioned ATM address and the associated action was accept.
      When the counter exceeds the maximum, it wraps to 0."
::= { mscAtmIfUniCallingAScrStatEntry 1 }

mscAtmIfUniCallingAScrRejectedCalls OBJECT-TYPE
   SYNTAX     Counter32 
   ACCESS     read-only
   STATUS     mandatory
   DESCRIPTION
     "This attribute counts the incoming SVC calls which were rejected 
      because the address specified in the call request matched a 
      provisioned ATM address, but the associated action was reject. 
      When the counter exceeds the maximum, it wraps to 0."
::= { mscAtmIfUniCallingAScrStatEntry 2 }

mscAtmIfUniCallingAScrUnmatchedCalls OBJECT-TYPE
   SYNTAX     Counter32 
   ACCESS     read-only
   STATUS     mandatory
   DESCRIPTION
     "This attribute counts the incoming SVC calls which were rejected 
      because none of the provisioned ATM addresses matched the 
      applicable address in the incoming SVC call request.
      When the counter exceeds the maximum, it wraps to 0."
::= { mscAtmIfUniCallingAScrStatEntry 3 }


-- AtmIf/n Uni CallingAScr Address/addr,action
-- AtmIf/n Iisp CallingAScr Address/addr,action 
-- AtmIf/n Uni CalledAScr Address/addr,action 
-- AtmIf/n Iisp CalledAScr Address/addr,action 
-- This component specifies a calling (or called) address with an 
-- action to accept or reject a connection request which contains a 
-- matching calling (or called) address.
-- For the Calling Address Screening feature, if the specified action is 
-- accept, any call whose calling address matches that address is 
-- accepted. If the specified action is reject, any call whose calling 
-- address matches that address is rejected.
-- For the Called Address Screening feature, if the specified action is 
-- accept, any call whose called address matches that address, is 
-- accepted. If the specified action is reject, any call whose called 
-- address matches that address is rejected.
-- For both features, the incoming SVC call request is rejected if the 
-- address is not provisioned and the feature is enabled.

mscAtmIfUniCallingAScrAddr OBJECT IDENTIFIER ::= { mscAtmIfUniCallingAScr 2 }



mscAtmIfUniCallingAScrAddrRowStatusTable OBJECT-TYPE
   SYNTAX     SEQUENCE OF MscAtmIfUniCallingAScrAddrRowStatusEntry
   ACCESS     not-accessible
   STATUS     mandatory
   DESCRIPTION
     "This entry controls the addition and deletion of 
      mscAtmIfUniCallingAScrAddr components."
::= { mscAtmIfUniCallingAScrAddr 1 }

mscAtmIfUniCallingAScrAddrRowStatusEntry OBJECT-TYPE
   SYNTAX     MscAtmIfUniCallingAScrAddrRowStatusEntry
   ACCESS     not-accessible
   STATUS     mandatory
   DESCRIPTION
     "A single entry in the table represents a single 
      mscAtmIfUniCallingAScrAddr component."
   INDEX {
      mscAtmIfIndex,
      mscAtmIfUniIndex,
      mscAtmIfUniCallingAScrIndex,
      mscAtmIfUniCallingAScrAddrAddressIndex,
      mscAtmIfUniCallingAScrAddrAddressActionIndex }
::= { mscAtmIfUniCallingAScrAddrRowStatusTable 1 }

MscAtmIfUniCallingAScrAddrRowStatusEntry ::= SEQUENCE {
   mscAtmIfUniCallingAScrAddrRowStatus
      RowStatus,
   mscAtmIfUniCallingAScrAddrComponentName
      DisplayString,
   mscAtmIfUniCallingAScrAddrStorageType
      StorageType,
   mscAtmIfUniCallingAScrAddrAddressIndex
      AsciiStringIndex,
   mscAtmIfUniCallingAScrAddrAddressActionIndex
      INTEGER }

mscAtmIfUniCallingAScrAddrRowStatus OBJECT-TYPE
   SYNTAX     RowStatus 
   ACCESS     read-write
   STATUS     mandatory
   DESCRIPTION
     "This variable is used as the basis for SNMP naming of
      mscAtmIfUniCallingAScrAddr components.
      These components can be added and deleted."
::= { mscAtmIfUniCallingAScrAddrRowStatusEntry 1 }

mscAtmIfUniCallingAScrAddrComponentName OBJECT-TYPE
   SYNTAX     DisplayString 
   ACCESS     read-only
   STATUS     mandatory
   DESCRIPTION
     "This variable provides the component's string name for
      use with the ASCII Console Interface"
::= { mscAtmIfUniCallingAScrAddrRowStatusEntry 2 }

mscAtmIfUniCallingAScrAddrStorageType OBJECT-TYPE
   SYNTAX     StorageType 
   ACCESS     read-only
   STATUS     mandatory
   DESCRIPTION
     "This variable represents the storage type value for the
      mscAtmIfUniCallingAScrAddr tables."
::= { mscAtmIfUniCallingAScrAddrRowStatusEntry 4 }

mscAtmIfUniCallingAScrAddrAddressIndex OBJECT-TYPE
   SYNTAX     AsciiStringIndex (SIZE (1..40))
   ACCESS     not-accessible
   STATUS     mandatory
   DESCRIPTION
     "This variable represents an index for the mscAtmIfUniCallingAScrAddr tables."
::= { mscAtmIfUniCallingAScrAddrRowStatusEntry 10 }

mscAtmIfUniCallingAScrAddrAddressActionIndex OBJECT-TYPE
   SYNTAX     INTEGER  {
                 accept(0),
                 reject(1) }
   ACCESS     not-accessible
   STATUS     mandatory
   DESCRIPTION
     "This variable represents an index for the mscAtmIfUniCallingAScrAddr tables."
::= { mscAtmIfUniCallingAScrAddrRowStatusEntry 11 }


-- AtmIf/n Uni CalledAddressScreening
-- AtmIf/n Iisp CalledAddressScreening
-- This component represents the screening of incoming ATM SVC 
-- call requests against provisioned ATM called addresses (that is, 
-- going to specific destinations). If this component is not provisioned, 
-- all call requests are accepted and no called address screening takes 
-- place.

mscAtmIfUniCalledAScr OBJECT IDENTIFIER ::= { mscAtmIfUni 6 }



mscAtmIfUniCalledAScrRowStatusTable OBJECT-TYPE
   SYNTAX     SEQUENCE OF MscAtmIfUniCalledAScrRowStatusEntry
   ACCESS     not-accessible
   STATUS     mandatory
   DESCRIPTION
     "This entry controls the addition and deletion of 
      mscAtmIfUniCalledAScr components."
::= { mscAtmIfUniCalledAScr 1 }

mscAtmIfUniCalledAScrRowStatusEntry OBJECT-TYPE
   SYNTAX     MscAtmIfUniCalledAScrRowStatusEntry
   ACCESS     not-accessible
   STATUS     mandatory
   DESCRIPTION
     "A single entry in the table represents a single 
      mscAtmIfUniCalledAScr component."
   INDEX {
      mscAtmIfIndex,
      mscAtmIfUniIndex,
      mscAtmIfUniCalledAScrIndex }
::= { mscAtmIfUniCalledAScrRowStatusTable 1 }

MscAtmIfUniCalledAScrRowStatusEntry ::= SEQUENCE {
   mscAtmIfUniCalledAScrRowStatus
      RowStatus,
   mscAtmIfUniCalledAScrComponentName
      DisplayString,
   mscAtmIfUniCalledAScrStorageType
      StorageType,
   mscAtmIfUniCalledAScrIndex
      NonReplicated }

mscAtmIfUniCalledAScrRowStatus OBJECT-TYPE
   SYNTAX     RowStatus 
   ACCESS     read-write
   STATUS     mandatory
   DESCRIPTION
     "This variable is used as the basis for SNMP naming of
      mscAtmIfUniCalledAScr components.
      These components can be added and deleted."
::= { mscAtmIfUniCalledAScrRowStatusEntry 1 }

mscAtmIfUniCalledAScrComponentName OBJECT-TYPE
   SYNTAX     DisplayString 
   ACCESS     read-only
   STATUS     mandatory
   DESCRIPTION
     "This variable provides the component's string name for
      use with the ASCII Console Interface"
::= { mscAtmIfUniCalledAScrRowStatusEntry 2 }

mscAtmIfUniCalledAScrStorageType OBJECT-TYPE
   SYNTAX     StorageType 
   ACCESS     read-only
   STATUS     mandatory
   DESCRIPTION
     "This variable represents the storage type value for the
      mscAtmIfUniCalledAScr tables."
::= { mscAtmIfUniCalledAScrRowStatusEntry 4 }

mscAtmIfUniCalledAScrIndex OBJECT-TYPE
   SYNTAX     NonReplicated 
   ACCESS     not-accessible
   STATUS     mandatory
   DESCRIPTION
     "This variable represents the index for the mscAtmIfUniCalledAScr tables."
::= { mscAtmIfUniCalledAScrRowStatusEntry 10 }

mscAtmIfUniCalledAScrProvTable OBJECT-TYPE
   SYNTAX     SEQUENCE OF MscAtmIfUniCalledAScrProvEntry
   ACCESS     not-accessible
   STATUS     mandatory
   DESCRIPTION
     "This attribute group contains the provisionable attributes for the 
      CalledAScr component."
::= { mscAtmIfUniCalledAScr 10 }

mscAtmIfUniCalledAScrProvEntry OBJECT-TYPE
   SYNTAX     MscAtmIfUniCalledAScrProvEntry
   ACCESS     not-accessible
   STATUS     mandatory
   DESCRIPTION
     "An entry in the mscAtmIfUniCalledAScrProvTable."
   INDEX {
      mscAtmIfIndex,
      mscAtmIfUniIndex,
      mscAtmIfUniCalledAScrIndex }
::= { mscAtmIfUniCalledAScrProvTable 1 }

MscAtmIfUniCalledAScrProvEntry ::= SEQUENCE {
   mscAtmIfUniCalledAScrAdminStatus
      INTEGER }

mscAtmIfUniCalledAScrAdminStatus OBJECT-TYPE
   SYNTAX     INTEGER  {
                 enabled(0),
                 disabled(1) }
   ACCESS     read-write
   STATUS     mandatory
   DESCRIPTION
     "This attribute specifies whether the called address screening feature 
      is enabled or disabled.
      If the value is enabled, incoming SVC calls will be screened against 
      provisioned called addresses. If the value is enabled and the called 
      address in the ATM SVC call request has been provisioned, the call 
      is accepted or rejected according to the action specified for that 
      address. If the value is enabled and the called address in the call 
      request is not provisioned, the call is rejected.
      If the value is disabled, no called address screening is performed."
   DEFVAL     { disabled }
::= { mscAtmIfUniCalledAScrProvEntry 1 }

mscAtmIfUniCalledAScrStatTable OBJECT-TYPE
   SYNTAX     SEQUENCE OF MscAtmIfUniCalledAScrStatEntry
   ACCESS     not-accessible
   STATUS     mandatory
   DESCRIPTION
     "This attribute group contains statistics related to the incoming SVC 
      call requests received while the adminStatus attribute is set to 
      enabled."
::= { mscAtmIfUniCalledAScr 11 }

mscAtmIfUniCalledAScrStatEntry OBJECT-TYPE
   SYNTAX     MscAtmIfUniCalledAScrStatEntry
   ACCESS     not-accessible
   STATUS     mandatory
   DESCRIPTION
     "An entry in the mscAtmIfUniCalledAScrStatTable."
   INDEX {
      mscAtmIfIndex,
      mscAtmIfUniIndex,
      mscAtmIfUniCalledAScrIndex }
::= { mscAtmIfUniCalledAScrStatTable 1 }

MscAtmIfUniCalledAScrStatEntry ::= SEQUENCE {
   mscAtmIfUniCalledAScrAcceptedCalls
      Counter32,
   mscAtmIfUniCalledAScrRejectedCalls
      Counter32,
   mscAtmIfUniCalledAScrUnmatchedCalls
      Counter32 }

mscAtmIfUniCalledAScrAcceptedCalls OBJECT-TYPE
   SYNTAX     Counter32 
   ACCESS     read-only
   STATUS     mandatory
   DESCRIPTION
     "This attribute counts the incoming SVC calls which were accepted 
      because the address specified in the call request matched a 
      provisioned ATM address and the associated action was accept.
      When the counter exceeds the maximum, it wraps to 0."
::= { mscAtmIfUniCalledAScrStatEntry 1 }

mscAtmIfUniCalledAScrRejectedCalls OBJECT-TYPE
   SYNTAX     Counter32 
   ACCESS     read-only
   STATUS     mandatory
   DESCRIPTION
     "This attribute counts the incoming SVC calls which were rejected 
      because the address specified in the call request matched a 
      provisioned ATM address, but the associated action was reject. 
      When the counter exceeds the maximum, it wraps to 0."
::= { mscAtmIfUniCalledAScrStatEntry 2 }

mscAtmIfUniCalledAScrUnmatchedCalls OBJECT-TYPE
   SYNTAX     Counter32 
   ACCESS     read-only
   STATUS     mandatory
   DESCRIPTION
     "This attribute counts the incoming SVC calls which were rejected 
      because none of the provisioned ATM addresses matched the 
      applicable address in the incoming SVC call request.
      When the counter exceeds the maximum, it wraps to 0."
::= { mscAtmIfUniCalledAScrStatEntry 3 }


-- AtmIf/n Uni CallingAScr Address/addr,action
-- AtmIf/n Iisp CallingAScr Address/addr,action 
-- AtmIf/n Uni CalledAScr Address/addr,action 
-- AtmIf/n Iisp CalledAScr Address/addr,action 
-- This component specifies a calling (or called) address with an 
-- action to accept or reject a connection request which contains a 
-- matching calling (or called) address.
-- For the Calling Address Screening feature, if the specified action is 
-- accept, any call whose calling address matches that address is 
-- accepted. If the specified action is reject, any call whose calling 
-- address matches that address is rejected.
-- For the Called Address Screening feature, if the specified action is 
-- accept, any call whose called address matches that address, is 
-- accepted. If the specified action is reject, any call whose called 
-- address matches that address is rejected.
-- For both features, the incoming SVC call request is rejected if the 
-- address is not provisioned and the feature is enabled.

mscAtmIfUniCalledAScrAddr OBJECT IDENTIFIER ::= { mscAtmIfUniCalledAScr 2 }



mscAtmIfUniCalledAScrAddrRowStatusTable OBJECT-TYPE
   SYNTAX     SEQUENCE OF MscAtmIfUniCalledAScrAddrRowStatusEntry
   ACCESS     not-accessible
   STATUS     mandatory
   DESCRIPTION
     "This entry controls the addition and deletion of 
      mscAtmIfUniCalledAScrAddr components."
::= { mscAtmIfUniCalledAScrAddr 1 }

mscAtmIfUniCalledAScrAddrRowStatusEntry OBJECT-TYPE
   SYNTAX     MscAtmIfUniCalledAScrAddrRowStatusEntry
   ACCESS     not-accessible
   STATUS     mandatory
   DESCRIPTION
     "A single entry in the table represents a single 
      mscAtmIfUniCalledAScrAddr component."
   INDEX {
      mscAtmIfIndex,
      mscAtmIfUniIndex,
      mscAtmIfUniCalledAScrIndex,
      mscAtmIfUniCalledAScrAddrAddressIndex,
      mscAtmIfUniCalledAScrAddrAddressActionIndex }
::= { mscAtmIfUniCalledAScrAddrRowStatusTable 1 }

MscAtmIfUniCalledAScrAddrRowStatusEntry ::= SEQUENCE {
   mscAtmIfUniCalledAScrAddrRowStatus
      RowStatus,
   mscAtmIfUniCalledAScrAddrComponentName
      DisplayString,
   mscAtmIfUniCalledAScrAddrStorageType
      StorageType,
   mscAtmIfUniCalledAScrAddrAddressIndex
      AsciiStringIndex,
   mscAtmIfUniCalledAScrAddrAddressActionIndex
      INTEGER }

mscAtmIfUniCalledAScrAddrRowStatus OBJECT-TYPE
   SYNTAX     RowStatus 
   ACCESS     read-write
   STATUS     mandatory
   DESCRIPTION
     "This variable is used as the basis for SNMP naming of
      mscAtmIfUniCalledAScrAddr components.
      These components can be added and deleted."
::= { mscAtmIfUniCalledAScrAddrRowStatusEntry 1 }

mscAtmIfUniCalledAScrAddrComponentName OBJECT-TYPE
   SYNTAX     DisplayString 
   ACCESS     read-only
   STATUS     mandatory
   DESCRIPTION
     "This variable provides the component's string name for
      use with the ASCII Console Interface"
::= { mscAtmIfUniCalledAScrAddrRowStatusEntry 2 }

mscAtmIfUniCalledAScrAddrStorageType OBJECT-TYPE
   SYNTAX     StorageType 
   ACCESS     read-only
   STATUS     mandatory
   DESCRIPTION
     "This variable represents the storage type value for the
      mscAtmIfUniCalledAScrAddr tables."
::= { mscAtmIfUniCalledAScrAddrRowStatusEntry 4 }

mscAtmIfUniCalledAScrAddrAddressIndex OBJECT-TYPE
   SYNTAX     AsciiStringIndex (SIZE (1..40))
   ACCESS     not-accessible
   STATUS     mandatory
   DESCRIPTION
     "This variable represents an index for the mscAtmIfUniCalledAScrAddr tables."
::= { mscAtmIfUniCalledAScrAddrRowStatusEntry 10 }

mscAtmIfUniCalledAScrAddrAddressActionIndex OBJECT-TYPE
   SYNTAX     INTEGER  {
                 accept(0),
                 reject(1) }
   ACCESS     not-accessible
   STATUS     mandatory
   DESCRIPTION
     "This variable represents an index for the mscAtmIfUniCalledAScrAddr tables."
::= { mscAtmIfUniCalledAScrAddrRowStatusEntry 11 }


-- AtmIf/n VirtualPathTerminator/m Uni
-- This component represents a virtual ATM UNI interface. If this 
-- component is provisioned, neither an Iisp component, nor a Pnni 
-- component can be provisioned under the same Vpt component. If 
-- this component is deleted, then all associated Vcc components are 
-- deleted.

mscAtmIfVptUni OBJECT IDENTIFIER ::= { mscAtmIfVpt 8 }



mscAtmIfVptUniRowStatusTable OBJECT-TYPE
   SYNTAX     SEQUENCE OF MscAtmIfVptUniRowStatusEntry
   ACCESS     not-accessible
   STATUS     mandatory
   DESCRIPTION
     "This entry controls the addition and deletion of 
      mscAtmIfVptUni components."
::= { mscAtmIfVptUni 1 }

mscAtmIfVptUniRowStatusEntry OBJECT-TYPE
   SYNTAX     MscAtmIfVptUniRowStatusEntry
   ACCESS     not-accessible
   STATUS     mandatory
   DESCRIPTION
     "A single entry in the table represents a single 
      mscAtmIfVptUni component."
   INDEX {
      mscAtmIfIndex,
      mscAtmIfVptIndex,
      mscAtmIfVptUniIndex }
::= { mscAtmIfVptUniRowStatusTable 1 }

MscAtmIfVptUniRowStatusEntry ::= SEQUENCE {
   mscAtmIfVptUniRowStatus
      RowStatus,
   mscAtmIfVptUniComponentName
      DisplayString,
   mscAtmIfVptUniStorageType
      StorageType,
   mscAtmIfVptUniIndex
      NonReplicated }

mscAtmIfVptUniRowStatus OBJECT-TYPE
   SYNTAX     RowStatus 
   ACCESS     read-write
   STATUS     mandatory
   DESCRIPTION
     "This variable is used as the basis for SNMP naming of
      mscAtmIfVptUni components.
      These components can be added and deleted."
::= { mscAtmIfVptUniRowStatusEntry 1 }

mscAtmIfVptUniComponentName OBJECT-TYPE
   SYNTAX     DisplayString 
   ACCESS     read-only
   STATUS     mandatory
   DESCRIPTION
     "This variable provides the component's string name for
      use with the ASCII Console Interface"
::= { mscAtmIfVptUniRowStatusEntry 2 }

mscAtmIfVptUniStorageType OBJECT-TYPE
   SYNTAX     StorageType 
   ACCESS     read-only
   STATUS     mandatory
   DESCRIPTION
     "This variable represents the storage type value for the
      mscAtmIfVptUni tables."
::= { mscAtmIfVptUniRowStatusEntry 4 }

mscAtmIfVptUniIndex OBJECT-TYPE
   SYNTAX     NonReplicated 
   ACCESS     not-accessible
   STATUS     mandatory
   DESCRIPTION
     "This variable represents the index for the mscAtmIfVptUni tables."
::= { mscAtmIfVptUniRowStatusEntry 10 }

mscAtmIfVptUniProvTable OBJECT-TYPE
   SYNTAX     SEQUENCE OF MscAtmIfVptUniProvEntry
   ACCESS     not-accessible
   STATUS     mandatory
   DESCRIPTION
     "This group contains the provisionable attributes for the Uni 
      component."
::= { mscAtmIfVptUni 10 }

mscAtmIfVptUniProvEntry OBJECT-TYPE
   SYNTAX     MscAtmIfVptUniProvEntry
   ACCESS     not-accessible
   STATUS     mandatory
   DESCRIPTION
     "An entry in the mscAtmIfVptUniProvTable."
   INDEX {
      mscAtmIfIndex,
      mscAtmIfVptIndex,
      mscAtmIfVptUniIndex }
::= { mscAtmIfVptUniProvTable 1 }

MscAtmIfVptUniProvEntry ::= SEQUENCE {
   mscAtmIfVptUniVersion
      INTEGER,
   mscAtmIfVptUniSide
      INTEGER,
   mscAtmIfVptUniSoftPvcRetryPeriod
      Unsigned32,
   mscAtmIfVptUniSoftPvpAndPvcRetryPeriod
      Unsigned32,
   mscAtmIfVptUniSoftPvpAndPvcHoldOffTime
      Unsigned32,
   mscAtmIfVptUniLoopPrevention
      INTEGER }

mscAtmIfVptUniVersion OBJECT-TYPE
   SYNTAX     INTEGER  {
                 atmForum30(0),
                 atmForum31(1),
                 atmForum40(5) }
   ACCESS     read-write
   STATUS     mandatory
   DESCRIPTION
     "This attribute specifies which specification the UNI complies with. 
      The options are ATM FORUM 3.0, ATM FORUM 3.1 or ATM 
      FORUM 4.0. If this attribute is changed then all switched Vcc 
      components in this interface are cleared due to the fact that the two 
      versions are incompatible."
   DEFVAL     { atmForum40 }
::= { mscAtmIfVptUniProvEntry 1 }

mscAtmIfVptUniSide OBJECT-TYPE
   SYNTAX     INTEGER  {
                 network(0),
                 user(1) }
   ACCESS     read-write
   STATUS     mandatory
   DESCRIPTION
     "This attribute indicates which side the interface is, user or network."
   DEFVAL     { network }
::= { mscAtmIfVptUniProvEntry 2 }

mscAtmIfVptUniSoftPvcRetryPeriod OBJECT-TYPE
   SYNTAX     Unsigned32 (20..999999)
   ACCESS     read-write
   STATUS     obsolete
   DESCRIPTION
     "This attribute represents the time in seconds to wait between call set 
      up retries. The resolution is to the nearest 10 seconds. 
      This attribute has been obsoleted and is replaced by the 
      softPvpAndPvcRetryPeriod attribute."
   DEFVAL     { 60 }
::= { mscAtmIfVptUniProvEntry 3 }

mscAtmIfVptUniSoftPvpAndPvcRetryPeriod OBJECT-TYPE
   SYNTAX     Unsigned32 (20..999999)
   ACCESS     read-write
   STATUS     mandatory
   DESCRIPTION
     "This attribute represents the time in seconds to wait between soft 
      PVP or soft PVC call setup retries. The resolution is to the nearest 
      10 seconds."
   DEFVAL     { 60 }
::= { mscAtmIfVptUniProvEntry 4 }

mscAtmIfVptUniSoftPvpAndPvcHoldOffTime OBJECT-TYPE
   SYNTAX     Unsigned32 (0 | 50..20000)
   ACCESS     read-write
   STATUS     mandatory
   DESCRIPTION
     "This attribute specifies how long to hold off retries following a 
      release or the connection. The resolution is to the nearest 50 ms."
   DEFVAL     { 0 }
::= { mscAtmIfVptUniProvEntry 5 }

mscAtmIfVptUniLoopPrevention OBJECT-TYPE
   SYNTAX     INTEGER  {
                 disabled(0),
                 enabled(1) }
   ACCESS     read-write
   STATUS     mandatory
   DESCRIPTION
     "This attribute specifies whether loop prevention is in effect on this 
      interface.
      
      When the value is enabled, incoming calls on this interface cannot 
      be routed back out the same interface.  When the value is disabled, 
      routing of incoming calls back out the same interface is permitted.
      
      The recommended value is enabled.  The value disabled should 
      only be used if routing of incoming calls back out over this interface 
      is actually required.  As an example, the value disabled might be 
      needed if the interface is connected to an end-user multiplexing 
      device which has no routing capability.
      
      Note that setting the value to enabled prevents only routing loops 
      which involve two network nodes."
   DEFVAL     { enabled }
::= { mscAtmIfVptUniProvEntry 6 }

mscAtmIfVptUniAcctOptTable OBJECT-TYPE
   SYNTAX     SEQUENCE OF MscAtmIfVptUniAcctOptEntry
   ACCESS     not-accessible
   STATUS     mandatory
   DESCRIPTION
     "This group contains the provisionable attributes for accounting."
::= { mscAtmIfVptUni 11 }

mscAtmIfVptUniAcctOptEntry OBJECT-TYPE
   SYNTAX     MscAtmIfVptUniAcctOptEntry
   ACCESS     not-accessible
   STATUS     mandatory
   DESCRIPTION
     "An entry in the mscAtmIfVptUniAcctOptTable."
   INDEX {
      mscAtmIfIndex,
      mscAtmIfVptIndex,
      mscAtmIfVptUniIndex }
::= { mscAtmIfVptUniAcctOptTable 1 }

MscAtmIfVptUniAcctOptEntry ::= SEQUENCE {
   mscAtmIfVptUniAccountCollection
      OCTET STRING,
   mscAtmIfVptUniAccountConnectionType
      INTEGER,
   mscAtmIfVptUniAccountClass
      Unsigned32,
   mscAtmIfVptUniServiceExchange
      Unsigned32 }

mscAtmIfVptUniAccountCollection OBJECT-TYPE
   SYNTAX     OCTET STRING (SIZE (1))
   ACCESS     read-write
   STATUS     mandatory
   DESCRIPTION
     "This attribute is used to turn accounting on or off for SVC and 
      SPVC connections. It also specifies the reason(s) for which 
      accounting data is collected: billing, test, study, audit or force. 
      
      If the set of reasons is not empty then accounting records will be 
      generated by this interface in the following situations:
      - on a TODA changeover if TODA is enabled;
      - every 12 hours (per connection) if TODA is disabled;
      - on every call clear (a call record with final cell counts).
      
      If none of the reasons is present, then accounting will be 
      suppressed.
      
      The reason for collection is recorded in the accounting record, in 
      the attribute callingCollectReason or calledCollectReason as 
      appropriate.

      Description of bits:
      bill(0)
      test(1)
      study(2)
      audit(3)
      force(4)"
::= { mscAtmIfVptUniAcctOptEntry 1 }

mscAtmIfVptUniAccountConnectionType OBJECT-TYPE
   SYNTAX     INTEGER  {
                 origTerm(0),
                 intermediate(1) }
   ACCESS     read-write
   STATUS     mandatory
   DESCRIPTION
     "This attribute specifies whether accounting records generated by 
      this interface should be marked as originating, terminating or 
      intermediate. This attribute, in combination with the direction of the 
      call, determines the value of attribute connPointType of the 
      accounting record and may be used by downstream accounting 
      processes to correlate the records.
      
      If the value is origTerm then records generated for incoming calls 
      will be marked as originating and records generated for outgoing 
      calls will be marked as terminating.
      
      If the value is intermediate then records generated for all calls will 
      be marked as intermediate."
   DEFVAL     { origTerm }
::= { mscAtmIfVptUniAcctOptEntry 2 }

mscAtmIfVptUniAccountClass OBJECT-TYPE
   SYNTAX     Unsigned32 (0..255)
   ACCESS     read-write
   STATUS     mandatory
   DESCRIPTION
     "This attribute specifies the accounting class associated with the 
      interface. Its meaning is determined by the network operator.
      
      Its value is simply recorded in the accounting records generated by 
      this interface, in the attribute callingServiceType or 
      calledServiceType as appropriate."
   DEFVAL     { 0 }
::= { mscAtmIfVptUniAcctOptEntry 3 }

mscAtmIfVptUniServiceExchange OBJECT-TYPE
   SYNTAX     Unsigned32 (0..255)
   ACCESS     read-write
   STATUS     mandatory
   DESCRIPTION
     "This attribute specifies the data service exchange associated with 
      this interface. Its meaning is determined by the network operator.
      
      Its value is simply recorded in the accounting records generated by 
      this interface, in the attribute callingDse or calledDse as 
      appropriate."
   DEFVAL     { 0 }
::= { mscAtmIfVptUniAcctOptEntry 4 }

mscAtmIfVptUniVProvTable OBJECT-TYPE
   SYNTAX     SEQUENCE OF MscAtmIfVptUniVProvEntry
   ACCESS     not-accessible
   STATUS     mandatory
   DESCRIPTION
     "This group contains the provisionable attributes for the Uni 
      component which are specific to virtual UNI interfaces."
::= { mscAtmIfVptUni 12 }

mscAtmIfVptUniVProvEntry OBJECT-TYPE
   SYNTAX     MscAtmIfVptUniVProvEntry
   ACCESS     not-accessible
   STATUS     mandatory
   DESCRIPTION
     "An entry in the mscAtmIfVptUniVProvTable."
   INDEX {
      mscAtmIfIndex,
      mscAtmIfVptIndex,
      mscAtmIfVptUniIndex }
::= { mscAtmIfVptUniVProvTable 1 }

MscAtmIfVptUniVProvEntry ::= SEQUENCE {
   mscAtmIfVptUniVpci
      Unsigned32 }

mscAtmIfVptUniVpci OBJECT-TYPE
   SYNTAX     Unsigned32 (0..255)
   ACCESS     read-write
   STATUS     mandatory
   DESCRIPTION
     "This attribute specifies the Virtual Path Connection Identifier 
      (VPCI) to be used between this signalling entity and its peer. The 
      VPCI of the peer virtual UNI must have the same value for 
      switched connections to be set up across the interface."
   DEFVAL     { 0 }
::= { mscAtmIfVptUniVProvEntry 1 }


-- AtmIf/n Iisp Signalling
-- AtmIf/n Uni Signalling
-- AtmIf/n Pnni Signalling
-- AtmIf/n Vpt/m Iisp Signalling
-- AtmIf/n Vpt/m Uni Signalling
-- AtmIf/n Vpt/m Pnni Signalling
-- 
-- This component represents the signalling entities for the interface.

mscAtmIfVptUniSig OBJECT IDENTIFIER ::= { mscAtmIfVptUni 2 }



mscAtmIfVptUniSigRowStatusTable OBJECT-TYPE
   SYNTAX     SEQUENCE OF MscAtmIfVptUniSigRowStatusEntry
   ACCESS     not-accessible
   STATUS     mandatory
   DESCRIPTION
     "This entry controls the addition and deletion of 
      mscAtmIfVptUniSig components."
::= { mscAtmIfVptUniSig 1 }

mscAtmIfVptUniSigRowStatusEntry OBJECT-TYPE
   SYNTAX     MscAtmIfVptUniSigRowStatusEntry
   ACCESS     not-accessible
   STATUS     mandatory
   DESCRIPTION
     "A single entry in the table represents a single 
      mscAtmIfVptUniSig component."
   INDEX {
      mscAtmIfIndex,
      mscAtmIfVptIndex,
      mscAtmIfVptUniIndex,
      mscAtmIfVptUniSigIndex }
::= { mscAtmIfVptUniSigRowStatusTable 1 }

MscAtmIfVptUniSigRowStatusEntry ::= SEQUENCE {
   mscAtmIfVptUniSigRowStatus
      RowStatus,
   mscAtmIfVptUniSigComponentName
      DisplayString,
   mscAtmIfVptUniSigStorageType
      StorageType,
   mscAtmIfVptUniSigIndex
      NonReplicated }

mscAtmIfVptUniSigRowStatus OBJECT-TYPE
   SYNTAX     RowStatus 
   ACCESS     read-only
   STATUS     mandatory
   DESCRIPTION
     "This variable is used as the basis for SNMP naming of
      mscAtmIfVptUniSig components.
      These components cannot be added nor deleted."
::= { mscAtmIfVptUniSigRowStatusEntry 1 }

mscAtmIfVptUniSigComponentName OBJECT-TYPE
   SYNTAX     DisplayString 
   ACCESS     read-only
   STATUS     mandatory
   DESCRIPTION
     "This variable provides the component's string name for
      use with the ASCII Console Interface"
::= { mscAtmIfVptUniSigRowStatusEntry 2 }

mscAtmIfVptUniSigStorageType OBJECT-TYPE
   SYNTAX     StorageType 
   ACCESS     read-only
   STATUS     mandatory
   DESCRIPTION
     "This variable represents the storage type value for the
      mscAtmIfVptUniSig tables."
::= { mscAtmIfVptUniSigRowStatusEntry 4 }

mscAtmIfVptUniSigIndex OBJECT-TYPE
   SYNTAX     NonReplicated 
   ACCESS     not-accessible
   STATUS     mandatory
   DESCRIPTION
     "This variable represents the index for the mscAtmIfVptUniSig tables."
::= { mscAtmIfVptUniSigRowStatusEntry 10 }

mscAtmIfVptUniSigProvTable OBJECT-TYPE
   SYNTAX     SEQUENCE OF MscAtmIfVptUniSigProvEntry
   ACCESS     not-accessible
   STATUS     mandatory
   DESCRIPTION
     "This attribute group contains the provisionable attributes for the 
      Signalling component."
::= { mscAtmIfVptUniSig 10 }

mscAtmIfVptUniSigProvEntry OBJECT-TYPE
   SYNTAX     MscAtmIfVptUniSigProvEntry
   ACCESS     not-accessible
   STATUS     mandatory
   DESCRIPTION
     "An entry in the mscAtmIfVptUniSigProvTable."
   INDEX {
      mscAtmIfIndex,
      mscAtmIfVptIndex,
      mscAtmIfVptUniIndex,
      mscAtmIfVptUniSigIndex }
::= { mscAtmIfVptUniSigProvTable 1 }

MscAtmIfVptUniSigProvEntry ::= SEQUENCE {
   mscAtmIfVptUniSigVci
      Unsigned32,
   mscAtmIfVptUniSigAddressConversion
      INTEGER,
   mscAtmIfVptUniSigOperatingMode
      INTEGER }

mscAtmIfVptUniSigVci OBJECT-TYPE
   SYNTAX     Unsigned32 (0..65535)
   ACCESS     read-write
   STATUS     mandatory
   DESCRIPTION
     "This attribute specifies the signalling channel number."
   DEFVAL     { 5 }
::= { mscAtmIfVptUniSigProvEntry 1 }

mscAtmIfVptUniSigAddressConversion OBJECT-TYPE
   SYNTAX     INTEGER  {
                 none(0),
                 nativeE164(1),
                 nsap(2) }
   ACCESS     read-write
   STATUS     mandatory
   DESCRIPTION
     "This attribute specifies the address conversion on the outgoing 
      signalling PDUs. The options are none, nativeE164, or nsap. The 
      none option is the default and if this option is chosen then nothing 
      is done to the address information element (IE) in the outgoing 
      signalling message. If nativeE164 option is chosen, then only 
      NSAP encapsulated E.164 addresses with zeros in the ESI are 
      converted to native E.164 format in the outgoing signalling 
      message. If the NSAP address is not encapsulated E.164 or the ESI 
      field is not zeros and the nativeE164 option is chosen, then the call 
      is cleared. If the nsap option is chosen, then native E.164 addresses 
      are converted to NSAP E.164 with zeros in the ESI field; otherwise 
      the address is in NSAP format and is not changed."
   DEFVAL     { none }
::= { mscAtmIfVptUniSigProvEntry 2 }

mscAtmIfVptUniSigOperatingMode OBJECT-TYPE
   SYNTAX     INTEGER  {
                 normal(0),
                 provisionedOnly(1) }
   ACCESS     read-write
   STATUS     mandatory
   DESCRIPTION
     "This attribute specifies the operating mode of the signaling channel. 				
      provisionedOnly indicates that only SPVCs and SPVPs are 
      supported on the interface and SVCs are not supported. This value 
      is permitted only on UNI interfaces.
      normal indicates that SVCs, SPVCs, and SPVPs are supported on 
      the interface."
   DEFVAL     { normal }
::= { mscAtmIfVptUniSigProvEntry 3 }

mscAtmIfVptUniSigStateTable OBJECT-TYPE
   SYNTAX     SEQUENCE OF MscAtmIfVptUniSigStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscAtmIfVptUniSig 11 }

mscAtmIfVptUniSigStateEntry OBJECT-TYPE
   SYNTAX     MscAtmIfVptUniSigStateEntry
   ACCESS     not-accessible
   STATUS     mandatory
   DESCRIPTION
     "An entry in the mscAtmIfVptUniSigStateTable."
   INDEX {
      mscAtmIfIndex,
      mscAtmIfVptIndex,
      mscAtmIfVptUniIndex,
      mscAtmIfVptUniSigIndex }
::= { mscAtmIfVptUniSigStateTable 1 }

MscAtmIfVptUniSigStateEntry ::= SEQUENCE {
   mscAtmIfVptUniSigAdminState
      INTEGER,
   mscAtmIfVptUniSigOperationalState
      INTEGER,
   mscAtmIfVptUniSigUsageState
      INTEGER }

mscAtmIfVptUniSigAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscAtmIfVptUniSigStateEntry 1 }

mscAtmIfVptUniSigOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscAtmIfVptUniSigStateEntry 2 }

mscAtmIfVptUniSigUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscAtmIfVptUniSigStateEntry 3 }

mscAtmIfVptUniSigOperTable OBJECT-TYPE
   SYNTAX     SEQUENCE OF MscAtmIfVptUniSigOperEntry
   ACCESS     not-accessible
   STATUS     mandatory
   DESCRIPTION
     "This attribute contains the operational attributes for the 
      AtmSignalling component."
::= { mscAtmIfVptUniSig 12 }

mscAtmIfVptUniSigOperEntry OBJECT-TYPE
   SYNTAX     MscAtmIfVptUniSigOperEntry
   ACCESS     not-accessible
   STATUS     mandatory
   DESCRIPTION
     "An entry in the mscAtmIfVptUniSigOperTable."
   INDEX {
      mscAtmIfIndex,
      mscAtmIfVptIndex,
      mscAtmIfVptUniIndex,
      mscAtmIfVptUniSigIndex }
::= { mscAtmIfVptUniSigOperTable 1 }

MscAtmIfVptUniSigOperEntry ::= SEQUENCE {
   mscAtmIfVptUniSigLastTxCauseCode
      Unsigned32,
   mscAtmIfVptUniSigLastTxDiagCode
      Hex,
   mscAtmIfVptUniSigLastRxCauseCode
      Unsigned32,
   mscAtmIfVptUniSigLastRxDiagCode
      Hex }

mscAtmIfVptUniSigLastTxCauseCode OBJECT-TYPE
   SYNTAX     Unsigned32 (0..255)
   ACCESS     read-only
   STATUS     mandatory
   DESCRIPTION
     "This attribute indicates the cause code in the last transmitted 
      signalling message that contains the CAUSE information element. 
      The cause code is used to describe the reason for generating certain 
      signalling messages."
::= { mscAtmIfVptUniSigOperEntry 1 }

mscAtmIfVptUniSigLastTxDiagCode OBJECT-TYPE
   SYNTAX     Hex (0..255)
   ACCESS     read-only
   STATUS     mandatory
   DESCRIPTION
     "This attribute contains the diagnostic code in the last transmitted 
      signalling message. The diagnostic code is contained in the CAUSE 
      information element and identifies an information element type or 
      timer type. The diagnostic code is present only if a procedural error 
      is detected by the signalling protocol. A diagnostic code is always 
      accompanied by the cause code. If there is no failure, this attribute 
      is set to 0."
::= { mscAtmIfVptUniSigOperEntry 2 }

mscAtmIfVptUniSigLastRxCauseCode OBJECT-TYPE
   SYNTAX     Unsigned32 (0..255)
   ACCESS     read-only
   STATUS     mandatory
   DESCRIPTION
     "This attribute contains the cause code in the last received signalling 
      message that contains the CAUSE information element. The cause 
      code is used to describe the reason for generating certain signalling 
      messages."
::= { mscAtmIfVptUniSigOperEntry 3 }

mscAtmIfVptUniSigLastRxDiagCode OBJECT-TYPE
   SYNTAX     Hex (0..255)
   ACCESS     read-only
   STATUS     mandatory
   DESCRIPTION
     "This attribute contains the diagnostic code in the last received 
      signalling message. The diagnostic code is contained in the CAUSE 
      information element and identifies an information element type or 
      timer type. The diagnostic code is present only if a procedural error 
      is detected by the signalling protocol. A diagnostic code is always 
      accompanied by the cause code. If there is no failure, this attribute 
      is set to 0."
::= { mscAtmIfVptUniSigOperEntry 4 }

mscAtmIfVptUniSigStatsTable OBJECT-TYPE
   SYNTAX     SEQUENCE OF MscAtmIfVptUniSigStatsEntry
   ACCESS     not-accessible
   STATUS     mandatory
   DESCRIPTION
     "This attribute group contains the statistics associated with the 
      AtmSignalling component."
::= { mscAtmIfVptUniSig 13 }

mscAtmIfVptUniSigStatsEntry OBJECT-TYPE
   SYNTAX     MscAtmIfVptUniSigStatsEntry
   ACCESS     not-accessible
   STATUS     mandatory
   DESCRIPTION
     "An entry in the mscAtmIfVptUniSigStatsTable."
   INDEX {
      mscAtmIfIndex,
      mscAtmIfVptIndex,
      mscAtmIfVptUniIndex,
      mscAtmIfVptUniSigIndex }
::= { mscAtmIfVptUniSigStatsTable 1 }

MscAtmIfVptUniSigStatsEntry ::= SEQUENCE {
   mscAtmIfVptUniSigCurrentConnections
      Counter32,
   mscAtmIfVptUniSigPeakConnections
      Gauge32,
   mscAtmIfVptUniSigSuccessfulConnections
      Counter32,
   mscAtmIfVptUniSigFailedConnections
      Counter32,
   mscAtmIfVptUniSigTxPdus
      Counter32,
   mscAtmIfVptUniSigRxPdus
      Counter32,
   mscAtmIfVptUniSigCurrentPmpConnections
      Gauge32,
   mscAtmIfVptUniSigPeakPmpConnections
      Gauge32,
   mscAtmIfVptUniSigSuccessfulPmpConnections
      Counter32,
   mscAtmIfVptUniSigFailedPmpConnections
      Counter32,
   mscAtmIfVptUniSigNewCurrentConnections
      Gauge32 }

mscAtmIfVptUniSigCurrentConnections OBJECT-TYPE
   SYNTAX     Counter32 
   ACCESS     read-only
   STATUS     obsolete
   DESCRIPTION
     "This attribute indicates the total number of currently active 
      connections."
::= { mscAtmIfVptUniSigStatsEntry 1 }

mscAtmIfVptUniSigPeakConnections OBJECT-TYPE
   SYNTAX     Gauge32 (0..4294967295)
   ACCESS     read-only
   STATUS     mandatory
   DESCRIPTION
     "This attribute indicates the high water mark of active point-to-
      point and point-to-multipoint connections."
::= { mscAtmIfVptUniSigStatsEntry 2 }

mscAtmIfVptUniSigSuccessfulConnections OBJECT-TYPE
   SYNTAX     Counter32 
   ACCESS     read-only
   STATUS     mandatory
   DESCRIPTION
     "This attribute counts the total number of switched point-to-
      point and point-to-multipoint connections that were successfully 
      established. The counter wraps to 0 when the maximum value is 
      exceeded."
::= { mscAtmIfVptUniSigStatsEntry 3 }

mscAtmIfVptUniSigFailedConnections OBJECT-TYPE
   SYNTAX     Counter32 
   ACCESS     read-only
   STATUS     mandatory
   DESCRIPTION
     "This attribute counts the total number of switched connections that 
      were not successfully established.The counter wraps to 0 when the 
      maximum value is exceeded."
::= { mscAtmIfVptUniSigStatsEntry 4 }

mscAtmIfVptUniSigTxPdus OBJECT-TYPE
   SYNTAX     Counter32 
   ACCESS     read-only
   STATUS     mandatory
   DESCRIPTION
     "This attribute counts the number of transmitted signalling 
      PDUs.The counter wraps to 0 when the maximum value is 
      exceeded."
::= { mscAtmIfVptUniSigStatsEntry 5 }

mscAtmIfVptUniSigRxPdus OBJECT-TYPE
   SYNTAX     Counter32 
   ACCESS     read-only
   STATUS     mandatory
   DESCRIPTION
     "This attribute counts the number of received signalling PDUs.The 
      counter wraps to 0 when the maximum value is exceeded."
::= { mscAtmIfVptUniSigStatsEntry 6 }

mscAtmIfVptUniSigCurrentPmpConnections OBJECT-TYPE
   SYNTAX     Gauge32 (0..4294967295)
   ACCESS     read-only
   STATUS     mandatory
   DESCRIPTION
     "This attribute indicates the number of currently active point-to-
      multipoint connections."
::= { mscAtmIfVptUniSigStatsEntry 7 }

mscAtmIfVptUniSigPeakPmpConnections OBJECT-TYPE
   SYNTAX     Gauge32 (0..4294967295)
   ACCESS     read-only
   STATUS     mandatory
   DESCRIPTION
     "This attribute indicates the high water mark of active point-to-
      multipoint connections."
::= { mscAtmIfVptUniSigStatsEntry 8 }

mscAtmIfVptUniSigSuccessfulPmpConnections OBJECT-TYPE
   SYNTAX     Counter32 
   ACCESS     read-only
   STATUS     mandatory
   DESCRIPTION
     "This attribute counts the total number of switched point-to-
      multipoint connections that were successfully established. 
      The counter wraps to 0 when the maximum value is 
      exceeded."
::= { mscAtmIfVptUniSigStatsEntry 9 }

mscAtmIfVptUniSigFailedPmpConnections OBJECT-TYPE
   SYNTAX     Counter32 
   ACCESS     read-only
   STATUS     mandatory
   DESCRIPTION
     "This attribute counts the number of switched point-to-
      multipoint connections that were not successfully 
      established.The counter wraps to 0 when the maximum value 
      is exceeded."
::= { mscAtmIfVptUniSigStatsEntry 10 }

mscAtmIfVptUniSigNewCurrentConnections OBJECT-TYPE
   SYNTAX     Gauge32 (0..4294967295)
   ACCESS     read-only
   STATUS     mandatory
   DESCRIPTION
     "This attribute indicates the total number of currently active point-to-
      point and point-to-multipoint connections."
::= { mscAtmIfVptUniSigStatsEntry 11 }


-- AtmIf/n Uni Sig VirtualChannelDescriptor
-- AtmIf/n Uni Ilmi VirtualChannelDescriptor
-- AtmIf/n Iisp Sig VirtualChannelDescriptor
-- AtmIf/n Pnni Sig VirtualChannelDescriptor
-- AtmIf/n Pnni Rcc VirtualChannelDescriptor
-- AtmIf/n Vpt/m Uni Sig VirtualChannelDescriptor
-- AtmIf/n Vpt/m Iisp Sig VirtualChannelDescriptor
-- AtmIf/n Vpt/m Pnni Sig VirtualChannelDescriptor
-- AtmIf/n Vpt/m Pnni Rcc VirtualChannelDescriptor
-- 
-- This component contains the provisionable traffic parameters for a 
-- control channel (Sig, Ilmi or Rcc component).

mscAtmIfVptUniSigVcd OBJECT IDENTIFIER ::= { mscAtmIfVptUniSig 2 }



mscAtmIfVptUniSigVcdRowStatusTable OBJECT-TYPE
   SYNTAX     SEQUENCE OF MscAtmIfVptUniSigVcdRowStatusEntry
   ACCESS     not-accessible
   STATUS     mandatory
   DESCRIPTION
     "This entry controls the addition and deletion of 
      mscAtmIfVptUniSigVcd components."
::= { mscAtmIfVptUniSigVcd 1 }

mscAtmIfVptUniSigVcdRowStatusEntry OBJECT-TYPE
   SYNTAX     MscAtmIfVptUniSigVcdRowStatusEntry
   ACCESS     not-accessible
   STATUS     mandatory
   DESCRIPTION
     "A single entry in the table represents a single 
      mscAtmIfVptUniSigVcd component."
   INDEX {
      mscAtmIfIndex,
      mscAtmIfVptIndex,
      mscAtmIfVptUniIndex,
      mscAtmIfVptUniSigIndex,
      mscAtmIfVptUniSigVcdIndex }
::= { mscAtmIfVptUniSigVcdRowStatusTable 1 }

MscAtmIfVptUniSigVcdRowStatusEntry ::= SEQUENCE {
   mscAtmIfVptUniSigVcdRowStatus
      RowStatus,
   mscAtmIfVptUniSigVcdComponentName
      DisplayString,
   mscAtmIfVptUniSigVcdStorageType
      StorageType,
   mscAtmIfVptUniSigVcdIndex
      NonReplicated }

mscAtmIfVptUniSigVcdRowStatus OBJECT-TYPE
   SYNTAX     RowStatus 
   ACCESS     read-write
   STATUS     mandatory
   DESCRIPTION
     "This variable is used as the basis for SNMP naming of
      mscAtmIfVptUniSigVcd components.
      These components can be added and deleted."
::= { mscAtmIfVptUniSigVcdRowStatusEntry 1 }

mscAtmIfVptUniSigVcdComponentName OBJECT-TYPE
   SYNTAX     DisplayString 
   ACCESS     read-only
   STATUS     mandatory
   DESCRIPTION
     "This variable provides the component's string name for
      use with the ASCII Console Interface"
::= { mscAtmIfVptUniSigVcdRowStatusEntry 2 }

mscAtmIfVptUniSigVcdStorageType OBJECT-TYPE
   SYNTAX     StorageType 
   ACCESS     read-only
   STATUS     mandatory
   DESCRIPTION
     "This variable represents the storage type value for the
      mscAtmIfVptUniSigVcd tables."
::= { mscAtmIfVptUniSigVcdRowStatusEntry 4 }

mscAtmIfVptUniSigVcdIndex OBJECT-TYPE
   SYNTAX     NonReplicated 
   ACCESS     not-accessible
   STATUS     mandatory
   DESCRIPTION
     "This variable represents the index for the mscAtmIfVptUniSigVcd tables."
::= { mscAtmIfVptUniSigVcdRowStatusEntry 10 }

mscAtmIfVptUniSigVcdProvTable OBJECT-TYPE
   SYNTAX     SEQUENCE OF MscAtmIfVptUniSigVcdProvEntry
   ACCESS     not-accessible
   STATUS     mandatory
   DESCRIPTION
     "This group contains the provisionable traffic attributes for a control 
      channel."
::= { mscAtmIfVptUniSigVcd 10 }

mscAtmIfVptUniSigVcdProvEntry OBJECT-TYPE
   SYNTAX     MscAtmIfVptUniSigVcdProvEntry
   ACCESS     not-accessible
   STATUS     mandatory
   DESCRIPTION
     "An entry in the mscAtmIfVptUniSigVcdProvTable."
   INDEX {
      mscAtmIfIndex,
      mscAtmIfVptIndex,
      mscAtmIfVptUniIndex,
      mscAtmIfVptUniSigIndex,
      mscAtmIfVptUniSigVcdIndex }
::= { mscAtmIfVptUniSigVcdProvTable 1 }

MscAtmIfVptUniSigVcdProvEntry ::= SEQUENCE {
   mscAtmIfVptUniSigVcdTrafficDescType
      INTEGER,
   mscAtmIfVptUniSigVcdAtmServiceCategory
      INTEGER,
   mscAtmIfVptUniSigVcdWeight
      Unsigned32,
   mscAtmIfVptUniSigVcdQosClass
      INTEGER,
   mscAtmIfVptUniSigVcdTrafficShaping
      INTEGER,
   mscAtmIfVptUniSigVcdUnshapedTransmitQueueing
      INTEGER,
   mscAtmIfVptUniSigVcdUsageParameterControl
      INTEGER }

mscAtmIfVptUniSigVcdTrafficDescType OBJECT-TYPE
   SYNTAX     INTEGER  {
                 n3(3),
                 n6(6),
                 n7(7),
                 n8(8) }
   ACCESS     read-write
   STATUS     mandatory
   DESCRIPTION
     "This attribute specifies the type of traffic management which is 
      applied to both the transmit and receive direction of this connection 
      as defined in the ATM Forum. The trafficDescType determines the 
      number and meaning of the parameters in the trafficDescParm 
      attribute."
   DEFVAL     { n6 }
::= { mscAtmIfVptUniSigVcdProvEntry 1 }

mscAtmIfVptUniSigVcdAtmServiceCategory OBJECT-TYPE
   SYNTAX     INTEGER  {
                 unspecifiedBitRate(0),
                 constantBitRate(1),
                 rtVariableBitRate(2),
                 nrtVariableBitRate(3) }
   ACCESS     read-write
   STATUS     mandatory
   DESCRIPTION
     "This attribute specifies the ATM service category for both directions 
      of the connection. 
      
      The constantBitRate service category is intended for real time 
      applications, that is those requiring tightly constrained delay and 
      delay variation, as would be appropriate for voice and video 
      applications. The consistent availability of a fixed quantity of 
      bandwidth is considered appropriate for CBR service. Cells which 
      are delayed beyond the value specified by CellTransfer Delay are 
      assumed to be of significantly reduce value to the application.
      
      The rtVariableBitRate service category is intended for real time 
      applications, that is those requiring tightly constrained delay and 
      delay variation, as would be appropriate for voice and video 
      applications. Sources are expected to transmit at a rate which varies 
      with time. Equivalently, the source can be described as 'bursty'. 
      Cells which are delayed beyond the value specified by CTD are 
      assumed to be of significantly reduced value to the application. Real 
      time VBR service may support statistical multiplexing of real time 
      sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections.
      
      The unspecifiedBitRate service is intended for non-real time 
      applications; that is, those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
   DEFVAL     { rtVariableBitRate }
::= { mscAtmIfVptUniSigVcdProvEntry 3 }

mscAtmIfVptUniSigVcdWeight OBJECT-TYPE
   SYNTAX     Unsigned32 (0 | 1..4095 | 65535)
   ACCESS     read-write
   STATUS     mandatory
   DESCRIPTION
     "This attribute specifies an override for the weight of this unshaped 
      connection. This attribute is ignored for shaped connections, for 
      ABR connections, for connections on a CQC-based ATM FP and 
      basic VPTs. 
      
      When the value is set to sameAsCa, the weight is determined by the 
      weight policy attribute under the CA service category component 
      for all but standard VPT VCCs. For standard VPT VCCs, the 
      weight is determined by the VCC's service category, when the value 
      is set to sameAsCa.
      
      When this attribute is set to a value from 1 to 4095, that value is 
      used for the weight policy of this connection relative to other 
      connections. For all but standard VPT VCCs, weight policy 
      determines the proportion of transit cell opportunities which are 
      allocated to this connection, compared to other connections in the 
      same service category. For standard VPT VCCs, weight policy 
      determines the proportion of transmit cell opportunities which are 
      allocated to this connection, compared to other connections 
      associated with the VPT.
      
      When the value is set to upToQueueLimit, the weight policy is 
      limited only by the txQueueLimit.

      VALUES (

      0 = upToQueueLimit

      65535 = sameAsCa

      )"
   DEFVAL     { 65535 }
::= { mscAtmIfVptUniSigVcdProvEntry 4 }

mscAtmIfVptUniSigVcdQosClass OBJECT-TYPE
   SYNTAX     INTEGER  {
                 n0(0),
                 n1(1),
                 n2(2),
                 n3(3),
                 n4(4) }
   ACCESS     read-write
   STATUS     mandatory
   DESCRIPTION
     "This attribute specifies the quality of service for both the forward 
      and backward direction for this connection.
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters."
   DEFVAL     { n2 }
::= { mscAtmIfVptUniSigVcdProvEntry 21 }

mscAtmIfVptUniSigVcdTrafficShaping OBJECT-TYPE
   SYNTAX     INTEGER  {
                 disabled(1),
                 sameAsCa(2) }
   ACCESS     read-write
   STATUS     mandatory
   DESCRIPTION
     "This attribute specifies whether this connection uses traffic shaping 
      when transmitting traffic to the ATM interface.
      
      When sameAsCa is selected, traffic shaping for this connection is 
      based on the trafficShaping attribute of the connection's service 
      category component under the AtmIf CA. If the service category has 
      traffic shaping enabled, then traffic shaping is enabled for the 
      connection. Note that enabling traffic shaping may have no effect 
      under certain cases. These cases are listed in the description of the 
      trafficShaping operational attribute, which is under the Vcc Tm and 
      Vpc Tm components.
      
      When disabled is selected, traffic shaping for this connection is 
      disabled."
   DEFVAL     { disabled }
::= { mscAtmIfVptUniSigVcdProvEntry 50 }

mscAtmIfVptUniSigVcdUnshapedTransmitQueueing OBJECT-TYPE
   SYNTAX     INTEGER  {
                 common(1),
                 sameAsCa(3) }
   ACCESS     read-write
   STATUS     mandatory
   DESCRIPTION
     "This attribute only applies when this connection is unshaped. This 
      attribute specifies the transmit queueing method for this connection 
      if it is unshaped. Refer to the unshapedTransmitQueueing attribute 
      under the AtmIf CA service category subcomponent for more details 
      on the meaning of this attribute. 
      
      When this attribute is set to sameAsCa, the transmit queueing 
      method for the connection is based on the 
      unshapedTransmitQueueing attribute of the connection's service 
      category component under the ConnectionAdministrator. 
      
      When this attribute is set to common, transmit traffic on this 
      unshaped connection is destined for the common queue. 
      
      The value sameAsInterface is for migration from previous software 
      releases, but should no longer be used"
   DEFVAL     { sameAsCa }
::= { mscAtmIfVptUniSigVcdProvEntry 60 }

mscAtmIfVptUniSigVcdUsageParameterControl OBJECT-TYPE
   SYNTAX     INTEGER  {
                 disabled(1),
                 sameAsCa(2) }
   ACCESS     read-write
   STATUS     mandatory
   DESCRIPTION
     "This attribute specifies whether this connection enforces usage 
      parameter control when receiving traffic from the ATM interface.
      
      When sameAsCa is selected, UPC for the connection is based on 
      the usageParameterControl attribute of the connection's service 
      category component under the ConnectionAdministrator. If the 
      service category has UPC enabled, then UPC is enabled for the 
      connection. Note that enabling UPC may have no effect under 
      certain cases. These cases are listed in the description of the 
      usageParameterControl operational attribute, which is under the 
      Vcc Tm or Vpc Tm component.
      
      When disabled is selected, UPC for this connection is disabled.
      
      The value sameAsInterface is for migration from previous software 
      releases, but should no longer be used"
   DEFVAL     { disabled }
::= { mscAtmIfVptUniSigVcdProvEntry 70 }

mscAtmIfVptUniSigVcdTdpTable OBJECT-TYPE
   SYNTAX     SEQUENCE OF MscAtmIfVptUniSigVcdTdpEntry
   ACCESS     not-accessible
   STATUS     mandatory
   DESCRIPTION
     "This attribute is a vector of five traffic parameters whose meanings 
      are defined by the trafficDescType attribute. The values of peak cell 
      rate (PCR), sustained cell rate (SCR) and requested shaping rate are 
      expressed in cell/s. Maximum burst size (MBS) is expressed in 
      cells. CDVT is expressed in microseconds. The values of PCR, 
      SCR, MBS and CDVT are used for connection admission control 
      (CAC). The value of CDVT is only used for connections where the 
      atmServiceCategory is constantBitRate. For all other values of 
      atmServiceCategory, CDVT is ignored. The values of PCR, SCR 
      and requested shaping rate are used to determine the actual shaping 
      rate where traffic shaping is enabled.
      
      When trafficDescType is 3, parameter 1 represents the PCR for CLP 
      equal to 0 and 1 traffic; parameter 4 represents the CDVT; and 
      parameter 5 represents the requested shaping rate. A non-zero value 
      in parameter 5 overrides any value in parameter 1. This result is 
      used as the PCR. Parameter 1 must be non-zero. Parameters 2 and 3 
      must be zero.
      
      When trafficDescType is 6, parameter 1 represents the PCR for CLP 
      equal to 0 and 1 traffic; parameter 2 represents the SCR for CLP 
      equal to 0 and 1 traffic; parameter 3 represents the MBS for CLP 
      equal to 0 and 1 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      When trafficDescType is 7, parameter 1 represents the PCR for CLP 
      equal to 0 and 1 traffic; parameter 2 represents the SCR for CLP 
      equal to 0 with cell discard; parameter 3 represents the MBS for 
      CLP equal to 0 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      When trafficDescType is 8, parameter 1 represents the PCR for CLP 
      equal to 0 and 1 traffic; parameter 2 represents the SCR for CLP 
      equal to 0 traffic with cell tagging; parameter 3 represents the MBS 
      for CLP equal to 0 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      Whenever it is valid for PCR to be specified, parameter 5 may also 
      be used to specify a requested shaping rate. A non-zero value in 
      parameter 5 overrides the value in parameter 1 and is used as the 
      peak cell rate in calculations of CAC and shaping rate.
      
      For trafficDescType 3 the traffic is shaped at the next rate less than 
      the PCR. 
      
      For trafficDescType 6, 7, and 8, the traffic is shaped at the highest 
      available rate which is between PCR and SCR. However, if there is 
      no available shaping rate between PCR and SCR, traffic is shaped at 
      the next rate above the PCR."
::= { mscAtmIfVptUniSigVcd 387 }

mscAtmIfVptUniSigVcdTdpEntry OBJECT-TYPE
   SYNTAX     MscAtmIfVptUniSigVcdTdpEntry
   ACCESS     not-accessible
   STATUS     mandatory
   DESCRIPTION
     "An entry in the mscAtmIfVptUniSigVcdTdpTable."
   INDEX {
      mscAtmIfIndex,
      mscAtmIfVptIndex,
      mscAtmIfVptUniIndex,
      mscAtmIfVptUniSigIndex,
      mscAtmIfVptUniSigVcdIndex,
      mscAtmIfVptUniSigVcdTdpIndex }
::= { mscAtmIfVptUniSigVcdTdpTable 1 }

MscAtmIfVptUniSigVcdTdpEntry ::= SEQUENCE {
   mscAtmIfVptUniSigVcdTdpIndex
      Integer32,
   mscAtmIfVptUniSigVcdTdpValue
      Unsigned32 }

mscAtmIfVptUniSigVcdTdpIndex OBJECT-TYPE
   SYNTAX     Integer32 (1..5)
   ACCESS     not-accessible
   STATUS     mandatory
   DESCRIPTION
     "This variable represents the mscAtmIfVptUniSigVcdTdpTable
      specific index for the mscAtmIfVptUniSigVcdTdpTable."
::= { mscAtmIfVptUniSigVcdTdpEntry 1 }

mscAtmIfVptUniSigVcdTdpValue OBJECT-TYPE
   SYNTAX     Unsigned32 (0..2147483647)
   ACCESS     read-write
   STATUS     mandatory
   DESCRIPTION
     "This variable represents an individual value for the
      mscAtmIfVptUniSigVcdTdpTable."
::= { mscAtmIfVptUniSigVcdTdpEntry 2 }


-- AtmIf/n Iisp Address/address,type
-- AtmIf/n Uni Address/address,type
-- AtmIf/n Pnni Address/address,type
-- AtmIf/n Vpt/m Iisp Address/address,type
-- AtmIf/n Vpt/m Uni Address/address,type
-- AtmIf/n Vpt/m Pnni Address/address,type
-- 
-- This component represents an address (dynamic or static) 
-- associated with the interface. The index is a string of 1 to 40 hex 
-- digits or a single wildcard ('?'), and a type. The type identifies 
-- whether the Address component is for a primary, alternate, 
-- registered, or default address. 
-- 
-- The types primary and alternate are used for provisioned addresses. 
-- The type registered is used for dynamic addresses registered 
-- through ILMI. The type default is used for Soft PVP and Soft PVC 
-- addresses.Virtual interfaces do not have addresses of 
-- type default.
-- 
-- The wildcard is only valid for provisioned addresses. If the address 
-- is a single wildcard, then that indicates that the interface supports 
-- all addresses. If there is no better match, then this interface may be 
-- chosen in the routing. If there is more than one interface with a 
-- single wildcard static address, then the choice is driven through a 
-- round robin algorithm. 
-- 
-- The round robin algorithm tries the primary routes and then the 
-- alternate routes if none of the primary routes succeed.
-- If this node participates in a PNNI hierarchy, then a PnniInfo 
-- subcomponent can be provisioned under the AtmAddress 
-- component to specify the level to which this address will be 
-- advertised.

mscAtmIfVptUniAddr OBJECT IDENTIFIER ::= { mscAtmIfVptUni 3 }



mscAtmIfVptUniAddrRowStatusTable OBJECT-TYPE
   SYNTAX     SEQUENCE OF MscAtmIfVptUniAddrRowStatusEntry
   ACCESS     not-accessible
   STATUS     mandatory
   DESCRIPTION
     "This entry controls the addition and deletion of 
      mscAtmIfVptUniAddr components."
::= { mscAtmIfVptUniAddr 1 }

mscAtmIfVptUniAddrRowStatusEntry OBJECT-TYPE
   SYNTAX     MscAtmIfVptUniAddrRowStatusEntry
   ACCESS     not-accessible
   STATUS     mandatory
   DESCRIPTION
     "A single entry in the table represents a single 
      mscAtmIfVptUniAddr component."
   INDEX {
      mscAtmIfIndex,
      mscAtmIfVptIndex,
      mscAtmIfVptUniIndex,
      mscAtmIfVptUniAddrAddressIndex,
      mscAtmIfVptUniAddrAddressTypeIndex }
::= { mscAtmIfVptUniAddrRowStatusTable 1 }

MscAtmIfVptUniAddrRowStatusEntry ::= SEQUENCE {
   mscAtmIfVptUniAddrRowStatus
      RowStatus,
   mscAtmIfVptUniAddrComponentName
      DisplayString,
   mscAtmIfVptUniAddrStorageType
      StorageType,
   mscAtmIfVptUniAddrAddressIndex
      AsciiStringIndex,
   mscAtmIfVptUniAddrAddressTypeIndex
      INTEGER }

mscAtmIfVptUniAddrRowStatus OBJECT-TYPE
   SYNTAX     RowStatus 
   ACCESS     read-write
   STATUS     mandatory
   DESCRIPTION
     "This variable is used as the basis for SNMP naming of
      mscAtmIfVptUniAddr components.
      These components can be added and deleted."
::= { mscAtmIfVptUniAddrRowStatusEntry 1 }

mscAtmIfVptUniAddrComponentName OBJECT-TYPE
   SYNTAX     DisplayString 
   ACCESS     read-only
   STATUS     mandatory
   DESCRIPTION
     "This variable provides the component's string name for
      use with the ASCII Console Interface"
::= { mscAtmIfVptUniAddrRowStatusEntry 2 }

mscAtmIfVptUniAddrStorageType OBJECT-TYPE
   SYNTAX     StorageType 
   ACCESS     read-only
   STATUS     mandatory
   DESCRIPTION
     "This variable represents the storage type value for the
      mscAtmIfVptUniAddr tables."
::= { mscAtmIfVptUniAddrRowStatusEntry 4 }

mscAtmIfVptUniAddrAddressIndex OBJECT-TYPE
   SYNTAX     AsciiStringIndex (SIZE (1..40))
   ACCESS     not-accessible
   STATUS     mandatory
   DESCRIPTION
     "This variable represents an index for the mscAtmIfVptUniAddr tables."
::= { mscAtmIfVptUniAddrRowStatusEntry 10 }

mscAtmIfVptUniAddrAddressTypeIndex OBJECT-TYPE
   SYNTAX     INTEGER  {
                 primary(0),
                 alternate(1),
                 registered(2),
                 default(3) }
   ACCESS     not-accessible
   STATUS     mandatory
   DESCRIPTION
     "This variable represents an index for the mscAtmIfVptUniAddr tables."
::= { mscAtmIfVptUniAddrRowStatusEntry 11 }

mscAtmIfVptUniAddrOperTable OBJECT-TYPE
   SYNTAX     SEQUENCE OF MscAtmIfVptUniAddrOperEntry
   ACCESS     not-accessible
   STATUS     mandatory
   DESCRIPTION
     "This attribute group contains the operational attributes for the 
      Address component."
::= { mscAtmIfVptUniAddr 10 }

mscAtmIfVptUniAddrOperEntry OBJECT-TYPE
   SYNTAX     MscAtmIfVptUniAddrOperEntry
   ACCESS     not-accessible
   STATUS     mandatory
   DESCRIPTION
     "An entry in the mscAtmIfVptUniAddrOperTable."
   INDEX {
      mscAtmIfIndex,
      mscAtmIfVptIndex,
      mscAtmIfVptUniIndex,
      mscAtmIfVptUniAddrAddressIndex,
      mscAtmIfVptUniAddrAddressTypeIndex }
::= { mscAtmIfVptUniAddrOperTable 1 }

MscAtmIfVptUniAddrOperEntry ::= SEQUENCE {
   mscAtmIfVptUniAddrScope
      INTEGER,
   mscAtmIfVptUniAddrReachability
      INTEGER }

mscAtmIfVptUniAddrScope OBJECT-TYPE
   SYNTAX     INTEGER (-1..104)
   ACCESS     read-only
   STATUS     mandatory
   DESCRIPTION
     "This attribute indicates the scope of the ATM address, which is the 
      highest level to which this address will be advertised in the PNNI 
      hierarchy. If no PnniInfo subcomponent has been provisioned, then 
      the scope will default to the level of this node in the PNNI 
      hierarchy. If this node does not participate in a PNNI hierarchy, then 
      this attribute will have the value of -1."
::= { mscAtmIfVptUniAddrOperEntry 1 }

mscAtmIfVptUniAddrReachability OBJECT-TYPE
   SYNTAX     INTEGER  {
                 internal(0),
                 exterior(1) }
   ACCESS     read-only
   STATUS     mandatory
   DESCRIPTION
     "This attribute indicates whether the address is internal or exterior. 
      An internal reachable address is an address of a destination that is 
      directly attached to the logical node advertising the address. An 
      exterior reachable address is an address that can be reached 
      through a PNNI routing domain, but which is not located in that 
      PNNI routing domain."
::= { mscAtmIfVptUniAddrOperEntry 2 }


-- AtmIf/n Iisp Address/address,type TerminateSPvpAndSPvc
-- AtmIf/n Uni Address/address,type TerminateSPvpAndSPvc
-- AtmIf/n Pnni Address/address,type TerminateSPvpAndSPvc
-- AtmIf/n Vpt/m Iisp Address/address,type TerminateSPvpAndSPvc
-- AtmIf/n Vpt/m Uni Address/address,type TerminateSPvpAndSPvc
-- AtmIf/n Vpt/m Pnni Address/address,type TerminateSPvpAndSPvc
-- 
-- The presence of this subcomponent indicates that SPvp and SPvc 
-- call setups terminate at this node if the destination address of the 
-- SPVP or SPVC matches the Address instance.

mscAtmIfVptUniAddrTermSP OBJECT IDENTIFIER ::= { mscAtmIfVptUniAddr 2 }



mscAtmIfVptUniAddrTermSPRowStatusTable OBJECT-TYPE
   SYNTAX     SEQUENCE OF MscAtmIfVptUniAddrTermSPRowStatusEntry
   ACCESS     not-accessible
   STATUS     mandatory
   DESCRIPTION
     "This entry controls the addition and deletion of 
      mscAtmIfVptUniAddrTermSP components."
::= { mscAtmIfVptUniAddrTermSP 1 }

mscAtmIfVptUniAddrTermSPRowStatusEntry OBJECT-TYPE
   SYNTAX     MscAtmIfVptUniAddrTermSPRowStatusEntry
   ACCESS     not-accessible
   STATUS     mandatory
   DESCRIPTION
     "A single entry in the table represents a single 
      mscAtmIfVptUniAddrTermSP component."
   INDEX {
      mscAtmIfIndex,
      mscAtmIfVptIndex,
      mscAtmIfVptUniIndex,
      mscAtmIfVptUniAddrAddressIndex,
      mscAtmIfVptUniAddrAddressTypeIndex,
      mscAtmIfVptUniAddrTermSPIndex }
::= { mscAtmIfVptUniAddrTermSPRowStatusTable 1 }

MscAtmIfVptUniAddrTermSPRowStatusEntry ::= SEQUENCE {
   mscAtmIfVptUniAddrTermSPRowStatus
      RowStatus,
   mscAtmIfVptUniAddrTermSPComponentName
      DisplayString,
   mscAtmIfVptUniAddrTermSPStorageType
      StorageType,
   mscAtmIfVptUniAddrTermSPIndex
      NonReplicated }

mscAtmIfVptUniAddrTermSPRowStatus OBJECT-TYPE
   SYNTAX     RowStatus 
   ACCESS     read-write
   STATUS     mandatory
   DESCRIPTION
     "This variable is used as the basis for SNMP naming of
      mscAtmIfVptUniAddrTermSP components.
      These components can be added and deleted."
::= { mscAtmIfVptUniAddrTermSPRowStatusEntry 1 }

mscAtmIfVptUniAddrTermSPComponentName OBJECT-TYPE
   SYNTAX     DisplayString 
   ACCESS     read-only
   STATUS     mandatory
   DESCRIPTION
     "This variable provides the component's string name for
      use with the ASCII Console Interface"
::= { mscAtmIfVptUniAddrTermSPRowStatusEntry 2 }

mscAtmIfVptUniAddrTermSPStorageType OBJECT-TYPE
   SYNTAX     StorageType 
   ACCESS     read-only
   STATUS     mandatory
   DESCRIPTION
     "This variable represents the storage type value for the
      mscAtmIfVptUniAddrTermSP tables."
::= { mscAtmIfVptUniAddrTermSPRowStatusEntry 4 }

mscAtmIfVptUniAddrTermSPIndex OBJECT-TYPE
   SYNTAX     NonReplicated 
   ACCESS     not-accessible
   STATUS     mandatory
   DESCRIPTION
     "This variable represents the index for the mscAtmIfVptUniAddrTermSP tables."
::= { mscAtmIfVptUniAddrTermSPRowStatusEntry 10 }


-- AtmIf/n Iisp Addr/address,type PnniInfo
-- AtmIf/n Uni Addr/address,type PnniInfo
-- AtmIf/n Pnni Addr/address,type PnniInfo
-- AtmIf/n Vpt/m Iisp Addr/address,type PnniInfo
-- AtmIf/n Vpt/m Uni Addr/address,type PnniInfo
-- AtmIf/n Vpt/m Pnni Addr/address,type PnniInfo
-- 
-- This component contains provisioned information associated with 
-- the ATM address related to PNNI. This component appears only 
-- under provisioned Address components.

mscAtmIfVptUniAddrPnniInfo OBJECT IDENTIFIER ::= { mscAtmIfVptUniAddr 3 }



mscAtmIfVptUniAddrPnniInfoRowStatusTable OBJECT-TYPE
   SYNTAX     SEQUENCE OF MscAtmIfVptUniAddrPnniInfoRowStatusEntry
   ACCESS     not-accessible
   STATUS     mandatory
   DESCRIPTION
     "This entry controls the addition and deletion of 
      mscAtmIfVptUniAddrPnniInfo components."
::= { mscAtmIfVptUniAddrPnniInfo 1 }

mscAtmIfVptUniAddrPnniInfoRowStatusEntry OBJECT-TYPE
   SYNTAX     MscAtmIfVptUniAddrPnniInfoRowStatusEntry
   ACCESS     not-accessible
   STATUS     mandatory
   DESCRIPTION
     "A single entry in the table represents a single 
      mscAtmIfVptUniAddrPnniInfo component."
   INDEX {
      mscAtmIfIndex,
      mscAtmIfVptIndex,
      mscAtmIfVptUniIndex,
      mscAtmIfVptUniAddrAddressIndex,
      mscAtmIfVptUniAddrAddressTypeIndex,
      mscAtmIfVptUniAddrPnniInfoIndex }
::= { mscAtmIfVptUniAddrPnniInfoRowStatusTable 1 }

MscAtmIfVptUniAddrPnniInfoRowStatusEntry ::= SEQUENCE {
   mscAtmIfVptUniAddrPnniInfoRowStatus
      RowStatus,
   mscAtmIfVptUniAddrPnniInfoComponentName
      DisplayString,
   mscAtmIfVptUniAddrPnniInfoStorageType
      StorageType,
   mscAtmIfVptUniAddrPnniInfoIndex
      NonReplicated }

mscAtmIfVptUniAddrPnniInfoRowStatus OBJECT-TYPE
   SYNTAX     RowStatus 
   ACCESS     read-write
   STATUS     mandatory
   DESCRIPTION
     "This variable is used as the basis for SNMP naming of
      mscAtmIfVptUniAddrPnniInfo components.
      These components can be added and deleted."
::= { mscAtmIfVptUniAddrPnniInfoRowStatusEntry 1 }

mscAtmIfVptUniAddrPnniInfoComponentName OBJECT-TYPE
   SYNTAX     DisplayString 
   ACCESS     read-only
   STATUS     mandatory
   DESCRIPTION
     "This variable provides the component's string name for
      use with the ASCII Console Interface"
::= { mscAtmIfVptUniAddrPnniInfoRowStatusEntry 2 }

mscAtmIfVptUniAddrPnniInfoStorageType OBJECT-TYPE
   SYNTAX     StorageType 
   ACCESS     read-only
   STATUS     mandatory
   DESCRIPTION
     "This variable represents the storage type value for the
      mscAtmIfVptUniAddrPnniInfo tables."
::= { mscAtmIfVptUniAddrPnniInfoRowStatusEntry 4 }

mscAtmIfVptUniAddrPnniInfoIndex OBJECT-TYPE
   SYNTAX     NonReplicated 
   ACCESS     not-accessible
   STATUS     mandatory
   DESCRIPTION
     "This variable represents the index for the mscAtmIfVptUniAddrPnniInfo tables."
::= { mscAtmIfVptUniAddrPnniInfoRowStatusEntry 10 }

mscAtmIfVptUniAddrPnniInfoProvTable OBJECT-TYPE
   SYNTAX     SEQUENCE OF MscAtmIfVptUniAddrPnniInfoProvEntry
   ACCESS     not-accessible
   STATUS     mandatory
   DESCRIPTION
     "This attribute group contains the provisioned attributes relating to 
      PNNI for a PnniInfo component."
::= { mscAtmIfVptUniAddrPnniInfo 10 }

mscAtmIfVptUniAddrPnniInfoProvEntry OBJECT-TYPE
   SYNTAX     MscAtmIfVptUniAddrPnniInfoProvEntry
   ACCESS     not-accessible
   STATUS     mandatory
   DESCRIPTION
     "An entry in the mscAtmIfVptUniAddrPnniInfoProvTable."
   INDEX {
      mscAtmIfIndex,
      mscAtmIfVptIndex,
      mscAtmIfVptUniIndex,
      mscAtmIfVptUniAddrAddressIndex,
      mscAtmIfVptUniAddrAddressTypeIndex,
      mscAtmIfVptUniAddrPnniInfoIndex }
::= { mscAtmIfVptUniAddrPnniInfoProvTable 1 }

MscAtmIfVptUniAddrPnniInfoProvEntry ::= SEQUENCE {
   mscAtmIfVptUniAddrPnniInfoScope
      INTEGER,
   mscAtmIfVptUniAddrPnniInfoReachability
      INTEGER }

mscAtmIfVptUniAddrPnniInfoScope OBJECT-TYPE
   SYNTAX     INTEGER (-1..104)
   ACCESS     read-write
   STATUS     mandatory
   DESCRIPTION
     "This attribute specifies the scope of the ATM address, which is the 
      highest level up to which this address will be advertised in the 
      PNNI hierarchy. The scope must be set to a value numerically less 
      than or equal to the level of the lowest level peer group containing 
      this node. Setting the scope to 0 will cause the address to be 
      advertised globally within this PNNI routing domain."
   DEFVAL     { -1 }
::= { mscAtmIfVptUniAddrPnniInfoProvEntry 1 }

mscAtmIfVptUniAddrPnniInfoReachability OBJECT-TYPE
   SYNTAX     INTEGER  {
                 internal(0),
                 exterior(1) }
   ACCESS     read-write
   STATUS     mandatory
   DESCRIPTION
     "This attribute indicates whether the address is internal or exterior. 
      An internal reachable address is an address of a destination that is 
      directly attached to the logical node advertising the address. An 
      exterior reachable address is an address that can be reached 
      through a PNNI routing domain, but which is not located in that 
      PNNI routing domain."
   DEFVAL     { internal }
::= { mscAtmIfVptUniAddrPnniInfoProvEntry 2 }


-- AtmIf/n Uni CallingAddressScreening
-- AtmIf/n Iisp CallingAddressScreening
-- This component represents the screening of incoming ATM SVC 
-- call requests against provisioned ATM calling addresses (that is, 
-- screening SVC calls coming from specific addresses). If this 
-- component is not provisioned, all call requests are accepted and no 
-- calling address screening takes place. 

mscAtmIfVptUniCallingAScr OBJECT IDENTIFIER ::= { mscAtmIfVptUni 4 }



mscAtmIfVptUniCallingAScrRowStatusTable OBJECT-TYPE
   SYNTAX     SEQUENCE OF MscAtmIfVptUniCallingAScrRowStatusEntry
   ACCESS     not-accessible
   STATUS     mandatory
   DESCRIPTION
     "This entry controls the addition and deletion of 
      mscAtmIfVptUniCallingAScr components."
::= { mscAtmIfVptUniCallingAScr 1 }

mscAtmIfVptUniCallingAScrRowStatusEntry OBJECT-TYPE
   SYNTAX     MscAtmIfVptUniCallingAScrRowStatusEntry
   ACCESS     not-accessible
   STATUS     mandatory
   DESCRIPTION
     "A single entry in the table represents a single 
      mscAtmIfVptUniCallingAScr component."
   INDEX {
      mscAtmIfIndex,
      mscAtmIfVptIndex,
      mscAtmIfVptUniIndex,
      mscAtmIfVptUniCallingAScrIndex }
::= { mscAtmIfVptUniCallingAScrRowStatusTable 1 }

MscAtmIfVptUniCallingAScrRowStatusEntry ::= SEQUENCE {
   mscAtmIfVptUniCallingAScrRowStatus
      RowStatus,
   mscAtmIfVptUniCallingAScrComponentName
      DisplayString,
   mscAtmIfVptUniCallingAScrStorageType
      StorageType,
   mscAtmIfVptUniCallingAScrIndex
      NonReplicated }

mscAtmIfVptUniCallingAScrRowStatus OBJECT-TYPE
   SYNTAX     RowStatus 
   ACCESS     read-write
   STATUS     mandatory
   DESCRIPTION
     "This variable is used as the basis for SNMP naming of
      mscAtmIfVptUniCallingAScr components.
      These components can be added and deleted."
::= { mscAtmIfVptUniCallingAScrRowStatusEntry 1 }

mscAtmIfVptUniCallingAScrComponentName OBJECT-TYPE
   SYNTAX     DisplayString 
   ACCESS     read-only
   STATUS     mandatory
   DESCRIPTION
     "This variable provides the component's string name for
      use with the ASCII Console Interface"
::= { mscAtmIfVptUniCallingAScrRowStatusEntry 2 }

mscAtmIfVptUniCallingAScrStorageType OBJECT-TYPE
   SYNTAX     StorageType 
   ACCESS     read-only
   STATUS     mandatory
   DESCRIPTION
     "This variable represents the storage type value for the
      mscAtmIfVptUniCallingAScr tables."
::= { mscAtmIfVptUniCallingAScrRowStatusEntry 4 }

mscAtmIfVptUniCallingAScrIndex OBJECT-TYPE
   SYNTAX     NonReplicated 
   ACCESS     not-accessible
   STATUS     mandatory
   DESCRIPTION
     "This variable represents the index for the mscAtmIfVptUniCallingAScr tables."
::= { mscAtmIfVptUniCallingAScrRowStatusEntry 10 }

mscAtmIfVptUniCallingAScrProvTable OBJECT-TYPE
   SYNTAX     SEQUENCE OF MscAtmIfVptUniCallingAScrProvEntry
   ACCESS     not-accessible
   STATUS     mandatory
   DESCRIPTION
     "This attribute group contains the provisionable attributes for the 
      CallingAScr component."
::= { mscAtmIfVptUniCallingAScr 10 }

mscAtmIfVptUniCallingAScrProvEntry OBJECT-TYPE
   SYNTAX     MscAtmIfVptUniCallingAScrProvEntry
   ACCESS     not-accessible
   STATUS     mandatory
   DESCRIPTION
     "An entry in the mscAtmIfVptUniCallingAScrProvTable."
   INDEX {
      mscAtmIfIndex,
      mscAtmIfVptIndex,
      mscAtmIfVptUniIndex,
      mscAtmIfVptUniCallingAScrIndex }
::= { mscAtmIfVptUniCallingAScrProvTable 1 }

MscAtmIfVptUniCallingAScrProvEntry ::= SEQUENCE {
   mscAtmIfVptUniCallingAScrAdminStatus
      INTEGER,
   mscAtmIfVptUniCallingAScrDefaultInsertionAddress
      HexString }

mscAtmIfVptUniCallingAScrAdminStatus OBJECT-TYPE
   SYNTAX     INTEGER  {
                 enabled(0),
                 disabled(1) }
   ACCESS     read-write
   STATUS     mandatory
   DESCRIPTION
     "This attribute specifies whether the calling address screening feature 
      is enabled or disabled. 
      
      If enabled, incoming SVC calls are screened against provisioned 
      addresses. If enabled and the calling address in the ATM SVC call 
      request is provisioned to be accepted, the call is accepted or rejected 
      according to the action specified for that address. If the value is 
      enabled, and the calling address in the address request is not 
      provisioned, the call is rejected
      
      If the value is disabled, no calling address screening is performed."
   DEFVAL     { disabled }
::= { mscAtmIfVptUniCallingAScrProvEntry 1 }

mscAtmIfVptUniCallingAScrDefaultInsertionAddress OBJECT-TYPE
   SYNTAX     HexString (SIZE (0..20))
   ACCESS     read-write
   STATUS     mandatory
   DESCRIPTION
     "This attribute specifies the address to be inserted into the SVC 
      connection request if adminStatus is enabled and the connection 
      request does not contain a calling address. If the adminStatus 
      attribute is enabled and this attribute is empty, all incoming SVC 
      calls which do not contain a calling address are rejected."
   DEFVAL     { ''H }  -- ""
::= { mscAtmIfVptUniCallingAScrProvEntry 2 }

mscAtmIfVptUniCallingAScrStatTable OBJECT-TYPE
   SYNTAX     SEQUENCE OF MscAtmIfVptUniCallingAScrStatEntry
   ACCESS     not-accessible
   STATUS     mandatory
   DESCRIPTION
     "This attribute group contains statistics related to the incoming SVC 
      call requests received while the adminStatus attribute is set to 
      enabled."
::= { mscAtmIfVptUniCallingAScr 11 }

mscAtmIfVptUniCallingAScrStatEntry OBJECT-TYPE
   SYNTAX     MscAtmIfVptUniCallingAScrStatEntry
   ACCESS     not-accessible
   STATUS     mandatory
   DESCRIPTION
     "An entry in the mscAtmIfVptUniCallingAScrStatTable."
   INDEX {
      mscAtmIfIndex,
      mscAtmIfVptIndex,
      mscAtmIfVptUniIndex,
      mscAtmIfVptUniCallingAScrIndex }
::= { mscAtmIfVptUniCallingAScrStatTable 1 }

MscAtmIfVptUniCallingAScrStatEntry ::= SEQUENCE {
   mscAtmIfVptUniCallingAScrAcceptedCalls
      Counter32,
   mscAtmIfVptUniCallingAScrRejectedCalls
      Counter32,
   mscAtmIfVptUniCallingAScrUnmatchedCalls
      Counter32 }

mscAtmIfVptUniCallingAScrAcceptedCalls OBJECT-TYPE
   SYNTAX     Counter32 
   ACCESS     read-only
   STATUS     mandatory
   DESCRIPTION
     "This attribute counts the incoming SVC calls which were accepted 
      because the address specified in the call request matched a 
      provisioned ATM address and the associated action was accept.
      When the counter exceeds the maximum, it wraps to 0."
::= { mscAtmIfVptUniCallingAScrStatEntry 1 }

mscAtmIfVptUniCallingAScrRejectedCalls OBJECT-TYPE
   SYNTAX     Counter32 
   ACCESS     read-only
   STATUS     mandatory
   DESCRIPTION
     "This attribute counts the incoming SVC calls which were rejected 
      because the address specified in the call request matched a 
      provisioned ATM address, but the associated action was reject. 
      When the counter exceeds the maximum, it wraps to 0."
::= { mscAtmIfVptUniCallingAScrStatEntry 2 }

mscAtmIfVptUniCallingAScrUnmatchedCalls OBJECT-TYPE
   SYNTAX     Counter32 
   ACCESS     read-only
   STATUS     mandatory
   DESCRIPTION
     "This attribute counts the incoming SVC calls which were rejected 
      because none of the provisioned ATM addresses matched the 
      applicable address in the incoming SVC call request.
      When the counter exceeds the maximum, it wraps to 0."
::= { mscAtmIfVptUniCallingAScrStatEntry 3 }


-- AtmIf/n Uni CallingAScr Address/addr,action
-- AtmIf/n Iisp CallingAScr Address/addr,action 
-- AtmIf/n Uni CalledAScr Address/addr,action 
-- AtmIf/n Iisp CalledAScr Address/addr,action 
-- This component specifies a calling (or called) address with an 
-- action to accept or reject a connection request which contains a 
-- matching calling (or called) address.
-- For the Calling Address Screening feature, if the specified action is 
-- accept, any call whose calling address matches that address is 
-- accepted. If the specified action is reject, any call whose calling 
-- address matches that address is rejected.
-- For the Called Address Screening feature, if the specified action is 
-- accept, any call whose called address matches that address, is 
-- accepted. If the specified action is reject, any call whose called 
-- address matches that address is rejected.
-- For both features, the incoming SVC call request is rejected if the 
-- address is not provisioned and the feature is enabled.

mscAtmIfVptUniCallingAScrAddr OBJECT IDENTIFIER ::= { mscAtmIfVptUniCallingAScr 2 }



mscAtmIfVptUniCallingAScrAddrRowStatusTable OBJECT-TYPE
   SYNTAX     SEQUENCE OF MscAtmIfVptUniCallingAScrAddrRowStatusEntry
   ACCESS     not-accessible
   STATUS     mandatory
   DESCRIPTION
     "This entry controls the addition and deletion of 
      mscAtmIfVptUniCallingAScrAddr components."
::= { mscAtmIfVptUniCallingAScrAddr 1 }

mscAtmIfVptUniCallingAScrAddrRowStatusEntry OBJECT-TYPE
   SYNTAX     MscAtmIfVptUniCallingAScrAddrRowStatusEntry
   ACCESS     not-accessible
   STATUS     mandatory
   DESCRIPTION
     "A single entry in the table represents a single 
      mscAtmIfVptUniCallingAScrAddr component."
   INDEX {
      mscAtmIfIndex,
      mscAtmIfVptIndex,
      mscAtmIfVptUniIndex,
      mscAtmIfVptUniCallingAScrIndex,
      mscAtmIfVptUniCallingAScrAddrAddressIndex,
      mscAtmIfVptUniCallingAScrAddrAddressActionIndex }
::= { mscAtmIfVptUniCallingAScrAddrRowStatusTable 1 }

MscAtmIfVptUniCallingAScrAddrRowStatusEntry ::= SEQUENCE {
   mscAtmIfVptUniCallingAScrAddrRowStatus
      RowStatus,
   mscAtmIfVptUniCallingAScrAddrComponentName
      DisplayString,
   mscAtmIfVptUniCallingAScrAddrStorageType
      StorageType,
   mscAtmIfVptUniCallingAScrAddrAddressIndex
      AsciiStringIndex,
   mscAtmIfVptUniCallingAScrAddrAddressActionIndex
      INTEGER }

mscAtmIfVptUniCallingAScrAddrRowStatus OBJECT-TYPE
   SYNTAX     RowStatus 
   ACCESS     read-write
   STATUS     mandatory
   DESCRIPTION
     "This variable is used as the basis for SNMP naming of
      mscAtmIfVptUniCallingAScrAddr components.
      These components can be added and deleted."
::= { mscAtmIfVptUniCallingAScrAddrRowStatusEntry 1 }

mscAtmIfVptUniCallingAScrAddrComponentName OBJECT-TYPE
   SYNTAX     DisplayString 
   ACCESS     read-only
   STATUS     mandatory
   DESCRIPTION
     "This variable provides the component's string name for
      use with the ASCII Console Interface"
::= { mscAtmIfVptUniCallingAScrAddrRowStatusEntry 2 }

mscAtmIfVptUniCallingAScrAddrStorageType OBJECT-TYPE
   SYNTAX     StorageType 
   ACCESS     read-only
   STATUS     mandatory
   DESCRIPTION
     "This variable represents the storage type value for the
      mscAtmIfVptUniCallingAScrAddr tables."
::= { mscAtmIfVptUniCallingAScrAddrRowStatusEntry 4 }

mscAtmIfVptUniCallingAScrAddrAddressIndex OBJECT-TYPE
   SYNTAX     AsciiStringIndex (SIZE (1..40))
   ACCESS     not-accessible
   STATUS     mandatory
   DESCRIPTION
     "This variable represents an index for the mscAtmIfVptUniCallingAScrAddr tables."
::= { mscAtmIfVptUniCallingAScrAddrRowStatusEntry 10 }

mscAtmIfVptUniCallingAScrAddrAddressActionIndex OBJECT-TYPE
   SYNTAX     INTEGER  {
                 accept(0),
                 reject(1) }
   ACCESS     not-accessible
   STATUS     mandatory
   DESCRIPTION
     "This variable represents an index for the mscAtmIfVptUniCallingAScrAddr tables."
::= { mscAtmIfVptUniCallingAScrAddrRowStatusEntry 11 }


-- AtmIf/n Uni CalledAddressScreening
-- AtmIf/n Iisp CalledAddressScreening
-- This component represents the screening of incoming ATM SVC 
-- call requests against provisioned ATM called addresses (that is, 
-- going to specific destinations). If this component is not provisioned, 
-- all call requests are accepted and no called address screening takes 
-- place.

mscAtmIfVptUniCalledAScr OBJECT IDENTIFIER ::= { mscAtmIfVptUni 5 }



mscAtmIfVptUniCalledAScrRowStatusTable OBJECT-TYPE
   SYNTAX     SEQUENCE OF MscAtmIfVptUniCalledAScrRowStatusEntry
   ACCESS     not-accessible
   STATUS     mandatory
   DESCRIPTION
     "This entry controls the addition and deletion of 
      mscAtmIfVptUniCalledAScr components."
::= { mscAtmIfVptUniCalledAScr 1 }

mscAtmIfVptUniCalledAScrRowStatusEntry OBJECT-TYPE
   SYNTAX     MscAtmIfVptUniCalledAScrRowStatusEntry
   ACCESS     not-accessible
   STATUS     mandatory
   DESCRIPTION
     "A single entry in the table represents a single 
      mscAtmIfVptUniCalledAScr component."
   INDEX {
      mscAtmIfIndex,
      mscAtmIfVptIndex,
      mscAtmIfVptUniIndex,
      mscAtmIfVptUniCalledAScrIndex }
::= { mscAtmIfVptUniCalledAScrRowStatusTable 1 }

MscAtmIfVptUniCalledAScrRowStatusEntry ::= SEQUENCE {
   mscAtmIfVptUniCalledAScrRowStatus
      RowStatus,
   mscAtmIfVptUniCalledAScrComponentName
      DisplayString,
   mscAtmIfVptUniCalledAScrStorageType
      StorageType,
   mscAtmIfVptUniCalledAScrIndex
      NonReplicated }

mscAtmIfVptUniCalledAScrRowStatus OBJECT-TYPE
   SYNTAX     RowStatus 
   ACCESS     read-write
   STATUS     mandatory
   DESCRIPTION
     "This variable is used as the basis for SNMP naming of
      mscAtmIfVptUniCalledAScr components.
      These components can be added and deleted."
::= { mscAtmIfVptUniCalledAScrRowStatusEntry 1 }

mscAtmIfVptUniCalledAScrComponentName OBJECT-TYPE
   SYNTAX     DisplayString 
   ACCESS     read-only
   STATUS     mandatory
   DESCRIPTION
     "This variable provides the component's string name for
      use with the ASCII Console Interface"
::= { mscAtmIfVptUniCalledAScrRowStatusEntry 2 }

mscAtmIfVptUniCalledAScrStorageType OBJECT-TYPE
   SYNTAX     StorageType 
   ACCESS     read-only
   STATUS     mandatory
   DESCRIPTION
     "This variable represents the storage type value for the
      mscAtmIfVptUniCalledAScr tables."
::= { mscAtmIfVptUniCalledAScrRowStatusEntry 4 }

mscAtmIfVptUniCalledAScrIndex OBJECT-TYPE
   SYNTAX     NonReplicated 
   ACCESS     not-accessible
   STATUS     mandatory
   DESCRIPTION
     "This variable represents the index for the mscAtmIfVptUniCalledAScr tables."
::= { mscAtmIfVptUniCalledAScrRowStatusEntry 10 }

mscAtmIfVptUniCalledAScrProvTable OBJECT-TYPE
   SYNTAX     SEQUENCE OF MscAtmIfVptUniCalledAScrProvEntry
   ACCESS     not-accessible
   STATUS     mandatory
   DESCRIPTION
     "This attribute group contains the provisionable attributes for the 
      CalledAScr component."
::= { mscAtmIfVptUniCalledAScr 10 }

mscAtmIfVptUniCalledAScrProvEntry OBJECT-TYPE
   SYNTAX     MscAtmIfVptUniCalledAScrProvEntry
   ACCESS     not-accessible
   STATUS     mandatory
   DESCRIPTION
     "An entry in the mscAtmIfVptUniCalledAScrProvTable."
   INDEX {
      mscAtmIfIndex,
      mscAtmIfVptIndex,
      mscAtmIfVptUniIndex,
      mscAtmIfVptUniCalledAScrIndex }
::= { mscAtmIfVptUniCalledAScrProvTable 1 }

MscAtmIfVptUniCalledAScrProvEntry ::= SEQUENCE {
   mscAtmIfVptUniCalledAScrAdminStatus
      INTEGER }

mscAtmIfVptUniCalledAScrAdminStatus OBJECT-TYPE
   SYNTAX     INTEGER  {
                 enabled(0),
                 disabled(1) }
   ACCESS     read-write
   STATUS     mandatory
   DESCRIPTION
     "This attribute specifies whether the called address screening feature 
      is enabled or disabled.
      If the value is enabled, incoming SVC calls will be screened against 
      provisioned called addresses. If the value is enabled and the called 
      address in the ATM SVC call request has been provisioned, the call 
      is accepted or rejected according to the action specified for that 
      address. If the value is enabled and the called address in the call 
      request is not provisioned, the call is rejected.
      If the value is disabled, no called address screening is performed."
   DEFVAL     { disabled }
::= { mscAtmIfVptUniCalledAScrProvEntry 1 }

mscAtmIfVptUniCalledAScrStatTable OBJECT-TYPE
   SYNTAX     SEQUENCE OF MscAtmIfVptUniCalledAScrStatEntry
   ACCESS     not-accessible
   STATUS     mandatory
   DESCRIPTION
     "This attribute group contains statistics related to the incoming SVC 
      call requests received while the adminStatus attribute is set to 
      enabled."
::= { mscAtmIfVptUniCalledAScr 11 }

mscAtmIfVptUniCalledAScrStatEntry OBJECT-TYPE
   SYNTAX     MscAtmIfVptUniCalledAScrStatEntry
   ACCESS     not-accessible
   STATUS     mandatory
   DESCRIPTION
     "An entry in the mscAtmIfVptUniCalledAScrStatTable."
   INDEX {
      mscAtmIfIndex,
      mscAtmIfVptIndex,
      mscAtmIfVptUniIndex,
      mscAtmIfVptUniCalledAScrIndex }
::= { mscAtmIfVptUniCalledAScrStatTable 1 }

MscAtmIfVptUniCalledAScrStatEntry ::= SEQUENCE {
   mscAtmIfVptUniCalledAScrAcceptedCalls
      Counter32,
   mscAtmIfVptUniCalledAScrRejectedCalls
      Counter32,
   mscAtmIfVptUniCalledAScrUnmatchedCalls
      Counter32 }

mscAtmIfVptUniCalledAScrAcceptedCalls OBJECT-TYPE
   SYNTAX     Counter32 
   ACCESS     read-only
   STATUS     mandatory
   DESCRIPTION
     "This attribute counts the incoming SVC calls which were accepted 
      because the address specified in the call request matched a 
      provisioned ATM address and the associated action was accept.
      When the counter exceeds the maximum, it wraps to 0."
::= { mscAtmIfVptUniCalledAScrStatEntry 1 }

mscAtmIfVptUniCalledAScrRejectedCalls OBJECT-TYPE
   SYNTAX     Counter32 
   ACCESS     read-only
   STATUS     mandatory
   DESCRIPTION
     "This attribute counts the incoming SVC calls which were rejected 
      because the address specified in the call request matched a 
      provisioned ATM address, but the associated action was reject. 
      When the counter exceeds the maximum, it wraps to 0."
::= { mscAtmIfVptUniCalledAScrStatEntry 2 }

mscAtmIfVptUniCalledAScrUnmatchedCalls OBJECT-TYPE
   SYNTAX     Counter32 
   ACCESS     read-only
   STATUS     mandatory
   DESCRIPTION
     "This attribute counts the incoming SVC calls which were rejected 
      because none of the provisioned ATM addresses matched the 
      applicable address in the incoming SVC call request.
      When the counter exceeds the maximum, it wraps to 0."
::= { mscAtmIfVptUniCalledAScrStatEntry 3 }


-- AtmIf/n Uni CallingAScr Address/addr,action
-- AtmIf/n Iisp CallingAScr Address/addr,action 
-- AtmIf/n Uni CalledAScr Address/addr,action 
-- AtmIf/n Iisp CalledAScr Address/addr,action 
-- This component specifies a calling (or called) address with an 
-- action to accept or reject a connection request which contains a 
-- matching calling (or called) address.
-- For the Calling Address Screening feature, if the specified action is 
-- accept, any call whose calling address matches that address is 
-- accepted. If the specified action is reject, any call whose calling 
-- address matches that address is rejected.
-- For the Called Address Screening feature, if the specified action is 
-- accept, any call whose called address matches that address, is 
-- accepted. If the specified action is reject, any call whose called 
-- address matches that address is rejected.
-- For both features, the incoming SVC call request is rejected if the 
-- address is not provisioned and the feature is enabled.

mscAtmIfVptUniCalledAScrAddr OBJECT IDENTIFIER ::= { mscAtmIfVptUniCalledAScr 2 }



mscAtmIfVptUniCalledAScrAddrRowStatusTable OBJECT-TYPE
   SYNTAX     SEQUENCE OF MscAtmIfVptUniCalledAScrAddrRowStatusEntry
   ACCESS     not-accessible
   STATUS     mandatory
   DESCRIPTION
     "This entry controls the addition and deletion of 
      mscAtmIfVptUniCalledAScrAddr components."
::= { mscAtmIfVptUniCalledAScrAddr 1 }

mscAtmIfVptUniCalledAScrAddrRowStatusEntry OBJECT-TYPE
   SYNTAX     MscAtmIfVptUniCalledAScrAddrRowStatusEntry
   ACCESS     not-accessible
   STATUS     mandatory
   DESCRIPTION
     "A single entry in the table represents a single 
      mscAtmIfVptUniCalledAScrAddr component."
   INDEX {
      mscAtmIfIndex,
      mscAtmIfVptIndex,
      mscAtmIfVptUniIndex,
      mscAtmIfVptUniCalledAScrIndex,
      mscAtmIfVptUniCalledAScrAddrAddressIndex,
      mscAtmIfVptUniCalledAScrAddrAddressActionIndex }
::= { mscAtmIfVptUniCalledAScrAddrRowStatusTable 1 }

MscAtmIfVptUniCalledAScrAddrRowStatusEntry ::= SEQUENCE {
   mscAtmIfVptUniCalledAScrAddrRowStatus
      RowStatus,
   mscAtmIfVptUniCalledAScrAddrComponentName
      DisplayString,
   mscAtmIfVptUniCalledAScrAddrStorageType
      StorageType,
   mscAtmIfVptUniCalledAScrAddrAddressIndex
      AsciiStringIndex,
   mscAtmIfVptUniCalledAScrAddrAddressActionIndex
      INTEGER }

mscAtmIfVptUniCalledAScrAddrRowStatus OBJECT-TYPE
   SYNTAX     RowStatus 
   ACCESS     read-write
   STATUS     mandatory
   DESCRIPTION
     "This variable is used as the basis for SNMP naming of
      mscAtmIfVptUniCalledAScrAddr components.
      These components can be added and deleted."
::= { mscAtmIfVptUniCalledAScrAddrRowStatusEntry 1 }

mscAtmIfVptUniCalledAScrAddrComponentName OBJECT-TYPE
   SYNTAX     DisplayString 
   ACCESS     read-only
   STATUS     mandatory
   DESCRIPTION
     "This variable provides the component's string name for
      use with the ASCII Console Interface"
::= { mscAtmIfVptUniCalledAScrAddrRowStatusEntry 2 }

mscAtmIfVptUniCalledAScrAddrStorageType OBJECT-TYPE
   SYNTAX     StorageType 
   ACCESS     read-only
   STATUS     mandatory
   DESCRIPTION
     "This variable represents the storage type value for the
      mscAtmIfVptUniCalledAScrAddr tables."
::= { mscAtmIfVptUniCalledAScrAddrRowStatusEntry 4 }

mscAtmIfVptUniCalledAScrAddrAddressIndex OBJECT-TYPE
   SYNTAX     AsciiStringIndex (SIZE (1..40))
   ACCESS     not-accessible
   STATUS     mandatory
   DESCRIPTION
     "This variable represents an index for the mscAtmIfVptUniCalledAScrAddr tables."
::= { mscAtmIfVptUniCalledAScrAddrRowStatusEntry 10 }

mscAtmIfVptUniCalledAScrAddrAddressActionIndex OBJECT-TYPE
   SYNTAX     INTEGER  {
                 accept(0),
                 reject(1) }
   ACCESS     not-accessible
   STATUS     mandatory
   DESCRIPTION
     "This variable represents an index for the mscAtmIfVptUniCalledAScrAddr tables."
::= { mscAtmIfVptUniCalledAScrAddrRowStatusEntry 11 }




-- 
-- Version and Compliance statements
-- 



-- Object-Group Statement:
-- A list of all current accessible leaf objects.

-- OBJECTS { mscAtmIfUniServiceExchange,
--           mscAtmIfVptUniAccountConnectionType,
--           mscAtmIfVptUniSigVcdTrafficShaping,
--           mscAtmIfVptUniCallingAScrComponentName,
--           mscAtmIfVptUniCallingAScrRowStatus,
--           mscAtmIfUniSigAdminState,
--           mscAtmIfVptUniSigLastTxCauseCode,
--           mscAtmIfVptUniSigPeakConnections,
--           mscAtmIfVptUniCalledAScrAddrComponentName,
--           mscAtmIfUniCallingAScrUnmatchedCalls,
--           mscAtmIfVptUniSigVcdTdpValue,
--           mscAtmIfUniSigRowStatus,
--           mscAtmIfVptUniCalledAScrRowStatus,
--           mscAtmIfVptUniSigVcdTrafficDescType,
--           mscAtmIfVptUniSigVcdUnshapedTransmitQueueing,
--           mscAtmIfVptUniAddrTermSPRowStatus,
--           mscAtmIfUniSigOperatingMode,
--           mscAtmIfUniSigPeakConnections,
--           mscAtmIfVptUniSigFailedConnections,
--           mscAtmIfUniSigTxPdus,
--           mscAtmIfVptUniCallingAScrRejectedCalls,
--           mscAtmIfVptUniAddrComponentName,
--           mscAtmIfUniSigUsageState,
--           mscAtmIfVptUniCallingAScrAddrStorageType,
--           mscAtmIfUniSigVcdWeight,
--           mscAtmIfVptUniAddrPnniInfoRowStatus,
--           mscAtmIfUniAddrPnniInfoReachability,
--           mscAtmIfVptUniSigVcdWeight,
--           mscAtmIfUniSigSuccessfulPmpConnections,
--           mscAtmIfUniSigFailedConnections,
--           mscAtmIfVptUniSigLastRxCauseCode,
--           mscAtmIfUniAddrScope,
--           mscAtmIfUniCallingAScrStorageType,
--           mscAtmIfUniSigSuccessfulConnections,
--           mscAtmIfUniLoopPrevention,
--           mscAtmIfUniSigVcdQosClass,
--           mscAtmIfVptUniSigAddressConversion,
--           mscAtmIfUniSigLastTxDiagCode,
--           mscAtmIfUniCallingAScrRejectedCalls,
--           mscAtmIfUniCalledAScrAddrComponentName,
--           mscAtmIfUniCalledAScrComponentName,
--           mscAtmIfVptUniSigCurrentPmpConnections,
--           mscAtmIfVptUniAddrStorageType,
--           mscAtmIfVptUniStorageType,
--           mscAtmIfUniSigCurrentPmpConnections,
--           mscAtmIfUniCalledAScrAdminStatus,
--           mscAtmIfUniSigVcdUsageParameterControl,
--           mscAtmIfUniAddrTermSPComponentName,
--           mscAtmIfVptUniCallingAScrAcceptedCalls,
--           mscAtmIfUniSigVcdComponentName,
--           mscAtmIfUniIlmiEsiToRegisterRowStatus,
--           mscAtmIfUniSigVcdTrafficDescType,
--           mscAtmIfVptUniSigStorageType,
--           mscAtmIfUniIlmiVci,
--           mscAtmIfVptUniCalledAScrComponentName,
--           mscAtmIfUniMacAddress,
--           mscAtmIfVptUniCalledAScrStorageType,
--           mscAtmIfVptUniAddrReachability,
--           mscAtmIfVptUniCalledAScrAdminStatus,
--           mscAtmIfUniAddrPnniInfoComponentName,
--           mscAtmIfUniCallingAScrAddrRowStatus,
--           mscAtmIfUniCallingAScrRowStatus,
--           mscAtmIfUniSigRxPdus,
--           mscAtmIfVptUniAddrTermSPComponentName,
--           mscAtmIfVptUniCalledAScrAddrRowStatus,
--           mscAtmIfVptUniAddrPnniInfoStorageType,
--           mscAtmIfVptUniCallingAScrAddrComponentName,
--           mscAtmIfUniSigLastRxDiagCode,
--           mscAtmIfUniCalledAScrUnmatchedCalls,
--           mscAtmIfUniSigVci,
--           mscAtmIfUniCalledAScrAcceptedCalls,
--           mscAtmIfUniSigLastTxCauseCode,
--           mscAtmIfUniSigPeakPmpConnections,
--           mscAtmIfVptUniSoftPvpAndPvcHoldOffTime,
--           mscAtmIfVptUniAccountCollection,
--           mscAtmIfVptUniSigOperationalState,
--           mscAtmIfUniIlmiEsiToRegisterValue,
--           mscAtmIfVptUniSigVcdRowStatus,
--           mscAtmIfVptUniSoftPvpAndPvcRetryPeriod,
--           mscAtmIfUniCallingAScrAcceptedCalls,
--           mscAtmIfVptUniSigComponentName,
--           mscAtmIfUniIlmiComponentName,
--           mscAtmIfUniCallingAScrComponentName,
--           mscAtmIfVptUniServiceExchange,
--           mscAtmIfUniSigNewCurrentConnections,
--           mscAtmIfVptUniAddrRowStatus,
--           mscAtmIfVptUniCalledAScrRejectedCalls,
--           mscAtmIfVptUniSigAdminState,
--           mscAtmIfUniSoftPvpAndPvcHoldOffTime,
--           mscAtmIfUniCallingAScrAddrStorageType,
--           mscAtmIfUniIlmiRxBadPdusDiscarded,
--           mscAtmIfUniCalledAScrAddrStorageType,
--           mscAtmIfUniSide,
--           mscAtmIfUniSigAddressConversion,
--           mscAtmIfUniComponentName,
--           mscAtmIfVptUniSigRowStatus,
--           mscAtmIfVptUniCalledAScrAcceptedCalls,
--           mscAtmIfUniAccountClass,
--           mscAtmIfUniSigLastRxCauseCode,
--           mscAtmIfUniSigVcdStorageType,
--           mscAtmIfVptUniAddrTermSPStorageType,
--           mscAtmIfUniSigVcdTdpValue,
--           mscAtmIfVptUniComponentName,
--           mscAtmIfVptUniSigVcdStorageType,
--           mscAtmIfUniAccountConnectionType,
--           mscAtmIfUniAddrPnniInfoStorageType,
--           mscAtmIfUniSigFailedPmpConnections,
--           mscAtmIfUniIlmiStorageType,
--           mscAtmIfVptUniCallingAScrAddrRowStatus,
--           mscAtmIfVptUniSigPeakPmpConnections,
--           mscAtmIfUniAddrComponentName,
--           mscAtmIfUniCalledAScrAddrRowStatus,
--           mscAtmIfUniCalledAScrRowStatus,
--           mscAtmIfVptUniAddrScope,
--           mscAtmIfVptUniCallingAScrStorageType,
--           mscAtmIfVptUniLoopPrevention,
--           mscAtmIfVptUniSigVcdQosClass,
--           mscAtmIfVptUniSigFailedPmpConnections,
--           mscAtmIfUniSigVcdUnshapedTransmitQueueing,
--           mscAtmIfUniAddrTermSPRowStatus,
--           mscAtmIfUniSigComponentName,
--           mscAtmIfUniSigVcdRowStatus,
--           mscAtmIfVptUniSigUsageState,
--           mscAtmIfUniIlmiAdminState,
--           mscAtmIfVptUniSigSuccessfulPmpConnections,
--           mscAtmIfUniCalledAScrStorageType,
--           mscAtmIfVptUniSigTxPdus,
--           mscAtmIfVptUniSigVcdComponentName,
--           mscAtmIfUniAddrPnniInfoRowStatus,
--           mscAtmIfVptUniSigSuccessfulConnections,
--           mscAtmIfUniIlmiRowStatus,
--           mscAtmIfUniAddrTermSPStorageType,
--           mscAtmIfUniCalledAScrRejectedCalls,
--           mscAtmIfVptUniAddrPnniInfoReachability,
--           mscAtmIfVptUniAddrPnniInfoComponentName,
--           mscAtmIfVptUniSigVcdUsageParameterControl,
--           mscAtmIfUniAccountCollection,
--           mscAtmIfVptUniSigVcdAtmServiceCategory,
--           mscAtmIfVptUniSigRxPdus,
--           mscAtmIfVptUniSigVci,
--           mscAtmIfUniAddrStorageType,
--           mscAtmIfUniStorageType,
--           mscAtmIfUniIlmiUsageState,
--           mscAtmIfVptUniAddrPnniInfoScope,
--           mscAtmIfVptUniSigLastRxDiagCode,
--           mscAtmIfVptUniCalledAScrUnmatchedCalls,
--           mscAtmIfUniVersion,
--           mscAtmIfUniSigVcdTrafficShaping,
--           mscAtmIfUniIlmiTxPdus,
--           mscAtmIfVptUniSigLastTxDiagCode,
--           mscAtmIfUniIlmiPrefixToRegisterRowStatus,
--           mscAtmIfVptUniCallingAScrUnmatchedCalls,
--           mscAtmIfUniAddrReachability,
--           mscAtmIfVptUniVersion,
--           mscAtmIfVptUniSigOperatingMode,
--           mscAtmIfUniIlmiOperationalState,
--           mscAtmIfUniSigOperationalState,
--           mscAtmIfVptUniRowStatus,
--           mscAtmIfUniIlmiPrefixToRegisterValue,
--           mscAtmIfVptUniSigNewCurrentConnections,
--           mscAtmIfUniCallingAScrAddrComponentName,
--           mscAtmIfUniAddrRowStatus,
--           mscAtmIfUniRowStatus,
--           mscAtmIfVptUniCalledAScrAddrStorageType,
--           mscAtmIfUniCallingAScrAdminStatus,
--           mscAtmIfUniSigStorageType,
--           mscAtmIfVptUniSide,
--           mscAtmIfVptUniCallingAScrDefaultInsertionAddress,
--           mscAtmIfUniCallingAScrDefaultInsertionAddress,
--           mscAtmIfUniIlmiRxPdus,
--           mscAtmIfVptUniCallingAScrAdminStatus,
--           mscAtmIfVptUniAccountClass,
--           mscAtmIfUniSoftPvpAndPvcRetryPeriod,
--           mscAtmIfVptUniVpci,
--           mscAtmIfUniSigVcdAtmServiceCategory,
--           mscAtmIfUniAddrPnniInfoScope,
--           mscAtmIfUniIlmiOperatingMode }
-- STATUS  mandatory
-- DESCRIPTION
--   "A list of all current accessible leaf objects."

atmUniGroup OBJECT IDENTIFIER ::= { atmUniMIB 1 }
atmUniGroupCA OBJECT IDENTIFIER ::= { atmUniGroup 1 }
atmUniGroupCA02 OBJECT IDENTIFIER ::= { atmUniGroupCA 3 }
atmUniGroupCA02A OBJECT IDENTIFIER ::= { atmUniGroupCA02 2 }



-- Agent-Capabilities Statement:

-- PRODUCT-RELEASE "MscPassport Release 1.2 AtmUni."
-- STATUS          mandatory
-- DESCRIPTION     "Carrier Passport AtmUni MIB: MIB Version CA02A,
--                  Software Version CA02S9C."
-- SUPPORTS        Nortel-MsCarrier-MscPassport-AtmUniMIB
--    INCLUDES     { atmUniGroupCA02A }

atmUniCapabilities OBJECT IDENTIFIER ::= { atmUniMIB 3 }
atmUniCapabilitiesCA OBJECT IDENTIFIER ::= { atmUniCapabilities 1 }
atmUniCapabilitiesCA02 OBJECT IDENTIFIER ::= { atmUniCapabilitiesCA 3 }
atmUniCapabilitiesCA02A OBJECT IDENTIFIER ::= { atmUniCapabilitiesCA02 2 }





END
