IP-SERVICES-MIB DEFINITIONS ::= BEGIN

-- Referencing the parent branch.

IMPORTS
            MODULE-IDENTITY, OBJECT-TYPE, IpAddress		FROM SNMPv2-SMI
	    RowStatus					FROM SNMPv2-TC
	    cjnProtocol                             	FROM Cajun-ROOT; 

cjnIpv4Serv MODULE-IDENTITY
        LAST-UPDATED "9902110000Z" -- Wednesday Feb 10, 1999"
        ORGANIZATION "Avaya's Concord Technology Center (CTC)"
        CONTACT-INFO
	        "Julie Flannery -- jflannery@avaya.com
		 Lilia Veksler -- lveksler@avaya.com"
	DESCRIPTION
       		"Cajun Private IP version 4 services MIB"
	::= { cjnProtocol 5 }

-- IP IRDP (Internet Router Discovery Protocol) Group
--
	cjnIpIRDPGblGroup	OBJECT IDENTIFIER ::= { cjnIpv4Serv 1 }
	
	cjnIpIRDPIfTable OBJECT-TYPE
           SYNTAX  SEQUENCE OF CjnIpIRDPIfEntry
           MAX-ACCESS  not-accessible
           STATUS  current
           DESCRIPTION
           "A list of interface specific IRDP Entries"
	   ::= {cjnIpIRDPGblGroup 1 }

	cjnIpIRDPIfEntry OBJECT-TYPE
	   SYNTAX  CjnIpIRDPIfEntry
           MAX-ACCESS  not-accessible
           STATUS  current
           DESCRIPTION
           "An cajun IRDP Interface instance "
           INDEX   { cjnIpIRDPIfIndex }
           ::= { cjnIpIRDPIfTable 1 }

	CjnIpIRDPIfEntry ::=
	   SEQUENCE {
		cjnIpIRDPIfIndex
			INTEGER,
		cjnIpIfIRDPEnabled
			INTEGER,
		cjnIpIfIRDPTxType
			INTEGER,
		cjnIpIfIRDPPref
			INTEGER,
		cjnIpIRDPTimerMax
			INTEGER,
		cjnIpIRDPTimerMin
			INTEGER,
		cjnIpIRDPLifetime
			INTEGER
		}		
		
	cjnIpIRDPIfIndex OBJECT-TYPE
              SYNTAX  INTEGER
	      MAX-ACCESS  read-only
              STATUS  current
              DESCRIPTION
              "The globally unique identifier for this interface. This number
	MUST correlate with the IfTable's IfIndex in MIB-II or RFC2233"
	      ::= { cjnIpIRDPIfEntry 1 } 

	cjnIpIfIRDPEnabled OBJECT-TYPE
              SYNTAX  INTEGER {
		enabled(1),
		disabled(2)
		}	
              MAX-ACCESS  read-create
              STATUS  current
              DESCRIPTION
                      "enables / disables the origination of IGMP Router discovery
	(IRDP) messages on this interface."
	      DEFVAL {1}
	      ::= { cjnIpIRDPIfEntry 2 }

	cjnIpIfIRDPTxType OBJECT-TYPE
              SYNTAX  INTEGER {
		multicast(1),
		broadcast(2)
		}	
              MAX-ACCESS  read-create
              STATUS  current
              DESCRIPTION
                      "Selects the transmission method of IRDP messages from this
	interface."
	      DEFVAL {1}
	      ::= { cjnIpIRDPIfEntry 3 }

	cjnIpIfIRDPPref OBJECT-TYPE
              SYNTAX  INTEGER 
              MAX-ACCESS  read-create
              STATUS  current
              DESCRIPTION
                      "The IRDP Preference Level used in IRDP updates for this interface."
	      DEFVAL {0}
	      ::= { cjnIpIRDPIfEntry 4 }

	cjnIpIRDPTimerMax OBJECT-TYPE
	   SYNTAX INTEGER
	   MAX-ACCESS read-create
	   STATUS current
	   DESCRIPTION
	   "Router Discovery Max. Advertisement Interval (sec) "
	   DEFVAL {600}
	   ::= { cjnIpIRDPIfEntry 5 }
	
	cjnIpIRDPTimerMin OBJECT-TYPE
	   SYNTAX INTEGER
	   MAX-ACCESS read-create
	   STATUS current
	   DESCRIPTION
	   "Router Discovery Min. Advertisement Interval (sec) "
	   DEFVAL {450}
	   ::= { cjnIpIRDPIfEntry 6 }

	cjnIpIRDPLifetime  OBJECT-TYPE
	   SYNTAX INTEGER
	   MAX-ACCESS read-create
	   STATUS current
	   DESCRIPTION
	   "Router Discovery Advertisement Lifetime (sec) "
	   DEFVAL {900}
	   ::= { cjnIpIRDPIfEntry 7 }

-- IP Bootp Relay (Boot Protocol) Group
--
	cjnIpBootpRelayGroup  OBJECT IDENTIFIER ::= { cjnIpv4Serv 2 }

	cjnBootpRelayEnabled OBJECT-TYPE
	   SYNTAX INTEGER {
		enabled(1),
		disabled(2)
		}
	   MAX-ACCESS read-create
	   STATUS current
	   DESCRIPTION
	   "Accept client requests for an IP address and forwards
	them to a server. This agent also relays responses from 
	the server to the client."
	   ::= { cjnIpBootpRelayGroup 1 }

	cjnBootpRelayTable OBJECT-TYPE
           SYNTAX  SEQUENCE OF CjnBootpRelayEntry
           MAX-ACCESS  not-accessible
           STATUS  current
           DESCRIPTION
           "A list of Bootp Relay Server Entries"
	   ::= { cjnIpBootpRelayGroup 2 }

	cjnBootpRelayEntry OBJECT-TYPE
	   SYNTAX  CjnBootpRelayEntry
           MAX-ACCESS  not-accessible
           STATUS  current
           DESCRIPTION
           "An cajun Bootp Relay instance "
           INDEX   { cjnBootpRelayServAddr }
           ::= { cjnBootpRelayTable 1 }

	CjnBootpRelayEntry ::=
	   SEQUENCE {
		cjnBootpRelayServAddr
			IpAddress,
		cjnBootpRelayRowStatus
			RowStatus
		}		
		
	cjnBootpRelayServAddr OBJECT-TYPE
              SYNTAX  IpAddress
	      MAX-ACCESS  read-create
              STATUS  current
              DESCRIPTION
              "The identifier the IP address for a bootp server"
	      ::= { cjnBootpRelayEntry 1 } 

	cjnBootpRelayRowStatus OBJECT-TYPE
              SYNTAX  RowStatus	
              MAX-ACCESS  read-create
              STATUS  current
              DESCRIPTION
                      "The Status of this entry in the table.  Note the
	available states: 
	active(1), -- Obviously Active.
	notInService(2) -- Interface configured but disabled.
	notReady(3), -- Interface NOT configured.
	createAndGo(4), 
	createAndWait(5)  
	or destroy(6) "
	      ::= { cjnBootpRelayEntry 2 } 


-- Bootp Server Stats
--
	cjnIpBootpServStats	OBJECT IDENTIFIER ::= { cjnIpv4Serv 3 }

	cjnBtprInReqs OBJECT-TYPE
	   SYNTAX INTEGER
	   MAX-ACCESS read-create
	   STATUS current
	   DESCRIPTION
	   " "
	   ::= { cjnIpBootpServStats 1 }

	cjnBtprInRsps OBJECT-TYPE
	   SYNTAX INTEGER
	   MAX-ACCESS read-create
	   STATUS current
	   DESCRIPTION
	   " "
	   ::= { cjnIpBootpServStats 2 }

	cjnBtprInDiscards OBJECT-TYPE
	   SYNTAX INTEGER
	   MAX-ACCESS read-create
	   STATUS current
	   DESCRIPTION
	   " "
	   ::= { cjnIpBootpServStats 3 }

	cjnBtprInHopsExceededs OBJECT-TYPE
	   SYNTAX INTEGER
	   MAX-ACCESS read-create
	   STATUS current
	   DESCRIPTION
	   " "
	   ::= { cjnIpBootpServStats 4 }

	cjnBtprOutReqs OBJECT-TYPE
	   SYNTAX INTEGER
	   MAX-ACCESS read-create
	   STATUS current
	   DESCRIPTION
	   " "
	   ::= { cjnIpBootpServStats 5 }

	cjnBtprOutRsps OBJECT-TYPE
	   SYNTAX INTEGER
	   MAX-ACCESS read-create
	   STATUS current
	   DESCRIPTION
	   " "
	   ::= { cjnIpBootpServStats 6 }

-- IP Helper Address Group
--
	cjnIpHelperAddressGroup  OBJECT IDENTIFIER ::= { cjnIpv4Serv 4 }

	cjnIpHelperAddressTable OBJECT-TYPE
           SYNTAX  SEQUENCE OF CjnIpHelperAddressEntry
           MAX-ACCESS  not-accessible
           STATUS  current
           DESCRIPTION
           "A list of interface specific Helper Address Entries"
	   ::= {cjnIpHelperAddressGroup 1 }

	cjnIpHelperAddressEntry OBJECT-TYPE
	   SYNTAX  CjnIpHelperAddressEntry
           MAX-ACCESS  not-accessible
           STATUS  current
           DESCRIPTION
           "A helper address instance "
           INDEX   { cjnIpHelperAddressIfIndex,
			cjnIpHelperAddressAddr }
           ::= { cjnIpHelperAddressTable 1 }

	CjnIpHelperAddressEntry ::=
	   SEQUENCE {
		cjnIpHelperAddressIfIndex
				INTEGER,
		cjnIpHelperAddressAddr
				IpAddress,
		cjnIpHelperAddressTFTP
				INTEGER,
		cjnIpHelperAddressDNS
				INTEGER,
		cjnIpHelperAddressTime
				INTEGER,
		cjnIpHelperAddressNetBiosName
				INTEGER,
		cjnIpHelperAddressNetBiosData
				INTEGER,
		cjnIpHelperAddressBootpServ
				INTEGER,
		cjnIpHelperAddressBootpClient
				INTEGER,
		cjnIpHelperAddressTacacs
				INTEGER
		}		
		
	cjnIpHelperAddressIfIndex OBJECT-TYPE
	      SYNTAX  INTEGER
	      MAX-ACCESS  read-create
              STATUS  current
              DESCRIPTION
              "The globally unique identifier for this interface. This number
	       MUST correlate with the IfTable's IfIndex in MIB-II or RFC2233"
	      ::= { cjnIpHelperAddressEntry 1}


	cjnIpHelperAddressAddr OBJECT-TYPE
              SYNTAX  IpAddress
	      MAX-ACCESS  read-create
              STATUS  current
              DESCRIPTION
              "The identifier the IP address for a helper address."
	      ::= { cjnIpHelperAddressEntry 2}

	cjnIpHelperAddressTFTP OBJECT-TYPE
	      SYNTAX  INTEGER
		{		
		enabled(1),
		disabled(2)
		}
	      MAX-ACCESS  read-create
	      STATUS  current
	      DESCRIPTION
	      "Enable or disable sending TFTP broadcast to the helper address."
	      ::= { cjnIpHelperAddressEntry 4 }

	cjnIpHelperAddressDNS OBJECT-TYPE
	      SYNTAX  INTEGER
		{		
		enabled(1),
		disabled(2)
		}
	      MAX-ACCESS  read-create
	      STATUS  current
	      DESCRIPTION
	      "Enable or disable sending DNS broadcast to the helper address."
	      ::= { cjnIpHelperAddressEntry 5 }

	cjnIpHelperAddressTime OBJECT-TYPE
	      SYNTAX  INTEGER
		{		
		enabled(1),
		disabled(2)
		}
	      MAX-ACCESS  read-create
	      STATUS  current
	      DESCRIPTION
	      "Enable or disable sending Time broadcast to the helper address."
	      ::= { cjnIpHelperAddressEntry 6}

	cjnIpHelperAddressNetBiosName OBJECT-TYPE
	      SYNTAX  INTEGER
		{		
		enabled(1),
		disabled(2)
		}
	      MAX-ACCESS  read-create
	      STATUS  current
	      DESCRIPTION
	      "Enable or disable sending NetBios Name Service broadcast to the helper address."
	      ::= { cjnIpHelperAddressEntry 7}

	cjnIpHelperAddressNetBiosData OBJECT-TYPE
	      SYNTAX  INTEGER
		{		
		enabled(1),
		disabled(2)
		}
	      MAX-ACCESS  read-create
	      STATUS  current
	      DESCRIPTION
	      "Enable or disable sending NetBios Data  broadcast to the helper address."
	      ::= { cjnIpHelperAddressEntry 8}

	cjnIpHelperAddressBootpServ OBJECT-TYPE
	      SYNTAX  INTEGER
		{		
		enabled(1),
		disabled(2)
		}
	      MAX-ACCESS  read-create
	      STATUS  current
	      DESCRIPTION
	      "Enable or disable sending Bootp Server broadcast to the helper address."
	      ::= { cjnIpHelperAddressEntry 9}

	cjnIpHelperAddressBootpClient OBJECT-TYPE
	      SYNTAX  INTEGER
		{		
		enabled(1),
		disabled(2)
		}
	      MAX-ACCESS  read-create
	      STATUS  current
	      DESCRIPTION
	      "Enable or disable sending Bootp Client broadcast to the helper address."
	      ::= { cjnIpHelperAddressEntry 10}

	cjnIpHelperAddressTacacs OBJECT-TYPE
	      SYNTAX  INTEGER
		{		
		enabled(1),
		disabled(2)
		}
	      MAX-ACCESS  read-create
	      STATUS  current
	      DESCRIPTION
	      "Enable or disable sending Tacacs broadcast to the helper address."
	      ::= { cjnIpHelperAddressEntry 11}

-- IP DHCP Option 82 (DHCP Agent Relay Protocol) Group
--
	cjnIpDHCPOption82Group  OBJECT IDENTIFIER ::= { cjnIpv4Serv 5 }

	cjnDHCPOpt82Sub1Enabled OBJECT-TYPE
	   SYNTAX INTEGER {
		enabled(1),
		disabled(2)
		}
	   MAX-ACCESS read-write
	   STATUS current
	   DESCRIPTION
	   "Enable or disable inserting Option 82 Circuit Id information (slot and port numbers) into DHCP packets."
	   ::= { cjnIpDHCPOption82Group 1 }

   cjnDHCPOpt82Sub2Enabled OBJECT-TYPE
	   SYNTAX INTEGER {
		enabled(1),
		disabled(2)
		}
	   MAX-ACCESS read-write
	   STATUS current
	   DESCRIPTION
	   "Enable or disable inserting Option 82 Agent Id information (IP Address and System Name of the switch) into DHCP packets."
	   ::= { cjnIpDHCPOption82Group 2 }

END
