-- *****************************************************************
-- CISCO-MAU-EXT-CAPABILITY.my:
-- Cisco CISCO-MAU-EXT-MIB AGENT-CAPABILITIES
--
-- December 2004, Binh P Le
--
-- Copyright (c) 2004 by Cisco Systems, Inc.
-- All rights reserved.
-- *****************************************************************

CISCO-MAU-EXT-CAPABILITY DEFINITIONS ::= BEGIN

IMPORTS
        MODULE-IDENTITY
                FROM SNMPv2-SMI
        AGENT-CAPABILITIES
                FROM SNMPv2-CONF
        ciscoAgentCapability
                FROM CISCO-SMI;

ciscoMauExtCapability MODULE-IDENTITY
        LAST-UPDATED    "200412310000Z"
        ORGANIZATION    "Cisco Systems, Inc."
        CONTACT-INFO
                "       Cisco Systems
                        Customer Service

                Postal: 170 West Tasman Drive
                        San Jose, CA  95134
                        USA

                   Tel: +1 800 553-NETS

                E-mail: cs-lan-switch-snmp@cisco.com"
        DESCRIPTION
                "The capabilities description of CISCO-MAU-EXT-MIB."

        REVISION        "200412310000Z"
        DESCRIPTION
                "Initial version of this MIB module."
        ::= { ciscoAgentCapability 404 }

ciscoMauExtCapCatOSV08R0401 AGENT-CAPABILITIES
    PRODUCT-RELEASE     "Cisco CatOS 8.4(1)."
    STATUS              current
    DESCRIPTION         "CISCO-MAU-EXT-MIB capabilities."

    SUPPORTS            CISCO-MAU-EXT-MIB
        INCLUDES        { cmExtJackConfigGroup, 
                          cmExtIfAutoMdixConfigGroup }
    ::= { ciscoMauExtCapability 1 }

END
