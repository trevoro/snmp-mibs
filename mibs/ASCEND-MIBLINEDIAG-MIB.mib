--			Ascend miblinediag MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBLINEDIAG-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibmibProfLineDiag  OBJECT IDENTIFIER ::= { configuration 145}

	-- The mibmibProfLineDiag table
	--
	-- This table contains parameters for the mibmibProfLineDiag profile
	--

    mibmibProfLineDiagTable	OBJECT-TYPE
	SYNTAX		SEQUENCE OF MibmibProfLineDiagEntry
	ACCESS		not-accessible
	STATUS		mandatory
	DESCRIPTION	"A list of mibmibProfLineDiag profile entries."
	::= { mibmibProfLineDiag 1 }

    mibmibProfLineDiagEntry	OBJECT-TYPE
	SYNTAX		MibmibProfLineDiagEntry
	ACCESS		not-accessible
	STATUS		mandatory
	DESCRIPTION	"A mibmibProfLineDiag entry containing objects that
			 maps to the parameters of mibmibProfLineDiag profile."
	INDEX		{ mibProfLineDiag-Shelf-o, mibProfLineDiag-Slot-o, mibProfLineDiag-Item-o }
	::= { mibmibProfLineDiagTable 1 }

    MibmibProfLineDiagEntry ::=
	SEQUENCE {
	    mibProfLineDiag-Shelf-o
		INTEGER,
	    mibProfLineDiag-Slot-o
		INTEGER,
	    mibProfLineDiag-Item-o
		INTEGER,
	    mibProfLineDiag-PhysicalAddress-Shelf
		INTEGER,
	    mibProfLineDiag-PhysicalAddress-Slot
		INTEGER,
	    mibProfLineDiag-PhysicalAddress-ItemNumber
		INTEGER,
	    mibProfLineDiag-BertTimer
		INTEGER,
	    mibProfLineDiag-BertEnable
		INTEGER,
	    mibProfLineDiag-IdtEnable
		INTEGER,
	    mibProfLineDiag-IdtNumOfMsg
		INTEGER,
	    mibProfLineDiag-Action-o
		INTEGER
	}

    mibProfLineDiag-Shelf-o	OBJECT-TYPE
	SYNTAX	INTEGER
	ACCESS	read-only
	STATUS	mandatory
	DESCRIPTION	""
	::= { mibmibProfLineDiagEntry 1 }

    mibProfLineDiag-Slot-o	OBJECT-TYPE
	SYNTAX	INTEGER
	ACCESS	read-only
	STATUS	mandatory
	DESCRIPTION	""
	::= { mibmibProfLineDiagEntry 2 }

    mibProfLineDiag-Item-o	OBJECT-TYPE
	SYNTAX	INTEGER
	ACCESS	read-only
	STATUS	mandatory
	DESCRIPTION	""
	::= { mibmibProfLineDiagEntry 3 }

    mibProfLineDiag-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibmibProfLineDiagEntry 4 }

    mibProfLineDiag-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibmibProfLineDiagEntry 5 }

    mibProfLineDiag-PhysicalAddress-ItemNumber	OBJECT-TYPE
	SYNTAX	INTEGER
	ACCESS	read-write
	STATUS	mandatory
	DESCRIPTION	"A number that specifies an addressable entity within the context of shelf and slot."
	::= { mibmibProfLineDiagEntry 6 }

    mibProfLineDiag-BertTimer	OBJECT-TYPE
	SYNTAX	INTEGER {
		    n-1Minute (60001),
		    n-2Minutes (120001),
		    n-3Minutes (180001),
		    n-4Minutes (240001),
		    n-5Minutes (300001),
		    n-10Minutes (600001),
		    n-15Minutes (900001),
		    n-20Minutes (1200001),
		    n-30Minutes (1800001)
		}
	ACCESS	read-write
	STATUS	mandatory
	DESCRIPTION	"When this time period expires the BER Test is stopped."
	::= { mibmibProfLineDiagEntry 7 }

    mibProfLineDiag-BertEnable	OBJECT-TYPE
	SYNTAX	INTEGER {
		    no (1),
		    yes (2)
		}
	ACCESS	read-write
	STATUS	mandatory
	DESCRIPTION	"To enable the BER test set this parameter to yes."
	::= { mibmibProfLineDiagEntry 8 }

    mibProfLineDiag-IdtEnable	OBJECT-TYPE
	SYNTAX	INTEGER {
		    no (1),
		    yes (2)
		}
	ACCESS	read-write
	STATUS	mandatory
	DESCRIPTION	"To enable the IDT test set this parameter to yes."
	::= { mibmibProfLineDiagEntry 9 }

    mibProfLineDiag-IdtNumOfMsg	OBJECT-TYPE
	SYNTAX	INTEGER
	ACCESS	read-write
	STATUS	mandatory
	DESCRIPTION	"Number of Messages to be sent for the IDT test."
	::= { mibmibProfLineDiagEntry 10 }

    mibProfLineDiag-Action-o	OBJECT-TYPE
	SYNTAX	INTEGER {
		    noAction (1),
		    createProfile (2),
		    deleteProfile (3)
		}
	ACCESS	read-write
	STATUS	mandatory
	DESCRIPTION	""
	::= { mibmibProfLineDiagEntry 11 }

END
