VOLUBILL-ROOT-MIB DEFINITIONS ::= BEGIN

IMPORTS
	enterprises
		FROM RFC1155-SMI;


volubill OBJECT IDENTIFIER ::= { enterprises 9905 }

vlbProducts OBJECT IDENTIFIER ::= { volubill 1 }

vlbComponents OBJECT IDENTIFIER ::= { volubill 2 }


END
