CXChassis2-MIB DEFINITIONS ::= BEGIN

IMPORTS
--	Counter, Gauge, TimeTicks, IpAddress, enterprises
--				FROM RFC1155-SMI
OBJECT-TYPE		FROM RFC-1212
--	DisplayString		FROM RFC1213-MIB;
--	RowStatus			FROM SNMPv2-TC;
--	IANAifType		FROM IANAifType-MIB;
cxChassis2		FROM CXProduct-SMI;


cxChassIfAdmGroup	OBJECT IDENTIFIER	::= { cxChassis2 5 }
--  to following keeps the ifStack Table in lines with what is specified in RFC-1573.
ifMIB		OBJECT IDENTIFIER	::= { cxChassis2 6 }
ifMIBObjects	OBJECT IDENTIFIER	::= { ifMIB 1 }



-- Proprietary Data Types

-- RowStatus is defined in SNMPv2-TC (Textual Conventions) (RFC1903) as follows:
--  RowStatus ::= INTEGER {
--		the following two values are states:
--		these values may be read or written
--		active(1),
--		notInService(2),
--		the following value is a state:
--		this value may be read, but not written
--		notReady(3),
--		the following three values are
--		actions: these values may be written,
--		but are never read
--		createAndGo(4),
--		createAndWait(5),
--		destroy(6)
--		}
--
-- for simplicity, we define RowStatus as follows:
RowStatus	::=     INTEGER {
invalid         (1),
valid           (2)
}


-- This MIB consists of the following:
-- (1)  InterfaceAdministration group
-- (2)  Interface Stacking group



--  Interface Administration group

--  This group controls the addition and deletion of interfaces above the physical level ,
--  (commonly known as logical interfaces).


cxChassLogIfAdmTable OBJECT-TYPE
SYNTAX  SEQUENCE OF CxChassLogIfAdmEntry
ACCESS  not-accessible
STATUS  mandatory
DESCRIPTION
  "A table containing mappings from ifIndex to CPU, type and logical channel."
::= { cxChassIfAdmGroup 2 }


cxChassLogIfAdmEntry OBJECT-TYPE
SYNTAX  CxChassLogIfAdmEntry
ACCESS  not-accessible
STATUS  mandatory
DESCRIPTION
  "Row representing a mapping entry of ifIndex to CPU, type and logical channel."
INDEX  { cxChassLogIfAdmCpuIndex,
cxChassLogIfAdmIfType,
cxChassLogIfAdmChannelIndex }
::= { cxChassLogIfAdmTable 1 }


CxChassLogIfAdmEntry::=
SEQUENCE {
cxChassLogIfAdmCpuIndex			INTEGER,	-- 1
cxChassLogIfAdmIfType			INTEGER,	-- 2
cxChassLogIfAdmChannelIndex			INTEGER,	-- 3
cxChassLogIfAdmIfIndex			INTEGER,	-- 4
cxChassLogIfAdmRowStatus			RowStatus		-- 5
}


cxChassLogIfAdmCpuIndex OBJECT-TYPE
SYNTAX  INTEGER (1..65535)
ACCESS  read-only
STATUS  mandatory
DESCRIPTION
  "The CPU number which corresponds to the slot number in the chassis.  For example, a row for CPU in slot 2 will use value '2'.  For single CPU chassis, the value to be used is '1'."
::= { cxChassLogIfAdmEntry 1 }



cxChassLogIfAdmIfType OBJECT-TYPE
--	SYNTAX  IANAifType
SYNTAX  INTEGER (1..255)
ACCESS  read-write
STATUS  mandatory
DESCRIPTION
"The type of interface to be created."
::= { cxChassLogIfAdmEntry 2 }


cxChassLogIfAdmChannelIndex OBJECT-TYPE
SYNTAX  INTEGER
ACCESS  read-only
STATUS  mandatory
DESCRIPTION
"The channel number belonging to a port in the IO card in a CPU.  If  the port is not channelized, then it will have only one entry in the table with this object set to value '1'.

Within our system, a channel will be associated with its own service access point, thus requiring the use of a service access point control block.  This object therefore takes on the sap control block identification.  Due to the internal sap control block numbering limitation, this object will be restricted in range from 1 to 255, but may be expanded when the internal limitations are lifted."
::= { cxChassLogIfAdmEntry 3 }


cxChassLogIfAdmIfIndex OBJECT-TYPE
SYNTAX  INTEGER (1..65535)
ACCESS  read-write
STATUS  mandatory
DESCRIPTION
"The Interface index which corressponds to the ifIndex in the ifTable.  If this value is specified, then it is the registered ifIndex used for the interface, otherwise the ifIndex will be obtained from the ifTable."
DEFVAL { 0 }
::= { cxChassLogIfAdmEntry 4 }


cxChassLogIfAdmRowStatus OBJECT-TYPE
SYNTAX  RowStatus
ACCESS  read-write
STATUS  mandatory
DESCRIPTION
"Used to create and deleted rows in this table."
DEFVAL { valid }
::= { cxChassLogIfAdmEntry 5 }



--  Interface Stacking group

--  This group is borrowed from RFC-1573 "Evolution of the Interfaces Group of MIB-II", and has been
--  converted from SNMPv2 to SNMPv1.
--
--  RFC-1573 will eventually succeed the current MIB-II defined in RFC-1213, and when it deso, this group
--  should be removed from this MIB.
--
--  This group contains objects that define the relationships among the sub-layers of an interface.


ifStackTable  OBJECT-TYPE
SYNTAX  SEQUENCE OF IfStackEntry
ACCESS  not-accessible
STATUS  mandatory
DESCRIPTION
  "The table containing information on the relationships between the multiple sub-layers of network interfaces.  In particular, it contains information on which sub-layers run 'on top of' which other sub-layers.  Each sub-layer corresponds to a conceptual row in the ifTable."
        ::= { ifMIBObjects 2 }


   ifStackEntry  OBJECT-TYPE
SYNTAX  IfStackEntry
ACCESS  not-accessible
STATUS  mandatory
DESCRIPTION
  "Information on a particular relationship between two sub-layers, specifying that one sub-layer runs on 'top' of the other sub-layer.  Each sub-layer corresponds to a conceptual row in the ifTable."
INDEX {  ifStackHigherLayer,
ifStackLowerLayer }
::= { ifStackTable 1 }


IfStackEntry ::=
SEQUENCE {
ifStackHigherLayer				INTEGER,	-- 1
ifStackLowerLayer				INTEGER,	-- 2
ifStackStatus				RowStatus		-- 3
}


ifStackHigherLayer  OBJECT-TYPE
SYNTAX  INTEGER
ACCESS  read-only
STATUS  mandatory
DESCRIPTION
"The value of ifIndex corresponding to the higher sub-layer of the relationship, i.e., the sub-layer which runs on 'top' of the sub-layer identified by the corresponding instance of ifStackLowerLayer.  If there is no higher sub-layer (below the internetwork layer), then this object has the value 0."
::= { ifStackEntry 1 }


ifStackLowerLayer  OBJECT-TYPE
SYNTAX  INTEGER
ACCESS  read-only
STATUS  mandatory
DESCRIPTION
"The value of ifIndex corresponding to the lower sub-layer of the relationship, i.e., the sub-layer which runs 'below' the sub-layer identified by the corresponding instance of ifStackHigherLayer.  If there is no lower sub-layer, then this object has the value 0."
::= { ifStackEntry 2 }


   ifStackStatus  OBJECT-TYPE
SYNTAX  RowStatus
ACCESS  read-write
STATUS  mandatory
DESCRIPTION
"The status of the relationship between two sub-layers.

Changing the value of this object from 'active' to 'notInService' or 'destroy' will likely have consequences up and down the interface stack.  Thus, write access to this object is likely to be inappropriate for some types of interfaces, and many implementations will choose not to support write-access for any type of interface."
::= { ifStackEntry 3 }

END
