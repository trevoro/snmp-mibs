INFORMANT-WMI-EXCHANGE DEFINITIONS ::= BEGIN

IMPORTS
    MODULE-IDENTITY, OBJECT-TYPE, Gauge32, Integer32
        FROM SNMPv2-SMI
    DateAndTime, TruthValue, DisplayString
        FROM SNMPv2-TC
    informant
        FROM WTCS;

wmiExchange MODULE-IDENTITY
    LAST-UPDATED "200804141717Z"
    ORGANIZATION "Informant Systems, Inc."
    CONTACT-INFO
            "Garth Williams
             11135-23A Ave
             Edmonton, AB  T6J4W5  Canada
             Tel: +1 780 434 4113
             E-mail: garth.williams@wtcs.org"
    DESCRIPTION
            "The MIB module for informant exchange WMI entities."
    REVISION      "200804141717Z"
    DESCRIPTION
            "Updated the description fields based on the WMI
             entries. Added the following missing Exchange WMI
             classes: exchangeQueuedSMTPMessageTable,
             exchangeQueuedX400MessageTable,
             exchangeQueueSMTPVirtualSrvTable,
             exchangeQueueX400VirtualSrvTable,
             exchangeScheduleIntervalTable,
             exchangeSMTPLinkTable,
             exchangeSMTPQueueTable,
             exchangeX400LinkTable,
             and exchangeX400QueueTable"
    REVISION      "200504110409Z"
    DESCRIPTION
            "The initial revision of this MIB module."
    ::= { informant 23 }

exchangeClusterResourceTable OBJECT-TYPE
    SYNTAX     SEQUENCE OF ExchangeClusterResourceEntry
    MAX-ACCESS not-accessible
    STATUS     current
    DESCRIPTION
        "The ExchangeClusterResource WMI class has properties that return
        information about a Microsoft Exchange cluster resource."
    ::= { wmiExchange 1 }

exchangeClusterResourceEntry OBJECT-TYPE
    SYNTAX     ExchangeClusterResourceEntry
    MAX-ACCESS not-accessible
    STATUS     current
    DESCRIPTION
        "None"
    INDEX      { excrIndex }
    ::= { exchangeClusterResourceTable 1 }

ExchangeClusterResourceEntry ::= SEQUENCE {
    excrIndex Integer32,
    excrName DisplayString,
    excrOwner DisplayString,
    excrState Gauge32,
    excrType DisplayString,
    excrVirtualMachine DisplayString
}

excrIndex OBJECT-TYPE
    SYNTAX     Integer32 (1..2147483647)
    MAX-ACCESS read-only
    STATUS     current
    DESCRIPTION
        "The value of this object uniquely identifies the instance entry
        for this class."
    ::= { exchangeClusterResourceEntry 1 }

excrName OBJECT-TYPE
    SYNTAX     DisplayString
    MAX-ACCESS read-only
    STATUS     current
    DESCRIPTION
        "The Name property returns the name of the Microsoft Exchange
        cluster resource. The Name property is read-only, and is a key
        property of this class."
    ::= { exchangeClusterResourceEntry 2 }

excrOwner OBJECT-TYPE
    SYNTAX     DisplayString
    MAX-ACCESS read-only
    STATUS     current
    DESCRIPTION
        "The Owner property for a cluster resource specifies the cluster
        node of which the resource is a part. The Owner property is
        read-only."
    ::= { exchangeClusterResourceEntry 3 }

excrState OBJECT-TYPE
    SYNTAX     Gauge32
    MAX-ACCESS read-only
    STATUS     current
    DESCRIPTION
        "The State property specifies the current state of the cluster
        resource."
    ::= { exchangeClusterResourceEntry 4 }

excrType OBJECT-TYPE
    SYNTAX     DisplayString
    MAX-ACCESS read-only
    STATUS     current
    DESCRIPTION
        "The Type property specifies the resource type."
    ::= { exchangeClusterResourceEntry 5 }

excrVirtualMachine OBJECT-TYPE
    SYNTAX     DisplayString
    MAX-ACCESS read-only
    STATUS     current
    DESCRIPTION
        "The Type property specifies the resource type."
    ::= { exchangeClusterResourceEntry 6 }

exchangeConnectorStateTable OBJECT-TYPE
    SYNTAX     SEQUENCE OF ExchangeConnectorStateEntry
    MAX-ACCESS not-accessible
    STATUS     current
    DESCRIPTION
        "The ExchangeConnectorState WMI class has properties that return
        information about a Microsoft Exchange connector."
    ::= { wmiExchange 2 }

exchangeConnectorStateEntry OBJECT-TYPE
    SYNTAX     ExchangeConnectorStateEntry
    MAX-ACCESS not-accessible
    STATUS     current
    DESCRIPTION
        "None"
    INDEX      { excsIndex }
    ::= { exchangeConnectorStateTable 1 }

ExchangeConnectorStateEntry ::= SEQUENCE {
    excsIndex Integer32,
    excsDN DisplayString,
    excsGroupDN DisplayString,
    excsGroupGUID DisplayString,
    excsGUID DisplayString,
    excsIsUp TruthValue,
    excsName DisplayString
}

excsIndex OBJECT-TYPE
    SYNTAX     Integer32 (1..2147483647)
    MAX-ACCESS read-only
    STATUS     current
    DESCRIPTION
        "The value of this object uniquely identifies the instance entry
        for this class."
    ::= { exchangeConnectorStateEntry 1 }

excsDN OBJECT-TYPE
    SYNTAX     DisplayString
    MAX-ACCESS read-only
    STATUS     current
    DESCRIPTION
        "The DN property specifies the Microsoft Active Directory
        distinguished name (DN) of the Exchange Connector object."
    ::= { exchangeConnectorStateEntry 2 }

excsGroupDN OBJECT-TYPE
    SYNTAX     DisplayString
    MAX-ACCESS read-only
    STATUS     current
    DESCRIPTION
        "The GroupDN property specifies the distinguished name (DN) in
        Active Directory of the routing group."
    ::= { exchangeConnectorStateEntry 3 }

excsGroupGUID OBJECT-TYPE
    SYNTAX     DisplayString
    MAX-ACCESS read-only
    STATUS     current
    DESCRIPTION
        "The GroupGUID property specifies the globally unique identifier
        (GUID) of the routing group."
    ::= { exchangeConnectorStateEntry 4 }

excsGUID OBJECT-TYPE
    SYNTAX     DisplayString
    MAX-ACCESS read-only
    STATUS     current
    DESCRIPTION
        "The GUID property specifies the GUID of the Exchange Connector."
    ::= { exchangeConnectorStateEntry 5 }

excsIsUp OBJECT-TYPE
    SYNTAX     TruthValue
    MAX-ACCESS read-only
    STATUS     current
    DESCRIPTION
        "The IsUp property, when True, specifies that the Exchange
        Connector is operating normally."
    ::= { exchangeConnectorStateEntry 6 }

excsName OBJECT-TYPE
    SYNTAX     DisplayString
    MAX-ACCESS read-only
    STATUS     current
    DESCRIPTION
        "The Name property specifies the name of the Exchange Connector."
    ::= { exchangeConnectorStateEntry 7 }

exchangeLinkTable OBJECT-TYPE
    SYNTAX     SEQUENCE OF ExchangeLinkEntry
    MAX-ACCESS not-accessible
    STATUS     current
    DESCRIPTION
        "The ExchangeLink WMI class has properties that return information
        about message-handling links between mail servers. A link can
        contain zero or more ExchangeQueue objects, depending on the
        current message traffic along the link. In the Exchange System
        Manager, these links are called queues."
    ::= { wmiExchange 3 }

exchangeLinkEntry OBJECT-TYPE
    SYNTAX     ExchangeLinkEntry
    MAX-ACCESS not-accessible
    STATUS     current
    DESCRIPTION
        "None"
    INDEX      { exlIndex }
    ::= { exchangeLinkTable 1 }

ExchangeLinkEntry ::= SEQUENCE {
    exlIndex Integer32,
    exlActionFreeze TruthValue,
    exlActionKick TruthValue,
    exlActionThaw TruthValue,
    exlExtendedStateInfo DisplayString,
    exlGlobalStop TruthValue,
    exlIncreasingTime Gauge32,
    exlLinkDN DisplayString,
    exlLinkName DisplayString,
    exlNextScheduledConnection DateAndTime,
    exlNumberOfMessages Gauge32,
    exlOldestMessage DateAndTime,
    exlProtocolName DisplayString,
    exlSizeOfQueue DisplayString,
    exlStateActive TruthValue,
    exlStateFlags Gauge32,
    exlStateFrozen TruthValue,
    exlStateReady TruthValue,
    exlStateRemote TruthValue,
    exlStateRetry TruthValue,
    exlStateScheduled TruthValue,
    exlSupportedLinkActions Gauge32,
    exlTypeCurrentlyUnreachable TruthValue,
    exlTypeDeferredDelivery TruthValue,
    exlTypeInternal TruthValue,
    exlTypeLocalDelivery TruthValue,
    exlTypePendingCategorization TruthValue,
    exlTypePendingRouting TruthValue,
    exlTypePendingSubmission TruthValue,
    exlTypeRemoteDelivery TruthValue,
    exlVersion Gauge32,
    exlVirtualMachine Gauge32,
    exlVirtualServerName DisplayString
}

exlIndex OBJECT-TYPE
    SYNTAX     Integer32 (1..2147483647)
    MAX-ACCESS read-only
    STATUS     current
    DESCRIPTION
        "The value of this object uniquely identifies the instance entry
        for this class."
    ::= { exchangeLinkEntry 1 }

exlActionFreeze OBJECT-TYPE
    SYNTAX     TruthValue
    MAX-ACCESS read-only
    STATUS     current
    DESCRIPTION
        "The ActionFreeze property, when True, specifies that the link
        supports freezing messages in its queues. The ActionFreeze property
        corresponds to the sixth bit (0x00000020) of the
        SupportedLinkActions property."
    ::= { exchangeLinkEntry 2 }

exlActionKick OBJECT-TYPE
    SYNTAX     TruthValue
    MAX-ACCESS read-only
    STATUS     current
    DESCRIPTION
        "The ActionKick property, when True, specifies that the link can
        trigger its queues to retry transmitting waiting messages
        immediately, instead of waiting for the default protocol timeout
        before retrying the transmission. The ActionKick property
        corresponds to the first bit (0x00000001) of the
        SupportedLinkActions property."
    ::= { exchangeLinkEntry 3 }

exlActionThaw OBJECT-TYPE
    SYNTAX     TruthValue
    MAX-ACCESS read-only
    STATUS     current
    DESCRIPTION
        "The ActionThaw property, when True, specifies that the link
        supports thawing messages in its queues. Thawing a queue is also
        known as 'unfreezing' that queue. The ActionThaw property
        corresponds to the seventh bit (0x00000040) of the
        SupportedLinkActions property."
    ::= { exchangeLinkEntry 4 }

exlExtendedStateInfo OBJECT-TYPE
    SYNTAX     DisplayString
    MAX-ACCESS read-only
    STATUS     current
    DESCRIPTION
        "The ExtendedStateInfo property specifies the text description of
        the current link status."
    ::= { exchangeLinkEntry 5 }

exlGlobalStop OBJECT-TYPE
    SYNTAX     TruthValue
    MAX-ACCESS read-only
    STATUS     current
    DESCRIPTION
        "The GlobalStop property specifies whether the link is currently
        stopped."
    ::= { exchangeLinkEntry 6 }

exlIncreasingTime OBJECT-TYPE
    SYNTAX     Gauge32
    MAX-ACCESS read-only
    STATUS     current
    DESCRIPTION
        "The IncreasingTime property specifies the amount of time, in
        milliseconds, that the number of messages waiting to be transferred
        by the link has been increasing."
    ::= { exchangeLinkEntry 7 }

exlLinkDN OBJECT-TYPE
    SYNTAX     DisplayString
    MAX-ACCESS read-only
    STATUS     current
    DESCRIPTION
        "The LinkDN property specifies the Active Directory globally unique
        identifier (GUID) of the connector object that generated the link."
    ::= { exchangeLinkEntry 8 }

exlLinkName OBJECT-TYPE
    SYNTAX     DisplayString
    MAX-ACCESS read-only
    STATUS     current
    DESCRIPTION
        "The LinkName property specifies the name of the link."
    ::= { exchangeLinkEntry 9 }

exlNextScheduledConnection OBJECT-TYPE
    SYNTAX     DateAndTime
    MAX-ACCESS read-only
    STATUS     current
    DESCRIPTION
        "The NextScheduledConnection property specifies the date and time
        when a connection will be attempted to transfer waiting messages."
    ::= { exchangeLinkEntry 10 }

exlNumberOfMessages OBJECT-TYPE
    SYNTAX     Gauge32
    MAX-ACCESS read-only
    STATUS     current
    DESCRIPTION
        "The NumberOfMessages property specifies the number of messages
        that are waiting for transmission across the link."
    ::= { exchangeLinkEntry 11 }

exlOldestMessage OBJECT-TYPE
    SYNTAX     DateAndTime
    MAX-ACCESS read-only
    STATUS     current
    DESCRIPTION
        "The OldestMessage property specifies the date and time that the
        oldest message that is still waiting to be transmitted was received
        into the link."
    ::= { exchangeLinkEntry 12 }

exlProtocolName OBJECT-TYPE
    SYNTAX     DisplayString
    MAX-ACCESS read-only
    STATUS     current
    DESCRIPTION
        "The ProtocolName property specifies the transmission protocol for
        the link."
    ::= { exchangeLinkEntry 13 }

exlSizeOfQueue OBJECT-TYPE
    SYNTAX     DisplayString
    MAX-ACCESS read-only
    STATUS     current
    DESCRIPTION
        "The SizeOfQueue property specifies the total size of the messages
        in the link, in bytes."
    ::= { exchangeLinkEntry 14 }

exlStateActive OBJECT-TYPE
    SYNTAX     TruthValue
    MAX-ACCESS read-only
    STATUS     current
    DESCRIPTION
        "The StateActive property, when True, specifies that the link is
        active. The StateActive property corresponds to first bit
        (0x00000001) of the StateFlags property."
    ::= { exchangeLinkEntry 15 }

exlStateFlags OBJECT-TYPE
    SYNTAX     Gauge32
    MAX-ACCESS read-only
    STATUS     current
    DESCRIPTION
        "The StateFlags property specifies the state of the link. The
        individual bits of this property are available as the link State.
        and Type. properties of this class."
    ::= { exchangeLinkEntry 16 }

exlStateFrozen OBJECT-TYPE
    SYNTAX     TruthValue
    MAX-ACCESS read-only
    STATUS     current
    DESCRIPTION
        "The StateFrozen property indicates whether the link is currently
        frozen. The StateFrozen property corresponds to the sixth bit
        (0x00000020) of the StateFlags property."
    ::= { exchangeLinkEntry 17 }

exlStateReady OBJECT-TYPE
    SYNTAX     TruthValue
    MAX-ACCESS read-only
    STATUS     current
    DESCRIPTION
        "The StateReady property, when True, specifies that the link is
        ready to accept new messages. The StateReady property corresponds
        to the second bit (0x00000002) of the StateFlags property."
    ::= { exchangeLinkEntry 18 }

exlStateRemote OBJECT-TYPE
    SYNTAX     TruthValue
    MAX-ACCESS read-only
    STATUS     current
    DESCRIPTION
        "The StateRemote property, when True, specifies that the
        destination for messages in this link is on a remote server,
        instead of the messages being delivered to a local store. The
        StateRemote property corresponds to the fifth bit (0x00000010) of
        the StateFlags property."
    ::= { exchangeLinkEntry 19 }

exlStateRetry OBJECT-TYPE
    SYNTAX     TruthValue
    MAX-ACCESS read-only
    STATUS     current
    DESCRIPTION
        "The StateRetry property, when True, specifies that the link is
        retrying a transmission that was unsuccessful. The StateRetry
        property corresponds to the third bit (0x00000004) of the
        StateFlags property."
    ::= { exchangeLinkEntry 20 }

exlStateScheduled OBJECT-TYPE
    SYNTAX     TruthValue
    MAX-ACCESS read-only
    STATUS     current
    DESCRIPTION
        "The StateScheduled property, when True, specifies that the link is
        scheduled for periodic activation, as compared with asynchronous,
        on-demand activation. The StateScheduled property corresponds to
        the fourth bit (0x00000008) of the StateFlags property."
    ::= { exchangeLinkEntry 21 }

exlSupportedLinkActions OBJECT-TYPE
    SYNTAX     Gauge32
    MAX-ACCESS read-only
    STATUS     current
    DESCRIPTION
        "The SupportedLinkActions property specifies the actions supported
        by the link. The individual bits of this property are available as
        the Action. properties in this class."
    ::= { exchangeLinkEntry 22 }

exlTypeCurrentlyUnreachable OBJECT-TYPE
    SYNTAX     TruthValue
    MAX-ACCESS read-only
    STATUS     current
    DESCRIPTION
        "The TypeCurrentlyUnreachable property, when True, specifies that
        the link holds messages for destinations that currently cannot be
        reached. The TypeCurrentlyUnreachable property corresponds to the
        thirteenth bit (0x00001000) of the StateFlags property."
    ::= { exchangeLinkEntry 23 }

exlTypeDeferredDelivery OBJECT-TYPE
    SYNTAX     TruthValue
    MAX-ACCESS read-only
    STATUS     current
    DESCRIPTION
        "The TypeDeferredDelivery property, when True, specifies that the
        link holds mail that is awaiting a trigger to start transmission.
        The TypeDeferredDelivery property corresponds to the fourteenth bit
        (0x00002000) of the StateFlags property."
    ::= { exchangeLinkEntry 24 }

exlTypeInternal OBJECT-TYPE
    SYNTAX     TruthValue
    MAX-ACCESS read-only
    STATUS     current
    DESCRIPTION
        "The TypeInternal property indicates that the link is used for
        internal message processing. The TypeInternal property corresponds
        to the fifteenth bit (0x00004000) of the StateFlags property."
    ::= { exchangeLinkEntry 25 }

exlTypeLocalDelivery OBJECT-TYPE
    SYNTAX     TruthValue
    MAX-ACCESS read-only
    STATUS     current
    DESCRIPTION
        "The TypeLocalDelivery property, when True, specifies that the link
        handles local mail delivery. The TypeLocalDelivery property
        corresponds to the tenth bit (0x00000200) of the StateFlags
        property."
    ::= { exchangeLinkEntry 26 }

exlTypePendingCategorization OBJECT-TYPE
    SYNTAX     TruthValue
    MAX-ACCESS read-only
    STATUS     current
    DESCRIPTION
        "The TypePendingCategorization property, when True, specifies that
        the link is resolving addresses against entries in Active
        Directory. The TypePendingCategorization property corresponds to
        the twelfth bit (0x00000800) of the StateFlags property."
    ::= { exchangeLinkEntry 27 }

exlTypePendingRouting OBJECT-TYPE
    SYNTAX     TruthValue
    MAX-ACCESS read-only
    STATUS     current
    DESCRIPTION
        "The TypePendingRouting property, when True, specifies that the
        link is determining the routing of the next message that is waiting
        to be transmitted. The TypePendingRouting property corresponds to
        the eleventh bit (0x00000400) of the StateFlags property."
    ::= { exchangeLinkEntry 28 }

exlTypePendingSubmission OBJECT-TYPE
    SYNTAX     TruthValue
    MAX-ACCESS read-only
    STATUS     current
    DESCRIPTION
        "The TypePendingSubmission property, when True, specifies that the
        link handles messages that have not yet been submitted to the
        routing engine. The TypePendingSubmission property corresponds to
        the sixteenth bit (0x00008000) of the StateFlags property."
    ::= { exchangeLinkEntry 29 }

exlTypeRemoteDelivery OBJECT-TYPE
    SYNTAX     TruthValue
    MAX-ACCESS read-only
    STATUS     current
    DESCRIPTION
        "The TypeRemoteDelivery property, when True, specifies that the
        link is currently handling a remote message delivery. The
        TypeRemoteDelivery property corresponds to the ninth bit
        (0x00000100) of the StateFlags property."
    ::= { exchangeLinkEntry 30 }

exlVersion OBJECT-TYPE
    SYNTAX     Gauge32
    MAX-ACCESS read-only
    STATUS     current
    DESCRIPTION
        "The Version property specifies the version number of the
        underlying link control software."
    ::= { exchangeLinkEntry 31 }

exlVirtualMachine OBJECT-TYPE
    SYNTAX     Gauge32
    MAX-ACCESS read-only
    STATUS     current
    DESCRIPTION
        "The VirtualMachine property specifies the name of the virtual
        machine that is the source of the link."
    ::= { exchangeLinkEntry 32 }

exlVirtualServerName OBJECT-TYPE
    SYNTAX     DisplayString
    MAX-ACCESS read-only
    STATUS     current
    DESCRIPTION
        "The value of the VirtualServerName property is the integer number
        of the virtual machine that is the source of the link. This number
        is the Microsoft Active Directorycommon name (CN) for the virtual
        server object."
    ::= { exchangeLinkEntry 33 }

exchangeQueueTable OBJECT-TYPE
    SYNTAX     SEQUENCE OF ExchangeQueueEntry
    MAX-ACCESS not-accessible
    STATUS     current
    DESCRIPTION
        "The ExchangeQueue WMI class has properties that return information
        about the dynamic queues created to transfer individual messages
        between mail servers. An ExchangeQueue is part of an ExchangeLink.
        ExchangeQueue objects are not the same as the queues listed in the
        Exchange System Manager."
    ::= { wmiExchange 4 }

exchangeQueueEntry OBJECT-TYPE
    SYNTAX     ExchangeQueueEntry
    MAX-ACCESS not-accessible
    STATUS     current
    DESCRIPTION
        "None"
    INDEX      { exqIndex }
    ::= { exchangeQueueTable 1 }

ExchangeQueueEntry ::= SEQUENCE {
    exqIndex Integer32,
    exqCanEnumAll TruthValue,
    exqCanEnumFailed TruthValue,
    exqCanEnumFirstNMessages TruthValue,
    exqCanEnumFrozen TruthValue,
    exqCanEnumInvertSense TruthValue,
    exqCanEnumLargerThan TruthValue,
    exqCanEnumNLargestMessages TruthValue,
    exqCanEnumNOldestMessages TruthValue,
    exqCanEnumOlderThan TruthValue,
    exqCanEnumRecipient TruthValue,
    exqCanEnumSender TruthValue,
    exqGlobalStop TruthValue,
    exqIncreasingTime Gauge32,
    exqLinkName DisplayString,
    exqMsgEnumFlagsSupported Gauge32,
    exqNumberOfMessages Gauge32,
    exqProtocolName DisplayString,
    exqQueueName DisplayString,
    exqSizeOfQueue DisplayString,
    exqVersion Gauge32,
    exqVirtualMachine DisplayString,
    exqVirtualServerName DisplayString
}

exqIndex OBJECT-TYPE
    SYNTAX     Integer32 (1..2147483647)
    MAX-ACCESS read-only
    STATUS     current
    DESCRIPTION
        "The value of this object uniquely identifies the instance entry
        for this class."
    ::= { exchangeQueueEntry 1 }

exqCanEnumAll OBJECT-TYPE
    SYNTAX     TruthValue
    MAX-ACCESS read-only
    STATUS     current
    DESCRIPTION
        "The CanEnumAll property, when True, specifies that the queue can
        enumerate all of the messages that it has waiting for transmission.
        The CanEnumAll property corresponds to the thirty-first bit
        (0x40000000) of the MsgEnumFlagsSupported property."
    ::= { exchangeQueueEntry 2 }

exqCanEnumFailed OBJECT-TYPE
    SYNTAX     TruthValue
    MAX-ACCESS read-only
    STATUS     current
    DESCRIPTION
        "The CanEnumFailed property, when True, specifies that the queue
        can enumerate the messages that it has waiting for transmission
        that it was unable to transfer. The CanEnumFailed property
        corresponds to the ninth bit (0x00000100) of the
        MsgEnumFlagsSupported property."
    ::= { exchangeQueueEntry 3 }

exqCanEnumFirstNMessages OBJECT-TYPE
    SYNTAX     TruthValue
    MAX-ACCESS read-only
    STATUS     current
    DESCRIPTION
        "The CanEnumFirstNMessages property, when True, specifies that the
        queue can enumerate the first N messages that it has waiting for
        transmission. The CanEnumFirstNMessages property corresponds to the
        first bit (0x00000001) of the MsgEnumFlagsSupported property."
    ::= { exchangeQueueEntry 4 }

exqCanEnumFrozen OBJECT-TYPE
    SYNTAX     TruthValue
    MAX-ACCESS read-only
    STATUS     current
    DESCRIPTION
        "The CanEnumFrozen property, when True, specifies that the queue
        can enumerate messages that it has waiting for transmission that
        have been frozen. The CanEnumFrozen property corresponds to the
        sixth bit (0x00000020) of the MsgEnumFlagsSupported property."
    ::= { exchangeQueueEntry 5 }

exqCanEnumInvertSense OBJECT-TYPE
    SYNTAX     TruthValue
    MAX-ACCESS read-only
    STATUS     current
    DESCRIPTION
        "The CanEnumInvertSense property, when True, specifies that the
        queue can enumerate messages that it has waiting for transmission
        that do not match the criteria requested. For example, requesting
        the oldest messages while inverting the request sense would return
        the newest messages. The CanEnumInvertSense property corresponds to
        the thirty-second bit (0x80000000) of the MsgEnumFlagsSupported
        property."
    ::= { exchangeQueueEntry 6 }

exqCanEnumLargerThan OBJECT-TYPE
    SYNTAX     TruthValue
    MAX-ACCESS read-only
    STATUS     current
    DESCRIPTION
        "The CanEnumLargerThan property, when True, specifies that the
        queue can enumerate the messages that it has waiting for
        transmission that are larger than a specified value. The
        CanEnumLargerThan property corresponds to the fourth bit
        (0x00000008) of the MsgEnumFlagsSupported property."
    ::= { exchangeQueueEntry 7 }

exqCanEnumNLargestMessages OBJECT-TYPE
    SYNTAX     TruthValue
    MAX-ACCESS read-only
    STATUS     current
    DESCRIPTION
        "The CanEnumNLargestMessages property, when True, specifies that
        the queue can enumerate the specified number of the largest
        messages that it has waiting for transmission. The
        CanEnumNLargestMessages property corresponds to the seventh bit
        (0x00000040) of the MsgEnumFlagsSupported property."
    ::= { exchangeQueueEntry 8 }

exqCanEnumNOldestMessages OBJECT-TYPE
    SYNTAX     TruthValue
    MAX-ACCESS read-only
    STATUS     current
    DESCRIPTION
        "The CanEnumNOldestMessages property, when True, specifies that the
        queue can enumerate the specified number of the oldest messages
        that it has waiting for transmission. The CanEnumNOldestMessages
        property corresponds to the eighth bit (0x00000080) of the
        MsgEnumFlagsSupported property."
    ::= { exchangeQueueEntry 9 }

exqCanEnumOlderThan OBJECT-TYPE
    SYNTAX     TruthValue
    MAX-ACCESS read-only
    STATUS     current
    DESCRIPTION
        "The CanEnumOlderThan property, when True, specifies that the queue
        can enumerate the messages that it has waiting for transmission
        that arrived before a specified date and time. The CanEnumOlderThan
        property corresponds to the fifth bit (0x00000010) of the
        MsgEnumFlagsSupported property."
    ::= { exchangeQueueEntry 10 }

exqCanEnumRecipient OBJECT-TYPE
    SYNTAX     TruthValue
    MAX-ACCESS read-only
    STATUS     current
    DESCRIPTION
        "The CanEnumRecipient property, when True, specifies that the queue
        can enumerate the recipients of messages that it has waiting for
        transmission. The CanEnumRecipient property corresponds to the
        fourth bit (0x00000004) of the MsgEnumFlagsSupported property."
    ::= { exchangeQueueEntry 11 }

exqCanEnumSender OBJECT-TYPE
    SYNTAX     TruthValue
    MAX-ACCESS read-only
    STATUS     current
    DESCRIPTION
        "The CanEnumSender property, when True, specifies that the queue
        can enumerate the senders of messages that it has waiting for
        transmission. The CanEnumSender property corresponds to the second
        bit (0x00000002) of the MsgEnumFlagsSupported property."
    ::= { exchangeQueueEntry 12 }

exqGlobalStop OBJECT-TYPE
    SYNTAX     TruthValue
    MAX-ACCESS read-only
    STATUS     current
    DESCRIPTION
        "The GlobalStop property specifies whether the queue is currently
        stopped."
    ::= { exchangeQueueEntry 13 }

exqIncreasingTime OBJECT-TYPE
    SYNTAX     Gauge32
    MAX-ACCESS read-only
    STATUS     current
    DESCRIPTION
        "The IncreasingTime property specifies the amount of time, in
        milliseconds, that the number of messages waiting to be transferred
        by the queue has been increasing."
    ::= { exchangeQueueEntry 14 }

exqLinkName OBJECT-TYPE
    SYNTAX     DisplayString
    MAX-ACCESS read-only
    STATUS     current
    DESCRIPTION
        "The LinkName property specifies the name of the link in which this
        queue is contained."
    ::= { exchangeQueueEntry 15 }

exqMsgEnumFlagsSupported OBJECT-TYPE
    SYNTAX     Gauge32
    MAX-ACCESS read-only
    STATUS     current
    DESCRIPTION
        "The MsgEnumFlagsSupported property specifies a bit-mapped set of
        flags that indicate what types of objects can be enumerated. The
        individual bits of this property are available as the queue
        CanEnum. properties in this class."
    ::= { exchangeQueueEntry 16 }

exqNumberOfMessages OBJECT-TYPE
    SYNTAX     Gauge32
    MAX-ACCESS read-only
    STATUS     current
    DESCRIPTION
        "The NumberOfMessages property specifies the number of messages
        that are waiting for transmission by the queue."
    ::= { exchangeQueueEntry 17 }

exqProtocolName OBJECT-TYPE
    SYNTAX     DisplayString
    MAX-ACCESS read-only
    STATUS     current
    DESCRIPTION
        "The ProtocolName property specifies the transmission protocol for
        the queue."
    ::= { exchangeQueueEntry 18 }

exqQueueName OBJECT-TYPE
    SYNTAX     DisplayString
    MAX-ACCESS read-only
    STATUS     current
    DESCRIPTION
        "The QueueName property specifies the name of the queue."
    ::= { exchangeQueueEntry 19 }

exqSizeOfQueue OBJECT-TYPE
    SYNTAX     DisplayString
    MAX-ACCESS read-only
    STATUS     current
    DESCRIPTION
        "The SizeOfQueue property specifies the total size of all messages
        in the queue, in bytes."
    ::= { exchangeQueueEntry 20 }

exqVersion OBJECT-TYPE
    SYNTAX     Gauge32
    MAX-ACCESS read-only
    STATUS     current
    DESCRIPTION
        "The Version property specifies the version number of the Microsoft
        Exchange software."
    ::= { exchangeQueueEntry 21 }

exqVirtualMachine OBJECT-TYPE
    SYNTAX     DisplayString
    MAX-ACCESS read-only
    STATUS     current
    DESCRIPTION
        "The VirtualMachine property specifies the name of the virtual
        machine that is the source of the link."
    ::= { exchangeQueueEntry 22 }

exqVirtualServerName OBJECT-TYPE
    SYNTAX     DisplayString
    MAX-ACCESS read-only
    STATUS     current
    DESCRIPTION
        "The value of the VirtualServerName property is the integer number
        of the virtual machine that is the source of the queue. This number
        is the Microsoft Active Directory common name (CN) for the virtual
        server object."
    ::= { exchangeQueueEntry 23 }

exchangeServerStateTable OBJECT-TYPE
    SYNTAX     SEQUENCE OF ExchangeServerStateEntry
    MAX-ACCESS not-accessible
    STATUS     current
    DESCRIPTION
        "The ExchangeServerState WMI class has properties that return
        information about the computer running Microsoft Exchange 2000
        Server."
    ::= { wmiExchange 5 }

exchangeServerStateEntry OBJECT-TYPE
    SYNTAX     ExchangeServerStateEntry
    MAX-ACCESS not-accessible
    STATUS     current
    DESCRIPTION
        "None"
    INDEX      { exssIndex }
    ::= { exchangeServerStateTable 1 }

ExchangeServerStateEntry ::= SEQUENCE {
    exssIndex Integer32,
    exssClusterState INTEGER,
    exssClusterStateString DisplayString,
    exssCPUState INTEGER,
    exssCPUStateString DisplayString,
    exssDisksState INTEGER,
    exssDisksStateString DisplayString,
    exssDN DisplayString,
    exssGroupDN DisplayString,
    exssGroupGUID DisplayString,
    exssGUID DisplayString,
    exssMemoryState INTEGER,
    exssMemoryStateString DisplayString,
    exssName DisplayString,
    exssQueuesState INTEGER,
    exssQueuesStateString DisplayString,
    exssServerMaintenance TruthValue,
    exssServerState INTEGER,
    exssServerStateString DisplayString,
    exssServicesState INTEGER,
    exssServicesStateString DisplayString,
    exssUnreachable TruthValue,
    exssVersion Gauge32
}

exssIndex OBJECT-TYPE
    SYNTAX     Integer32 (1..2147483647)
    MAX-ACCESS read-only
    STATUS     current
    DESCRIPTION
        "The value of this object uniquely identifies the instance entry
        for this class."
    ::= { exchangeServerStateEntry 1 }

exssClusterState OBJECT-TYPE
    SYNTAX     INTEGER {
        unknown(0),
        ok(1),
        warning(2),
        error(3)
    }
    MAX-ACCESS read-only
    STATUS     current
    DESCRIPTION
        "When the ExchangeServerState instance represents a
        clustered Exchange server, the ClusterState
        property specifies the state of the clustered
        resources on that server."
    ::= { exchangeServerStateEntry 2 }

exssClusterStateString OBJECT-TYPE
    SYNTAX     DisplayString
    MAX-ACCESS read-only
    STATUS     current
    DESCRIPTION
        "When the ExchangeServerState instance represents a
        clustered Exchange server, the ClusterStateString
        property specifies the state of the cluster
        resources on that server."
    ::= { exchangeServerStateEntry 3 }

exssCPUState OBJECT-TYPE
    SYNTAX     INTEGER {
        unknown(0),
        ok(1),
        warning(2),
        error(3)
    }
    MAX-ACCESS read-only
    STATUS     current
    DESCRIPTION
        "The CPUState property specifies the current state
        of the CPU on the Exchange server. This is the same
        state information shown on the Monitoring and
        Status Properties page of the Exchange System
        Manager."
    ::= { exchangeServerStateEntry 4 }

exssCPUStateString OBJECT-TYPE
    SYNTAX     DisplayString
    MAX-ACCESS read-only
    STATUS     current
    DESCRIPTION
        "The CPUStateString property specifies the current
        state of the CPU on the Exchange server."
    ::= { exchangeServerStateEntry 5 }

exssDisksState OBJECT-TYPE
    SYNTAX     INTEGER {
        unknown(0),
        ok(1),
        warning(2),
        error(3)
    }
    MAX-ACCESS read-only
    STATUS     current
    DESCRIPTION
        "The DisksState property specifies the current
        state of the disk storage on the computer running
        Exchange 2000 Server."
    ::= { exchangeServerStateEntry 6 }

exssDisksStateString OBJECT-TYPE
    SYNTAX     DisplayString
    MAX-ACCESS read-only
    STATUS     current
    DESCRIPTION
        "The DisksStateString property specifies the
        current state of the disk storage on the computer
        running Exchange 2000 Server."
    ::= { exchangeServerStateEntry 7 }

exssDN OBJECT-TYPE
    SYNTAX     DisplayString
    MAX-ACCESS read-only
    STATUS     current
    DESCRIPTION
        "The DN property specifies the Microsoft Active
        Directory distinguished name (DN) of the Exchange
        server object."
    ::= { exchangeServerStateEntry 8 }

exssGroupDN OBJECT-TYPE
    SYNTAX     DisplayString
    MAX-ACCESS read-only
    STATUS     current
    DESCRIPTION
        "The GroupDN property specifies the DN of the
        Exchange 2000 Server routing group in Active
        Directory."
    ::= { exchangeServerStateEntry 9 }

exssGroupGUID OBJECT-TYPE
    SYNTAX     DisplayString
    MAX-ACCESS read-only
    STATUS     current
    DESCRIPTION
        "The GroupGUID property specifies the globally
        unique identifier (GUID) of the Exchange 2000
        Server routing group in Active Directory."
    ::= { exchangeServerStateEntry 10 }

exssGUID OBJECT-TYPE
    SYNTAX     DisplayString
    MAX-ACCESS read-only
    STATUS     current
    DESCRIPTION
        "The GUID property specifies the GUID of the
        Exchange 2000 Server server object in Active
        Directory."
    ::= { exchangeServerStateEntry 11 }

exssMemoryState OBJECT-TYPE
    SYNTAX     INTEGER {
        unknown(0),
        ok(1),
        warning(2),
        error(3)
    }
    MAX-ACCESS read-only
    STATUS     current
    DESCRIPTION
        "The MemoryState property specifies the current
        state of the memory on the computer running
        Exchange 2000 Server."
    ::= { exchangeServerStateEntry 12 }

exssMemoryStateString OBJECT-TYPE
    SYNTAX     DisplayString
    MAX-ACCESS read-only
    STATUS     current
    DESCRIPTION
        "The MemoryStateString property specifies the
        current state of the memory on the computer running
        Exchange 2000 Server."
    ::= { exchangeServerStateEntry 13 }

exssName OBJECT-TYPE
    SYNTAX     DisplayString
    MAX-ACCESS read-only
    STATUS     current
    DESCRIPTION
        "The Name property specifies the name of the
        computer running Exchange 2000 Server."
    ::= { exchangeServerStateEntry 14 }

exssQueuesState OBJECT-TYPE
    SYNTAX     INTEGER {
        unknown(0),
        ok(1),
        warning(2),
        error(3)
    }
    MAX-ACCESS read-only
    STATUS     current
    DESCRIPTION
        "The QueuesState property specifies the current
        state of the queues on the computer running
        Exchange 2000 Server."
    ::= { exchangeServerStateEntry 15 }

exssQueuesStateString OBJECT-TYPE
    SYNTAX     DisplayString
    MAX-ACCESS read-only
    STATUS     current
    DESCRIPTION
        "The QueuesStateString property specifies the
        current state of the queues on the computer running
        Exchange 2000 Server."
    ::= { exchangeServerStateEntry 16 }

exssServerMaintenance OBJECT-TYPE
    SYNTAX     TruthValue
    MAX-ACCESS read-only
    STATUS     current
    DESCRIPTION
        "The ServerMaintenance property, when True,
        specifies that the notifications set up in the
        Exchange 2000 Server System Manager Monitoring and
        Status page have been disabled."
    ::= { exchangeServerStateEntry 17 }

exssServerState OBJECT-TYPE
    SYNTAX     INTEGER {
        unknown(0),
        ok(1),
        warning(2),
        error(3)
    }
    MAX-ACCESS read-only
    STATUS     current
    DESCRIPTION
        "The ServerState property specifies the current
        state of the computer running Exchange 2000
        Server."
    ::= { exchangeServerStateEntry 18 }

exssServerStateString OBJECT-TYPE
    SYNTAX     DisplayString
    MAX-ACCESS read-only
    STATUS     current
    DESCRIPTION
        "The ServerStateString property specifies the
        current state of the computer running Exchange 2000
        Server."
    ::= { exchangeServerStateEntry 19 }

exssServicesState OBJECT-TYPE
    SYNTAX     INTEGER {
        unknown(0),
        ok(1),
        warning(2),
        error(3)
    }
    MAX-ACCESS read-only
    STATUS     current
    DESCRIPTION
        "The ServicesState property specifies the current
        state of the monitoring services running on the
        Exchange 2000 Server computer."
    ::= { exchangeServerStateEntry 20 }

exssServicesStateString OBJECT-TYPE
    SYNTAX     DisplayString
    MAX-ACCESS read-only
    STATUS     current
    DESCRIPTION
        "The ServicesStateString property specifies the
        current state of the monitoring services running on
        the Exchange 2000 Server computer."
    ::= { exchangeServerStateEntry 21 }

exssUnreachable OBJECT-TYPE
    SYNTAX     TruthValue
    MAX-ACCESS read-only
    STATUS     current
    DESCRIPTION
        "The Unreachable property, when True, specifies
        that the Exchange 2000 Server computer is currently
        unreachable."
    ::= { exchangeServerStateEntry 22 }

exssVersion OBJECT-TYPE
    SYNTAX     Gauge32
    MAX-ACCESS read-only
    STATUS     current
    DESCRIPTION
        "The Version property indicates the version of the
        Exchange server."
    ::= { exchangeServerStateEntry 23 }

exchangeDSAccessDCTable OBJECT-TYPE
    SYNTAX     SEQUENCE OF ExchangeDSAccessDCEntry
    MAX-ACCESS not-accessible
    STATUS     current
    DESCRIPTION
        "The properties of the Exchange_DSAccessDC class
        provide information about Microsoft Active
        Directory and Microsoft Exchange Server 5.5 domain
        controllers that are accessible to the Exchange
        2000 Server DSAccess service."
    ::= { wmiExchange 6 }

exchangeDSAccessDCEntry OBJECT-TYPE
    SYNTAX     ExchangeDSAccessDCEntry
    MAX-ACCESS not-accessible
    STATUS     current
    DESCRIPTION
        "None"
    INDEX      { exdsIndex }
    ::= { exchangeDSAccessDCTable 1 }

ExchangeDSAccessDCEntry ::= SEQUENCE {
    exdsIndex Integer32,
    exdsConfigurationType INTEGER,
    exdsIsFast TruthValue,
    exdsIsInSync TruthValue,
    exdsIsUp TruthValue,
    exdsLDAPPort Gauge32,
    exdsName DisplayString,
    exdsType INTEGER
}

exdsIndex OBJECT-TYPE
    SYNTAX     Integer32 (1..2147483647)
    MAX-ACCESS read-only
    STATUS     current
    DESCRIPTION
        "The value of this object uniquely identifies the
        instance entry for this class."
    ::= { exchangeDSAccessDCEntry 1 }

exdsConfigurationType OBJECT-TYPE
    SYNTAX     INTEGER {
        manual(0),
        automatic(1)
    }
    MAX-ACCESS read-only
    STATUS     current
    DESCRIPTION
        "The ConfigurationType property indicates whether
        the instance describes a domain controller that was
        detected automatically, or one that was specified
        manually."
    ::= { exchangeDSAccessDCEntry 2 }

exdsIsFast OBJECT-TYPE
    SYNTAX     TruthValue
    MAX-ACCESS read-only
    STATUS     current
    DESCRIPTION
        "The IsFast property indicates, when True, that the
        domain controller response time has been less than
        two seconds."
    ::= { exchangeDSAccessDCEntry 3 }

exdsIsInSync OBJECT-TYPE
    SYNTAX     TruthValue
    MAX-ACCESS read-only
    STATUS     current
    DESCRIPTION
        "The IsInSync property indicates whether the domain
        controller is synchronized with the Global Catalog
        server and with the Configuration domain
        controller."
    ::= { exchangeDSAccessDCEntry 4 }

exdsIsUp OBJECT-TYPE
    SYNTAX     TruthValue
    MAX-ACCESS read-only
    STATUS     current
    DESCRIPTION
        "The IsUp property indicates whether the domain
        controller was available the last time Exchange
        attempted to access it."
    ::= { exchangeDSAccessDCEntry 5 }

exdsLDAPPort OBJECT-TYPE
    SYNTAX     Gauge32
    MAX-ACCESS read-only
    STATUS     current
    DESCRIPTION
        "The LDAPPort property specifies the TCP/IP port on
        which the domain controller listens for LDAP
        requests."
    ::= { exchangeDSAccessDCEntry 6 }

exdsName OBJECT-TYPE
    SYNTAX     DisplayString
    MAX-ACCESS read-only
    STATUS     current
    DESCRIPTION
        "The Name property specifies the computer name of
        the domain controller."
    ::= { exchangeDSAccessDCEntry 7 }

exdsType OBJECT-TYPE
    SYNTAX     INTEGER {
        configurationDomainController(0),
        localDomainController(1),
        globalCatalog(2)
    }
    MAX-ACCESS read-only
    STATUS     current
    DESCRIPTION
        "The Type property specifies the role that the
        domain controller plays in the Exchange system."
    ::= { exchangeDSAccessDCEntry 8 }

exchangeFolderTreeTable OBJECT-TYPE
    SYNTAX     SEQUENCE OF ExchangeFolderTreeEntry
    MAX-ACCESS not-accessible
    STATUS     current
    DESCRIPTION
        "Instances of the Exchange_FolderTree WMI class
        provide information about public and private folder
        trees on Microsoft Exchange servers."
    ::= { wmiExchange 7 }

exchangeFolderTreeEntry OBJECT-TYPE
    SYNTAX     ExchangeFolderTreeEntry
    MAX-ACCESS not-accessible
    STATUS     current
    DESCRIPTION
        "None"
    INDEX      { exftIndex }
    ::= { exchangeFolderTreeTable 1 }

ExchangeFolderTreeEntry ::= SEQUENCE {
    exftIndex Integer32,
    exftAdministrativeGroup DisplayString,
    exftAdministrativeNote DisplayString,
    exftAssociatedPublicStores DisplayString,
    exftCreationTime DateAndTime,
    exftGUID DisplayString,
    exftHasLocalPublicStore TruthValue,
    exftLastModificationTime DateAndTime,
    exftMapiFolderTree TruthValue,
    exftName DisplayString,
    exftRootFolderURL DisplayString
}

exftIndex OBJECT-TYPE
    SYNTAX     Integer32 (1..2147483647)
    MAX-ACCESS read-only
    STATUS     current
    DESCRIPTION
        "The value of this object uniquely identifies the
        instance entry for this class."
    ::= { exchangeFolderTreeEntry 1 }

exftAdministrativeGroup OBJECT-TYPE
    SYNTAX     DisplayString
    MAX-ACCESS read-only
    STATUS     current
    DESCRIPTION
        "The AdministrativeGroup property indicates the
        name of the administrative group that the top-level
        hierarchy (TLH) resides under in Active Directory."
    ::= { exchangeFolderTreeEntry 2 }

exftAdministrativeNote OBJECT-TYPE
    SYNTAX     DisplayString
    MAX-ACCESS read-only
    STATUS     current
    DESCRIPTION
        "The AdministrativeNote property indicates the
        administrative note attached to the Microsoft
        Active Directory object representing the tree."
    ::= { exchangeFolderTreeEntry 3 }

exftAssociatedPublicStores OBJECT-TYPE
    SYNTAX     DisplayString
    MAX-ACCESS read-only
    STATUS     current
    DESCRIPTION
        "The AssociatedPublicStores property indicates the
        list of MDBs associated with the top-level
        hierarchy (TLH)."
    ::= { exchangeFolderTreeEntry 4 }

exftCreationTime OBJECT-TYPE
    SYNTAX     DateAndTime
    MAX-ACCESS read-only
    STATUS     current
    DESCRIPTION
        "The CreationTime property indicates when the tree
        was created."
    ::= { exchangeFolderTreeEntry 5 }

exftGUID OBJECT-TYPE
    SYNTAX     DisplayString
    MAX-ACCESS read-only
    STATUS     current
    DESCRIPTION
        "The GUID property indicates the globally unique
        identifier (GUID) attribute of the top-level
        hierarchy (TLH) object in Active Directory."
    ::= { exchangeFolderTreeEntry 6 }

exftHasLocalPublicStore OBJECT-TYPE
    SYNTAX     TruthValue
    MAX-ACCESS read-only
    STATUS     current
    DESCRIPTION
        "The HasLocalPublicStore property indicates whether
        the computer contains the Exchange store associated
        with the folder tree."
    ::= { exchangeFolderTreeEntry 7 }

exftLastModificationTime OBJECT-TYPE
    SYNTAX     DateAndTime
    MAX-ACCESS read-only
    STATUS     current
    DESCRIPTION
        "The LastModificationTime property indicates when
        the tree was last modified."
    ::= { exchangeFolderTreeEntry 8 }

exftMapiFolderTree OBJECT-TYPE
    SYNTAX     TruthValue
    MAX-ACCESS read-only
    STATUS     current
    DESCRIPTION
        "The MapiFolderTree property indicates whether this
        is the MAPI top-level hierarchy (TLH)."
    ::= { exchangeFolderTreeEntry 9 }

exftName OBJECT-TYPE
    SYNTAX     DisplayString
    MAX-ACCESS read-only
    STATUS     current
    DESCRIPTION
        "The Name property indicates the name of the
        top-level hierarchy (TLH)."
    ::= { exchangeFolderTreeEntry 10 }

exftRootFolderURL OBJECT-TYPE
    SYNTAX     DisplayString
    MAX-ACCESS read-only
    STATUS     current
    DESCRIPTION
        "The RootFolderURL property indicates the URL to
        the root of the tree referenced through the
        Exchange administration IIS virtual directory."
    ::= { exchangeFolderTreeEntry 11 }

exchangeLinkV2Table OBJECT-TYPE
    SYNTAX     SEQUENCE OF ExchangeLinkV2Entry
    MAX-ACCESS not-accessible
    STATUS     current
    DESCRIPTION
        "The Exchange_Link WMI class has properties that
        return information about message-handling links
        between mail servers. A link can contain zero or
        more Exchange_Queue objects, depending on the
        current message traffic along the link. In the
        Microsoft Exchange System Manager, these links are
        called queues."
    ::= { wmiExchange 8 }

exchangeLinkV2Entry OBJECT-TYPE
    SYNTAX     ExchangeLinkV2Entry
    MAX-ACCESS not-accessible
    STATUS     current
    DESCRIPTION
        "None"
    INDEX      { exl2Index }
    ::= { exchangeLinkV2Table 1 }

ExchangeLinkV2Entry ::= SEQUENCE {
    exl2Index Integer32,
    exl2ActionFreeze TruthValue,
    exl2ActionKick TruthValue,
    exl2ActionThaw TruthValue,
    exl2ExtendedStateInfo DisplayString,
    exl2GlobalStop TruthValue,
    exl2LinkDN DisplayString,
    exl2LinkId DisplayString,
    exl2LinkName DisplayString,
    exl2MessageCount Gauge32,
    exl2NextScheduledConnection DateAndTime,
    exl2OldestMessage DateAndTime,
    exl2ProtocolName DisplayString,
    exl2Size DisplayString,
    exl2StateActive TruthValue,
    exl2StateFlags Gauge32,
    exl2StateFrozen TruthValue,
    exl2StateReady TruthValue,
    exl2StateRemote TruthValue,
    exl2StateRetry TruthValue,
    exl2StateScheduled TruthValue,
    exl2SupportedLinkActions Gauge32,
    exl2TypeCurrentlyUnreachable TruthValue,
    exl2TypeDeferredDelivery TruthValue,
    exl2TypeInternal TruthValue,
    exl2TypeLocalDelivery TruthValue,
    exl2TypePendingCategorization TruthValue,
    exl2TypePendingRouting TruthValue,
    exl2TypePendingSubmission TruthValue,
    exl2TypeRemoteDelivery TruthValue,
    exl2Version Gauge32,
    exl2VirtualMachine DisplayString,
    exl2VirtualServerName DisplayString
}

exl2Index OBJECT-TYPE
    SYNTAX     Integer32 (1..2147483647)
    MAX-ACCESS read-only
    STATUS     current
    DESCRIPTION
        "The value of this object uniquely identifies the
        instance entry for this class."
    ::= { exchangeLinkV2Entry 1 }

exl2ActionFreeze OBJECT-TYPE
    SYNTAX     TruthValue
    MAX-ACCESS read-only
    STATUS     current
    DESCRIPTION
        "The ActionFreeze property, when TRUE, specifies
        that the link supports freezing messages in its
        queues. The ActionFreeze property corresponds to
        the sixth bit (0x00000020) of the
        SupportedLinkActions property."
    ::= { exchangeLinkV2Entry 2 }

exl2ActionKick OBJECT-TYPE
    SYNTAX     TruthValue
    MAX-ACCESS read-only
    STATUS     current
    DESCRIPTION
        "The ActionKick property, when TRUE, specifies that
        the link can trigger its queues to retry
        transmitting waiting messages immediately, instead
        of waiting for the default protocol timeout before
        retrying the transmission. The ActionKick property
        corresponds to the first bit (0x00000001) of the
        SupportedLinkActions property."
    ::= { exchangeLinkV2Entry 3 }

exl2ActionThaw OBJECT-TYPE
    SYNTAX     TruthValue
    MAX-ACCESS read-only
    STATUS     current
    DESCRIPTION
        "The ActionThaw property, when TRUE, specifies that
        the link supports thawing messages in its queues.
        Thawing a queue is also known as 'unfreezing' that
        queue. The ActionThaw property corresponds to the
        seventh bit (0x00000040) of the
        SupportedLinkActions property."
    ::= { exchangeLinkV2Entry 4 }

exl2ExtendedStateInfo OBJECT-TYPE
    SYNTAX     DisplayString
    MAX-ACCESS read-only
    STATUS     current
    DESCRIPTION
        "The ExtendedStateInfo property provides the text
        description of the current link status, including
        extended error reporting and troubleshooting
        information."
    ::= { exchangeLinkV2Entry 5 }

exl2GlobalStop OBJECT-TYPE
    SYNTAX     TruthValue
    MAX-ACCESS read-only
    STATUS     current
    DESCRIPTION
        "The GlobalStop property indicates whether the
        virtual server for the link is in disabled mode. If
        True, the virtual server is disabled."
    ::= { exchangeLinkV2Entry 6 }

exl2LinkDN OBJECT-TYPE
    SYNTAX     DisplayString
    MAX-ACCESS read-only
    STATUS     current
    DESCRIPTION
        "The LinkDN property specifies the name of the
        link."
    ::= { exchangeLinkV2Entry 7 }

exl2LinkId OBJECT-TYPE
    SYNTAX     DisplayString
    MAX-ACCESS read-only
    STATUS     current
    DESCRIPTION
        "The LinkId property indicates the identifier for
        the link."
    ::= { exchangeLinkV2Entry 8 }

exl2LinkName OBJECT-TYPE
    SYNTAX     DisplayString
    MAX-ACCESS read-only
    STATUS     current
    DESCRIPTION
        "The LinkName property indicates the name of the
        link."
    ::= { exchangeLinkV2Entry 9 }

exl2MessageCount OBJECT-TYPE
    SYNTAX     Gauge32
    MAX-ACCESS read-only
    STATUS     current
    DESCRIPTION
        "The MessageCount property specifies the number of
        messages that are waiting for transmission across
        the link."
    ::= { exchangeLinkV2Entry 10 }

exl2NextScheduledConnection OBJECT-TYPE
    SYNTAX     DateAndTime
    MAX-ACCESS read-only
    STATUS     current
    DESCRIPTION
        "The NextScheduledConnection property indicates the
        next time a connection will be attempted."
    ::= { exchangeLinkV2Entry 11 }

exl2OldestMessage OBJECT-TYPE
    SYNTAX     DateAndTime
    MAX-ACCESS read-only
    STATUS     current
    DESCRIPTION
        "The OldestMessage property specifies the date and
        time that the oldest message that is still waiting
        to be transmitted was received into the link."
    ::= { exchangeLinkV2Entry 12 }

exl2ProtocolName OBJECT-TYPE
    SYNTAX     DisplayString
    MAX-ACCESS read-only
    STATUS     current
    DESCRIPTION
        "The ProtocolName property indicates the
        transmission protocol used by the link."
    ::= { exchangeLinkV2Entry 13 }

exl2Size OBJECT-TYPE
    SYNTAX     DisplayString
    MAX-ACCESS read-only
    STATUS     current
    DESCRIPTION
        "The Size property specifies the total size of the
        messages in the link, in bytes."
    ::= { exchangeLinkV2Entry 14 }

exl2StateActive OBJECT-TYPE
    SYNTAX     TruthValue
    MAX-ACCESS read-only
    STATUS     current
    DESCRIPTION
        "The StateActive property, when TRUE, specifies
        that the link is active. The StateActive property
        corresponds to first bit (0x00000001) of the
        StateFlags property."
    ::= { exchangeLinkV2Entry 15 }

exl2StateFlags OBJECT-TYPE
    SYNTAX     Gauge32
    MAX-ACCESS read-only
    STATUS     current
    DESCRIPTION
        "The StateFlags property specifies the state of the
        link. The individual bits of this property are
        available as the link State. and Type. properties
        of this class."
    ::= { exchangeLinkV2Entry 16 }

exl2StateFrozen OBJECT-TYPE
    SYNTAX     TruthValue
    MAX-ACCESS read-only
    STATUS     current
    DESCRIPTION
        "The StateFrozen property indicates whether the
        link is currently frozen. The StateFrozen property
        corresponds to the sixth bit (0x00000020) of the
        StateFlags property."
    ::= { exchangeLinkV2Entry 17 }

exl2StateReady OBJECT-TYPE
    SYNTAX     TruthValue
    MAX-ACCESS read-only
    STATUS     current
    DESCRIPTION
        "The StateReady property, when TRUE, specifies that
        the link is ready to accept new messages. The
        StateReady property corresponds to the second bit
        (0x00000002) of the StateFlags property."
    ::= { exchangeLinkV2Entry 18 }

exl2StateRemote OBJECT-TYPE
    SYNTAX     TruthValue
    MAX-ACCESS read-only
    STATUS     current
    DESCRIPTION
        "The StateRemote property, when TRUE, specifies
        that the destination for messages in this link is
        on a remote server, instead of the messages being
        delivered to a local store. The StateRemote
        property corresponds to the fifth bit (0x00000010)
        of the StateFlags property."
    ::= { exchangeLinkV2Entry 19 }

exl2StateRetry OBJECT-TYPE
    SYNTAX     TruthValue
    MAX-ACCESS read-only
    STATUS     current
    DESCRIPTION
        "The StateRetry property, when TRUE, specifies that
        the link is retrying a transmission that was
        unsuccessful. The StateRetry property corresponds
        to the third bit (0x00000004) of the StateFlags
        property."
    ::= { exchangeLinkV2Entry 20 }

exl2StateScheduled OBJECT-TYPE
    SYNTAX     TruthValue
    MAX-ACCESS read-only
    STATUS     current
    DESCRIPTION
        "The StateScheduled property, when TRUE, specifies
        that the link is scheduled for periodic activation,
        as compared with asynchronous, on-demand
        activation. The StateScheduled property corresponds
        to the fourth bit (0x00000008) of the StateFlags
        property."
    ::= { exchangeLinkV2Entry 21 }

exl2SupportedLinkActions OBJECT-TYPE
    SYNTAX     Gauge32
    MAX-ACCESS read-only
    STATUS     current
    DESCRIPTION
        "The SupportedLinkActions property specifies the
        actions supported by the link. The individual bits
        of this property are available as the Action.
        properties in this class."
    ::= { exchangeLinkV2Entry 22 }

exl2TypeCurrentlyUnreachable OBJECT-TYPE
    SYNTAX     TruthValue
    MAX-ACCESS read-only
    STATUS     current
    DESCRIPTION
        "The TypeCurrentlyUnreachable property, when TRUE,
        specifies that the link holds messages for
        destinations that currently cannot be reached. The
        TypeCurrentlyUnreachable property corresponds to
        the thirteenth bit (0x00001000) of the StateFlags
        property."
    ::= { exchangeLinkV2Entry 23 }

exl2TypeDeferredDelivery OBJECT-TYPE
    SYNTAX     TruthValue
    MAX-ACCESS read-only
    STATUS     current
    DESCRIPTION
        "The TypeDeferredDelivery property, when TRUE,
        specifies that the link holds mail that is awaiting
        a trigger to start transmission. The
        TypeDeferredDelivery property corresponds to the
        fourteenth bit (0x00002000) of the StateFlags
        property."
    ::= { exchangeLinkV2Entry 24 }

exl2TypeInternal OBJECT-TYPE
    SYNTAX     TruthValue
    MAX-ACCESS read-only
    STATUS     current
    DESCRIPTION
        "The TypeInternal property indicates that the link
        is used for internal message processing. The
        TypeInternal property corresponds to the fifteenth
        bit (0x00004000) of the StateFlags property."
    ::= { exchangeLinkV2Entry 25 }

exl2TypeLocalDelivery OBJECT-TYPE
    SYNTAX     TruthValue
    MAX-ACCESS read-only
    STATUS     current
    DESCRIPTION
        "The TypeLocalDelivery property, when TRUE,
        specifies that the link handles local mail
        delivery. The TypeLocalDelivery property
        corresponds to the tenth bit (0x00000200) of the
        StateFlags property."
    ::= { exchangeLinkV2Entry 26 }

exl2TypePendingCategorization OBJECT-TYPE
    SYNTAX     TruthValue
    MAX-ACCESS read-only
    STATUS     current
    DESCRIPTION
        "The TypePendingCategorization property, when TRUE,
        specifies that the link is resolving addresses
        against entries in Active Directory. The
        TypePendingCategorization property corresponds to
        the twelfth bit (0x00000800) of the StateFlags
        property."
    ::= { exchangeLinkV2Entry 27 }

exl2TypePendingRouting OBJECT-TYPE
    SYNTAX     TruthValue
    MAX-ACCESS read-only
    STATUS     current
    DESCRIPTION
        "The TypePendingRouting property, when TRUE,
        specifies that the link is determining the routing
        of the next message that is waiting to be
        transmitted. The TypePendingRouting property
        corresponds to the eleventh bit (0x00000400) of the
        StateFlags property."
    ::= { exchangeLinkV2Entry 28 }

exl2TypePendingSubmission OBJECT-TYPE
    SYNTAX     TruthValue
    MAX-ACCESS read-only
    STATUS     current
    DESCRIPTION
        "The TypePendingSubmission property, when TRUE,
        specifies that the link handles messages that have
        not yet been submitted to the routing engine. The
        TypePendingSubmission property corresponds to the
        sixteenth bit (0x00008000) of the StateFlags
        property."
    ::= { exchangeLinkV2Entry 29 }

exl2TypeRemoteDelivery OBJECT-TYPE
    SYNTAX     TruthValue
    MAX-ACCESS read-only
    STATUS     current
    DESCRIPTION
        "The TypeRemoteDelivery property, when TRUE,
        specifies that the link is currently handling a
        remote message delivery. The TypeRemoteDelivery
        property corresponds to the ninth bit (0x00000100)
        of the StateFlags property."
    ::= { exchangeLinkV2Entry 30 }

exl2Version OBJECT-TYPE
    SYNTAX     Gauge32
    MAX-ACCESS read-only
    STATUS     current
    DESCRIPTION
        "The Version property specifies the version number
        of the underlying link control software."
    ::= { exchangeLinkV2Entry 31 }

exl2VirtualMachine OBJECT-TYPE
    SYNTAX     DisplayString
    MAX-ACCESS read-only
    STATUS     current
    DESCRIPTION
        "The VirtualMachine property indicates the name of
        the virtual machine that is the source of the
        link."
    ::= { exchangeLinkV2Entry 32 }

exl2VirtualServerName OBJECT-TYPE
    SYNTAX     DisplayString
    MAX-ACCESS read-only
    STATUS     current
    DESCRIPTION
        "The value of the VirtualServerName property is the
        integer number of the virtual machine that is the
        source of the link. This number is the Microsoft
        Active Directory common name (CN) for the virtual
        server object."
    ::= { exchangeLinkV2Entry 33 }

exchangeLogonTable OBJECT-TYPE
    SYNTAX     SEQUENCE OF ExchangeLogonEntry
    MAX-ACCESS not-accessible
    STATUS     current
    DESCRIPTION
        "Instances of Exchange_Logon represent the users
        currently logged on to Microsoft Exchange."
    ::= { wmiExchange 9 }

exchangeLogonEntry OBJECT-TYPE
    SYNTAX     ExchangeLogonEntry
    MAX-ACCESS not-accessible
    STATUS     current
    DESCRIPTION
        "None"
    INDEX      { exloIndex }
    ::= { exchangeLogonTable 1 }

ExchangeLogonEntry ::= SEQUENCE {
    exloIndex Integer32,
    exloAdapterSpeed Gauge32,
    exloClientIP DisplayString,
    exloClientMode INTEGER,
    exloClientName DisplayString,
    exloClientVersion DisplayString,
    exloCodePageID Gauge32,
    exloFolderOperationRate Gauge32,
    exloHostAddress DisplayString,
    exloLastOperationTime DateAndTime,
    exloLatency Gauge32,
    exloLocaleID Gauge32,
    exloLoggedOnUserAccount DisplayString,
    exloLoggedOnUsersMailboxLegacyDN DisplayString,
    exloLogonTime DateAndTime,
    exloMacAddress DisplayString,
    exloMailboxDisplayName DisplayString,
    exloMailboxLegacyDN DisplayString,
    exloMessagingOperationRate Gauge32,
    exloOpenAttachmentCount Gauge32,
    exloOpenFolderCount Gauge32,
    exloOpenMessageCount Gauge32,
    exloOtherOperationRate Gauge32,
    exloProgressOperationRate Gauge32,
    exloRowID Gauge32,
    exloRPCSucceeded Integer32,
    exloServerName DisplayString,
    exloStorageGroupName DisplayString,
    exloStoreName DisplayString,
    exloStoreType INTEGER,
    exloStreamOperationRate Gauge32,
    exloTableOperationRate Gauge32,
    exloTotalOperationRate Gauge32,
    exloTransferOperationRate Gauge32
}

exloIndex OBJECT-TYPE
    SYNTAX     Integer32 (1..2147483647)
    MAX-ACCESS read-only
    STATUS     current
    DESCRIPTION
        "The value of this object uniquely identifies the
        instance entry for this class."
    ::= { exchangeLogonEntry 1 }

exloAdapterSpeed OBJECT-TYPE
    SYNTAX     Gauge32
    UNITS "Kbits/s"
    MAX-ACCESS read-only
    STATUS     current
    DESCRIPTION
        "The AdapterSpeed property indicates the speed of
        the client network interface card, in
        kilobits/second"
    ::= { exchangeLogonEntry 2 }

exloClientIP OBJECT-TYPE
    SYNTAX     DisplayString
    MAX-ACCESS read-only
    STATUS     current
    DESCRIPTION
        "The ClientIP property indicates the IP address of
        the client computer."
    ::= { exchangeLogonEntry 3 }

exloClientMode OBJECT-TYPE
    SYNTAX     INTEGER {
        classicOnline(1),
        cached(2)
    }
    MAX-ACCESS read-only
    STATUS     current
    DESCRIPTION
        "The ClientMode property indicates whether the
        client is using local data caching."
    ::= { exchangeLogonEntry 4 }

exloClientName OBJECT-TYPE
    SYNTAX     DisplayString
    MAX-ACCESS read-only
    STATUS     current
    DESCRIPTION
        "The ClientName property indicates the client
        computer name."
    ::= { exchangeLogonEntry 5 }

exloClientVersion OBJECT-TYPE
    SYNTAX     DisplayString
    MAX-ACCESS read-only
    STATUS     current
    DESCRIPTION
        "The ClientVersion property indicates the version
        of the client used to log on."
    ::= { exchangeLogonEntry 6 }

exloCodePageID OBJECT-TYPE
    SYNTAX     Gauge32
    MAX-ACCESS read-only
    STATUS     current
    DESCRIPTION
        "The CodePageID property indicates the code page of
        the client."
    ::= { exchangeLogonEntry 7 }

exloFolderOperationRate OBJECT-TYPE
    SYNTAX     Gauge32
    UNITS "per second"
    MAX-ACCESS read-only
    STATUS     current
    DESCRIPTION
        "The FolderOperationRate property indicates the
        folder operation rate (per second) performed by the
        store on behalf of the client."
    ::= { exchangeLogonEntry 8 }

exloHostAddress OBJECT-TYPE
    SYNTAX     DisplayString
    MAX-ACCESS read-only
    STATUS     current
    DESCRIPTION
        "The HostAddress property indicates the
        client-specific identification information."
    ::= { exchangeLogonEntry 9 }

exloLastOperationTime OBJECT-TYPE
    SYNTAX     DateAndTime
    MAX-ACCESS read-only
    STATUS     current
    DESCRIPTION
        "The LastOperationTime property indicates the time
        when the last operation was performed."
    ::= { exchangeLogonEntry 10 }

exloLatency OBJECT-TYPE
    SYNTAX     Gauge32
    UNITS "msec"
    MAX-ACCESS read-only
    STATUS     current
    DESCRIPTION
        "The Latency property indicates the server response
        latency time reported by the client, in
        milliseconds."
    ::= { exchangeLogonEntry 11 }

exloLocaleID OBJECT-TYPE
    SYNTAX     Gauge32
    MAX-ACCESS read-only
    STATUS     current
    DESCRIPTION
        "The LocaleID property indicates the Windows locale
        of the client."
    ::= { exchangeLogonEntry 12 }

exloLoggedOnUserAccount OBJECT-TYPE
    SYNTAX     DisplayString
    MAX-ACCESS read-only
    STATUS     current
    DESCRIPTION
        "The LoggedOnUserAccount property indicates the
        name of the user account that logged on in the
        format DOMAIN\SAMAccountName."
    ::= { exchangeLogonEntry 13 }

exloLoggedOnUsersMailboxLegacyDN OBJECT-TYPE
    SYNTAX     DisplayString
    MAX-ACCESS read-only
    STATUS     current
    DESCRIPTION
        "The LoggedOnUsersMailboxLegacyDN property
        indicates the legacyDN of the user who is currently
        logged on."
    ::= { exchangeLogonEntry 14 }

exloLogonTime OBJECT-TYPE
    SYNTAX     DateAndTime
    MAX-ACCESS read-only
    STATUS     current
    DESCRIPTION
        "The LogonTime property indicates the time that the
        user logged on."
    ::= { exchangeLogonEntry 15 }

exloMacAddress OBJECT-TYPE
    SYNTAX     DisplayString
    MAX-ACCESS read-only
    STATUS     current
    DESCRIPTION
        "The MacAddress property indicates the network
        interface card Media Access Connector address of
        the client computer."
    ::= { exchangeLogonEntry 16 }

exloMailboxDisplayName OBJECT-TYPE
    SYNTAX     DisplayString
    MAX-ACCESS read-only
    STATUS     current
    DESCRIPTION
        "The MailboxDisplayName property indicates the name
        of the mailbox."
    ::= { exchangeLogonEntry 17 }

exloMailboxLegacyDN OBJECT-TYPE
    SYNTAX     DisplayString
    MAX-ACCESS read-only
    STATUS     current
    DESCRIPTION
        "The MailboxLegacyDN property indicates the
        legacyDN of the mailbox."
    ::= { exchangeLogonEntry 18 }

exloMessagingOperationRate OBJECT-TYPE
    SYNTAX     Gauge32
    UNITS "per second"
    MAX-ACCESS read-only
    STATUS     current
    DESCRIPTION
        "The MessagingOperationRate property indicates the
        rate of send/receive operations performed per
        second by the store on behalf of the client."
    ::= { exchangeLogonEntry 19 }

exloOpenAttachmentCount OBJECT-TYPE
    SYNTAX     Gauge32
    MAX-ACCESS read-only
    STATUS     current
    DESCRIPTION
        "The OpenAttachmentCount property indicates the
        number of attachments currently opened by the
        client."
    ::= { exchangeLogonEntry 20 }

exloOpenFolderCount OBJECT-TYPE
    SYNTAX     Gauge32
    MAX-ACCESS read-only
    STATUS     current
    DESCRIPTION
        "The OpenFolderCount property indicates the number
        of folders currently opened by the client."
    ::= { exchangeLogonEntry 21 }

exloOpenMessageCount OBJECT-TYPE
    SYNTAX     Gauge32
    MAX-ACCESS read-only
    STATUS     current
    DESCRIPTION
        "The OpenMessageCount property indicates the number
        of messages currently opened by the client."
    ::= { exchangeLogonEntry 22 }

exloOtherOperationRate OBJECT-TYPE
    SYNTAX     Gauge32
    UNITS "per second"
    MAX-ACCESS read-only
    STATUS     current
    DESCRIPTION
        "The OtherOperationRate property indicates the rate
        of operations performed on the store, in response
        to client requests that are not within the other
        categories of operation-request properties."
    ::= { exchangeLogonEntry 23 }

exloProgressOperationRate OBJECT-TYPE
    SYNTAX     Gauge32
    UNITS "per second"
    MAX-ACCESS read-only
    STATUS     current
    DESCRIPTION
        "The ProgressOperationRate property indicates the
        rate of progress operations performed per second by
        the store on behalf of the client."
    ::= { exchangeLogonEntry 24 }

exloRowID OBJECT-TYPE
    SYNTAX     Gauge32
    MAX-ACCESS read-only
    STATUS     current
    DESCRIPTION
        "The RowID property indicates that a random
        identifier is generated per query to ensure
        uniqueness."
    ::= { exchangeLogonEntry 25 }

exloRPCSucceeded OBJECT-TYPE
    SYNTAX     Integer32
    MAX-ACCESS read-only
    STATUS     current
    DESCRIPTION
        "The RPCSucceeded property indicates the number of
        successful RPC requests made by the client."
    ::= { exchangeLogonEntry 26 }

exloServerName OBJECT-TYPE
    SYNTAX     DisplayString
    MAX-ACCESS read-only
    STATUS     current
    DESCRIPTION
        "The ServerName property indicates the name of the
        server where the mailbox resides."
    ::= { exchangeLogonEntry 27 }

exloStorageGroupName OBJECT-TYPE
    SYNTAX     DisplayString
    MAX-ACCESS read-only
    STATUS     current
    DESCRIPTION
        "The StorageGroupName property indicates the name
        of the storage group that contains the mailbox."
    ::= { exchangeLogonEntry 28 }

exloStoreName OBJECT-TYPE
    SYNTAX     DisplayString
    MAX-ACCESS read-only
    STATUS     current
    DESCRIPTION
        "The StoreName property indicates the name of the
        MDB that contains the mailbox."
    ::= { exchangeLogonEntry 29 }

exloStoreType OBJECT-TYPE
    SYNTAX     INTEGER {
        mailboxStore(1),
        publicStore(2)
    }
    MAX-ACCESS read-only
    STATUS     current
    DESCRIPTION
        "The StoreType property indicates whether the store
        contains mailboxes or public folders."
    ::= { exchangeLogonEntry 30 }

exloStreamOperationRate OBJECT-TYPE
    SYNTAX     Gauge32
    UNITS "per second"
    MAX-ACCESS read-only
    STATUS     current
    DESCRIPTION
        "The StreamOperationRate property indicates the
        rate of stream operations performed per second by
        the store on behalf of the client."
    ::= { exchangeLogonEntry 31 }

exloTableOperationRate OBJECT-TYPE
    SYNTAX     Gauge32
    UNITS "per second"
    MAX-ACCESS read-only
    STATUS     current
    DESCRIPTION
        "The TableOperationRate property indicates the rate
        of table operations performed per second by the
        store on behalf of the client."
    ::= { exchangeLogonEntry 32 }

exloTotalOperationRate OBJECT-TYPE
    SYNTAX     Gauge32
    UNITS "per second"
    MAX-ACCESS read-only
    STATUS     current
    DESCRIPTION
        "The TotalOperationRate property indicates the rate
        of all operations performed per second by the store
        on behalf of the client."
    ::= { exchangeLogonEntry 33 }

exloTransferOperationRate OBJECT-TYPE
    SYNTAX     Gauge32
    UNITS "per second"
    MAX-ACCESS read-only
    STATUS     current
    DESCRIPTION
        "The TransferOperationRate property indicates the
        rate of transfer operations performed per second by
        the store on behalf of the client."
    ::= { exchangeLogonEntry 34 }

exchangeMailboxTable OBJECT-TYPE
    SYNTAX     SEQUENCE OF ExchangeMailboxEntry
    MAX-ACCESS not-accessible
    STATUS     current
    DESCRIPTION
        "The Exchange_Mailbox WMI class has properties that
        return information about Microsoft Exchange
        mailboxes."
    ::= { wmiExchange 10 }

exchangeMailboxEntry OBJECT-TYPE
    SYNTAX     ExchangeMailboxEntry
    MAX-ACCESS not-accessible
    STATUS     current
    DESCRIPTION
        "None"
    INDEX      { exmIndex }
    ::= { exchangeMailboxTable 1 }

ExchangeMailboxEntry ::= SEQUENCE {
    exmIndex Integer32,
    exmAssocContentCount Gauge32,
    exmDateDiscoveredAbsentInDS DateAndTime,
    exmDeletedMessageSizeExtended DisplayString,
    exmLastLoggedOnUserAccount DisplayString,
    exmLastLogoffTime DateAndTime,
    exmLastLogonTime DateAndTime,
    exmLegacyDN DisplayString,
    exmMailboxDisplayName DisplayString,
    exmMailboxGUID DisplayString,
    exmServerName DisplayString,
    exmSize DisplayString,
    exmStorageGroupName DisplayString,
    exmStorageLimitInfo INTEGER,
    exmStoreName DisplayString,
    exmTotalItems Gauge32
}

exmIndex OBJECT-TYPE
    SYNTAX     Integer32 (1..2147483647)
    MAX-ACCESS read-only
    STATUS     current
    DESCRIPTION
        "The value of this object uniquely identifies the
        instance entry for this class."
    ::= { exchangeMailboxEntry 1 }

exmAssocContentCount OBJECT-TYPE
    SYNTAX     Gauge32
    MAX-ACCESS read-only
    STATUS     current
    DESCRIPTION
        "The AssocContentCount property indicates the total
        number of messages associated with the mailbox
        folders."
    ::= { exchangeMailboxEntry 2 }

exmDateDiscoveredAbsentInDS OBJECT-TYPE
    SYNTAX     DateAndTime
    MAX-ACCESS read-only
    STATUS     current
    DESCRIPTION
        "The DateDiscoveredAbsentInDS property indicates
        when the store detected that the mailbox no longer
        had a corresponding user entry in Microsoft Active
        Directory."
    ::= { exchangeMailboxEntry 3 }

exmDeletedMessageSizeExtended OBJECT-TYPE
    SYNTAX     DisplayString
    UNITS "Bytes"
    MAX-ACCESS read-only
    STATUS     current
    DESCRIPTION
        "The DeletedMessageSizeExtended property indicates
        the cumulative size of all deleted messages that
        are still being retained according to retention
        policy settings."
    ::= { exchangeMailboxEntry 4 }

exmLastLoggedOnUserAccount OBJECT-TYPE
    SYNTAX     DisplayString
    MAX-ACCESS read-only
    STATUS     current
    DESCRIPTION
        "The LastLoggedOnUserAccount property indicates the
        account name last used to log on to the mailbox."
    ::= { exchangeMailboxEntry 5 }

exmLastLogoffTime OBJECT-TYPE
    SYNTAX     DateAndTime
    MAX-ACCESS read-only
    STATUS     current
    DESCRIPTION
        "The LastLogoffTime property indicates the time
        that the last user logged off."
    ::= { exchangeMailboxEntry 6 }

exmLastLogonTime OBJECT-TYPE
    SYNTAX     DateAndTime
    MAX-ACCESS read-only
    STATUS     current
    DESCRIPTION
        "The LastLogonTime property indicates the time that
        the last user logged on."
    ::= { exchangeMailboxEntry 7 }

exmLegacyDN OBJECT-TYPE
    SYNTAX     DisplayString
    MAX-ACCESS read-only
    STATUS     current
    DESCRIPTION
        "The LegacyDN property indicates the legacyDN of
        the mailbox and matches the legacyDN attribute of
        the user object in Microsoft Active Directory."
    ::= { exchangeMailboxEntry 8 }

exmMailboxDisplayName OBJECT-TYPE
    SYNTAX     DisplayString
    MAX-ACCESS read-only
    STATUS     current
    DESCRIPTION
        "The MailboxDisplayName property indicates the
        display name of the mailbox and matches the
        displayName attribute in Microsoft Active
        Directory."
    ::= { exchangeMailboxEntry 9 }

exmMailboxGUID OBJECT-TYPE
    SYNTAX     DisplayString
    MAX-ACCESS read-only
    STATUS     current
    DESCRIPTION
        "The MailboxGUID property indicates the globally
        unique identifier (GUID) that links the mailbox to
        a user in Microsoft Active Directory."
    ::= { exchangeMailboxEntry 10 }

exmServerName OBJECT-TYPE
    SYNTAX     DisplayString
    MAX-ACCESS read-only
    STATUS     current
    DESCRIPTION
        "The ServerName property indicates the name of the
        server where the mailbox resides."
    ::= { exchangeMailboxEntry 11 }

exmSize OBJECT-TYPE
    SYNTAX     DisplayString
    UNITS "Bytes"
    MAX-ACCESS read-only
    STATUS     current
    DESCRIPTION
        "The Size property indicates the cumulative size of
        all of the messages in the mailbox, in bytes."
    ::= { exchangeMailboxEntry 12 }

exmStorageGroupName OBJECT-TYPE
    SYNTAX     DisplayString
    MAX-ACCESS read-only
    STATUS     current
    DESCRIPTION
        "The StorageGroupName property indicates the name
        of the storage group that contains the mailbox."
    ::= { exchangeMailboxEntry 13 }

exmStorageLimitInfo OBJECT-TYPE
    SYNTAX     INTEGER {
        belowLimit(1),
        issueWarning(2),
        prohibitSend(4),
        noChecking(8),
        mailboxDisabled(16)
    }
    MAX-ACCESS read-only
    STATUS     current
    DESCRIPTION
        "The StorageLimitInfo property contains the storage
        limit settings on the mailbox."
    ::= { exchangeMailboxEntry 14 }

exmStoreName OBJECT-TYPE
    SYNTAX     DisplayString
    MAX-ACCESS read-only
    STATUS     current
    DESCRIPTION
        "The StoreName property indicates the name of the
        MDB that contains the mailbox."
    ::= { exchangeMailboxEntry 15 }

exmTotalItems OBJECT-TYPE
    SYNTAX     Gauge32
    MAX-ACCESS read-only
    STATUS     current
    DESCRIPTION
        "The TotalItems property indicates the total number
        of messages in the mailbox."
    ::= { exchangeMailboxEntry 16 }

exchangeMessageTrackingTable OBJECT-TYPE
    SYNTAX     SEQUENCE OF ExchangeMessageTrackingEntry
    MAX-ACCESS not-accessible
    STATUS     current
    DESCRIPTION
        "Instances of the Exchange_MessageTrackingEntry
        class provide information about events that have
        occurred to the message during the time it was
        under the control of the computer running Microsoft
        Exchange 2000 Server."
    ::= { wmiExchange 11 }

exchangeMessageTrackingEntry OBJECT-TYPE
    SYNTAX     ExchangeMessageTrackingEntry
    MAX-ACCESS not-accessible
    STATUS     current
    DESCRIPTION
        "None"
    INDEX      { exmtIndex }
    ::= { exchangeMessageTrackingTable 1 }

ExchangeMessageTrackingEntry ::= SEQUENCE {
    exmtIndex Integer32,
    exmtAttemptedPartnerServer DisplayString,
    exmtClientIP DisplayString,
    exmtClientName DisplayString,
    exmtCost Gauge32,
    exmtDeliveryTime Gauge32,
    exmtEncrypted TruthValue,
    exmtEntryType Gauge32,
    exmtExpansionDL DisplayString,
    exmtKeyID DisplayString,
    exmtLinkedMessageID DisplayString,
    exmtMessageID DisplayString,
    exmtOriginationTime DateAndTime,
    exmtPartnerServer DisplayString,
    exmtPriority Gauge32,
    exmtRecipientAddress DisplayString,
    exmtRecipientCount Gauge32,
    exmtRecipientStatus Gauge32,
    exmtSenderAddress DisplayString,
    exmtServerIP DisplayString,
    exmtServerName DisplayString,
    exmtSize Gauge32,
    exmtSubject DisplayString,
    exmtSubjectID DisplayString,
    exmtTimeLogged DateAndTime,
    exmtVersion DisplayString
}

exmtIndex OBJECT-TYPE
    SYNTAX     Integer32 (1..2147483647)
    MAX-ACCESS read-only
    STATUS     current
    DESCRIPTION
        "The value of this object uniquely identifies the
        instance entry for this class."
    ::= { exchangeMessageTrackingEntry 1 }

exmtAttemptedPartnerServer OBJECT-TYPE
    SYNTAX     DisplayString
    MAX-ACCESS read-only
    STATUS     current
    DESCRIPTION
        "The AttemptedPartnerServer property indicates the
        server to which Exchange tried to send a message,
        but was unable to complete the transfer."
    ::= { exchangeMessageTrackingEntry 2 }

exmtClientIP OBJECT-TYPE
    SYNTAX     DisplayString
    MAX-ACCESS read-only
    STATUS     current
    DESCRIPTION
        "The ClientIP property indicates the TCP/IP address
        of the messaging client that originally submitted
        the message."
    ::= { exchangeMessageTrackingEntry 3 }

exmtClientName OBJECT-TYPE
    SYNTAX     DisplayString
    MAX-ACCESS read-only
    STATUS     current
    DESCRIPTION
        "The ClientName property indicates the name of the
        messaging client application that submitted the
        message."
    ::= { exchangeMessageTrackingEntry 4 }

exmtCost OBJECT-TYPE
    SYNTAX     Gauge32
    MAX-ACCESS read-only
    STATUS     current
    DESCRIPTION
        "The Cost property indicates the relative effort
        required to transfer the message. There are no
        specific units used in this property. Higher values
        indicate that slower network connections must be
        used, or that a greater number of transfers is
        required to transfer the message."
    ::= { exchangeMessageTrackingEntry 5 }

exmtDeliveryTime OBJECT-TYPE
    SYNTAX     Gauge32
    UNITS "seconds"
    MAX-ACCESS read-only
    STATUS     current
    DESCRIPTION
        "The DeliveryTime property indicates the amount of
        time, in seconds, required to deliver the message."
    ::= { exchangeMessageTrackingEntry 6 }

exmtEncrypted OBJECT-TYPE
    SYNTAX     TruthValue
    MAX-ACCESS read-only
    STATUS     current
    DESCRIPTION
        "The Encrypted property indicates, when True, that
        the message is encrypted."
    ::= { exchangeMessageTrackingEntry 7 }

exmtEntryType OBJECT-TYPE
    SYNTAX     Gauge32
    MAX-ACCESS read-only
    STATUS     current
    DESCRIPTION
        "The EntryType property indicates what occurred to
        cause the message tracking log entry to be
        created."
    ::= { exchangeMessageTrackingEntry 8 }

exmtExpansionDL OBJECT-TYPE
    SYNTAX     DisplayString
    MAX-ACCESS read-only
    STATUS     current
    DESCRIPTION
        "The ExpansionDL property indicates the name of the
        Exchange distribution list that was expanded. After
        the distribution list is expanded, the message
        recipient list includes the names of the individual
        members of that distribution list."
    ::= { exchangeMessageTrackingEntry 9 }

exmtKeyID OBJECT-TYPE
    SYNTAX     DisplayString
    MAX-ACCESS read-only
    STATUS     current
    DESCRIPTION
        "The KeyID property uniquely identifies the message
        log entry."
    ::= { exchangeMessageTrackingEntry 10 }

exmtLinkedMessageID OBJECT-TYPE
    SYNTAX     DisplayString
    MAX-ACCESS read-only
    STATUS     current
    DESCRIPTION
        "The LinkedMessageID property is the string
        identifier assigned to the message when it is
        received by the PartnerServer property. This
        property sometimes has the same value as the
        MessageID Property."
    ::= { exchangeMessageTrackingEntry 11 }

exmtMessageID OBJECT-TYPE
    SYNTAX     DisplayString
    MAX-ACCESS read-only
    STATUS     current
    DESCRIPTION
        "The MessageID property indicates the identifier
        string for the message. The identifier may be
        assigned by the messaging client application or by
        the Exchange server."
    ::= { exchangeMessageTrackingEntry 12 }

exmtOriginationTime OBJECT-TYPE
    SYNTAX     DateAndTime
    MAX-ACCESS read-only
    STATUS     current
    DESCRIPTION
        "The OriginationTime property indicates the date
        and time, in UTC, when the message was received by
        Exchange."
    ::= { exchangeMessageTrackingEntry 13 }

exmtPartnerServer OBJECT-TYPE
    SYNTAX     DisplayString
    MAX-ACCESS read-only
    STATUS     current
    DESCRIPTION
        "The PartnerServer property indicates the server to
        which Exchange transferred the message."
    ::= { exchangeMessageTrackingEntry 14 }

exmtPriority OBJECT-TYPE
    SYNTAX     Gauge32
    MAX-ACCESS read-only
    STATUS     current
    DESCRIPTION
        "The Priority property specifies the importance of
        the message, as displayed by the messaging client
        application."
    ::= { exchangeMessageTrackingEntry 15 }

exmtRecipientAddress OBJECT-TYPE
    SYNTAX     DisplayString
    MAX-ACCESS read-only
    STATUS     current
    DESCRIPTION
        "The RecipientAddress property returns an array.
        Each array element contains the e-mail address of
        one of the message recipients."
    ::= { exchangeMessageTrackingEntry 16 }

exmtRecipientCount OBJECT-TYPE
    SYNTAX     Gauge32
    MAX-ACCESS read-only
    STATUS     current
    DESCRIPTION
        "The RecipientCount property indicates how many
        recipients are in the recipients list for the
        message."
    ::= { exchangeMessageTrackingEntry 17 }

exmtRecipientStatus OBJECT-TYPE
    SYNTAX     Gauge32
    MAX-ACCESS read-only
    STATUS     current
    DESCRIPTION
        "Each element of the RecipientStatus array
        indicates the message type sent to the recipient
        specified in the corresponding element of the
        RecipientAddress array."
    ::= { exchangeMessageTrackingEntry 18 }

exmtSenderAddress OBJECT-TYPE
    SYNTAX     DisplayString
    MAX-ACCESS read-only
    STATUS     current
    DESCRIPTION
        "The SenderAddress property specifies the e-mail
        address of the message sender."
    ::= { exchangeMessageTrackingEntry 19 }

exmtServerIP OBJECT-TYPE
    SYNTAX     DisplayString
    MAX-ACCESS read-only
    STATUS     current
    DESCRIPTION
        "The ServerIP property indicates the TCP/IP
        protocol address of the Exchange server."
    ::= { exchangeMessageTrackingEntry 20 }

exmtServerName OBJECT-TYPE
    SYNTAX     DisplayString
    MAX-ACCESS read-only
    STATUS     current
    DESCRIPTION
        "The ServerName property indicates the name of the
        virtual server instance that created the message
        tracking log entry."
    ::= { exchangeMessageTrackingEntry 21 }

exmtSize OBJECT-TYPE
    SYNTAX     Gauge32
    MAX-ACCESS read-only
    STATUS     current
    DESCRIPTION
        "The Size property indicates the message size,
        including attachments, in bytes."
    ::= { exchangeMessageTrackingEntry 22 }

exmtSubject OBJECT-TYPE
    SYNTAX     DisplayString
    MAX-ACCESS read-only
    STATUS     current
    DESCRIPTION
        "The Subject property indicates the subject of the
        message, as found in the Subject: message header."
    ::= { exchangeMessageTrackingEntry 23 }

exmtSubjectID OBJECT-TYPE
    SYNTAX     DisplayString
    MAX-ACCESS read-only
    STATUS     current
    DESCRIPTION
        "The SubjectID property specifies an identifier
        created by the messaging client application."
    ::= { exchangeMessageTrackingEntry 24 }

exmtTimeLogged OBJECT-TYPE
    SYNTAX     DateAndTime
    MAX-ACCESS read-only
    STATUS     current
    DESCRIPTION
        "The TimeLogged property indicates the date and
        time, in UTC, when the message tracking log entry
        was created."
    ::= { exchangeMessageTrackingEntry 25 }

exmtVersion OBJECT-TYPE
    SYNTAX     DisplayString
    MAX-ACCESS read-only
    STATUS     current
    DESCRIPTION
        "The Version property indicates the version of the
        service that created the message tracking log
        entry."
    ::= { exchangeMessageTrackingEntry 26 }

exchangePublicFolderTable OBJECT-TYPE
    SYNTAX     SEQUENCE OF ExchangePublicFolderEntry
    MAX-ACCESS not-accessible
    STATUS     current
    DESCRIPTION
        "The Exchange_PublicFolder WMI class provides
        properties and methods for working with Microsoft
        Exchange public folders."
    ::= { wmiExchange 12 }

exchangePublicFolderEntry OBJECT-TYPE
    SYNTAX     ExchangePublicFolderEntry
    MAX-ACCESS not-accessible
    STATUS     current
    DESCRIPTION
        "None"
    INDEX      { expfIndex }
    ::= { exchangePublicFolderTable 1 }

ExchangePublicFolderEntry ::= SEQUENCE {
    expfIndex Integer32,
    expfAddressBookName DisplayString,
    expfAdministrativeNote DisplayString,
    expfAdminSecurityDescriptor DisplayString,
    expfADProxyPath DisplayString,
    expfAssociatedMessageCount Gauge32,
    expfAttachmentCount Gauge32,
    expfCategorizationCount Gauge32,
    expfComment DisplayString,
    expfContactCount Gauge32,
    expfContainsRules TruthValue,
    expfCreationTime DateAndTime,
    expfDeletedItemLifetime Gauge32,
    expfFolderTree DisplayString,
    expfFriendlyUrl DisplayString,
    expfHasChildren TruthValue,
    expfHasLocalReplica TruthValue,
    expfIsMailEnabled TruthValue,
    expfIsNormalFolder TruthValue,
    expfIsPerUserReadDisabled TruthValue,
    expfIsSearchFolder TruthValue,
    expfIsSecureInSite TruthValue,
    expfLastAccessTime DateAndTime,
    expfLastModificationTime DateAndTime,
    expfMaximumItemSize Gauge32,
    expfMessageCount Gauge32,
    expfMessageWithAttachmentsCount Gauge32,
    expfName DisplayString,
    expfNormalMessageSize Gauge32,
    expfOwnerCount Gauge32,
    expfParentFriendlyUrl DisplayString,
    expfPath DisplayString,
    expfProhibitPostLimit Gauge32,
    expfPublishInAddressBook TruthValue,
    expfRecipientCountOnAssociateMsg Gauge32,
    expfRecipientCountOnNormalMsg Gauge32,
    expfReplicaAgeLimit Gauge32,
    expfReplicaList DisplayString,
    expfReplicationMessagePriority INTEGER,
    expfReplicationSchedule DisplayString,
    expfReplicationStyle INTEGER,
    expfRestrictionCount Gauge32,
    expfSecurityDescriptor DisplayString,
    expfStorageLimitStyle INTEGER,
    expfTargetAddress DisplayString,
    expfTotalMessageSize Gauge32,
    expfUrl DisplayString,
    expfUsePublicStoreAgeLimits TruthValue,
    expfUsePublicStoreDelItemLifetm TruthValue,
    expfWarningLimit Gauge32
}

expfIndex OBJECT-TYPE
    SYNTAX     Integer32 (1..2147483647)
    MAX-ACCESS read-only
    STATUS     current
    DESCRIPTION
        "The value of this object uniquely identifies the
        instance entry for this class."
    ::= { exchangePublicFolderEntry 1 }

expfAddressBookName OBJECT-TYPE
    SYNTAX     DisplayString
    MAX-ACCESS read-only
    STATUS     current
    DESCRIPTION
        "The AddressBookName property specifies the address
        book name of the folder."
    ::= { exchangePublicFolderEntry 2 }

expfAdministrativeNote OBJECT-TYPE
    SYNTAX     DisplayString
    MAX-ACCESS read-only
    STATUS     current
    DESCRIPTION
        "The AdministrativeNote property specifies the
        administrative note associated with the folder."
    ::= { exchangePublicFolderEntry 3 }

expfAdminSecurityDescriptor OBJECT-TYPE
    SYNTAX     DisplayString
    MAX-ACCESS read-only
    STATUS     current
    DESCRIPTION
        "The AdminSecurityDescriptor property specifies the
        security descriptor that is used when a user logs
        on to the store with administrative privileges."
    ::= { exchangePublicFolderEntry 4 }

expfADProxyPath OBJECT-TYPE
    SYNTAX     DisplayString
    MAX-ACCESS read-only
    STATUS     current
    DESCRIPTION
        "The ADProxyPath property indicates the globally
        unique identifier (GUID) of the Active Directory
        mail proxy for the folder."
    ::= { exchangePublicFolderEntry 5 }

expfAssociatedMessageCount OBJECT-TYPE
    SYNTAX     Gauge32
    MAX-ACCESS read-only
    STATUS     current
    DESCRIPTION
        "The AssociatedMessageCount property is a MAPI
        property that contains the total number of
        associated messages in the public folder."
    ::= { exchangePublicFolderEntry 6 }

expfAttachmentCount OBJECT-TYPE
    SYNTAX     Gauge32
    MAX-ACCESS read-only
    STATUS     current
    DESCRIPTION
        "The AttachmentCount property indicates the total
        number of attachments on all normal messages in a
        folder."
    ::= { exchangePublicFolderEntry 7 }

expfCategorizationCount OBJECT-TYPE
    SYNTAX     Gauge32
    MAX-ACCESS read-only
    STATUS     current
    DESCRIPTION
        "The CategorizationCount property indicates the
        total number of categorizations on the public
        folder."
    ::= { exchangePublicFolderEntry 8 }

expfComment OBJECT-TYPE
    SYNTAX     DisplayString
    MAX-ACCESS read-only
    STATUS     current
    DESCRIPTION
        "The Comment property specifies the folder
        comment."
    ::= { exchangePublicFolderEntry 9 }

expfContactCount OBJECT-TYPE
    SYNTAX     Gauge32
    MAX-ACCESS read-only
    STATUS     current
    DESCRIPTION
        "The ContactCount property indicates the number of
        contacts in a public folder."
    ::= { exchangePublicFolderEntry 10 }

expfContainsRules OBJECT-TYPE
    SYNTAX     TruthValue
    MAX-ACCESS read-only
    STATUS     current
    DESCRIPTION
        "The ContainsRules property indicates whether the
        public folder contains rules."
    ::= { exchangePublicFolderEntry 11 }

expfCreationTime OBJECT-TYPE
    SYNTAX     DateAndTime
    MAX-ACCESS read-only
    STATUS     current
    DESCRIPTION
        "The CreationTime property indicates when the
        folder was created."
    ::= { exchangePublicFolderEntry 12 }

expfDeletedItemLifetime OBJECT-TYPE
    SYNTAX     Gauge32
    UNITS "days"
    MAX-ACCESS read-only
    STATUS     current
    DESCRIPTION
        "The DeletedItemLifetime property specifies how
        long, in days, that deleted messages can be
        recovered."
    ::= { exchangePublicFolderEntry 13 }

expfFolderTree OBJECT-TYPE
    SYNTAX     DisplayString
    MAX-ACCESS read-only
    STATUS     current
    DESCRIPTION
        "The FolderTree property indicates the WMI path to
        the top-level hierarchy object to which the folder
        belongs."
    ::= { exchangePublicFolderEntry 14 }

expfFriendlyUrl OBJECT-TYPE
    SYNTAX     DisplayString
    MAX-ACCESS read-only
    STATUS     current
    DESCRIPTION
        "The FriendlyUrl property indicates the path-based
        URL to the folder."
    ::= { exchangePublicFolderEntry 15 }

expfHasChildren OBJECT-TYPE
    SYNTAX     TruthValue
    MAX-ACCESS read-only
    STATUS     current
    DESCRIPTION
        "The HasChildren property indicates whether the
        folder has subfolders."
    ::= { exchangePublicFolderEntry 16 }

expfHasLocalReplica OBJECT-TYPE
    SYNTAX     TruthValue
    MAX-ACCESS read-only
    STATUS     current
    DESCRIPTION
        "The HasLocalReplica property indicates whether the
        folder has a local replica."
    ::= { exchangePublicFolderEntry 17 }

expfIsMailEnabled OBJECT-TYPE
    SYNTAX     TruthValue
    MAX-ACCESS read-only
    STATUS     current
    DESCRIPTION
        "The IsMailEnabled property specifies whether the
        folder is mail-enabled."
    ::= { exchangePublicFolderEntry 18 }

expfIsNormalFolder OBJECT-TYPE
    SYNTAX     TruthValue
    MAX-ACCESS read-only
    STATUS     current
    DESCRIPTION
        "The IsNormalFolder property indicates whether the
        public folder is a normal folder."
    ::= { exchangePublicFolderEntry 19 }

expfIsPerUserReadDisabled OBJECT-TYPE
    SYNTAX     TruthValue
    MAX-ACCESS read-only
    STATUS     current
    DESCRIPTION
        "The IsPerUserReadDisabled property specifies
        whether the folder tracks per-user read information
        for messages."
    ::= { exchangePublicFolderEntry 20 }

expfIsSearchFolder OBJECT-TYPE
    SYNTAX     TruthValue
    MAX-ACCESS read-only
    STATUS     current
    DESCRIPTION
        "The IsSearchFolder property indicates whether the
        public folder is a search folder."
    ::= { exchangePublicFolderEntry 21 }

expfIsSecureInSite OBJECT-TYPE
    SYNTAX     TruthValue
    MAX-ACCESS read-only
    STATUS     current
    DESCRIPTION
        "The IsSecureInSite property specifies whether
        administrative access is limited to the home site
        of the folder."
    ::= { exchangePublicFolderEntry 22 }

expfLastAccessTime OBJECT-TYPE
    SYNTAX     DateAndTime
    MAX-ACCESS read-only
    STATUS     current
    DESCRIPTION
        "The LastAccessTime property indicates the last
        date that the replica of a public folder was
        accessed."
    ::= { exchangePublicFolderEntry 23 }

expfLastModificationTime OBJECT-TYPE
    SYNTAX     DateAndTime
    MAX-ACCESS read-only
    STATUS     current
    DESCRIPTION
        "The LastModificationTime property indicates when
        the folder was last modified."
    ::= { exchangePublicFolderEntry 24 }

expfMaximumItemSize OBJECT-TYPE
    SYNTAX     Gauge32
    UNITS "KB"
    MAX-ACCESS read-only
    STATUS     current
    DESCRIPTION
        "The MaximumItemSize property specifies the maximum
        size, in kilobytes, that is allowed for an
        individual post to the folder."
    ::= { exchangePublicFolderEntry 25 }

expfMessageCount OBJECT-TYPE
    SYNTAX     Gauge32
    MAX-ACCESS read-only
    STATUS     current
    DESCRIPTION
        "The MessageCount property indicates the number of
        messages in a public folder."
    ::= { exchangePublicFolderEntry 26 }

expfMessageWithAttachmentsCount OBJECT-TYPE
    SYNTAX     Gauge32
    MAX-ACCESS read-only
    STATUS     current
    DESCRIPTION
        "The MessageWithAttachmentsCount property indicates
        the total number of normal messages with
        attachments in the public folder."
    ::= { exchangePublicFolderEntry 27 }

expfName OBJECT-TYPE
    SYNTAX     DisplayString
    MAX-ACCESS read-only
    STATUS     current
    DESCRIPTION
        "The Name property indicates the name of the
        folder."
    ::= { exchangePublicFolderEntry 28 }

expfNormalMessageSize OBJECT-TYPE
    SYNTAX     Gauge32
    UNITS "bytes"
    MAX-ACCESS read-only
    STATUS     current
    DESCRIPTION
        "The NormalMessageSize property indicates the total
        size, in bytes, of all of the normal messages in
        the public folder."
    ::= { exchangePublicFolderEntry 29 }

expfOwnerCount OBJECT-TYPE
    SYNTAX     Gauge32
    MAX-ACCESS read-only
    STATUS     current
    DESCRIPTION
        "The OwnerCount property indicates the number of
        owners of the public folder."
    ::= { exchangePublicFolderEntry 30 }

expfParentFriendlyUrl OBJECT-TYPE
    SYNTAX     DisplayString
    MAX-ACCESS read-only
    STATUS     current
    DESCRIPTION
        "The ParentFriendlyUrl property indicates the
        folder path-based URL to the parent of the folder."
    ::= { exchangePublicFolderEntry 31 }

expfPath OBJECT-TYPE
    SYNTAX     DisplayString
    MAX-ACCESS read-only
    STATUS     current
    DESCRIPTION
        "The Path property indicates the folder path minus
        the URL http://server/vroot header portion."
    ::= { exchangePublicFolderEntry 32 }

expfProhibitPostLimit OBJECT-TYPE
    SYNTAX     Gauge32
    UNITS "KB"
    MAX-ACCESS read-only
    STATUS     current
    DESCRIPTION
        "The ProhibitPostLimit property specifies the
        folder size limit, in kilobytes, when posting is
        prevented."
    ::= { exchangePublicFolderEntry 33 }

expfPublishInAddressBook OBJECT-TYPE
    SYNTAX     TruthValue
    MAX-ACCESS read-only
    STATUS     current
    DESCRIPTION
        "The PublishInAddressBook property specifies
        whether the folder will show up in the global
        address list if it is mail-enabled."
    ::= { exchangePublicFolderEntry 34 }

expfRecipientCountOnAssociateMsg OBJECT-TYPE
    SYNTAX     Gauge32
    MAX-ACCESS read-only
    STATUS     current
    DESCRIPTION
        "The RecipientCountOnAssociatedMessages property
        indicates the total number of recipients on the
        associated messages in the public folder."
    ::= { exchangePublicFolderEntry 35 }

expfRecipientCountOnNormalMsg OBJECT-TYPE
    SYNTAX     Gauge32
    MAX-ACCESS read-only
    STATUS     current
    DESCRIPTION
        "The RecipientCountOnNormalMessages property
        indicates the total number of recipients on the
        normal messages in the public folder."
    ::= { exchangePublicFolderEntry 36 }

expfReplicaAgeLimit OBJECT-TYPE
    SYNTAX     Gauge32
    UNITS "days"
    MAX-ACCESS read-only
    STATUS     current
    DESCRIPTION
        "The ReplicaAgeLimit property specifies the age
        limit for messages across all replicas."
    ::= { exchangePublicFolderEntry 37 }

expfReplicaList OBJECT-TYPE
    SYNTAX     DisplayString
    MAX-ACCESS read-only
    STATUS     current
    DESCRIPTION
        "The ReplicaList property indicates the list of
        distinguished names of the MDBs to which the folder
        is replicated."
    ::= { exchangePublicFolderEntry 38 }

expfReplicationMessagePriority OBJECT-TYPE
    SYNTAX     INTEGER {
        notUrgent(0),
        normal(1),
        urgent(2)
    }
    MAX-ACCESS read-only
    STATUS     current
    DESCRIPTION
        "The ReplicationMessagePriority property specifies
        the priority level for replicating folder
        messages."
    ::= { exchangePublicFolderEntry 39 }

expfReplicationSchedule OBJECT-TYPE
    SYNTAX     DisplayString
    MAX-ACCESS read-only
    STATUS     current
    DESCRIPTION
        "The array elements of the ReplicationSchedule
        property specify the replication schedule of the
        folder."
    ::= { exchangePublicFolderEntry 40 }

expfReplicationStyle OBJECT-TYPE
    SYNTAX     INTEGER {
        custom(0),
        never(1),
        always(2),
        everyHour(3),
        everyTwoHours(4),
        everyFourHours(5),
        usePublicStoreSchedule(6)
    }
    MAX-ACCESS read-only
    STATUS     current
    DESCRIPTION
        "The ReplicationStyle property specifies how often
        the folder contents are replicated."
    ::= { exchangePublicFolderEntry 41 }

expfRestrictionCount OBJECT-TYPE
    SYNTAX     Gauge32
    MAX-ACCESS read-only
    STATUS     current
    DESCRIPTION
        "The RestrictionCount property indicates the total
        number of restrictions on the public folder."
    ::= { exchangePublicFolderEntry 42 }

expfSecurityDescriptor OBJECT-TYPE
    SYNTAX     DisplayString
    MAX-ACCESS read-only
    STATUS     current
    DESCRIPTION
        "The SecurityDescriptor property specifies the
        administrative security descriptor for the folder."
    ::= { exchangePublicFolderEntry 43 }

expfStorageLimitStyle OBJECT-TYPE
    SYNTAX     INTEGER {
        usePublicStoreStyle(0),
        useSpecifiedQuota(1),
        noQuota(2)
    }
    MAX-ACCESS read-only
    STATUS     current
    DESCRIPTION
        "The StorageLimitStyle property specifies whether
        the folder should use public store storage limits,
        have no quota, or use quota values set on the
        folder."
    ::= { exchangePublicFolderEntry 44 }

expfTargetAddress OBJECT-TYPE
    SYNTAX     DisplayString
    MAX-ACCESS read-only
    STATUS     current
    DESCRIPTION
        "The TargetAddress property is a MAPI property that
        contains the e-mail address of the public folder."
    ::= { exchangePublicFolderEntry 45 }

expfTotalMessageSize OBJECT-TYPE
    SYNTAX     Gauge32
    UNITS "bytes"
    MAX-ACCESS read-only
    STATUS     current
    DESCRIPTION
        "The TotalMessageSize property indicates the total
        size, in bytes, of all of the normal messages in
        the public folder. The TotalMessageSize property is
        an 8-byte version of the NormalMessageSize
        property."
    ::= { exchangePublicFolderEntry 46 }

expfUrl OBJECT-TYPE
    SYNTAX     DisplayString
    MAX-ACCESS read-only
    STATUS     current
    DESCRIPTION
        "The Url property indicates the folder URL,
        constructed using the folder globally unique
        identifier (GUID)."
    ::= { exchangePublicFolderEntry 47 }

expfUsePublicStoreAgeLimits OBJECT-TYPE
    SYNTAX     TruthValue
    MAX-ACCESS read-only
    STATUS     current
    DESCRIPTION
        "The UsePublicStoreAgeLimits property specifies
        whether the folder should use the age limits of the
        MDB in which it is stored."
    ::= { exchangePublicFolderEntry 48 }

expfUsePublicStoreDelItemLifetm OBJECT-TYPE
    SYNTAX     TruthValue
    MAX-ACCESS read-only
    STATUS     current
    DESCRIPTION
        "The UsePublicStoreDeletedItemLifetime property
        specifies whether the folder should use the deleted
        item lifetime of the local public MDB."
    ::= { exchangePublicFolderEntry 49 }

expfWarningLimit OBJECT-TYPE
    SYNTAX     Gauge32
    UNITS "KB"
    MAX-ACCESS read-only
    STATUS     current
    DESCRIPTION
        "The WarningLimit property specifies the folder
        size limit, in kilobytes, when warning messages are
        sent."
    ::= { exchangePublicFolderEntry 50 }

exchangeQueueV2Table OBJECT-TYPE
    SYNTAX     SEQUENCE OF ExchangeQueueV2Entry
    MAX-ACCESS not-accessible
    STATUS     current
    DESCRIPTION
        "The Exchange_Queue WMI class provides properties
        and methods for working with Microsoft Exchange
        queues."
    ::= { wmiExchange 13 }

exchangeQueueV2Entry OBJECT-TYPE
    SYNTAX     ExchangeQueueV2Entry
    MAX-ACCESS not-accessible
    STATUS     current
    DESCRIPTION
        "None"
    INDEX      { exq2Index }
    ::= { exchangeQueueV2Table 1 }

ExchangeQueueV2Entry ::= SEQUENCE {
    exq2Index Integer32,
    exq2CanEnumAll TruthValue,
    exq2GlobalStop TruthValue,
    exq2LinkId DisplayString,
    exq2LinkName DisplayString,
    exq2MessageCount Gauge32,
    exq2MsgEnumFlagsSupported Gauge32,
    exq2ProtocolName DisplayString,
    exq2QueueId DisplayString,
    exq2QueueName DisplayString,
    exq2Size DisplayString,
    exq2Version Gauge32,
    exq2VirtualMachine DisplayString,
    exq2VirtualServerName DisplayString
}

exq2Index OBJECT-TYPE
    SYNTAX     Integer32 (1..2147483647)
    MAX-ACCESS read-only
    STATUS     current
    DESCRIPTION
        "The value of this object uniquely identifies the
        instance entry for this class."
    ::= { exchangeQueueV2Entry 1 }

exq2CanEnumAll OBJECT-TYPE
    SYNTAX     TruthValue
    MAX-ACCESS read-only
    STATUS     current
    DESCRIPTION
        "The CanEnumAll property indicates whether the
        queue can enumerate all of the messages that it has
        waiting for transmission."
    ::= { exchangeQueueV2Entry 2 }

exq2GlobalStop OBJECT-TYPE
    SYNTAX     TruthValue
    MAX-ACCESS read-only
    STATUS     current
    DESCRIPTION
        "The GlobalStop property indicates whether the
        virtual server for the queue is in disabled mode.
        If True, the virtual server is disabled."
    ::= { exchangeQueueV2Entry 3 }

exq2LinkId OBJECT-TYPE
    SYNTAX     DisplayString
    MAX-ACCESS read-only
    STATUS     current
    DESCRIPTION
        "The LinkId property indicates the identifier for
        the link that contains the queue."
    ::= { exchangeQueueV2Entry 4 }

exq2LinkName OBJECT-TYPE
    SYNTAX     DisplayString
    MAX-ACCESS read-only
    STATUS     current
    DESCRIPTION
        "The LinkName property indicates the name of the
        link that contains the queue."
    ::= { exchangeQueueV2Entry 5 }

exq2MessageCount OBJECT-TYPE
    SYNTAX     Gauge32
    MAX-ACCESS read-only
    STATUS     current
    DESCRIPTION
        "The MessageCount property indicates the number of
        messages in the queue."
    ::= { exchangeQueueV2Entry 6 }

exq2MsgEnumFlagsSupported OBJECT-TYPE
    SYNTAX     Gauge32
    MAX-ACCESS read-only
    STATUS     current
    DESCRIPTION
        "The MsgEnumFlagsSupported property contains a mask
        of all enumeration flags for the queue."
    ::= { exchangeQueueV2Entry 7 }

exq2ProtocolName OBJECT-TYPE
    SYNTAX     DisplayString
    MAX-ACCESS read-only
    STATUS     current
    DESCRIPTION
        "The ProtocolName property indicates the
        transmission protocol for the queue."
    ::= { exchangeQueueV2Entry 8 }

exq2QueueId OBJECT-TYPE
    SYNTAX     DisplayString
    MAX-ACCESS read-only
    STATUS     current
    DESCRIPTION
        "The QueueId property indicates the identifier of
        the queue."
    ::= { exchangeQueueV2Entry 9 }

exq2QueueName OBJECT-TYPE
    SYNTAX     DisplayString
    MAX-ACCESS read-only
    STATUS     current
    DESCRIPTION
        "The QueueName property indicates the name of the
        queue."
    ::= { exchangeQueueV2Entry 10 }

exq2Size OBJECT-TYPE
    SYNTAX     DisplayString
    MAX-ACCESS read-only
    STATUS     current
    DESCRIPTION
        "The Size property indicates the message size,
        including attachments, in bytes."
    ::= { exchangeQueueV2Entry 11 }

exq2Version OBJECT-TYPE
    SYNTAX     Gauge32
    MAX-ACCESS read-only
    STATUS     current
    DESCRIPTION
        "The Version property indicates the version of the
        service that created the message tracking log
        entry."
    ::= { exchangeQueueV2Entry 12 }

exq2VirtualMachine OBJECT-TYPE
    SYNTAX     DisplayString
    MAX-ACCESS read-only
    STATUS     current
    DESCRIPTION
        "The VirtualMachine property indicates the name of
        the virtual machine that contains the queue."
    ::= { exchangeQueueV2Entry 13 }

exq2VirtualServerName OBJECT-TYPE
    SYNTAX     DisplayString
    MAX-ACCESS read-only
    STATUS     current
    DESCRIPTION
        "The VirtualServerName property indicates the name
        of the virtual server the queue is on."
    ::= { exchangeQueueV2Entry 14 }

exchangeQueueCacheReloadEvtTable OBJECT-TYPE
    SYNTAX     SEQUENCE OF ExchangeQueueCacheReloadEventEntry
    MAX-ACCESS not-accessible
    STATUS     current
    DESCRIPTION
        "Instances of the Exchange_QueueCacheReloadEvent
        class provide information about when the queue's
        cache was reloaded."
    ::= { wmiExchange 14 }

exchangeQueueCacheReloadEvtEntry OBJECT-TYPE
    SYNTAX     ExchangeQueueCacheReloadEventEntry
    MAX-ACCESS not-accessible
    STATUS     current
    DESCRIPTION
        "None"
    INDEX      { exqcreIndex }
    ::= { exchangeQueueCacheReloadEvtTable 1 }

ExchangeQueueCacheReloadEventEntry ::= SEQUENCE {
    exqcreIndex Integer32,
    exqcreReloadTime DateAndTime
}

exqcreIndex OBJECT-TYPE
    SYNTAX     Integer32 (1..2147483647)
    MAX-ACCESS read-only
    STATUS     current
    DESCRIPTION
        "The value of this object uniquely identifies the
        instance entry for this class."
    ::= { exchangeQueueCacheReloadEvtEntry 1 }

exqcreReloadTime OBJECT-TYPE
    SYNTAX     DateAndTime
    MAX-ACCESS read-only
    STATUS     current
    DESCRIPTION
        "The ReloadTime property indicates the last time
        that the queue provider updated its data."
    ::= { exchangeQueueCacheReloadEvtEntry 2 }

exchangeQueuedMessageTable OBJECT-TYPE
    SYNTAX     SEQUENCE OF ExchangeQueuedMessageEntry
    MAX-ACCESS not-accessible
    STATUS     current
    DESCRIPTION
        "The Exchange_QueuedMessage WMI class is the base
        class for the Exchange_QueuedX400Message and
        Exchange_QueuedSMTPMessage classes. The
        Exchange_QueuedMessage class provides information
        about messages that reside in Microsoft Exchange
        queues."
    ::= { wmiExchange 15 }

exchangeQueuedMessageEntry OBJECT-TYPE
    SYNTAX     ExchangeQueuedMessageEntry
    MAX-ACCESS not-accessible
    STATUS     current
    DESCRIPTION
        "None"
    INDEX      { exqmIndex }
    ::= { exchangeQueuedMessageTable 1 }

ExchangeQueuedMessageEntry ::= SEQUENCE {
    exqmIndex Integer32,
    exqmActionDeleteNDR TruthValue,
    exqmActionDeleteNoNDR TruthValue,
    exqmActionFreeze TruthValue,
    exqmActionThaw TruthValue,
    exqmExpiry DateAndTime,
    exqmHighPriority TruthValue,
    exqmLinkId DisplayString,
    exqmLinkName DisplayString,
    exqmLowPriority TruthValue,
    exqmMessageId DisplayString,
    exqmNormalPriority TruthValue,
    exqmProtocolName DisplayString,
    exqmQueueId DisplayString,
    exqmQueueName DisplayString,
    exqmReceived DateAndTime,
    exqmRecipientCount Gauge32,
    exqmRecipients DisplayString,
    exqmSender DisplayString,
    exqmSize Gauge32,
    exqmStateFlags Gauge32,
    exqmStateFrozen TruthValue,
    exqmStateRetry TruthValue,
    exqmSubject DisplayString,
    exqmSubmission DateAndTime,
    exqmVersion Gauge32,
    exqmVirtualMachine DisplayString,
    exqmVirtualServerName DisplayString
}

exqmIndex OBJECT-TYPE
    SYNTAX     Integer32 (1..2147483647)
    MAX-ACCESS read-only
    STATUS     current
    DESCRIPTION
        "The value of this object uniquely identifies the
        instance entry for this class."
    ::= { exchangeQueuedMessageEntry 1 }

exqmActionDeleteNDR OBJECT-TYPE
    SYNTAX     TruthValue
    MAX-ACCESS read-only
    STATUS     current
    DESCRIPTION
        "The ActionDeleteNDR property indicates whether the
        message supports the DeleteWithNDR method."
    ::= { exchangeQueuedMessageEntry 2 }

exqmActionDeleteNoNDR OBJECT-TYPE
    SYNTAX     TruthValue
    MAX-ACCESS read-only
    STATUS     current
    DESCRIPTION
        "The ActionDeleteNoNDR property indicates whether
        the message supports the DeleteWithoutNDR method."
    ::= { exchangeQueuedMessageEntry 3 }

exqmActionFreeze OBJECT-TYPE
    SYNTAX     TruthValue
    MAX-ACCESS read-only
    STATUS     current
    DESCRIPTION
        "The ActionFreeze property indicates whether the
        message supports the Freeze method."
    ::= { exchangeQueuedMessageEntry 4 }

exqmActionThaw OBJECT-TYPE
    SYNTAX     TruthValue
    MAX-ACCESS read-only
    STATUS     current
    DESCRIPTION
        "The ActionThaw property indicates whether the
        message supports the Thaw method."
    ::= { exchangeQueuedMessageEntry 5 }

exqmExpiry OBJECT-TYPE
    SYNTAX     DateAndTime
    MAX-ACCESS read-only
    STATUS     current
    DESCRIPTION
        "The Expiry property indicates the expiration time
        stamp for the message."
    ::= { exchangeQueuedMessageEntry 6 }

exqmHighPriority OBJECT-TYPE
    SYNTAX     TruthValue
    MAX-ACCESS read-only
    STATUS     current
    DESCRIPTION
        "The HighPriority property indicates whether the
        message has high priority."
    ::= { exchangeQueuedMessageEntry 7 }

exqmLinkId OBJECT-TYPE
    SYNTAX     DisplayString
    MAX-ACCESS read-only
    STATUS     current
    DESCRIPTION
        "The LinkId property indicates the identifier for
        the link that contains the queued message."
    ::= { exchangeQueuedMessageEntry 8 }

exqmLinkName OBJECT-TYPE
    SYNTAX     DisplayString
    MAX-ACCESS read-only
    STATUS     current
    DESCRIPTION
        "The LinkName property indicates the name of the
        link that contains the queued message."
    ::= { exchangeQueuedMessageEntry 9 }

exqmLowPriority OBJECT-TYPE
    SYNTAX     TruthValue
    MAX-ACCESS read-only
    STATUS     current
    DESCRIPTION
        "The LowPriority property indicates whether the
        message has low priority."
    ::= { exchangeQueuedMessageEntry 10 }

exqmMessageId OBJECT-TYPE
    SYNTAX     DisplayString
    MAX-ACCESS read-only
    STATUS     current
    DESCRIPTION
        "The MessageId property indicates the identifier of
        the queued message."
    ::= { exchangeQueuedMessageEntry 11 }

exqmNormalPriority OBJECT-TYPE
    SYNTAX     TruthValue
    MAX-ACCESS read-only
    STATUS     current
    DESCRIPTION
        "The NormalPriority property indicates whether the
        message has normal priority."
    ::= { exchangeQueuedMessageEntry 12 }

exqmProtocolName OBJECT-TYPE
    SYNTAX     DisplayString
    MAX-ACCESS read-only
    STATUS     current
    DESCRIPTION
        "The ProtocolName property indicates the
        transmission protocol for the queued message."
    ::= { exchangeQueuedMessageEntry 13 }

exqmQueueId OBJECT-TYPE
    SYNTAX     DisplayString
    MAX-ACCESS read-only
    STATUS     current
    DESCRIPTION
        "The QueueId property indicates the identifier of
        the queue that the queued message is on."
    ::= { exchangeQueuedMessageEntry 14 }

exqmQueueName OBJECT-TYPE
    SYNTAX     DisplayString
    MAX-ACCESS read-only
    STATUS     current
    DESCRIPTION
        "The QueueName property indicates the name of the
        queue that contains the message."
    ::= { exchangeQueuedMessageEntry 15 }

exqmReceived OBJECT-TYPE
    SYNTAX     DateAndTime
    MAX-ACCESS read-only
    STATUS     current
    DESCRIPTION
        "The Received property indicates the received time
        stamp for the message."
    ::= { exchangeQueuedMessageEntry 16 }

exqmRecipientCount OBJECT-TYPE
    SYNTAX     Gauge32
    MAX-ACCESS read-only
    STATUS     current
    DESCRIPTION
        "The RecipientCount property indicates the number
        of recipients in the message."
    ::= { exchangeQueuedMessageEntry 17 }

exqmRecipients OBJECT-TYPE
    SYNTAX     DisplayString
    MAX-ACCESS read-only
    STATUS     current
    DESCRIPTION
        "The Recipients property indicates the recipients
        of the message."
    ::= { exchangeQueuedMessageEntry 18 }

exqmSender OBJECT-TYPE
    SYNTAX     DisplayString
    MAX-ACCESS read-only
    STATUS     current
    DESCRIPTION
        "The Sender property indicates the name of the
        sender."
    ::= { exchangeQueuedMessageEntry 19 }

exqmSize OBJECT-TYPE
    SYNTAX     Gauge32
    UNITS "KB"
    MAX-ACCESS read-only
    STATUS     current
    DESCRIPTION
        "The Size property indicates the size of the
        message."
    ::= { exchangeQueuedMessageEntry 20 }

exqmStateFlags OBJECT-TYPE
    SYNTAX     Gauge32
    MAX-ACCESS read-only
    STATUS     current
    DESCRIPTION
        "The StateFlags property contains a mask of all of
        the state flags for the message."
    ::= { exchangeQueuedMessageEntry 21 }

exqmStateFrozen OBJECT-TYPE
    SYNTAX     TruthValue
    MAX-ACCESS read-only
    STATUS     current
    DESCRIPTION
        "The StateFrozen property indicates whether the
        message is in a frozen state."
    ::= { exchangeQueuedMessageEntry 22 }

exqmStateRetry OBJECT-TYPE
    SYNTAX     TruthValue
    MAX-ACCESS read-only
    STATUS     current
    DESCRIPTION
        "The StateRetry property indicates that
        transmission is being retried for a message that
        was not delivered successfully."
    ::= { exchangeQueuedMessageEntry 23 }

exqmSubject OBJECT-TYPE
    SYNTAX     DisplayString
    MAX-ACCESS read-only
    STATUS     current
    DESCRIPTION
        "The Subject property indicates the subject of the
        message."
    ::= { exchangeQueuedMessageEntry 24 }

exqmSubmission OBJECT-TYPE
    SYNTAX     DateAndTime
    MAX-ACCESS read-only
    STATUS     current
    DESCRIPTION
        "The Submission property indicates the submission
        time stamp for the message."
    ::= { exchangeQueuedMessageEntry 25 }

exqmVersion OBJECT-TYPE
    SYNTAX     Gauge32
    MAX-ACCESS read-only
    STATUS     current
    DESCRIPTION
        "The Version property indicates the version of the
        Queue Application Programming Interface (QAPI) used
        to generate the WMI object."
    ::= { exchangeQueuedMessageEntry 26 }

exqmVirtualMachine OBJECT-TYPE
    SYNTAX     DisplayString
    MAX-ACCESS read-only
    STATUS     current
    DESCRIPTION
        "The VirtualMachine property indicates the name of
        the virtual machine that contains the queued
        message."
    ::= { exchangeQueuedMessageEntry 27 }

exqmVirtualServerName OBJECT-TYPE
    SYNTAX     DisplayString
    MAX-ACCESS read-only
    STATUS     current
    DESCRIPTION
        "The VirtualServerName property indicates the name
        of the virtual server that contains the queued
        message."
    ::= { exchangeQueuedMessageEntry 28 }

exchangeQueueVirtualServerTable OBJECT-TYPE
    SYNTAX     SEQUENCE OF ExchangeQueueVirtualServerEntry
    MAX-ACCESS not-accessible
    STATUS     current
    DESCRIPTION
        "The Exchange_QueueVirtualServer Class is the Base
        class for the Exchange_QueueSMTPVirtualServer and
        Exchange_QueueX400VirtualServer classes."
    ::= { wmiExchange 16 }

exchangeQueueVirtualServerEntry OBJECT-TYPE
    SYNTAX     ExchangeQueueVirtualServerEntry
    MAX-ACCESS not-accessible
    STATUS     current
    DESCRIPTION
        "None"
    INDEX      { exvsIndex }
    ::= { exchangeQueueVirtualServerTable 1 }

ExchangeQueueVirtualServerEntry ::= SEQUENCE {
    exvsIndex Integer32,
    exvsGlobalActionsSupported TruthValue,
    exvsGlobalStop TruthValue,
    exvsProtocolName DisplayString,
    exvsVirtualMachine DisplayString,
    exvsVirtualServerName DisplayString
}

exvsIndex OBJECT-TYPE
    SYNTAX     Integer32 (1..2147483647)
    MAX-ACCESS read-only
    STATUS     current
    DESCRIPTION
        "The value of this object uniquely identifies the
        instance entry for this class."
    ::= { exchangeQueueVirtualServerEntry 1 }

exvsGlobalActionsSupported OBJECT-TYPE
    SYNTAX     TruthValue
    MAX-ACCESS read-only
    STATUS     current
    DESCRIPTION
        "The GlobalActionsSupported property indicates
        whether all remote connections for the virtual
        server can be controlled."
    ::= { exchangeQueueVirtualServerEntry 2 }

exvsGlobalStop OBJECT-TYPE
    SYNTAX     TruthValue
    MAX-ACCESS read-only
    STATUS     current
    DESCRIPTION
        "The GlobalStop property indicates whether the
        virtual server for the link is in disabled mode. If
        True, the virtual server is disabled."
    ::= { exchangeQueueVirtualServerEntry 3 }

exvsProtocolName OBJECT-TYPE
    SYNTAX     DisplayString
    MAX-ACCESS read-only
    STATUS     current
    DESCRIPTION
        "The ProtocolName property indicates the name of
        the protocol for the virtual server."
    ::= { exchangeQueueVirtualServerEntry 4 }

exvsVirtualMachine OBJECT-TYPE
    SYNTAX     DisplayString
    MAX-ACCESS read-only
    STATUS     current
    DESCRIPTION
        "The VirtualMachine property indicates the name of
        the virtual machine that contains the virtual
        server."
    ::= { exchangeQueueVirtualServerEntry 5 }

exvsVirtualServerName OBJECT-TYPE
    SYNTAX     DisplayString
    MAX-ACCESS read-only
    STATUS     current
    DESCRIPTION
        "The VirtualServerName property indicates the name
        of the virtual server."
    ::= { exchangeQueueVirtualServerEntry 6 }

exchangeServerTable OBJECT-TYPE
    SYNTAX     SEQUENCE OF ExchangeServerEntry
    MAX-ACCESS not-accessible
    STATUS     current
    DESCRIPTION
        "Instances of the Exchange_Server WMI class provide
        properties and methods for working with Exchange
        servers."
    ::= { wmiExchange 17 }

exchangeServerEntry OBJECT-TYPE
    SYNTAX     ExchangeServerEntry
    MAX-ACCESS not-accessible
    STATUS     current
    DESCRIPTION
        "None"
    INDEX      { exsIndex }
    ::= { exchangeServerTable 1 }

ExchangeServerEntry ::= SEQUENCE {
    exsIndex Integer32,
    exsAdministrativeGroup DisplayString,
    exsAdministrativeNote DisplayString,
    exsCreationTime DateAndTime,
    exsDN DisplayString,
    exsExchangeVersion DisplayString,
    exsFQDN DisplayString,
    exsGUID DisplayString,
    exsIsFrontEndServer TruthValue,
    exsLastModificationTime DateAndTime,
    exsMessageTrackingEnabled TruthValue,
    exsMessageTrackingLogFileLifetm Gauge32,
    exsMessageTrackingLogFilePath DisplayString,
    exsMonitoringEnabled TruthValue,
    exsMTADataPath DisplayString,
    exsName DisplayString,
    exsRoutingGroup DisplayString,
    exsSubjectLoggingEnabled TruthValue,
    exsType INTEGER
}

exsIndex OBJECT-TYPE
    SYNTAX     Integer32 (1..2147483647)
    MAX-ACCESS read-only
    STATUS     current
    DESCRIPTION
        "The value of this object uniquely identifies the
        instance entry for this class."
    ::= { exchangeServerEntry 1 }

exsAdministrativeGroup OBJECT-TYPE
    SYNTAX     DisplayString
    MAX-ACCESS read-only
    STATUS     current
    DESCRIPTION
        "The AdministrativeGroup property indicates the
        name of the Exchange 2000 administrator group to
        which the server belongs."
    ::= { exchangeServerEntry 2 }

exsAdministrativeNote OBJECT-TYPE
    SYNTAX     DisplayString
    MAX-ACCESS read-only
    STATUS     current
    DESCRIPTION
        "The AdministrativeNote property specifies the
        administrative note for the server."
    ::= { exchangeServerEntry 3 }

exsCreationTime OBJECT-TYPE
    SYNTAX     DateAndTime
    MAX-ACCESS read-only
    STATUS     current
    DESCRIPTION
        "The CreationTime property indicates when the
        Active Directory object was created."
    ::= { exchangeServerEntry 4 }

exsDN OBJECT-TYPE
    SYNTAX     DisplayString
    MAX-ACCESS read-only
    STATUS     current
    DESCRIPTION
        "The DN property indicates the distinguished name
        attribute on the server object in Microsoft Active
        Directory."
    ::= { exchangeServerEntry 5 }

exsExchangeVersion OBJECT-TYPE
    SYNTAX     DisplayString
    MAX-ACCESS read-only
    STATUS     current
    DESCRIPTION
        "The ExchangeVersion property indicates the product
        version information, including build and service
        pack number."
    ::= { exchangeServerEntry 6 }

exsFQDN OBJECT-TYPE
    SYNTAX     DisplayString
    MAX-ACCESS read-only
    STATUS     current
    DESCRIPTION
        "The FQDN property indicates the fully qualified
        domain name of the Exchange server."
    ::= { exchangeServerEntry 7 }

exsGUID OBJECT-TYPE
    SYNTAX     DisplayString
    MAX-ACCESS read-only
    STATUS     current
    DESCRIPTION
        "The GUID property indicates the globally unique
        identifier (GUID) attribute of the server object in
        Microsoft Active Directory."
    ::= { exchangeServerEntry 8 }

exsIsFrontEndServer OBJECT-TYPE
    SYNTAX     TruthValue
    MAX-ACCESS read-only
    STATUS     current
    DESCRIPTION
        "The IsFrontEndServer property indicates whether
        the server is a front-end server."
    ::= { exchangeServerEntry 9 }

exsLastModificationTime OBJECT-TYPE
    SYNTAX     DateAndTime
    MAX-ACCESS read-only
    STATUS     current
    DESCRIPTION
        "The LastModificationTime property indicates when
        the Active Directory object was last modified."
    ::= { exchangeServerEntry 10 }

exsMessageTrackingEnabled OBJECT-TYPE
    SYNTAX     TruthValue
    MAX-ACCESS read-only
    STATUS     current
    DESCRIPTION
        "The MessageTrackingEnabled property indicates
        whether message tracking is enabled on the server."
    ::= { exchangeServerEntry 11 }

exsMessageTrackingLogFileLifetm OBJECT-TYPE
    SYNTAX     Gauge32
    UNITS "days"
    MAX-ACCESS read-only
    STATUS     current
    DESCRIPTION
        "The MessageTrackingLogFileLifetime property
        specifies how long message tracking logs are to be
        kept."
    ::= { exchangeServerEntry 12 }

exsMessageTrackingLogFilePath OBJECT-TYPE
    SYNTAX     DisplayString
    MAX-ACCESS read-only
    STATUS     current
    DESCRIPTION
        "The MessageTrackingLogFilePath property indicates
        the location where message tracking logs are
        stored"
    ::= { exchangeServerEntry 13 }

exsMonitoringEnabled OBJECT-TYPE
    SYNTAX     TruthValue
    MAX-ACCESS read-only
    STATUS     current
    DESCRIPTION
        "The MonitoringEnabled property specifies whether
        monitoring is enabled on the server."
    ::= { exchangeServerEntry 14 }

exsMTADataPath OBJECT-TYPE
    SYNTAX     DisplayString
    MAX-ACCESS read-only
    STATUS     current
    DESCRIPTION
        "The MTADataPath property indicates the location of
        the MTA queue files."
    ::= { exchangeServerEntry 15 }

exsName OBJECT-TYPE
    SYNTAX     DisplayString
    MAX-ACCESS read-only
    STATUS     current
    DESCRIPTION
        "The Name property indicates the NetBIOS name of
        the Exchange server."
    ::= { exchangeServerEntry 16 }

exsRoutingGroup OBJECT-TYPE
    SYNTAX     DisplayString
    MAX-ACCESS read-only
    STATUS     current
    DESCRIPTION
        "The RoutingGroup property indicates the name of
        the Exchange 2000 routing group to which the server
        belongs."
    ::= { exchangeServerEntry 17 }

exsSubjectLoggingEnabled OBJECT-TYPE
    SYNTAX     TruthValue
    MAX-ACCESS read-only
    STATUS     current
    DESCRIPTION
        "The SubjectLoggingEnabled property controls
        whether message subjects are included in message
        tracking logs. It also controls whether subjects
        are displayed in the queue viewer."
    ::= { exchangeServerEntry 18 }

exsType OBJECT-TYPE
    SYNTAX     INTEGER {
        standard(0),
        enterprise(1),
        conferencing(2)
    }
    MAX-ACCESS read-only
    STATUS     current
    DESCRIPTION
        "The Type property indicates the server type."
    ::= { exchangeServerEntry 19 }

exchangeQueuedSMTPMessageTable OBJECT-TYPE
    SYNTAX     SEQUENCE OF ExchangeQueuedSMTPMessage
    MAX-ACCESS not-accessible
    STATUS     current
    DESCRIPTION
        "The Exchange_QueuedSMTPMessage class provides
        methods to work with Microsoft Exchange messages
        currently in an SMTP queue."
    ::= { wmiExchange 18 }

exchangeQueuedSMTPMessageEntry OBJECT-TYPE
    SYNTAX     ExchangeQueuedSMTPMessage
    MAX-ACCESS not-accessible
    STATUS     current
    DESCRIPTION
        "None"
    INDEX      { exqsmIndex }
    ::= { exchangeQueuedSMTPMessageTable 1 }

ExchangeQueuedSMTPMessage ::= SEQUENCE {
    exqsmIndex Integer32,
    exqsmActionDeleteNDR TruthValue,
    exqsmActionDeleteNoNDR TruthValue,
    exqsmActionFreeze TruthValue,
    exqsmActionThaw TruthValue,
    exqsmExpiry DateAndTime,
    exqsmHighPriority TruthValue,
    exqsmLinkId DisplayString,
    exqsmLinkName DisplayString,
    exqsmLowPriority TruthValue,
    exqsmMessageId DisplayString,
    exqsmNormalPriority TruthValue,
    exqsmProtocolName DisplayString,
    exqsmQueueId DisplayString,
    exqsmQueueName DisplayString,
    exqsmReceived DateAndTime,
    exqsmRecipientCount Gauge32,
    exqsmRecipients DisplayString,
    exqsmSender DisplayString,
    exqsmSize Gauge32,
    exqsmStateFlags Gauge32,
    exqsmStateFrozen TruthValue,
    exqsmStateRetry TruthValue,
    exqsmSubject DisplayString,
    exqsmSubmission DateAndTime,
    exqsmVersion Gauge32,
    exqsmVirtualMachine DisplayString,
    exqsmVirtualServerName DisplayString
}

exqsmIndex OBJECT-TYPE
    SYNTAX     Integer32 (1..2147483647)
    MAX-ACCESS read-only
    STATUS     current
    DESCRIPTION
        "The value of this object uniquely identifies the
        instance entry for this class."
    ::= { exchangeQueuedSMTPMessageEntry 1 }

exqsmActionDeleteNDR OBJECT-TYPE
    SYNTAX     TruthValue
    MAX-ACCESS read-only
    STATUS     current
    DESCRIPTION
        "The ActionDeleteNDR property indicates whether the
        message supports the DeleteWithNDR method."
    ::= { exchangeQueuedSMTPMessageEntry 2 }

exqsmActionDeleteNoNDR OBJECT-TYPE
    SYNTAX     TruthValue
    MAX-ACCESS read-only
    STATUS     current
    DESCRIPTION
        "The ActionDeleteNoNDR property indicates whether
        the message supports the DeleteWithoutNDR method."
    ::= { exchangeQueuedSMTPMessageEntry 3 }

exqsmActionFreeze OBJECT-TYPE
    SYNTAX     TruthValue
    MAX-ACCESS read-only
    STATUS     current
    DESCRIPTION
        "The ActionFreeze property indicates whether the
        message supports the Freeze method."
    ::= { exchangeQueuedSMTPMessageEntry 4 }

exqsmActionThaw OBJECT-TYPE
    SYNTAX     TruthValue
    MAX-ACCESS read-only
    STATUS     current
    DESCRIPTION
        "The ActionThaw property indicates whether the
        message supports the Thaw method."
    ::= { exchangeQueuedSMTPMessageEntry 5 }

exqsmExpiry OBJECT-TYPE
    SYNTAX     DateAndTime
    MAX-ACCESS read-only
    STATUS     current
    DESCRIPTION
        "The Expiry property indicates the expiration time
        stamp for the message."
    ::= { exchangeQueuedSMTPMessageEntry 6 }

exqsmHighPriority OBJECT-TYPE
    SYNTAX     TruthValue
    MAX-ACCESS read-only
    STATUS     current
    DESCRIPTION
        "The HighPriority property indicates whether the
        message has high priority."
    ::= { exchangeQueuedSMTPMessageEntry 7 }

exqsmLinkId OBJECT-TYPE
    SYNTAX     DisplayString
    MAX-ACCESS read-only
    STATUS     current
    DESCRIPTION
        "The LinkId property indicates the identifier for
        the link that contains the queued message."
    ::= { exchangeQueuedSMTPMessageEntry 8 }

exqsmLinkName OBJECT-TYPE
    SYNTAX     DisplayString
    MAX-ACCESS read-only
    STATUS     current
    DESCRIPTION
        "The LinkName property indicates the name of the
        link that contains the queued message."
    ::= { exchangeQueuedSMTPMessageEntry 9 }

exqsmLowPriority OBJECT-TYPE
    SYNTAX     TruthValue
    MAX-ACCESS read-only
    STATUS     current
    DESCRIPTION
        "The LowPriority property indicates whether the
        message has low priority."
    ::= { exchangeQueuedSMTPMessageEntry 10 }

exqsmMessageId OBJECT-TYPE
    SYNTAX     DisplayString
    MAX-ACCESS read-only
    STATUS     current
    DESCRIPTION
        "The MessageId property indicates the identifier of
        the queued message."
    ::= { exchangeQueuedSMTPMessageEntry 11 }

exqsmNormalPriority OBJECT-TYPE
    SYNTAX     TruthValue
    MAX-ACCESS read-only
    STATUS     current
    DESCRIPTION
        "The NormalPriority property indicates whether the
        message has normal priority."
    ::= { exchangeQueuedSMTPMessageEntry 12 }

exqsmProtocolName OBJECT-TYPE
    SYNTAX     DisplayString
    MAX-ACCESS read-only
    STATUS     current
    DESCRIPTION
        "The ProtocolName property indicates the
        transmission protocol for the queued message."
    ::= { exchangeQueuedSMTPMessageEntry 13 }

exqsmQueueId OBJECT-TYPE
    SYNTAX     DisplayString
    MAX-ACCESS read-only
    STATUS     current
    DESCRIPTION
        "The QueueId property indicates the identifier of
        the queue that the queued message is on."
    ::= { exchangeQueuedSMTPMessageEntry 14 }

exqsmQueueName OBJECT-TYPE
    SYNTAX     DisplayString
    MAX-ACCESS read-only
    STATUS     current
    DESCRIPTION
        "The QueueName property indicates the name of the
        queue that contains the message."
    ::= { exchangeQueuedSMTPMessageEntry 15 }

exqsmReceived OBJECT-TYPE
    SYNTAX     DateAndTime
    MAX-ACCESS read-only
    STATUS     current
    DESCRIPTION
        "The Received property indicates the received time
        stamp for the message."
    ::= { exchangeQueuedSMTPMessageEntry 16 }

exqsmRecipientCount OBJECT-TYPE
    SYNTAX     Gauge32
    MAX-ACCESS read-only
    STATUS     current
    DESCRIPTION
        "The RecipientCount property indicates the number
        of recipients in the message."
    ::= { exchangeQueuedSMTPMessageEntry 17 }

exqsmRecipients OBJECT-TYPE
    SYNTAX     DisplayString
    MAX-ACCESS read-only
    STATUS     current
    DESCRIPTION
        "The Recipients property indicates the recipients
        of the message."
    ::= { exchangeQueuedSMTPMessageEntry 18 }

exqsmSender OBJECT-TYPE
    SYNTAX     DisplayString
    MAX-ACCESS read-only
    STATUS     current
    DESCRIPTION
        "The Sender property indicates the name of the
        sender."
    ::= { exchangeQueuedSMTPMessageEntry 19 }

exqsmSize OBJECT-TYPE
    SYNTAX     Gauge32
    UNITS "KB"
    MAX-ACCESS read-only
    STATUS     current
    DESCRIPTION
        "The Size property indicates the size of the
        message."
    ::= { exchangeQueuedSMTPMessageEntry 20 }

exqsmStateFlags OBJECT-TYPE
    SYNTAX     Gauge32
    MAX-ACCESS read-only
    STATUS     current
    DESCRIPTION
        "The StateFlags property contains a mask of all of
        the state flags for the message."
    ::= { exchangeQueuedSMTPMessageEntry 21 }

exqsmStateFrozen OBJECT-TYPE
    SYNTAX     TruthValue
    MAX-ACCESS read-only
    STATUS     current
    DESCRIPTION
        "The StateFrozen property indicates whether the
        message is in a frozen state."
    ::= { exchangeQueuedSMTPMessageEntry 22 }

exqsmStateRetry OBJECT-TYPE
    SYNTAX     TruthValue
    MAX-ACCESS read-only
    STATUS     current
    DESCRIPTION
        "The StateRetry property indicates that
        transmission is being retried for a message that
        was not successfully delivered."
    ::= { exchangeQueuedSMTPMessageEntry 23 }

exqsmSubject OBJECT-TYPE
    SYNTAX     DisplayString
    MAX-ACCESS read-only
    STATUS     current
    DESCRIPTION
        "The Subject property indicates the subject of the
        message."
    ::= { exchangeQueuedSMTPMessageEntry 24 }

exqsmSubmission OBJECT-TYPE
    SYNTAX     DateAndTime
    MAX-ACCESS read-only
    STATUS     current
    DESCRIPTION
        "The Submission property indicates the submission
        time stamp for the message."
    ::= { exchangeQueuedSMTPMessageEntry 25 }

exqsmVersion OBJECT-TYPE
    SYNTAX     Gauge32
    MAX-ACCESS read-only
    STATUS     current
    DESCRIPTION
        "The Version property indicates the version of the
        QAPI used to generate the WMI object."
    ::= { exchangeQueuedSMTPMessageEntry 26 }

exqsmVirtualMachine OBJECT-TYPE
    SYNTAX     DisplayString
    MAX-ACCESS read-only
    STATUS     current
    DESCRIPTION
        "The VirtualMachine property indicates the name of
        the virtual machine that contains the queued
        message."
    ::= { exchangeQueuedSMTPMessageEntry 27 }

exqsmVirtualServerName OBJECT-TYPE
    SYNTAX     DisplayString
    MAX-ACCESS read-only
    STATUS     current
    DESCRIPTION
        "The VirtualServerName property indicates the name
        of the virtual server that contains the queued
        message."
    ::= { exchangeQueuedSMTPMessageEntry 28 }

exchangeQueuedX400MessageTable OBJECT-TYPE
    SYNTAX     SEQUENCE OF ExchangeQueuedX400Message
    MAX-ACCESS not-accessible
    STATUS     current
    DESCRIPTION
        "The Exchange_QueuedX400Message class provides
        methods to work with Microsoft Exchange messages
        currently in an X400 queue."
    ::= { wmiExchange 19 }

exchangeQueuedX400MessageEntry OBJECT-TYPE
    SYNTAX     ExchangeQueuedX400Message
    MAX-ACCESS not-accessible
    STATUS     current
    DESCRIPTION
        "None"
    INDEX      { exqxmIndex }
    ::= { exchangeQueuedX400MessageTable 1 }

ExchangeQueuedX400Message ::= SEQUENCE {
    exqxmIndex Integer32,
    exqxmActionDeleteNDR TruthValue,
    exqxmActionDeleteNoNDR TruthValue,
    exqxmActionFreeze TruthValue,
    exqxmActionThaw TruthValue,
    exqxmExpiry DateAndTime,
    exqxmHighPriority TruthValue,
    exqxmLinkId DisplayString,
    exqxmLinkName DisplayString,
    exqxmLowPriority TruthValue,
    exqxmMessageId DisplayString,
    exqxmNormalPriority TruthValue,
    exqxmProtocolName DisplayString,
    exqxmQueueId DisplayString,
    exqxmQueueName DisplayString,
    exqxmReceived DateAndTime,
    exqxmRecipientCount Gauge32,
    exqxmRecipients DisplayString,
    exqxmSender DisplayString,
    exqxmSize Gauge32,
    exqxmStateFlags Gauge32,
    exqxmStateFrozen TruthValue,
    exqxmStateRetry TruthValue,
    exqxmSubject DisplayString,
    exqxmSubmission DateAndTime,
    exqxmVersion Gauge32,
    exqxmVirtualMachine DisplayString,
    exqxmVirtualServerName DisplayString
}

exqxmIndex OBJECT-TYPE
    SYNTAX     Integer32 (1..2147483647)
    MAX-ACCESS read-only
    STATUS     current
    DESCRIPTION
        "The value of this object uniquely identifies the
        instance entry for this class."
    ::= { exchangeQueuedX400MessageEntry 1 }

exqxmActionDeleteNDR OBJECT-TYPE
    SYNTAX     TruthValue
    MAX-ACCESS read-only
    STATUS     current
    DESCRIPTION
        "The ActionDeleteNDR property indicates whether the
        message supports the DeleteWithNDR method."
    ::= { exchangeQueuedX400MessageEntry 2 }

exqxmActionDeleteNoNDR OBJECT-TYPE
    SYNTAX     TruthValue
    MAX-ACCESS read-only
    STATUS     current
    DESCRIPTION
        "The ActionDeleteNoNDR property indicates whether
        the message supports the DeleteWithoutNDR method."
    ::= { exchangeQueuedX400MessageEntry 3 }

exqxmActionFreeze OBJECT-TYPE
    SYNTAX     TruthValue
    MAX-ACCESS read-only
    STATUS     current
    DESCRIPTION
        "The ActionFreeze property indicates whether the
        message supports the Freeze method."
    ::= { exchangeQueuedX400MessageEntry 4 }

exqxmActionThaw OBJECT-TYPE
    SYNTAX     TruthValue
    MAX-ACCESS read-only
    STATUS     current
    DESCRIPTION
        "The ActionThaw property indicates whether the
        message supports the Thaw method."
    ::= { exchangeQueuedX400MessageEntry 5 }

exqxmExpiry OBJECT-TYPE
    SYNTAX     DateAndTime
    MAX-ACCESS read-only
    STATUS     current
    DESCRIPTION
        "The Expiry property indicates the expiration time
        stamp for the message."
    ::= { exchangeQueuedX400MessageEntry 6 }

exqxmHighPriority OBJECT-TYPE
    SYNTAX     TruthValue
    MAX-ACCESS read-only
    STATUS     current
    DESCRIPTION
        "The HighPriority property indicates whether the
        message has high priority."
    ::= { exchangeQueuedX400MessageEntry 7 }

exqxmLinkId OBJECT-TYPE
    SYNTAX     DisplayString
    MAX-ACCESS read-only
    STATUS     current
    DESCRIPTION
        "The LinkId property indicates the identifier for
        the link that contains the queued message."
    ::= { exchangeQueuedX400MessageEntry 8 }

exqxmLinkName OBJECT-TYPE
    SYNTAX     DisplayString
    MAX-ACCESS read-only
    STATUS     current
    DESCRIPTION
        "The LinkName property indicates the name of the
        link that contains the queued message."
    ::= { exchangeQueuedX400MessageEntry 9 }

exqxmLowPriority OBJECT-TYPE
    SYNTAX     TruthValue
    MAX-ACCESS read-only
    STATUS     current
    DESCRIPTION
        "The LowPriority property indicates whether the
        message has low priority."
    ::= { exchangeQueuedX400MessageEntry 10 }

exqxmMessageId OBJECT-TYPE
    SYNTAX     DisplayString
    MAX-ACCESS read-only
    STATUS     current
    DESCRIPTION
        "The MessageId property indicates the identifier of
        the queued message."
    ::= { exchangeQueuedX400MessageEntry 11 }

exqxmNormalPriority OBJECT-TYPE
    SYNTAX     TruthValue
    MAX-ACCESS read-only
    STATUS     current
    DESCRIPTION
        "The NormalPriority property indicates whether the
        message has normal priority."
    ::= { exchangeQueuedX400MessageEntry 12 }

exqxmProtocolName OBJECT-TYPE
    SYNTAX     DisplayString
    MAX-ACCESS read-only
    STATUS     current
    DESCRIPTION
        "The ProtocolName property indicates the
        transmission protocol for the queued message."
    ::= { exchangeQueuedX400MessageEntry 13 }

exqxmQueueId OBJECT-TYPE
    SYNTAX     DisplayString
    MAX-ACCESS read-only
    STATUS     current
    DESCRIPTION
        "The QueueId property indicates the identifier of
        the queue that the queued message is on."
    ::= { exchangeQueuedX400MessageEntry 14 }

exqxmQueueName OBJECT-TYPE
    SYNTAX     DisplayString
    MAX-ACCESS read-only
    STATUS     current
    DESCRIPTION
        "The QueueName property indicates the name of the
        queue that contains the message."
    ::= { exchangeQueuedX400MessageEntry 15 }

exqxmReceived OBJECT-TYPE
    SYNTAX     DateAndTime
    MAX-ACCESS read-only
    STATUS     current
    DESCRIPTION
        "The Received property indicates the received time
        stamp for the message."
    ::= { exchangeQueuedX400MessageEntry 16 }

exqxmRecipientCount OBJECT-TYPE
    SYNTAX     Gauge32
    MAX-ACCESS read-only
    STATUS     current
    DESCRIPTION
        "The RecipientCount property indicates the number
        of recipients in the message."
    ::= { exchangeQueuedX400MessageEntry 17 }

exqxmRecipients OBJECT-TYPE
    SYNTAX     DisplayString
    MAX-ACCESS read-only
    STATUS     current
    DESCRIPTION
        "The Recipients property indicates the recipients
        of the message."
    ::= { exchangeQueuedX400MessageEntry 18 }

exqxmSender OBJECT-TYPE
    SYNTAX     DisplayString
    MAX-ACCESS read-only
    STATUS     current
    DESCRIPTION
        "The Sender property indicates the name of the
        sender."
    ::= { exchangeQueuedX400MessageEntry 19 }

exqxmSize OBJECT-TYPE
    SYNTAX     Gauge32
    UNITS "KB"
    MAX-ACCESS read-only
    STATUS     current
    DESCRIPTION
        "The Size property indicates the size of the
        message."
    ::= { exchangeQueuedX400MessageEntry 20 }

exqxmStateFlags OBJECT-TYPE
    SYNTAX     Gauge32
    MAX-ACCESS read-only
    STATUS     current
    DESCRIPTION
        "The StateFlags property contains a mask of all of
        the state flags for the message."
    ::= { exchangeQueuedX400MessageEntry 21 }

exqxmStateFrozen OBJECT-TYPE
    SYNTAX     TruthValue
    MAX-ACCESS read-only
    STATUS     current
    DESCRIPTION
        "The StateFrozen property indicates whether the
        message is in a frozen state."
    ::= { exchangeQueuedX400MessageEntry 22 }

exqxmStateRetry OBJECT-TYPE
    SYNTAX     TruthValue
    MAX-ACCESS read-only
    STATUS     current
    DESCRIPTION
        "The StateRetry property indicates that
        transmission is being retried for a message that
        was not successfully delivered."
    ::= { exchangeQueuedX400MessageEntry 23 }

exqxmSubject OBJECT-TYPE
    SYNTAX     DisplayString
    MAX-ACCESS read-only
    STATUS     current
    DESCRIPTION
        "The Subject property indicates the subject of the
        message."
    ::= { exchangeQueuedX400MessageEntry 24 }

exqxmSubmission OBJECT-TYPE
    SYNTAX     DateAndTime
    MAX-ACCESS read-only
    STATUS     current
    DESCRIPTION
        "The Submission property indicates the submission
        time stamp for the message."
    ::= { exchangeQueuedX400MessageEntry 25 }

exqxmVersion OBJECT-TYPE
    SYNTAX     Gauge32
    MAX-ACCESS read-only
    STATUS     current
    DESCRIPTION
        "The Version property indicates the version of the
        QAPI used to generate the WMI object."
    ::= { exchangeQueuedX400MessageEntry 26 }

exqxmVirtualMachine OBJECT-TYPE
    SYNTAX     DisplayString
    MAX-ACCESS read-only
    STATUS     current
    DESCRIPTION
        "The VirtualMachine property indicates the name of
        the virtual machine that contains the queued
        message."
    ::= { exchangeQueuedX400MessageEntry 27 }

exqxmVirtualServerName OBJECT-TYPE
    SYNTAX     DisplayString
    MAX-ACCESS read-only
    STATUS     current
    DESCRIPTION
        "The VirtualServerName property indicates the name
        of the virtual server that contains the queued
        message."
    ::= { exchangeQueuedX400MessageEntry 28 }

exchangeQueueSMTPVirtualSrvTable OBJECT-TYPE
    SYNTAX     SEQUENCE OF ExchangeQueueSMTPVirtualServer
    MAX-ACCESS not-accessible
    STATUS     current
    DESCRIPTION
        "The Exchange_QueueSMTPVirtualServer class returns
        properties for SMTP queue virtual servers. This
        class provides two methods in addition to the
        properties it inherits from the
        Exchange_QueueVirtualServer class."
    ::= { wmiExchange 20 }

exchangeQueueSMTPVirtualSrvEntry OBJECT-TYPE
    SYNTAX     ExchangeQueueSMTPVirtualServer
    MAX-ACCESS not-accessible
    STATUS     current
    DESCRIPTION
        "None"
    INDEX      { exqsvsIndex }
    ::= { exchangeQueueSMTPVirtualSrvTable 1 }

ExchangeQueueSMTPVirtualServer ::= SEQUENCE {
    exqsvsIndex Integer32,
    exqsvsGlobalActionsSupported TruthValue,
    exqsvsGlobalStop TruthValue,
    exqsvsProtocolName DisplayString,
    exqsvsVirtualMachine DisplayString,
    exqsvsVirtualServerName DisplayString
}

exqsvsIndex OBJECT-TYPE
    SYNTAX     Integer32 (1..2147483647)
    MAX-ACCESS read-only
    STATUS     current
    DESCRIPTION
        "The value of this object uniquely identifies the
        instance entry for this class."
    ::= { exchangeQueueSMTPVirtualSrvEntry 1 }

exqsvsGlobalActionsSupported OBJECT-TYPE
    SYNTAX     TruthValue
    MAX-ACCESS read-only
    STATUS     current
    DESCRIPTION
        "The GlobalActionsSupported property indicates
        whether all remote connections for the virtual
        server can be controlled."
    ::= { exchangeQueueSMTPVirtualSrvEntry 2 }

exqsvsGlobalStop OBJECT-TYPE
    SYNTAX     TruthValue
    MAX-ACCESS read-only
    STATUS     current
    DESCRIPTION
        "The GlobalStop property indicates whether the
        virtual server for the link is in disabled mode. If
        True, the virtual server is disabled."
    ::= { exchangeQueueSMTPVirtualSrvEntry 3 }

exqsvsProtocolName OBJECT-TYPE
    SYNTAX     DisplayString
    MAX-ACCESS read-only
    STATUS     current
    DESCRIPTION
        "The ProtocolName property indicates the name of
        the protocol for the virtual server."
    ::= { exchangeQueueSMTPVirtualSrvEntry 4 }

exqsvsVirtualMachine OBJECT-TYPE
    SYNTAX     DisplayString
    MAX-ACCESS read-only
    STATUS     current
    DESCRIPTION
        "The VirtualMachine property indicates the name of
        the virtual machine that contains the virtual
        server."
    ::= { exchangeQueueSMTPVirtualSrvEntry 5 }

exqsvsVirtualServerName OBJECT-TYPE
    SYNTAX     DisplayString
    MAX-ACCESS read-only
    STATUS     current
    DESCRIPTION
        "The VirtualServerName property indicates the name
        of the virtual server."
    ::= { exchangeQueueSMTPVirtualSrvEntry 6 }

exchangeQueueX400VirtualSrvTable OBJECT-TYPE
    SYNTAX     SEQUENCE OF ExchangeQueueX400VirtualServer
    MAX-ACCESS not-accessible
    STATUS     current
    DESCRIPTION
        "The Exchange_QueueX400VirtualServer class returns
        properties for X400 queue virtual servers. This
        class inherits all its properties from the
        Exchange_QueueVirtualServer class."
    ::= { wmiExchange 21 }

exchangeQueueX400VirtualSrvEntry OBJECT-TYPE
    SYNTAX     ExchangeQueueX400VirtualServer
    MAX-ACCESS not-accessible
    STATUS     current
    DESCRIPTION
        "None"
    INDEX      { exqxvsIndex }
    ::= { exchangeQueueX400VirtualSrvTable 1 }

ExchangeQueueX400VirtualServer ::= SEQUENCE {
    exqxvsIndex Integer32,
    exqxvsGlobalActionsSupported TruthValue,
    exqxvsGlobalStop TruthValue,
    exqxvsProtocolName DisplayString,
    exqxvsVirtualMachine DisplayString,
    exqxvsVirtualServerName DisplayString
}

exqxvsIndex OBJECT-TYPE
    SYNTAX     Integer32 (1..2147483647)
    MAX-ACCESS read-only
    STATUS     current
    DESCRIPTION
        "The value of this object uniquely identifies the
        instance entry for this class."
    ::= { exchangeQueueX400VirtualSrvEntry 1 }

exqxvsGlobalActionsSupported OBJECT-TYPE
    SYNTAX     TruthValue
    MAX-ACCESS read-only
    STATUS     current
    DESCRIPTION
        "The GlobalActionsSupported property indicates
        whether all remote connections for the virtual
        server can be controlled."
    ::= { exchangeQueueX400VirtualSrvEntry 2 }

exqxvsGlobalStop OBJECT-TYPE
    SYNTAX     TruthValue
    MAX-ACCESS read-only
    STATUS     current
    DESCRIPTION
        "The GlobalStop property indicates whether the
        virtual server for the link is in disabled mode. If
        True, the virtual server is disabled."
    ::= { exchangeQueueX400VirtualSrvEntry 3 }

exqxvsProtocolName OBJECT-TYPE
    SYNTAX     DisplayString
    MAX-ACCESS read-only
    STATUS     current
    DESCRIPTION
        "The ProtocolName property indicates the name of
        the protocol for the virtual server."
    ::= { exchangeQueueX400VirtualSrvEntry 4 }

exqxvsVirtualMachine OBJECT-TYPE
    SYNTAX     DisplayString
    MAX-ACCESS read-only
    STATUS     current
    DESCRIPTION
        "The VirtualMachine property indicates the name of
        the virtual machine that contains the virtual
        server."
    ::= { exchangeQueueX400VirtualSrvEntry 5 }

exqxvsVirtualServerName OBJECT-TYPE
    SYNTAX     DisplayString
    MAX-ACCESS read-only
    STATUS     current
    DESCRIPTION
        "The VirtualServerName property indicates the name
        of the virtual server."
    ::= { exchangeQueueX400VirtualSrvEntry 6 }

exchangeScheduleIntervalTable OBJECT-TYPE
    SYNTAX     SEQUENCE OF ExchangeScheduleInterval
    MAX-ACCESS not-accessible
    STATUS     current
    DESCRIPTION
        "The Exchange_ScheduleInterval WMI class provides
        information about the start and stop time of the
        public folder replication schedule. Instances of
        the Exchange_ScheduleInterval class are returned as
        members of an array from the ReplicationSchedule
        Property."
    ::= { wmiExchange 22 }

exchangeScheduleIntervalEntry OBJECT-TYPE
    SYNTAX     ExchangeScheduleInterval
    MAX-ACCESS not-accessible
    STATUS     current
    DESCRIPTION
        "None"
    INDEX      { exsiIndex }
    ::= { exchangeScheduleIntervalTable 1 }

ExchangeScheduleInterval ::= SEQUENCE {
    exsiIndex Integer32,
    exsiStartTime DateAndTime,
    exsiStopTime DateAndTime
}

exsiIndex OBJECT-TYPE
    SYNTAX     Integer32 (1..2147483647)
    MAX-ACCESS read-only
    STATUS     current
    DESCRIPTION
        "The value of this object uniquely identifies the
        instance entry for this class."
    ::= { exchangeScheduleIntervalEntry 1 }

exsiStartTime OBJECT-TYPE
    SYNTAX     DateAndTime
    MAX-ACCESS read-only
    STATUS     current
    DESCRIPTION
        "The StartTime property indicates the start time,
        formatted as 0000dd-hhmm00:000000."
    ::= { exchangeScheduleIntervalEntry 2 }

exsiStopTime OBJECT-TYPE
    SYNTAX     DateAndTime
    MAX-ACCESS read-only
    STATUS     current
    DESCRIPTION
        "The StopTime property indicates the stop time,
        formatted as 0000dd-hhmm00:000000."
    ::= { exchangeScheduleIntervalEntry 3 }

exchangeSMTPLinkTable OBJECT-TYPE
    SYNTAX     SEQUENCE OF ExchangeSMTPLink
    MAX-ACCESS not-accessible
    STATUS     current
    DESCRIPTION
        "The Exchange_SMTPLink Class provides methods for
        controlling an Microsoft Exchange Link. The
        Exchange_SMTPLink class inherits all the properties
        of the Exchange_Link class."
    ::= { wmiExchange 23 }

exchangeSMTPLinkEntry OBJECT-TYPE
    SYNTAX     ExchangeSMTPLink
    MAX-ACCESS not-accessible
    STATUS     current
    DESCRIPTION
        "None"
    INDEX      { exslIndex }
    ::= { exchangeSMTPLinkTable 1 }

ExchangeSMTPLink ::= SEQUENCE {
    exslIndex Integer32,
    exslActionFreeze TruthValue,
    exslActionKick TruthValue,
    exslActionThaw TruthValue,
    exslExtendedStateInfo DisplayString,
    exslGlobalStop TruthValue,
    exslLinkDN DisplayString,
    exslLinkId DisplayString,
    exslLinkName DisplayString,
    exslMessageCount Gauge32,
    exslNextScheduledConnection DateAndTime,
    exslOldestMessage DateAndTime,
    exslProtocolName DisplayString,
    exslKSize Gauge32,
    exslMSize Gauge32,
    exslStateActive TruthValue,
    exslStateFlags Gauge32,
    exslStateFrozen TruthValue,
    exslStateReady TruthValue,
    exslStateRemote TruthValue,
    exslStateRetry TruthValue,
    exslStateScheduled TruthValue,
    exslSupportedLinkActions Gauge32,
    exslTypeCurrentlyUnreachable TruthValue,
    exslTypeDeferredDelivery TruthValue,
    exslTypeInternal TruthValue,
    exslTypeLocalDelivery TruthValue,
    exslTypePendingCategorization TruthValue,
    exslTypePendingRouting TruthValue,
    exslTypePendingSubmission TruthValue,
    exslTypeRemoteDelivery TruthValue,
    exslVersion Gauge32,
    exslVirtualMachine DisplayString,
    exslVirtualServerName DisplayString
}

exslIndex OBJECT-TYPE
    SYNTAX     Integer32 (1..2147483647)
    MAX-ACCESS read-only
    STATUS     current
    DESCRIPTION
        "The value of this object uniquely identifies the
        instance entry for this class."
    ::= { exchangeSMTPLinkEntry 1 }

exslActionFreeze OBJECT-TYPE
    SYNTAX     TruthValue
    MAX-ACCESS read-only
    STATUS     current
    DESCRIPTION
        "The ActionFreeze property indicates whether the
        link supports the Freeze method."
    ::= { exchangeSMTPLinkEntry 2 }

exslActionKick OBJECT-TYPE
    SYNTAX     TruthValue
    MAX-ACCESS read-only
    STATUS     current
    DESCRIPTION
        "The ActionKick property indicates whether the link
        supports the ForceConnection method."
    ::= { exchangeSMTPLinkEntry 3 }

exslActionThaw OBJECT-TYPE
    SYNTAX     TruthValue
    MAX-ACCESS read-only
    STATUS     current
    DESCRIPTION
        "The ActionThaw property indicates whether the link
        supports the Thaw method."
    ::= { exchangeSMTPLinkEntry 4 }

exslExtendedStateInfo OBJECT-TYPE
    SYNTAX     DisplayString
    MAX-ACCESS read-only
    STATUS     current
    DESCRIPTION
        "The ExtendedStateInfo property indicates extended
        error and reporting troubleshooting information."
    ::= { exchangeSMTPLinkEntry 5 }

exslGlobalStop OBJECT-TYPE
    SYNTAX     TruthValue
    MAX-ACCESS read-only
    STATUS     current
    DESCRIPTION
        "The GlobalStop property indicates whether the
        virtual server for the link is in disabled mode. If
        True, the virtual server is disabled."
    ::= { exchangeSMTPLinkEntry 6 }

exslLinkDN OBJECT-TYPE
    SYNTAX     DisplayString
    MAX-ACCESS read-only
    STATUS     current
    DESCRIPTION
        "The LinkDN property indicates the distinguished
        name (DN) of the link."
    ::= { exchangeSMTPLinkEntry 7 }

exslLinkId OBJECT-TYPE
    SYNTAX     DisplayString
    MAX-ACCESS read-only
    STATUS     current
    DESCRIPTION
        "The LinkId property indicates the identifier for
        the link."
    ::= { exchangeSMTPLinkEntry 8 }

exslLinkName OBJECT-TYPE
    SYNTAX     DisplayString
    MAX-ACCESS read-only
    STATUS     current
    DESCRIPTION
        "The LinkName property indicates the name of the
        link."
    ::= { exchangeSMTPLinkEntry 9 }

exslMessageCount OBJECT-TYPE
    SYNTAX     Gauge32
    MAX-ACCESS read-only
    STATUS     current
    DESCRIPTION
        "The MessageCount property indicates the number of
        messages in the link."
    ::= { exchangeSMTPLinkEntry 10 }

exslNextScheduledConnection OBJECT-TYPE
    SYNTAX     DateAndTime
    MAX-ACCESS read-only
    STATUS     current
    DESCRIPTION
        "The NextScheduledConnection property indicates the
        next time a connection will be attempted."
    ::= { exchangeSMTPLinkEntry 11 }

exslOldestMessage OBJECT-TYPE
    SYNTAX     DateAndTime
    MAX-ACCESS read-only
    STATUS     current
    DESCRIPTION
        "The OldestMessage property indicates the time
        stamp of the oldest message."
    ::= { exchangeSMTPLinkEntry 12 }

exslProtocolName OBJECT-TYPE
    SYNTAX     DisplayString
    MAX-ACCESS read-only
    STATUS     current
    DESCRIPTION
        "The ProtocolName property indicates the name of
        the protocol used by the link."
    ::= { exchangeSMTPLinkEntry 13 }

exslKSize OBJECT-TYPE
    SYNTAX     Gauge32
    UNITS "KB"
    MAX-ACCESS read-only
    STATUS     current
    DESCRIPTION
        "The Size property indicates the size of the link
        (in kilobytes)."
    ::= { exchangeSMTPLinkEntry 14 }

exslMSize OBJECT-TYPE
    SYNTAX     Gauge32
    UNITS "MB"
    MAX-ACCESS read-only
    STATUS     current
    DESCRIPTION
        "The Size property indicates the size of the link
        (in megabytes)."
    ::= { exchangeSMTPLinkEntry 15 }

exslStateActive OBJECT-TYPE
    SYNTAX     TruthValue
    MAX-ACCESS read-only
    STATUS     current
    DESCRIPTION
        "The StateActive property indicates that the link
        is active."
    ::= { exchangeSMTPLinkEntry 16 }

exslStateFlags OBJECT-TYPE
    SYNTAX     Gauge32
    MAX-ACCESS read-only
    STATUS     current
    DESCRIPTION
        "The StateFlags property contains a mask of all of
        the state flags for the link."
    ::= { exchangeSMTPLinkEntry 17 }

exslStateFrozen OBJECT-TYPE
    SYNTAX     TruthValue
    MAX-ACCESS read-only
    STATUS     current
    DESCRIPTION
        "The StateFrozen property indicates whether the
        link is currently frozen."
    ::= { exchangeSMTPLinkEntry 18 }

exslStateReady OBJECT-TYPE
    SYNTAX     TruthValue
    MAX-ACCESS read-only
    STATUS     current
    DESCRIPTION
        "The StateReady property indicates that the link is
        ready to accept new messages."
    ::= { exchangeSMTPLinkEntry 19 }

exslStateRemote OBJECT-TYPE
    SYNTAX     TruthValue
    MAX-ACCESS read-only
    STATUS     current
    DESCRIPTION
        "The StateRemote property indicates that the
        destination for messages in the link is on a remote
        server."
    ::= { exchangeSMTPLinkEntry 20 }

exslStateRetry OBJECT-TYPE
    SYNTAX     TruthValue
    MAX-ACCESS read-only
    STATUS     current
    DESCRIPTION
        "The StateRetry property indicates that the link is
        retrying a transmission that was unsuccessful."
    ::= { exchangeSMTPLinkEntry 21 }

exslStateScheduled OBJECT-TYPE
    SYNTAX     TruthValue
    MAX-ACCESS read-only
    STATUS     current
    DESCRIPTION
        "The StateScheduled property indicates that the
        link is scheduled for periodic activation."
    ::= { exchangeSMTPLinkEntry 22 }

exslSupportedLinkActions OBJECT-TYPE
    SYNTAX     Gauge32
    MAX-ACCESS read-only
    STATUS     current
    DESCRIPTION
        "The SupportedLinkActions property indicates the
        actions that are supported on the link."
    ::= { exchangeSMTPLinkEntry 23 }

exslTypeCurrentlyUnreachable OBJECT-TYPE
    SYNTAX     TruthValue
    MAX-ACCESS read-only
    STATUS     current
    DESCRIPTION
        "The TypeCurrentlyUnreachable property indicates
        that the link holds messages for destinations that
        are currently unreachable."
    ::= { exchangeSMTPLinkEntry 24 }

exslTypeDeferredDelivery OBJECT-TYPE
    SYNTAX     TruthValue
    MAX-ACCESS read-only
    STATUS     current
    DESCRIPTION
        "The TypeDeferredDelivery property indicates that
        the link holds mail that is awaiting a trigger to
        start transmission."
    ::= { exchangeSMTPLinkEntry 25 }

exslTypeInternal OBJECT-TYPE
    SYNTAX     TruthValue
    MAX-ACCESS read-only
    STATUS     current
    DESCRIPTION
        "The TypeInternal property indicates that the link
        is used for internal message processing."
    ::= { exchangeSMTPLinkEntry 26 }

exslTypeLocalDelivery OBJECT-TYPE
    SYNTAX     TruthValue
    MAX-ACCESS read-only
    STATUS     current
    DESCRIPTION
        "The TypeLocalDelivery property indicates whether
        the link is used for local delivery."
    ::= { exchangeSMTPLinkEntry 27 }

exslTypePendingCategorization OBJECT-TYPE
    SYNTAX     TruthValue
    MAX-ACCESS read-only
    STATUS     current
    DESCRIPTION
        "The TypePendingCategorization property indicates
        that the link is for messages whose recipient
        addresses require resolution in Microsoft Active
        Directory."
    ::= { exchangeSMTPLinkEntry 28 }

exslTypePendingRouting OBJECT-TYPE
    SYNTAX     TruthValue
    MAX-ACCESS read-only
    STATUS     current
    DESCRIPTION
        "The TypePendingRouting property indicates that the
        link is for routing the next message that is
        waiting to be transmitted."
    ::= { exchangeSMTPLinkEntry 29 }

exslTypePendingSubmission OBJECT-TYPE
    SYNTAX     TruthValue
    MAX-ACCESS read-only
    STATUS     current
    DESCRIPTION
        "The TypePendingSubmission property indicates that
        the link handles messages that have not yet been
        submitted to the routing engine."
    ::= { exchangeSMTPLinkEntry 30 }

exslTypeRemoteDelivery OBJECT-TYPE
    SYNTAX     TruthValue
    MAX-ACCESS read-only
    STATUS     current
    DESCRIPTION
        "The TypeRemoteDelivery property indicates whether
        the link is currently handling a remote message
        delivery."
    ::= { exchangeSMTPLinkEntry 31 }

exslVersion OBJECT-TYPE
    SYNTAX     Gauge32
    MAX-ACCESS read-only
    STATUS     current
    DESCRIPTION
        "The Version property indicates the version of the
        QAPI used to generate the WMI object."
    ::= { exchangeSMTPLinkEntry 32 }

exslVirtualMachine OBJECT-TYPE
    SYNTAX     DisplayString
    MAX-ACCESS read-only
    STATUS     current
    DESCRIPTION
        "The VirtualMachine property indicates the name of
        the virtual machine that is the source of the
        link."
    ::= { exchangeSMTPLinkEntry 33 }

exslVirtualServerName OBJECT-TYPE
    SYNTAX     DisplayString
    MAX-ACCESS read-only
    STATUS     current
    DESCRIPTION
        "The VirtualServerName property indicates the name
        of the virtual server that is the source of the
        link."
    ::= { exchangeSMTPLinkEntry 34 }

exchangeSMTPQueueTable OBJECT-TYPE
    SYNTAX     SEQUENCE OF ExchangeSMTPQueue
    MAX-ACCESS not-accessible
    STATUS     current
    DESCRIPTION
        "The Exchange_SMTPQueue class returns properties
        for SMTP queues."
    ::= { wmiExchange 24 }

exchangeSMTPQueueEntry OBJECT-TYPE
    SYNTAX     ExchangeSMTPQueue
    MAX-ACCESS not-accessible
    STATUS     current
    DESCRIPTION
        "None"
    INDEX      { exsqIndex }
    ::= { exchangeSMTPQueueTable 1 }

ExchangeSMTPQueue ::= SEQUENCE {
    exsqIndex Integer32,
    exsqCanEnumAll TruthValue,
    exsqGlobalStop TruthValue,
    exsqLinkId DisplayString,
    exsqLinkName DisplayString,
    exsqMessageCount Gauge32,
    exsqMsgEnumFlagsSupported Gauge32,
    exsqProtocolName DisplayString,
    exsqQueueId DisplayString,
    exsqQueueName DisplayString,
    exsqKSize Gauge32,
    exsqMSize Gauge32,
    exsqVersion Gauge32,
    exsqVirtualMachine DisplayString,
    exsqVirtualServerName DisplayString
}

exsqIndex OBJECT-TYPE
    SYNTAX     Integer32 (1..2147483647)
    MAX-ACCESS read-only
    STATUS     current
    DESCRIPTION
        "The value of this object uniquely identifies the
        instance entry for this class."
    ::= { exchangeSMTPQueueEntry 1 }

exsqCanEnumAll OBJECT-TYPE
    SYNTAX     TruthValue
    MAX-ACCESS read-only
    STATUS     current
    DESCRIPTION
        "The CanEnumAll property indicates whether the
        queue can enumerate all of the messages that it has
        waiting for transmission."
    ::= { exchangeSMTPQueueEntry 2 }

exsqGlobalStop OBJECT-TYPE
    SYNTAX     TruthValue
    MAX-ACCESS read-only
    STATUS     current
    DESCRIPTION
        "The GlobalStop property indicates whether the
        virtual server for the queue is in disabled mode.
        If True, the virtual server is disabled."
    ::= { exchangeSMTPQueueEntry 3 }

exsqLinkId OBJECT-TYPE
    SYNTAX     DisplayString
    MAX-ACCESS read-only
    STATUS     current
    DESCRIPTION
        "The LinkId property indicates the identifier for
        the link that contains the queue."
    ::= { exchangeSMTPQueueEntry 4 }

exsqLinkName OBJECT-TYPE
    SYNTAX     DisplayString
    MAX-ACCESS read-only
    STATUS     current
    DESCRIPTION
        "The LinkName property indicates the name of the
        link that contains the queue."
    ::= { exchangeSMTPQueueEntry 5 }

exsqMessageCount OBJECT-TYPE
    SYNTAX     Gauge32
    MAX-ACCESS read-only
    STATUS     current
    DESCRIPTION
        "The MessageCount property indicates the number of
        messages in the queue."
    ::= { exchangeSMTPQueueEntry 6 }

exsqMsgEnumFlagsSupported OBJECT-TYPE
    SYNTAX     Gauge32
    MAX-ACCESS read-only
    STATUS     current
    DESCRIPTION
        "The MsgEnumFlagsSupported property contains a mask
        of all enumeration flags for the queue."
    ::= { exchangeSMTPQueueEntry 7 }

exsqProtocolName OBJECT-TYPE
    SYNTAX     DisplayString
    MAX-ACCESS read-only
    STATUS     current
    DESCRIPTION
        "The ProtocolName property indicates transmission
        protocol for the queue."
    ::= { exchangeSMTPQueueEntry 8 }

exsqQueueId OBJECT-TYPE
    SYNTAX     DisplayString
    MAX-ACCESS read-only
    STATUS     current
    DESCRIPTION
        "The QueueId property indicates the identifier of
        the queue."
    ::= { exchangeSMTPQueueEntry 9 }

exsqQueueName OBJECT-TYPE
    SYNTAX     DisplayString
    MAX-ACCESS read-only
    STATUS     current
    DESCRIPTION
        "The QueueName property indicates the name of the
        queue."
    ::= { exchangeSMTPQueueEntry 10 }

exsqKSize OBJECT-TYPE
    SYNTAX     Gauge32
    UNITS "KB"
    MAX-ACCESS read-only
    STATUS     current
    DESCRIPTION
        "The Size property indicates the size of the queue
        (in kilobytes)."
    ::= { exchangeSMTPQueueEntry 11 }

exsqMSize OBJECT-TYPE
    SYNTAX     Gauge32
    UNITS "MB"
    MAX-ACCESS read-only
    STATUS     current
    DESCRIPTION
        "The Size property indicates the size of the queue
        (in megabytes)."
    ::= { exchangeSMTPQueueEntry 12 }

exsqVersion OBJECT-TYPE
    SYNTAX     Gauge32
    MAX-ACCESS read-only
    STATUS     current
    DESCRIPTION
        "The Version property indicates the version of the
        QAPI used to generate the WMI object."
    ::= { exchangeSMTPQueueEntry 13 }

exsqVirtualMachine OBJECT-TYPE
    SYNTAX     DisplayString
    MAX-ACCESS read-only
    STATUS     current
    DESCRIPTION
        "The VirtualMachine property indicates the name of
        the virtual machine that contains the queue."
    ::= { exchangeSMTPQueueEntry 14 }

exsqVirtualServerName OBJECT-TYPE
    SYNTAX     DisplayString
    MAX-ACCESS read-only
    STATUS     current
    DESCRIPTION
        "The VirtualServerName property indicates the name
        of the virtual server the queue is on."
    ::= { exchangeSMTPQueueEntry 15 }

exchangeX400LinkTable OBJECT-TYPE
    SYNTAX     SEQUENCE OF ExchangeX400Link
    MAX-ACCESS not-accessible
    STATUS     current
    DESCRIPTION
        "The Exchange_X400Link Class provides methods for
        controlling an Microsoft Exchange Link. The
        Exchange_SMTPLink class inherits all the properties
        of the Exchange_Link class."
    ::= { wmiExchange 25 }

exchangeX400LinkEntry OBJECT-TYPE
    SYNTAX     ExchangeX400Link
    MAX-ACCESS not-accessible
    STATUS     current
    DESCRIPTION
        "None"
    INDEX      { exxlIndex }
    ::= { exchangeX400LinkTable 1 }

ExchangeX400Link ::= SEQUENCE {
    exxlIndex Integer32,
    exxlActionFreeze TruthValue,
    exxlActionKick TruthValue,
    exxlActionThaw TruthValue,
    exxlExtendedStateInfo DisplayString,
    exxlGlobalStop TruthValue,
    exxlLinkDN DisplayString,
    exxlLinkId DisplayString,
    exxlLinkName DisplayString,
    exxlMessageCount Gauge32,
    exxlNextScheduledConnection DateAndTime,
    exxlOldestMessage DateAndTime,
    exxlProtocolName DisplayString,
    exxlKSize Gauge32,
    exxlMSize Gauge32,
    exxlStateActive TruthValue,
    exxlStateFlags Gauge32,
    exxlStateFrozen TruthValue,
    exxlStateReady TruthValue,
    exxlStateRemote TruthValue,
    exxlStateRetry TruthValue,
    exxlStateScheduled TruthValue,
    exxlSupportedLinkActions Gauge32,
    exxlTypeCurrentlyUnreachable TruthValue,
    exxlTypeDeferredDelivery TruthValue,
    exxlTypeInternal TruthValue,
    exxlTypeLocalDelivery TruthValue,
    exxlTypePendingCategorization TruthValue,
    exxlTypePendingRouting TruthValue,
    exxlTypePendingSubmission TruthValue,
    exxlTypeRemoteDelivery TruthValue,
    exxlVersion Gauge32,
    exxlVirtualMachine DisplayString,
    exxlVirtualServerName DisplayString
}

exxlIndex OBJECT-TYPE
    SYNTAX     Integer32 (1..2147483647)
    MAX-ACCESS read-only
    STATUS     current
    DESCRIPTION
        "The value of this object uniquely identifies the
        instance entry for this class."
    ::= { exchangeX400LinkEntry 1 }

exxlActionFreeze OBJECT-TYPE
    SYNTAX     TruthValue
    MAX-ACCESS read-only
    STATUS     current
    DESCRIPTION
        "The ActionFreeze property indicates whether the
        link supports the Freeze method."
    ::= { exchangeX400LinkEntry 2 }

exxlActionKick OBJECT-TYPE
    SYNTAX     TruthValue
    MAX-ACCESS read-only
    STATUS     current
    DESCRIPTION
        "The ActionKick property indicates whether the link
        supports the ForceConnection method."
    ::= { exchangeX400LinkEntry 3 }

exxlActionThaw OBJECT-TYPE
    SYNTAX     TruthValue
    MAX-ACCESS read-only
    STATUS     current
    DESCRIPTION
        "The ActionThaw property indicates whether the link
        supports the Thaw method."
    ::= { exchangeX400LinkEntry 4 }

exxlExtendedStateInfo OBJECT-TYPE
    SYNTAX     DisplayString
    MAX-ACCESS read-only
    STATUS     current
    DESCRIPTION
        "The ExtendedStateInfo property indicates extended
        error and reporting troubleshooting information."
    ::= { exchangeX400LinkEntry 5 }

exxlGlobalStop OBJECT-TYPE
    SYNTAX     TruthValue
    MAX-ACCESS read-only
    STATUS     current
    DESCRIPTION
        "The GlobalStop property indicates whether the
        virtual server for the link is in disabled mode. If
        True, the virtual server is disabled."
    ::= { exchangeX400LinkEntry 6 }

exxlLinkDN OBJECT-TYPE
    SYNTAX     DisplayString
    MAX-ACCESS read-only
    STATUS     current
    DESCRIPTION
        "The LinkDN property indicates the distinguished
        name (DN) of the link."
    ::= { exchangeX400LinkEntry 7 }

exxlLinkId OBJECT-TYPE
    SYNTAX     DisplayString
    MAX-ACCESS read-only
    STATUS     current
    DESCRIPTION
        "The LinkId property indicates the identifier for
        the link."
    ::= { exchangeX400LinkEntry 8 }

exxlLinkName OBJECT-TYPE
    SYNTAX     DisplayString
    MAX-ACCESS read-only
    STATUS     current
    DESCRIPTION
        "The LinkName property indicates the name of the
        link."
    ::= { exchangeX400LinkEntry 9 }

exxlMessageCount OBJECT-TYPE
    SYNTAX     Gauge32
    MAX-ACCESS read-only
    STATUS     current
    DESCRIPTION
        "The MessageCount property indicates the number of
        messages in the link."
    ::= { exchangeX400LinkEntry 10 }

exxlNextScheduledConnection OBJECT-TYPE
    SYNTAX     DateAndTime
    MAX-ACCESS read-only
    STATUS     current
    DESCRIPTION
        "The NextScheduledConnection property indicates the
        next time a connection will be attempted."
    ::= { exchangeX400LinkEntry 11 }

exxlOldestMessage OBJECT-TYPE
    SYNTAX     DateAndTime
    MAX-ACCESS read-only
    STATUS     current
    DESCRIPTION
        "The OldestMessage property indicates the time
        stamp of the oldest message."
    ::= { exchangeX400LinkEntry 12 }

exxlProtocolName OBJECT-TYPE
    SYNTAX     DisplayString
    MAX-ACCESS read-only
    STATUS     current
    DESCRIPTION
        "The ProtocolName property indicates the name of
        the protocol used by the link."
    ::= { exchangeX400LinkEntry 13 }

exxlKSize OBJECT-TYPE
    SYNTAX     Gauge32
    UNITS "KB"
    MAX-ACCESS read-only
    STATUS     current
    DESCRIPTION
        "The Size property indicates the size of the link
        (in kilobytes)."
    ::= { exchangeX400LinkEntry 14 }

exxlMSize OBJECT-TYPE
    SYNTAX     Gauge32
    UNITS "MB"
    MAX-ACCESS read-only
    STATUS     current
    DESCRIPTION
        "The Size property indicates the size of the link
        (in megabytes)."
    ::= { exchangeX400LinkEntry 15 }

exxlStateActive OBJECT-TYPE
    SYNTAX     TruthValue
    MAX-ACCESS read-only
    STATUS     current
    DESCRIPTION
        "The StateActive property indicates that the link
        is active."
    ::= { exchangeX400LinkEntry 16 }

exxlStateFlags OBJECT-TYPE
    SYNTAX     Gauge32
    MAX-ACCESS read-only
    STATUS     current
    DESCRIPTION
        "The StateFlags property contains a mask of all of
        the state flags for the link."
    ::= { exchangeX400LinkEntry 17 }

exxlStateFrozen OBJECT-TYPE
    SYNTAX     TruthValue
    MAX-ACCESS read-only
    STATUS     current
    DESCRIPTION
        "The StateFrozen property indicates whether the
        link is currently frozen."
    ::= { exchangeX400LinkEntry 18 }

exxlStateReady OBJECT-TYPE
    SYNTAX     TruthValue
    MAX-ACCESS read-only
    STATUS     current
    DESCRIPTION
        "The StateReady property indicates that the link is
        ready to accept new messages."
    ::= { exchangeX400LinkEntry 19 }

exxlStateRemote OBJECT-TYPE
    SYNTAX     TruthValue
    MAX-ACCESS read-only
    STATUS     current
    DESCRIPTION
        "The StateRemote property indicates that the
        destination for messages in the link is on a remote
        server."
    ::= { exchangeX400LinkEntry 20 }

exxlStateRetry OBJECT-TYPE
    SYNTAX     TruthValue
    MAX-ACCESS read-only
    STATUS     current
    DESCRIPTION
        "The StateRetry property indicates that the link is
        retrying a transmission that was unsuccessful."
    ::= { exchangeX400LinkEntry 21 }

exxlStateScheduled OBJECT-TYPE
    SYNTAX     TruthValue
    MAX-ACCESS read-only
    STATUS     current
    DESCRIPTION
        "The StateScheduled property indicates that the
        link is scheduled for periodic activation."
    ::= { exchangeX400LinkEntry 22 }

exxlSupportedLinkActions OBJECT-TYPE
    SYNTAX     Gauge32
    MAX-ACCESS read-only
    STATUS     current
    DESCRIPTION
        "The SupportedLinkActions property indicates the
        actions that are supported on the link."
    ::= { exchangeX400LinkEntry 23 }

exxlTypeCurrentlyUnreachable OBJECT-TYPE
    SYNTAX     TruthValue
    MAX-ACCESS read-only
    STATUS     current
    DESCRIPTION
        "The TypeCurrentlyUnreachable property indicates
        that the link holds messages for destinations that
        are currently unreachable."
    ::= { exchangeX400LinkEntry 24 }

exxlTypeDeferredDelivery OBJECT-TYPE
    SYNTAX     TruthValue
    MAX-ACCESS read-only
    STATUS     current
    DESCRIPTION
        "The TypeDeferredDelivery property indicates that
        the link holds mail that is awaiting a trigger to
        start transmission."
    ::= { exchangeX400LinkEntry 25 }

exxlTypeInternal OBJECT-TYPE
    SYNTAX     TruthValue
    MAX-ACCESS read-only
    STATUS     current
    DESCRIPTION
        "The TypeInternal property indicates that the link
        is used for internal message processing."
    ::= { exchangeX400LinkEntry 26 }

exxlTypeLocalDelivery OBJECT-TYPE
    SYNTAX     TruthValue
    MAX-ACCESS read-only
    STATUS     current
    DESCRIPTION
        "The TypeLocalDelivery property indicates whether
        the link is used for local delivery."
    ::= { exchangeX400LinkEntry 27 }

exxlTypePendingCategorization OBJECT-TYPE
    SYNTAX     TruthValue
    MAX-ACCESS read-only
    STATUS     current
    DESCRIPTION
        "The TypePendingCategorization property indicates
        that the link is for messages whose recipient
        addresses require resolution in Microsoft Active
        Directory."
    ::= { exchangeX400LinkEntry 28 }

exxlTypePendingRouting OBJECT-TYPE
    SYNTAX     TruthValue
    MAX-ACCESS read-only
    STATUS     current
    DESCRIPTION
        "The TypePendingRouting property indicates that the
        link is for routing the next message that is
        waiting to be transmitted."
    ::= { exchangeX400LinkEntry 29 }

exxlTypePendingSubmission OBJECT-TYPE
    SYNTAX     TruthValue
    MAX-ACCESS read-only
    STATUS     current
    DESCRIPTION
        "The TypePendingSubmission property indicates that
        the link handles messages that have not yet been
        submitted to the routing engine."
    ::= { exchangeX400LinkEntry 30 }

exxlTypeRemoteDelivery OBJECT-TYPE
    SYNTAX     TruthValue
    MAX-ACCESS read-only
    STATUS     current
    DESCRIPTION
        "The TypeRemoteDelivery property indicates whether
        the link is currently handling a remote message
        delivery."
    ::= { exchangeX400LinkEntry 31 }

exxlVersion OBJECT-TYPE
    SYNTAX     Gauge32
    MAX-ACCESS read-only
    STATUS     current
    DESCRIPTION
        "The Version property indicates the version of the
        QAPI used to generate the WMI object."
    ::= { exchangeX400LinkEntry 32 }

exxlVirtualMachine OBJECT-TYPE
    SYNTAX     DisplayString
    MAX-ACCESS read-only
    STATUS     current
    DESCRIPTION
        "The VirtualMachine property indicates the name of
        the virtual machine that is the source of the
        link."
    ::= { exchangeX400LinkEntry 33 }

exxlVirtualServerName OBJECT-TYPE
    SYNTAX     DisplayString
    MAX-ACCESS read-only
    STATUS     current
    DESCRIPTION
        "The VirtualServerName property indicates the name
        of the virtual server that is the source of the
        link."
    ::= { exchangeX400LinkEntry 34 }

exchangeX400QueueTable OBJECT-TYPE
    SYNTAX     SEQUENCE OF ExchangeX400Queue
    MAX-ACCESS not-accessible
    STATUS     current
    DESCRIPTION
        "The Exchange_X400Queue class returns properties
        for X400 queues."
    ::= { wmiExchange 26 }

exchangeX400QueueEntry OBJECT-TYPE
    SYNTAX     ExchangeX400Queue
    MAX-ACCESS not-accessible
    STATUS     current
    DESCRIPTION
        "None"
    INDEX      { exxqIndex }
    ::= { exchangeX400QueueTable 1 }

ExchangeX400Queue ::= SEQUENCE {
    exxqIndex Integer32,
    exxqCanEnumAll TruthValue,
    exxqGlobalStop TruthValue,
    exxqLinkId DisplayString,
    exxqLinkName DisplayString,
    exxqMessageCount Gauge32,
    exxqMsgEnumFlagsSupported Gauge32,
    exxqProtocolName DisplayString,
    exxqQueueId DisplayString,
    exxqQueueName DisplayString,
    exxqKSize Gauge32,
    exxqMSize Gauge32,
    exxqVersion Gauge32,
    exxqVirtualMachine DisplayString,
    exxqVirtualServerName DisplayString
}

exxqIndex OBJECT-TYPE
    SYNTAX     Integer32 (1..2147483647)
    MAX-ACCESS read-only
    STATUS     current
    DESCRIPTION
        "The value of this object uniquely identifies the
        instance entry for this class."
    ::= { exchangeX400QueueEntry 1 }

exxqCanEnumAll OBJECT-TYPE
    SYNTAX     TruthValue
    MAX-ACCESS read-only
    STATUS     current
    DESCRIPTION
        "The CanEnumAll property indicates whether the
        queue can enumerate all of the messages that it has
        waiting for transmission."
    ::= { exchangeX400QueueEntry 2 }

exxqGlobalStop OBJECT-TYPE
    SYNTAX     TruthValue
    MAX-ACCESS read-only
    STATUS     current
    DESCRIPTION
        "The GlobalStop property indicates whether the
        virtual server for the queue is in disabled mode.
        If True, the virtual server is disabled."
    ::= { exchangeX400QueueEntry 3 }

exxqLinkId OBJECT-TYPE
    SYNTAX     DisplayString
    MAX-ACCESS read-only
    STATUS     current
    DESCRIPTION
        "The LinkId property indicates the identifier for
        the link that contains the queue."
    ::= { exchangeX400QueueEntry 4 }

exxqLinkName OBJECT-TYPE
    SYNTAX     DisplayString
    MAX-ACCESS read-only
    STATUS     current
    DESCRIPTION
        "The LinkName property indicates the name of the
        link that contains the queue."
    ::= { exchangeX400QueueEntry 5 }

exxqMessageCount OBJECT-TYPE
    SYNTAX     Gauge32
    MAX-ACCESS read-only
    STATUS     current
    DESCRIPTION
        "The MessageCount property indicates the number of
        messages in the queue."
    ::= { exchangeX400QueueEntry 6 }

exxqMsgEnumFlagsSupported OBJECT-TYPE
    SYNTAX     Gauge32
    MAX-ACCESS read-only
    STATUS     current
    DESCRIPTION
        "The MsgEnumFlagsSupported property contains a mask
        of all enumeration flags for the queue."
    ::= { exchangeX400QueueEntry 7 }

exxqProtocolName OBJECT-TYPE
    SYNTAX     DisplayString
    MAX-ACCESS read-only
    STATUS     current
    DESCRIPTION
        "The ProtocolName property indicates transmission
        protocol for the queue."
    ::= { exchangeX400QueueEntry 8 }

exxqQueueId OBJECT-TYPE
    SYNTAX     DisplayString
    MAX-ACCESS read-only
    STATUS     current
    DESCRIPTION
        "The QueueId property indicates the identifier of
        the queue."
    ::= { exchangeX400QueueEntry 9 }

exxqQueueName OBJECT-TYPE
    SYNTAX     DisplayString
    MAX-ACCESS read-only
    STATUS     current
    DESCRIPTION
        "The QueueName property indicates the name of the
        queue."
    ::= { exchangeX400QueueEntry 10 }

exxqKSize OBJECT-TYPE
    SYNTAX     Gauge32
    UNITS "KB"
    MAX-ACCESS read-only
    STATUS     current
    DESCRIPTION
        "The Size property indicates the size of the queue
        (in kilobytes)."
    ::= { exchangeX400QueueEntry 11 }

exxqMSize OBJECT-TYPE
    SYNTAX     Gauge32
    UNITS "MB"
    MAX-ACCESS read-only
    STATUS     current
    DESCRIPTION
        "The Size property indicates the size of the queue
        (in megabytes)."
    ::= { exchangeX400QueueEntry 12 }

exxqVersion OBJECT-TYPE
    SYNTAX     Gauge32
    MAX-ACCESS read-only
    STATUS     current
    DESCRIPTION
        "The Version property indicates the version of the
        QAPI used to generate the WMI object."
    ::= { exchangeX400QueueEntry 13 }

exxqVirtualMachine OBJECT-TYPE
    SYNTAX     DisplayString
    MAX-ACCESS read-only
    STATUS     current
    DESCRIPTION
        "The VirtualMachine property indicates the name of
        the virtual machine that contains the queue."
    ::= { exchangeX400QueueEntry 14 }

exxqVirtualServerName OBJECT-TYPE
    SYNTAX     DisplayString
    MAX-ACCESS read-only
    STATUS     current
    DESCRIPTION
        "The VirtualServerName property indicates the name
        of the virtual server the queue is on."
    ::= { exchangeX400QueueEntry 15 }

END
