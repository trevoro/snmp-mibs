INTEL-IGMP-PRUNING-MIB DEFINITIONS ::= BEGIN

-- Copyright (C) 1998 Intel Corporation. All rights reserved.
--
-- IGMP Pruning MIB, 98-06-29
--
-- This MIB defines the management information for a system using IGMP
-- pruning.
--
-- Build 2
--
-- Change History:
-- 99-03-18 Per port enable/disable added, descriptions updated and
--          version number added.
-- 98-06-29 Initial version

    IMPORTS
--      Counter, IpAddress FROM RFC1155-SMI
      mib2ext            FROM INTEL-GEN-MIB
      OBJECT-TYPE        FROM RFC-1212;


    igmppru	         OBJECT IDENTIFIER ::= { mib2ext 35 }

--********************** IGMP Pruning ******* ********************************

    conf                 OBJECT IDENTIFIER ::= { igmppru 1 }

    confIgmpPruEnabled OBJECT-TYPE
        SYNTAX INTEGER {
          enabled (1),
          disabled (2)
        }
        ACCESS read-write
        STATUS mandatory
        DESCRIPTION
                 "The administrative status requested by management
                  for IGMP pruning. The value enabled(1) indicates
                  that IGMP pruning should be enabled on this device,
                  in all VLANs, on all ports for which it has not been
                  specifically disabled. When disabled(2), IGMP pruning
                  is disabled, in all VLANs, on all ports."
        ::= { conf 1 }

    confIgmpPruTimer OBJECT-TYPE
        SYNTAX INTEGER (1..10000)
        ACCESS read-write
        STATUS mandatory
        DESCRIPTION "IGMP pruning timer value in seconds. The timer
                     value should be greater than two times the
                     interval between IGMP general queries."
        ::= { conf 2 }

    confIgmpPruPortTable OBJECT-TYPE
        SYNTAX  SEQUENCE OF ConfIgmpPruPortEntry
        ACCESS  not-accessible
        STATUS  mandatory
        DESCRIPTION
                 "Port configuration table"
        ::= { conf 3 }

    confIgmpPruPortEntry OBJECT-TYPE
        SYNTAX  ConfIgmpPruPortEntry
        ACCESS  not-accessible
        STATUS  mandatory
        DESCRIPTION
                 "An entry containing the objects for
                  configuration and status of a port."
        INDEX   { confIgmpPruPortIndex }
        ::= { confIgmpPruPortTable 1 }

    ConfIgmpPruPortEntry ::=
        SEQUENCE {
                  confIgmpPruPortIndex     INTEGER,
                  confIgmpPruPortEnabled   INTEGER
                 }

    confIgmpPruPortIndex OBJECT-TYPE
        SYNTAX  INTEGER
        ACCESS  read-only
        STATUS  mandatory
        DESCRIPTION
                 "An index value that uniquely identifies
                  an interface. The interface identified by
                  a particular value of this index is the
                  same interface as identified by the same
                  value of ifIndex."
        ::= { confIgmpPruPortEntry 1 }

    confIgmpPruPortEnabled OBJECT-TYPE
        SYNTAX INTEGER {
          enabled (1),
          disabled (2)
        }
        ACCESS  read-write
        STATUS  mandatory
        DESCRIPTION
                 "The state of IGMP pruning operation on this port.
                  The value enabled(1) indicates that IGMP pruning
                  is enabled on this port, in all VLANs, as long as
                  confIgmpPruEnabled is also enabled for this device.
                  When disabled(2) but confIgmpPruEnabled is still
                  enabled for the device, IGMP pruning is disabled
                  on this port in all VLANs."

        ::= { confIgmpPruPortEntry 2 }

    confIgmpPruAllowAsQuerier OBJECT-TYPE
        SYNTAX INTEGER {
          enabled (1),
          disabled (2)
        }
        ACCESS read-write
        STATUS mandatory
        DESCRIPTION
                 "The administrative status requested by management
                  for allowing this device to participate in the
                  IGMP querier/non-querier election. The value
                  enabled(1) indicates that the device will
                  participate in the IGMP querier/non-querier
                  election scheme and thus may transmit IGMP
                  queries, in all VLANs, on all ports for which
                  IGMP pruning is also enabled. When disabled(2),
                  the device will NOT participate in the IGMP
                  querier/non-querier election scheme and will
                  NOT transmit any IGMP queries, in all VLANs, on
                  all ports. "
        ::= { conf 4 }

END
