--			Ascend mibospfnbma MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBOSPFNBMA-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibospfNbmaNeighborProfile  OBJECT IDENTIFIER ::= { configuration 98}

	-- The mibospfNbmaNeighborProfile table
	--
	-- This table contains parameters for the mibospfNbmaNeighborProfile profile
	--

    mibospfNbmaNeighborProfileTable	OBJECT-TYPE
	SYNTAX		SEQUENCE OF MibospfNbmaNeighborProfileEntry
	ACCESS		not-accessible
	STATUS		mandatory
	DESCRIPTION	"A list of mibospfNbmaNeighborProfile profile entries."
	::= { mibospfNbmaNeighborProfile 1 }

    mibospfNbmaNeighborProfileEntry	OBJECT-TYPE
	SYNTAX		MibospfNbmaNeighborProfileEntry
	ACCESS		not-accessible
	STATUS		mandatory
	DESCRIPTION	"A mibospfNbmaNeighborProfile entry containing objects that
			 maps to the parameters of mibospfNbmaNeighborProfile profile."
	INDEX		{ ospfNbmaNeighborProfile-Name }
	::= { mibospfNbmaNeighborProfileTable 1 }

    MibospfNbmaNeighborProfileEntry ::=
	SEQUENCE {
	    ospfNbmaNeighborProfile-Name
		DisplayString,
	    ospfNbmaNeighborProfile-HostName
		DisplayString,
	    ospfNbmaNeighborProfile-IpAddress
		IpAddress,
	    ospfNbmaNeighborProfile-DrCapable
		INTEGER,
	    ospfNbmaNeighborProfile-Action-o
		INTEGER
	}

    ospfNbmaNeighborProfile-Name	OBJECT-TYPE
	SYNTAX	DisplayString
	ACCESS	read-only
	STATUS	mandatory
	DESCRIPTION	"The name of this profile."
	::= { mibospfNbmaNeighborProfileEntry 1 }

    ospfNbmaNeighborProfile-HostName	OBJECT-TYPE
	SYNTAX	DisplayString
	ACCESS	read-write
	STATUS	mandatory
	DESCRIPTION	"The name of the associated connection profile."
	::= { mibospfNbmaNeighborProfileEntry 2 }

    ospfNbmaNeighborProfile-IpAddress	OBJECT-TYPE
	SYNTAX	IpAddress
	ACCESS	read-write
	STATUS	mandatory
	DESCRIPTION	"The neighbor's IP address."
	::= { mibospfNbmaNeighborProfileEntry 3 }

    ospfNbmaNeighborProfile-DrCapable	OBJECT-TYPE
	SYNTAX	INTEGER {
		    no (1),
		    yes (2)
		}
	ACCESS	read-write
	STATUS	mandatory
	DESCRIPTION	"Can the neighbor be a Designated Router?"
	::= { mibospfNbmaNeighborProfileEntry 4 }

    ospfNbmaNeighborProfile-Action-o	OBJECT-TYPE
	SYNTAX	INTEGER {
		    noAction (1),
		    createProfile (2),
		    deleteProfile (3)
		}
	ACCESS	read-write
	STATUS	mandatory
	DESCRIPTION	""
	::= { mibospfNbmaNeighborProfileEntry 5 }

END
