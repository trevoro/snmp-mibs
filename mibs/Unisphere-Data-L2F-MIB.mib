-- *****************************************************************************
-- Unisphere-Data-L2F-MIB
--
-- Unisphere Networks Inc. Enterprise MIB
-- Layer Two Forwarding Protocol (L2F) MIB
--
-- Copyright (c) 2001 Unisphere Networks, Inc.  All Rights Reserved.
-- *****************************************************************************

Unisphere-Data-L2F-MIB DEFINITIONS ::= BEGIN

IMPORTS
    MODULE-IDENTITY,
    OBJECT-TYPE, 
    Integer32,
    Counter32,
    Gauge32,
    Unsigned32,
    IpAddress
        FROM SNMPv2-SMI
    TEXTUAL-CONVENTION,
    DisplayString, 
    RowStatus, 
    TruthValue
        FROM SNMPv2-TC
    OBJECT-GROUP, 
    MODULE-COMPLIANCE
        FROM SNMPv2-CONF
    InterfaceIndex,
    InterfaceIndexOrZero
        FROM IF-MIB
    usDataMibs
        FROM Unisphere-Data-MIBs
    UsdEnable
        FROM Unisphere-Data-TC;

usdL2fMIB MODULE-IDENTITY
    LAST-UPDATED "200109251354Z"  -- 25-Sep-01 09:54 AM EDT
    ORGANIZATION "Unisphere Networks, Inc."
    CONTACT-INFO
        "       Unisphere Networks, Inc.
        Postal: 10 Technology Park Drive
                Westford, MA  01886
                USA
        Tel:    +1 978 589 5800
        Email:  mib@UnisphereNetworks.com"
    DESCRIPTION
        "The Layer 2 Forwarding MIB for the Unisphere Networks enterprise."
    -- Revision History
    REVISION    "200109251354Z"  -- 25-Sep-01 09:54 AM EDT  - RX 3.3
    DESCRIPTION
        "Added new object usdL2tpSysConfigReceiveDataSequencingIgnore."
    REVISION    "200109191807Z"  -- 19-Sep-01 02:07 PM EDT  - RX 3.2
    DESCRIPTION
        "Initial version of this MIB module."
    ::= { usDataMibs 53 }


-- ++++++++++++++++++++++++++++++++++++++++++++++++++++++++++++++++++++++
-- Textual conventions
-- ++++++++++++++++++++++++++++++++++++++++++++++++++++++++++++++++++++++

UsdL2fTunnelId ::= TEXTUAL-CONVENTION
    STATUS      current
    DESCRIPTION
        "An L2F Tunnel ID.  Implementation constraints may restrict the range of
        values actually used."
    SYNTAX      Integer32(0..65535)

UsdL2fSessionId ::= TEXTUAL-CONVENTION
    STATUS      current
    DESCRIPTION
        "An L2F Session ID.  Implementation constraints may restrict the range
        of values actually used."
    SYNTAX      Integer32(0..65535)

UsdL2fAdminState ::= TEXTUAL-CONVENTION
    STATUS      current
    DESCRIPTION
        "The administrative state exerted on L2F tunnels sessions at some scope
        of control.

        enabled         New tunnels/sessions may be instantiated.
        disabled        All tunnels/sessions are terminated.
        drain           No new tunnels/sessions may be instantiated,
                        but any existing tunnels/sessions may 
                        persist until they expire by other means.

        The DESCRIPTION clause of an object defined to have this syntax must
        describe the scope of control that object exerts (e.g., all
        tunnels/sessions across the system, sessions within a single tunnel,
        etc.)."
    SYNTAX      INTEGER {
                    enabled(0),
                    disabled(1),
                    drain(2)
                }

UsdL2fTransport ::= TEXTUAL-CONVENTION
    STATUS      current
    DESCRIPTION
        "Transport type over which L2F is carried."
    SYNTAX      INTEGER {
                    other(0),
                    udpIp(1)
                }

-- ++++++++++++++++++++++++++++++++++++++++++++++++++++++++++++++++++++++
-- Managed object groups
-- ++++++++++++++++++++++++++++++++++++++++++++++++++++++++++++++++++++++

usdL2fTraps           OBJECT IDENTIFIER  ::= { usdL2fMIB 0 }
usdL2fObjects         OBJECT IDENTIFIER  ::= { usdL2fMIB 1 }
usdL2fTrapControl     OBJECT IDENTIFIER  ::= { usdL2fMIB 2 }
usdL2fConformance     OBJECT IDENTIFIER  ::= { usdL2fMIB 3 }

--
-- Major subtrees
--
usdL2fSystem          OBJECT IDENTIFIER  ::= { usdL2fObjects 1 }
usdL2fDestination     OBJECT IDENTIFIER  ::= { usdL2fObjects 2 }
usdL2fTunnel          OBJECT IDENTIFIER  ::= { usdL2fObjects 3 }
usdL2fSession         OBJECT IDENTIFIER  ::= { usdL2fObjects 4 }
usdL2fTransport       OBJECT IDENTIFIER  ::= { usdL2fObjects 5 }


-- ......................................................................
-- L2F System Group
-- ......................................................................

usdL2fSystemConfig      OBJECT IDENTIFIER   ::= { usdL2fSystem 1 }
usdL2fSystemStatus      OBJECT IDENTIFIER   ::= { usdL2fSystem 2 }

--
-- L2F System-level Configuration
--
usdL2fSysConfigAdminState OBJECT-TYPE
    SYNTAX      UsdL2fAdminState
    MAX-ACCESS  read-write
    STATUS      current
    DESCRIPTION
        "Exerts control over all L2F tunnels/sessions in the system."
    ::= { usdL2fSystemConfig 1 }

usdL2fSysConfigDestructTimeout OBJECT-TYPE
    SYNTAX      Integer32(0..3600)
    UNITS       "seconds"
    MAX-ACCESS  read-write
    STATUS      current
    DESCRIPTION
        "The amount of time, in seconds, to preserve dynamic tunnels/sessions
        after they become inactive, e.g. to poll their statistics."
    ::= { usdL2fSystemConfig 2 }

usdL2fSysConfigIpChecksumEnable OBJECT-TYPE
    SYNTAX      UsdEnable
    MAX-ACCESS  read-write
    STATUS      current
    DESCRIPTION
        "Enable/disable IP checksumming for tunnels with UDP/IP transport."
    ::= { usdL2fSystemConfig 3 }

usdL2fSysConfigReceiveDataSequencingIgnore OBJECT-TYPE
    SYNTAX      UsdEnable
    MAX-ACCESS  read-write
    STATUS      current
    DESCRIPTION
        "Enable/disable ignoring of receive sequencing of L2F data packets."
    ::= { usdL2fSystemConfig 4 }

--
-- L2F System-level Status and Statistics
--

usdL2fSysStatusProtocolVersion OBJECT-TYPE
    SYNTAX      OCTET STRING (SIZE(2..256))
    MAX-ACCESS  read-only
    STATUS      current
    DESCRIPTION
        "Vector of supported L2F protocol version and revision numbers.
        Supported versions are identified via a two octet pairing where the
        first octet indicates the version and the second octet contains the
        revision."
    ::= { usdL2fSystemStatus 1 }

usdL2fSysStatusVendorName OBJECT-TYPE
    SYNTAX      DisplayString
    MAX-ACCESS  read-only
    STATUS      current
    DESCRIPTION
        "Vendor name of the L2F protocol stack."
    ::= { usdL2fSystemStatus 2 }

usdL2fSysStatusFirmwareRev OBJECT-TYPE
    SYNTAX      Integer32
    MAX-ACCESS  read-only
    STATUS      current
    DESCRIPTION
        "Firmware revision for the L2F protocol stack."
    ::= { usdL2fSystemStatus 3 }

usdL2fSysStatusTotalDestinations OBJECT-TYPE
    SYNTAX      Counter32
    MAX-ACCESS  read-only
    STATUS      current
    DESCRIPTION
        "Number of destination creations attempted."
    ::= { usdL2fSystemStatus 4 }

usdL2fSysStatusFailedDestinations OBJECT-TYPE
    SYNTAX      Counter32
    MAX-ACCESS  read-only
    STATUS      current
    DESCRIPTION
        "Number of destination creation attempts that failed."
    ::= { usdL2fSystemStatus 5 }

usdL2fSysStatusActiveDestinations OBJECT-TYPE
    SYNTAX      Gauge32
    MAX-ACCESS  read-only
    STATUS      current
    DESCRIPTION
        "Number of destinations having at least one active tunnel."
    ::= { usdL2fSystemStatus 6 }

usdL2fSysStatusTotalTunnels OBJECT-TYPE
    SYNTAX      Counter32
    MAX-ACCESS  read-only
    STATUS      current
    DESCRIPTION
        "Number of tunnel creations attempted."
    ::= { usdL2fSystemStatus 7 }

usdL2fSysStatusFailedTunnels OBJECT-TYPE
    SYNTAX      Counter32
    MAX-ACCESS  read-only
    STATUS      current
    DESCRIPTION
        "Number of tunnel creation attempts that failed to reach the established
        state."
    ::= { usdL2fSystemStatus 8 }

usdL2fSysStatusFailedTunnelAuthens OBJECT-TYPE
    SYNTAX      Counter32
    MAX-ACCESS  read-only
    STATUS      current
    DESCRIPTION
        "Number of tunnel creation attempts that failed authentication."
    ::= { usdL2fSystemStatus 9 }

usdL2fSysStatusActiveTunnels OBJECT-TYPE
    SYNTAX      Gauge32
    MAX-ACCESS  read-only
    STATUS      current
    DESCRIPTION
        "Number of tunnels currently established."
    ::= { usdL2fSystemStatus 10 }

usdL2fSysStatusTotalSessions OBJECT-TYPE
    SYNTAX      Counter32
    MAX-ACCESS  read-only
    STATUS      current
    DESCRIPTION
        "Number of session creations attempted."
    ::= { usdL2fSystemStatus 11 }

usdL2fSysStatusFailedSessions OBJECT-TYPE
    SYNTAX      Counter32
    MAX-ACCESS  read-only
    STATUS      current
    DESCRIPTION
        "Number of session creation attempts that failed to reach the
        established state."
    ::= { usdL2fSystemStatus 12 }

usdL2fSysStatusActiveSessions OBJECT-TYPE
    SYNTAX      Gauge32
    MAX-ACCESS  read-only
    STATUS      current
    DESCRIPTION
        "Number of sessions currently established."
    ::= { usdL2fSystemStatus 13 }

-- ......................................................................
-- L2F Destination Group
-- ......................................................................

usdL2fDestConfig      OBJECT IDENTIFIER   ::= { usdL2fDestination 1 }
usdL2fDestStatus      OBJECT IDENTIFIER   ::= { usdL2fDestination 2 }
usdL2fDestStatistics  OBJECT IDENTIFIER   ::= { usdL2fDestination 3 }

-- 
-- Destination-level Configuration
--

-- { usdL2fDestConfig 1 } reserved for "next ifIndex" acquisition

usdL2fDestConfigTable   OBJECT-TYPE
    SYNTAX      SEQUENCE OF UsdL2fDestConfigEntry
    MAX-ACCESS  not-accessible
    STATUS      current
    DESCRIPTION
        "The L2F destination configuration table.  Each entry in this table has
        a corresponding entry in the Interfaces MIB ifTable, and in
        usdL2fDestStatsTable."
    ::= { usdL2fDestConfig 2 }

usdL2fDestConfigEntry   OBJECT-TYPE
    SYNTAX      UsdL2fDestConfigEntry
    MAX-ACCESS  not-accessible
    STATUS      current
    DESCRIPTION
        "Describes the configuration attributes of an L2F destination."
    INDEX { usdL2fDestConfigIfIndex }
    ::= { usdL2fDestConfigTable 1 }

UsdL2fDestConfigEntry ::= SEQUENCE {
    usdL2fDestConfigIfIndex
        InterfaceIndex,
    usdL2fDestConfigRowStatus
        RowStatus,
    usdL2fDestConfigAdminState
        UsdL2fAdminState
    }

usdL2fDestConfigIfIndex OBJECT-TYPE
    SYNTAX      InterfaceIndex
    MAX-ACCESS  not-accessible
    STATUS      current
    DESCRIPTION
        "Same value as ifIndex for the corresponding entry in Interfaces MIB
        ifTable."
    ::= { usdL2fDestConfigEntry 1 }

usdL2fDestConfigRowStatus  OBJECT-TYPE
    SYNTAX      RowStatus
    MAX-ACCESS  read-create
    STATUS      current
    DESCRIPTION
        "An implementation may choose not to support administrative
        configuration of tunnels."
    ::= { usdL2fDestConfigEntry 2 }

usdL2fDestConfigAdminState  OBJECT-TYPE
    SYNTAX      UsdL2fAdminState
    MAX-ACCESS  read-create
    STATUS      current
    DESCRIPTION
        "The configured administrative state."
    DEFVAL { enabled }
    ::= { usdL2fDestConfigEntry 3 }

-- 
-- Destination-level Status
--

usdL2fDestStatusTable   OBJECT-TYPE
    SYNTAX      SEQUENCE OF UsdL2fDestStatusEntry
    MAX-ACCESS  not-accessible
    STATUS      current
    DESCRIPTION
        "The L2F destination status table.  Each entry in this table has a
        corresponding entry in the Interfaces MIB ifTable, and in
        usdL2fDestConfigTable."
    ::= { usdL2fDestStatus 1 }

usdL2fDestStatusEntry   OBJECT-TYPE
    SYNTAX      UsdL2fDestStatusEntry
    MAX-ACCESS  not-accessible
    STATUS      current
    DESCRIPTION
        "Describes the status attributes of an L2F destination."
    INDEX { usdL2fDestStatusIfIndex }
    ::= { usdL2fDestStatusTable 1 }

UsdL2fDestStatusEntry ::= SEQUENCE {
    usdL2fDestStatusIfIndex
        InterfaceIndex,
    usdL2fDestStatusTransport
        UsdL2fTransport,
    usdL2fDestStatusEffectiveAdminState
        UsdL2fAdminState,
    usdL2fDestStatusTotalTunnels
        Counter32,
    usdL2fDestStatusFailedTunnels
        Counter32,
    usdL2fDestStatusFailedTunnelAuthens
        Counter32,
    usdL2fDestStatusActiveTunnels
        Gauge32,
    usdL2fDestStatusTotalSessions
        Counter32,
    usdL2fDestStatusFailedSessions
        Counter32,
    usdL2fDestStatusActiveSessions
        Gauge32
    }

usdL2fDestStatusIfIndex OBJECT-TYPE
    SYNTAX      InterfaceIndex
    MAX-ACCESS  not-accessible
    STATUS      current
    DESCRIPTION
        "Same value as ifIndex for the corresponding entry in Interfaces MIB
        ifTable."
    ::= { usdL2fDestStatusEntry 1 }

usdL2fDestStatusTransport OBJECT-TYPE
    SYNTAX      UsdL2fTransport
    MAX-ACCESS  read-only
    STATUS      current
    DESCRIPTION
        "The underlying transport over which this L2F destination is carried."
    ::= { usdL2fDestStatusEntry 2 }

usdL2fDestStatusEffectiveAdminState  OBJECT-TYPE
    SYNTAX      UsdL2fAdminState
    MAX-ACCESS  read-only
    STATUS      current
    DESCRIPTION
        "The administrative state currently in effect.  This could be the
        configured admin state for this destination, or an overriding admin
        state exerted from a higher hierarchical level (system)."
    ::= { usdL2fDestStatusEntry 3 }

usdL2fDestStatusTotalTunnels OBJECT-TYPE
    SYNTAX      Counter32
    MAX-ACCESS  read-only
    STATUS      current
    DESCRIPTION
        "Number of tunnel creations attempted."
    ::= { usdL2fDestStatusEntry 4 }

usdL2fDestStatusFailedTunnels OBJECT-TYPE
    SYNTAX      Counter32
    MAX-ACCESS  read-only
    STATUS      current
    DESCRIPTION
        "Number of tunnel creation attempts that failed to reach the established
        state."
    ::= { usdL2fDestStatusEntry 5 }

usdL2fDestStatusFailedTunnelAuthens OBJECT-TYPE
    SYNTAX      Counter32
    MAX-ACCESS  read-only
    STATUS      current
    DESCRIPTION
        "Number of tunnel creation attempts that failed authentication."
    ::= { usdL2fDestStatusEntry 6 }

usdL2fDestStatusActiveTunnels OBJECT-TYPE
    SYNTAX      Gauge32
    MAX-ACCESS  read-only
    STATUS      current
    DESCRIPTION
        "Number of tunnels currently established."
    ::= { usdL2fDestStatusEntry 7 }

usdL2fDestStatusTotalSessions OBJECT-TYPE
    SYNTAX      Counter32
    MAX-ACCESS  read-only
    STATUS      current
    DESCRIPTION
        "Number of session creations attempted."
    ::= { usdL2fDestStatusEntry 8 }

usdL2fDestStatusFailedSessions OBJECT-TYPE
    SYNTAX      Counter32
    MAX-ACCESS  read-only
    STATUS      current
    DESCRIPTION
        "Number of session creation attempts that failed to reach the
        established state."
    ::= { usdL2fDestStatusEntry 9 }

usdL2fDestStatusActiveSessions OBJECT-TYPE
    SYNTAX      Gauge32
    MAX-ACCESS  read-only
    STATUS      current
    DESCRIPTION
        "Number of sessions currently established."
    ::= { usdL2fDestStatusEntry 10 }

-- 
-- Destination-level Statistics
--

usdL2fDestStatTable   OBJECT-TYPE
    SYNTAX      SEQUENCE OF UsdL2fDestStatEntry
    MAX-ACCESS  not-accessible
    STATUS      current
    DESCRIPTION
        "The L2F destination statistics table.  Describes the aggregate control
        and payload statistics for all L2F tunnels configured on each
        destination.  Each entry in this table has a corresponding entry in the
        Interfaces MIB ifTable, and in usdL2fDestConfigTable."
    ::= { usdL2fDestStatistics 1 }

usdL2fDestStatEntry   OBJECT-TYPE
    SYNTAX      UsdL2fDestStatEntry
    MAX-ACCESS  not-accessible
    STATUS      current
    DESCRIPTION
        "Describes the aggregate L2F control and payload statistics for all
        L2F tunnels on an L2F destination."
    INDEX { usdL2fDestStatIfIndex }
    ::= { usdL2fDestStatTable 1 }

UsdL2fDestStatEntry ::= SEQUENCE {
    usdL2fDestStatIfIndex
        InterfaceIndex,
    usdL2fDestStatCtlRecvOctets
        Counter32,
    usdL2fDestStatCtlRecvPackets
        Counter32,
    usdL2fDestStatCtlRecvErrors
        Counter32,
    usdL2fDestStatCtlRecvDiscards
        Counter32,
    usdL2fDestStatCtlSendOctets
        Counter32,
    usdL2fDestStatCtlSendPackets
        Counter32,
    usdL2fDestStatCtlSendErrors
        Counter32,
    usdL2fDestStatCtlSendDiscards
        Counter32,
    usdL2fDestStatPayRecvOctets
        Counter32,
    usdL2fDestStatPayRecvPackets
        Counter32,
    usdL2fDestStatPayRecvErrors
        Counter32,
    usdL2fDestStatPayRecvDiscards
        Counter32,
    usdL2fDestStatPaySendOctets
        Counter32,
    usdL2fDestStatPaySendPackets
        Counter32,
    usdL2fDestStatPaySendErrors
        Counter32,
    usdL2fDestStatPaySendDiscards
        Counter32
    }

usdL2fDestStatIfIndex OBJECT-TYPE
    SYNTAX      InterfaceIndex
    MAX-ACCESS  not-accessible
    STATUS      current
    DESCRIPTION
        "Same value as ifIndex for the corresponding entry in Interfaces MIB
        ifTable."
    ::= { usdL2fDestStatEntry 1 }

usdL2fDestStatCtlRecvOctets OBJECT-TYPE
    SYNTAX      Counter32
    MAX-ACCESS  read-only
    STATUS      current
    DESCRIPTION
        "Number of control octets received."
    ::= { usdL2fDestStatEntry 2 }

usdL2fDestStatCtlRecvPackets OBJECT-TYPE
    SYNTAX      Counter32
    MAX-ACCESS  read-only
    STATUS      current
    DESCRIPTION
        "Number of control packets received."
    ::= { usdL2fDestStatEntry 3 }

usdL2fDestStatCtlRecvErrors OBJECT-TYPE
    SYNTAX      Counter32
    MAX-ACCESS  read-only
    STATUS      current
    DESCRIPTION
        "Number of control packets incurring reception errors."
    ::= { usdL2fDestStatEntry 4 }

usdL2fDestStatCtlRecvDiscards OBJECT-TYPE
    SYNTAX      Counter32
    MAX-ACCESS  read-only
    STATUS      current
    DESCRIPTION
        "Number of control packets discarded after reception."
    ::= { usdL2fDestStatEntry 5 }

usdL2fDestStatCtlSendOctets OBJECT-TYPE
    SYNTAX      Counter32
    MAX-ACCESS  read-only
    STATUS      current
    DESCRIPTION
        "Number of control octets sent."
    ::= { usdL2fDestStatEntry 6 }

usdL2fDestStatCtlSendPackets OBJECT-TYPE
    SYNTAX      Counter32
    MAX-ACCESS  read-only
    STATUS      current
    DESCRIPTION
        "Number of control packets sent."
    ::= { usdL2fDestStatEntry 7 }

usdL2fDestStatCtlSendErrors OBJECT-TYPE
    SYNTAX      Counter32
    MAX-ACCESS  read-only
    STATUS      current
    DESCRIPTION
        "Number of control packets incurring transmission errors."
    ::= { usdL2fDestStatEntry 8 }

usdL2fDestStatCtlSendDiscards OBJECT-TYPE
    SYNTAX      Counter32
    MAX-ACCESS  read-only
    STATUS      current
    DESCRIPTION
        "Number of control packets discarded before transmission."
    ::= { usdL2fDestStatEntry 9 }

usdL2fDestStatPayRecvOctets OBJECT-TYPE
    SYNTAX      Counter32
    MAX-ACCESS  read-only
    STATUS      current
    DESCRIPTION
        "Number of payload octets received."
    ::= { usdL2fDestStatEntry 10 }

usdL2fDestStatPayRecvPackets OBJECT-TYPE
    SYNTAX      Counter32
    MAX-ACCESS  read-only
    STATUS      current
    DESCRIPTION
        "Number of payload packets received."
    ::= { usdL2fDestStatEntry 11 }

usdL2fDestStatPayRecvErrors OBJECT-TYPE
    SYNTAX      Counter32
    MAX-ACCESS  read-only
    STATUS      current
    DESCRIPTION
        "Number of payload packets incurring reception errors."
    ::= { usdL2fDestStatEntry 12 }

usdL2fDestStatPayRecvDiscards OBJECT-TYPE
    SYNTAX      Counter32
    MAX-ACCESS  read-only
    STATUS      current
    DESCRIPTION
        "Number of payload packets discarded after reception."
    ::= { usdL2fDestStatEntry 13 }

usdL2fDestStatPaySendOctets OBJECT-TYPE
    SYNTAX      Counter32
    MAX-ACCESS  read-only
    STATUS      current
    DESCRIPTION
        "Number of payload octets sent."
    ::= { usdL2fDestStatEntry 14 }

usdL2fDestStatPaySendPackets OBJECT-TYPE
    SYNTAX      Counter32
    MAX-ACCESS  read-only
    STATUS      current
    DESCRIPTION
        "Number of payload packets sent."
    ::= { usdL2fDestStatEntry 15 }

usdL2fDestStatPaySendErrors OBJECT-TYPE
    SYNTAX      Counter32
    MAX-ACCESS  read-only
    STATUS      current
    DESCRIPTION
        "Number of payload packets incurring transmission errors."
    ::= { usdL2fDestStatEntry 16 }

usdL2fDestStatPaySendDiscards OBJECT-TYPE
    SYNTAX      Counter32
    MAX-ACCESS  read-only
    STATUS      current
    DESCRIPTION
        "Number of payload packets discarded before transmission."
    ::= { usdL2fDestStatEntry 17 }

-- ......................................................................
-- L2F Tunnel Group
-- ......................................................................

usdL2fTunnelConfig      OBJECT IDENTIFIER   ::= { usdL2fTunnel 1 }
usdL2fTunnelStatus      OBJECT IDENTIFIER   ::= { usdL2fTunnel 2 }
usdL2fTunnelStatistics  OBJECT IDENTIFIER   ::= { usdL2fTunnel 3 }
usdL2fTunnelMap         OBJECT IDENTIFIER   ::= { usdL2fTunnel 4 }

-- 
-- Tunnel-level Configuration
--

-- { usdL2fTunnelConfig 1 } reserved for "next ifIndex" acquisition

usdL2fTunnelConfigTable   OBJECT-TYPE
    SYNTAX      SEQUENCE OF UsdL2fTunnelConfigEntry
    MAX-ACCESS  not-accessible
    STATUS      current
    DESCRIPTION
        "The L2F tunnel configuration table.  Each entry in this table has a
        corresponding entry in the Interfaces MIB ifTable, and in
        usdL2fTunnelStatsTable."
    ::= { usdL2fTunnelConfig 2 }

usdL2fTunnelConfigEntry   OBJECT-TYPE
    SYNTAX      UsdL2fTunnelConfigEntry
    MAX-ACCESS  not-accessible
    STATUS      current
    DESCRIPTION
        "Describes the configuration attributes of an L2F tunnel."
    INDEX { usdL2fTunnelConfigIfIndex }
    ::= { usdL2fTunnelConfigTable 1 }

UsdL2fTunnelConfigEntry ::= SEQUENCE {
    usdL2fTunnelConfigIfIndex
        InterfaceIndex,
    usdL2fTunnelConfigRowStatus
        RowStatus,
    usdL2fTunnelConfigAdminState
        UsdL2fAdminState
    }

usdL2fTunnelConfigIfIndex OBJECT-TYPE
    SYNTAX      InterfaceIndex
    MAX-ACCESS  not-accessible
    STATUS      current
    DESCRIPTION
        "Same value as ifIndex for the corresponding entry in Interfaces MIB
        ifTable."
    ::= { usdL2fTunnelConfigEntry 1 }

usdL2fTunnelConfigRowStatus  OBJECT-TYPE
    SYNTAX      RowStatus
    MAX-ACCESS  read-create
    STATUS      current
    DESCRIPTION
        "An implementation may choose not to support administrative
        configuration of tunnels."
    ::= { usdL2fTunnelConfigEntry 2 }

usdL2fTunnelConfigAdminState  OBJECT-TYPE
    SYNTAX      UsdL2fAdminState
    MAX-ACCESS  read-create
    STATUS      current
    DESCRIPTION
        "The configured administrative state."
    DEFVAL { enabled }
    ::= { usdL2fTunnelConfigEntry 3 }

-- 
-- Tunnel-level Status and Statistics
--
usdL2fTunnelStatusTable    OBJECT-TYPE
    SYNTAX      SEQUENCE OF UsdL2fTunnelStatusEntry
    MAX-ACCESS  not-accessible
    STATUS      current
    DESCRIPTION
        "The L2F tunnel status and statistics table.  Each entry in this table
        has a corresponding entry in the Interfaces MIB ifTable, and in
        usdL2fTunnelConfigTable."
    ::= { usdL2fTunnelStatus 1 }

usdL2fTunnelStatusEntry    OBJECT-TYPE
    SYNTAX      UsdL2fTunnelStatusEntry
    MAX-ACCESS  not-accessible
    STATUS      current
    DESCRIPTION
        "An L2F tunnel interface stats entry."
    INDEX { usdL2fTunnelStatusIfIndex }
    ::= { usdL2fTunnelStatusTable 1 }

UsdL2fTunnelStatusEntry ::= SEQUENCE {
    usdL2fTunnelStatusIfIndex
        InterfaceIndex,
    usdL2fTunnelStatusTransport
        UsdL2fTransport,
    usdL2fTunnelStatusLocalTunnelId
        UsdL2fTunnelId,
    usdL2fTunnelStatusRemoteTunnelId
        UsdL2fTunnelId,
    usdL2fTunnelStatusEffectiveAdminState
        UsdL2fAdminState,
    usdL2fTunnelStatusState
        INTEGER,
    usdL2fTunnelStatusInitiated
        INTEGER,
    usdL2fTunnelStatusRemoteHostName
        DisplayString,
    usdL2fTunnelStatusTotalSessions
        Counter32,
    usdL2fTunnelStatusFailedSessions
        Counter32,
    usdL2fTunnelStatusActiveSessions
        Gauge32,
    usdL2fTunnelStatusLastErrorCode
        Integer32,
    usdL2fTunnelStatusLastErrorMessage
        DisplayString,
    usdL2fTunnelStatusCumEstabTime
        Unsigned32
    }

usdL2fTunnelStatusIfIndex  OBJECT-TYPE
    SYNTAX      InterfaceIndex
    MAX-ACCESS  not-accessible
    STATUS      current
    DESCRIPTION
        "Same as the value of ifIndex for the corresponding entry in Interfaces
        MIB ifTable."
    ::= { usdL2fTunnelStatusEntry 1 }

usdL2fTunnelStatusTransport OBJECT-TYPE
    SYNTAX      UsdL2fTransport
    MAX-ACCESS  read-only
    STATUS      current
    DESCRIPTION
        "The underlying transport over which this L2F tunnel is carried."
    ::= { usdL2fTunnelStatusEntry 2 }

usdL2fTunnelStatusLocalTunnelId OBJECT-TYPE
    SYNTAX      UsdL2fTunnelId
    MAX-ACCESS  read-only
    STATUS      current
    DESCRIPTION
        "The local tunnel identifier."
    ::= { usdL2fTunnelStatusEntry 3 }

usdL2fTunnelStatusRemoteTunnelId OBJECT-TYPE
    SYNTAX      UsdL2fTunnelId
    MAX-ACCESS  read-only
    STATUS      current
    DESCRIPTION
        "The remote tunnel identifier."
    ::= { usdL2fTunnelStatusEntry 4 }

usdL2fTunnelStatusEffectiveAdminState  OBJECT-TYPE
    SYNTAX      UsdL2fAdminState
    MAX-ACCESS  read-only
    STATUS      current
    DESCRIPTION
        "The administrative state currently in effect.  This could be the
        configured admin state for this tunnel, or an overriding admin state
        exerted from a higher hierarchical level (system, destination)."
    ::= { usdL2fTunnelStatusEntry 5 }

usdL2fTunnelStatusState    OBJECT-TYPE
    SYNTAX      INTEGER {
                    idle(0),
                    connecting(1),
                    established(2),
                    disconnecting(3)
                }
    MAX-ACCESS  read-only
    STATUS      current
    DESCRIPTION
        "The current state of the tunnel."
    ::= { usdL2fTunnelStatusEntry 6 }

usdL2fTunnelStatusInitiated  OBJECT-TYPE
    SYNTAX      INTEGER {
                    none(0),
                    local(1),
                    remote(2)
                }
    MAX-ACCESS  read-only
    STATUS      current
    DESCRIPTION
        "Indicates whether the tunnel was initiated locally, or by the remote
        tunnel peer."
    ::= { usdL2fTunnelStatusEntry 7 }

usdL2fTunnelStatusRemoteHostName  OBJECT-TYPE
    SYNTAX      DisplayString
    MAX-ACCESS  read-only
    STATUS      current
    DESCRIPTION
        "The host name obtained during the tunnel establishment phase (via the
        Host Name AVP) of the L2F peer.  If the tunnel is idle, this object
        should maintain its value from the last time it was connected, or a
        zero-length string if no name was previously known."
    ::= { usdL2fTunnelStatusEntry 8 }

usdL2fTunnelStatusTotalSessions  OBJECT-TYPE
    SYNTAX      Counter32
    MAX-ACCESS  read-only
    STATUS      current
    DESCRIPTION
        "The total number of sessions that this tunnel has successfully
        connected through to its tunnel peer since this tunnel was created,
        including those that have since terminated."
    ::= { usdL2fTunnelStatusEntry 9 }

usdL2fTunnelStatusFailedSessions  OBJECT-TYPE
    SYNTAX      Counter32
    MAX-ACCESS  read-only
    STATUS      current
    DESCRIPTION
        "The number of sessions that were initiated but failed to reach the
        established phase."
    ::= { usdL2fTunnelStatusEntry 10 }

usdL2fTunnelStatusActiveSessions  OBJECT-TYPE
    SYNTAX      Gauge32
    MAX-ACCESS  read-only
    STATUS      current
    DESCRIPTION
        "The current number of sessions in the established state."
    ::= { usdL2fTunnelStatusEntry 11 }

usdL2fTunnelStatusLastErrorCode  OBJECT-TYPE
    SYNTAX      Integer32 (0..65535)
    MAX-ACCESS  read-only
    STATUS      current
    DESCRIPTION
        "The last value of the error code as described in the Result Code AVP
        which caused the tunnel to disconnect."
    ::= { usdL2fTunnelStatusEntry 12 }

usdL2fTunnelStatusLastErrorMessage  OBJECT-TYPE
    SYNTAX      DisplayString
    MAX-ACCESS  read-only
    STATUS      current
    DESCRIPTION
        "The last value of the optional message as described in the Result Code
        AVP which caused the tunnel to disconnect."
    ::= { usdL2fTunnelStatusEntry 13 }

usdL2fTunnelStatusCumEstabTime OBJECT-TYPE
    SYNTAX      Unsigned32
    UNITS       "seconds"
    MAX-ACCESS  read-only
    STATUS      current
    DESCRIPTION
        "The cumulative time in seconds that this tunnel, since first being
        created, has spent in the established state (which may be punctuated by
        intervals outside the established state)."
    ::= { usdL2fTunnelStatusEntry 14 }

-- 
-- Tunnel-level Statistics
--

usdL2fTunnelStatTable   OBJECT-TYPE
    SYNTAX      SEQUENCE OF UsdL2fTunnelStatEntry
    MAX-ACCESS  not-accessible
    STATUS      current
    DESCRIPTION
        "The L2F tunnel statistics table.  Describes the control and payload
        statistics for each L2F tunnel.  Each entry in this table has a
        corresponding entry in the Interfaces MIB ifTable, and in
        usdL2fTunnelConfigTable."
    ::= { usdL2fTunnelStatistics 1 }

usdL2fTunnelStatEntry   OBJECT-TYPE
    SYNTAX      UsdL2fTunnelStatEntry
    MAX-ACCESS  not-accessible
    STATUS      current
    DESCRIPTION
        "Describes the L2F control and payload statistics for an L2F tunnel."
    INDEX { usdL2fTunnelStatIfIndex }
    ::= { usdL2fTunnelStatTable 1 }

UsdL2fTunnelStatEntry ::= SEQUENCE {
    usdL2fTunnelStatIfIndex
        InterfaceIndex,
    usdL2fTunnelStatCtlRecvOctets
        Counter32,
    usdL2fTunnelStatCtlRecvPackets
        Counter32,
    usdL2fTunnelStatCtlRecvErrors
        Counter32,
    usdL2fTunnelStatCtlRecvDiscards
        Counter32,
    usdL2fTunnelStatCtlSendOctets
        Counter32,
    usdL2fTunnelStatCtlSendPackets
        Counter32,
    usdL2fTunnelStatCtlSendErrors
        Counter32,
    usdL2fTunnelStatCtlSendDiscards
        Counter32,
    usdL2fTunnelStatPayRecvOctets
        Counter32,
    usdL2fTunnelStatPayRecvPackets
        Counter32,
    usdL2fTunnelStatPayRecvErrors
        Counter32,
    usdL2fTunnelStatPayRecvDiscards
        Counter32,
    usdL2fTunnelStatPaySendOctets
        Counter32,
    usdL2fTunnelStatPaySendPackets
        Counter32,
    usdL2fTunnelStatPaySendErrors
        Counter32,
    usdL2fTunnelStatPaySendDiscards
        Counter32,
    usdL2fTunnelStatCtlRecvOutOfSequence
        Counter32
    }

usdL2fTunnelStatIfIndex OBJECT-TYPE
    SYNTAX      InterfaceIndex
    MAX-ACCESS  not-accessible
    STATUS      current
    DESCRIPTION
        "Same value as ifIndex for the corresponding entry in Interfaces MIB
        ifTable."
    ::= { usdL2fTunnelStatEntry 1 }

usdL2fTunnelStatCtlRecvOctets OBJECT-TYPE
    SYNTAX      Counter32
    MAX-ACCESS  read-only
    STATUS      current
    DESCRIPTION
        "Number of control octets received."
    ::= { usdL2fTunnelStatEntry 2 }

usdL2fTunnelStatCtlRecvPackets OBJECT-TYPE
    SYNTAX      Counter32
    MAX-ACCESS  read-only
    STATUS      current
    DESCRIPTION
        "Number of control packets received."
    ::= { usdL2fTunnelStatEntry 3 }

usdL2fTunnelStatCtlRecvErrors OBJECT-TYPE
    SYNTAX      Counter32
    MAX-ACCESS  read-only
    STATUS      current
    DESCRIPTION
        "Number of control packets incurring reception errors."
    ::= { usdL2fTunnelStatEntry 4 }

usdL2fTunnelStatCtlRecvDiscards OBJECT-TYPE
    SYNTAX      Counter32
    MAX-ACCESS  read-only
    STATUS      current
    DESCRIPTION
        "Number of control packets discarded after reception."
    ::= { usdL2fTunnelStatEntry 5 }

usdL2fTunnelStatCtlSendOctets OBJECT-TYPE
    SYNTAX      Counter32
    MAX-ACCESS  read-only
    STATUS      current
    DESCRIPTION
        "Number of control octets sent."
    ::= { usdL2fTunnelStatEntry 6 }

usdL2fTunnelStatCtlSendPackets OBJECT-TYPE
    SYNTAX      Counter32
    MAX-ACCESS  read-only
    STATUS      current
    DESCRIPTION
        "Number of control packets sent."
    ::= { usdL2fTunnelStatEntry 7 }

usdL2fTunnelStatCtlSendErrors OBJECT-TYPE
    SYNTAX      Counter32
    MAX-ACCESS  read-only
    STATUS      current
    DESCRIPTION
        "Number of control packets incurring transmission errors."
    ::= { usdL2fTunnelStatEntry 8 }

usdL2fTunnelStatCtlSendDiscards OBJECT-TYPE
    SYNTAX      Counter32
    MAX-ACCESS  read-only
    STATUS      current
    DESCRIPTION
        "Number of control packets discarded before transmission."
    ::= { usdL2fTunnelStatEntry 9 }

usdL2fTunnelStatPayRecvOctets OBJECT-TYPE
    SYNTAX      Counter32
    MAX-ACCESS  read-only
    STATUS      current
    DESCRIPTION
        "Number of payload octets received."
    ::= { usdL2fTunnelStatEntry 10 }

usdL2fTunnelStatPayRecvPackets OBJECT-TYPE
    SYNTAX      Counter32
    MAX-ACCESS  read-only
    STATUS      current
    DESCRIPTION
        "Number of payload packets received."
    ::= { usdL2fTunnelStatEntry 11 }

usdL2fTunnelStatPayRecvErrors OBJECT-TYPE
    SYNTAX      Counter32
    MAX-ACCESS  read-only
    STATUS      current
    DESCRIPTION
        "Number of payload packets incurring reception errors."
    ::= { usdL2fTunnelStatEntry 12 }

usdL2fTunnelStatPayRecvDiscards OBJECT-TYPE
    SYNTAX      Counter32
    MAX-ACCESS  read-only
    STATUS      current
    DESCRIPTION
        "Number of payload packets discarded after reception."
    ::= { usdL2fTunnelStatEntry 13 }

usdL2fTunnelStatPaySendOctets OBJECT-TYPE
    SYNTAX      Counter32
    MAX-ACCESS  read-only
    STATUS      current
    DESCRIPTION
        "Number of payload octets sent."
    ::= { usdL2fTunnelStatEntry 14 }

usdL2fTunnelStatPaySendPackets OBJECT-TYPE
    SYNTAX      Counter32
    MAX-ACCESS  read-only
    STATUS      current
    DESCRIPTION
        "Number of payload packets sent."
    ::= { usdL2fTunnelStatEntry 15 }

usdL2fTunnelStatPaySendErrors OBJECT-TYPE
    SYNTAX      Counter32
    MAX-ACCESS  read-only
    STATUS      current
    DESCRIPTION
        "Number of payload packets incurring transmission errors."
    ::= { usdL2fTunnelStatEntry 16 }

usdL2fTunnelStatPaySendDiscards OBJECT-TYPE
    SYNTAX      Counter32
    MAX-ACCESS  read-only
    STATUS      current
    DESCRIPTION
        "Number of payload packets discarded before transmission."
    ::= { usdL2fTunnelStatEntry 17 }

-- 
-- additional granularity
--

usdL2fTunnelStatCtlRecvOutOfSequence  OBJECT-TYPE
    SYNTAX      Counter32
    MAX-ACCESS  read-only
    STATUS      current
    DESCRIPTION
        "Number of control packets not received in the correct sequence number
        order."
    ::= { usdL2fTunnelStatEntry 18 }

--
-- Tunnel Mappings
--

--
-- TunnelIf/SessionId -> SessionIf Mapping
--
usdL2fMapTifSidToSifTable   OBJECT-TYPE
    SYNTAX      SEQUENCE OF UsdL2fMapTifSidToSifEntry
    MAX-ACCESS  not-accessible
    STATUS      current
    DESCRIPTION
        "Table of TunnelIf/SessionId -> SessionIf mappings."
    ::= { usdL2fTunnelMap 1 }

usdL2fMapTifSidToSifEntry   OBJECT-TYPE
    SYNTAX      UsdL2fMapTifSidToSifEntry
    MAX-ACCESS  not-accessible
    STATUS      current
    DESCRIPTION
        "A mapping of TunnelIf/SessionId to SessionIf."
    INDEX { usdL2fMapTifSidToSifTunnelIfIndex,
            usdL2fMapTifSidToSifLocalSessionId }
    ::= { usdL2fMapTifSidToSifTable 1 }

UsdL2fMapTifSidToSifEntry ::= SEQUENCE {
    usdL2fMapTifSidToSifTunnelIfIndex
        InterfaceIndex,
    usdL2fMapTifSidToSifLocalSessionId
        UsdL2fSessionId,
    usdL2fMapTifSidToSifSessionIfIndex
        InterfaceIndex
    }

usdL2fMapTifSidToSifTunnelIfIndex OBJECT-TYPE
    SYNTAX      InterfaceIndex
    MAX-ACCESS  not-accessible
    STATUS      current
    DESCRIPTION
        "The ifIndex of a tunnel interface."
    ::= { usdL2fMapTifSidToSifEntry 1 }

usdL2fMapTifSidToSifLocalSessionId  OBJECT-TYPE
    SYNTAX      UsdL2fSessionId
    MAX-ACCESS  not-accessible
    STATUS      current
    DESCRIPTION
        "A local session ID on the associated tunnel interface."
    ::= { usdL2fMapTifSidToSifEntry 2 }

usdL2fMapTifSidToSifSessionIfIndex OBJECT-TYPE
    SYNTAX      InterfaceIndex
    MAX-ACCESS  read-only
    STATUS      current
    DESCRIPTION
        "The ifIndex of the session interface identified by this entry's Tunnel
        ifIndex and local Session Id pair."
    ::= { usdL2fMapTifSidToSifEntry 3 }

--
-- Tunnel ID -> Tunnel If
--
usdL2fMapTidToTifTable OBJECT-TYPE
    SYNTAX      SEQUENCE OF UsdL2fMapTidToTifEntry
    MAX-ACCESS  not-accessible
    STATUS      current
    DESCRIPTION
        "Map L2F tunnel IDs to tunnel interfaces."
    ::= { usdL2fTunnelMap 2 }

usdL2fMapTidToTifEntry OBJECT-TYPE
    SYNTAX      UsdL2fMapTidToTifEntry
    MAX-ACCESS  not-accessible
    STATUS      current
    DESCRIPTION
        "A mapping of L2F tunnel ID to tunnel interface."
    INDEX { usdL2fMapTidToTifLocalTunnelId }
    ::= { usdL2fMapTidToTifTable 1 }

UsdL2fMapTidToTifEntry ::= SEQUENCE {
    usdL2fMapTidToTifLocalTunnelId
        UsdL2fTunnelId,
    usdL2fMapTidToTifIfIndex
        InterfaceIndex
    }

usdL2fMapTidToTifLocalTunnelId OBJECT-TYPE
    SYNTAX      UsdL2fTunnelId
    MAX-ACCESS  not-accessible
    STATUS      current
    DESCRIPTION
        "A local tunnel identifier."
    ::= { usdL2fMapTidToTifEntry 1 }

usdL2fMapTidToTifIfIndex  OBJECT-TYPE
    SYNTAX      InterfaceIndex
    MAX-ACCESS  read-only
    STATUS      current
    DESCRIPTION
        "The ifIndex of the tunnel interface having the associated tunnel
        identifier."
    ::= { usdL2fMapTidToTifEntry 2 }

-- ......................................................................
-- L2F Session Group
-- ......................................................................

usdL2fSessionConfig     OBJECT IDENTIFIER   ::= { usdL2fSession 1 }
usdL2fSessionStatus     OBJECT IDENTIFIER   ::= { usdL2fSession 2 }
usdL2fSessionStatistics OBJECT IDENTIFIER   ::= { usdL2fSession 3 }


--
-- Session-level Configuration
--

-- { usdL2fSessionConfig 1 } reserved for "next ifIndex" acquisition

usdL2fSessionConfigTable   OBJECT-TYPE
    SYNTAX      SEQUENCE OF UsdL2fSessionConfigEntry
    MAX-ACCESS  not-accessible
    STATUS      current
    DESCRIPTION
        "The L2F session configuration table.  Each entry in this table has a
        corresponding entry in the Interfaces MIB ifTable, and in
        usdL2fSessionStatsTable."
    ::= { usdL2fSessionConfig 2 }

usdL2fSessionConfigEntry   OBJECT-TYPE
    SYNTAX      UsdL2fSessionConfigEntry
    MAX-ACCESS  not-accessible
    STATUS      current
    DESCRIPTION
        "Describes the configuration attributes of an L2F session."
    INDEX { usdL2fSessionConfigIfIndex }
    ::= { usdL2fSessionConfigTable 1 }

UsdL2fSessionConfigEntry ::= SEQUENCE {
    usdL2fSessionConfigIfIndex
        InterfaceIndex,
    usdL2fSessionConfigRowStatus
        RowStatus,
    usdL2fSessionConfigAdminState
        UsdL2fAdminState
    }

usdL2fSessionConfigIfIndex OBJECT-TYPE
    SYNTAX      InterfaceIndex
    MAX-ACCESS  not-accessible
    STATUS      current
    DESCRIPTION
        "Same value as ifIndex for the corresponding entry in Interfaces MIB
        ifTable."
    ::= { usdL2fSessionConfigEntry 1 }

usdL2fSessionConfigRowStatus  OBJECT-TYPE
    SYNTAX      RowStatus
    MAX-ACCESS  read-create
    STATUS      current
    DESCRIPTION
        "An implementation may choose not to support administrative
        configuration of tunnels."
    ::= { usdL2fSessionConfigEntry 2 }

usdL2fSessionConfigAdminState  OBJECT-TYPE
    SYNTAX      UsdL2fAdminState
    MAX-ACCESS  read-create
    STATUS      current
    DESCRIPTION
        "The configured administrative state."
    DEFVAL { enabled }
    ::= { usdL2fSessionConfigEntry 3 }


--
-- L2F Session-level Status and Statistics
--
usdL2fSessionStatusTable   OBJECT-TYPE
    SYNTAX      SEQUENCE OF UsdL2fSessionStatusEntry
    MAX-ACCESS  not-accessible
    STATUS      current
    DESCRIPTION
        "The L2F session status and statistics table."
    ::= { usdL2fSessionStatus 1 }

usdL2fSessionStatusEntry   OBJECT-TYPE
    SYNTAX      UsdL2fSessionStatusEntry
    MAX-ACCESS  not-accessible
    STATUS      current
    DESCRIPTION
        "An L2F session interface status and statistics entry."
    INDEX { usdL2fSessionStatusIfIndex }
    ::= { usdL2fSessionStatusTable 1 }

UsdL2fSessionStatusEntry ::= SEQUENCE {
    usdL2fSessionStatusIfIndex
        InterfaceIndex,
    usdL2fSessionStatusLocalSessionId
        UsdL2fSessionId,
    usdL2fSessionStatusRemoteSessionId
        UsdL2fSessionId,
    usdL2fSessionStatusUserName
        DisplayString,
    usdL2fSessionStatusEffectiveAdminState
        UsdL2fAdminState,
    usdL2fSessionStatusState
        INTEGER,
    usdL2fSessionStatusCallType
        INTEGER,
    usdL2fSessionStatusTxConnectSpeed
        Integer32,
    usdL2fSessionStatusRxConnectSpeed
        Integer32,
    usdL2fSessionStatusProxyLcp
        TruthValue,
    usdL2fSessionStatusAuthMethod
        INTEGER,
    usdL2fSessionStatusSequencingState
        INTEGER,
    usdL2fSessionStatusLacTunneledIfIndex
        InterfaceIndexOrZero,
    usdL2fSessionStatusCumEstabTime
        Unsigned32
    }

usdL2fSessionStatusIfIndex OBJECT-TYPE
    SYNTAX      InterfaceIndex
    MAX-ACCESS  not-accessible
    STATUS      current
    DESCRIPTION
        "The ifIndex of an L2F session interface."
    ::= { usdL2fSessionStatusEntry 1 }

usdL2fSessionStatusLocalSessionId  OBJECT-TYPE
    SYNTAX      UsdL2fSessionId
    MAX-ACCESS  read-only
    STATUS      current
    DESCRIPTION
        "The local session ID for the session."
    ::= { usdL2fSessionStatusEntry 2 }

usdL2fSessionStatusRemoteSessionId  OBJECT-TYPE
    SYNTAX      UsdL2fSessionId
    MAX-ACCESS  read-only
    STATUS      current
    DESCRIPTION
        "The remote session ID for the session."
    ::= { usdL2fSessionStatusEntry 3 }

usdL2fSessionStatusUserName  OBJECT-TYPE
    SYNTAX      DisplayString
    MAX-ACCESS  read-only
    STATUS      current
    DESCRIPTION
        "The peer session name on this interface, typically the login name of
        the remote user.  If the user name is unknown this object will contain a
        zero-length string."
    ::= { usdL2fSessionStatusEntry 4 }

usdL2fSessionStatusEffectiveAdminState  OBJECT-TYPE
    SYNTAX      UsdL2fAdminState
    MAX-ACCESS  read-only
    STATUS      current
    DESCRIPTION
        "The administrative state currently in effect.  This could be the
        configured admin state for this session, or an overriding admin state
        exerted from a higher hierarchical level (system, destination, tunnel)."
    ::= { usdL2fSessionStatusEntry 5 }

usdL2fSessionStatusState   OBJECT-TYPE
    SYNTAX      INTEGER {
                    idle(0),
                    connecting(1),
                    established(2),
                    disconnecting(3)
                }
    MAX-ACCESS  read-only
    STATUS      current
    DESCRIPTION
        "The current state of the session."
    ::= { usdL2fSessionStatusEntry 6 }

usdL2fSessionStatusCallType  OBJECT-TYPE
    SYNTAX      INTEGER {
                    none(0),
                    lacIncoming(1),
                    lnsIncoming(2),
                    lacOutgoing(3),
                    lnsOutgoing(4)
                }
    MAX-ACCESS  read-only
    STATUS      current
    DESCRIPTION
        "The type of call and role this tunnel peer is providing for this
        session.  For example, lacIncoming(1) indicates this tunnel peer is
        acting as a LAC and generated a Incoming-Call-Request to the tunnel peer
        (the LNS).  Note that tunnel peers can be both LAC and LNS
        simultaneously."
    ::= { usdL2fSessionStatusEntry 7 }

usdL2fSessionStatusTxConnectSpeed  OBJECT-TYPE
    SYNTAX      Integer32
    MAX-ACCESS  read-only
    STATUS      current
    DESCRIPTION
        "The last known transmit baud rate for this session."
    ::= { usdL2fSessionStatusEntry 8 }

usdL2fSessionStatusRxConnectSpeed  OBJECT-TYPE
    SYNTAX      Integer32
    MAX-ACCESS  read-only
    STATUS      current
    DESCRIPTION
        "The last known receive baud rate for this session."
    ::= { usdL2fSessionStatusEntry 9 }

usdL2fSessionStatusProxyLcp  OBJECT-TYPE
    SYNTAX      TruthValue
    MAX-ACCESS  read-only
    STATUS      current
    DESCRIPTION
        "Indicates whether the LAC performed proxy LCP for this session."
    ::= { usdL2fSessionStatusEntry 10 }

usdL2fSessionStatusAuthMethod  OBJECT-TYPE
    SYNTAX      INTEGER {
                    none(0),
                    pppChap(1),
                    pppPap(2),
                    pppMsChap(3)
                }
    MAX-ACCESS  read-only
    STATUS      current
    DESCRIPTION
        "The proxy authentication method employed by the LAC for the session.
        If usdL2fSessionProxyLcp is false(2) this object reports a value of
        'none' and should be ignored."
    ::= { usdL2fSessionStatusEntry 11 }

usdL2fSessionStatusSequencingState  OBJECT-TYPE
    SYNTAX      INTEGER {
                    none(0),
                    remote(1),
                    local(2),
                    both(3)
                }
    MAX-ACCESS  read-only
    STATUS      current
    DESCRIPTION
        "Indicates which tunnel peers have requested payload sequencing."
    ::= { usdL2fSessionStatusEntry 12 }

usdL2fSessionStatusLacTunneledIfIndex OBJECT-TYPE
    SYNTAX      InterfaceIndexOrZero
    MAX-ACCESS  read-only
    STATUS      current
    DESCRIPTION
        "For pass-through remote client sessions (conventional LAC), the ifIndex
        of an associated local interface through which the remote LAC client was
        connected.  If unknown, this object contains a value of zero.

        For locally originated sessions (LNS-like), this
        object has a value of zero."
    ::= { usdL2fSessionStatusEntry 13 }

usdL2fSessionStatusCumEstabTime OBJECT-TYPE
    SYNTAX      Unsigned32
    UNITS       "seconds"
    MAX-ACCESS  read-only
    STATUS      current
    DESCRIPTION
        "The cumulative time in seconds that this session, since first being
        created, has spent in the established state (which may be punctuated by
        intervals outside the established state)."
    ::= { usdL2fSessionStatusEntry 14 }


--
-- L2F Session-level Statistics
--
usdL2fSessionStatTable   OBJECT-TYPE
    SYNTAX      SEQUENCE OF UsdL2fSessionStatEntry
    MAX-ACCESS  not-accessible
    STATUS      current
    DESCRIPTION
        "The L2F session statistics table."
    ::= { usdL2fSessionStatistics 1 }

usdL2fSessionStatEntry   OBJECT-TYPE
    SYNTAX      UsdL2fSessionStatEntry
    MAX-ACCESS  not-accessible
    STATUS      current
    DESCRIPTION
        "An L2F session interface statistics entry."
    INDEX { usdL2fSessionStatIfIndex }
    ::= { usdL2fSessionStatTable 1 }

UsdL2fSessionStatEntry ::= SEQUENCE {
    usdL2fSessionStatIfIndex
        InterfaceIndex,
    usdL2fSessionStatPayRecvOctets
        Counter32,
    usdL2fSessionStatPayRecvPackets
        Counter32,
    usdL2fSessionStatPayRecvErrors
        Counter32,
    usdL2fSessionStatPayRecvDiscards
        Counter32,
    usdL2fSessionStatPaySendOctets
        Counter32,
    usdL2fSessionStatPaySendPackets
        Counter32,
    usdL2fSessionStatPaySendErrors
        Counter32,
    usdL2fSessionStatPaySendDiscards
        Counter32,

    usdL2fSessionStatRecvOutOfSequence
        Counter32,
    usdL2fSessionStatResequencingTimeouts
        Counter32,

    usdL2fSessionStatPayLostPackets
        Unsigned32
    }

usdL2fSessionStatIfIndex OBJECT-TYPE
    SYNTAX      InterfaceIndex
    MAX-ACCESS  not-accessible
    STATUS      current
    DESCRIPTION
        "The ifIndex of an L2F session interface."
    ::= { usdL2fSessionStatEntry 1 }

usdL2fSessionStatPayRecvOctets OBJECT-TYPE
    SYNTAX      Counter32
    MAX-ACCESS  read-only
    STATUS      current
    DESCRIPTION
        "Number of payload octets received."
    ::= { usdL2fSessionStatEntry 2 }

usdL2fSessionStatPayRecvPackets OBJECT-TYPE
    SYNTAX      Counter32
    MAX-ACCESS  read-only
    STATUS      current
    DESCRIPTION
        "Number of payload packets received."
    ::= { usdL2fSessionStatEntry 3 }

usdL2fSessionStatPayRecvErrors OBJECT-TYPE
    SYNTAX      Counter32
    MAX-ACCESS  read-only
    STATUS      current
    DESCRIPTION
        "Number of payload packets incurring reception errors."
    ::= { usdL2fSessionStatEntry 4 }

usdL2fSessionStatPayRecvDiscards OBJECT-TYPE
    SYNTAX      Counter32
    MAX-ACCESS  read-only
    STATUS      current
    DESCRIPTION
        "Number of payload packets discarded after reception."
    ::= { usdL2fSessionStatEntry 5 }

usdL2fSessionStatPaySendOctets OBJECT-TYPE
    SYNTAX      Counter32
    MAX-ACCESS  read-only
    STATUS      current
    DESCRIPTION
        "Number of payload octets sent."
    ::= { usdL2fSessionStatEntry 6 }

usdL2fSessionStatPaySendPackets OBJECT-TYPE
    SYNTAX      Counter32
    MAX-ACCESS  read-only
    STATUS      current
    DESCRIPTION
        "Number of payload packets sent."
    ::= { usdL2fSessionStatEntry 7 }

usdL2fSessionStatPaySendErrors OBJECT-TYPE
    SYNTAX      Counter32
    MAX-ACCESS  read-only
    STATUS      current
    DESCRIPTION
        "Number of payload packets incurring transmission errors."
    ::= { usdL2fSessionStatEntry 8 }

usdL2fSessionStatPaySendDiscards OBJECT-TYPE
    SYNTAX      Counter32
    MAX-ACCESS  read-only
    STATUS      current
    DESCRIPTION
        "Number of payload packets discarded before transmission."
    ::= { usdL2fSessionStatEntry 9 }

--
-- other
--
usdL2fSessionStatRecvOutOfSequence  OBJECT-TYPE
    SYNTAX      Counter32
    MAX-ACCESS  read-only
    STATUS      current
    DESCRIPTION
        "The number of packets received out of sequence."
    ::= { usdL2fSessionStatEntry 10 }

usdL2fSessionStatResequencingTimeouts  OBJECT-TYPE
    SYNTAX      Counter32
    MAX-ACCESS  read-only
    STATUS      current
    DESCRIPTION
        "The number of reassembly timeouts that have occurred."
    ::= { usdL2fSessionStatEntry 11 }


usdL2fSessionStatPayLostPackets OBJECT-TYPE
    SYNTAX      Unsigned32
    MAX-ACCESS  read-only
    STATUS      current
    DESCRIPTION
        "When sequence numbers are enabled, this value represents the estimated
        number of payload packets lost, based on observed gaps in sequence
        numbers.  This estimate is subject to correction (decrement) upon
        receipt of out-of-sequence packets that fill previously observed gaps."
    ::= { usdL2fSessionStatEntry 12 }


-- ......................................................................
-- L2F Transport Group
-- ......................................................................

--
-- UDP/IP Transport
--
usdL2fTransportUdpIp        OBJECT IDENTIFIER   ::= { usdL2fTransport 1 }
usdL2fUdpIpDestination      OBJECT IDENTIFIER   ::= { usdL2fTransportUdpIp 1 }
usdL2fUdpIpTunnel           OBJECT IDENTIFIER   ::= { usdL2fTransportUdpIp 2 }

-- 
-- UDP/IP Destination
--
usdL2fUdpIpDestTable   OBJECT-TYPE
    SYNTAX      SEQUENCE OF UsdL2fUdpIpDestEntry
    MAX-ACCESS  not-accessible
    STATUS      current
    DESCRIPTION
        "The L2F UDP/IP destination table.  Reports the UDP/IP characteristics
        of a L2F UDP/IP destination.

        A L2F UDP/IP destination is associated with a local router, a local IP
        address, and with a remote IP address for the L2F peer.  More specific
        UDP/IP detail per tunnel is reported in the usdL2fUdpIpTunnelTable."
    ::= { usdL2fUdpIpDestination 1 }

usdL2fUdpIpDestEntry   OBJECT-TYPE
    SYNTAX      UsdL2fUdpIpDestEntry
    MAX-ACCESS  not-accessible
    STATUS      current
    DESCRIPTION
        "Describes the UDP/IP attributes of an L2F destination."
    INDEX { usdL2fUdpIpDestIfIndex }
    ::= { usdL2fUdpIpDestTable 1 }

UsdL2fUdpIpDestEntry ::= SEQUENCE {
    usdL2fUdpIpDestIfIndex
        InterfaceIndex,
    usdL2fUdpIpDestRouterIndex
        Unsigned32,
    usdL2fUdpIpDestLocalAddress
        IpAddress,
    usdL2fUdpIpDestRemoteAddress
        IpAddress
    }

usdL2fUdpIpDestIfIndex OBJECT-TYPE
    SYNTAX      InterfaceIndex
    MAX-ACCESS  not-accessible
    STATUS      current
    DESCRIPTION
        "Same value as ifIndex for the corresponding entry in Interfaces MIB
        ifTable."
    ::= { usdL2fUdpIpDestEntry 1 }

usdL2fUdpIpDestRouterIndex  OBJECT-TYPE
    SYNTAX      Unsigned32
    MAX-ACCESS  read-only
    STATUS      current
    DESCRIPTION
        "The index of an entry in the usdRouterTable for the local router with
        which this L2F destination interface is associated."
    ::= { usdL2fUdpIpDestEntry 2 }

usdL2fUdpIpDestLocalAddress  OBJECT-TYPE
    SYNTAX      IpAddress
    MAX-ACCESS  read-only
    STATUS      current
    DESCRIPTION
        "This L2F destination's local IP address."
    ::= { usdL2fUdpIpDestEntry 3 }

usdL2fUdpIpDestRemoteAddress  OBJECT-TYPE
    SYNTAX      IpAddress
    MAX-ACCESS  read-only
    STATUS      current
    DESCRIPTION
        "The IP address of the remote L2F endpoint."
    ::= { usdL2fUdpIpDestEntry 4 }


--
-- UDP/IP Tunnel
--
usdL2fUdpIpTunnelTable    OBJECT-TYPE
    SYNTAX      SEQUENCE OF UsdL2fUdpIpTunnelEntry
    MAX-ACCESS  not-accessible
    STATUS      current
    DESCRIPTION
        "The L2F UDP/IP tunnel table.  Reports the UDP/IP characteristics of
        L2F UDP/IP tunnels.

        A L2F UDP/IP tunnel is defined in terms of the local and remote IP
        addresses and UDP ports."
    ::= { usdL2fUdpIpTunnel 1 }

usdL2fUdpIpTunnelEntry    OBJECT-TYPE
    SYNTAX      UsdL2fUdpIpTunnelEntry
    MAX-ACCESS  not-accessible
    STATUS      current
    DESCRIPTION
        "An L2F UDP/IP tunnel entry."
    INDEX { usdL2fUdpIpTunnelIfIndex }
    ::= { usdL2fUdpIpTunnelTable 1 }

UsdL2fUdpIpTunnelEntry ::= SEQUENCE {
    usdL2fUdpIpTunnelIfIndex
        InterfaceIndex,
    usdL2fUdpIpTunnelRouterIndex
        Unsigned32,
    usdL2fUdpIpTunnelLocalAddress
        IpAddress,
    usdL2fUdpIpTunnelLocalPort
        Integer32,
    usdL2fUdpIpTunnelRemoteAddress
        IpAddress,
    usdL2fUdpIpTunnelRemotePort
        Integer32
    }

usdL2fUdpIpTunnelIfIndex  OBJECT-TYPE
    SYNTAX      InterfaceIndex
    MAX-ACCESS  not-accessible
    STATUS      current
    DESCRIPTION
        "Same as the value of ifIndex for the corresponding entry in Interfaces
        MIB ifTable."
    ::= { usdL2fUdpIpTunnelEntry 1 }

usdL2fUdpIpTunnelRouterIndex  OBJECT-TYPE
    SYNTAX      Unsigned32
    MAX-ACCESS  read-only
    STATUS      current
    DESCRIPTION
        "The index of an entry in the usdRouterTable for the local router with
        which this L2F tunnel interface is associated."
    ::= { usdL2fUdpIpTunnelEntry 2 }

usdL2fUdpIpTunnelLocalAddress OBJECT-TYPE
    SYNTAX      IpAddress
    MAX-ACCESS  read-only
    STATUS      current
    DESCRIPTION
        "The local IP address for this UDP/IP tunnel."
    ::= { usdL2fUdpIpTunnelEntry 3 }

usdL2fUdpIpTunnelLocalPort OBJECT-TYPE
    SYNTAX      Integer32
    MAX-ACCESS  read-only
    STATUS      current
    DESCRIPTION
        "The local UDP port for this UDP/IP tunnel."
    ::= { usdL2fUdpIpTunnelEntry 4 }

usdL2fUdpIpTunnelRemoteAddress OBJECT-TYPE
    SYNTAX      IpAddress
    MAX-ACCESS  read-only
    STATUS      current
    DESCRIPTION
        "The remote IP address for this UDP/IP tunnel."
    ::= { usdL2fUdpIpTunnelEntry 5 }

usdL2fUdpIpTunnelRemotePort OBJECT-TYPE
    SYNTAX      Integer32
    MAX-ACCESS  read-only
    STATUS      current
    DESCRIPTION
        "The remote UDP port for this UDP/IP tunnel."
    ::= { usdL2fUdpIpTunnelEntry 6 }


-- ++++++++++++++++++++++++++++++++++++++++++++++++++++++++++++++++++++++
-- conformance information
-- ++++++++++++++++++++++++++++++++++++++++++++++++++++++++++++++++++++++

usdL2fGroups      OBJECT IDENTIFIER ::= { usdL2fConformance 1 }
usdL2fCompliances OBJECT IDENTIFIER ::= { usdL2fConformance 2 }

--
-- compliance statements
--

usdL2fCompliance MODULE-COMPLIANCE
    STATUS      current
    DESCRIPTION
        "The compliance statement for SNMPv2 entities which implement the L2F
        MIB."
    MODULE      -- this module
        -- unconditionally mandatory groups
        MANDATORY-GROUPS {
            usdL2fConfigGroup,
            usdL2fStatusGroup,
            usdL2fStatGroup,
            usdL2fMapGroup
        }
    ::= { usdL2fCompliances 1 }                                        -- RX 3.2

-- units of conformance

usdL2fConfigGroup OBJECT-GROUP
    OBJECTS {
        usdL2fSysConfigAdminState,
        usdL2fSysConfigDestructTimeout,
        usdL2fSysConfigIpChecksumEnable,
        usdL2fSysConfigReceiveDataSequencingIgnore,

        usdL2fDestConfigRowStatus,
        usdL2fDestConfigAdminState,

        usdL2fTunnelConfigRowStatus,
        usdL2fTunnelConfigAdminState,
        
        usdL2fSessionConfigRowStatus,
        usdL2fSessionConfigAdminState
    }
    STATUS          current
    DESCRIPTION
        "A collection of objects providing configuration information of the L2F
        protocol, tunnels and sessions."
    ::= { usdL2fGroups 1 }

usdL2fStatusGroup OBJECT-GROUP
    OBJECTS {
        usdL2fSysStatusProtocolVersion,
        usdL2fSysStatusVendorName,
        usdL2fSysStatusFirmwareRev,
        usdL2fSysStatusTotalDestinations,
        usdL2fSysStatusFailedDestinations,
        usdL2fSysStatusActiveDestinations,
        usdL2fSysStatusTotalTunnels,
        usdL2fSysStatusFailedTunnels,
        usdL2fSysStatusFailedTunnelAuthens,
        usdL2fSysStatusActiveTunnels,
        usdL2fSysStatusTotalSessions,
        usdL2fSysStatusFailedSessions,
        usdL2fSysStatusActiveSessions,

        usdL2fDestStatusTransport,
        usdL2fDestStatusEffectiveAdminState,
        usdL2fDestStatusTotalTunnels,
        usdL2fDestStatusFailedTunnels,
        usdL2fDestStatusFailedTunnelAuthens,
        usdL2fDestStatusActiveTunnels,
        usdL2fDestStatusTotalSessions,
        usdL2fDestStatusFailedSessions,
        usdL2fDestStatusActiveSessions,

        usdL2fTunnelStatusTransport,
        usdL2fTunnelStatusLocalTunnelId,
        usdL2fTunnelStatusRemoteTunnelId,
        usdL2fTunnelStatusEffectiveAdminState,
        usdL2fTunnelStatusState,
        usdL2fTunnelStatusInitiated,
        usdL2fTunnelStatusRemoteHostName,
        usdL2fTunnelStatusTotalSessions,
        usdL2fTunnelStatusFailedSessions,
        usdL2fTunnelStatusActiveSessions,
        usdL2fTunnelStatusLastErrorCode,
        usdL2fTunnelStatusLastErrorMessage,
        usdL2fTunnelStatusCumEstabTime,

        -- usdL2fSessionStatusLacPppIfIndex deprecated
        usdL2fSessionStatusLocalSessionId,
        usdL2fSessionStatusRemoteSessionId,
        usdL2fSessionStatusUserName,
        usdL2fSessionStatusEffectiveAdminState,
        usdL2fSessionStatusState,
        usdL2fSessionStatusCallType,
        usdL2fSessionStatusTxConnectSpeed,
        usdL2fSessionStatusRxConnectSpeed,
        usdL2fSessionStatusProxyLcp,
        usdL2fSessionStatusAuthMethod,
        usdL2fSessionStatusSequencingState,
        usdL2fSessionStatusLacTunneledIfIndex,
        usdL2fSessionStatusCumEstabTime
    }
    STATUS          current
    DESCRIPTION
        "A collection of objects providing status of the L2F protocol at the
        system, destination, tunnel, and session levels."
    ::= { usdL2fGroups 2 }

usdL2fStatGroup OBJECT-GROUP
    OBJECTS {
        usdL2fDestStatCtlRecvOctets,
        usdL2fDestStatCtlRecvPackets,
        usdL2fDestStatCtlRecvErrors,
        usdL2fDestStatCtlRecvDiscards,
        usdL2fDestStatCtlSendOctets,
        usdL2fDestStatCtlSendPackets,
        usdL2fDestStatCtlSendErrors,
        usdL2fDestStatCtlSendDiscards,
        usdL2fDestStatPayRecvOctets,
        usdL2fDestStatPayRecvPackets,
        usdL2fDestStatPayRecvErrors,
        usdL2fDestStatPayRecvDiscards,
        usdL2fDestStatPaySendOctets,
        usdL2fDestStatPaySendPackets,
        usdL2fDestStatPaySendErrors,
        usdL2fDestStatPaySendDiscards,

        usdL2fTunnelStatCtlRecvOctets,
        usdL2fTunnelStatCtlRecvPackets,
        usdL2fTunnelStatCtlRecvErrors,
        usdL2fTunnelStatCtlRecvDiscards,
        usdL2fTunnelStatCtlSendOctets,
        usdL2fTunnelStatCtlSendPackets,
        usdL2fTunnelStatCtlSendErrors,
        usdL2fTunnelStatCtlSendDiscards,
        usdL2fTunnelStatPayRecvOctets,
        usdL2fTunnelStatPayRecvPackets,
        usdL2fTunnelStatPayRecvErrors,
        usdL2fTunnelStatPayRecvDiscards,
        usdL2fTunnelStatPaySendOctets,
        usdL2fTunnelStatPaySendPackets,
        usdL2fTunnelStatPaySendErrors,
        usdL2fTunnelStatPaySendDiscards,
        usdL2fTunnelStatCtlRecvOutOfSequence,

        usdL2fSessionStatPayRecvOctets,
        usdL2fSessionStatPayRecvPackets,
        usdL2fSessionStatPayRecvErrors,
        usdL2fSessionStatPayRecvDiscards,
        usdL2fSessionStatPaySendOctets,
        usdL2fSessionStatPaySendPackets,
        usdL2fSessionStatPaySendErrors,
        usdL2fSessionStatPaySendDiscards,
        usdL2fSessionStatRecvOutOfSequence,
        usdL2fSessionStatResequencingTimeouts,
        usdL2fSessionStatPayLostPackets
    }
    STATUS          current
    DESCRIPTION
        "A collection of objects providing statistics of the L2F protocol at
        the destination, tunnel, and session levels."
    ::= { usdL2fGroups 3 }

usdL2fMapGroup OBJECT-GROUP
    OBJECTS {
        usdL2fMapTifSidToSifSessionIfIndex,
        usdL2fMapTidToTifIfIndex
    }
    STATUS          current
    DESCRIPTION
        "A collection of objects providing mapping associations among L2F
        components."
    ::= { usdL2fGroups 4 }

usdL2fUdpIpGroup OBJECT-GROUP
    OBJECTS {
        usdL2fUdpIpDestRouterIndex,
        usdL2fUdpIpDestLocalAddress,
        usdL2fUdpIpDestRemoteAddress,

        usdL2fUdpIpTunnelRouterIndex,
        usdL2fUdpIpTunnelLocalAddress,
        usdL2fUdpIpTunnelLocalPort,
        usdL2fUdpIpTunnelRemoteAddress,
        usdL2fUdpIpTunnelRemotePort
    }
    STATUS          current
    DESCRIPTION
        "A collection of objects providing UDP/IP transport information for L2F
        components."
    ::= { usdL2fGroups 5 }

END
