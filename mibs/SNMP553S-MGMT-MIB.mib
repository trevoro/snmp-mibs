-- Copyright 1995 General DataComm Inc., Inc. All Rights Reserved.
--
-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive license to use
-- this Specification in connection with the management of GDC's products.
--
-- This Specification is supplied "AS IS," and GDC makes no warranty,
-- either expressed or implied, as to the use operation, condition, or
-- performance of the Specification.

-- Revision History
-- Version   Date	Name		Description
-- 1.00A     01-Sep-94  B. Bergquist	Initial Revision
-- 1.00B     13-Oct-94	J. Tokarski	Removed the following entries
--  					from the NMS553UnitConfigTable:
--  					  nms553ExtModemPresent
--  					  nms553ManagementSource
--    					  nms553ShelfMaster
--  					  nms553forceFakeMaster
--  					  nms553daisyChainBps
--  					The corresponding variables
--  					  now reside in the gdcnms MIB
--  					Added nms553CompatibilityMode
-- 1.00C     16-Nov-94  J. Deptula      Renamed everything as SNMP
--					Fixed compile bugs
--					Added set-config vars
--					Merged with gdcnms.mib
-- 					Redefined location in MIB tree
-- 1.00D     16-Jan-95  J. Deptula      Added some misc CONFORMANCE statements
--					Enhanced description of snmp553SaveCsuConfig
--					   and snmp553SaveDsuConfig
--					Added snmp553ProductType variable
-- 1.00E     26-Jan-95  J. Deptula      Removed SNMPV1 CONFORMANCE statements
-- 1.00F     7-Feb-95   J. Deptula      Added snmp553LedStatus
-- 1.00G     6-Mar-95   J. Deptula      Added snmp553DiagTestDuration
--                                      Added snmp553DiagProgPattern
--           7-Mar-95   T. Ecsedy       Added snmp553AlarmHistoryTable
--					Added snmp553AlarmMaintenanceTable
-- 1.00H     30-Mar-95	J. Deptula	Redefined snmp553SaveCsuConfig and 
--					   snmp553SaveDsuConfig variables 
--					Moved snmp553 branch components
--					   under nms553s from GDCDSX1-MIB         
--					Added alarm block from GDCDSX1-MIB
--					Renamed everything snmp553s
-- 1.00I     3-Apr-95   J. Deptula      Added snmp553sUnitSerialNumber variable
--					Divided snmp553sUnitConfigTable into:
--					   snmp553sUnitConfigTable,
--					   snmp553sMaintenanceTable,
--					   snmp553sDiagTable
-- 1.00J     11-Apr-95  T. Ecsedy	General description corrections
-- 1.00K     18-Apr-95  T. Ecsedy	Clarify snmp553AlarmData description
-- 1.00L     30-Jun-95  J. Deptula      Added Channel SD and RD disclaimer
--					   to snmp553sLedStatus
--           30-Jun-95	T. Ecsedy       Add reading of the time of last alarm
--                                         history clear in alarm maintenance 
--                                         table.
-- 1.00M     11-Jul-95  J. Deptula      Added snmp553sSaveAllConfig variable
-- 1.00N     7-Aug-95   J. Deptula      Added OBJECT IDENTIFIER for snmp553sc
--
SNMP553S-MGMT-MIB DEFINITIONS ::= BEGIN

IMPORTS
 
	Gauge				FROM RFC1155-SMI
 	OBJECT-TYPE			FROM RFC-1212
	DisplayString			FROM RFC1213-MIB
	SCinstance			FROM GDCMACRO-MIB
	dsx1				FROM GDCDSX1-MIB;

snmp553s	OBJECT IDENTIFIER ::= { dsx1 3 }
snmp553sc	OBJECT IDENTIFIER ::= { dsx1 4 }

-- This MIB module uses the extended OBJECT-TYPE macro as
-- defined in RFC 1212.

-- The implementation of all groups is mandatory.

-- Note:  All rows in all tables defined within this MIB module are
-- virtual.  They can neither be created or deleted by management
-- operations.

--
-- SNMP553S Alarm Object Identifier Definitions
--
snmp553sAlarmData		OBJECT IDENTIFIER ::= { snmp553s 1 }

snmp553sNoResponseAlm		OBJECT IDENTIFIER ::= { snmp553sAlarmData 1 }
snmp553sDiagRxErrAlm		OBJECT IDENTIFIER ::= { snmp553sAlarmData 2 }
snmp553sPowerUpAlm		OBJECT IDENTIFIER ::= { snmp553sAlarmData 3 }
snmp553sNvRamCorrupt		OBJECT IDENTIFIER ::= { snmp553sAlarmData 4 }
snmp553sUnitFailure		OBJECT IDENTIFIER ::= { snmp553sAlarmData 5 }
snmp553sMbiLock			OBJECT IDENTIFIER ::= { snmp553sAlarmData 6 }
snmp553sLocalPwrFail		OBJECT IDENTIFIER ::= { snmp553sAlarmData 7 }
snmp553sTimingLoss		OBJECT IDENTIFIER ::= { snmp553sAlarmData 8 }
snmp553sStatusChange		OBJECT IDENTIFIER ::= { snmp553sAlarmData 9 }
snmp553sUnsoTest		OBJECT IDENTIFIER ::= { snmp553sAlarmData 10 }
snmp553sLossOfSignal		OBJECT IDENTIFIER ::= { snmp553sAlarmData 11 }
snmp553sLossOfFrame		OBJECT IDENTIFIER ::= { snmp553sAlarmData 12 }
snmp553sAis			OBJECT IDENTIFIER ::= { snmp553sAlarmData 13 }
snmp553sReceivedYellow		OBJECT IDENTIFIER ::= { snmp553sAlarmData 14 }
snmp553sUnavailSignalState	OBJECT IDENTIFIER ::= { snmp553sAlarmData 15 }
snmp553sExcessiveZeros		OBJECT IDENTIFIER ::= { snmp553sAlarmData 16 }
snmp553sLowAverageDensity	OBJECT IDENTIFIER ::= { snmp553sAlarmData 17 }
snmp553sControlledSlips		OBJECT IDENTIFIER ::= { snmp553sAlarmData 18 }
snmp553sBipolarViolations	OBJECT IDENTIFIER ::= { snmp553sAlarmData 19 }
snmp553sCrcErrors		OBJECT IDENTIFIER ::= { snmp553sAlarmData 20 }


 -- The following Table provides a description of the alarms on the 553s.
 -- The index sub-identifier for each alarm on an interface basis is:
 --
 -- 			unit sub-identifier = 1
 -- 			net  sub-identifier = 1
 -- 			casc sub-identifier = 2
 -- 
 -- ALARM                       Maskable   Valid interfaces   win/thres	Type
 -- ============================================================================
 -- snmp553sNoResponseAlm       no         unit               no	major
 -- snmp553sDiagRxErrAlm        no         unit               no	major
 -- snmp553sPowerUpAlm          no         unit               no	major
 -- snmp553sNvRamCorrupt        no         unit               no	major
 -- snmp553sUnitFailure         no         unit               no	major
 -- snmp553sMbiLock             Not Supported on 553S
 -- snmp553sLocalPwrFail        Not Supported on 553S
 -- snmp553sTimingLoss          yes        unit               no	major
 -- snmp553sStatusChange        yes        unit               no	other
 -- snmp553sUnsoTest            yes        unit               no	other
 -- snmp553sLossofSignal        yes        net/casc           no	major
 -- snmp553sLossOfFrame         yes        net/casc           no	major
 -- snmp553sAis                 yes        net/casc           no	major
 -- snmp553sReceivedYellow      yes        net/casc           no	minor
 -- snmp553sUnavailSignalstate  yes        net/casc           no	major
 -- snmp553sExcessiveZeros      yes        net only           no	minor
 -- snmp553sLowAverageDensity   yes        net only           no	minor
 -- snmp553sControlledSlips     yes        net only           no	minor
 -- snmp553sBipolarViolations   yes        net/casc           yes	minor
 -- snmp553sCrcErrors           yes        net/casc           yes	minor



-- The Version Group. This group identifies the version information
-- for the MIB.
--
snmp553sMIBversion OBJECT-TYPE
    SYNTAX DisplayString (SIZE (5))
    ACCESS read-only
    STATUS mandatory
    DESCRIPTION
    	"Identifies the version of the MIB. The format of the version
    	is x.yzT, where 'x' identifies the major revision number, 'y'
    	identifies the minor revision number, 'z' identifies the
    	typographical revision, and T identifies the test revision.
    	Acceptable values for the individual revision components are
    	as follows:

    		x: 1 - 9
    		y: 0 - 9
    		z: 0 - 9
    		T: A - Z

    	Upon formal release, no designation for the test revision will
    	be present."
    ::= { snmp553s 2 }

-- The SNMP553S Group.  This group contains objects that support the
-- specific management requirements of the 553S that are not addressed
-- through other standard MIB modules. The group contains four tables:

--		snmp553s Maintenance table
--		SNMP553S Unit Configuration table
--		SNMP553S Channel Configuration  
--		SNMP553S Alarm History table

-- The SNMP553S Maintenance Table.  There is one entry in
-- this table for each managed SNMP553S

snmp553sMaintenanceTable OBJECT-TYPE
    SYNTAX SEQUENCE OF Snmp553sMaintenanceEntry
    ACCESS not-accessible
    STATUS mandatory
    DESCRIPTION
    	"The SNMP553S Maintenance table. This table augments the
    	Gdc Dsx1 maintenance table, providing maintenance functions
	specific to the 553S."
    ::= { snmp553s 3 }

snmp553sMaintenanceEntry OBJECT-TYPE
    SYNTAX Snmp553sMaintenanceEntry
    ACCESS not-accessible
    STATUS mandatory
    DESCRIPTION
    	"The SNMP553S Maintenance table entry."
    INDEX { snmp553sMaintenanceIndex }
    ::= { snmp553sMaintenanceTable 1 }

Snmp553sMaintenanceEntry ::= 
    SEQUENCE {
        snmp553sMaintenanceIndex SCinstance,
        snmp553sCascadePresent INTEGER,
    	snmp553sExtModemPresent INTEGER,
	snmp553sUnitType INTEGER,
        snmp553sManagementSource INTEGER,
	snmp553sProductType INTEGER,
        snmp553sLedStatus OCTET STRING,
	snmp553sUnitSerialNumber OCTET STRING,
	snmp553sSaveAllConfig INTEGER
 }

snmp553sMaintenanceIndex OBJECT-TYPE
    SYNTAX SCinstance
    ACCESS read-only
    STATUS mandatory
    DESCRIPTION
    	"The index value which uniquely identifies the 553S to which
    	this entry is applicable.  This has the form of a SCinstance
    	which defines the slot, line, and drop of the 553S with 
    	sub-identifier value set to unit(1)."
    ::= { snmp553sMaintenanceEntry 1 }

snmp553sCascadePresent OBJECT-TYPE
    SYNTAX INTEGER {
    	notPresent(1),			-- cascade interface not present
    	present(2)			-- cascade interface present
    }
    ACCESS read-only
    STATUS mandatory
    DESCRIPTION
    	"Identifies whether or not the cascade interface cards
    	are installed."
    ::= { snmp553sMaintenanceEntry 2 }

snmp553sExtModemPresent OBJECT-TYPE
    SYNTAX INTEGER {
    	notPresent(1),			-- modem not present
    	present(2)			-- modem present
    }
    ACCESS read-only
    STATUS mandatory
    DESCRIPTION
    	"Identifies whether or not an external modem is attached to the
	modem ppp interface."
    ::= { snmp553sMaintenanceEntry 3 }

snmp553sUnitType OBJECT-TYPE
    SYNTAX INTEGER {
    	master(1),
    	remote(2)
    }
    ACCESS read-only
    STATUS mandatory
    DESCRIPTION
    	"Identifies the GDC Netcon position of the unit. The value master(1)
    	indicates that the NMS unit is configured as a Netcon Master, whereby
	diagnostic management information is received through a local Netcon
	port. The value remote(2) indicates that the unit is configured as a
	Netcon remote, whereby diagnostic management information is received
	through it's network interface or through an out of band (modem) link."
    ::= { snmp553sMaintenanceEntry 4 }

snmp553sManagementSource OBJECT-TYPE
    SYNTAX INTEGER {
    	modemSnmp(1),			-- modem snmp ppp port
    	secondaryChannel(2),		-- secondary channel
    	fdl(3),				-- facility data link
    	daisyChain(4),			-- Netcon daisy chain
    	bus485(5),			-- RS485 bus
	localSnmp(6)			-- local snmp ppp port
    }
    ACCESS read-only
    STATUS mandatory
    DESCRIPTION
    	"Identifies the management data source. The value modemSnmp(1)
	indicates that the management source is SNMP via an dial-up
	ppp link. The value secondaryChannel(2)indicates that the
	management source is via an inband Diagnostics communications
	channel. The value fdl(3) indicates that the management source
	is via the out-of-band facilities data link. The value daisyChain(4)
	indicates that the management source via the NETCON master-in port.
	The value bus485(5) indicates that the management source is via
	the shelf commander in the Universal Systems Shelf. The value
	localSnmp(6) indicates that the management source is SNMP via
	a locap ppp link."
    ::= { snmp553sMaintenanceEntry 5 }

snmp553sProductType OBJECT-TYPE
    SYNTAX INTEGER {
    	snmp553sd1ifp(1),
    	snmp553sd3ifp(2),
	snmp553scifp(3),
	nms553d1(4),
     	nms553d1ifp(5),
   	nms553d3ifp(6),
 	nms553c(7),
	nms553cifp(8)
    }
    ACCESS read-only
    STATUS mandatory
    DESCRIPTION
    	"Indicates the product type of the unit."
    ::= { snmp553sMaintenanceEntry 6 }

snmp553sLedStatus OBJECT-TYPE
    SYNTAX  OCTET STRING (SIZE(3))
    ACCESS  read-only
    STATUS  mandatory
    DESCRIPTION
	"Returns a bitwise snapshot of the front panel LED state.
	Octet 1 bit 7 - not used
		 bit 6 - ON
		 bit 5 - DSX1
		 bit 4 - NMSRSP (nms553 products) or MGMT DATA (553s products)
		 bit 3 - NMSDAT (nms553 products) or MGMT RESP (553s products)
		 bit 2 - ER
		 bit 1 - DSX OOF
		 bit 0 - DSX LOS

	 Octet 2 bit 7 - not used
		 bit 6 - NET OOF
		 bit 5 - NET LOS
		 bit 4 - NET BPV
		 bit 3 - NET AIS
		 bit 2 - TM/ALM
		 bit 1 - LBK
		 bit 0 - future use

 	 Octet 3 bit 7 - not used
		 bit 6 - CHA SD  ==> 553D1 and 553D3 only
		 bit 5 - CHA RD  ==>   ''
		 bit 4 - CHB SD  ==> 553D3 only
		 bit 3 - CHB RD  ==>   ''
		 bit 2 - CHC SD  ==>   ''
		 bit 1 - CHC RD  ==>   ''
		 bit 0 - future use.

	Note: The value returned for all Channel SD and RD leds
	      is unreliable when the unit is performing DSU level
	      self-tests and loopbacks." 
    ::= { snmp553sMaintenanceEntry 7 }

snmp553sUnitSerialNumber OBJECT-TYPE
    SYNTAX  OCTET STRING (SIZE(16))
    ACCESS  read-only
    STATUS  mandatory
    DESCRIPTION
	"This object returns the GDC 8-byte unit serial number in 
        16 nibbles.  Each device has a unique serial number of the
	form:
		00xx0pmmddyy####
	where
		xx =   Product type:
			26 - NMS553C products
			27 - NMS553D products
			43 - 553SD products
			44 - 553SC products
		p  =   Source of Software
			1  - Software programmed by manufacturing
'			9  - Software programmed by engineering
		mm =   Month of manufacture
		dd =   Day of manufacture
		yy =   Year of manufacture
		#### = Daily manufacturing sequence number."
    ::= { snmp553sMaintenanceEntry 8 }

snmp553sSaveAllConfig OBJECT-TYPE
    SYNTAX INTEGER {
	normal(1),              	-- All config vars not saved
	saveConfig(2)                  	-- All config vars saved
    }
    ACCESS read-write
    STATUS mandatory
    DESCRIPTION
    	"Commands unit to save 553S CSU and DSU configuration variables in
        non-volatile memory and configure the unit as defined.

	When CSU and DSU configuration variables are modified they are not
	updated in the 553S hardware until a SaveConfig command
	is received via this object.

	When this value is set to SaveConfig(2) the current 553S
	csu and dsu configuration variables become active within the unit.

	The value of normal(1) will be returned when the 
	initialization is complete. The value normal(1) cannot be
	set by management."

    ::= { snmp553sMaintenanceEntry 9 }

-- The SNMP553S Unit Configuration Table.  There is one entry in
-- this table for each managed SNMP553S

snmp553sUnitConfigTable OBJECT-TYPE
    SYNTAX SEQUENCE OF Snmp553sUnitConfigEntry
    ACCESS not-accessible
    STATUS mandatory
    DESCRIPTION
    	"The SNMP553S Unit Configuration table. This table augments the
    	GDC dsx1 configuration table, providing additional unit level
    	configuration specific to the 553s."
    ::= { snmp553s 4 }

snmp553sUnitConfigEntry OBJECT-TYPE
    SYNTAX Snmp553sUnitConfigEntry
    ACCESS not-accessible
    STATUS mandatory
    DESCRIPTION
    	"The SNMP553S Unit Configuration table entry."
    INDEX { snmp553sUnitConfigIndex }
    ::= { snmp553sUnitConfigTable 1 }

Snmp553sUnitConfigEntry ::= 
    SEQUENCE {
        snmp553sUnitConfigIndex SCinstance,
	snmp553sSaveCsuConfig INTEGER,
        snmp553sShelfCommander INTEGER,
        snmp553sForceFakeMaster INTEGER,
        snmp553sDaisyChainBps INTEGER
 }

snmp553sUnitConfigIndex OBJECT-TYPE
    SYNTAX SCinstance
    ACCESS read-only
    STATUS mandatory
    DESCRIPTION
    	"The index value which uniquely identifies the SNMP553S to which
    	this entry is applicable. This has the form of a SCinstance
    	which defines the slot, line, and drop of 553S with a
    	sub-identifier value of unit(1)."
    ::= { snmp553sUnitConfigEntry 1 }

snmp553sSaveCsuConfig OBJECT-TYPE
    SYNTAX INTEGER {
	normal(1),              	-- CSU config vars not saved
	saveConfig(2)                  	-- CSU config vars saved
    }
    ACCESS read-write
    STATUS mandatory
    DESCRIPTION
    	"Commands unit to save 553S CSU configuration variables in
        non-volatile memory and configure the unit as defined.

	When CSU configuration variables are modified they are not
	updated in the 553S hardware until a SaveConfig command
	is received via this object.

	When this value is set to SaveConfig(2) the current 553S
	csu configuration variables become active within the unit.

	The value of normal(1) will be returned when the 
	initialization is complete. The value normal(1) cannot be
	set by management."

    ::= { snmp553sUnitConfigEntry 2 }


snmp553sShelfCommander OBJECT-TYPE
    SYNTAX INTEGER {
    	disabled(1),			-- Normal mode
    	enabled(2)			-- Unit provides the
    				    	-- diagnostic source for the
    				    	-- shelf via RS485 bus
    }
    ACCESS read-write
    STATUS mandatory
    DESCRIPTION
    	"Identifies the 553s unit as the shelf commander in a
	Datacomm 4-pak or Universal Systems Shelf. When configured
	as the shelf commander, the unit passes the SNMP diagnostics
	information using the Netcon protocol to other units in the
	shelf via the RS485 bus."
    ::= { snmp553sUnitConfigEntry 3 }
    
snmp553sForceFakeMaster OBJECT-TYPE
    SYNTAX INTEGER {
    	enabled(1),			-- Unit is temporary master
    	disabled(2)			-- Normal mode
    }
    ACCESS read-write
    STATUS mandatory
    DESCRIPTION
    	"Forces the 553s as a Netcon Master unit. This option
	allows a unit without a master-in connection to a netcon
	controller behave as a Netcon master for configuring
    	diagnostics on downstream (remote) units."
    ::= { snmp553sUnitConfigEntry 4 }

snmp553sDaisyChainBps OBJECT-TYPE
    SYNTAX INTEGER {
	none(1),			-- no daisy Chain present
    	bps75(2),			-- data rate is 75 bits/sec
    	bps9600(3)			-- data rate is 9600 bits/sec
    }
    ACCESS read-write
    STATUS mandatory
    DESCRIPTION
    	"Indicates the data rate at which a remote unit will propogate
	NMS commands out of a daisy chain connection.  None(1) 
	indicates that no outbound daisy chain exists on this unit."
    ::= { snmp553sUnitConfigEntry 5 }


-- The 553S Channel Configuration Table.  There is one entry in
-- this table for each managed 553S

snmp553sChannelConfigTable OBJECT-TYPE
    SYNTAX SEQUENCE OF Snmp553sChannelConfigEntry
    ACCESS not-accessible
    STATUS mandatory
    DESCRIPTION
    	"The SNMP553S Channel Configuration table.  This table augments the
    	GDC dsu Channel Configuration table,  providing additional unit level
    	configuration specific to the 553s."
    ::= { snmp553s 5 }

snmp553sChannelConfigEntry OBJECT-TYPE
    SYNTAX Snmp553sChannelConfigEntry
    ACCESS not-accessible
    STATUS mandatory
    DESCRIPTION
    	"The SNMP553S Channel Configuration table entry."
    INDEX { snmp553sChannelConfigIndex }
    ::= { snmp553sChannelConfigTable 1 }

Snmp553sChannelConfigEntry ::= 
    SEQUENCE {
        snmp553sChannelConfigIndex SCinstance,
    	snmp553sDCCCompatibilityMode INTEGER,
	snmp553sSaveDsuConfig INTEGER
     }

snmp553sChannelConfigIndex OBJECT-TYPE
    SYNTAX SCinstance
    ACCESS read-only
    STATUS mandatory
    DESCRIPTION
    	"The index value which uniquely identifies the 553S to which
    	this entry is applicable.  This has the form of a SCinstance
    	which defines the slot, line, drop, and channel of the 553S."
    ::= { snmp553sChannelConfigEntry 1 }

snmp553sDCCCompatibilityMode OBJECT-TYPE
    SYNTAX INTEGER {
    	nms553(1),			-- straight 553 functionality
    	nms510(2),			-- NMS510 compatible
    	other(3)
    }
    ACCESS read-write
    STATUS mandatory
    DESCRIPTION
    	"Identifies the 553S DCC mode. The value nms553(1) indicates
	that the inband link is communicating with an NMS553 remote.
	The value nms510(2) indicates that the inband link is
	communicating with an NMS510 remote. This object works with
    	with snmp553sUnitType; it can never be set to nms510(2) unless
    	snmp553sUnitType is master(1).

    	The value other(3) indicates that the compatibility mode has
    	been specified elsewhere. This value can never be set by
    	management operation."
    ::= { snmp553sChannelConfigEntry 2 }

snmp553sSaveDsuConfig OBJECT-TYPE
    SYNTAX INTEGER {
	normal(1),              	-- DSU config vars not saved
	saveConfig(2)                  	-- DSU config vars saved
    }
    ACCESS read-write
    STATUS mandatory
    DESCRIPTION
    	"Commands unit to save 553S channel configuration variables in
        non-volatile memory and configure the unit as defined.
	
	When DSU configuration variables are modified they are not
	updated in the 553S hardware until a SaveConfig command
	is received via this object.

	When this value is set to SaveConfig(2) the current 553S
	dsu configuration variables become active within the unit.

	The value of normal(1) will be returned when the 
	initialization is complete. The value normal(1) cannot be
	set by management."
     ::= { snmp553sChannelConfigEntry 3 }


-- The SNMP553S Diagnostics Table.  There is one entry in
-- this table for each managed SNMP553S

snmp553sDiagTable OBJECT-TYPE
    SYNTAX SEQUENCE OF Snmp553sDiagEntry
    ACCESS not-accessible
    STATUS mandatory
    DESCRIPTION
    	"The 553S Diagnostics table. This table augments the
    	GDC dsx1 Diagnostics table and the GDC dsu diagnostics
	table."
    ::= { snmp553s 6 }

snmp553sDiagEntry OBJECT-TYPE
    SYNTAX Snmp553sDiagEntry
    ACCESS not-accessible
    STATUS mandatory
    DESCRIPTION
    	"The SNMP553S Diagnostics table entry."
    INDEX { snmp553sDiagIndex }
    ::= { snmp553sDiagTable 1 }

Snmp553sDiagEntry ::= 
    SEQUENCE {
        snmp553sDiagIndex SCinstance,
	snmp553sDiagTestDuration INTEGER,
	snmp553sDiagProgPattern INTEGER
 }

snmp553sDiagIndex OBJECT-TYPE
    SYNTAX SCinstance
    ACCESS read-only
    STATUS mandatory
    DESCRIPTION
    	"The index value which uniquely identifies the 553S to which
    	this entry is applicable.  This has the form of a SCinstance
    	which defines the slot, line, and drop of the 553S with a
    	sub-identifier value of unit(1)."
    ::= { snmp553sDiagEntry 1 }


snmp553sDiagTestDuration OBJECT-TYPE
     SYNTAX INTEGER	{
		 noLimit(1),
		 testTime1Min(2),
		 testTime2Mins(3),
		 testTime3Mins(4),
		 testTime4Mins(5),
		 testTime5Mins(6),
		 testTime6Mins(7),
		 testTime7Mins(8),
		 testTime8Mins(9),
		 testTime9Mins(10),
		 testTime10Mins(11),
		 testTime15Mins(12),
		 testTime20Mins(13),
		 testTime25Mins(14),
		 testTime30Mins(15),
		 testTime30Secs(16)
	     }			
     ACCESS read-write
     STATUS mandatory
     DESCRIPTION
	"Selects the duration to run a diagnostic test, in time.
	The value(1) noLimit indicates that the test should run
	until explicitly terminated. The default value is noLimit(1).
	
	This object is used for all tests defined in both the GDC
	dsx1 mib and the GDC dsu mib."
      ::= { snmp553sDiagEntry 2 }

snmp553sDiagProgPattern OBJECT-TYPE
     SYNTAX INTEGER (0..'ffff'h)
     ACCESS read-write
     STATUS mandatory
     DESCRIPTION
     	"The 16 bit user programmable test pattern.  This object
     	works with the  gdcDsx1SendCode object in that when  gdcDsx1SendCode
	is set to sendProgPattern(4), the the value of this object is
	used as the 16 bit user programmable test pattern.

	This object is used for all tests defined in both the GDC
	dsx1 mib."

     ::= { snmp553sDiagEntry 3 }

-- ********************************************************************
-- The GDC snmp553s DSX-1 Alarm History Table
-- ********************************************************************

snmp553sAlarmHistoryTable OBJECT-TYPE
    SYNTAX SEQUENCE OF Snmp553sAlarmHistoryEntry
    ACCESS not-accessible
    STATUS mandatory
    DESCRIPTION
    	"The snmp553sAlarmHistoryTable contains entries that report the
	history of all supported alarms.  The history consists of the
	the number of times the alarm has occurred since last history
	reset, the time of the first alarm occurence (hours,minutes,
	seconds,day,month,year), and the time of the last alarm occurrence
	(hours,minutes,seconds,day,month,year).

        The structure of the table is such that alarm status is
        supported on a unit or interface basis, and then on an alarm
        type basis within the interface.  For simplicity sake and to
        support the reporting of status of all alarms, a unit is
        treated as an interface 1 in this table."
    ::= { snmp553s 7 }

snmp553sAlarmHistoryEntry OBJECT-TYPE
    SYNTAX Snmp553sAlarmHistoryEntry
    ACCESS not-accessible
    STATUS mandatory
    DESCRIPTION
    	"An entry in the GDC SNMP553S Alarm History table."
    INDEX { snmp553sAlarmHistoryIndex, snmp553sAlarmHistoryIdentifier }
    ::= { snmp553sAlarmHistoryTable 1 }

Snmp553sAlarmHistoryEntry ::=
    SEQUENCE {
    	snmp553sAlarmHistoryIndex
    	    SCinstance,
    	snmp553sAlarmHistoryIdentifier
    	    OBJECT IDENTIFIER,
	snmp553sAlarmCount
	    Gauge,
	snmp553sAlarmFirstOccurrenceHours
	    INTEGER,
	snmp553sAlarmFirstOccurrenceMinutes
	    INTEGER,
	snmp553sAlarmFirstOccurrenceSeconds
	    INTEGER,
	snmp553sAlarmFirstOccurrenceMonth
	    INTEGER,
	snmp553sAlarmFirstOccurrenceDay
	    INTEGER,
	snmp553sAlarmFirstOccurrenceYear
	    INTEGER,
	snmp553sAlarmLastOccurrenceHours
	    INTEGER,
	snmp553sAlarmLastOccurrenceMinutes
	    INTEGER,
	snmp553sAlarmLastOccurrenceSeconds
	    INTEGER,
	snmp553sAlarmLastOccurrenceMonth
	    INTEGER,
	snmp553sAlarmLastOccurrenceDay
	    INTEGER,
	snmp553sAlarmLastOccurrenceYear
	    INTEGER
    }

snmp553sAlarmHistoryIndex OBJECT-TYPE
    SYNTAX SCinstance
    ACCESS read-only
    STATUS mandatory
    DESCRIPTION
    	"The index value which uniquely identifies the interface to
    	which this entry is applicable."
    ::= { snmp553sAlarmHistoryEntry 1 }

snmp553sAlarmHistoryIdentifier OBJECT-TYPE
    SYNTAX OBJECT IDENTIFIER
    ACCESS read-only
    STATUS mandatory
    DESCRIPTION
    	"The unique alarm identifier assigned to this alarm type.
    	The format of this identifier is an OBJECT IDENTIFIER that has
    	the following format: {iso(1) org(3) dod(6) internet(1)
    	private(4) enterprises(1) gdc(498) xxx(x) alarm(z) yyy(y) 
	where xxx(x) is the administratively assigned family object 
	identifier (z) is the object identifier for alarms in the family
	defined MIB and yyy(y) is the administratively assigned alarm 
	type identifier for this alarm."
  ::= { snmp553sAlarmHistoryEntry 2 }

snmp553sAlarmCount OBJECT-TYPE
    SYNTAX Gauge
    ACCESS read-only
    STATUS mandatory
    DESCRIPTION
    	"The number of occurrences of this alarm.  This objects value
    	is incremented once for each time that the alarm occurs.  This
    	count is incremented regardless of whether or not the alarm
    	is masked or is not reporteded because of the threshold
    	configuration."
    ::= { snmp553sAlarmHistoryEntry 3 }

snmp553sAlarmFirstOccurrenceHours OBJECT-TYPE
    SYNTAX INTEGER
    ACCESS read-only
    STATUS mandatory
    DESCRIPTION
   	"The hour (0-23) the alarm first occurred." 
    ::= { snmp553sAlarmHistoryEntry 4 }

snmp553sAlarmFirstOccurrenceMinutes OBJECT-TYPE
    SYNTAX INTEGER
    ACCESS read-only
    STATUS mandatory
    DESCRIPTION
   	"The minute (0-59) the alarm first occurred." 
    ::= { snmp553sAlarmHistoryEntry 5 }

snmp553sAlarmFirstOccurrenceSeconds OBJECT-TYPE
    SYNTAX INTEGER
    ACCESS read-only
    STATUS mandatory
    DESCRIPTION
   	"The second (0-59) the alarm first occurred." 
    ::= { snmp553sAlarmHistoryEntry 6 }

snmp553sAlarmFirstOccurrenceMonth OBJECT-TYPE
    SYNTAX INTEGER
    ACCESS read-only
    STATUS mandatory
    DESCRIPTION
   	"The month (1-12) the alarm first occurred." 
    ::= { snmp553sAlarmHistoryEntry 7 }

snmp553sAlarmFirstOccurrenceDay OBJECT-TYPE
    SYNTAX INTEGER
    ACCESS read-only
    STATUS mandatory
    DESCRIPTION
   	"The day (1-31) the alarm first occurred." 
    ::= { snmp553sAlarmHistoryEntry 8 }

snmp553sAlarmFirstOccurrenceYear OBJECT-TYPE
    SYNTAX INTEGER
    ACCESS read-only
    STATUS mandatory
    DESCRIPTION
   	"The year (0-99) the alarm first occurred." 
    ::= { snmp553sAlarmHistoryEntry 9 }

snmp553sAlarmLastOccurrenceHours OBJECT-TYPE
    SYNTAX INTEGER
    ACCESS read-only
    STATUS mandatory
    DESCRIPTION
   	"The hour (0-23) the alarm last occurred." 
    ::= { snmp553sAlarmHistoryEntry 10 }

snmp553sAlarmLastOccurrenceMinutes OBJECT-TYPE
    SYNTAX INTEGER
    ACCESS read-only
    STATUS mandatory
    DESCRIPTION
   	"The minute (0-59) the alarm last occurred." 
    ::= { snmp553sAlarmHistoryEntry 11 }

snmp553sAlarmLastOccurrenceSeconds OBJECT-TYPE
    SYNTAX INTEGER
    ACCESS read-only
    STATUS mandatory
    DESCRIPTION
   	"The second (0-59) the alarm last occurred." 
    ::= { snmp553sAlarmHistoryEntry 12 }

snmp553sAlarmLastOccurrenceMonth OBJECT-TYPE
    SYNTAX INTEGER
    ACCESS read-only
    STATUS mandatory
    DESCRIPTION
   	"The month (1-12) the alarm last occurred." 
    ::= { snmp553sAlarmHistoryEntry 13 }

snmp553sAlarmLastOccurrenceDay OBJECT-TYPE
    SYNTAX INTEGER
    ACCESS read-only
    STATUS mandatory
    DESCRIPTION
   	"The day (1-31) the alarm last occurred." 
    ::= { snmp553sAlarmHistoryEntry 14 }

snmp553sAlarmLastOccurrenceYear OBJECT-TYPE
    SYNTAX INTEGER
    ACCESS read-only
    STATUS mandatory
    DESCRIPTION
   	"The year (0-99) the alarm last occurred." 
    ::= { snmp553sAlarmHistoryEntry 15 }

-- ********************************************************************
-- The GDC snmp553s DSX-1 Alarm Maintenance Table
-- ********************************************************************
snmp553sAlarmMaintenanceTable OBJECT-TYPE
    SYNTAX SEQUENCE OF Snmp553sAlarmMaintenanceEntry
    ACCESS not-accessible
    STATUS mandatory
    DESCRIPTION
    	"The snmp553sAlarmMaintenanceTable contains entries that configure
	the real time clock and that clear the alarm history table."
    ::= { snmp553s 8 }


 snmp553sAlarmMaintenanceEntry OBJECT-TYPE
	 SYNTAX	Snmp553sAlarmMaintenanceEntry
	 ACCESS	not-accessible
	 STATUS	mandatory
	 DESCRIPTION
		 "An entry in the GDC snmp553s Alarm Maintenance Table."
	 INDEX	{ snmp553sAlarmMaintenanceIndex }
	 ::= { snmp553sAlarmMaintenanceTable 1 }

 Snmp553sAlarmMaintenanceEntry ::=
	 SEQUENCE {
		  snmp553sAlarmMaintenanceIndex
			 SCinstance,
		  snmp553sClearAlarmHistory
			 INTEGER,
		  snmp553sRTCHours
			 INTEGER,
		  snmp553sRTCMinutes
			 INTEGER,
		  snmp553sRTCSeconds
			 INTEGER,
		  snmp553sRTCMonth
			 INTEGER,
		  snmp553sRTCDay
			 INTEGER,
		  snmp553sRTCYear
			 INTEGER,
		  snmp553sTimeOfLastAlarmClear
			 OCTET STRING (SIZE(6))
	}

 snmp553sAlarmMaintenanceIndex OBJECT-TYPE
    SYNTAX SCinstance
    ACCESS read-only
    STATUS mandatory
    DESCRIPTION
    	"The index value which uniquely identifies the interface to
    	which this entry is applicable."
    ::= { snmp553sAlarmMaintenanceEntry 1 }

 snmp553sClearAlarmHistory 	OBJECT-TYPE
	 SYNTAX	INTEGER {
			 clear(1),
			 norm(2)
		 }
	 ACCESS	read-write
	 STATUS	mandatory
	 DESCRIPTION
		"Supports the action of clearing the alarm history table.
		When this object is set to clear(1), then the unit clears
		the alarm history table. The value of norm(2) will be
		returned when the clear is complete.
		  
		The value of norm(2) can not be set by management."

	 ::= { snmp553sAlarmMaintenanceEntry 2 }

snmp553sRTCHours OBJECT-TYPE
    SYNTAX INTEGER
    ACCESS read-write
    STATUS mandatory
    DESCRIPTION
   	"The hour of day (0-23) to be set or read." 
    ::= { snmp553sAlarmMaintenanceEntry 3 }

snmp553sRTCMinutes OBJECT-TYPE
    SYNTAX INTEGER
    ACCESS read-write
    STATUS mandatory
    DESCRIPTION
   	"The minute of the hour (0-59) to be set or read." 
    ::= { snmp553sAlarmMaintenanceEntry 4 }

snmp553sRTCSeconds OBJECT-TYPE
    SYNTAX INTEGER
    ACCESS read-write
    STATUS mandatory
    DESCRIPTION
   	"The second of the minute (0-59) to be set or read." 
    ::= { snmp553sAlarmMaintenanceEntry 5 }

snmp553sRTCMonth OBJECT-TYPE
    SYNTAX INTEGER
    ACCESS read-write
    STATUS mandatory
    DESCRIPTION
   	"The month of the year (1-12) to be set or read." 
    ::= { snmp553sAlarmMaintenanceEntry 6 }

snmp553sRTCDay OBJECT-TYPE
    SYNTAX INTEGER
    ACCESS read-write
    STATUS mandatory
    DESCRIPTION
   	"The day of the month (1-31) to be set or read." 
    ::= { snmp553sAlarmMaintenanceEntry 7 }

snmp553sRTCYear OBJECT-TYPE
    SYNTAX INTEGER
    ACCESS read-write
    STATUS mandatory
    DESCRIPTION
   	"The year (0-99) to be set or read." 
    ::= { snmp553sAlarmMaintenanceEntry 8 }

snmp553sTimeOfLastAlarmClear OBJECT-TYPE
    SYNTAX OCTET STRING (SIZE(6))
    ACCESS  read-only
    STATUS  mandatory
    DESCRIPTION
	"Returns the time (hours,minutes,seconds,month,day,year) of
	the last alarm clear command sent to the unit.
	Octet 1 - Hour of last alarm clear (0-23)
	Octet 2 - Minute of last alarm clear (0-59)
	Octet 3 - Second of last alarm clear (0-59)
	Octet 4 - Month of last alarm clear (1-12)
	Octet 5 - Day of last alarm clear (1-31)
	Octet 6 - Year of last alarm clear (0-99)." 
    ::= { snmp553sAlarmMaintenanceEntry 9 }
END
