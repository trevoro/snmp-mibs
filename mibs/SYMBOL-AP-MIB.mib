--
-- SYMBOL-AP-MIB-01g13.mib
-- MIB generated by MG-SOFT Visual MIB Builder Version 6.0  Build 88
-- Wednesday, December 30, 2009 at 13:37:26
--

-- 
-- Notes for AP5131 MIB:
-- 
-- === v2.1.0.0, (MIB='01e'):
-- 
-- Values 'apRadioCfgRfFunction', 'apWipsPrimaryServerAddr', and 'apWipsSecondaryServerAddr' Added.
-- 
-- === v2.0.0.0, (MIB='03d'):
-- 
-- Value 'apRadioSettingsQBSSLoadElementMode' Added.
-- 
-- === v2.0.0.0, (MIB='02d'):
-- 
-- Value 'apRadiusServer' Added.
-- (To support AAA Time based access policy rules)
-- 
-- === v2.0.0.0, (MIB='01d'):
-- 
-- Value 'apWlanWeight' is obsoleted
-- (Refer to apRadioWlanWeight).
-- 
-- === v1.1.1.0, (MIB='01c'):
-- 
-- This MIB can now be used for both AP5131 and AP5181.
-- 
-- New sysoid is introduced for AP5181.
-- 
-- Table 'apWanDynDNS' added to support DynDNS feature.
-- 
-- Mesh Time Out Changes: In a dual-radio AP, if the radio running as a client bridge (CB) does not have an uplink connection to the base bridge (BB) after the Timeout period (in seconds), stop the other radio from sending beacons.
-- 
-- Login Message Feature added: User can now configure a Login message text which gets displayed on successful login. This feature can be turned ON/OFF with Login message mode settings.
-- 
-- 
-- 
-- === v1.1, (MIB='01b'):
-- 
-- Value 'apLanEnable' is deprecated (We shall be using the
-- ccSubnetEnable from the WS2000 MIB for this operation).
-- 
-- Value 'apLanVlanEnable' is obsoleted
-- (Refer to apSubnetVlanTable).
-- 
-- Value 'apLanTypeFilterAccessMode' is obsoleted
-- (Refer to apSubnetTypeFilterAccessMode).
-- 
-- Added another index 'apLanTypeFilterSubnetIndex' in the
-- apLanTypeFilterTable.
-- 
-- 
-- === v1.0, (MIB='01a'):
-- 
-- (no notes at this time).

	SYMBOL-AP-MIB DEFINITIONS ::= BEGIN
 
		IMPORTS
			OBJECT-GROUP, NOTIFICATION-GROUP			
				FROM SNMPv2-CONF			
			enterprises, TimeTicks, IpAddress, Integer32, Unsigned32, 
			Counter32, OBJECT-TYPE, MODULE-IDENTITY, OBJECT-IDENTITY, 
			NOTIFICATION-TYPE			
				FROM SNMPv2-SMI			
			DisplayString, TruthValue, TestAndIncr, PhysAddress, TEXTUAL-CONVENTION			
				FROM SNMPv2-TC			
			ccWanVpnEntry, ccSubnetEntry, ccPortalIndex, ccMuMac, ccWlanIndex, 
			ccMuWlanIndex, ccMuWlanName, ccMuIsDataReady, ccMuPortalIndex, ccMuPortalMac, 
			ccMuSymbolRogueApEna, ccMuIpAddr, ccMuType, ccMuRadioType, ccMuSupportedRates, 
			ccMuPowerMode, ccMuAuthenticationMethod, ccMuEncryptionMethod, ccMuVlanId, ccMuMeshMode, 
			ccMuTxPktsUcast, ccMuRxPktsUcast, ccMuRxPktsNUcast, ccMuTxOctetsUcast, ccMuRxOctetsUcast, 
			ccMuRxOctetsNUcast, ccMuRxUndecryptablePkts, ccMuRxRssiNumPkts, ccMuRxRssiSum, ccMuRxRssiSumSquares, 
			ccMuRxRssiMostRecent, ccMuLastActivity, ccMuRxPktsAt1Mb, ccMuRxPktsAt2Mb, ccMuRxPktsAt5pt5Mb, 
			ccMuRxPktsAt6Mb, ccMuRxPktsAt9Mb, ccMuRxPktsAt11Mb, ccMuRxPktsAt12Mb, ccMuRxPktsAt18Mb, 
			ccMuRxPktsAt22Mb, ccMuRxPktsAt24Mb, ccMuRxPktsAt36Mb, ccMuRxPktsAt48Mb, ccMuRxPktsAt54Mb, 
			ccMuTxPktsAt1Mb, ccMuTxPktsAt2Mb, ccMuTxPktsAt5pt5Mb, ccMuTxPktsAt6Mb, ccMuTxPktsAt9Mb, 
			ccMuTxPktsAt11Mb, ccMuTxPktsAt12Mb, ccMuTxPktsAt18Mb, ccMuTxPktsAt22Mb, ccMuTxPktsAt24Mb, 
			ccMuTxPktsAt36Mb, ccMuTxPktsAt48Mb, ccMuTxPktsAt54Mb, ccMuRxOctetsAt1Mb, ccMuRxOctetsAt2Mb, 
			ccMuRxOctetsAt5pt5Mb, ccMuRxOctetsAt6Mb, ccMuRxOctetsAt9Mb, ccMuRxOctetsAt11Mb, ccMuRxOctetsAt12Mb, 
			ccMuRxOctetsAt18Mb, ccMuRxOctetsAt22Mb, ccMuRxOctetsAt24Mb, ccMuRxOctetsAt36Mb, ccMuRxOctetsAt48Mb, 
			ccMuRxOctetsAt54Mb, ccMuTxOctetsAt1Mb, ccMuTxOctetsAt2Mb, ccMuTxOctetsAt5pt5Mb, ccMuTxOctetsAt6Mb, 
			ccMuTxOctetsAt9Mb, ccMuTxOctetsAt11Mb, ccMuTxOctetsAt12Mb, ccMuTxOctetsAt18Mb, ccMuTxOctetsAt22Mb, 
			ccMuTxOctetsAt24Mb, ccMuTxOctetsAt36Mb, ccMuTxOctetsAt48Mb, ccMuTxOctetsAt54Mb, ccMuTxRetriesNone, 
			ccMuTxRetries01, ccMuTxRetries02, ccMuTxRetries03, ccMuTxRetries04, ccMuTxRetries05, 
			ccMuTxRetries06, ccMuTxRetries07, ccMuTxRetries08, ccMuTxRetries09, ccMuTxRetries10, 
			ccMuTxRetries11, ccMuTxRetries12, ccMuTxRetries13, ccMuTxRetries14, ccMuTxRetries15, 
			ccMuTxRetriesFailed, ccMuTxRetriesTotal, ccMuTxRetriesMostRecent, ccMuLastMac, ccMuLastReason, 
			ccMuLastPortal, ccMuTxRetriesOctetsNone, ccMuTxRetriesOctets01, ccMuTxRetriesOctets02, ccMuTxRetriesOctets03, 
			ccMuTxRetriesOctets04, ccMuTxRetriesOctets05, ccMuTxRetriesOctets06, ccMuTxRetriesOctets07, ccMuTxRetriesOctets08, 
			ccMuTxRetriesOctets09, ccMuTxRetriesOctets10, ccMuTxRetriesOctets11, ccMuTxRetriesOctets12, ccMuTxRetriesOctets13, 
			ccMuTxRetriesOctets14, ccMuTxRetriesOctets15, ccMuTxRetriesOctetsFailed, ccMuSigStatsNumPkts, ccMuSigStatsSignalBest, 
			ccMuSigStatsSignalWorst, ccMuSigStatsSignalSum, ccMuSigStatsSignalSumSquares, ccMuSigStatsSignalMostRecent, ccMuSigStatsNoiseBest, 
			ccMuSigStatsNoiseWorst, ccMuSigStatsNoiseSum, ccMuSigStatsNoiseSumSquares, ccMuSigStatsNoiseMostRecent, ccMuSigStatsSnrBest, 
			ccMuSigStatsSnrWorst, ccMuSigStatsSnrSum, ccMuSigStatsSnrSumSquares, ccMuSigStatsSnrMostRecent, ccMuSumStatsShortTimestamp, 
			ccMuSumStatsShortNumPkts, ccMuSumStatsShortPktsPerSec100, ccMuSumStatsShortPktsPerSecTx100, ccMuSumStatsShortPktsPerSecRx100, ccMuSumStatsShortThroughput, 
			ccMuSumStatsShortThroughputTx, ccMuSumStatsShortThroughputRx, ccMuSumStatsShortAvgBitSpeed, ccMuSumStatsShortAvgMuSignal, ccMuSumStatsShortAvgMuNoise, 
			ccMuSumStatsShortAvgMuSnr, ccMuSumStatsShortPp10kNUcastPkts, ccMuSumStatsShortPp10kTxWithRetries, ccMuSumStatsShortPp10kDropped, ccMuSumStatsShortTxAvgRetries100, 
			ccMuSumStatsShortPp10kRxUndecrypt, ccMuSumStatsLongTimestamp, ccMuSumStatsLongNumPkts, ccMuSumStatsLongPktsPerSec100, ccMuSumStatsLongPktsPerSecTx100, 
			ccMuSumStatsLongPktsPerSecRx100, ccMuSumStatsLongThroughput, ccMuSumStatsLongThroughputTx, ccMuSumStatsLongThroughputRx, ccMuSumStatsLongAvgBitSpeed, 
			ccMuSumStatsLongAvgMuSignal, ccMuSumStatsLongAvgMuNoise, ccMuSumStatsLongAvgMuSnr, ccMuSumStatsLongPp10kNUcastPkts, ccMuSumStatsLongPp10kTxWithRetries, 
			ccMuSumStatsLongPp10kDropped, ccMuSumStatsLongTxAvgRetries100, ccMuSumStatsLongPp10kRxUndecrypt, ccWlanName, ccWlanEssid, 
			ccWlanSubnet, ccWlanPortalsAdopted, ccWlanEnable, ccWlanDisallowMuToMu, ccWlanVoicePrioritization, 
			ccWlanAnswerBroadcastEss, ccWlanMulticastAddr1, ccWlanMulticastAddr2, ccWlanMuAclDefault, ccWlanAuthentication, 
			ccWlanEncryption, ccWlanWeight, ccWlanSecBeacon, ccWlanVlanId, ccWlanThresholdRate, 
			ccWlanAuthEapReauthenticationEnable, ccWlanAuthEapReauthenticationPeriod, ccWlanAuthEapReauthenticationMaxRetries, ccWlanAuthEapRadius1Server, ccWlanAuthEapRadius1Port, 
			ccWlanAuthEapRadius1SharedSecret, ccWlanAuthEapRadius2Server, ccWlanAuthEapRadius2Port, ccWlanAuthEapRadius2SharedSecret, ccWlanAuthEapMuQuietPeriod, 
			ccWlanAuthEapMuTimeout, ccWlanAuthEapMuTxPeriod, ccWlanAuthEapMuMaxRetries, ccWlanAuthEapServerTimeout, ccWlanAuthEapServerMaxRetries, 
			ccWlanAuthEapRadiusAcctMode, ccWlanAuthEapRadiusAcctMuTimeout, ccWlanAuthEapRadiusAcctMuRetries, ccWlanAuthEapSyslogMode, ccWlanAuthEapSyslogSeverIp, 
			ccWlanAuthKerberosRealmName, ccWlanAuthKerberosUsername, ccWlanAuthKerberosPassword, ccWlanAuthKerberosKdcServerIp1, ccWlanAuthKerberosKdcPort1, 
			ccWlanAuthKerberosKdcServerIp2, ccWlanAuthKerberosKdcPort2, ccWlanAuthKerberosKdcServerIpR, ccWlanAuthKerberosKdcPortR, ccWlanCryptoWepPassKey, 
			ccWlanCryptoWepKey1, ccWlanCryptoWepKey2, ccWlanCryptoWepKey3, ccWlanCryptoWepKey4, ccWlanCryptoWepKeyToUse, 
			ccWlanCryptoWpaBcastKeyRotation, ccWlanCryptoWpaKeyRotationInterval, ccWlanCryptoWpaKeyToUse, ccWlanCryptoWpaPassphrase, ccWlanCryptoWpaKey, 
			ccWlanCryptoUseWpa2, ccWlanCryptoKeyguardPasskey, ccWlanCryptoKeyguardKey1, ccWlanCryptoKeyguardKey2, ccWlanCryptoKeyguardKey3, 
			ccWlanCryptoKeyguardKey4, ccWlanCryptoKeyguardKeyToUse, ccWlanCryptoWpaTwoBcastKeyRotation, ccWlanCryptoWpaTwoKeyRotationInterval, ccWlanCryptoWpaTwoKeyToUse, 
			ccWlanCryptoWpaTwoPassphrase, ccWlanCryptoWpaTwoKey, ccWlanCryptoWpaTwoAllowTkipClient, ccWlanCryptoWpaTwoFastRoamPreAuth, ccWlanCryptoWpaTwoFastRoamKeyCache, 
			ccWlanMuAclIndex, ccWlanMuAclStartingMac, ccWlanMuAclEndingMac, ccWlanMuAclRowStatus, ccWlanMuAclName, 
			ccWlanBwShareMode, ccWlanQosMonitorSent, ccWlanQosMonitorDropped, ccWlanQosWMEProfileIndex, ccWlanQosWMEProfileName, 
			ccWlanQosWMEProfileBestEffortECwmin, ccWlanQosWMEProfileBestEffortECwmax, ccWlanQosWMEProfileBestEffortAifsn, ccWlanQosWMEProfileBestEffortTxopsTime, ccWlanQosWMEProfileBackgroundECwmin, 
			ccWlanQosWMEProfileBackgroundECwmax, ccWlanQosWMEProfileBackgroundAifsn, ccWlanQosWMEProfileBackgroundTxopsTime, ccWlanQosWMEProfileVideoECwmin, ccWlanQosWMEProfileVideoECwmax, 
			ccWlanQosWMEProfileVideoAifsn, ccWlanQosWMEProfileVideoTxopsTime, ccWlanQosWMEProfileVoiceECwmin, ccWlanQosWMEProfileVoiceECwmax, ccWlanQosWMEProfileVoiceAifsn, 
			ccWlanQosWMEProfileVoiceTxopsTime, ccWlanQosWMEProfileRowStatus, ccWlanQosWMEWlanProfile, ccWlanQosWMETrafficIndex, ccWlanQosWMETrafficSrcIp, 
			ccWlanQosWMETrafficSrcMask, ccWlanQosWMETrafficDestIp, ccWlanQosWMETrafficDestMask, ccWlanQosWMETrafficSrcPortStart, ccWlanQosWMETrafficSrcPortEnd, 
			ccWlanQosWMETrafficDestPortStart, ccWlanQosWMETrafficDestPortEnd, ccWlanQosWMETrafficAccessCategory, ccWlanQosWMETrafficRowStatus, ccWlanQosWMEPriorityConversion, 
			ccWlanMuInactivityTimeout, ccWlanWEPSharedMode, ccWlanTxPktsUcast, ccWlanRxPktsUcast, ccWlanRxPktsNUcast, 
			ccWlanTxOctetsUcast, ccWlanRxOctetsUcast, ccWlanRxOctetsNUcast, ccWlanRxUndecryptablePkts, ccWlanLastActivity, 
			ccWlanRxPktsAt1Mb, ccWlanRxPktsAt2Mb, ccWlanRxPktsAt5pt5Mb, ccWlanRxPktsAt6Mb, ccWlanRxPktsAt9Mb, 
			ccWlanRxPktsAt11Mb, ccWlanRxPktsAt12Mb, ccWlanRxPktsAt18Mb, ccWlanRxPktsAt22Mb, ccWlanRxPktsAt24Mb, 
			ccWlanRxPktsAt36Mb, ccWlanRxPktsAt48Mb, ccWlanRxPktsAt54Mb, ccWlanTxPktsAt1Mb, ccWlanTxPktsAt2Mb, 
			ccWlanTxPktsAt5pt5Mb, ccWlanTxPktsAt6Mb, ccWlanTxPktsAt9Mb, ccWlanTxPktsAt11Mb, ccWlanTxPktsAt12Mb, 
			ccWlanTxPktsAt18Mb, ccWlanTxPktsAt22Mb, ccWlanTxPktsAt24Mb, ccWlanTxPktsAt36Mb, ccWlanTxPktsAt48Mb, 
			ccWlanTxPktsAt54Mb, ccWlanRxOctetsAt1Mb, ccWlanRxOctetsAt2Mb, ccWlanRxOctetsAt5pt5Mb, ccWlanRxOctetsAt6Mb, 
			ccWlanRxOctetsAt9Mb, ccWlanRxOctetsAt11Mb, ccWlanRxOctetsAt12Mb, ccWlanRxOctetsAt18Mb, ccWlanRxOctetsAt22Mb, 
			ccWlanRxOctetsAt24Mb, ccWlanRxOctetsAt36Mb, ccWlanRxOctetsAt48Mb, ccWlanRxOctetsAt54Mb, ccWlanTxOctetsAt1Mb, 
			ccWlanTxOctetsAt2Mb, ccWlanTxOctetsAt5pt5Mb, ccWlanTxOctetsAt6Mb, ccWlanTxOctetsAt9Mb, ccWlanTxOctetsAt11Mb, 
			ccWlanTxOctetsAt12Mb, ccWlanTxOctetsAt18Mb, ccWlanTxOctetsAt22Mb, ccWlanTxOctetsAt24Mb, ccWlanTxOctetsAt36Mb, 
			ccWlanTxOctetsAt48Mb, ccWlanTxOctetsAt54Mb, ccWlanTxRetriesPktsNone, ccWlanTxRetriesPkts01, ccWlanTxRetriesPkts02, 
			ccWlanTxRetriesPkts03, ccWlanTxRetriesPkts04, ccWlanTxRetriesPkts05, ccWlanTxRetriesPkts06, ccWlanTxRetriesPkts07, 
			ccWlanTxRetriesPkts08, ccWlanTxRetriesPkts09, ccWlanTxRetriesPkts10, ccWlanTxRetriesPkts11, ccWlanTxRetriesPkts12, 
			ccWlanTxRetriesPkts13, ccWlanTxRetriesPkts14, ccWlanTxRetriesPkts15, ccWlanTxRetriesPktsFailed, ccWlanTxRetriesOctetsNone, 
			ccWlanTxRetriesOctets01, ccWlanTxRetriesOctets02, ccWlanTxRetriesOctets03, ccWlanTxRetriesOctets04, ccWlanTxRetriesOctets05, 
			ccWlanTxRetriesOctets06, ccWlanTxRetriesOctets07, ccWlanTxRetriesOctets08, ccWlanTxRetriesOctets09, ccWlanTxRetriesOctets10, 
			ccWlanTxRetriesOctets11, ccWlanTxRetriesOctets12, ccWlanTxRetriesOctets13, ccWlanTxRetriesOctets14, ccWlanTxRetriesOctets15, 
			ccWlanTxRetriesOctetsFailed, ccWlanSigStatsNumPkts, ccWlanSigStatsSignalBest, ccWlanSigStatsSignalWorst, ccWlanSigStatsSignalSum, 
			ccWlanSigStatsSignalSumSquares, ccWlanSigStatsNoiseBest, ccWlanSigStatsNoiseWorst, ccWlanSigStatsNoiseSum, ccWlanSigStatsNoiseSumSquares, 
			ccWlanSigStatsSnrBest, ccWlanSigStatsSnrWorst, ccWlanSigStatsSnrSum, ccWlanSigStatsSnrSumSquares, ccWlanSumStatsShortTimestamp, 
			ccWlanSumStatsShortNumPkts, ccWlanSumStatsShortPktsPerSec100, ccWlanSumStatsShortPktsPerSecTx100, ccWlanSumStatsShortPktsPerSecRx100, ccWlanSumStatsShortThroughput, 
			ccWlanSumStatsShortThroughputTx, ccWlanSumStatsShortThroughputRx, ccWlanSumStatsShortAvgBitSpeed, ccWlanSumStatsShortAvgMuSignal, ccWlanSumStatsShortAvgMuNoise, 
			ccWlanSumStatsShortAvgMuSnr, ccWlanSumStatsShortPp10kNUcastPkts, ccWlanSumStatsShortPp10kTxWithRetries, ccWlanSumStatsShortPp10kDropped, ccWlanSumStatsShortTxAvgRetries100, 
			ccWlanSumStatsShortPp10kRxUndecrypt, ccWlanSumStatsShortTotalMus, ccWlanSumStatsShortSkip1, ccWlanSumStatsLongTimestamp, ccWlanSumStatsLongNumPkts, 
			ccWlanSumStatsLongPktsPerSec100, ccWlanSumStatsLongPktsPerSecTx100, ccWlanSumStatsLongPktsPerSecRx100, ccWlanSumStatsLongThroughput, ccWlanSumStatsLongThroughputTx, 
			ccWlanSumStatsLongThroughputRx, ccWlanSumStatsLongAvgBitSpeed, ccWlanSumStatsLongAvgMuSignal, ccWlanSumStatsLongAvgMuNoise, ccWlanSumStatsLongAvgMuSnr, 
			ccWlanSumStatsLongPp10kNUcastPkts, ccWlanSumStatsLongPp10kTxWithRetries, ccWlanSumStatsLongPp10kDropped, ccWlanSumStatsLongTxAvgRetries100, ccWlanSumStatsLongPp10kRxUndecrypt, 
			ccWlanSumStatsLongTotalMus, ccWlanSumStatsLongSkip1, ccPortalPointerToAp, ccPortalPointersToWlans, ccPortalName, 
			ccPortalLocation, ccPortalOptions, ccPortalMac, ccPortalNumberOfEss, ccPortalNumberOfBss, 
			ccPortalAssociatedMus, ccPortalRadioType, ccPortalChannel, ccPortalTxPowerLevel, ccPortalLastAdoption, 
			ccPortalState, ccPortalBackgroundNoiseNumSamples, ccPortalBackgroundNoiseBest, ccPortalBackgroundNoiseWorst, ccPortalBackgroundNoiseSum, 
			ccPortalBackgroundNoiseSumSquares, ccPortalIpAddress, ccPortalModeLegacy, ccPortalLastMac, ccPortalLastReason, 
			ccPortalAdoptionIndex, ccPortalAdoptionStartMac, ccPortalAdoptionEndMac, ccPortalAdoptionWlanPointers, ccPortalAdoptionRowStatus, 
			ccPortalSystemStatsBeaconsTx, ccPortalSystemStatsBeaconsTxOctets, ccPortalSystemStatsProbeReqRx, ccPortalSystemStatsProbeReqRxOctets, ccPortalSystemStatsProbeRespRetriesNone, 
			ccPortalSystemStatsProbeRespRetries1, ccPortalSystemStatsProbeRespRetries2, ccPortalSystemStatsProbeRespRetries3OrMore, ccPortalSystemStatsProbeRespRetriesFailed, ccPortalSystemStatsProbeRespTxOctets, 
			ccPortalSettingsName, ccPortalSettingsLocation, ccPortalSettingsAntenna, ccPortalSettingsShortPreamble, ccPortalSettingsUniSpread, 
			ccPortalSettingsRtsThresh, ccPortalSettingsBeaconInt, ccPortalSettingsDtimPrd, ccPortalSettingsSecBeacon, ccPortalSettingsPriWlan, 
			ccPortalSettingsBasicRates, ccPortalSettingsSupportedRates, ccPortalSettingsBGMode, ccPortalSettingsAdoptedWlan, ccPortalSettingsDetector, 
			ccPortalSettingsWMEProfile, ccPortalSettingsDtimPrd2, ccPortalSettingsDtimPrd3, ccPortalSettingsDtimPrd4, ccPortalSettingsRevertAp, 
			ccPortalSettingsSipAllowedSessCnt, ccPortalSettingsSipActiveSessCnt, ccPortalSettingsSipInActiveSessCnt, ccPortalSettingsSipRoamedSessCnt, ccPortalSettingsMeshClientEnable, 
			ccPortalSettingsMeshClientWlanIndex, ccPortalSettingsMeshAutoBaseSelection, ccPortalSettingsMeshBaseChannel, ccPortalSettingsMeshBaseEnable, ccPortalSettingsMeshMaxClients, 
			ccPortalCfgRadioDesPlacement, ccPortalCfgRadioPosChannel, ccPortalCfgRadioDesChannel, ccPortalCfgRadioPosPowerLevel, ccPortalCfgRadioDesPowerLevel, 
			ccPortalCfgRadioDesPowerInMW, ccPortalCfgRadioSet, ccPortalCfgRadioReset, ccPortalCfgRadioPlacement, ccPortalCfgRadioChannel, 
			ccPortalCfgRadioPowerLevel, ccPortalCfgRadioPowerInMW, ccPortalCfgRadioChannelMode, ccPortalCfgRadioRemapChannel, ccPortalSettingsDefaultIndex, 
			ccPortalSettingsDefaultAntenna, ccPortalSettingsDefaultShortPreamble, ccPortalSettingsDefaultUniSpread, ccPortalSettingsDefaultRtsThresh, ccPortalSettingsDefaultBeaconInt, 
			ccPortalSettingsDefaultDtimPrd, ccPortalSettingsDefaultSecBeacon, ccPortalSettingsDefaultPriWlan, ccPortalSettingsDefaultBasicRates, ccPortalSettingsDefaultSupportedRates, 
			ccPortalSettingsDefaultBGMode, ccPortalSettingsDefaultDtimPrd2, ccPortalSettingsDefaultDtimPrd3, ccPortalSettingsDefaultDtimPrd4, ccPortalCfgRadioDefaultDesPlacement, 
			ccPortalCfgRadioDefaultPosChannel, ccPortalCfgRadioDefaultDesChannel, ccPortalCfgRadioDefaultPosPowerLevel, ccPortalCfgRadioDefaultDesPowerLevel, ccPortalCfgRadioDefaultDesPowerInMW, 
			ccPortalCfgRadioDefaultSet, ccPortalCfgRadioDefaultReset, ccPortalCfgRadioDefaultPlacement, ccPortalCfgRadioDefaultChannel, ccPortalCfgRadioDefaultPowerLevel, 
			ccPortalCfgRadioDefaultPowerInMW, ccPortalCfgRadioDefaultChannelMode, cc802dt1xPortAuthLogin, cc802dt1xPortAuthPass, cc802dt1xPortAuthSetAp300, 
			ccPortalRadioRemapChannel, ccPortalSIPCacMode, ccPortalMeshAvailableBaseMac, ccPortalMeshAvailableBaseChannel, ccPortalMeshAvailableBaseRssi, 
			ccPortalMeshPreferredBaseMac, ccPortalMeshPreferredBaseRowStatus, ccPortalTxPktsUcast, ccPortalRxPktsUcast, ccPortalRxPktsNUcast, 
			ccPortalTxOctetsUcast, ccPortalRxOctetsUcast, ccPortalRxOctetsNUcast, ccPortalRxUndecryptablePkts, ccPortalLastActivity, 
			ccPortalRxPktsAt1Mb, ccPortalRxPktsAt2Mb, ccPortalRxPktsAt5pt5Mb, ccPortalRxPktsAt6Mb, ccPortalRxPktsAt9Mb, 
			ccPortalRxPktsAt11Mb, ccPortalRxPktsAt12Mb, ccPortalRxPktsAt18Mb, ccPortalRxPktsAt22Mb, ccPortalRxPktsAt24Mb, 
			ccPortalRxPktsAt36Mb, ccPortalRxPktsAt48Mb, ccPortalRxPktsAt54Mb, ccPortalTxPktsAt1Mb, ccPortalTxPktsAt2Mb, 
			ccPortalTxPktsAt5pt5Mb, ccPortalTxPktsAt6Mb, ccPortalTxPktsAt9Mb, ccPortalTxPktsAt11Mb, ccPortalTxPktsAt12Mb, 
			ccPortalTxPktsAt18Mb, ccPortalTxPktsAt22Mb, ccPortalTxPktsAt24Mb, ccPortalTxPktsAt36Mb, ccPortalTxPktsAt48Mb, 
			ccPortalTxPktsAt54Mb, ccPortalRxOctetsAt1Mb, ccPortalRxOctetsAt2Mb, ccPortalRxOctetsAt5pt5Mb, ccPortalRxOctetsAt6Mb, 
			ccPortalRxOctetsAt9Mb, ccPortalRxOctetsAt11Mb, ccPortalRxOctetsAt12Mb, ccPortalRxOctetsAt18Mb, ccPortalRxOctetsAt22Mb, 
			ccPortalRxOctetsAt24Mb, ccPortalRxOctetsAt36Mb, ccPortalRxOctetsAt48Mb, ccPortalRxOctetsAt54Mb, ccPortalTxOctetsAt1Mb, 
			ccPortalTxOctetsAt2Mb, ccPortalTxOctetsAt5pt5Mb, ccPortalTxOctetsAt6Mb, ccPortalTxOctetsAt9Mb, ccPortalTxOctetsAt11Mb, 
			ccPortalTxOctetsAt12Mb, ccPortalTxOctetsAt18Mb, ccPortalTxOctetsAt22Mb, ccPortalTxOctetsAt24Mb, ccPortalTxOctetsAt36Mb, 
			ccPortalTxOctetsAt48Mb, ccPortalTxOctetsAt54Mb, ccPortalTxRetriesPktsNone, ccPortalTxRetriesPkts01, ccPortalTxRetriesPkts02, 
			ccPortalTxRetriesPkts03, ccPortalTxRetriesPkts04, ccPortalTxRetriesPkts05, ccPortalTxRetriesPkts06, ccPortalTxRetriesPkts07, 
			ccPortalTxRetriesPkts08, ccPortalTxRetriesPkts09, ccPortalTxRetriesPkts10, ccPortalTxRetriesPkts11, ccPortalTxRetriesPkts12, 
			ccPortalTxRetriesPkts13, ccPortalTxRetriesPkts14, ccPortalTxRetriesPkts15, ccPortalTxRetriesPktsFailed, ccPortalTxRetriesOctetsNone, 
			ccPortalTxRetriesOctets01, ccPortalTxRetriesOctets02, ccPortalTxRetriesOctets03, ccPortalTxRetriesOctets04, ccPortalTxRetriesOctets05, 
			ccPortalTxRetriesOctets06, ccPortalTxRetriesOctets07, ccPortalTxRetriesOctets08, ccPortalTxRetriesOctets09, ccPortalTxRetriesOctets10, 
			ccPortalTxRetriesOctets11, ccPortalTxRetriesOctets12, ccPortalTxRetriesOctets13, ccPortalTxRetriesOctets14, ccPortalTxRetriesOctets15, 
			ccPortalTxRetriesOctetsFailed, ccPortalSigStatsNumPkts, ccPortalSigStatsSignalBest, ccPortalSigStatsSignalWorst, ccPortalSigStatsSignalSum, 
			ccPortalSigStatsSignalSumSquares, ccPortalSigStatsSignalMostRecent, ccPortalSigStatsNoiseBest, ccPortalSigStatsNoiseWorst, ccPortalSigStatsNoiseSum, 
			ccPortalSigStatsNoiseSumSquares, ccPortalSigStatsNoiseMostRecent, ccPortalSigStatsSnrBest, ccPortalSigStatsSnrWorst, ccPortalSigStatsSnrSum, 
			ccPortalSigStatsSnrSumSquares, ccPortalSigStatsSnrMostRecent, ccPortalSumStatsShortTimestamp, ccPortalSumStatsShortNumPkts, ccPortalSumStatsShortPktsPerSec100, 
			ccPortalSumStatsShortPktsPerSecTx100, ccPortalSumStatsShortPktsPerSecRx100, ccPortalSumStatsShortThroughput, ccPortalSumStatsShortThroughputTx, ccPortalSumStatsShortThroughputRx, 
			ccPortalSumStatsShortAvgBitSpeed, ccPortalSumStatsShortAvgMuSignal, ccPortalSumStatsShortAvgMuNoise, ccPortalSumStatsShortAvgMuSnr, ccPortalSumStatsShortPp10kNUcastPkts, 
			ccPortalSumStatsShortPp10kTxWithRetries, ccPortalSumStatsShortPp10kTxMaxRetries, ccPortalSumStatsShortTxAvgRetries100, ccPortalSumStatsShortPp10kRxUndecrypt, ccPortalSumStatsShortTotalMus, 
			ccPortalSumStatsShortPp10kRfUtil, ccPortalSumStatsShortPp10kDropped, ccPortalSumStatsLongTimestamp, ccPortalSumStatsLongNumPkts, ccPortalSumStatsLongPktsPerSec100, 
			ccPortalSumStatsLongPktsPerSecTx100, ccPortalSumStatsLongPktsPerSecRx100, ccPortalSumStatsLongThroughput, ccPortalSumStatsLongThroughputTx, ccPortalSumStatsLongThroughputRx, 
			ccPortalSumStatsLongAvgBitSpeed, ccPortalSumStatsLongAvgMuSignal, ccPortalSumStatsLongAvgMuNoise, ccPortalSumStatsLongAvgMuSnr, ccPortalSumStatsLongPp10kNUcastPkts, 
			ccPortalSumStatsLongPp10kTxWithRetries, ccPortalSumStatsLongPp10kTxMaxRetries, ccPortalSumStatsLongTxAvgRetries100, ccPortalSumStatsLongPp10kRxUndecrypt, ccPortalSumStatsLongTotalMus, 
			ccPortalSumStatsLongPp10kRfUtil, ccPortalSumStatsLongPp10kDropped, ccPortalLegacyMode			
				FROM SYMBOL-CC-WS2000-MIB;
	
	
		-- 1.3.6.1.4.1.388.11.3.1
		moduleid MODULE-IDENTITY 
			LAST-UPDATED "200912301336Z"		-- December 30, 2009 at 13:36 GMT
			ORGANIZATION 
				"Symbol WSD (Wireless Infrastructure Division, San Jose)"
			CONTACT-INFO 
				"Carl Mower
				cmower@symbol.com"
			DESCRIPTION 
				" "
			REVISION "200912301336Z"		-- December 30, 2009 at 13:36 GMT
			DESCRIPTION 
				"apLoadCfg modified to support SFTP"
			::= { abgAP 1 }

		
	
--
-- Type definitions
--
	
--  
-- 
		SinglePointer ::= INTEGER (0..255)

		MultiPointer63 ::= BITS
			{
			null(0),
			referToEntry001(1),
			referToEntry002(2),
			referToEntry003(3),
			referToEntry004(4),
			referToEntry005(5),
			referToEntry006(6),
			referToEntry007(7),
			referToEntry008(8),
			referToEntry009(9),
			referToEntry010(10),
			referToEntry011(11),
			referToEntry012(12),
			referToEntry013(13),
			referToEntry014(14),
			referToEntry015(15),
			referToEntry016(16),
			referToEntry017(17),
			referToEntry018(18),
			referToEntry019(19),
			referToEntry020(20),
			referToEntry021(21),
			referToEntry022(22),
			referToEntry023(23),
			referToEntry024(24),
			referToEntry025(25),
			referToEntry026(26),
			referToEntry027(27),
			referToEntry028(28),
			referToEntry029(29),
			referToEntry030(30),
			referToEntry031(31),
			referToEntry032(32),
			referToEntry033(33),
			referToEntry034(34),
			referToEntry035(35),
			referToEntry036(36),
			referToEntry037(37),
			referToEntry038(38),
			referToEntry039(39),
			referToEntry040(40),
			referToEntry041(41),
			referToEntry042(42),
			referToEntry043(43),
			referToEntry044(44),
			referToEntry045(45),
			referToEntry046(46),
			referToEntry047(47),
			referToEntry048(48),
			referToEntry049(49),
			referToEntry050(50),
			referToEntry051(51),
			referToEntry052(52),
			referToEntry053(53),
			referToEntry054(54),
			referToEntry055(55),
			referToEntry056(56),
			referToEntry057(57),
			referToEntry058(58),
			referToEntry059(59),
			referToEntry060(60),
			referToEntry061(61),
			referToEntry062(62),
			referToEntry063(63)
			}

		MultiPointer255 ::= BITS
			{
			null(0),
			referToEntry001(1),
			referToEntry002(2),
			referToEntry003(3),
			referToEntry004(4),
			referToEntry005(5),
			referToEntry006(6),
			referToEntry007(7),
			referToEntry008(8),
			referToEntry009(9),
			referToEntry010(10),
			referToEntry011(11),
			referToEntry012(12),
			referToEntry013(13),
			referToEntry014(14),
			referToEntry015(15),
			referToEntry016(16),
			referToEntry017(17),
			referToEntry018(18),
			referToEntry019(19),
			referToEntry020(20),
			referToEntry021(21),
			referToEntry022(22),
			referToEntry023(23),
			referToEntry024(24),
			referToEntry025(25),
			referToEntry026(26),
			referToEntry027(27),
			referToEntry028(28),
			referToEntry029(29),
			referToEntry030(30),
			referToEntry031(31),
			referToEntry032(32),
			referToEntry033(33),
			referToEntry034(34),
			referToEntry035(35),
			referToEntry036(36),
			referToEntry037(37),
			referToEntry038(38),
			referToEntry039(39),
			referToEntry040(40),
			referToEntry041(41),
			referToEntry042(42),
			referToEntry043(43),
			referToEntry044(44),
			referToEntry045(45),
			referToEntry046(46),
			referToEntry047(47),
			referToEntry048(48),
			referToEntry049(49),
			referToEntry050(50),
			referToEntry051(51),
			referToEntry052(52),
			referToEntry053(53),
			referToEntry054(54),
			referToEntry055(55),
			referToEntry056(56),
			referToEntry057(57),
			referToEntry058(58),
			referToEntry059(59),
			referToEntry060(60),
			referToEntry061(61),
			referToEntry062(62),
			referToEntry063(63),
			referToEntry064(64),
			referToEntry065(65),
			referToEntry066(66),
			referToEntry067(67),
			referToEntry068(68),
			referToEntry069(69),
			referToEntry070(70),
			referToEntry071(71),
			referToEntry072(72),
			referToEntry073(73),
			referToEntry074(74),
			referToEntry075(75),
			referToEntry076(76),
			referToEntry077(77),
			referToEntry078(78),
			referToEntry079(79),
			referToEntry080(80),
			referToEntry081(81),
			referToEntry082(82),
			referToEntry083(83),
			referToEntry084(84),
			referToEntry085(85),
			referToEntry086(86),
			referToEntry087(87),
			referToEntry088(88),
			referToEntry089(89),
			referToEntry090(90),
			referToEntry091(91),
			referToEntry092(92),
			referToEntry093(93),
			referToEntry094(94),
			referToEntry095(95),
			referToEntry096(96),
			referToEntry097(97),
			referToEntry098(98),
			referToEntry099(99),
			referToEntry100(100),
			referToEntry101(101),
			referToEntry102(102),
			referToEntry103(103),
			referToEntry104(104),
			referToEntry105(105),
			referToEntry106(106),
			referToEntry107(107),
			referToEntry108(108),
			referToEntry109(109),
			referToEntry110(110),
			referToEntry111(111),
			referToEntry112(112),
			referToEntry113(113),
			referToEntry114(114),
			referToEntry115(115),
			referToEntry116(116),
			referToEntry117(117),
			referToEntry118(118),
			referToEntry119(119),
			referToEntry120(120),
			referToEntry121(121),
			referToEntry122(122),
			referToEntry123(123),
			referToEntry124(124),
			referToEntry125(125),
			referToEntry126(126),
			referToEntry127(127),
			referToEntry128(128),
			referToEntry129(129),
			referToEntry130(130),
			referToEntry131(131),
			referToEntry132(132),
			referToEntry133(133),
			referToEntry134(134),
			referToEntry135(135),
			referToEntry136(136),
			referToEntry137(137),
			referToEntry138(138),
			referToEntry139(139),
			referToEntry140(140),
			referToEntry141(141),
			referToEntry142(142),
			referToEntry143(143),
			referToEntry144(144),
			referToEntry145(145),
			referToEntry146(146),
			referToEntry147(147),
			referToEntry148(148),
			referToEntry149(149),
			referToEntry150(150),
			referToEntry151(151),
			referToEntry152(152),
			referToEntry153(153),
			referToEntry154(154),
			referToEntry155(155),
			referToEntry156(156),
			referToEntry157(157),
			referToEntry158(158),
			referToEntry159(159),
			referToEntry160(160),
			referToEntry161(161),
			referToEntry162(162),
			referToEntry163(163),
			referToEntry164(164),
			referToEntry165(165),
			referToEntry166(166),
			referToEntry167(167),
			referToEntry168(168),
			referToEntry169(169),
			referToEntry170(170),
			referToEntry171(171),
			referToEntry172(172),
			referToEntry173(173),
			referToEntry174(174),
			referToEntry175(175),
			referToEntry176(176),
			referToEntry177(177),
			referToEntry178(178),
			referToEntry179(179),
			referToEntry180(180),
			referToEntry181(181),
			referToEntry182(182),
			referToEntry183(183),
			referToEntry184(184),
			referToEntry185(185),
			referToEntry186(186),
			referToEntry187(187),
			referToEntry188(188),
			referToEntry189(189),
			referToEntry190(190),
			referToEntry191(191),
			referToEntry192(192),
			referToEntry193(193),
			referToEntry194(194),
			referToEntry195(195),
			referToEntry196(196),
			referToEntry197(197),
			referToEntry198(198),
			referToEntry199(199),
			referToEntry200(200),
			referToEntry201(201),
			referToEntry202(202),
			referToEntry203(203),
			referToEntry204(204),
			referToEntry205(205),
			referToEntry206(206),
			referToEntry207(207),
			referToEntry208(208),
			referToEntry209(209),
			referToEntry210(210),
			referToEntry211(211),
			referToEntry212(212),
			referToEntry213(213),
			referToEntry214(214),
			referToEntry215(215),
			referToEntry216(216),
			referToEntry217(217),
			referToEntry218(218),
			referToEntry219(219),
			referToEntry220(220),
			referToEntry221(221),
			referToEntry222(222),
			referToEntry223(223),
			referToEntry224(224),
			referToEntry225(225),
			referToEntry226(226),
			referToEntry227(227),
			referToEntry228(228),
			referToEntry229(229),
			referToEntry230(230),
			referToEntry231(231),
			referToEntry232(232),
			referToEntry233(233),
			referToEntry234(234),
			referToEntry235(235),
			referToEntry236(236),
			referToEntry237(237),
			referToEntry238(238),
			referToEntry239(239),
			referToEntry240(240),
			referToEntry241(241),
			referToEntry242(242),
			referToEntry243(243),
			referToEntry244(244),
			referToEntry245(245),
			referToEntry246(246),
			referToEntry247(247),
			referToEntry248(248),
			referToEntry249(249),
			referToEntry250(250),
			referToEntry251(251),
			referToEntry252(252),
			referToEntry253(253),
			referToEntry254(254),
			referToEntry255(255)
			}

-- This datatype always means that the MIB variable is
-- a simple ENUM that when written to 'doActionRightNow', 
-- causes the described action to take place, (much like 
-- a button pressed in a UI).
-- 
-- Such a value does NOT remain in state 'doActionRightNow'
-- while the operation is in-process, but instead when read 
-- always returns 'idleState'.
		DoActionNow ::= INTEGER
			{
			doActionRightNow(1),
			idleState(2)
			}

		RadioType ::= INTEGER
			{
			radio802dot11A(1),
			radio802dot11B(2),
			radio802dot11G(3),
			radio802dot11FH(4)
			}

-- Values of this type are passwords.  They can be written,
-- but when read, they return a 0-length string.
		Password ::= OCTET STRING (SIZE (0..255))

-- In order to make the switch's implementation of 
-- numerous tables simpler, tables using this datatype
-- have a fixed number of entries with fixed indices.
-- In such tables, no entries may be added or deleted, 
-- but the pre-existing rows can be enabled or disabled 
-- using the value declared with this datatype.
		StaticRowEnable ::= INTEGER
			{
			enable(1),
			disable(2)
			}

		PartsPer10k ::= Unsigned32 (0..10000)
-- This datatype is used for all percentage values that have
-- interesting tenths and hundreths, (such as 1.37%).  SNMP
-- cannot report decimals, only whole numbers.  Values of 
-- this datatype are expressed not as parts-per-100, (percent),
-- but as parts-per-10000.
-- 
-- Said another way, values of this type are percent 
-- multiplied by 100.
-- 
-- For example, 1.37% would be reported as 137.
-- 
		ScaleBy100 ::= Unsigned32
-- This datatype is used for all values that have interesting 
-- tenths and hundreths, (such as 2.48).  SNMP cannot report 
-- decimals, only whole numbers.  Values of this datatype are 
-- scaled (muliplied) by 100.
-- 
-- For example, 2.48 would be reported as 248.
-- In order to make the switch's implementation of some
-- dynamic tables simpler, tables using this datatype
-- use an abbreviated form of RowStatus.
-- 
-- Only CreateAndGo and Destroy states are supported.
-- 
-- On row creation, a single SET-PDU must contain all
-- the required values, including this value set to
-- createAndGo.  (This greatly simplifies row validation
-- for the switch).
-- 
-- Setting this value to Destroy causes the corresponding
-- row to be deleted.
-- 
		AbbrevRowStatus ::= INTEGER
			{
			createAndGo(4),
			destroy(6)
			}

-- This datatype always means that the MIB variable is
-- a simple ENUM that when written to 'doActionRightNow', 
-- causes the described action to take place, (much like 
-- a button pressed in a UI).
-- 
-- Such a value DOES remain in state 'doActionRightNow'
-- while the operation is in-process;  when the operation is
-- completed, it will then return the value 'idleState'.
		DoActionShowProgress ::= INTEGER
			{
			doActionRightNow(1),
			idleState(2)
			}

-- Values of this type are keys, expressed in hexadecimal as
-- a sequence of characters '0'..'9' plus 'A'..'F'.
-- 
-- Unless otherwise noted, the default value for variables of
-- this type is all-0s.
-- 
-- Values of this type are passwords.  They can be written,
-- but when read, they return a 0-length string.
		HexPassword ::= OCTET STRING (SIZE (0..255))

		TransmitRate ::= BITS
			{
			null(0),
			rate1Mb(1),
			rate2Mb(2),
			rate5pt5Mb(3),
			rate6Mb(4),
			rate9Mb(5),
			rate11Mb(6),
			rate12Mb(7),
			rate18Mb(8),
			rate22Mb(9),
			rate24Mb(10),
			rate36Mb(11),
			rate48Mb(12),
			rate54Mb(13)
			}

-- This is a list of valid channels.
-- For the 2.4 GHz band, we can use channels 1-14.
-- For the 5.0 GHz band, we can use channels:
-- 36, 40, 44, 48, 52, 56, 60, 64, 100, 104, 108, 112, 116, 
-- 120, 124, 128, 132, 136, 140, 149, 153, 157, 161, 165
		AllowedChannels ::= INTEGER
			{
			channel1(1),
			channel2(2),
			channel3(3),
			channel4(4),
			channel5(5),
			channel6(6),
			channel7(7),
			channel8(8),
			channel9(9),
			channel10(10),
			channel11(11),
			channel12(12),
			channel13(13),
			channel14(14),
			channel36(36),
			channel40(40),
			channel44(44),
			channel48(48),
			channel52(52),
			channel56(56),
			channel60(60),
			channel64(64),
			channel100(100),
			channel104(104),
			channel108(108),
			channel112(112),
			channel116(116),
			channel120(120),
			channel124(124),
			channel128(128),
			channel132(132),
			channel136(136),
			channel140(140),
			channel149(149),
			channel153(153),
			channel157(157),
			channel161(161),
			channel165(165)
			}

	
--
-- Textual conventions
--
	
		RowStatus ::= TEXTUAL-CONVENTION
			STATUS current
			DESCRIPTION 
				"The RowStatus textual convention is used to manage the
				creation and deletion of conceptual rows, and is used as the
				value of the SYNTAX clause for the status column of a
				conceptual row (as described in Section 7.7.1 of [2].)
				
				The status column has six defined values:
				
				     - `active', which indicates that the conceptual row is
				     available for use by the managed device;
				
				     - `notInService', which indicates that the conceptual
				     row exists in the agent, but is unavailable for use by
				     the managed device (see NOTE below);
				
				     - `notReady', which indicates that the conceptual row
				     exists in the agent, but is missing information
				     necessary in order to be available for use by the
				     managed device;
				
				     - `createAndGo', which is supplied by a management
				     station wishing to create a new instance of a
				     conceptual row and to have its status automatically set
				     to active, making it available for use by the managed
				     device;
				
				     - `createAndWait', which is supplied by a management
				     station wishing to create a new instance of a
				     conceptual row (but not make it available for use by
				     the managed device); and,
				
				     - `destroy', which is supplied by a management station
				     wishing to delete all of the instances associated with
				     an existing conceptual row.
				
				Whereas five of the six values (all except `notReady') may
				be specified in a management protocol set operation, only
				three values will be returned in response to a management
				protocol retrieval operation:  `notReady', `notInService' or
				`active'.  That is, when queried, an existing conceptual row
				has only three states:  it is either available for use by
				the managed device (the status column has value `active');
				it is not available for use by the managed device, though
				the agent has sufficient information to make it so (the
				status column has value `notInService'); or, it is not
				available for use by the managed device, and an attempt to
				make it so would fail because the agent has insufficient
				information (the state column has value `notReady').
				
				                         NOTE WELL
				
				     This textual convention may be used for a MIB table,
				     irrespective of whether the values of that table's
				     conceptual rows are able to be modified while it is
				     active, or whether its conceptual rows must be taken
				     out of service in order to be modified.  That is, it is
				     the responsibility of the DESCRIPTION clause of the
				     status column to specify whether the status column must
				     not be `active' in order for the value of some other
				     column of the same conceptual row to be modified.  If
				     such a specification is made, affected columns may be
				     changed by an SNMP set PDU if the RowStatus would not
				     be equal to `active' either immediately before or after
				     processing the PDU.  In other words, if the PDU also
				     contained a varbind that would change the RowStatus
				     value, the column in question may be changed if the
				     RowStatus was not equal to `active' as the PDU was
				     received, or if the varbind sets the status to a value
				     other than 'active'.
				
				
				Also note that whenever any elements of a row exist, the
				RowStatus column must also exist.
				
				To summarize the effect of having a conceptual row with a
				status column having a SYNTAX clause value of RowStatus,
				consider the following state diagram:
				
				
				                                           STATE
				                +--------------+-----------+-------------+-------------
				                |      A       |     B     |      C      |      D
				                |              |status col.|status column|
				                |status column |    is     |      is     |status column
				      ACTION    |does not exist|  notReady | notInService|  is active
				  --------------+--------------+-----------+-------------+-------------
				  set status    |noError    ->D|inconsist- |inconsistent-|inconsistent-
				  column to     |       or     |   entValue|        Value|        Value
				  createAndGo   |inconsistent- |           |             |
				                |         Value|           |             |
				  --------------+--------------+-----------+-------------+-------------
				  set status    |noError  see 1|inconsist- |inconsistent-|inconsistent-
				  column to     |       or     |   entValue|        Value|        Value
				  createAndWait |wrongValue    |           |             |
				  --------------+--------------+-----------+-------------+-------------
				  set status    |inconsistent- |inconsist- |noError      |noError
				  column to     |         Value|   entValue|             |
				  active        |              |           |             |
				                |              |     or    |             |
				                |              |           |             |
				                |              |see 2   ->D|          ->D|          ->D
				  --------------+--------------+-----------+-------------+-------------
				  set status    |inconsistent- |inconsist- |noError      |noError   ->C
				  column to     |         Value|   entValue|             |
				  notInService  |              |           |             |
				                |              |     or    |             |      or
				                |              |           |             |
				                |              |see 3   ->C|          ->C|wrongValue
				  --------------+--------------+-----------+-------------+-------------
				  set status    |noError       |noError    |noError      |noError
				  column to     |              |           |             |
				  destroy       |           ->A|        ->A|          ->A|          ->A
				  --------------+--------------+-----------+-------------+-------------
				  set any other |see 4         |noError    |noError      |see 5
				  column to some|              |           |             |
				  value         |              |      see 1|          ->C|          ->D
				  --------------+--------------+-----------+-------------+-------------
				  
				(1) goto B or C, depending on information available to the
				agent.
				
				(2) if other variable bindings included in the same PDU,
				provide values for all columns which are missing but
				required, then return noError and goto D.
				
				(3) if other variable bindings included in the same PDU,
				provide values for all columns which are missing but
				required, then return noError and goto C.
				
				(4) at the discretion of the agent, the return value may be
				either:
				
				     inconsistentName:  because the agent does not choose to
				     create such an instance when the corresponding
				     RowStatus instance does not exist, or
				
				     inconsistentValue:  if the supplied value is
				     inconsistent with the state of some other MIB object's
				     value, or
				
				     noError: because the agent chooses to create the
				     instance.
				
				If noError is returned, then the instance of the status
				column must also be created, and the new state is B or C,
				depending on the information available to the agent.  If
				inconsistentName or inconsistentValue is returned, the row
				remains in state A.
				
				(5) depending on the MIB definition for the column/table,
				either noError or inconsistentValue may be returned.
				
				NOTE: Other processing of the set request may result in a
				response other than noError being returned, e.g.,
				wrongValue, noCreation, etc.
				
				
				                  Conceptual Row Creation
				
				There are four potential interactions when creating a
				conceptual row:  selecting an instance-identifier which is
				not in use; creating the conceptual row; initializing any
				objects for which the agent does not supply a default; and,
				making the conceptual row available for use by the managed
				device.
				
				Interaction 1: Selecting an Instance-Identifier
				
				The algorithm used to select an instance-identifier varies
				for each conceptual row.  In some cases, the instance-
				identifier is semantically significant, e.g., the
				destination address of a route, and a management station
				selects the instance-identifier according to the semantics.
				
				In other cases, the instance-identifier is used solely to
				distinguish conceptual rows, and a management station
				without specific knowledge of the conceptual row might
				examine the instances present in order to determine an
				unused instance-identifier.  (This approach may be used, but
				it is often highly sub-optimal; however, it is also a
				questionable practice for a naive management station to
				attempt conceptual row creation.)
				
				Alternately, the MIB module which defines the conceptual row
				might provide one or more objects which provide assistance
				in determining an unused instance-identifier.  For example,
				if the conceptual row is indexed by an integer-value, then
				an object having an integer-valued SYNTAX clause might be
				defined for such a purpose, allowing a management station to
				issue a management protocol retrieval operation.  In order
				to avoid unnecessary collisions between competing management
				stations, `adjacent' retrievals of this object should be
				different.
				
				Finally, the management station could select a pseudo-random
				number to use as the index.  In the event that this index
				was already in use and an inconsistentValue was returned in
				response to the management protocol set operation, the
				management station should simply select a new pseudo-random
				number and retry the operation.
				
				A MIB designer should choose between the two latter
				algorithms based on the size of the table (and therefore the
				efficiency of each algorithm).  For tables in which a large
				number of entries are expected, it is recommended that a MIB
				object be defined that returns an acceptable index for
				creation.  For tables with small numbers of entries, it is
				recommended that the latter pseudo-random index mechanism be
				used.
				
				
				Interaction 2: Creating the Conceptual Row
				
				Once an unused instance-identifier has been selected, the
				management station determines if it wishes to create and
				activate the conceptual row in one transaction or in a
				negotiated set of interactions.
				
				Interaction 2a: Creating and Activating the Conceptual Row
				
				The management station must first determine the column
				requirements, i.e., it must determine those columns for
				which it must or must not provide values.  Depending on the
				complexity of the table and the management station's
				knowledge of the agent's capabilities, this determination
				can be made locally by the management station.  Alternately,
				the management station issues a management protocol get
				operation to examine all columns in the conceptual row that
				it wishes to create.  In response, for each column, there
				are three possible outcomes:
				
				     - a value is returned, indicating that some other
				     management station has already created this conceptual
				     row.  We return to interaction 1.
				
				     - the exception `noSuchInstance' is returned,
				     indicating that the agent implements the object-type
				     associated with this column, and that this column in at
				     least one conceptual row would be accessible in the MIB
				     view used by the retrieval were it to exist. For those
				     columns to which the agent provides read-create access,
				     the `noSuchInstance' exception tells the management
				     station that it should supply a value for this column
				     when the conceptual row is to be created.
				
				     - the exception `noSuchObject' is returned, indicating
				     that the agent does not implement the object-type
				     associated with this column or that there is no
				     conceptual row for which this column would be
				     accessible in the MIB view used by the retrieval.  As
				     such, the management station can not issue any
				     management protocol set operations to create an
				     instance of this column.
				
				Once the column requirements have been determined, a
				management protocol set operation is accordingly issued.
				This operation also sets the new instance of the status
				column to `createAndGo'.
				
				When the agent processes the set operation, it verifies that
				it has sufficient information to make the conceptual row
				available for use by the managed device.  The information
				available to the agent is provided by two sources:  the
				management protocol set operation which creates the
				conceptual row, and, implementation-specific defaults
				supplied by the agent (note that an agent must provide
				implementation-specific defaults for at least those objects
				which it implements as read-only).  If there is sufficient
				information available, then the conceptual row is created, a
				`noError' response is returned, the status column is set to
				`active', and no further interactions are necessary (i.e.,
				interactions 3 and 4 are skipped).  If there is insufficient
				information, then the conceptual row is not created, and the
				set operation fails with an error of `inconsistentValue'.
				On this error, the management station can issue a management
				protocol retrieval operation to determine if this was
				because it failed to specify a value for a required column,
				or, because the selected instance of the status column
				already existed.  In the latter case, we return to
				interaction 1.  In the former case, the management station
				can re-issue the set operation with the additional
				information, or begin interaction 2 again using
				`createAndWait' in order to negotiate creation of the
				conceptual row.
				
				                         NOTE WELL
				
				     Regardless of the method used to determine the column
				     requirements, it is possible that the management
				     station might deem a column necessary when, in fact,
				     the agent will not allow that particular columnar
				     instance to be created or written.  In this case, the
				     management protocol set operation will fail with an
				     error such as `noCreation' or `notWritable'.  In this
				     case, the management station decides whether it needs
				     to be able to set a value for that particular columnar
				     instance.  If not, the management station re-issues the
				     management protocol set operation, but without setting
				     a value for that particular columnar instance;
				     otherwise, the management station aborts the row
				     creation algorithm.
				
				Interaction 2b: Negotiating the Creation of the Conceptual
				Row
				
				The management station issues a management protocol set
				operation which sets the desired instance of the status
				column to `createAndWait'.  If the agent is unwilling to
				process a request of this sort, the set operation fails with
				an error of `wrongValue'.  (As a consequence, such an agent
				must be prepared to accept a single management protocol set
				operation, i.e., interaction 2a above, containing all of the
				columns indicated by its column requirements.)  Otherwise,
				the conceptual row is created, a `noError' response is
				returned, and the status column is immediately set to either
				`notInService' or `notReady', depending on whether it has
				sufficient information to make the conceptual row available
				for use by the managed device.  If there is sufficient
				information available, then the status column is set to
				`notInService'; otherwise, if there is insufficient
				information, then the status column is set to `notReady'.
				Regardless, we proceed to interaction 3.
				
				Interaction 3: Initializing non-defaulted Objects
				
				The management station must now determine the column
				requirements.  It issues a management protocol get operation
				to examine all columns in the created conceptual row.  In
				the response, for each column, there are three possible
				outcomes:
				
				     - a value is returned, indicating that the agent
				     implements the object-type associated with this column
				     and had sufficient information to provide a value.  For
				     those columns to which the agent provides read-create
				     access (and for which the agent allows their values to
				     be changed after their creation), a value return tells
				     the management station that it may issue additional
				     management protocol set operations, if it desires, in
				     order to change the value associated with this column.
				
				     - the exception `noSuchInstance' is returned,
				     indicating that the agent implements the object-type
				     associated with this column, and that this column in at
				     least one conceptual row would be accessible in the MIB
				     view used by the retrieval were it to exist. However,
				     the agent does not have sufficient information to
				     provide a value, and until a value is provided, the
				     conceptual row may not be made available for use by the
				     managed device.  For those columns to which the agent
				     provides read-create access, the `noSuchInstance'
				     exception tells the management station that it must
				     issue additional management protocol set operations, in
				     order to provide a value associated with this column.
				
				     - the exception `noSuchObject' is returned, indicating
				     that the agent does not implement the object-type
				     associated with this column or that there is no
				     conceptual row for which this column would be
				     accessible in the MIB view used by the retrieval.  As
				     such, the management station can not issue any
				     management protocol set operations to create an
				     instance of this column.
				
				If the value associated with the status column is
				`notReady', then the management station must first deal with
				all `noSuchInstance' columns, if any.  Having done so, the
				value of the status column becomes `notInService', and we
				proceed to interaction 4.
				
				Interaction 4: Making the Conceptual Row Available
				
				Once the management station is satisfied with the values
				associated with the columns of the conceptual row, it issues
				a management protocol set operation to set the status column
				to `active'.  If the agent has sufficient information to
				make the conceptual row available for use by the managed
				device, the management protocol set operation succeeds (a
				`noError' response is returned).  Otherwise, the management
				protocol set operation fails with an error of
				`inconsistentValue'.
				
				
				                         NOTE WELL
				
				     A conceptual row having a status column with value
				     `notInService' or `notReady' is unavailable to the
				     managed device.  As such, it is possible for the
				     managed device to create its own instances during the
				     time between the management protocol set operation
				     which sets the status column to `createAndWait' and the
				     management protocol set operation which sets the status
				     column to `active'.  In this case, when the management
				     protocol set operation is issued to set the status
				     column to `active', the values held in the agent
				     supersede those used by the managed device.
				
				If the management station is prevented from setting the
				status column to `active' (e.g., due to management station
				or network failure) the conceptual row will be left in the
				`notInService' or `notReady' state, consuming resources
				indefinitely.  The agent must detect conceptual rows that
				have been in either state for an abnormally long period of
				time and remove them.  It is the responsibility of the
				DESCRIPTION clause of the status column to indicate what an
				abnormally long period of time would be.  This period of
				time should be long enough to allow for human response time
				(including `think time') between the creation of the
				conceptual row and the setting of the status to `active'.
				In the absense of such information in the DESCRIPTION
				clause, it is suggested that this period be approximately 5
				minutes in length.  This removal action applies not only to
				newly-created rows, but also to previously active rows which
				are set to, and left in, the notInService state for a
				prolonged period exceeding that which is considered normal
				for such a conceptual row.
				
				
				                 Conceptual Row Suspension
				
				When a conceptual row is `active', the management station
				may issue a management protocol set operation which sets the
				instance of the status column to `notInService'.  If the
				agent is unwilling to do so, the set operation fails with an
				error of `wrongValue'.  Otherwise, the conceptual row is
				taken out of service, and a `noError' response is returned.
				It is the responsibility of the DESCRIPTION clause of the
				status column to indicate under what circumstances the
				status column should be taken out of service (e.g., in order
				for the value of some other column of the same conceptual
				row to be modified).
				
				
				                  Conceptual Row Deletion
				
				For deletion of conceptual rows, a management protocol set
				operation is issued which sets the instance of the status
				column to `destroy'.  This request may be made regardless of
				the current value of the status column (e.g., it is possible
				to delete conceptual rows which are either `notReady',
				`notInService' or `active'.)  If the operation succeeds,
				then all instances associated with the conceptual row are
				immediately removed."
			SYNTAX INTEGER
				{
				active(1),
				notInService(2),
				notReady(3),
				createAndGo(4),
				createAndWait(5),
				destroy(6)
				}

		DateAndTime ::= TEXTUAL-CONVENTION
			DISPLAY-HINT 
				"2d-1d-1d,1d:1d:1d.1d,1a1d:1d"
			STATUS current
			DESCRIPTION 
				"A date-time specification.
				
				field  octets  contents                  range
				-----  ------  --------                  -----
				  1      1-2   year                      0..65536
				  2       3    month                     1..12
				  3       4    day                       1..31
				  4       5    hour                      0..23
				  5       6    minutes                   0..59
				  6       7    seconds                   0..60
				               (use 60 for leap-second)
				  7       8    deci-seconds              0..9
				  8       9    direction from UTC        '+' / '-'
				  9      10    hours from UTC            0..11
				 10      11    minutes from UTC          0..59
				
				For example, Tuesday May 26, 1992 at 1:30:15 PM EDT would be
				displayed as:
				
				                1992-5-26,13:30:15.0,-4:0
				
				Note that if only local time is known, then timezone
				information (fields 8-10) is not present."
			SYNTAX OCTET STRING (SIZE (8 | 11))

		EthernetType ::= TEXTUAL-CONVENTION
			DISPLAY-HINT 
				"1x "
			STATUS current
			DESCRIPTION 
				"Represents Ethernet Types."
			SYNTAX OCTET STRING (SIZE (2))

	
--
-- Node definitions
--
	
-- Node definitions
-- 
		-- 1.3.6.1.4.1.388
		symbol OBJECT IDENTIFIER ::= { enterprises 388 }

		
-- !!- OID: .11 - as specified by Symbol MIB Admin.
-- 
-- This sub-tree used for MIBs and sysOIDs produced 
-- by WSD, (Wireless Infrastructure Division, 
-- San Jose).
-- 
		-- 1.3.6.1.4.1.388.11
		wsd OBJECT IDENTIFIER ::= { symbol 11 }

		
-- This node reserved for sysOIDs of devices produced 
-- by WSD.
-- 
		-- 1.3.6.1.4.1.388.11.1
		sysoids OBJECT IDENTIFIER ::= { wsd 1 }

		
		-- 1.3.6.1.4.1.388.11.1.2
		ap5131 OBJECT-IDENTITY
			STATUS current
			DESCRIPTION 
				"AP5131 with 1 WAN port, 1 LAN ports."
			::= { sysoids 2 }

		
		-- 1.3.6.1.4.1.388.11.1.3
		ap5181 OBJECT-IDENTITY
			STATUS current
			DESCRIPTION 
				"AP5131 with 1 WAN port, 1 LAN ports, 533Mhz processor speed."
			::= { sysoids 3 }

		
		-- 1.3.6.1.4.1.388.11.1.4
		ap7131 OBJECT-IDENTITY
			STATUS current
			DESCRIPTION 
				"AP7131"
			::= { sysoids 4 }

		
		-- 1.3.6.1.4.1.388.11.1.5
		ap7181 OBJECT-IDENTITY
			STATUS current
			DESCRIPTION 
				"AP7181."
			::= { sysoids 5 }

		
-- MIBs implemented by AP5131 devices.
-- 
-- All counter variables, under this tree node wrap in no less
-- than 5.8 minutes, EXCEPT as noted below.  (Be advised that
-- all values referred to here as 'counters' are not 
-- necessarily of type Counter32 or Counter64;  some are
-- Unsigned32, and some Signal & Noise values are Integer32).
-- 
-- Exception #1: for all values that count the number
-- of tx/rx/both octets when the MAX number of Portals (12)
-- are all running at a full 54Mb.  In such cases, those
-- counters could theoretically wrap in 0.8min.  But, since
-- 54Mb does not practically achieve 54Mb, this wrap time
-- is more realistically at least 1-2min.  If the switch does
-- not have all 12 Portals, that wrap time would be even 
-- longer.
-- 
-- Exception #2: there are three _SignalSum values, (Portal,
-- MU, and WLAN);  since Signal values range up to around
-- -90dBm, they could theoretically wrap in 0.5min if the MAX
-- number of Portals all had a full 54Mb of short packets 
-- flowing, all with _Signal values of around -100.  Since you
-- generally cannot communicate at 54Mb at -100dBm, this is
-- not practially realistic.  At more realistic levels, these
-- values would wrap no faster than 1-2min, and verly likely
-- no faster than 5min.
-- 
-- (It was considered to increase the affected counters to
-- 64bits, but given the difficulty implementing larger 
-- counters and the large number of values to change, as
-- weighed against the REALISTIC wrap risk did not suggest
-- doing this work).
-- 
-- Given all this, a poll time of 5min, (or less), will
-- basically ensure that no data is lost due to counter wrap.
-- 
-- 
-- 
-- Numerous tables include _SumSquares values.  These MIB
-- variables are always the summation of the square of each
-- individual value.  These _SumSquares values can be used,
-- (in conjunction with 'N' and _Sum), to calculate standard
-- deviation, (a statistical measure of the variance of the
-- data points).
		-- 1.3.6.1.4.1.388.11.3
		abgAP OBJECT IDENTIFIER ::= { wsd 3 }

		
		-- 1.3.6.1.4.1.388.11.3.3
		dot1x OBJECT IDENTIFIER ::= { abgAP 3 }

		
		-- 1.3.6.1.4.1.388.11.3.3.1
		dot1xPaeAuthenticator OBJECT IDENTIFIER ::= { dot1x 1 }

		
		-- 1.3.6.1.4.1.388.11.3.3.1.1
		dot1xAuthConfigTable OBJECT-TYPE
			SYNTAX SEQUENCE OF Dot1xAuthConfigEntry
			MAX-ACCESS not-accessible
			STATUS current
			DESCRIPTION
				"A table that contains the configuration objects for the
				Authenticator PAE associated with each port.
				An entry appears in this table for each port that may
				authenticate access to itself.
				"
			::= { dot1xPaeAuthenticator 1 }

		
		-- 1.3.6.1.4.1.388.11.3.3.1.1.1
		dot1xAuthConfigEntry OBJECT-TYPE
			SYNTAX Dot1xAuthConfigEntry
			MAX-ACCESS not-accessible
			STATUS current
			DESCRIPTION
				"The configuration information for an Authenticator PAE.
				"
			INDEX { dot1xPaePortNumber }
			::= { dot1xAuthConfigTable 1 }

		
		Dot1xAuthConfigEntry ::=
			SEQUENCE { 
				dot1xPaePortNumber
					Integer32,
				dot1xPaeState
					INTEGER,
				dot1xAuthBackendAuthState
					INTEGER,
				dot1xAuthAdminControlledDirections
					Integer32,
				dot1xAuthOperControlledDirections
					Integer32,
				dot1xAuthAuthControlledPortStatus
					Integer32,
				dot1xAuthAuthControlledPortControl
					Integer32,
				dot1xAuthQuietPeriod
					Unsigned32,
				dot1xAuthTxPeriod
					Unsigned32,
				dot1xAuthSuppTimeout
					Unsigned32,
				dot1xAuthServerTimeout
					Unsigned32,
				dot1xAuthMaxReq
					Unsigned32,
				dot1xAuthReAuthPeriod
					Unsigned32,
				dot1xAuthReAuthEnabled
					TruthValue,
				dot1xAuthKeyTxEnabled
					TruthValue
			 }

		-- 1.3.6.1.4.1.388.11.3.3.1.1.1.1
		dot1xPaePortNumber OBJECT-TYPE
			SYNTAX Integer32 (1..200)
			MAX-ACCESS accessible-for-notify
			STATUS current
			DESCRIPTION
				"The Port number associated with this Port."
			::= { dot1xAuthConfigEntry 1 }

		
		-- 1.3.6.1.4.1.388.11.3.3.1.1.1.2
		dot1xPaeState OBJECT-TYPE
			SYNTAX INTEGER
				{
				intialize(1),
				disconnected(2),
				connecting(3),
				authenticating(4),
				authenticated(5),
				aborting(6),
				held(7),
				forceAuth(8),
				forceUnauth(9)
				}
			MAX-ACCESS read-only
			STATUS current
			DESCRIPTION
				"The current value of the Authenticator PAE state machine.
				"
			::= { dot1xAuthConfigEntry 2 }

		
		-- 1.3.6.1.4.1.388.11.3.3.1.1.1.3
		dot1xAuthBackendAuthState OBJECT-TYPE
			SYNTAX INTEGER
				{
				request(1),
				response(2),
				success(3),
				fail(4),
				timeout(5),
				idle(6),
				initialize(7)
				}
			MAX-ACCESS read-only
			STATUS current
			DESCRIPTION
				"The current state of the Backend Authentication	state machine.
				"
			::= { dot1xAuthConfigEntry 3 }

		
		-- 1.3.6.1.4.1.388.11.3.3.1.1.1.4
		dot1xAuthAdminControlledDirections OBJECT-TYPE
			SYNTAX Integer32
			MAX-ACCESS read-only
			STATUS current
			DESCRIPTION
				"The current value of the administrative controlled 
				directions parameter for the Port."
			::= { dot1xAuthConfigEntry 4 }

		
		-- 1.3.6.1.4.1.388.11.3.3.1.1.1.5
		dot1xAuthOperControlledDirections OBJECT-TYPE
			SYNTAX Integer32
			MAX-ACCESS read-only
			STATUS current
			DESCRIPTION
				"The current value of the operational controlled
				directions parameter for the Port.
				"
			::= { dot1xAuthConfigEntry 5 }

		
		-- 1.3.6.1.4.1.388.11.3.3.1.1.1.6
		dot1xAuthAuthControlledPortStatus OBJECT-TYPE
			SYNTAX Integer32
			MAX-ACCESS read-only
			STATUS current
			DESCRIPTION
				"The current value of the controlled Port
				status parameter for the Port.
				"
			::= { dot1xAuthConfigEntry 6 }

		
		-- 1.3.6.1.4.1.388.11.3.3.1.1.1.7
		dot1xAuthAuthControlledPortControl OBJECT-TYPE
			SYNTAX Integer32
			MAX-ACCESS read-only
			STATUS current
			DESCRIPTION
				"The current value of the controlled Port
				control parameter for the Port.
				"
			::= { dot1xAuthConfigEntry 7 }

		
		-- 1.3.6.1.4.1.388.11.3.3.1.1.1.8
		dot1xAuthQuietPeriod OBJECT-TYPE
			SYNTAX Unsigned32
			MAX-ACCESS read-only
			STATUS current
			DESCRIPTION
				"The value, in seconds, of the quietPeriod constant
				currently in use by the Authenticator PAE state
				machine.
				"
			::= { dot1xAuthConfigEntry 8 }

		
		-- 1.3.6.1.4.1.388.11.3.3.1.1.1.9
		dot1xAuthTxPeriod OBJECT-TYPE
			SYNTAX Unsigned32
			MAX-ACCESS read-only
			STATUS current
			DESCRIPTION
				"The value, in seconds, of the txPeriod constant
				currently in use by the Authenticator PAE state
				machine.
				"
			::= { dot1xAuthConfigEntry 9 }

		
		-- 1.3.6.1.4.1.388.11.3.3.1.1.1.10
		dot1xAuthSuppTimeout OBJECT-TYPE
			SYNTAX Unsigned32
			MAX-ACCESS read-only
			STATUS current
			DESCRIPTION
				"The value, in seconds, of the suppTimeout constant
				currently in use by the Backend Authentication state
				machine.
				"
			::= { dot1xAuthConfigEntry 10 }

		
		-- 1.3.6.1.4.1.388.11.3.3.1.1.1.11
		dot1xAuthServerTimeout OBJECT-TYPE
			SYNTAX Unsigned32
			MAX-ACCESS read-only
			STATUS current
			DESCRIPTION
				"The value, in seconds, of the serverTimeout constant
				currently in use by the Backend Authentication state
				machine.
				"
			::= { dot1xAuthConfigEntry 11 }

		
		-- 1.3.6.1.4.1.388.11.3.3.1.1.1.12
		dot1xAuthMaxReq OBJECT-TYPE
			SYNTAX Unsigned32
			MAX-ACCESS read-only
			STATUS current
			DESCRIPTION
				"The value of the maxReq constant currently in use by
				the Backend Authentication state machine.
				"
			::= { dot1xAuthConfigEntry 12 }

		
		-- 1.3.6.1.4.1.388.11.3.3.1.1.1.13
		dot1xAuthReAuthPeriod OBJECT-TYPE
			SYNTAX Unsigned32
			MAX-ACCESS read-only
			STATUS current
			DESCRIPTION
				"The value, in seconds, of the reAuthPeriod constant
				currently in use by the Reauthentication Timer state
				machine.
				"
			::= { dot1xAuthConfigEntry 13 }

		
		-- 1.3.6.1.4.1.388.11.3.3.1.1.1.14
		dot1xAuthReAuthEnabled OBJECT-TYPE
			SYNTAX TruthValue
			MAX-ACCESS read-only
			STATUS current
			DESCRIPTION
				"The enable/disable control used by the Reauthentication
				Timer state machine"
			::= { dot1xAuthConfigEntry 14 }

		
		-- 1.3.6.1.4.1.388.11.3.3.1.1.1.15
		dot1xAuthKeyTxEnabled OBJECT-TYPE
			SYNTAX TruthValue
			MAX-ACCESS read-only
			STATUS current
			DESCRIPTION
				"The value of the keyTransmissionEnabled constant
				currently in use by the Authenticator PAE state
				machine."
			::= { dot1xAuthConfigEntry 15 }

		
		-- 1.3.6.1.4.1.388.11.3.3.1.2
		dot1xAuthStatsTable OBJECT-TYPE
			SYNTAX SEQUENCE OF Dot1xAuthStatsEntry
			MAX-ACCESS not-accessible
			STATUS current
			DESCRIPTION
				"A table that contains the statistics objects for the
				Authenticator PAE associated with each Port.
				An entry appears in this table for each port that may
				authenticate access to itself.
				"
			::= { dot1xPaeAuthenticator 2 }

		
		-- 1.3.6.1.4.1.388.11.3.3.1.2.1
		dot1xAuthStatsEntry OBJECT-TYPE
			SYNTAX Dot1xAuthStatsEntry
			MAX-ACCESS not-accessible
			STATUS current
			DESCRIPTION
				"The statistics information for an Authenticator PAE.
				"
			INDEX { dot1xPaePortNumber }
			::= { dot1xAuthStatsTable 1 }

		
		Dot1xAuthStatsEntry ::=
			SEQUENCE { 
				dot1xAuthEapolFramesRx
					Counter32,
				dot1xAuthEapolFramesTx
					Counter32,
				dot1xAuthEapolStartFramesRx
					Counter32,
				dot1xAuthEapolLogoffFramesRx
					Counter32,
				dot1xAuthEapolRespIdFramesRx
					Counter32,
				dot1xAuthEapolRespFramesRx
					Counter32,
				dot1xAuthEapolReqIdFramesTx
					Counter32,
				dot1xAuthEapolReqFramesTx
					Counter32,
				dot1xAuthInvalidEapolFramesRx
					Counter32,
				dot1xAuthEapLengthErrorFramesRx
					Counter32,
				dot1xAuthLastEapolFrameVersion
					OCTET STRING,
				dot1xAuthLastEapolFrameSource
					PhysAddress
			 }

		-- 1.3.6.1.4.1.388.11.3.3.1.2.1.1
		dot1xAuthEapolFramesRx OBJECT-TYPE
			SYNTAX Counter32
			MAX-ACCESS read-only
			STATUS current
			DESCRIPTION
				"The number of valid EAPOL frames of any type
				that have been received by this Authenticator.
				"
			::= { dot1xAuthStatsEntry 1 }

		
		-- 1.3.6.1.4.1.388.11.3.3.1.2.1.2
		dot1xAuthEapolFramesTx OBJECT-TYPE
			SYNTAX Counter32
			MAX-ACCESS read-only
			STATUS current
			DESCRIPTION
				"The number of EAPOL frames of any type
				that have been transmitted by this Authenticator.
				"
			::= { dot1xAuthStatsEntry 2 }

		
		-- 1.3.6.1.4.1.388.11.3.3.1.2.1.3
		dot1xAuthEapolStartFramesRx OBJECT-TYPE
			SYNTAX Counter32
			MAX-ACCESS read-only
			STATUS current
			DESCRIPTION
				"The number of EAPOL Start frames that have
				been received by this Authenticator.
				"
			::= { dot1xAuthStatsEntry 3 }

		
		-- 1.3.6.1.4.1.388.11.3.3.1.2.1.4
		dot1xAuthEapolLogoffFramesRx OBJECT-TYPE
			SYNTAX Counter32
			MAX-ACCESS read-only
			STATUS current
			DESCRIPTION
				"The number of EAPOL Logoff frames that have
				been received by this Authenticator.
				"
			::= { dot1xAuthStatsEntry 4 }

		
		-- 1.3.6.1.4.1.388.11.3.3.1.2.1.5
		dot1xAuthEapolRespIdFramesRx OBJECT-TYPE
			SYNTAX Counter32
			MAX-ACCESS read-only
			STATUS current
			DESCRIPTION
				"The number of EAP Resp/Id frames that have
				been received by this Authenticator.
				"
			::= { dot1xAuthStatsEntry 5 }

		
		-- 1.3.6.1.4.1.388.11.3.3.1.2.1.6
		dot1xAuthEapolRespFramesRx OBJECT-TYPE
			SYNTAX Counter32
			MAX-ACCESS read-only
			STATUS current
			DESCRIPTION
				"The number of valid EAP Response frames
				(other than Resp/Id frames) that have been
				received by this Authenticator.
				"
			::= { dot1xAuthStatsEntry 6 }

		
		-- 1.3.6.1.4.1.388.11.3.3.1.2.1.7
		dot1xAuthEapolReqIdFramesTx OBJECT-TYPE
			SYNTAX Counter32
			MAX-ACCESS read-only
			STATUS current
			DESCRIPTION
				"The number of EAP Req/Id frames that have been
				transmitted by this Authenticator.
				
				"
			::= { dot1xAuthStatsEntry 7 }

		
		-- 1.3.6.1.4.1.388.11.3.3.1.2.1.8
		dot1xAuthEapolReqFramesTx OBJECT-TYPE
			SYNTAX Counter32
			MAX-ACCESS read-only
			STATUS current
			DESCRIPTION
				"The number of EAP Request frames
				(other than Rq/Id frames) that have been
				transmitted by this Authenticator.
				
				"
			::= { dot1xAuthStatsEntry 8 }

		
		-- 1.3.6.1.4.1.388.11.3.3.1.2.1.9
		dot1xAuthInvalidEapolFramesRx OBJECT-TYPE
			SYNTAX Counter32
			MAX-ACCESS read-only
			STATUS current
			DESCRIPTION
				"The number of EAPOL frames that have been
				received by this Authenticator in which the
				frame type is not recognized."
			::= { dot1xAuthStatsEntry 9 }

		
		-- 1.3.6.1.4.1.388.11.3.3.1.2.1.10
		dot1xAuthEapLengthErrorFramesRx OBJECT-TYPE
			SYNTAX Counter32
			MAX-ACCESS read-only
			STATUS current
			DESCRIPTION
				"The number of EAPOL frames that have been received
				by this Authenticator in which the Packet Body
				Length field is invalid.
				
				"
			::= { dot1xAuthStatsEntry 10 }

		
		-- 1.3.6.1.4.1.388.11.3.3.1.2.1.11
		dot1xAuthLastEapolFrameVersion OBJECT-TYPE
			SYNTAX OCTET STRING (SIZE (0..255))
			MAX-ACCESS read-only
			STATUS current
			DESCRIPTION
				"The protocol version number carried in the
				most recently received EAPOL frame.
				"
			::= { dot1xAuthStatsEntry 11 }

		
		-- 1.3.6.1.4.1.388.11.3.3.1.2.1.12
		dot1xAuthLastEapolFrameSource OBJECT-TYPE
			SYNTAX PhysAddress
			MAX-ACCESS read-only
			STATUS current
			DESCRIPTION
				"The source MAC address carried in the
				most recently received EAPOL frame.
				"
			::= { dot1xAuthStatsEntry 12 }

		
		-- 1.3.6.1.4.1.388.11.3.3.1.3
		dot1xAuthDiagTable OBJECT-TYPE
			SYNTAX SEQUENCE OF Dot1xAuthDiagEntry
			MAX-ACCESS not-accessible
			STATUS current
			DESCRIPTION
				"A table that contains the diagnostics objects for the
				Authenticator PAE associated with each Port.
				An entry appears in this table for each port that may
				authenticate access to itself.
				"
			::= { dot1xPaeAuthenticator 3 }

		
		-- 1.3.6.1.4.1.388.11.3.3.1.3.1
		dot1xAuthDiagEntry OBJECT-TYPE
			SYNTAX Dot1xAuthDiagEntry
			MAX-ACCESS not-accessible
			STATUS current
			DESCRIPTION
				"The diagnostics information for an Authenticator PAE.
				"
			INDEX { dot1xPaePortNumber }
			::= { dot1xAuthDiagTable 1 }

		
		Dot1xAuthDiagEntry ::=
			SEQUENCE { 
				dot1xAuthEntersConnecting
					Counter32,
				dot1xAuthEapLogoffsWhileConnecting
					Counter32,
				dot1xAuthEntersAuthenticating
					Counter32,
				dot1xAuthAuthSuccessWhileAuthenticating
					Counter32,
				dot1xAuthAuthTimeoutsWhileAuthenticating
					Counter32,
				dot1xAuthAuthFailWhileAuthenticating
					Counter32,
				dot1xAuthAuthReauthsWhileAuthenticating
					Counter32,
				dot1xAuthAuthEapStartsWhileAuthenticating
					Counter32,
				dot1xAuthAuthEapLogoffWhileAuthenticating
					Counter32,
				dot1xAuthAuthReauthsWhileAuthenticated
					Counter32,
				dot1xAuthAuthEapStartsWhileAuthenticated
					Counter32,
				dot1xAuthAuthEapLogoffWhileAuthenticated
					Counter32,
				dot1xAuthBackendResponses
					Counter32,
				dot1xAuthBackendAccessChallenges
					Counter32,
				dot1xAuthBackendOtherRequestsToSupplicant
					Counter32,
				dot1xAuthBackendNonNakResponsesFromSupplicant
					Counter32,
				dot1xAuthBackendAuthSuccesses
					Counter32,
				dot1xAuthBackendAuthFails
					Counter32
			 }

		-- 1.3.6.1.4.1.388.11.3.3.1.3.1.1
		dot1xAuthEntersConnecting OBJECT-TYPE
			SYNTAX Counter32
			MAX-ACCESS read-only
			STATUS current
			DESCRIPTION
				"Counts the number of times that the state machine
				transitions to the CONNECTING state from any other
				state.
				"
			::= { dot1xAuthDiagEntry 1 }

		
		-- 1.3.6.1.4.1.388.11.3.3.1.3.1.2
		dot1xAuthEapLogoffsWhileConnecting OBJECT-TYPE
			SYNTAX Counter32
			MAX-ACCESS read-only
			STATUS current
			DESCRIPTION
				"Counts the number of times that the state machine
				transitions from CONNECTING to DISCONNECTED as a result
				of receiving an EAPOL-Logoff message.
				"
			::= { dot1xAuthDiagEntry 2 }

		
		-- 1.3.6.1.4.1.388.11.3.3.1.3.1.3
		dot1xAuthEntersAuthenticating OBJECT-TYPE
			SYNTAX Counter32
			MAX-ACCESS read-only
			STATUS current
			DESCRIPTION
				"Counts the number of times that the state machine
				transitions from CONNECTING to AUTHENTICATING, as a
				result of an EAP-Response/Identity message being
				received from the Supplicant.
				"
			::= { dot1xAuthDiagEntry 3 }

		
		-- 1.3.6.1.4.1.388.11.3.3.1.3.1.4
		dot1xAuthAuthSuccessWhileAuthenticating OBJECT-TYPE
			SYNTAX Counter32
			MAX-ACCESS read-only
			STATUS current
			DESCRIPTION
				"Counts the number of times that the state machine
				transitions from AUTHENTICATING to AUTHENTICATED, as a
				result of the Backend Authentication state machine
				indicating successful authentication of the Supplicant
				(authSuccess = TRUE)."
			::= { dot1xAuthDiagEntry 4 }

		
		-- 1.3.6.1.4.1.388.11.3.3.1.3.1.5
		dot1xAuthAuthTimeoutsWhileAuthenticating OBJECT-TYPE
			SYNTAX Counter32
			MAX-ACCESS read-only
			STATUS current
			DESCRIPTION
				"Counts the number of times that the state machine
				transitions from AUTHENTICATING to ABORTING, as a result
				of the Backend Authentication state machine indicating
				authentication timeout (authTimeout = TRUE).
				"
			::= { dot1xAuthDiagEntry 5 }

		
		-- 1.3.6.1.4.1.388.11.3.3.1.3.1.6
		dot1xAuthAuthFailWhileAuthenticating OBJECT-TYPE
			SYNTAX Counter32
			MAX-ACCESS read-only
			STATUS current
			DESCRIPTION
				"Counts the number of times that the state machine
				transitions from AUTHENTICATING to HELD, as a result
				of the Backend Authentication state machine indicating
				authentication failure (authFail = TRUE).
				"
			::= { dot1xAuthDiagEntry 6 }

		
		-- 1.3.6.1.4.1.388.11.3.3.1.3.1.7
		dot1xAuthAuthReauthsWhileAuthenticating OBJECT-TYPE
			SYNTAX Counter32
			MAX-ACCESS read-only
			STATUS current
			DESCRIPTION
				"Counts the number of times that the state machine
				transitions from AUTHENTICATING to ABORTING, as a result
				of a reauthentication request (reAuthenticate = TRUE).
				"
			::= { dot1xAuthDiagEntry 7 }

		
		-- 1.3.6.1.4.1.388.11.3.3.1.3.1.8
		dot1xAuthAuthEapStartsWhileAuthenticating OBJECT-TYPE
			SYNTAX Counter32
			MAX-ACCESS read-only
			STATUS current
			DESCRIPTION
				"Counts the number of times that the state machine
				transitions from AUTHENTICATING to ABORTING, as a result
				of an EAPOL-Start message being received
				from the Supplicant.
				"
			::= { dot1xAuthDiagEntry 8 }

		
		-- 1.3.6.1.4.1.388.11.3.3.1.3.1.9
		dot1xAuthAuthEapLogoffWhileAuthenticating OBJECT-TYPE
			SYNTAX Counter32
			MAX-ACCESS read-only
			STATUS current
			DESCRIPTION
				"Counts the number of times that the state machine
				transitions from AUTHENTICATING to ABORTING, as a result
				of an EAPOL-Logoff message being received
				from the Supplicant.
				"
			::= { dot1xAuthDiagEntry 9 }

		
		-- 1.3.6.1.4.1.388.11.3.3.1.3.1.10
		dot1xAuthAuthReauthsWhileAuthenticated OBJECT-TYPE
			SYNTAX Counter32
			MAX-ACCESS read-only
			STATUS current
			DESCRIPTION
				"Counts the number of times that the state machine
				transitions from AUTHENTICATED to CONNECTING, as a
				result of a reauthentication request
				(reAuthenticate = TRUE).
				"
			::= { dot1xAuthDiagEntry 10 }

		
		-- 1.3.6.1.4.1.388.11.3.3.1.3.1.11
		dot1xAuthAuthEapStartsWhileAuthenticated OBJECT-TYPE
			SYNTAX Counter32
			MAX-ACCESS read-only
			STATUS current
			DESCRIPTION
				"Counts the number of times that the state machine
				transitions from AUTHENTICATED to CONNECTING, as a
				result of an EAPOL-Start message being received from the
				Supplicant.
				"
			::= { dot1xAuthDiagEntry 11 }

		
		-- 1.3.6.1.4.1.388.11.3.3.1.3.1.12
		dot1xAuthAuthEapLogoffWhileAuthenticated OBJECT-TYPE
			SYNTAX Counter32
			MAX-ACCESS read-only
			STATUS current
			DESCRIPTION
				"Counts the number of times that the state machine
				transitions from AUTHENTICATED to DISCONNECTED, as a
				result of an EAPOL-Logoff message being received from
				the Supplicant.
				"
			::= { dot1xAuthDiagEntry 12 }

		
		-- 1.3.6.1.4.1.388.11.3.3.1.3.1.13
		dot1xAuthBackendResponses OBJECT-TYPE
			SYNTAX Counter32
			MAX-ACCESS read-only
			STATUS current
			DESCRIPTION
				"Counts the number of times that the state machine sends
				an initial Access-Request packet to the Authentication
				server (i.e., executes sendRespToServer on entry to the
				RESPONSE state). Indicates that the Authenticator
				attempted communication with the Authentication Server.
				"
			::= { dot1xAuthDiagEntry 13 }

		
		-- 1.3.6.1.4.1.388.11.3.3.1.3.1.14
		dot1xAuthBackendAccessChallenges OBJECT-TYPE
			SYNTAX Counter32
			MAX-ACCESS read-only
			STATUS current
			DESCRIPTION
				"Counts the number of times that the state machine
				receives an initial Access-Challenge packet from the
				Authentication server (i.e., aReq becomes TRUE,
				causing exit from the RESPONSE state). Indicates that
				the Authentication Server has communication with
				the Authenticator.
				"
			::= { dot1xAuthDiagEntry 14 }

		
		-- 1.3.6.1.4.1.388.11.3.3.1.3.1.15
		dot1xAuthBackendOtherRequestsToSupplicant OBJECT-TYPE
			SYNTAX Counter32
			MAX-ACCESS read-only
			STATUS current
			DESCRIPTION
				"Counts the number of times that the state machine
				sends an EAP-Request packet (other than an Identity,
				Notification, Failure or Success message) to the
				Supplicant (i.e., executes txReq on entry to the
				REQUEST state). Indicates that the Authenticator chose
				an EAP-method."
			::= { dot1xAuthDiagEntry 15 }

		
		-- 1.3.6.1.4.1.388.11.3.3.1.3.1.16
		dot1xAuthBackendNonNakResponsesFromSupplicant OBJECT-TYPE
			SYNTAX Counter32
			MAX-ACCESS read-only
			STATUS current
			DESCRIPTION
				"Counts the number of times that the state machine
				receives a response from the Supplicant to an initial
				EAP-Request, and the response is something other than
				EAP-NAK (i.e., rxResp becomes TRUE, causing the state
				machine to transition from REQUEST to RESPONSE,
				and the response is not an EAP-NAK). Indicates that
				the Supplicant can respond to the Authenticator's
				chosen EAP-method.
				"
			::= { dot1xAuthDiagEntry 16 }

		
		-- 1.3.6.1.4.1.388.11.3.3.1.3.1.17
		dot1xAuthBackendAuthSuccesses OBJECT-TYPE
			SYNTAX Counter32
			MAX-ACCESS read-only
			STATUS current
			DESCRIPTION
				"Counts the number of times that the state machine
				receives an EAP-Success message from the Authentication
				Server (i.e., aSuccess becomes TRUE, causing a
				transition from RESPONSE to SUCCESS). Indicates that
				the Supplicant has successfully authenticated to
				the Authentication Server.
				"
			::= { dot1xAuthDiagEntry 17 }

		
		-- 1.3.6.1.4.1.388.11.3.3.1.3.1.18
		dot1xAuthBackendAuthFails OBJECT-TYPE
			SYNTAX Counter32
			MAX-ACCESS read-only
			STATUS current
			DESCRIPTION
				"Counts the number of times that the state machine
				receives an EAP-Failure message from the Authentication
				Server (i.e., aFail becomes TRUE, causing a transition
				from RESPONSE to FAIL). Indicates that the Supplicant
				has not authenticated to the Authentication Server.
				"
			::= { dot1xAuthDiagEntry 18 }

		
		-- 1.3.6.1.4.1.388.11.3.3.1.4
		dot1xAuthSessionStatsTable OBJECT-TYPE
			SYNTAX SEQUENCE OF Dot1xAuthSessionStatsEntry
			MAX-ACCESS not-accessible
			STATUS current
			DESCRIPTION
				"A table that contains the session statistics objects
				for the Authenticator PAE associated with each Port.
				An entry appears in this table for each port that may
				authenticate access to itself.
				"
			::= { dot1xPaeAuthenticator 4 }

		
		-- 1.3.6.1.4.1.388.11.3.3.1.4.1
		dot1xAuthSessionStatsEntry OBJECT-TYPE
			SYNTAX Dot1xAuthSessionStatsEntry
			MAX-ACCESS not-accessible
			STATUS current
			DESCRIPTION
				"The session statistics information for an Authenticator
				PAE. This shows the current values being collected for
				each session that is still in progress, or the final
				values for the last valid session on each port where
				there is no session currently active.
				"
			INDEX { dot1xPaePortNumber }
			::= { dot1xAuthSessionStatsTable 1 }

		
		Dot1xAuthSessionStatsEntry ::=
			SEQUENCE { 
				dot1xAuthSessionOctetsRx
					Counter32,
				dot1xAuthSessionOctetsTx
					Counter32,
				dot1xAuthSessionFramesRx
					Counter32,
				dot1xAuthSessionFramesTx
					Counter32,
				dot1xAuthSessionId
					OCTET STRING,
				dot1xAuthSessionAuthenticMethod
					INTEGER,
				dot1xAuthSessionTime
					TimeTicks,
				dot1xAuthSessionTerminateCause
					INTEGER,
				dot1xAuthSessionUserName
					OCTET STRING
			 }

		-- 1.3.6.1.4.1.388.11.3.3.1.4.1.1
		dot1xAuthSessionOctetsRx OBJECT-TYPE
			SYNTAX Counter32
			MAX-ACCESS read-only
			STATUS current
			DESCRIPTION
				"The number of octets received in user data
				frames on this Port during the session.
				"
			::= { dot1xAuthSessionStatsEntry 1 }

		
		-- 1.3.6.1.4.1.388.11.3.3.1.4.1.2
		dot1xAuthSessionOctetsTx OBJECT-TYPE
			SYNTAX Counter32
			MAX-ACCESS read-only
			STATUS current
			DESCRIPTION
				"The number of octets transmitted in user data
				frames on this Port during the session.
				"
			::= { dot1xAuthSessionStatsEntry 2 }

		
		-- 1.3.6.1.4.1.388.11.3.3.1.4.1.3
		dot1xAuthSessionFramesRx OBJECT-TYPE
			SYNTAX Counter32
			MAX-ACCESS read-only
			STATUS current
			DESCRIPTION
				"The number of user data frames received
				on this Port during the session.
				"
			::= { dot1xAuthSessionStatsEntry 3 }

		
		-- 1.3.6.1.4.1.388.11.3.3.1.4.1.4
		dot1xAuthSessionFramesTx OBJECT-TYPE
			SYNTAX Counter32
			MAX-ACCESS read-only
			STATUS current
			DESCRIPTION
				"The number of user data frames transmitted
				on this Port during the session.
				"
			::= { dot1xAuthSessionStatsEntry 4 }

		
		-- 1.3.6.1.4.1.388.11.3.3.1.4.1.5
		dot1xAuthSessionId OBJECT-TYPE
			SYNTAX OCTET STRING (SIZE (0..255))
			MAX-ACCESS read-only
			STATUS current
			DESCRIPTION
				"A unique identifier for the session, in the
				form of a printable ASCII string of at least
				three characters.
				"
			::= { dot1xAuthSessionStatsEntry 5 }

		
		-- 1.3.6.1.4.1.388.11.3.3.1.4.1.6
		dot1xAuthSessionAuthenticMethod OBJECT-TYPE
			SYNTAX INTEGER
				{
				remoteAuthServer(1),
				localAuthServer(2)
				}
			MAX-ACCESS read-only
			STATUS current
			DESCRIPTION
				"The authentication method used to establish the
				session.
				"
			::= { dot1xAuthSessionStatsEntry 6 }

		
		-- 1.3.6.1.4.1.388.11.3.3.1.4.1.7
		dot1xAuthSessionTime OBJECT-TYPE
			SYNTAX TimeTicks
			MAX-ACCESS read-only
			STATUS current
			DESCRIPTION
				"The duration of the session in seconds.
				"
			::= { dot1xAuthSessionStatsEntry 7 }

		
		-- 1.3.6.1.4.1.388.11.3.3.1.4.1.8
		dot1xAuthSessionTerminateCause OBJECT-TYPE
			SYNTAX INTEGER
				{
				supplicantLogoff(1),
				portFailure(2),
				supplicantRestart(3),
				reauthFailed(4),
				authControlForceUnauth(5),
				portReInit(6),
				portAdminDisabled(7),
				notTerminatedYet(999)
				}
			MAX-ACCESS read-only
			STATUS current
			DESCRIPTION
				"The reason for the session termination."
			::= { dot1xAuthSessionStatsEntry 8 }

		
		-- 1.3.6.1.4.1.388.11.3.3.1.4.1.9
		dot1xAuthSessionUserName OBJECT-TYPE
			SYNTAX OCTET STRING (SIZE (0..255))
			MAX-ACCESS read-only
			STATUS current
			DESCRIPTION
				"The User-Name representing the identity of the
				Supplicant PAE.
				"
			::= { dot1xAuthSessionStatsEntry 9 }

		
		-- 1.3.6.1.4.1.388.11.3.4
		apRf OBJECT IDENTIFIER ::= { abgAP 4 }

		
-- This group contains MIB values that describe the
-- Portals known to and adopted by this AP5131.
-- 
-- An Access Port will contain 1, 2, (and in the 
-- future, possibly more), 'Portals'.  Such Portals
-- may be thought of as the radio portion of an
-- Access Port.
-- 
-- Descriptions of each data item are only provided here in 
-- the Portal tables, (since it occurs first in the MIB).
-- For the nearly identical values in the MU and WLAN tables,
-- refer back to the descriptions found here.  (Did this to 
-- avoid massive cut-and-paste which later leads to 
-- discrepencies and inconsistencies when changes are 
-- incorrectly made to the descriptions in one location but 
-- not the others).
		-- 1.3.6.1.4.1.388.11.3.4.1
		apRadio OBJECT IDENTIFIER ::= { apRf 1 }

		
		-- 1.3.6.1.4.1.388.11.3.4.1.1
		apRadioSettingsTable OBJECT-TYPE
			SYNTAX SEQUENCE OF ApRadioSettingsEntry
			MAX-ACCESS not-accessible
			STATUS current
			DESCRIPTION
				"Use apRadioSettingsTable to view and set the properties
				of the radios.
				
				"
			::= { apRadio 1 }

		
		-- 1.3.6.1.4.1.388.11.3.4.1.1.1
		apRadioSettingsEntry OBJECT-TYPE
			SYNTAX ApRadioSettingsEntry
			MAX-ACCESS not-accessible
			STATUS current
			DESCRIPTION
				" "
			INDEX { apRadioSettingsIndex }
			::= { apRadioSettingsTable 1 }

		
		ApRadioSettingsEntry ::=
			SEQUENCE { 
				apRadioSettingsIndex
					Integer32,
				apRadioSettingsEnable
					TruthValue,
				apRadioSettingsBand
					INTEGER,
				apRadioSettingsPointersToWlans
					MultiPointer63,
				apRadioSettingsName
					INTEGER,
				apRadioSettingsMacAddress
					PhysAddress,
				apRadioSettingsAntenna
					INTEGER,
				apRadioSettingsShortPreamble
					TruthValue,
				apRadioSettingsRtsThresh
					Integer32,
				apRadioSettingsBeaconInt
					Integer32,
				apRadioSettingsDtimPrd
					Integer32,
				apRadioSettingsBasicRates
					BITS,
				apRadioSettingsSupportedRates
					BITS,
				apRadioSettingsBGMode
					INTEGER,
				apRadioSettingsBackgroundMode
					TruthValue,
				apRadioSettingsBackgroundCwMin
					Integer32,
				apRadioSettingsBackgroundCwMax
					Integer32,
				apRadioSettingsBackgroundAifsn
					Integer32,
				apRadioSettingsBackgroundTxopsTime
					Integer32,
				apRadioSettingsBackgroundTxopsTimeInMS
					Integer32,
				apRadioSettingsBestEffortMode
					TruthValue,
				apRadioSettingsBestEffortCwMin
					Integer32,
				apRadioSettingsBestEffortCwMax
					Integer32,
				apRadioSettingsBestEffortAifsn
					Integer32,
				apRadioSettingsBestEffortTxopsTime
					Integer32,
				apRadioSettingsBestEffortTxopsTimeInMS
					Integer32,
				apRadioSettingsVideoMode
					TruthValue,
				apRadioSettingsVideoCwMin
					Integer32,
				apRadioSettingsVideoCwMax
					Integer32,
				apRadioSettingsVideoAifsn
					Integer32,
				apRadioSettingsVideoTxopsTime
					Integer32,
				apRadioSettingsVideoTxopsTimeInMS
					Integer32,
				apRadioSettingsVoiceMode
					TruthValue,
				apRadioSettingsVoiceCwMin
					Integer32,
				apRadioSettingsVoiceCwMax
					Integer32,
				apRadioSettingsVoiceAifsn
					Integer32,
				apRadioSettingsVoiceTxopsTime
					Integer32,
				apRadioSettingsVoiceTxopsTimeInMS
					Integer32,
				apRadioSettingsE2BMapMessage
					DisplayString,
				apRadioSettingsERPProtectionStatus
					TruthValue,
				apRadioSettingsWMMQosParam
					INTEGER,
				apRadioSettingsQBSSChannelBeaconInt
					Integer32,
				apRadioSettingsQBSSLoadElementMode
					INTEGER
			 }

		-- 1.3.6.1.4.1.388.11.3.4.1.1.1.1
		apRadioSettingsIndex OBJECT-TYPE
			SYNTAX Integer32 (1..2)
			MAX-ACCESS accessible-for-notify
			STATUS current
			DESCRIPTION
				" Simple index."
			::= { apRadioSettingsEntry 1 }

		
		-- 1.3.6.1.4.1.388.11.3.4.1.1.1.2
		apRadioSettingsEnable OBJECT-TYPE
			SYNTAX TruthValue
			MAX-ACCESS read-write
			STATUS current
			DESCRIPTION
				"Row enable."
			::= { apRadioSettingsEntry 2 }

		
		-- 1.3.6.1.4.1.388.11.3.4.1.1.1.3
		apRadioSettingsBand OBJECT-TYPE
			SYNTAX INTEGER
				{
				aRadio(1),
				bgRadio(2)
				}
			MAX-ACCESS read-write
			STATUS current
			DESCRIPTION
				"In a system that contains only 1 radio, Radio 1
				can be configured for 802.11b/g or 802.11a.
				
				In a system that contains 2 radios, Radio 1 will
				be configured for 802.11b/g and Radio 2 will be
				configured for 802.11a regardless of the user setting.
				One will get a set-fail if attempts to make a change.
				
				Note that 'aRadio' means an 802.11a standard radio that uses the 5.0 GHz band, and, 
				'bgRadio' means an 802.11b and 802.11g standards radio that use the 2.4 GHz band.
				An 802.11n radio can use both 2.4 GHz and/or 5.0 GHz bands, so, both these values 
				are applicable for an 802.11n radio."
			::= { apRadioSettingsEntry 3 }

		
		-- 1.3.6.1.4.1.388.11.3.4.1.1.1.4
		apRadioSettingsPointersToWlans OBJECT-TYPE
			SYNTAX MultiPointer63
			MAX-ACCESS read-only
			STATUS current
			DESCRIPTION
				"This scalar points to multiple WLANs that use this radio."
			::= { apRadioSettingsEntry 4 }

		
		-- 1.3.6.1.4.1.388.11.3.4.1.1.1.5
		apRadioSettingsName OBJECT-TYPE
			SYNTAX INTEGER
				{
				radio802dt11a(1),
				radio802dt11bg(2),
				radio802dt11n2400MHz(3),
				radio802dt11n5000MHz(4)
				}
			MAX-ACCESS read-only
			STATUS current
			DESCRIPTION
				"Name of Radio.
				
				Note that 'radio802dt11a' means an 802.11a standard radio that uses the 
				5GHz band, and, 'radio802dt11bg' means an 802.11b and 802.11g standards 
				radio that use the 2.4 GHz band.
				An 802.11n radio can use both 2.4 GHz and/or 5.0 GHz bands, so, both these values 
				are applicable for an 802.11n radio."
			::= { apRadioSettingsEntry 5 }

		
		-- 1.3.6.1.4.1.388.11.3.4.1.1.1.6
		apRadioSettingsMacAddress OBJECT-TYPE
			SYNTAX PhysAddress
			MAX-ACCESS read-only
			STATUS current
			DESCRIPTION
				"MAC address of the radio."
			::= { apRadioSettingsEntry 6 }

		
		-- 1.3.6.1.4.1.388.11.3.4.1.1.1.7
		apRadioSettingsAntenna OBJECT-TYPE
			SYNTAX INTEGER
				{
				fullDiversity(1),
				primaryOnly(2),
				secondaryOnly(3)
				}
			MAX-ACCESS read-write
			STATUS current
			DESCRIPTION
				"The antenna diversity setting for the radio.
				
				Note that this setting does not apply for an 802.11n radio."
			::= { apRadioSettingsEntry 7 }

		
		-- 1.3.6.1.4.1.388.11.3.4.1.1.1.8
		apRadioSettingsShortPreamble OBJECT-TYPE
			SYNTAX TruthValue
			MAX-ACCESS read-write
			STATUS current
			DESCRIPTION
				"Enable support for Short Preamble when MUs 
				associate with the Access Point.  Enabling Short
				Preamble may cause incompatibility with some older
				clients."
			::= { apRadioSettingsEntry 8 }

		
		-- 1.3.6.1.4.1.388.11.3.4.1.1.1.9
		apRadioSettingsRtsThresh OBJECT-TYPE
			SYNTAX Integer32
			MAX-ACCESS read-write
			STATUS current
			DESCRIPTION
				"The Request To Send(RTS) threshold(in bytes) for use
				by the radio for the WLAN."
			::= { apRadioSettingsEntry 9 }

		
		-- 1.3.6.1.4.1.388.11.3.4.1.1.1.10
		apRadioSettingsBeaconInt OBJECT-TYPE
			SYNTAX Integer32 (50..200)
			MAX-ACCESS read-write
			STATUS current
			DESCRIPTION
				"Specify a beacon interval in units of 1,000 
				microseconds (K-us). This is a multiple of the DTIM 
				(apRadioSettingDtimPrd) value, for example, 
				100 : 10. "
			::= { apRadioSettingsEntry 10 }

		
		-- 1.3.6.1.4.1.388.11.3.4.1.1.1.11
		apRadioSettingsDtimPrd OBJECT-TYPE
			SYNTAX Integer32 (1..50)
			MAX-ACCESS read-write
			STATUS current
			DESCRIPTION
				"Specify a period for the Delivery Traffic Indication 
				Message (DTIM). This is a divisor of the beacon 
				interval (in milliseconds), for example, 10 : 100. 
				
				Note that this object's status is current for 802.11n radios, 
				whereas it is obsolete for a/b/g radios."
			::= { apRadioSettingsEntry 11 }

		
		-- 1.3.6.1.4.1.388.11.3.4.1.1.1.12
		apRadioSettingsBasicRates OBJECT-TYPE
			SYNTAX BITS
				{
				null(0),
				rate1Mb(1),
				rate2Mb(2),
				rate5pt5Mb(3),
				rate6Mb(4),
				rate9Mb(5),
				rate11Mb(6),
				rate12Mb(7),
				rate18Mb(8),
				rate22Mb(9),
				rate24Mb(10),
				rate36Mb(11),
				rate48Mb(12),
				rate54Mb(13)
				}
			MAX-ACCESS read-write
			STATUS current
			DESCRIPTION
				"List of basic rates for the radio.
				
				Note that this setting does not apply for an 802.11n radio."
			::= { apRadioSettingsEntry 12 }

		
		-- 1.3.6.1.4.1.388.11.3.4.1.1.1.13
		apRadioSettingsSupportedRates OBJECT-TYPE
			SYNTAX BITS
				{
				null(0),
				rate1Mb(1),
				rate2Mb(2),
				rate5pt5Mb(3),
				rate6Mb(4),
				rate9Mb(5),
				rate11Mb(6),
				rate12Mb(7),
				rate18Mb(8),
				rate22Mb(9),
				rate24Mb(10),
				rate36Mb(11),
				rate48Mb(12),
				rate54Mb(13)
				}
			MAX-ACCESS read-write
			STATUS current
			DESCRIPTION
				"List of supported rates for the radio."
			::= { apRadioSettingsEntry 13 }

		
		-- 1.3.6.1.4.1.388.11.3.4.1.1.1.14
		apRadioSettingsBGMode OBJECT-TYPE
			SYNTAX INTEGER
				{
				modeBandG(1),
				modeG(2),
				modeB(3)
				}
			MAX-ACCESS read-write
			STATUS current
			DESCRIPTION
				"Radio mode.
				
				Note that this setting does not apply for an 802.11n radio.
				Please use the object apRadioNSettingsMode under apRadioNSettingsTable 
				for 802.11n radios."
			::= { apRadioSettingsEntry 14 }

		
		-- 1.3.6.1.4.1.388.11.3.4.1.1.1.15
		apRadioSettingsBackgroundMode OBJECT-TYPE
			SYNTAX TruthValue
			MAX-ACCESS read-write
			STATUS obsolete
			DESCRIPTION
				"This QOS parameter is used by the AP for the
				Background access category."
			::= { apRadioSettingsEntry 15 }

		
		-- 1.3.6.1.4.1.388.11.3.4.1.1.1.16
		apRadioSettingsBackgroundCwMin OBJECT-TYPE
			SYNTAX Integer32
			MAX-ACCESS read-write
			STATUS current
			DESCRIPTION
				"This QOS parameter is used by the AP for the
				Background access category."
			::= { apRadioSettingsEntry 16 }

		
		-- 1.3.6.1.4.1.388.11.3.4.1.1.1.17
		apRadioSettingsBackgroundCwMax OBJECT-TYPE
			SYNTAX Integer32
			MAX-ACCESS read-write
			STATUS current
			DESCRIPTION
				"This QOS parameter is used by the AP for the
				Background access category."
			::= { apRadioSettingsEntry 17 }

		
		-- 1.3.6.1.4.1.388.11.3.4.1.1.1.18
		apRadioSettingsBackgroundAifsn OBJECT-TYPE
			SYNTAX Integer32
			MAX-ACCESS read-write
			STATUS current
			DESCRIPTION
				"This QOS parameter is used by the AP for the
				Background access category."
			::= { apRadioSettingsEntry 18 }

		
		-- 1.3.6.1.4.1.388.11.3.4.1.1.1.19
		apRadioSettingsBackgroundTxopsTime OBJECT-TYPE
			SYNTAX Integer32
			MAX-ACCESS read-write
			STATUS current
			DESCRIPTION
				"This QOS parameter is used by the AP for the
				Background access category."
			::= { apRadioSettingsEntry 19 }

		
		-- 1.3.6.1.4.1.388.11.3.4.1.1.1.20
		apRadioSettingsBackgroundTxopsTimeInMS OBJECT-TYPE
			SYNTAX Integer32
			MAX-ACCESS read-only
			STATUS current
			DESCRIPTION
				"This QOS parameter is used by the AP for the
				Background access category."
			::= { apRadioSettingsEntry 20 }

		
		-- 1.3.6.1.4.1.388.11.3.4.1.1.1.21
		apRadioSettingsBestEffortMode OBJECT-TYPE
			SYNTAX TruthValue
			MAX-ACCESS read-write
			STATUS obsolete
			DESCRIPTION
				"This QOS parameter is used by the AP for the
				Best Effort access category."
			::= { apRadioSettingsEntry 21 }

		
		-- 1.3.6.1.4.1.388.11.3.4.1.1.1.22
		apRadioSettingsBestEffortCwMin OBJECT-TYPE
			SYNTAX Integer32
			MAX-ACCESS read-write
			STATUS current
			DESCRIPTION
				"This QOS parameter is used by the AP for the
				Best Effort access category."
			::= { apRadioSettingsEntry 22 }

		
		-- 1.3.6.1.4.1.388.11.3.4.1.1.1.23
		apRadioSettingsBestEffortCwMax OBJECT-TYPE
			SYNTAX Integer32
			MAX-ACCESS read-write
			STATUS current
			DESCRIPTION
				"This QOS parameter is used by the AP for the
				Best Effort access category."
			::= { apRadioSettingsEntry 23 }

		
		-- 1.3.6.1.4.1.388.11.3.4.1.1.1.24
		apRadioSettingsBestEffortAifsn OBJECT-TYPE
			SYNTAX Integer32
			MAX-ACCESS read-write
			STATUS current
			DESCRIPTION
				"This QOS parameter is used by the AP for the
				Best Effort access category."
			::= { apRadioSettingsEntry 24 }

		
		-- 1.3.6.1.4.1.388.11.3.4.1.1.1.25
		apRadioSettingsBestEffortTxopsTime OBJECT-TYPE
			SYNTAX Integer32
			MAX-ACCESS read-write
			STATUS current
			DESCRIPTION
				"This QOS parameter is used by the AP for the
				Best Effort access category."
			::= { apRadioSettingsEntry 25 }

		
		-- 1.3.6.1.4.1.388.11.3.4.1.1.1.26
		apRadioSettingsBestEffortTxopsTimeInMS OBJECT-TYPE
			SYNTAX Integer32
			MAX-ACCESS read-only
			STATUS current
			DESCRIPTION
				"This QOS parameter is used by the AP for the
				Best Effort access category."
			::= { apRadioSettingsEntry 26 }

		
		-- 1.3.6.1.4.1.388.11.3.4.1.1.1.27
		apRadioSettingsVideoMode OBJECT-TYPE
			SYNTAX TruthValue
			MAX-ACCESS read-write
			STATUS obsolete
			DESCRIPTION
				"This QOS parameter is used by the AP for the
				Video access category."
			::= { apRadioSettingsEntry 27 }

		
		-- 1.3.6.1.4.1.388.11.3.4.1.1.1.28
		apRadioSettingsVideoCwMin OBJECT-TYPE
			SYNTAX Integer32
			MAX-ACCESS read-write
			STATUS current
			DESCRIPTION
				"This QOS parameter is used by the AP for the
				Video access category."
			::= { apRadioSettingsEntry 28 }

		
		-- 1.3.6.1.4.1.388.11.3.4.1.1.1.29
		apRadioSettingsVideoCwMax OBJECT-TYPE
			SYNTAX Integer32
			MAX-ACCESS read-write
			STATUS current
			DESCRIPTION
				"This QOS parameter is used by the AP for the
				Video access category."
			::= { apRadioSettingsEntry 29 }

		
		-- 1.3.6.1.4.1.388.11.3.4.1.1.1.30
		apRadioSettingsVideoAifsn OBJECT-TYPE
			SYNTAX Integer32
			MAX-ACCESS read-write
			STATUS current
			DESCRIPTION
				"This QOS parameter is used by the AP for the
				Video access category."
			::= { apRadioSettingsEntry 30 }

		
		-- 1.3.6.1.4.1.388.11.3.4.1.1.1.31
		apRadioSettingsVideoTxopsTime OBJECT-TYPE
			SYNTAX Integer32
			MAX-ACCESS read-write
			STATUS current
			DESCRIPTION
				"This QOS parameter is used by the AP for the
				Video access category."
			::= { apRadioSettingsEntry 31 }

		
		-- 1.3.6.1.4.1.388.11.3.4.1.1.1.32
		apRadioSettingsVideoTxopsTimeInMS OBJECT-TYPE
			SYNTAX Integer32
			MAX-ACCESS read-only
			STATUS current
			DESCRIPTION
				"This QOS parameter is used by the AP for the
				Video access category."
			::= { apRadioSettingsEntry 32 }

		
		-- 1.3.6.1.4.1.388.11.3.4.1.1.1.33
		apRadioSettingsVoiceMode OBJECT-TYPE
			SYNTAX TruthValue
			MAX-ACCESS read-write
			STATUS obsolete
			DESCRIPTION
				"This QOS parameter is used by the AP for the
				Voice access category."
			::= { apRadioSettingsEntry 33 }

		
		-- 1.3.6.1.4.1.388.11.3.4.1.1.1.34
		apRadioSettingsVoiceCwMin OBJECT-TYPE
			SYNTAX Integer32
			MAX-ACCESS read-write
			STATUS current
			DESCRIPTION
				"This QOS parameter is used by the AP for the
				Voice access category."
			::= { apRadioSettingsEntry 34 }

		
		-- 1.3.6.1.4.1.388.11.3.4.1.1.1.35
		apRadioSettingsVoiceCwMax OBJECT-TYPE
			SYNTAX Integer32
			MAX-ACCESS read-write
			STATUS current
			DESCRIPTION
				"This QOS parameter is used by the AP for the
				Voice access category."
			::= { apRadioSettingsEntry 35 }

		
		-- 1.3.6.1.4.1.388.11.3.4.1.1.1.36
		apRadioSettingsVoiceAifsn OBJECT-TYPE
			SYNTAX Integer32
			MAX-ACCESS read-write
			STATUS current
			DESCRIPTION
				"This QOS parameter is used by the AP for the
				Voice access category."
			::= { apRadioSettingsEntry 36 }

		
		-- 1.3.6.1.4.1.388.11.3.4.1.1.1.37
		apRadioSettingsVoiceTxopsTime OBJECT-TYPE
			SYNTAX Integer32
			MAX-ACCESS read-write
			STATUS current
			DESCRIPTION
				"This QOS parameter is used by the AP for the
				Voice access category."
			::= { apRadioSettingsEntry 37 }

		
		-- 1.3.6.1.4.1.388.11.3.4.1.1.1.38
		apRadioSettingsVoiceTxopsTimeInMS OBJECT-TYPE
			SYNTAX Integer32
			MAX-ACCESS read-only
			STATUS current
			DESCRIPTION
				"This QOS parameter is used by the AP for the
				Voice access category."
			::= { apRadioSettingsEntry 38 }

		
		-- 1.3.6.1.4.1.388.11.3.4.1.1.1.39
		apRadioSettingsE2BMapMessage OBJECT-TYPE
			SYNTAX DisplayString
			MAX-ACCESS read-only
			STATUS current
			DESCRIPTION
				"Global ESS to BSS mapping status message."
			::= { apRadioSettingsEntry 39 }

		
		-- 1.3.6.1.4.1.388.11.3.4.1.1.1.40
		apRadioSettingsERPProtectionStatus OBJECT-TYPE
			SYNTAX TruthValue
			MAX-ACCESS read-only
			STATUS current
			DESCRIPTION
				"Whether ERP Protection is ON or OFF."
			::= { apRadioSettingsEntry 40 }

		
		-- 1.3.6.1.4.1.388.11.3.4.1.1.1.41
		apRadioSettingsWMMQosParam OBJECT-TYPE
			SYNTAX INTEGER
				{
				manual(1),
				wifi11agn(2),
				wifi11b(3),
				default11agn(4),
				default11b(5),
				voice11agn(6),
				voice11b(7)
				}
			MAX-ACCESS read-write
			STATUS current
			DESCRIPTION
				"Pre-Programmed WMM QOS Parameters.
				manual - Modify parameters
				wifi11agn - WiFi 11a/11g/11n defaults
				wifi11b  - WiFi 11b defaults
				default11agn - Symbol 11a/11g/11n defaults
				default11b  - Symbol 11b defaults
				voice11agn - Symbol 11a/11g/11n voice params
				voice11b  - Symbol 11b voice params"
			::= { apRadioSettingsEntry 41 }

		
		-- 1.3.6.1.4.1.388.11.3.4.1.1.1.42
		apRadioSettingsQBSSChannelBeaconInt OBJECT-TYPE
			SYNTAX Integer32 (10..200)
			MAX-ACCESS read-write
			STATUS current
			DESCRIPTION
				"Channel Utilization Beacon Intervals for QBSS Load Element (802.11e)"
			::= { apRadioSettingsEntry 42 }

		
		-- 1.3.6.1.4.1.388.11.3.4.1.1.1.43
		apRadioSettingsQBSSLoadElementMode OBJECT-TYPE
			SYNTAX INTEGER
				{
				disable(0),
				enable(1)
				}
			MAX-ACCESS read-write
			STATUS current
			DESCRIPTION
				"Enable/Disable QBSS Load Element."
			::= { apRadioSettingsEntry 43 }

		
		-- 1.3.6.1.4.1.388.11.3.4.1.2
		apRadioCfgTable OBJECT-TYPE
			SYNTAX SEQUENCE OF ApRadioCfgEntry
			MAX-ACCESS not-accessible
			STATUS current
			DESCRIPTION
				"Use apRadioCfgTable to view and set the radio 
				properties of the Access Points.
				
				
				The process can be broken down into the following steps:
				1. Set apRadioCfgReset to TRUE.
				2. Set apRadioCfgDesPlacement
				3. Get apRadioCfgPosChannel
				4. Set apRadioCfgDesChannel
				5. Get apRadioCfgPosPowerLevel
				6. Set apRadioCfgDesPowerLevel
				7. Get apRadioCfgPowerInMW
				8. Set and pull progress of apRadioCfgSet 
				9. Validate the configuration has been set by getting
				     apRadioCfgPlacement
				     apRadioCfgChannel
				     apRadioCfgPowerLevel
				
				"
			::= { apRadio 2 }

		
		-- 1.3.6.1.4.1.388.11.3.4.1.2.1
		apRadioCfgEntry OBJECT-TYPE
			SYNTAX ApRadioCfgEntry
			MAX-ACCESS not-accessible
			STATUS current
			DESCRIPTION
				" "
			INDEX { apRadioSettingsIndex }
			::= { apRadioCfgTable 1 }

		
		ApRadioCfgEntry ::=
			SEQUENCE { 
				apRadioCfgChannelMode
					INTEGER,
				apRadioCfgDesPlacement
					INTEGER,
				apRadioCfgPosChannel
					BITS,
				apRadioCfgDesChannel
					INTEGER,
				apRadioCfgPosPowerLevel
					Integer32,
				apRadioCfgDesPowerLevel
					Integer32,
				apRadioCfgDesPowerInMW
					Integer32,
				apRadioCfgSet
					DoActionShowProgress,
				apRadioCfgReset
					DoActionShowProgress,
				apRadioCfgPlacement
					INTEGER,
				apRadioCfgChannel
					INTEGER,
				apRadioCfgPowerLevel
					Integer32,
				apRadioCfgPowerInMW
					Integer32,
				apRadioCfgRfFunction
					INTEGER,
				apRadioCfgExceptionChannel
					BITS
			 }

		-- 1.3.6.1.4.1.388.11.3.4.1.2.1.1
		apRadioCfgChannelMode OBJECT-TYPE
			SYNTAX INTEGER
				{
				userSelect(1),
				autoSelect(2),
				uniformSpreading(3),
				autoSelect40(4),
				uniformSpreading40(5)
				}
			MAX-ACCESS read-write
			STATUS current
			DESCRIPTION
				"Channel Mode for the Radio.
				The user is allowed to enter the apRadioDesChannel
				value only if the Channel Mode is Set to userSelect.
				
				The values autoSelect40(4) and uniformSpreading40(5) are 
				applicable only in case of 802.11n radios."
			::= { apRadioCfgEntry 1 }

		
		-- 1.3.6.1.4.1.388.11.3.4.1.2.1.2
		apRadioCfgDesPlacement OBJECT-TYPE
			SYNTAX INTEGER
				{
				indoor(1),
				outdoor(2)
				}
			MAX-ACCESS read-write
			STATUS current
			DESCRIPTION
				"The desired placement for radio."
			::= { apRadioCfgEntry 2 }

		
		-- 1.3.6.1.4.1.388.11.3.4.1.2.1.3
		apRadioCfgPosChannel OBJECT-TYPE
			SYNTAX BITS
				{
				null(0),
				bchannel01(1),
				bchannel02(2),
				bchannel03(3),
				bchannel04(4),
				bchannel05(5),
				bchannel06(6),
				bchannel07(7),
				bchannel08(8),
				bchannel09(9),
				bchannel10(10),
				bchannel11(11),
				bchannel12(12),
				bchannel13(13),
				bchannel14(14),
				achannel36(15),
				achannel40(16),
				achannel44(17),
				achannel48(18),
				achannel52(19),
				achannel56(20),
				achannel60(21),
				achannel64(22),
				achannel149(23),
				achannel153(24),
				achannel157(25),
				achannel161(26),
				achannel165(27)
				}
			MAX-ACCESS read-only
			STATUS current
			DESCRIPTION
				"The possible channels that can be set when placement = 
				apRadioCfgDesPlacement."
			::= { apRadioCfgEntry 3 }

		
		-- 1.3.6.1.4.1.388.11.3.4.1.2.1.4
		apRadioCfgDesChannel OBJECT-TYPE
			SYNTAX INTEGER
				{
				null(0),
				bchannel01(1),
				bchannel02(2),
				bchannel03(3),
				bchannel04(4),
				bchannel05(5),
				bchannel06(6),
				bchannel07(7),
				bchannel08(8),
				bchannel09(9),
				bchannel10(10),
				bchannel11(11),
				bchannel12(12),
				bchannel13(13),
				bchannel14(14),
				achannel36(36),
				achannel40(40),
				achannel44(44),
				achannel48(48),
				achannel52(52),
				achannel56(56),
				achannel60(60),
				achannel64(64),
				achannel149(149),
				achannel153(153),
				achannel157(157),
				achannel161(161),
				achannel165(165)
				}
			MAX-ACCESS read-write
			STATUS current
			DESCRIPTION
				"The desired channel for radio.
				
				Please do not use this object for an access point 
				that supports 802.11n radio.
				Use apRadioNCfgDesChannel instead."
			::= { apRadioCfgEntry 4 }

		
		-- 1.3.6.1.4.1.388.11.3.4.1.2.1.5
		apRadioCfgPosPowerLevel OBJECT-TYPE
			SYNTAX Integer32
			MAX-ACCESS read-only
			STATUS current
			DESCRIPTION
				"The max possible power level (dBm) that can be set when 
				channel= apRadioCfgDesChannel. The range is 4 to 20 dBm."
			::= { apRadioCfgEntry 5 }

		
		-- 1.3.6.1.4.1.388.11.3.4.1.2.1.6
		apRadioCfgDesPowerLevel OBJECT-TYPE
			SYNTAX Integer32 (4..20)
			MAX-ACCESS read-write
			STATUS current
			DESCRIPTION
				"The desired power level (dBm) for radio.
				
				The following power levels are available
				4dBm=3mW,   5dBm=3mW,   6dBm=4mW,
				7dBm=5mW,   8dBm=6mW,   9dBm=8mW,
				10dBm=10mW, 11dBm=13mW, 12dBm=16mW, 
				13dBm=20mW, 14dBm=25mW, 15dBm=32mW,
				16dBm=40mW, 17dBm=50mW, 18dBm=63mW, 
				19dBm=79mW, 20dBm=100mW
				
				Note: Power level allowed depends on radio type, 
				channel and country of operation."
			::= { apRadioCfgEntry 6 }

		
		-- 1.3.6.1.4.1.388.11.3.4.1.2.1.7
		apRadioCfgDesPowerInMW OBJECT-TYPE
			SYNTAX Integer32
			MAX-ACCESS read-only
			STATUS current
			DESCRIPTION
				"apRadioCfgDesPowerLevel in mW."
			::= { apRadioCfgEntry 7 }

		
		-- 1.3.6.1.4.1.388.11.3.4.1.2.1.8
		apRadioCfgSet OBJECT-TYPE
			SYNTAX DoActionShowProgress
			MAX-ACCESS read-write
			STATUS current
			DESCRIPTION
				"Validate values in apRadioCfgDes_ fields.  If it is
				a valid combination, configure the switch with this 
				combination and set apRadioCfg_ to these values."
			::= { apRadioCfgEntry 8 }

		
		-- 1.3.6.1.4.1.388.11.3.4.1.2.1.9
		apRadioCfgReset OBJECT-TYPE
			SYNTAX DoActionShowProgress
			MAX-ACCESS read-write
			STATUS current
			DESCRIPTION
				"Reset the following OIDs.
				
				apRadioCfgDesPlacement
				apRadioCfgDesChannel
				apRadioCfgDesPowerLevel
				apRadioCfgPosChannel
				apRadioCfgPosPowerLevel
				apRadioCfgPowerInMW
				"
			::= { apRadioCfgEntry 9 }

		
		-- 1.3.6.1.4.1.388.11.3.4.1.2.1.10
		apRadioCfgPlacement OBJECT-TYPE
			SYNTAX INTEGER
				{
				indoor(1),
				outdoor(2)
				}
			MAX-ACCESS read-only
			STATUS current
			DESCRIPTION
				"The placement configuration for radio."
			::= { apRadioCfgEntry 10 }

		
		-- 1.3.6.1.4.1.388.11.3.4.1.2.1.11
		apRadioCfgChannel OBJECT-TYPE
			SYNTAX INTEGER
				{
				null(0),
				bchannel01(1),
				bchannel02(2),
				bchannel03(3),
				bchannel04(4),
				bchannel05(5),
				bchannel06(6),
				bchannel07(7),
				bchannel08(8),
				bchannel09(9),
				bchannel10(10),
				bchannel11(11),
				achannel36(36),
				achannel40(40),
				achannel44(44),
				achannel48(48),
				achannel52(52),
				achannel56(56),
				achannel60(60),
				achannel64(64),
				achannel149(149),
				achannel153(153),
				achannel157(157),
				achannel161(161),
				achannel165(165)
				}
			MAX-ACCESS read-only
			STATUS current
			DESCRIPTION
				"The channel configuration for radio."
			::= { apRadioCfgEntry 11 }

		
		-- 1.3.6.1.4.1.388.11.3.4.1.2.1.12
		apRadioCfgPowerLevel OBJECT-TYPE
			SYNTAX Integer32
			MAX-ACCESS read-only
			STATUS current
			DESCRIPTION
				"The power level (dBm) configuration for radio."
			::= { apRadioCfgEntry 12 }

		
		-- 1.3.6.1.4.1.388.11.3.4.1.2.1.13
		apRadioCfgPowerInMW OBJECT-TYPE
			SYNTAX Integer32
			MAX-ACCESS read-only
			STATUS current
			DESCRIPTION
				"apRadioCfgPowerLevel in mW."
			::= { apRadioCfgEntry 13 }

		
		-- 1.3.6.1.4.1.388.11.3.4.1.2.1.14
		apRadioCfgRfFunction OBJECT-TYPE
			SYNTAX INTEGER
				{
				wlan(1),
				wips(2)
				}
			MAX-ACCESS read-write
			STATUS current
			DESCRIPTION
				"WLAN or WIPS sensor operation mode for the Radio."
			::= { apRadioCfgEntry 14 }

		
		-- 1.3.6.1.4.1.388.11.3.4.1.2.1.15
		apRadioCfgExceptionChannel OBJECT-TYPE
			SYNTAX BITS
				{
				null(0),
				bchannel01(1),
				bchannel02(2),
				bchannel03(3),
				bchannel04(4),
				bchannel05(5),
				bchannel06(6),
				bchannel07(7),
				bchannel08(8),
				bchannel09(9),
				bchannel10(10),
				bchannel11(11),
				bchannel12(12),
				bchannel13(13),
				bchannel14(14),
				achannel36(15),
				achannel40(16),
				achannel44(17),
				achannel48(18),
				achannel52(19),
				achannel56(20),
				achannel60(21),
				achannel64(22),
				achannel149(23),
				achannel153(24),
				achannel157(25),
				achannel161(26),
				achannel165(27)
				}
			MAX-ACCESS read-write
			STATUS current
			DESCRIPTION
				"The channels that will be excluded from scanning when channelMode is autoSelect."
			::= { apRadioCfgEntry 15 }

		
		-- 1.3.6.1.4.1.388.11.3.4.1.3
		apRadioWlanBssTable OBJECT-TYPE
			SYNTAX SEQUENCE OF ApRadioWlanBssEntry
			MAX-ACCESS not-accessible
			STATUS current
			DESCRIPTION
				"Table of BSSIDs mapped to WLANs."
			::= { apRadio 3 }

		
		-- 1.3.6.1.4.1.388.11.3.4.1.3.1
		apRadioWlanBssEntry OBJECT-TYPE
			SYNTAX ApRadioWlanBssEntry
			MAX-ACCESS not-accessible
			STATUS current
			DESCRIPTION
				" "
			INDEX { apRadioSettingsIndex, apWlanIndex }
			::= { apRadioWlanBssTable 1 }

		
		ApRadioWlanBssEntry ::=
			SEQUENCE { 
				apRadioWlanBssid
					Integer32
			 }

		-- 1.3.6.1.4.1.388.11.3.4.1.3.1.1
		apRadioWlanBssid OBJECT-TYPE
			SYNTAX Integer32
			MAX-ACCESS read-write
			STATUS current
			DESCRIPTION
				"BSSID assigned to this particular WLAN."
			::= { apRadioWlanBssEntry 1 }

		
		-- 1.3.6.1.4.1.388.11.3.4.1.4
		apRadioBssTable OBJECT-TYPE
			SYNTAX SEQUENCE OF ApRadioBssEntry
			MAX-ACCESS not-accessible
			STATUS current
			DESCRIPTION
				"Use apRadioBssTable to view and set the properties
				of the Bss's.
				"
			::= { apRadio 4 }

		
		-- 1.3.6.1.4.1.388.11.3.4.1.4.1
		apRadioBssEntry OBJECT-TYPE
			SYNTAX ApRadioBssEntry
			MAX-ACCESS not-accessible
			STATUS current
			DESCRIPTION
				" "
			INDEX { apRadioSettingsIndex, apRadioBssIndex }
			::= { apRadioBssTable 1 }

		
		ApRadioBssEntry ::=
			SEQUENCE { 
				apRadioBssIndex
					Integer32,
				apRadioBssPrimaryWlan
					Integer32,
				apRadioBssDtimPrd
					Integer32
			 }

		-- 1.3.6.1.4.1.388.11.3.4.1.4.1.1
		apRadioBssIndex OBJECT-TYPE
			SYNTAX Integer32 (1..4)
			MAX-ACCESS accessible-for-notify
			STATUS current
			DESCRIPTION
				" "
			::= { apRadioBssEntry 1 }

		
		-- 1.3.6.1.4.1.388.11.3.4.1.4.1.2
		apRadioBssPrimaryWlan OBJECT-TYPE
			SYNTAX Integer32 (0..16)
			MAX-ACCESS read-write
			STATUS current
			DESCRIPTION
				"Primary WLAN used by the AP to send beacons."
			::= { apRadioBssEntry 2 }

		
		-- 1.3.6.1.4.1.388.11.3.4.1.4.1.3
		apRadioBssDtimPrd OBJECT-TYPE
			SYNTAX Integer32 (1..50)
			MAX-ACCESS read-write
			STATUS current
			DESCRIPTION
				"Specify a period for the Delivery Traffic Indication 
				Message (DTIM). This is a divisor of the beacon 
				interval (in milliseconds), for example, 10 : 100. 
				
				Note that BSS DTIM period is not supported for 802.11n radios."
			::= { apRadioBssEntry 3 }

		
		-- 1.3.6.1.4.1.388.11.3.4.1.5
		apRadioE2BMapStatusTable OBJECT-TYPE
			SYNTAX SEQUENCE OF ApRadioE2BMapStatusEntry
			MAX-ACCESS not-accessible
			STATUS current
			DESCRIPTION
				"The table describes the ESS to BSS mapping status."
			::= { apRadio 5 }

		
		-- 1.3.6.1.4.1.388.11.3.4.1.5.1
		apRadioE2BMapStatusEntry OBJECT-TYPE
			SYNTAX ApRadioE2BMapStatusEntry
			MAX-ACCESS not-accessible
			STATUS current
			DESCRIPTION
				" "
			INDEX { apRadioSettingsIndex, apWlanIndex }
			::= { apRadioE2BMapStatusTable 1 }

		
		ApRadioE2BMapStatusEntry ::=
			SEQUENCE { 
				apRadioE2BMapStatusBcMcEncCipher
					INTEGER,
				apRadioE2BMapStatus
					INTEGER,
				apRadioE2BMapStatusMessage
					DisplayString
			 }

		-- 1.3.6.1.4.1.388.11.3.4.1.5.1.1
		apRadioE2BMapStatusBcMcEncCipher OBJECT-TYPE
			SYNTAX INTEGER
				{
				open(1),
				wep64(2),
				wep128(3),
				keyguard(4),
				wpaTkip(5),
				wpa2Ccmp(6)
				}
			MAX-ACCESS read-only
			STATUS current
			DESCRIPTION
				"Broadcast/Mulitcast Encryption cipher
				based on the ESS to BSS mapping."
			::= { apRadioE2BMapStatusEntry 1 }

		
		-- 1.3.6.1.4.1.388.11.3.4.1.5.1.2
		apRadioE2BMapStatus OBJECT-TYPE
			SYNTAX INTEGER
				{
				good(1),
				warning(2),
				error(3)
				}
			MAX-ACCESS read-only
			STATUS current
			DESCRIPTION
				"ESS to BSS map status."
			::= { apRadioE2BMapStatusEntry 2 }

		
		-- 1.3.6.1.4.1.388.11.3.4.1.5.1.3
		apRadioE2BMapStatusMessage OBJECT-TYPE
			SYNTAX DisplayString
			MAX-ACCESS read-only
			STATUS current
			DESCRIPTION
				"ESS to BSS map status message."
			::= { apRadioE2BMapStatusEntry 3 }

		
		-- 1.3.6.1.4.1.388.11.3.4.1.6
		apRadioMesh OBJECT IDENTIFIER ::= { apRadio 6 }

		
		-- 1.3.6.1.4.1.388.11.3.4.1.6.1
		apRadioMeshTable OBJECT-TYPE
			SYNTAX SEQUENCE OF ApRadioMeshEntry
			MAX-ACCESS not-accessible
			STATUS current
			DESCRIPTION
				"Table for MESH configuration for Radio."
			::= { apRadioMesh 1 }

		
		-- 1.3.6.1.4.1.388.11.3.4.1.6.1.1
		apRadioMeshEntry OBJECT-TYPE
			SYNTAX ApRadioMeshEntry
			MAX-ACCESS not-accessible
			STATUS current
			DESCRIPTION
				" "
			INDEX { apRadioSettingsIndex }
			::= { apRadioMeshTable 1 }

		
		ApRadioMeshEntry ::=
			SEQUENCE { 
				apRadioMeshBaseBridgeMode
					TruthValue,
				apRadioMeshMaxClients
					Integer32,
				apRadioMeshClientBridgeMode
					TruthValue,
				apRadioMeshWlanPtr
					SinglePointer,
				apRadioMeshConnAutoSelect
					TruthValue,
				apRadioMeshTimeout
					INTEGER,
				apRadioMeshTimeoutValue
					INTEGER
			 }

		-- 1.3.6.1.4.1.388.11.3.4.1.6.1.1.1
		apRadioMeshBaseBridgeMode OBJECT-TYPE
			SYNTAX TruthValue
			MAX-ACCESS read-write
			STATUS current
			DESCRIPTION
				"MESH base bridge mode for radio."
			::= { apRadioMeshEntry 1 }

		
		-- 1.3.6.1.4.1.388.11.3.4.1.6.1.1.2
		apRadioMeshMaxClients OBJECT-TYPE
			SYNTAX Integer32 (1..12)
			MAX-ACCESS read-write
			STATUS current
			DESCRIPTION
				"Maximum number of MESH client bridges."
			::= { apRadioMeshEntry 2 }

		
		-- 1.3.6.1.4.1.388.11.3.4.1.6.1.1.3
		apRadioMeshClientBridgeMode OBJECT-TYPE
			SYNTAX TruthValue
			MAX-ACCESS read-write
			STATUS current
			DESCRIPTION
				"MESH client bridge mode for radio."
			::= { apRadioMeshEntry 3 }

		
		-- 1.3.6.1.4.1.388.11.3.4.1.6.1.1.4
		apRadioMeshWlanPtr OBJECT-TYPE
			SYNTAX SinglePointer (0..16)
			MAX-ACCESS read-write
			STATUS current
			DESCRIPTION
				"MESH client bridge WLAN.
				For the value 0 there is no WLAN assigned
				for Client Bridge connection."
			::= { apRadioMeshEntry 4 }

		
		-- 1.3.6.1.4.1.388.11.3.4.1.6.1.1.5
		apRadioMeshConnAutoSelect OBJECT-TYPE
			SYNTAX TruthValue
			MAX-ACCESS read-write
			STATUS current
			DESCRIPTION
				"Enable/Disable the MESH Auto Connection Select Mode."
			::= { apRadioMeshEntry 5 }

		
		-- 1.3.6.1.4.1.388.11.3.4.1.6.1.1.6
		apRadioMeshTimeout OBJECT-TYPE
			SYNTAX INTEGER
				{
				disabled(0),
				uplinkDetect(1),
				enabled(2)
				}
			MAX-ACCESS read-write
			STATUS current
			DESCRIPTION
				"Mesh Timeout Status."
			::= { apRadioMeshEntry 6 }

		
		-- 1.3.6.1.4.1.388.11.3.4.1.6.1.1.7
		apRadioMeshTimeoutValue OBJECT-TYPE
			SYNTAX INTEGER (45..65535)
			MAX-ACCESS read-write
			STATUS current
			DESCRIPTION
				"If Mesh is not connected after Timeout period (in seconds),
				stop the AP from sending beacons."
			::= { apRadioMeshEntry 7 }

		
		-- 1.3.6.1.4.1.388.11.3.4.1.6.2
		apRadioMeshAvailableConnTable OBJECT-TYPE
			SYNTAX SEQUENCE OF ApRadioMeshAvailableConnEntry
			MAX-ACCESS not-accessible
			STATUS current
			DESCRIPTION
				"Table of Available Base Bridge MESH connections."
			::= { apRadioMesh 2 }

		
		-- 1.3.6.1.4.1.388.11.3.4.1.6.2.1
		apRadioMeshAvailableConnEntry OBJECT-TYPE
			SYNTAX ApRadioMeshAvailableConnEntry
			MAX-ACCESS not-accessible
			STATUS current
			DESCRIPTION
				" "
			INDEX { apRadioSettingsIndex, apRadioMeshAvailableConnIndex }
			::= { apRadioMeshAvailableConnTable 1 }

		
		ApRadioMeshAvailableConnEntry ::=
			SEQUENCE { 
				apRadioMeshAvailableConnIndex
					Integer32,
				apRadioMeshAvailableConnMac
					PhysAddress,
				apRadioMeshAvailableConnChannel
					Integer32,
				apRadioMeshAvailableConnRssi
					Integer32
			 }

		-- 1.3.6.1.4.1.388.11.3.4.1.6.2.1.1
		apRadioMeshAvailableConnIndex OBJECT-TYPE
			SYNTAX Integer32 (1..32)
			MAX-ACCESS accessible-for-notify
			STATUS current
			DESCRIPTION
				"Simple Index."
			::= { apRadioMeshAvailableConnEntry 1 }

		
		-- 1.3.6.1.4.1.388.11.3.4.1.6.2.1.2
		apRadioMeshAvailableConnMac OBJECT-TYPE
			SYNTAX PhysAddress
			MAX-ACCESS read-only
			STATUS current
			DESCRIPTION
				"Mac Address of Available Base Bridge."
			::= { apRadioMeshAvailableConnEntry 2 }

		
		-- 1.3.6.1.4.1.388.11.3.4.1.6.2.1.3
		apRadioMeshAvailableConnChannel OBJECT-TYPE
			SYNTAX Integer32
			MAX-ACCESS read-only
			STATUS current
			DESCRIPTION
				"Channel of Available Base Bridge."
			::= { apRadioMeshAvailableConnEntry 3 }

		
		-- 1.3.6.1.4.1.388.11.3.4.1.6.2.1.4
		apRadioMeshAvailableConnRssi OBJECT-TYPE
			SYNTAX Integer32
			MAX-ACCESS read-only
			STATUS current
			DESCRIPTION
				"RSSI value of Available Base Bridge."
			::= { apRadioMeshAvailableConnEntry 4 }

		
		-- 1.3.6.1.4.1.388.11.3.4.1.6.3
		apRadioMeshPreferredConnTable OBJECT-TYPE
			SYNTAX SEQUENCE OF ApRadioMeshPreferredConnEntry
			MAX-ACCESS not-accessible
			STATUS current
			DESCRIPTION
				"Table of Preferred Base Bridge MESH connections."
			::= { apRadioMesh 3 }

		
		-- 1.3.6.1.4.1.388.11.3.4.1.6.3.1
		apRadioMeshPreferredConnEntry OBJECT-TYPE
			SYNTAX ApRadioMeshPreferredConnEntry
			MAX-ACCESS not-accessible
			STATUS current
			DESCRIPTION
				" "
			INDEX { apRadioSettingsIndex, apRadioMeshPreferredConnIndex }
			::= { apRadioMeshPreferredConnTable 1 }

		
		ApRadioMeshPreferredConnEntry ::=
			SEQUENCE { 
				apRadioMeshPreferredConnIndex
					Integer32,
				apRadioMeshPreferredConnPriority
					Integer32,
				apRadioMeshPreferredConnMac
					PhysAddress,
				apRadioMeshPreferredConnRowStatus
					AbbrevRowStatus
			 }

		-- 1.3.6.1.4.1.388.11.3.4.1.6.3.1.1
		apRadioMeshPreferredConnIndex OBJECT-TYPE
			SYNTAX Integer32 (1..16)
			MAX-ACCESS accessible-for-notify
			STATUS current
			DESCRIPTION
				"Simple Index."
			::= { apRadioMeshPreferredConnEntry 1 }

		
		-- 1.3.6.1.4.1.388.11.3.4.1.6.3.1.2
		apRadioMeshPreferredConnPriority OBJECT-TYPE
			SYNTAX Integer32
			MAX-ACCESS read-write
			STATUS current
			DESCRIPTION
				"Preferred Base Bridge Priority."
			::= { apRadioMeshPreferredConnEntry 2 }

		
		-- 1.3.6.1.4.1.388.11.3.4.1.6.3.1.3
		apRadioMeshPreferredConnMac OBJECT-TYPE
			SYNTAX PhysAddress
			MAX-ACCESS read-write
			STATUS current
			DESCRIPTION
				"Preferred Base Bridge MAC Address."
			::= { apRadioMeshPreferredConnEntry 3 }

		
		-- 1.3.6.1.4.1.388.11.3.4.1.6.3.1.4
		apRadioMeshPreferredConnRowStatus OBJECT-TYPE
			SYNTAX AbbrevRowStatus
			MAX-ACCESS read-write
			STATUS current
			DESCRIPTION
				"Row Status used to add or delete entries."
			::= { apRadioMeshPreferredConnEntry 4 }

		
		-- 1.3.6.1.4.1.388.11.3.4.1.7
		apRadioWlanBandwidthTable OBJECT-TYPE
			SYNTAX SEQUENCE OF ApRadioWlanBandwidthEntry
			MAX-ACCESS not-accessible
			STATUS current
			DESCRIPTION
				"Table of Radio Wlan Bandwidth management."
			::= { apRadio 7 }

		
		-- 1.3.6.1.4.1.388.11.3.4.1.7.1
		apRadioWlanBandwidthEntry OBJECT-TYPE
			SYNTAX ApRadioWlanBandwidthEntry
			MAX-ACCESS not-accessible
			STATUS current
			DESCRIPTION
				" "
			INDEX { apRadioSettingsIndex, apWlanIndex }
			::= { apRadioWlanBandwidthTable 1 }

		
		ApRadioWlanBandwidthEntry ::=
			SEQUENCE { 
				apRadioWlanWeight
					Integer32
			 }

		-- 1.3.6.1.4.1.388.11.3.4.1.7.1.1
		apRadioWlanWeight OBJECT-TYPE
			SYNTAX Integer32
			MAX-ACCESS read-write
			STATUS current
			DESCRIPTION
				"The weight to be used when QoS for all WLANs is set to weighted-round-robin.
								
				Note that the sum of all weights across all WLANs need not total 100.
				"
			::= { apRadioWlanBandwidthEntry 1 }

		
		-- 1.3.6.1.4.1.388.11.3.4.1.8
		apRadioNSettingsTable OBJECT-TYPE
			SYNTAX SEQUENCE OF ApRadioNSettingsEntry
			MAX-ACCESS not-accessible
			STATUS current
			DESCRIPTION
				"This table adds 802.11n specific settings for an 'n' radio in 
				addition to the common settings under apRadioSettingsTable."
			::= { apRadio 8 }

		
		-- 1.3.6.1.4.1.388.11.3.4.1.8.1
		apRadioNSettingsEntry OBJECT-TYPE
			SYNTAX ApRadioNSettingsEntry
			MAX-ACCESS not-accessible
			STATUS current
			DESCRIPTION
				"An 802.11n radio settings entry."
			INDEX { apRadioSettingsIndex }
			::= { apRadioNSettingsTable 1 }

		
		ApRadioNSettingsEntry ::=
			SEQUENCE { 
				apRadioNSettingsMode
					INTEGER,
				apRadioNSettingsHTProtectionStatus
					INTEGER,
				apRadioNSettingsBasicRates
					INTEGER
			 }

		-- 1.3.6.1.4.1.388.11.3.4.1.8.1.1
		apRadioNSettingsMode OBJECT-TYPE
			SYNTAX INTEGER
				{
				modeA(1),
				modeB(2),
				modeG(3),
				modeN2400MHz(4),
				modeN5000MHz(5),
				modeAandN(6),
				modeBandG(7),
				modeGandN(8),
				modeBGandN(9)
				}
			MAX-ACCESS read-write
			STATUS current
			DESCRIPTION
				"The modes available for an 802.11n radio depend on the radio band. 
				For 5.0 GHz (11an), the modes are:
				        
				        modeA
				        modeN5000MHz
				        modeAandN
				
				For 2.4 GHz (11bgn), the modes are:
				        modeBGandN
				        modeBandG
				        modeGandN
				        modeB
				        modeG  
				        modeN2400MHz"
			::= { apRadioNSettingsEntry 1 }

		
		-- 1.3.6.1.4.1.388.11.3.4.1.8.1.2
		apRadioNSettingsHTProtectionStatus OBJECT-TYPE
			SYNTAX INTEGER
				{
				pureHt(1),
				nonHtStaOnChannel(2),
				htWith20MHzOnlySta(3),
				nonHtStaAssociated(4)
				}
			MAX-ACCESS read-only
			STATUS current
			DESCRIPTION
				"This is a new setting for 802.11n radios that indicates 
				the HT Protection Status. The possible values are:
				
				        Pure HT (1)
				        non-HT STA on Channel (2)
				        HT with 20 MHz-only STA (3)
				        non-HT STA associated (4)"
			::= { apRadioNSettingsEntry 2 }

		
		-- 1.3.6.1.4.1.388.11.3.4.1.8.1.3
		apRadioNSettingsBasicRates OBJECT-TYPE
			SYNTAX INTEGER
				{
				rate1and2Mbps(1),
				rate1and2and5point5and11Mbps(2),
				rate1and2and5point5and11and6and12and24Mbps(3),
				rate6and12and24Mbps(4),
				rateMCS0to7(5),
				rate6and12and24MbpsandMCS0to7(6),
				rate1and2and5point5and11and6and12and24MbpsandMCS0to7(7)
				}
			MAX-ACCESS read-write
			STATUS current
			DESCRIPTION
				"For basic rate the following options are available:
				(1)	1 and 2 Mbps
				(2)	1, 2, 5.5 and 11 Mbps
				(3)	1, 2, 5.5, 11 and 6, 12, 24 Mbps
				(4)	6, 12 and 24 Mbps
				(5)	MCS 0-7
				(6)	6, 12 and 24 Mbps and MCS 0-7
				(7)	1, 2, 5.5, 11 and 6, 12, 24 Mbps and MCS 0-7"
			::= { apRadioNSettingsEntry 3 }

		
		-- 1.3.6.1.4.1.388.11.3.4.1.9
		apRadioNCfgTable OBJECT-TYPE
			SYNTAX SEQUENCE OF ApRadioNCfgEntry
			MAX-ACCESS not-accessible
			STATUS current
			DESCRIPTION
				"Description."
			::= { apRadio 9 }

		
		-- 1.3.6.1.4.1.388.11.3.4.1.9.1
		apRadioNCfgEntry OBJECT-TYPE
			SYNTAX ApRadioNCfgEntry
			MAX-ACCESS not-accessible
			STATUS current
			DESCRIPTION
				"Description."
			INDEX { apRadioSettingsIndex }
			::= { apRadioNCfgTable 1 }

		
		ApRadioNCfgEntry ::=
			SEQUENCE { 
				apRadioNCfgPosChannel
					BITS,
				apRadioNCfgDesChannel
					AllowedChannels,
				apRadioNCfgChannel
					INTEGER,
				apRadioNCfgChannelWidth
					INTEGER,
				apRadioNCfgAmsduAggregationMaxRecvSize
					INTEGER,
				apRadioNCfgAmsduTransmitEnabled
					TruthValue,
				apRadioNCfgAmpduAggregationMaxRecvSize
					INTEGER,
				apRadioNCfgAmpduAggregationDensity
					INTEGER,
				apRadioNCfgAmpduTransmitSizeLimit
					INTEGER,
				apRadioNCfgShortGuardInterval
					TruthValue,
				apRadioNCfgAmpduTransmitEnabled
					TruthValue,
				apRadioNCfgChannelOffset
					INTEGER
			 }

		-- 1.3.6.1.4.1.388.11.3.4.1.9.1.1
		apRadioNCfgPosChannel OBJECT-TYPE
			SYNTAX BITS
				{
				null(0),
				bgnChannel1(1),
				bgnChannel2(2),
				bgnChannel3(3),
				bgnChannel4(4),
				bgnChannel5(5),
				bgnChannel6(6),
				bgnChannel7(7),
				bgnChannel8(8),
				bgnChannel9(9),
				bgnChannel10(10),
				bgnChannel11(11),
				bgnChannel12(12),
				bgnChannel13(13),
				bgnChannel14(14),
				anChannel36(15),
				anChannel40(16),
				anChannel44(17),
				anChannel48(18),
				anChannel52(19),
				anChannel56(20),
				anChannel60(21),
				anChannel64(22),
				anChannel100(23),
				anChannel104(24),
				anChannel108(25),
				anChannel112(26),
				anChannel116(27),
				anChannel120(28),
				anChannel124(29),
				anChannel128(30),
				anChannel132(31),
				anChannel136(32),
				anChannel140(33),
				anChannel149(34),
				anChannel153(35),
				anChannel157(36),
				anChannel161(37),
				anChannel165(38)
				}
			MAX-ACCESS read-only
			STATUS current
			DESCRIPTION
				"The possible channels that can be set when placement = 
				apRadioCfgDesPlacement"
			::= { apRadioNCfgEntry 1 }

		
		-- 1.3.6.1.4.1.388.11.3.4.1.9.1.2
		apRadioNCfgDesChannel OBJECT-TYPE
			SYNTAX AllowedChannels
			MAX-ACCESS read-write
			STATUS current
			DESCRIPTION
				"The desired channel for the 'n' radio.
				
				When changing 802.11n channels, make changes in the following order:
				1) Width (apRadioNCfgChannelWidth)
				2) Offset (apRadioNCfgChannelOffset)
				3) Channel (apRadioNCfgDesChannel)"
			::= { apRadioNCfgEntry 2 }

		
		-- 1.3.6.1.4.1.388.11.3.4.1.9.1.3
		apRadioNCfgChannel OBJECT-TYPE
			SYNTAX INTEGER
			MAX-ACCESS read-only
			STATUS current
			DESCRIPTION
				"The channel configuration for the 'n' radio."
			::= { apRadioNCfgEntry 3 }

		
		-- 1.3.6.1.4.1.388.11.3.4.1.9.1.4
		apRadioNCfgChannelWidth OBJECT-TYPE
			SYNTAX INTEGER
				{
				twentyMHz(1),
				dynamic(2)
				}
			MAX-ACCESS read-write
			STATUS current
			DESCRIPTION
				"When this value is set to twentyMhz, the AP works on 
				20MHz mode for both transmit and receive operations.
				
				dynamic: The 20/40 MHz operation is a dynamic feature in which 
				the AP can receive packets from clients that use 20 MHz 
				of bandwidth while transmitting a packet OR that use 40 MHz 
				of bandwidth while transmitting a packet.  
				Likewise, the AP can send packets either with a bandwidth of 
				20 or 40 MHz.
				
				When changing 802.11n channels, make changes in the following order:
				1) Width (apRadioNCfgChannelWidth)
				2) Offset (apRadioNCfgChannelOffset)
				3) Channel (apRadioNCfgDesChannel)"
			::= { apRadioNCfgEntry 4 }

		
		-- 1.3.6.1.4.1.388.11.3.4.1.9.1.5
		apRadioNCfgAmsduAggregationMaxRecvSize OBJECT-TYPE
			SYNTAX INTEGER { size3839(3839) }
			UNITS "bytes"
			MAX-ACCESS read-only
			STATUS current
			DESCRIPTION
				"The AP will always be enabled to receive AMSDU frames.
				
				The user will be able to set the AMSDU limit to 3839 bytes. 
				This value will be advertised in the HT Capabilities 
				element.
				
				The user may be able to enable and disable the transmission 
				of AMSDU frames in future releases."
			::= { apRadioNCfgEntry 5 }

		
		-- 1.3.6.1.4.1.388.11.3.4.1.9.1.6
		apRadioNCfgAmsduTransmitEnabled OBJECT-TYPE
			SYNTAX TruthValue
			MAX-ACCESS read-only
			STATUS current
			DESCRIPTION
				"When set to TRUE it enables the transmission of AMSDU frames.
				Setting it to FALSE disable AMSDU transmission.
				This object is not supported in the current release, hence 
				it will not be returned during a get/get-next/walk."
			::= { apRadioNCfgEntry 6 }

		
		-- 1.3.6.1.4.1.388.11.3.4.1.9.1.7
		apRadioNCfgAmpduAggregationMaxRecvSize OBJECT-TYPE
			SYNTAX INTEGER
				{
				size0(0),
				size8191(8191),
				size16383(16383),
				size32767(32767),
				size65535(65535)
				}
			UNITS "bytes"
			MAX-ACCESS read-write
			STATUS current
			DESCRIPTION
				"This value is used to tell other stations the maximum length AMPDU 
				that they can send. The allowed values are:
				      0 bytes (special case, to disable AMPDU rx-limit).
				   8191 bytes
				  16383 bytes
				  32767 bytes
				  65535 bytes."
			::= { apRadioNCfgEntry 7 }

		
		-- 1.3.6.1.4.1.388.11.3.4.1.9.1.8
		apRadioNCfgAmpduAggregationDensity OBJECT-TYPE
			SYNTAX INTEGER
				{
				zero(0),
				onefourth(250),
				onehalf(500),
				one(1000),
				two(2000),
				four(4000),
				eight(8000)
				}
			UNITS "nanoseconds"
			MAX-ACCESS read-write
			STATUS current
			DESCRIPTION
				"Used to configure the AMPDU density which controls how close 
				together the MPDU’s are within the AMPDU.
				
				The choices are: 0 (none), 1/4 usec, 1/2 usec, 1 usec, 2 usec, 
				4 usec and 8 usec.
				
				Since SNMP cannot represent fractions or decimals, the enumerations 
				are given multiplied by 1000 i.e. in nanoseconds."
			::= { apRadioNCfgEntry 8 }

		
		-- 1.3.6.1.4.1.388.11.3.4.1.9.1.9
		apRadioNCfgAmpduTransmitSizeLimit OBJECT-TYPE
			SYNTAX INTEGER (0..65535)
			MAX-ACCESS read-write
			STATUS current
			DESCRIPTION
				"This is a threshold that controls when the AP will setup a 
				Block ACK agreement with a client to begin aggregating,
				that is, sending A-MPDU frames, to that client. 
				It takes a range from 0-65535 bytes.  "
			::= { apRadioNCfgEntry 9 }

		
		-- 1.3.6.1.4.1.388.11.3.4.1.9.1.10
		apRadioNCfgShortGuardInterval OBJECT-TYPE
			SYNTAX TruthValue
			MAX-ACCESS read-write
			STATUS current
			DESCRIPTION
				"This is a boolean. The 802.11n AP has an option to configure 
				short guard interval(SGI). 
				
				The possible values of guard interval are 400ns or 800ns.
				
				When the user turns SGI on, both 400ns and 800ns will be enabled together.
				When the user turns SGI off, only 800ns will be enabled.
				"
			::= { apRadioNCfgEntry 10 }

		
		-- 1.3.6.1.4.1.388.11.3.4.1.9.1.11
		apRadioNCfgAmpduTransmitEnabled OBJECT-TYPE
			SYNTAX TruthValue
			MAX-ACCESS read-write
			STATUS current
			DESCRIPTION
				"When set to TRUE it enables the transmission of AMPDU frames.
				Setting it to FALSE disable AMPDU transmission."
			::= { apRadioNCfgEntry 11 }

		
		-- 1.3.6.1.4.1.388.11.3.4.1.9.1.12
		apRadioNCfgChannelOffset OBJECT-TYPE
			SYNTAX INTEGER
				{
				none(1),
				above(2),
				below(3)
				}
			MAX-ACCESS read-write
			STATUS current
			DESCRIPTION
				"The channel offset.
				
				When changing 802.11n channels, make changes in the following order:
				1) Width (apRadioNCfgChannelWidth)
				2) Offset (apRadioNCfgChannelOffset)
				3) Channel (apRadioNCfgDesChannel)"
			::= { apRadioNCfgEntry 12 }

		
		-- 1.3.6.1.4.1.388.11.3.4.1.10
		apRadioNMcsRateTable OBJECT-TYPE
			SYNTAX SEQUENCE OF ApRadioNMcsRateEntry
			MAX-ACCESS not-accessible
			STATUS current
			DESCRIPTION
				"The AP with the 802.11n radio supports modulation coding schemes 
				(MCS) 0-15. This maps to the table entries 1-16.
				To the user, this is part of the Set Rates function."
			::= { apRadio 10 }

		
		-- 1.3.6.1.4.1.388.11.3.4.1.10.1
		apRadioNMcsRateEntry OBJECT-TYPE
			SYNTAX ApRadioNMcsRateEntry
			MAX-ACCESS not-accessible
			STATUS current
			DESCRIPTION
				"An entry which gives the MCS supported by an 'n' radio in the AP."
			INDEX { apRadioSettingsIndex, apRadioNMcsRateIndex }
			::= { apRadioNMcsRateTable 1 }

		
		ApRadioNMcsRateEntry ::=
			SEQUENCE { 
				apRadioNMcsRateIndex
					INTEGER,
				apRadioNMcsRate20MHzChanSgiDisabled
					Integer32,
				apRadioNMcsRate20MHzChanSgiEnabled
					Integer32,
				apRadioNMcsRate40MHzChanSgiDisabled
					Integer32,
				apRadioNMcsRate40MHzChanSgiEnabled
					Integer32,
				apRadioNMcsRateType
					INTEGER,
				apRadioNMcsRateEnabled
					TruthValue
			 }

		-- 1.3.6.1.4.1.388.11.3.4.1.10.1.1
		apRadioNMcsRateIndex OBJECT-TYPE
			SYNTAX INTEGER (1..16)
			MAX-ACCESS read-only
			STATUS current
			DESCRIPTION
				"MCS index, from 1-16, corresponding to schemes 0-15."
			::= { apRadioNMcsRateEntry 1 }

		
		-- 1.3.6.1.4.1.388.11.3.4.1.10.1.2
		apRadioNMcsRate20MHzChanSgiDisabled OBJECT-TYPE
			SYNTAX Integer32
			UNITS "Kbps"
			MAX-ACCESS read-only
			STATUS current
			DESCRIPTION
				"Rate on 20MHz channel with SGI disabled"
			::= { apRadioNMcsRateEntry 2 }

		
		-- 1.3.6.1.4.1.388.11.3.4.1.10.1.3
		apRadioNMcsRate20MHzChanSgiEnabled OBJECT-TYPE
			SYNTAX Integer32
			UNITS "Kbps"
			MAX-ACCESS read-only
			STATUS deprecated
			DESCRIPTION
				"Rate on 20MHz channel with SGI enabled"
			::= { apRadioNMcsRateEntry 3 }

		
		-- 1.3.6.1.4.1.388.11.3.4.1.10.1.4
		apRadioNMcsRate40MHzChanSgiDisabled OBJECT-TYPE
			SYNTAX Integer32
			UNITS "Kbps"
			MAX-ACCESS read-only
			STATUS current
			DESCRIPTION
				"Rate on 40MHz channel with SGI disabled"
			::= { apRadioNMcsRateEntry 4 }

		
		-- 1.3.6.1.4.1.388.11.3.4.1.10.1.5
		apRadioNMcsRate40MHzChanSgiEnabled OBJECT-TYPE
			SYNTAX Integer32
			UNITS "Kbps"
			MAX-ACCESS read-only
			STATUS current
			DESCRIPTION
				"Rate on 40MHz channel with SGI enabled."
			::= { apRadioNMcsRateEntry 5 }

		
		-- 1.3.6.1.4.1.388.11.3.4.1.10.1.6
		apRadioNMcsRateType OBJECT-TYPE
			SYNTAX INTEGER
				{
				basic(1),
				supported(2)
				}
			MAX-ACCESS read-write
			STATUS current
			DESCRIPTION
				"Whether this MCS rate is basic or supported."
			::= { apRadioNMcsRateEntry 6 }

		
		-- 1.3.6.1.4.1.388.11.3.4.1.10.1.7
		apRadioNMcsRateEnabled OBJECT-TYPE
			SYNTAX TruthValue
			MAX-ACCESS read-write
			STATUS current
			DESCRIPTION
				"Whether this MCS is disabled (false), or, enabled (true) for this 'n' radio."
			::= { apRadioNMcsRateEntry 7 }

		
-- This group describes all wireless LANs on the switch,
-- and their corresponding security settings.
		-- 1.3.6.1.4.1.388.11.3.4.2
		apWlan OBJECT IDENTIFIER ::= { apRf 2 }

		
		-- 1.3.6.1.4.1.388.11.3.4.2.1
		apWlanTable OBJECT-TYPE
			SYNTAX SEQUENCE OF ApWlanEntry
			MAX-ACCESS not-accessible
			STATUS current
			DESCRIPTION
				"Table of wireless LANs configured on the AP."
			::= { apWlan 1 }

		
		-- 1.3.6.1.4.1.388.11.3.4.2.1.1
		apWlanEntry OBJECT-TYPE
			SYNTAX ApWlanEntry
			MAX-ACCESS not-accessible
			STATUS current
			DESCRIPTION
				" "
			INDEX { apWlanIndex }
			::= { apWlanTable 1 }

		
		ApWlanEntry ::=
			SEQUENCE { 
				apWlanIndex
					Integer32,
				apWlanName
					DisplayString,
				apWlanEssid
					DisplayString,
				apWlanUseRadio
					INTEGER,
				apWlanMaxMus
					Integer32,
				apWlanAclPolicy
					SinglePointer,
				apWlanSecurityPolicy
					SinglePointer,
				apWlanQosPolicy
					SinglePointer,
				apWlanAuthKerberosUsername
					DisplayString,
				apWlanAuthKerberosPassword
					Password,
				apWlanDisallowMuToMu
					TruthValue,
				apWlanUseSecureBeacon
					TruthValue,
				apWlanAnswerBroadcastEss
					TruthValue,
				apWlanWeight
					Integer32,
				apWlanVlanMode
					INTEGER,
				apWlanVlanId
					SinglePointer,
				apWlanSubnet
					INTEGER,
				apWlanClientBackHaul
					TruthValue,
				apWlanHotspot
					TruthValue,
				apWlanEnable
					TruthValue,
				apWlanMuIdleTimeout
					INTEGER
			 }

		-- 1.3.6.1.4.1.388.11.3.4.2.1.1.1
		apWlanIndex OBJECT-TYPE
			SYNTAX Integer32 (1..16)
			MAX-ACCESS accessible-for-notify
			STATUS current
			DESCRIPTION
				"Simple index."
			::= { apWlanEntry 1 }

		
		-- 1.3.6.1.4.1.388.11.3.4.2.1.1.2
		apWlanName OBJECT-TYPE
			SYNTAX DisplayString
			MAX-ACCESS read-write
			STATUS current
			DESCRIPTION
				"Name of the WLAN."
			::= { apWlanEntry 2 }

		
		-- 1.3.6.1.4.1.388.11.3.4.2.1.1.3
		apWlanEssid OBJECT-TYPE
			SYNTAX DisplayString
			MAX-ACCESS read-write
			STATUS current
			DESCRIPTION
				"ESSID of the WLAN."
			::= { apWlanEntry 3 }

		
		-- 1.3.6.1.4.1.388.11.3.4.2.1.1.4
		apWlanUseRadio OBJECT-TYPE
			SYNTAX INTEGER
				{
				noneBand(0),
				bgRadio(1),
				aRadio(2),
				bothBand(3),
				nRadio2400MHz(4),
				nRadio5000MHz(5)
				}
			MAX-ACCESS read-write
			STATUS current
			DESCRIPTION
				"Use either 802.11a radio or 802.11b/g radio, or, for 802.11n radios, 
				select the frequency band i.e. 2.4 GHz or 5.0 GHz."
			::= { apWlanEntry 4 }

		
		-- 1.3.6.1.4.1.388.11.3.4.2.1.1.5
		apWlanMaxMus OBJECT-TYPE
			SYNTAX Integer32
			MAX-ACCESS read-write
			STATUS current
			DESCRIPTION
				"Maximum number of MU associations is allowed for the
				WLAN. The total number of MUs for the entire AP cannot
				exceed 127."
			::= { apWlanEntry 5 }

		
		-- 1.3.6.1.4.1.388.11.3.4.2.1.1.6
		apWlanAclPolicy OBJECT-TYPE
			SYNTAX SinglePointer
			MAX-ACCESS read-write
			STATUS current
			DESCRIPTION
				"Point to the ACL policy used for this WLAN."
			::= { apWlanEntry 6 }

		
		-- 1.3.6.1.4.1.388.11.3.4.2.1.1.7
		apWlanSecurityPolicy OBJECT-TYPE
			SYNTAX SinglePointer
			MAX-ACCESS read-write
			STATUS current
			DESCRIPTION
				"Point to the Security policy used for this WLAN."
			::= { apWlanEntry 7 }

		
		-- 1.3.6.1.4.1.388.11.3.4.2.1.1.8
		apWlanQosPolicy OBJECT-TYPE
			SYNTAX SinglePointer
			MAX-ACCESS read-write
			STATUS current
			DESCRIPTION
				"Point to the QOS policy used for this WLAN."
			::= { apWlanEntry 8 }

		
		-- 1.3.6.1.4.1.388.11.3.4.2.1.1.9
		apWlanAuthKerberosUsername OBJECT-TYPE
			SYNTAX DisplayString
			MAX-ACCESS read-only
			STATUS current
			DESCRIPTION
				"Kerberos Username which is the same as the ESSID
				if the WLAN uses Kerberos Authentication"
			::= { apWlanEntry 9 }

		
		-- 1.3.6.1.4.1.388.11.3.4.2.1.1.10
		apWlanAuthKerberosPassword OBJECT-TYPE
			SYNTAX Password
			MAX-ACCESS read-write
			STATUS current
			DESCRIPTION
				"Kerberos Password for authenticating the AP to the KDC."
			::= { apWlanEntry 10 }

		
		-- 1.3.6.1.4.1.388.11.3.4.2.1.1.11
		apWlanDisallowMuToMu OBJECT-TYPE
			SYNTAX TruthValue
			MAX-ACCESS read-write
			STATUS current
			DESCRIPTION
				"Set to true to prohibit MU-to-MU communication."
			::= { apWlanEntry 11 }

		
		-- 1.3.6.1.4.1.388.11.3.4.2.1.1.12
		apWlanUseSecureBeacon OBJECT-TYPE
			SYNTAX TruthValue
			MAX-ACCESS read-write
			STATUS current
			DESCRIPTION
				"Enable the Secure Beacon checkbox to disallow the 
				Access Point from broadcasting an ESSID in its 
				beacons. This is a safeguard to prevent intruders 
				from tapping into the WLAN. Consider this security 
				measure for a private, corporate network."
			::= { apWlanEntry 12 }

		
		-- 1.3.6.1.4.1.388.11.3.4.2.1.1.13
		apWlanAnswerBroadcastEss OBJECT-TYPE
			SYNTAX TruthValue
			MAX-ACCESS read-write
			STATUS current
			DESCRIPTION
				"Answer broadcast ESS."
			::= { apWlanEntry 13 }

		
		-- 1.3.6.1.4.1.388.11.3.4.2.1.1.14
		apWlanWeight OBJECT-TYPE
			SYNTAX Integer32
			MAX-ACCESS read-write
			STATUS obsolete
			DESCRIPTION
				"The weight to be used when QoS for all WLANs
				is set to weighted-round-robin.
				
				Note that the sum of all weights across all
				WLANs need not total 100.
				"
			::= { apWlanEntry 14 }

		
		-- 1.3.6.1.4.1.388.11.3.4.2.1.1.15
		apWlanVlanMode OBJECT-TYPE
			SYNTAX INTEGER
				{
				modeDynamic(1),
				modeStatic(2)
				}
			MAX-ACCESS read-write
			STATUS current
			DESCRIPTION
				"VLAN mode can either Dynamic or Static."
			::= { apWlanEntry 15 }

		
		-- 1.3.6.1.4.1.388.11.3.4.2.1.1.16
		apWlanVlanId OBJECT-TYPE
			SYNTAX SinglePointer
			MAX-ACCESS read-write
			STATUS current
			DESCRIPTION
				"Point to the VLAN id corresponding to WLAN."
			::= { apWlanEntry 16 }

		
		-- 1.3.6.1.4.1.388.11.3.4.2.1.1.17
		apWlanSubnet OBJECT-TYPE
			SYNTAX INTEGER
				{
				lan1(1),
				lan2(2)
				}
			MAX-ACCESS read-write
			STATUS current
			DESCRIPTION
				"The LAN to which a WLAN is mapped."
			::= { apWlanEntry 17 }

		
		-- 1.3.6.1.4.1.388.11.3.4.2.1.1.18
		apWlanClientBackHaul OBJECT-TYPE
			SYNTAX TruthValue
			MAX-ACCESS read-write
			STATUS current
			DESCRIPTION
				"Enable/Disable MESH Client Backhaul on this WLAN."
			::= { apWlanEntry 18 }

		
		-- 1.3.6.1.4.1.388.11.3.4.2.1.1.19
		apWlanHotspot OBJECT-TYPE
			SYNTAX TruthValue
			MAX-ACCESS read-write
			STATUS current
			DESCRIPTION
				"Enable or Disable Hotspot functionality on this WLAN."
			::= { apWlanEntry 19 }

		
		-- 1.3.6.1.4.1.388.11.3.4.2.1.1.20
		apWlanEnable OBJECT-TYPE
			SYNTAX TruthValue
			MAX-ACCESS read-write
			STATUS current
			DESCRIPTION
				"Row enable/disable."
			::= { apWlanEntry 20 }

		
		-- 1.3.6.1.4.1.388.11.3.4.2.1.1.21
		apWlanMuIdleTimeout OBJECT-TYPE
			SYNTAX INTEGER (1..1440)
			UNITS "minutes"
			MAX-ACCESS read-write
			STATUS current
			DESCRIPTION
				"Maximum MU idle time in minutes."
			::= { apWlanEntry 21 }

		
		-- 1.3.6.1.4.1.388.11.3.4.2.2
		apWlanSecPolicyTable OBJECT-TYPE
			SYNTAX SEQUENCE OF ApWlanSecPolicyEntry
			MAX-ACCESS not-accessible
			STATUS current
			DESCRIPTION
				"Security Policy that can be used by different WLANs."
			::= { apWlan 2 }

		
		-- 1.3.6.1.4.1.388.11.3.4.2.2.1
		apWlanSecPolicyEntry OBJECT-TYPE
			SYNTAX ApWlanSecPolicyEntry
			MAX-ACCESS not-accessible
			STATUS current
			DESCRIPTION
				" "
			INDEX { apWlanSecPolicyIndex }
			::= { apWlanSecPolicyTable 1 }

		
		ApWlanSecPolicyEntry ::=
			SEQUENCE { 
				apWlanSecPolicyIndex
					Integer32,
				apWlanSecPolicyName
					DisplayString,
				apWlanSecPolicyAuthentication
					INTEGER,
				apWlanSecPolicyEncryption
					INTEGER,
				apWlanSecPolicyPointerToWlan
					MultiPointer63,
				apWlanSecPolicyRowStatus
					AbbrevRowStatus
			 }

		-- 1.3.6.1.4.1.388.11.3.4.2.2.1.1
		apWlanSecPolicyIndex OBJECT-TYPE
			SYNTAX Integer32 (1..16)
			MAX-ACCESS accessible-for-notify
			STATUS current
			DESCRIPTION
				"Simple index."
			::= { apWlanSecPolicyEntry 1 }

		
		-- 1.3.6.1.4.1.388.11.3.4.2.2.1.2
		apWlanSecPolicyName OBJECT-TYPE
			SYNTAX DisplayString
			MAX-ACCESS read-write
			STATUS current
			DESCRIPTION
				"Name of security policy."
			::= { apWlanSecPolicyEntry 2 }

		
		-- 1.3.6.1.4.1.388.11.3.4.2.2.1.3
		apWlanSecPolicyAuthentication OBJECT-TYPE
			SYNTAX INTEGER
				{
				authNone(1),
				auth802dot1xEap(2),
				authKerberos(3)
				}
			MAX-ACCESS read-write
			STATUS current
			DESCRIPTION
				"If auth802dot1xEap, additional EAP settings for this
				WLAN will be used from the matching entry in the
				apWlanAuthEapTable.
				
				Likewise, if authKerberos, use the settings in the
				matching entry in the apWlanAuthKerberosTable."
			::= { apWlanSecPolicyEntry 3 }

		
		-- 1.3.6.1.4.1.388.11.3.4.2.2.1.4
		apWlanSecPolicyEncryption OBJECT-TYPE
			SYNTAX INTEGER
				{
				cryptoNone(1),
				cryptoWep40(2),
				cryptoWep128(3),
				cryptoKeyguardMcm(4),
				cryptoWpaTkip(5),
				cryptoCcmp(6)
				}
			MAX-ACCESS read-write
			STATUS current
			DESCRIPTION
				"If cryptoWep40 or cryptoWep128, additional WEP 
				settings for this WLAN will be used from the matching
				entry in the apWlanCryptoWepTable.
				
				Likewise, if cryptoWpaTkip, use the settings in the
				matching entry in the apWlanCryptoTkipTable.
				
				Likewise, if cryptoKeyguardMcm, use the settings in
				the matching entry in the apWlanCryptoKeyguardTable.
				
				Likewise, if cryptoCcmp, use the settings in
				the matching entry in the apWlanCryptoCcmpTable."
			::= { apWlanSecPolicyEntry 4 }

		
		-- 1.3.6.1.4.1.388.11.3.4.2.2.1.5
		apWlanSecPolicyPointerToWlan OBJECT-TYPE
			SYNTAX MultiPointer63
			MAX-ACCESS read-only
			STATUS current
			DESCRIPTION
				"Points to the WLAN which have this 
				particular security policy."
			::= { apWlanSecPolicyEntry 5 }

		
		-- 1.3.6.1.4.1.388.11.3.4.2.2.1.6
		apWlanSecPolicyRowStatus OBJECT-TYPE
			SYNTAX AbbrevRowStatus
			MAX-ACCESS read-write
			STATUS current
			DESCRIPTION
				"Row Status used for Creation or Deletion."
			::= { apWlanSecPolicyEntry 6 }

		
-- This group contains authentication settings for all
-- WLANs.
		-- 1.3.6.1.4.1.388.11.3.4.2.3
		apWlanAuth OBJECT IDENTIFIER ::= { apWlan 3 }

		
		-- 1.3.6.1.4.1.388.11.3.4.2.3.1
		apWlanAuthEapTable OBJECT-TYPE
			SYNTAX SEQUENCE OF ApWlanAuthEapEntry
			MAX-ACCESS not-accessible
			STATUS current
			DESCRIPTION
				"Table of EAP authentication settings
				for each Security Policy using this method."
			::= { apWlanAuth 1 }

		
		-- 1.3.6.1.4.1.388.11.3.4.2.3.1.1
		apWlanAuthEapEntry OBJECT-TYPE
			SYNTAX ApWlanAuthEapEntry
			MAX-ACCESS not-accessible
			STATUS current
			DESCRIPTION
				" "
			INDEX { apWlanSecPolicyIndex }
			::= { apWlanAuthEapTable 1 }

		
		ApWlanAuthEapEntry ::=
			SEQUENCE { 
				apWlanAuthEapReauthenticationEnable
					TruthValue,
				apWlanAuthEapReauthenticationPeriod
					Unsigned32,
				apWlanAuthEapReauthenticationMaxRetries
					Unsigned32,
				apWlanAuthEapRadius1Server
					IpAddress,
				apWlanAuthEapRadius1Port
					Unsigned32,
				apWlanAuthEapRadius1SharedSecret
					Password,
				apWlanAuthEapRadius2Server
					IpAddress,
				apWlanAuthEapRadius2Port
					Unsigned32,
				apWlanAuthEapRadius2SharedSecret
					Password,
				apWlanAuthEapMuQuietPeriod
					Unsigned32,
				apWlanAuthEapMuTimeout
					Unsigned32,
				apWlanAuthEapMuTxPeriod
					Unsigned32,
				apWlanAuthEapMuMaxRetries
					Unsigned32,
				apWlanAuthEapServerTimeout
					Unsigned32,
				apWlanAuthEapServerMaxRetries
					Unsigned32,
				apWlanAuthEapRadiusAcctMode
					TruthValue,
				apWlanAuthEapRadiusAcctMuTimeout
					Unsigned32,
				apWlanAuthEapRadiusAcctMuRetries
					Unsigned32,
				apWlanAuthEapSyslogMode
					TruthValue,
				apWlanAuthEapSyslogServerIp
					IpAddress,
				apWlanAuthEapRadiusExtAcctServer
					IpAddress,
				apWlanAuthEapRadiusExtPort
					Unsigned32,
				apWlanAuthEapRadiusExtSharedSecret
					Password
			 }

		-- 1.3.6.1.4.1.388.11.3.4.2.3.1.1.1
		apWlanAuthEapReauthenticationEnable OBJECT-TYPE
			SYNTAX TruthValue
			MAX-ACCESS read-write
			STATUS current
			DESCRIPTION
				"Enable reauthentication."
			::= { apWlanAuthEapEntry 1 }

		
		-- 1.3.6.1.4.1.388.11.3.4.2.3.1.1.2
		apWlanAuthEapReauthenticationPeriod OBJECT-TYPE
			SYNTAX Unsigned32 (30..9999)
			UNITS "seconds"
			MAX-ACCESS read-write
			STATUS current
			DESCRIPTION
				"Reauthentication period."
			::= { apWlanAuthEapEntry 2 }

		
		-- 1.3.6.1.4.1.388.11.3.4.2.3.1.1.3
		apWlanAuthEapReauthenticationMaxRetries OBJECT-TYPE
			SYNTAX Unsigned32 (1..99)
			MAX-ACCESS read-write
			STATUS current
			DESCRIPTION
				"Reauthentication max retries."
			::= { apWlanAuthEapEntry 3 }

		
		-- 1.3.6.1.4.1.388.11.3.4.2.3.1.1.4
		apWlanAuthEapRadius1Server OBJECT-TYPE
			SYNTAX IpAddress
			MAX-ACCESS read-write
			STATUS current
			DESCRIPTION
				"IP address of the primary RADIUS server.
				Use 127.0.0.1 to use the Local Radius Server on the AP5131."
			::= { apWlanAuthEapEntry 4 }

		
		-- 1.3.6.1.4.1.388.11.3.4.2.3.1.1.5
		apWlanAuthEapRadius1Port OBJECT-TYPE
			SYNTAX Unsigned32
			MAX-ACCESS read-write
			STATUS current
			DESCRIPTION
				"Port number of the primary RADIUS server."
			::= { apWlanAuthEapEntry 5 }

		
		-- 1.3.6.1.4.1.388.11.3.4.2.3.1.1.6
		apWlanAuthEapRadius1SharedSecret OBJECT-TYPE
			SYNTAX Password
			MAX-ACCESS read-write
			STATUS current
			DESCRIPTION
				"Shared secret of the primary RADIUS server."
			::= { apWlanAuthEapEntry 6 }

		
		-- 1.3.6.1.4.1.388.11.3.4.2.3.1.1.7
		apWlanAuthEapRadius2Server OBJECT-TYPE
			SYNTAX IpAddress
			MAX-ACCESS read-write
			STATUS current
			DESCRIPTION
				"IP address of the secondary RADIUS server.
				Use 127.0.0.1 to use the Local Radius Server on the AP5131."
			::= { apWlanAuthEapEntry 7 }

		
		-- 1.3.6.1.4.1.388.11.3.4.2.3.1.1.8
		apWlanAuthEapRadius2Port OBJECT-TYPE
			SYNTAX Unsigned32
			MAX-ACCESS read-write
			STATUS current
			DESCRIPTION
				"Port number of the secondary RADIUS server."
			::= { apWlanAuthEapEntry 8 }

		
		-- 1.3.6.1.4.1.388.11.3.4.2.3.1.1.9
		apWlanAuthEapRadius2SharedSecret OBJECT-TYPE
			SYNTAX Password
			MAX-ACCESS read-write
			STATUS current
			DESCRIPTION
				"Shared secret of the secondary RADIUS server."
			::= { apWlanAuthEapEntry 9 }

		
		-- 1.3.6.1.4.1.388.11.3.4.2.3.1.1.10
		apWlanAuthEapMuQuietPeriod OBJECT-TYPE
			SYNTAX Unsigned32 (1..65535)
			UNITS "seconds"
			MAX-ACCESS read-write
			STATUS current
			DESCRIPTION
				"MU quiet period."
			::= { apWlanAuthEapEntry 10 }

		
		-- 1.3.6.1.4.1.388.11.3.4.2.3.1.1.11
		apWlanAuthEapMuTimeout OBJECT-TYPE
			SYNTAX Unsigned32 (1..255)
			UNITS "seconds"
			MAX-ACCESS read-write
			STATUS current
			DESCRIPTION
				"MU timeout."
			::= { apWlanAuthEapEntry 11 }

		
		-- 1.3.6.1.4.1.388.11.3.4.2.3.1.1.12
		apWlanAuthEapMuTxPeriod OBJECT-TYPE
			SYNTAX Unsigned32 (1..65535)
			UNITS "seconds"
			MAX-ACCESS read-write
			STATUS current
			DESCRIPTION
				"MU Tx period."
			::= { apWlanAuthEapEntry 12 }

		
		-- 1.3.6.1.4.1.388.11.3.4.2.3.1.1.13
		apWlanAuthEapMuMaxRetries OBJECT-TYPE
			SYNTAX Unsigned32 (1..10)
			MAX-ACCESS read-write
			STATUS current
			DESCRIPTION
				"MU max retries."
			::= { apWlanAuthEapEntry 13 }

		
		-- 1.3.6.1.4.1.388.11.3.4.2.3.1.1.14
		apWlanAuthEapServerTimeout OBJECT-TYPE
			SYNTAX Unsigned32 (1..255)
			UNITS "seconds"
			MAX-ACCESS read-write
			STATUS current
			DESCRIPTION
				"Server timeout."
			::= { apWlanAuthEapEntry 14 }

		
		-- 1.3.6.1.4.1.388.11.3.4.2.3.1.1.15
		apWlanAuthEapServerMaxRetries OBJECT-TYPE
			SYNTAX Unsigned32 (1..255)
			MAX-ACCESS read-write
			STATUS current
			DESCRIPTION
				"Server max retries."
			::= { apWlanAuthEapEntry 15 }

		
		-- 1.3.6.1.4.1.388.11.3.4.2.3.1.1.16
		apWlanAuthEapRadiusAcctMode OBJECT-TYPE
			SYNTAX TruthValue
			MAX-ACCESS read-write
			STATUS current
			DESCRIPTION
				"Radius Accounting Mode."
			::= { apWlanAuthEapEntry 16 }

		
		-- 1.3.6.1.4.1.388.11.3.4.2.3.1.1.17
		apWlanAuthEapRadiusAcctMuTimeout OBJECT-TYPE
			SYNTAX Unsigned32 (1..255)
			MAX-ACCESS read-write
			STATUS current
			DESCRIPTION
				"Radius Accounting MU Timeout value"
			::= { apWlanAuthEapEntry 17 }

		
		-- 1.3.6.1.4.1.388.11.3.4.2.3.1.1.18
		apWlanAuthEapRadiusAcctMuRetries OBJECT-TYPE
			SYNTAX Unsigned32 (1..10)
			MAX-ACCESS read-write
			STATUS current
			DESCRIPTION
				"Radius Accounting Number of MU Retries."
			::= { apWlanAuthEapEntry 18 }

		
		-- 1.3.6.1.4.1.388.11.3.4.2.3.1.1.19
		apWlanAuthEapSyslogMode OBJECT-TYPE
			SYNTAX TruthValue
			MAX-ACCESS read-write
			STATUS current
			DESCRIPTION
				"Syslogging Mode."
			::= { apWlanAuthEapEntry 19 }

		
		-- 1.3.6.1.4.1.388.11.3.4.2.3.1.1.20
		apWlanAuthEapSyslogServerIp OBJECT-TYPE
			SYNTAX IpAddress
			MAX-ACCESS read-write
			STATUS current
			DESCRIPTION
				"Syslog Server IP Address."
			::= { apWlanAuthEapEntry 20 }

		
		-- 1.3.6.1.4.1.388.11.3.4.2.3.1.1.21
		apWlanAuthEapRadiusExtAcctServer OBJECT-TYPE
			SYNTAX IpAddress
			MAX-ACCESS read-write
			STATUS current
			DESCRIPTION
				"External Radius Accounting Server IP Address."
			::= { apWlanAuthEapEntry 21 }

		
		-- 1.3.6.1.4.1.388.11.3.4.2.3.1.1.22
		apWlanAuthEapRadiusExtPort OBJECT-TYPE
			SYNTAX Unsigned32
			MAX-ACCESS read-write
			STATUS current
			DESCRIPTION
				"Port number of the external RADIUS server."
			::= { apWlanAuthEapEntry 22 }

		
		-- 1.3.6.1.4.1.388.11.3.4.2.3.1.1.23
		apWlanAuthEapRadiusExtSharedSecret OBJECT-TYPE
			SYNTAX Password
			MAX-ACCESS read-write
			STATUS current
			DESCRIPTION
				"Shared secret of the external RADIUS server."
			::= { apWlanAuthEapEntry 23 }

		
		-- 1.3.6.1.4.1.388.11.3.4.2.3.2
		apWlanAuthKerberosTable OBJECT-TYPE
			SYNTAX SEQUENCE OF ApWlanAuthKerberosEntry
			MAX-ACCESS not-accessible
			STATUS current
			DESCRIPTION
				"Table of Kerberos authentication settings
				for each Security Policy using this method."
			::= { apWlanAuth 2 }

		
		-- 1.3.6.1.4.1.388.11.3.4.2.3.2.1
		apWlanAuthKerberosEntry OBJECT-TYPE
			SYNTAX ApWlanAuthKerberosEntry
			MAX-ACCESS not-accessible
			STATUS current
			DESCRIPTION
				" "
			INDEX { apWlanSecPolicyIndex }
			::= { apWlanAuthKerberosTable 1 }

		
		ApWlanAuthKerberosEntry ::=
			SEQUENCE { 
				apWlanAuthKerberosRealmName
					DisplayString,
				apWlanAuthKerberosKdcServerIp1
					IpAddress,
				apWlanAuthKerberosKdcPort1
					Unsigned32,
				apWlanAuthKerberosKdcServerIp2
					IpAddress,
				apWlanAuthKerberosKdcPort2
					Unsigned32,
				apWlanAuthKerberosKdcServerIpR
					IpAddress,
				apWlanAuthKerberosKdcPortR
					Unsigned32
			 }

		-- 1.3.6.1.4.1.388.11.3.4.2.3.2.1.1
		apWlanAuthKerberosRealmName OBJECT-TYPE
			SYNTAX DisplayString
			MAX-ACCESS read-write
			STATUS current
			DESCRIPTION
				"Realm name."
			::= { apWlanAuthKerberosEntry 1 }

		
		-- 1.3.6.1.4.1.388.11.3.4.2.3.2.1.2
		apWlanAuthKerberosKdcServerIp1 OBJECT-TYPE
			SYNTAX IpAddress
			MAX-ACCESS read-write
			STATUS current
			DESCRIPTION
				"Primary KDC server IP addr."
			::= { apWlanAuthKerberosEntry 2 }

		
		-- 1.3.6.1.4.1.388.11.3.4.2.3.2.1.3
		apWlanAuthKerberosKdcPort1 OBJECT-TYPE
			SYNTAX Unsigned32
			MAX-ACCESS read-write
			STATUS current
			DESCRIPTION
				"Primary KDC port."
			::= { apWlanAuthKerberosEntry 3 }

		
		-- 1.3.6.1.4.1.388.11.3.4.2.3.2.1.4
		apWlanAuthKerberosKdcServerIp2 OBJECT-TYPE
			SYNTAX IpAddress
			MAX-ACCESS read-write
			STATUS current
			DESCRIPTION
				"Backup KDC server IP addr."
			::= { apWlanAuthKerberosEntry 4 }

		
		-- 1.3.6.1.4.1.388.11.3.4.2.3.2.1.5
		apWlanAuthKerberosKdcPort2 OBJECT-TYPE
			SYNTAX Unsigned32
			MAX-ACCESS read-write
			STATUS current
			DESCRIPTION
				"Backup KDC port."
			::= { apWlanAuthKerberosEntry 5 }

		
		-- 1.3.6.1.4.1.388.11.3.4.2.3.2.1.6
		apWlanAuthKerberosKdcServerIpR OBJECT-TYPE
			SYNTAX IpAddress
			MAX-ACCESS read-write
			STATUS current
			DESCRIPTION
				"Remote KDC server IP addr."
			::= { apWlanAuthKerberosEntry 6 }

		
		-- 1.3.6.1.4.1.388.11.3.4.2.3.2.1.7
		apWlanAuthKerberosKdcPortR OBJECT-TYPE
			SYNTAX Unsigned32
			MAX-ACCESS read-write
			STATUS current
			DESCRIPTION
				"Remote KDC port."
			::= { apWlanAuthKerberosEntry 7 }

		
-- This group contains encryption settings for all WLANs.
		-- 1.3.6.1.4.1.388.11.3.4.2.4
		apWlanCrypto OBJECT IDENTIFIER ::= { apWlan 4 }

		
		-- 1.3.6.1.4.1.388.11.3.4.2.4.1
		apWlanCryptoWepTable OBJECT-TYPE
			SYNTAX SEQUENCE OF ApWlanCryptoWepEntry
			MAX-ACCESS not-accessible
			STATUS current
			DESCRIPTION
				"Table of WEP encryption settings
				for each Security Policy using this method."
			::= { apWlanCrypto 1 }

		
		-- 1.3.6.1.4.1.388.11.3.4.2.4.1.1
		apWlanCryptoWepEntry OBJECT-TYPE
			SYNTAX ApWlanCryptoWepEntry
			MAX-ACCESS not-accessible
			STATUS current
			DESCRIPTION
				" "
			INDEX { apWlanSecPolicyIndex }
			::= { apWlanCryptoWepTable 1 }

		
		ApWlanCryptoWepEntry ::=
			SEQUENCE { 
				apWlanCryptoWepPassKey
					Password,
				apWlanCryptoWepKey1
					OCTET STRING,
				apWlanCryptoWepKey2
					OCTET STRING,
				apWlanCryptoWepKey3
					OCTET STRING,
				apWlanCryptoWepKey4
					OCTET STRING,
				apWlanCryptoWepKeyToUse
					Integer32,
				apWlanCryptoWepMixedMode
					TruthValue
			 }

		-- 1.3.6.1.4.1.388.11.3.4.2.4.1.1.1
		apWlanCryptoWepPassKey OBJECT-TYPE
			SYNTAX Password (SIZE (4..32))
			MAX-ACCESS read-write
			STATUS current
			DESCRIPTION
				"Pass key.
				
				If this value is written, the four WepKey1..4 will
				be overwritten."
			::= { apWlanCryptoWepEntry 1 }

		
		-- 1.3.6.1.4.1.388.11.3.4.2.4.1.1.2
		apWlanCryptoWepKey1 OBJECT-TYPE
			SYNTAX OCTET STRING (SIZE (0..13))
			MAX-ACCESS read-write
			STATUS current
			DESCRIPTION
				"WEP key #1
				
				exactly 13 octets for WEP-128 (104-bit key);
				exactly  5 octets for WEP-64 (40-bit key).
				"
			::= { apWlanCryptoWepEntry 2 }

		
		-- 1.3.6.1.4.1.388.11.3.4.2.4.1.1.3
		apWlanCryptoWepKey2 OBJECT-TYPE
			SYNTAX OCTET STRING (SIZE (0..13))
			MAX-ACCESS read-write
			STATUS current
			DESCRIPTION
				"WEP key #2
				
				exactly 13 octets for WEP-128 (104-bit key);
				exactly  5 octets for WEP-64 (40-bit key)."
			::= { apWlanCryptoWepEntry 3 }

		
		-- 1.3.6.1.4.1.388.11.3.4.2.4.1.1.4
		apWlanCryptoWepKey3 OBJECT-TYPE
			SYNTAX OCTET STRING (SIZE (0..13))
			MAX-ACCESS read-write
			STATUS current
			DESCRIPTION
				"WEP key #3
				
				exactly 13 octets for WEP-128 (104-bit key);
				exactly  5 octets for WEP-64 (40-bit key)."
			::= { apWlanCryptoWepEntry 4 }

		
		-- 1.3.6.1.4.1.388.11.3.4.2.4.1.1.5
		apWlanCryptoWepKey4 OBJECT-TYPE
			SYNTAX OCTET STRING (SIZE (0..13))
			MAX-ACCESS read-write
			STATUS current
			DESCRIPTION
				"WEP key #4
				
				exactly 13 octets for WEP-128 (104-bit key);
				exactly  5 octets for WEP-64 (40-bit key)."
			::= { apWlanCryptoWepEntry 5 }

		
		-- 1.3.6.1.4.1.388.11.3.4.2.4.1.1.6
		apWlanCryptoWepKeyToUse OBJECT-TYPE
			SYNTAX Integer32 (1..4)
			MAX-ACCESS read-write
			STATUS current
			DESCRIPTION
				"Specifies which WEP key to use."
			::= { apWlanCryptoWepEntry 6 }

		
		-- 1.3.6.1.4.1.388.11.3.4.2.4.1.1.7
		apWlanCryptoWepMixedMode OBJECT-TYPE
			SYNTAX TruthValue
			MAX-ACCESS read-write
			STATUS current
			DESCRIPTION
				"Allow WEP128 clients"
			::= { apWlanCryptoWepEntry 7 }

		
		-- 1.3.6.1.4.1.388.11.3.4.2.4.2
		apWlanCryptoTkipTable OBJECT-TYPE
			SYNTAX SEQUENCE OF ApWlanCryptoTkipEntry
			MAX-ACCESS not-accessible
			STATUS current
			DESCRIPTION
				"Table of WPA-TKIP encryption settings
				for each Security Policy using this method."
			::= { apWlanCrypto 2 }

		
		-- 1.3.6.1.4.1.388.11.3.4.2.4.2.1
		apWlanCryptoTkipEntry OBJECT-TYPE
			SYNTAX ApWlanCryptoTkipEntry
			MAX-ACCESS not-accessible
			STATUS current
			DESCRIPTION
				" "
			INDEX { apWlanSecPolicyIndex }
			::= { apWlanCryptoTkipTable 1 }

		
		ApWlanCryptoTkipEntry ::=
			SEQUENCE { 
				apWlanCryptoTkipBcastKeyRotation
					TruthValue,
				apWlanCryptoTkipKeyRotationInterval
					Unsigned32,
				apWlanCryptoTkipKeyToUse
					INTEGER,
				apWlanCryptoTkipPassphrase
					OCTET STRING,
				apWlanCryptoTkipKey
					OCTET STRING,
				apWlanCryptoTkipAllowWpa2Client
					INTEGER,
				apWlanCryptoTkipFastRoamPreAuth
					INTEGER
			 }

		-- 1.3.6.1.4.1.388.11.3.4.2.4.2.1.1
		apWlanCryptoTkipBcastKeyRotation OBJECT-TYPE
			SYNTAX TruthValue
			MAX-ACCESS read-write
			STATUS current
			DESCRIPTION
				"Use broadcast key rotation."
			::= { apWlanCryptoTkipEntry 1 }

		
		-- 1.3.6.1.4.1.388.11.3.4.2.4.2.1.2
		apWlanCryptoTkipKeyRotationInterval OBJECT-TYPE
			SYNTAX Unsigned32 (30..604800)
			UNITS "seconds"
			MAX-ACCESS read-write
			STATUS current
			DESCRIPTION
				"Broadcast key rotation, (if enabled), occurs every 
				this many seconds."
			::= { apWlanCryptoTkipEntry 2 }

		
		-- 1.3.6.1.4.1.388.11.3.4.2.4.2.1.3
		apWlanCryptoTkipKeyToUse OBJECT-TYPE
			SYNTAX INTEGER
				{
				useAsciiPassphrase(1),
				use256bitKey(2)
				}
			MAX-ACCESS read-write
			STATUS current
			DESCRIPTION
				"Specifies whether to use ASCII Passphrase
				or 256-bit Hex Key."
			::= { apWlanCryptoTkipEntry 3 }

		
		-- 1.3.6.1.4.1.388.11.3.4.2.4.2.1.4
		apWlanCryptoTkipPassphrase OBJECT-TYPE
			SYNTAX OCTET STRING (SIZE (8..63))
			MAX-ACCESS read-write
			STATUS current
			DESCRIPTION
				"ASCII Passphrase."
			::= { apWlanCryptoTkipEntry 4 }

		
		-- 1.3.6.1.4.1.388.11.3.4.2.4.2.1.5
		apWlanCryptoTkipKey OBJECT-TYPE
			SYNTAX OCTET STRING (SIZE (32))
			MAX-ACCESS read-write
			STATUS current
			DESCRIPTION
				"WPA/TKIP 256 bit Key.
				No need to enter key if ASCII passphrase is entered."
			::= { apWlanCryptoTkipEntry 5 }

		
		-- 1.3.6.1.4.1.388.11.3.4.2.4.2.1.6
		apWlanCryptoTkipAllowWpa2Client OBJECT-TYPE
			SYNTAX INTEGER
				{
				enable(1),
				disable(2)
				}
			MAX-ACCESS read-write
			STATUS current
			DESCRIPTION
				"Allows WPA2 TKIP."
			::= { apWlanCryptoTkipEntry 6 }

		
		-- 1.3.6.1.4.1.388.11.3.4.2.4.2.1.7
		apWlanCryptoTkipFastRoamPreAuth OBJECT-TYPE
			SYNTAX INTEGER
				{
				enable(1),
				disable(2)
				}
			MAX-ACCESS read-write
			STATUS current
			DESCRIPTION
				"Allows Pre-Authentication."
			::= { apWlanCryptoTkipEntry 7 }

		
		-- 1.3.6.1.4.1.388.11.3.4.2.4.3
		apWlanCryptoCcmpTable OBJECT-TYPE
			SYNTAX SEQUENCE OF ApWlanCryptoCcmpEntry
			MAX-ACCESS not-accessible
			STATUS current
			DESCRIPTION
				"Table of WPA2-CCMP encryption settings
				for each Security Policy using this method."
			::= { apWlanCrypto 3 }

		
		-- 1.3.6.1.4.1.388.11.3.4.2.4.3.1
		apWlanCryptoCcmpEntry OBJECT-TYPE
			SYNTAX ApWlanCryptoCcmpEntry
			MAX-ACCESS not-accessible
			STATUS current
			DESCRIPTION
				" "
			INDEX { apWlanSecPolicyIndex }
			::= { apWlanCryptoCcmpTable 1 }

		
		ApWlanCryptoCcmpEntry ::=
			SEQUENCE { 
				apWlanCryptoCcmpBcastKeyRotation
					TruthValue,
				apWlanCryptoCcmpKeyRotationInterval
					Unsigned32,
				apWlanCryptoCcmpKeyToUse
					INTEGER,
				apWlanCryptoCcmpPassphrase
					OCTET STRING,
				apWlanCryptoCcmpKey
					OCTET STRING,
				apWlanCryptoCcmpMixedMode
					TruthValue,
				apWlanCryptoCcmpFastRoamPreAuth
					TruthValue
			 }

		-- 1.3.6.1.4.1.388.11.3.4.2.4.3.1.1
		apWlanCryptoCcmpBcastKeyRotation OBJECT-TYPE
			SYNTAX TruthValue
			MAX-ACCESS read-write
			STATUS current
			DESCRIPTION
				"Use broadcast key rotation."
			::= { apWlanCryptoCcmpEntry 1 }

		
		-- 1.3.6.1.4.1.388.11.3.4.2.4.3.1.2
		apWlanCryptoCcmpKeyRotationInterval OBJECT-TYPE
			SYNTAX Unsigned32 (30..604800)
			UNITS "seconds"
			MAX-ACCESS read-write
			STATUS current
			DESCRIPTION
				"Broadcast key rotation, (if enabled), occurs every 
				this many seconds."
			::= { apWlanCryptoCcmpEntry 2 }

		
		-- 1.3.6.1.4.1.388.11.3.4.2.4.3.1.3
		apWlanCryptoCcmpKeyToUse OBJECT-TYPE
			SYNTAX INTEGER
				{
				useAsciiPassphrase(1),
				use256bitKey(2)
				}
			MAX-ACCESS read-write
			STATUS current
			DESCRIPTION
				"Specifies whether to use ASCII Passphrase
				or 256-bit Hex Key."
			::= { apWlanCryptoCcmpEntry 3 }

		
		-- 1.3.6.1.4.1.388.11.3.4.2.4.3.1.4
		apWlanCryptoCcmpPassphrase OBJECT-TYPE
			SYNTAX OCTET STRING (SIZE (8..63))
			MAX-ACCESS read-write
			STATUS current
			DESCRIPTION
				"ASCII Passphrase."
			::= { apWlanCryptoCcmpEntry 4 }

		
		-- 1.3.6.1.4.1.388.11.3.4.2.4.3.1.5
		apWlanCryptoCcmpKey OBJECT-TYPE
			SYNTAX OCTET STRING (SIZE (32))
			MAX-ACCESS read-write
			STATUS current
			DESCRIPTION
				"WPA2/CCMP 256 bit Key.
				No need to enter key if ASCII passphrase is entered."
			::= { apWlanCryptoCcmpEntry 5 }

		
		-- 1.3.6.1.4.1.388.11.3.4.2.4.3.1.6
		apWlanCryptoCcmpMixedMode OBJECT-TYPE
			SYNTAX TruthValue
			MAX-ACCESS read-write
			STATUS current
			DESCRIPTION
				"Allow WPA-TKIP clients"
			::= { apWlanCryptoCcmpEntry 6 }

		
		-- 1.3.6.1.4.1.388.11.3.4.2.4.3.1.7
		apWlanCryptoCcmpFastRoamPreAuth OBJECT-TYPE
			SYNTAX TruthValue
			MAX-ACCESS read-write
			STATUS current
			DESCRIPTION
				"Enabling this option enables a client associated with one 
				Access Point to carry out an 802.1x authentication with 
				another Access Point before it roams over to it. The Access Point 
				will cache the keying information of the client until it 
				roams to the new Access Point. This enables the roaming the 
				client to start sending and receiving data sooner by not 
				having to do 802.1x authentication after it roams.
				
				Note: This option only works when 802.1x authentication is 
				enabled for the WLAN. "
			::= { apWlanCryptoCcmpEntry 7 }

		
		-- 1.3.6.1.4.1.388.11.3.4.2.4.4
		apWlanCryptoKeyguardTable OBJECT-TYPE
			SYNTAX SEQUENCE OF ApWlanCryptoKeyguardEntry
			MAX-ACCESS not-accessible
			STATUS current
			DESCRIPTION
				"Table of KeyGuard-MCM encryption settings
				for each Security Policy using this method."
			::= { apWlanCrypto 4 }

		
		-- 1.3.6.1.4.1.388.11.3.4.2.4.4.1
		apWlanCryptoKeyguardEntry OBJECT-TYPE
			SYNTAX ApWlanCryptoKeyguardEntry
			MAX-ACCESS not-accessible
			STATUS current
			DESCRIPTION
				" "
			INDEX { apWlanSecPolicyIndex }
			::= { apWlanCryptoKeyguardTable 1 }

		
		ApWlanCryptoKeyguardEntry ::=
			SEQUENCE { 
				apWlanCryptoKeyguardPassKey
					OCTET STRING,
				apWlanCryptoKeyguardKey1
					OCTET STRING,
				apWlanCryptoKeyguardKey2
					OCTET STRING,
				apWlanCryptoKeyguardKey3
					OCTET STRING,
				apWlanCryptoKeyguardKey4
					OCTET STRING,
				apWlanCryptoKeyguardKeyToUse
					Integer32,
				apWlanCryptoKeyguardMixedMode
					TruthValue
			 }

		-- 1.3.6.1.4.1.388.11.3.4.2.4.4.1.1
		apWlanCryptoKeyguardPassKey OBJECT-TYPE
			SYNTAX OCTET STRING (SIZE (4..32))
			MAX-ACCESS read-write
			STATUS current
			DESCRIPTION
				"Pass key.
				
				If this value is written, the four KeyguardKey1..4 will
				be overwritten."
			::= { apWlanCryptoKeyguardEntry 1 }

		
		-- 1.3.6.1.4.1.388.11.3.4.2.4.4.1.2
		apWlanCryptoKeyguardKey1 OBJECT-TYPE
			SYNTAX OCTET STRING (SIZE (13))
			MAX-ACCESS read-write
			STATUS current
			DESCRIPTION
				"Key #1."
			::= { apWlanCryptoKeyguardEntry 2 }

		
		-- 1.3.6.1.4.1.388.11.3.4.2.4.4.1.3
		apWlanCryptoKeyguardKey2 OBJECT-TYPE
			SYNTAX OCTET STRING (SIZE (13))
			MAX-ACCESS read-write
			STATUS current
			DESCRIPTION
				"Key #2."
			::= { apWlanCryptoKeyguardEntry 3 }

		
		-- 1.3.6.1.4.1.388.11.3.4.2.4.4.1.4
		apWlanCryptoKeyguardKey3 OBJECT-TYPE
			SYNTAX OCTET STRING (SIZE (13))
			MAX-ACCESS read-write
			STATUS current
			DESCRIPTION
				"Key #3."
			::= { apWlanCryptoKeyguardEntry 4 }

		
		-- 1.3.6.1.4.1.388.11.3.4.2.4.4.1.5
		apWlanCryptoKeyguardKey4 OBJECT-TYPE
			SYNTAX OCTET STRING (SIZE (13))
			MAX-ACCESS read-write
			STATUS current
			DESCRIPTION
				"Key #4."
			::= { apWlanCryptoKeyguardEntry 5 }

		
		-- 1.3.6.1.4.1.388.11.3.4.2.4.4.1.6
		apWlanCryptoKeyguardKeyToUse OBJECT-TYPE
			SYNTAX Integer32 (1..4)
			MAX-ACCESS read-write
			STATUS current
			DESCRIPTION
				"Specifies which WEP key to use."
			::= { apWlanCryptoKeyguardEntry 6 }

		
		-- 1.3.6.1.4.1.388.11.3.4.2.4.4.1.7
		apWlanCryptoKeyguardMixedMode OBJECT-TYPE
			SYNTAX TruthValue
			MAX-ACCESS read-write
			STATUS current
			DESCRIPTION
				"Allow WEP128 clients"
			::= { apWlanCryptoKeyguardEntry 7 }

		
		-- 1.3.6.1.4.1.388.11.3.4.2.5
		apWlanMuAclPolicyTable OBJECT-TYPE
			SYNTAX SEQUENCE OF ApWlanMuAclPolicyEntry
			MAX-ACCESS not-accessible
			STATUS current
			DESCRIPTION
				"Access Control List that can be used by different WLANs."
			::= { apWlan 5 }

		
		-- 1.3.6.1.4.1.388.11.3.4.2.5.1
		apWlanMuAclPolicyEntry OBJECT-TYPE
			SYNTAX ApWlanMuAclPolicyEntry
			MAX-ACCESS not-accessible
			STATUS current
			DESCRIPTION
				" "
			INDEX { apWlanMuAclPolicyIndex }
			::= { apWlanMuAclPolicyTable 1 }

		
		ApWlanMuAclPolicyEntry ::=
			SEQUENCE { 
				apWlanMuAclPolicyIndex
					Integer32,
				apWlanMuAclPolicyName
					DisplayString,
				apWlanMuAclPolicyAccessMode
					INTEGER,
				apWlanMuAclPolicyPointerToWlan
					MultiPointer63,
				apWlanMuAclPolicyRowStatus
					AbbrevRowStatus
			 }

		-- 1.3.6.1.4.1.388.11.3.4.2.5.1.1
		apWlanMuAclPolicyIndex OBJECT-TYPE
			SYNTAX Integer32 (1..16)
			MAX-ACCESS accessible-for-notify
			STATUS current
			DESCRIPTION
				"Simple index."
			::= { apWlanMuAclPolicyEntry 1 }

		
		-- 1.3.6.1.4.1.388.11.3.4.2.5.1.2
		apWlanMuAclPolicyName OBJECT-TYPE
			SYNTAX DisplayString
			MAX-ACCESS read-write
			STATUS current
			DESCRIPTION
				"Name of the Access Control policy."
			::= { apWlanMuAclPolicyEntry 2 }

		
		-- 1.3.6.1.4.1.388.11.3.4.2.5.1.3
		apWlanMuAclPolicyAccessMode OBJECT-TYPE
			SYNTAX INTEGER
				{
				allow(1),
				deny(2)
				}
			MAX-ACCESS read-write
			STATUS current
			DESCRIPTION
				"MUs match this policy can either be Allowed or
				Denied association."
			::= { apWlanMuAclPolicyEntry 3 }

		
		-- 1.3.6.1.4.1.388.11.3.4.2.5.1.4
		apWlanMuAclPolicyPointerToWlan OBJECT-TYPE
			SYNTAX MultiPointer63
			MAX-ACCESS read-only
			STATUS current
			DESCRIPTION
				"Points to the WLAN which have this 
				particular MU Acl policy."
			::= { apWlanMuAclPolicyEntry 4 }

		
		-- 1.3.6.1.4.1.388.11.3.4.2.5.1.5
		apWlanMuAclPolicyRowStatus OBJECT-TYPE
			SYNTAX AbbrevRowStatus
			MAX-ACCESS read-write
			STATUS current
			DESCRIPTION
				"Row Status."
			::= { apWlanMuAclPolicyEntry 5 }

		
		-- 1.3.6.1.4.1.388.11.3.4.2.6
		apWlanMuAclTable OBJECT-TYPE
			SYNTAX SEQUENCE OF ApWlanMuAclEntry
			MAX-ACCESS not-accessible
			STATUS current
			DESCRIPTION
				"Table describing ACLs for allowing or denying,
				(depending on default behavior for the WLAN
				specified in apWlanMuAclPolicyTable), MU association with
				each WLAN."
			::= { apWlan 6 }

		
		-- 1.3.6.1.4.1.388.11.3.4.2.6.1
		apWlanMuAclEntry OBJECT-TYPE
			SYNTAX ApWlanMuAclEntry
			MAX-ACCESS not-accessible
			STATUS current
			DESCRIPTION
				" "
			INDEX { apWlanMuAclIndex }
			::= { apWlanMuAclTable 1 }

		
		ApWlanMuAclEntry ::=
			SEQUENCE { 
				apWlanMuAclIndex
					Integer32,
				apWlanMuAclStartingMac
					PhysAddress,
				apWlanMuAclEndingMac
					PhysAddress,
				apWlanMuAclPointerToAclPolicy
					SinglePointer,
				apWlanMuAclRowStatus
					AbbrevRowStatus
			 }

		-- 1.3.6.1.4.1.388.11.3.4.2.6.1.1
		apWlanMuAclIndex OBJECT-TYPE
			SYNTAX Integer32 (1..127)
			MAX-ACCESS accessible-for-notify
			STATUS current
			DESCRIPTION
				"Simple index."
			::= { apWlanMuAclEntry 1 }

		
		-- 1.3.6.1.4.1.388.11.3.4.2.6.1.2
		apWlanMuAclStartingMac OBJECT-TYPE
			SYNTAX PhysAddress
			MAX-ACCESS read-write
			STATUS current
			DESCRIPTION
				"Starting MAC address in a range of addresses."
			::= { apWlanMuAclEntry 2 }

		
		-- 1.3.6.1.4.1.388.11.3.4.2.6.1.3
		apWlanMuAclEndingMac OBJECT-TYPE
			SYNTAX PhysAddress
			MAX-ACCESS read-write
			STATUS current
			DESCRIPTION
				"Ending MAC address in a range of addresses."
			::= { apWlanMuAclEntry 3 }

		
		-- 1.3.6.1.4.1.388.11.3.4.2.6.1.4
		apWlanMuAclPointerToAclPolicy OBJECT-TYPE
			SYNTAX SinglePointer
			MAX-ACCESS read-write
			STATUS current
			DESCRIPTION
				"Pointer to the ACL policy that this row belongs."
			::= { apWlanMuAclEntry 4 }

		
		-- 1.3.6.1.4.1.388.11.3.4.2.6.1.5
		apWlanMuAclRowStatus OBJECT-TYPE
			SYNTAX AbbrevRowStatus
			MAX-ACCESS read-write
			STATUS current
			DESCRIPTION
				"Row status."
			::= { apWlanMuAclEntry 5 }

		
		-- 1.3.6.1.4.1.388.11.3.4.2.7
		apWlanQosPolicyTable OBJECT-TYPE
			SYNTAX SEQUENCE OF ApWlanQosPolicyEntry
			MAX-ACCESS not-accessible
			STATUS current
			DESCRIPTION
				"QoS Policy that can be used by different WLANs."
			::= { apWlan 7 }

		
		-- 1.3.6.1.4.1.388.11.3.4.2.7.1
		apWlanQosPolicyEntry OBJECT-TYPE
			SYNTAX ApWlanQosPolicyEntry
			MAX-ACCESS not-accessible
			STATUS current
			DESCRIPTION
				" "
			INDEX { apWlanQosPolicyIndex }
			::= { apWlanQosPolicyTable 1 }

		
		ApWlanQosPolicyEntry ::=
			SEQUENCE { 
				apWlanQosPolicyIndex
					Integer32,
				apWlanQosPolicyName
					DisplayString,
				apWlanEnableWMM
					TruthValue,
				apWlanWMMQosParam
					INTEGER,
				apWlanQosPolicyBackgroundCwMin
					Integer32,
				apWlanQosPolicyBackgroundCwMax
					Integer32,
				apWlanQosPolicyBackgroundAifsn
					Integer32,
				apWlanQosPolicyBackgroundTxopsTime
					Integer32,
				apWlanQosPolicyBackgroundTxopsTimeInMS
					Integer32,
				apWlanQosPolicyBestEffortCwMin
					Integer32,
				apWlanQosPolicyBestEffortCwMax
					Integer32,
				apWlanQosPolicyBestEffortAifsn
					Integer32,
				apWlanQosPolicyBestEffortTxopsTime
					Integer32,
				apWlanQosPolicyBestEffortTxopsTimeInMS
					Integer32,
				apWlanQosPolicyVideoCwMin
					Integer32,
				apWlanQosPolicyVideoCwMax
					Integer32,
				apWlanQosPolicyVideoAifsn
					Integer32,
				apWlanQosPolicyVideoTxopsTime
					Integer32,
				apWlanQosPolicyVideoTxopsTimeInMS
					Integer32,
				apWlanQosPolicyVoiceCwMin
					Integer32,
				apWlanQosPolicyVoiceCwMax
					Integer32,
				apWlanQosPolicyVoiceAifsn
					Integer32,
				apWlanQosPolicyVoiceTxopsTime
					Integer32,
				apWlanQosPolicyVoiceTxopsTimeInMS
					Integer32,
				apWlanVoicePrioritization
					TruthValue,
				apWlanMulticastAddr1
					PhysAddress,
				apWlanMulticastAddr2
					PhysAddress,
				apWlanQosPolicyPointerToWlan
					MultiPointer63,
				apWlanQosPolicyRowStatus
					AbbrevRowStatus
			 }

		-- 1.3.6.1.4.1.388.11.3.4.2.7.1.1
		apWlanQosPolicyIndex OBJECT-TYPE
			SYNTAX Integer32 (1..16)
			MAX-ACCESS accessible-for-notify
			STATUS current
			DESCRIPTION
				"Simple index."
			::= { apWlanQosPolicyEntry 1 }

		
		-- 1.3.6.1.4.1.388.11.3.4.2.7.1.2
		apWlanQosPolicyName OBJECT-TYPE
			SYNTAX DisplayString
			MAX-ACCESS read-write
			STATUS current
			DESCRIPTION
				"Name of the QoS policy."
			::= { apWlanQosPolicyEntry 2 }

		
		-- 1.3.6.1.4.1.388.11.3.4.2.7.1.3
		apWlanEnableWMM OBJECT-TYPE
			SYNTAX TruthValue
			MAX-ACCESS read-write
			STATUS current
			DESCRIPTION
				"Enable WiFi Multimedia Extension support."
			::= { apWlanQosPolicyEntry 3 }

		
		-- 1.3.6.1.4.1.388.11.3.4.2.7.1.4
		apWlanWMMQosParam OBJECT-TYPE
			SYNTAX INTEGER
				{
				manual(1),
				wifi11agn(2),
				wifi11b(3),
				default11agn(4),
				default11b(5),
				voice11agn(6),
				voice11b(7)
				}
			MAX-ACCESS read-write
			STATUS current
			DESCRIPTION
				"Pre-Programmed WMM QOS Parameters.
				manual - Modify parameters
				wifi11agn - WiFi 11a/11g/11n defaults
				wifi11b  - WiFi 11b defaults
				default11agn - Symbol 11a/11g/11n defaults
				default11b  - Symbol 11b defaults
				voice11agn - Symbol 11a/11g/11n voice params
				voice11b  - Symbol 11b voice params"
			::= { apWlanQosPolicyEntry 4 }

		
		-- 1.3.6.1.4.1.388.11.3.4.2.7.1.5
		apWlanQosPolicyBackgroundCwMin OBJECT-TYPE
			SYNTAX Integer32
			MAX-ACCESS read-write
			STATUS current
			DESCRIPTION
				"This QoS parameter is to be used by the MU for the
				Background access category."
			::= { apWlanQosPolicyEntry 5 }

		
		-- 1.3.6.1.4.1.388.11.3.4.2.7.1.6
		apWlanQosPolicyBackgroundCwMax OBJECT-TYPE
			SYNTAX Integer32
			MAX-ACCESS read-write
			STATUS current
			DESCRIPTION
				"This QoS parameter is to be used by the MU for the
				Background access category."
			::= { apWlanQosPolicyEntry 6 }

		
		-- 1.3.6.1.4.1.388.11.3.4.2.7.1.7
		apWlanQosPolicyBackgroundAifsn OBJECT-TYPE
			SYNTAX Integer32
			MAX-ACCESS read-write
			STATUS current
			DESCRIPTION
				"This QoS parameter is to be used by the MU for the
				Background access category."
			::= { apWlanQosPolicyEntry 7 }

		
		-- 1.3.6.1.4.1.388.11.3.4.2.7.1.8
		apWlanQosPolicyBackgroundTxopsTime OBJECT-TYPE
			SYNTAX Integer32
			MAX-ACCESS read-write
			STATUS current
			DESCRIPTION
				"This QoS parameter is to be used by the MU for the
				Background access category."
			::= { apWlanQosPolicyEntry 8 }

		
		-- 1.3.6.1.4.1.388.11.3.4.2.7.1.9
		apWlanQosPolicyBackgroundTxopsTimeInMS OBJECT-TYPE
			SYNTAX Integer32
			MAX-ACCESS read-only
			STATUS current
			DESCRIPTION
				"This QoS parameter is to be used by the MU for the
				Background access category."
			::= { apWlanQosPolicyEntry 9 }

		
		-- 1.3.6.1.4.1.388.11.3.4.2.7.1.10
		apWlanQosPolicyBestEffortCwMin OBJECT-TYPE
			SYNTAX Integer32
			MAX-ACCESS read-write
			STATUS current
			DESCRIPTION
				"This QoS parameter is to be used by the MU for the
				Best Effort access category."
			::= { apWlanQosPolicyEntry 10 }

		
		-- 1.3.6.1.4.1.388.11.3.4.2.7.1.11
		apWlanQosPolicyBestEffortCwMax OBJECT-TYPE
			SYNTAX Integer32
			MAX-ACCESS read-write
			STATUS current
			DESCRIPTION
				"This QoS parameter is to be used by the MU for the
				Best Effort access category."
			::= { apWlanQosPolicyEntry 11 }

		
		-- 1.3.6.1.4.1.388.11.3.4.2.7.1.12
		apWlanQosPolicyBestEffortAifsn OBJECT-TYPE
			SYNTAX Integer32
			MAX-ACCESS read-write
			STATUS current
			DESCRIPTION
				"This QoS parameter is to be used by the MU for the
				Best Effort access category."
			::= { apWlanQosPolicyEntry 12 }

		
		-- 1.3.6.1.4.1.388.11.3.4.2.7.1.13
		apWlanQosPolicyBestEffortTxopsTime OBJECT-TYPE
			SYNTAX Integer32
			MAX-ACCESS read-write
			STATUS current
			DESCRIPTION
				"This QoS parameter is to be used by the MU for the
				Best Effort access category."
			::= { apWlanQosPolicyEntry 13 }

		
		-- 1.3.6.1.4.1.388.11.3.4.2.7.1.14
		apWlanQosPolicyBestEffortTxopsTimeInMS OBJECT-TYPE
			SYNTAX Integer32
			MAX-ACCESS read-only
			STATUS current
			DESCRIPTION
				"This QoS parameter is to be used by the MU for the
				Best Effort access category."
			::= { apWlanQosPolicyEntry 14 }

		
		-- 1.3.6.1.4.1.388.11.3.4.2.7.1.15
		apWlanQosPolicyVideoCwMin OBJECT-TYPE
			SYNTAX Integer32
			MAX-ACCESS read-write
			STATUS current
			DESCRIPTION
				"This QoS parameter is to be used by the MU for the
				Video access category."
			::= { apWlanQosPolicyEntry 15 }

		
		-- 1.3.6.1.4.1.388.11.3.4.2.7.1.16
		apWlanQosPolicyVideoCwMax OBJECT-TYPE
			SYNTAX Integer32
			MAX-ACCESS read-write
			STATUS current
			DESCRIPTION
				"This QoS parameter is to be used by the MU for the
				Video access category."
			::= { apWlanQosPolicyEntry 16 }

		
		-- 1.3.6.1.4.1.388.11.3.4.2.7.1.17
		apWlanQosPolicyVideoAifsn OBJECT-TYPE
			SYNTAX Integer32
			MAX-ACCESS read-write
			STATUS current
			DESCRIPTION
				"This QoS parameter is to be used by the MU for the
				Video access category."
			::= { apWlanQosPolicyEntry 17 }

		
		-- 1.3.6.1.4.1.388.11.3.4.2.7.1.18
		apWlanQosPolicyVideoTxopsTime OBJECT-TYPE
			SYNTAX Integer32
			MAX-ACCESS read-write
			STATUS current
			DESCRIPTION
				"This QoS parameter is to be used by the MU for the
				Video access category."
			::= { apWlanQosPolicyEntry 18 }

		
		-- 1.3.6.1.4.1.388.11.3.4.2.7.1.19
		apWlanQosPolicyVideoTxopsTimeInMS OBJECT-TYPE
			SYNTAX Integer32
			MAX-ACCESS read-only
			STATUS current
			DESCRIPTION
				"This QoS parameter is to be used by the MU for the
				Video access category."
			::= { apWlanQosPolicyEntry 19 }

		
		-- 1.3.6.1.4.1.388.11.3.4.2.7.1.20
		apWlanQosPolicyVoiceCwMin OBJECT-TYPE
			SYNTAX Integer32
			MAX-ACCESS read-write
			STATUS current
			DESCRIPTION
				"This QoS parameter is to be used by the MU for the
				Voice access category."
			::= { apWlanQosPolicyEntry 20 }

		
		-- 1.3.6.1.4.1.388.11.3.4.2.7.1.21
		apWlanQosPolicyVoiceCwMax OBJECT-TYPE
			SYNTAX Integer32
			MAX-ACCESS read-write
			STATUS current
			DESCRIPTION
				"This QoS parameter is to be used by the MU for the
				Voice access category."
			::= { apWlanQosPolicyEntry 21 }

		
		-- 1.3.6.1.4.1.388.11.3.4.2.7.1.22
		apWlanQosPolicyVoiceAifsn OBJECT-TYPE
			SYNTAX Integer32
			MAX-ACCESS read-write
			STATUS current
			DESCRIPTION
				"This QoS parameter is to be used by the MU for the
				Voice access category."
			::= { apWlanQosPolicyEntry 22 }

		
		-- 1.3.6.1.4.1.388.11.3.4.2.7.1.23
		apWlanQosPolicyVoiceTxopsTime OBJECT-TYPE
			SYNTAX Integer32
			MAX-ACCESS read-write
			STATUS current
			DESCRIPTION
				"This QoS parameter is to be used by the MU for the
				Voice access category."
			::= { apWlanQosPolicyEntry 23 }

		
		-- 1.3.6.1.4.1.388.11.3.4.2.7.1.24
		apWlanQosPolicyVoiceTxopsTimeInMS OBJECT-TYPE
			SYNTAX Integer32
			MAX-ACCESS read-only
			STATUS current
			DESCRIPTION
				"This QoS parameter is to be used by the MU for the
				Voice access category."
			::= { apWlanQosPolicyEntry 24 }

		
		-- 1.3.6.1.4.1.388.11.3.4.2.7.1.25
		apWlanVoicePrioritization OBJECT-TYPE
			SYNTAX TruthValue
			MAX-ACCESS read-write
			STATUS current
			DESCRIPTION
				"Support legacy voice prioritization."
			::= { apWlanQosPolicyEntry 25 }

		
		-- 1.3.6.1.4.1.388.11.3.4.2.7.1.26
		apWlanMulticastAddr1 OBJECT-TYPE
			SYNTAX PhysAddress
			MAX-ACCESS read-write
			STATUS current
			DESCRIPTION
				"Multicast address 1."
			::= { apWlanQosPolicyEntry 26 }

		
		-- 1.3.6.1.4.1.388.11.3.4.2.7.1.27
		apWlanMulticastAddr2 OBJECT-TYPE
			SYNTAX PhysAddress
			MAX-ACCESS read-write
			STATUS current
			DESCRIPTION
				"Multicast address 2."
			::= { apWlanQosPolicyEntry 27 }

		
		-- 1.3.6.1.4.1.388.11.3.4.2.7.1.28
		apWlanQosPolicyPointerToWlan OBJECT-TYPE
			SYNTAX MultiPointer63
			MAX-ACCESS read-only
			STATUS current
			DESCRIPTION
				"Points to the WLAN which have this 
				particular QOS policy."
			::= { apWlanQosPolicyEntry 28 }

		
		-- 1.3.6.1.4.1.388.11.3.4.2.7.1.29
		apWlanQosPolicyRowStatus OBJECT-TYPE
			SYNTAX AbbrevRowStatus
			MAX-ACCESS read-write
			STATUS current
			DESCRIPTION
				"Row Status."
			::= { apWlanQosPolicyEntry 29 }

		
		-- 1.3.6.1.4.1.388.11.3.4.2.8
		apWlanBwShareModeTable OBJECT-TYPE
			SYNTAX SEQUENCE OF ApWlanBwShareModeEntry
			MAX-ACCESS not-accessible
			STATUS current
			DESCRIPTION
				"Description."
			::= { apWlan 8 }

		
		-- 1.3.6.1.4.1.388.11.3.4.2.8.1
		apWlanBwShareModeEntry OBJECT-TYPE
			SYNTAX ApWlanBwShareModeEntry
			MAX-ACCESS not-accessible
			STATUS current
			DESCRIPTION
				"Description."
			INDEX { apRadioSettingsIndex }
			::= { apWlanBwShareModeTable 1 }

		
		ApWlanBwShareModeEntry ::=
			SEQUENCE { 
				apWlanBwShareMode
					INTEGER
			 }

		-- 1.3.6.1.4.1.388.11.3.4.2.8.1.1
		apWlanBwShareMode OBJECT-TYPE
			SYNTAX INTEGER
				{
				firstInFirstOut(0),
				roundRobin(1),
				weightedRoundRobin(2)
				}
			MAX-ACCESS read-write
			STATUS current
			DESCRIPTION
				"This variable configures the manner in which bandwidth is shared among the WLANs.  Only in mode 'weightedRoundRobin' are the apRadioWlanWeight values for each Radio and WLAN used."
			::= { apWlanBwShareModeEntry 1 }

		
		-- 1.3.6.1.4.1.388.11.3.4.3
		apHotSpot OBJECT IDENTIFIER ::= { apRf 3 }

		
		-- 1.3.6.1.4.1.388.11.3.4.3.2
		apHotSpotWhiteListTable OBJECT-TYPE
			SYNTAX SEQUENCE OF ApHotSpotWhiteListEntry
			MAX-ACCESS not-accessible
			STATUS current
			DESCRIPTION
				"Table of White List entires for HotSpot for the WLANs."
			::= { apHotSpot 2 }

		
		-- 1.3.6.1.4.1.388.11.3.4.3.2.1
		apHotSpotWhiteListEntry OBJECT-TYPE
			SYNTAX ApHotSpotWhiteListEntry
			MAX-ACCESS not-accessible
			STATUS current
			DESCRIPTION
				" "
			INDEX { apWlanIndex, apHotSpotWhiteListIndex }
			::= { apHotSpotWhiteListTable 1 }

		
		ApHotSpotWhiteListEntry ::=
			SEQUENCE { 
				apHotSpotWhiteListIndex
					Integer32,
				apHotSpotWhiteListWalledGardenIp
					IpAddress,
				apHotSpotWhiteListRowStatus
					AbbrevRowStatus
			 }

		-- 1.3.6.1.4.1.388.11.3.4.3.2.1.1
		apHotSpotWhiteListIndex OBJECT-TYPE
			SYNTAX Integer32 (1..10)
			MAX-ACCESS accessible-for-notify
			STATUS current
			DESCRIPTION
				"Simple Index 1...10"
			::= { apHotSpotWhiteListEntry 1 }

		
		-- 1.3.6.1.4.1.388.11.3.4.3.2.1.2
		apHotSpotWhiteListWalledGardenIp OBJECT-TYPE
			SYNTAX IpAddress
			MAX-ACCESS read-write
			STATUS current
			DESCRIPTION
				"IP Address of White List entries"
			::= { apHotSpotWhiteListEntry 2 }

		
		-- 1.3.6.1.4.1.388.11.3.4.3.2.1.3
		apHotSpotWhiteListRowStatus OBJECT-TYPE
			SYNTAX AbbrevRowStatus
			MAX-ACCESS read-write
			STATUS current
			DESCRIPTION
				"Value to control row creation/deletion."
			::= { apHotSpotWhiteListEntry 3 }

		
		-- 1.3.6.1.4.1.388.11.3.4.3.1
		apHotSpotTable OBJECT-TYPE
			SYNTAX SEQUENCE OF ApHotSpotEntry
			MAX-ACCESS not-accessible
			STATUS current
			DESCRIPTION
				"Table for Hotspot configuration."
			::= { apHotSpot 1 }

		
		-- 1.3.6.1.4.1.388.11.3.4.3.1.1
		apHotSpotEntry OBJECT-TYPE
			SYNTAX ApHotSpotEntry
			MAX-ACCESS not-accessible
			STATUS current
			DESCRIPTION
				" "
			INDEX { apWlanIndex }
			::= { apHotSpotTable 1 }

		
		ApHotSpotEntry ::=
			SEQUENCE { 
				apHotSpotDefaultFileMode
					INTEGER,
				apHotSpotExternalLoginPageUrl
					DisplayString,
				apHotSpotExternalWelomePageUrl
					DisplayString,
				apHotSpotExternalFailPageUrl
					DisplayString,
				apHotSpotPriRadiusServerIp
					IpAddress,
				apHotSpotPriRadiusPort
					Integer32,
				apHotSpotPriRadiusSecret
					Password,
				apHotSpotSecRadiusServerIp
					IpAddress,
				apHotSpotSecRadiusPort
					Integer32,
				apHotSpotSecRadiusSecret
					Password,
				apHotSpotRadiusAcctMode
					TruthValue,
				apHotSpotRadiusAcctServerIp
					IpAddress,
				apHotSpotRadiusAcctPort
					Integer32,
				apHotSpotRadiusAcctSecret
					Password,
				apHotSpotRadiusAcctTimeout
					Integer32,
				apHotSpotRadiusAcctRetryCount
					Integer32,
				apHotSpotRadiusSessMode
					TruthValue,
				apHotSpotRadiusSessTimeout
					Integer32
			 }

		-- 1.3.6.1.4.1.388.11.3.4.3.1.1.1
		apHotSpotDefaultFileMode OBJECT-TYPE
			SYNTAX INTEGER
				{
				default(1),
				externalURL(2)
				}
			MAX-ACCESS read-write
			STATUS current
			DESCRIPTION
				"Default File Mode for Login, Welcome and Fail Pages."
			::= { apHotSpotEntry 1 }

		
		-- 1.3.6.1.4.1.388.11.3.4.3.1.1.2
		apHotSpotExternalLoginPageUrl OBJECT-TYPE
			SYNTAX DisplayString
			MAX-ACCESS read-write
			STATUS current
			DESCRIPTION
				"Login Page URL on external server."
			::= { apHotSpotEntry 2 }

		
		-- 1.3.6.1.4.1.388.11.3.4.3.1.1.3
		apHotSpotExternalWelomePageUrl OBJECT-TYPE
			SYNTAX DisplayString
			MAX-ACCESS read-write
			STATUS current
			DESCRIPTION
				"Welcome Page URL on external server."
			::= { apHotSpotEntry 3 }

		
		-- 1.3.6.1.4.1.388.11.3.4.3.1.1.4
		apHotSpotExternalFailPageUrl OBJECT-TYPE
			SYNTAX DisplayString
			MAX-ACCESS read-write
			STATUS current
			DESCRIPTION
				"Fail Page URL on external server."
			::= { apHotSpotEntry 4 }

		
		-- 1.3.6.1.4.1.388.11.3.4.3.1.1.5
		apHotSpotPriRadiusServerIp OBJECT-TYPE
			SYNTAX IpAddress
			MAX-ACCESS read-write
			STATUS current
			DESCRIPTION
				"IP Address of Primary Radius Server.
				Use 127.0.0.1 to use the Local Radius Server on the AP5131."
			::= { apHotSpotEntry 5 }

		
		-- 1.3.6.1.4.1.388.11.3.4.3.1.1.6
		apHotSpotPriRadiusPort OBJECT-TYPE
			SYNTAX Integer32
			MAX-ACCESS read-write
			STATUS current
			DESCRIPTION
				"Port for Primary Radius Server."
			::= { apHotSpotEntry 6 }

		
		-- 1.3.6.1.4.1.388.11.3.4.3.1.1.7
		apHotSpotPriRadiusSecret OBJECT-TYPE
			SYNTAX Password
			MAX-ACCESS read-write
			STATUS current
			DESCRIPTION
				"Shared Secret for Primary Radius Server."
			::= { apHotSpotEntry 7 }

		
		-- 1.3.6.1.4.1.388.11.3.4.3.1.1.8
		apHotSpotSecRadiusServerIp OBJECT-TYPE
			SYNTAX IpAddress
			MAX-ACCESS read-write
			STATUS current
			DESCRIPTION
				"IP Address of Secondary Radius Server.
				Use 127.0.0.1 to use the Local Radius Server on the AP5131."
			::= { apHotSpotEntry 8 }

		
		-- 1.3.6.1.4.1.388.11.3.4.3.1.1.9
		apHotSpotSecRadiusPort OBJECT-TYPE
			SYNTAX Integer32
			MAX-ACCESS read-write
			STATUS current
			DESCRIPTION
				"Port for Secondary Radius Server."
			::= { apHotSpotEntry 9 }

		
		-- 1.3.6.1.4.1.388.11.3.4.3.1.1.10
		apHotSpotSecRadiusSecret OBJECT-TYPE
			SYNTAX Password
			MAX-ACCESS read-write
			STATUS current
			DESCRIPTION
				"Shared Secret for Secondary Radius Server."
			::= { apHotSpotEntry 10 }

		
		-- 1.3.6.1.4.1.388.11.3.4.3.1.1.11
		apHotSpotRadiusAcctMode OBJECT-TYPE
			SYNTAX TruthValue
			MAX-ACCESS read-write
			STATUS current
			DESCRIPTION
				"Radius Accounting Mode."
			::= { apHotSpotEntry 11 }

		
		-- 1.3.6.1.4.1.388.11.3.4.3.1.1.12
		apHotSpotRadiusAcctServerIp OBJECT-TYPE
			SYNTAX IpAddress
			MAX-ACCESS read-write
			STATUS current
			DESCRIPTION
				"External Accounting Radius Server."
			::= { apHotSpotEntry 12 }

		
		-- 1.3.6.1.4.1.388.11.3.4.3.1.1.13
		apHotSpotRadiusAcctPort OBJECT-TYPE
			SYNTAX Integer32
			MAX-ACCESS read-write
			STATUS current
			DESCRIPTION
				"Port for External Accounting Radius Server."
			::= { apHotSpotEntry 13 }

		
		-- 1.3.6.1.4.1.388.11.3.4.3.1.1.14
		apHotSpotRadiusAcctSecret OBJECT-TYPE
			SYNTAX Password
			MAX-ACCESS read-write
			STATUS current
			DESCRIPTION
				"Shared Secret for External Accounting Radius Server."
			::= { apHotSpotEntry 14 }

		
		-- 1.3.6.1.4.1.388.11.3.4.3.1.1.15
		apHotSpotRadiusAcctTimeout OBJECT-TYPE
			SYNTAX Integer32 (1..255)
			MAX-ACCESS read-write
			STATUS current
			DESCRIPTION
				"Radius Accounting Timeout value."
			::= { apHotSpotEntry 15 }

		
		-- 1.3.6.1.4.1.388.11.3.4.3.1.1.16
		apHotSpotRadiusAcctRetryCount OBJECT-TYPE
			SYNTAX Integer32 (1..10)
			MAX-ACCESS read-write
			STATUS current
			DESCRIPTION
				"Radius Accounting Retry Count value."
			::= { apHotSpotEntry 16 }

		
		-- 1.3.6.1.4.1.388.11.3.4.3.1.1.17
		apHotSpotRadiusSessMode OBJECT-TYPE
			SYNTAX TruthValue
			MAX-ACCESS read-write
			STATUS current
			DESCRIPTION
				"Radius Session Timeout Mode (Applicable only for Internal Radius Server)"
			::= { apHotSpotEntry 17 }

		
		-- 1.3.6.1.4.1.388.11.3.4.3.1.1.18
		apHotSpotRadiusSessTimeout OBJECT-TYPE
			SYNTAX Integer32
			MAX-ACCESS read-write
			STATUS current
			DESCRIPTION
				"Radius Session Timeout (Applicable only for Internal Radius Server)"
			::= { apHotSpotEntry 18 }

		
		-- 1.3.6.1.4.1.388.11.3.4.4
		apMus OBJECT IDENTIFIER ::= { apRf 4 }

		
-- This group describes MU Locationing settings and table.
		-- 1.3.6.1.4.1.388.11.3.4.4.1
		apMuLocationing OBJECT IDENTIFIER ::= { apMus 1 }

		
		-- 1.3.6.1.4.1.388.11.3.4.4.1.1
		apMuLocationingEnable OBJECT-TYPE
			SYNTAX TruthValue
			MAX-ACCESS read-write
			STATUS current
			DESCRIPTION
				"Enable/disable MU Locationing feature. 
				"
			::= { apMuLocationing 1 }

		
		-- 1.3.6.1.4.1.388.11.3.4.4.1.2
		apMuLocationingClear OBJECT-TYPE
			SYNTAX DoActionNow
			MAX-ACCESS read-write
			STATUS current
			DESCRIPTION
				"Setting this value to TRUE clears all apMuLocationingTable entries.
				
				Any probe request heard after that event will be treated as newly heard."
			::= { apMuLocationing 2 }

		
		-- 1.3.6.1.4.1.388.11.3.4.4.1.3
		apMuLocationingMaxMus OBJECT-TYPE
			SYNTAX Integer32 (20..200)
			MAX-ACCESS read-write
			STATUS current
			DESCRIPTION
				"Maximum number of MU's to be reported in the apMuLocationingTable.
				The minimum number is 20 and maximum 200. "
			::= { apMuLocationing 3 }

		
		-- 1.3.6.1.4.1.388.11.3.4.4.1.4
		apMuLocationingTable OBJECT-TYPE
			SYNTAX SEQUENCE OF ApMuLocationingEntry
			MAX-ACCESS not-accessible
			STATUS current
			DESCRIPTION
				"The switch shall store the information received 
				in the probe request messages in this table. 
				"
			::= { apMuLocationing 4 }

		
		-- 1.3.6.1.4.1.388.11.3.4.4.1.4.1
		apMuLocationingEntry OBJECT-TYPE
			SYNTAX ApMuLocationingEntry
			MAX-ACCESS not-accessible
			STATUS current
			DESCRIPTION
				"Description."
			INDEX { apMuLocationingIndex }
			::= { apMuLocationingTable 1 }

		
		ApMuLocationingEntry ::=
			SEQUENCE { 
				apMuLocationingIndex
					Integer32,
				apMuLocationingMuMac
					PhysAddress,
				apMuLocationingPortalMac
					PhysAddress,
				apMuLocationingSignalStrength
					Integer32,
				apMuLocationingHeardChannel
					Integer32,
				apMuLocationingHeardTime
					TimeTicks
			 }

		-- 1.3.6.1.4.1.388.11.3.4.4.1.4.1.1
		apMuLocationingIndex OBJECT-TYPE
			SYNTAX Integer32 (1..2400)
			MAX-ACCESS accessible-for-notify
			STATUS current
			DESCRIPTION
				"Simple index."
			::= { apMuLocationingEntry 1 }

		
		-- 1.3.6.1.4.1.388.11.3.4.4.1.4.1.2
		apMuLocationingMuMac OBJECT-TYPE
			SYNTAX PhysAddress
			MAX-ACCESS read-only
			STATUS current
			DESCRIPTION
				"MAC address of the MU."
			::= { apMuLocationingEntry 2 }

		
		-- 1.3.6.1.4.1.388.11.3.4.4.1.4.1.3
		apMuLocationingPortalMac OBJECT-TYPE
			SYNTAX PhysAddress
			MAX-ACCESS read-only
			STATUS current
			DESCRIPTION
				"MAC address of the Portal."
			::= { apMuLocationingEntry 3 }

		
		-- 1.3.6.1.4.1.388.11.3.4.4.1.4.1.4
		apMuLocationingSignalStrength OBJECT-TYPE
			SYNTAX Integer32
			UNITS "dBm"
			MAX-ACCESS read-only
			STATUS current
			DESCRIPTION
				"Received Signal Strength in dBm by the Heard Portal."
			::= { apMuLocationingEntry 4 }

		
		-- 1.3.6.1.4.1.388.11.3.4.4.1.4.1.5
		apMuLocationingHeardChannel OBJECT-TYPE
			SYNTAX Integer32
			MAX-ACCESS read-only
			STATUS current
			DESCRIPTION
				"Describes on which channel probe is heard."
			::= { apMuLocationingEntry 5 }

		
		-- 1.3.6.1.4.1.388.11.3.4.4.1.4.1.6
		apMuLocationingHeardTime OBJECT-TYPE
			SYNTAX TimeTicks
			MAX-ACCESS read-only
			STATUS current
			DESCRIPTION
				"Describes the time when this probe is heard."
			::= { apMuLocationingEntry 6 }

		
		-- 1.3.6.1.4.1.388.11.3.4.4.1.5
		apMuLocationingAddEntryToTable OBJECT-TYPE
			SYNTAX SEQUENCE OF ApMuLocationingAddEntryToEntry
			MAX-ACCESS not-accessible
			STATUS current
			DESCRIPTION
				"The switch shall provide option to append information 
				to apMuLocationingTable."
			::= { apMuLocationing 5 }

		
		-- 1.3.6.1.4.1.388.11.3.4.4.1.5.1
		apMuLocationingAddEntryToEntry OBJECT-TYPE
			SYNTAX ApMuLocationingAddEntryToEntry
			MAX-ACCESS not-accessible
			STATUS current
			DESCRIPTION
				"Description."
			INDEX { apMuLocationingIndex }
			::= { apMuLocationingAddEntryToTable 1 }

		
		ApMuLocationingAddEntryToEntry ::=
			SEQUENCE { 
				apMuLocationingAddMuMac
					PhysAddress,
				apMuLocationingAddPortalMac
					PhysAddress,
				apMuLocationingAddSignalStrength
					Integer32,
				apMuLocationingAddHeardChannel
					Integer32,
				apMuLocationingAddHeardTime
					TimeTicks
			 }

		-- 1.3.6.1.4.1.388.11.3.4.4.1.5.1.1
		apMuLocationingAddMuMac OBJECT-TYPE
			SYNTAX PhysAddress
			MAX-ACCESS read-write
			STATUS current
			DESCRIPTION
				"MAC address of the MU."
			::= { apMuLocationingAddEntryToEntry 1 }

		
		-- 1.3.6.1.4.1.388.11.3.4.4.1.5.1.2
		apMuLocationingAddPortalMac OBJECT-TYPE
			SYNTAX PhysAddress
			MAX-ACCESS read-write
			STATUS current
			DESCRIPTION
				"MAC address of the Portal."
			::= { apMuLocationingAddEntryToEntry 2 }

		
		-- 1.3.6.1.4.1.388.11.3.4.4.1.5.1.3
		apMuLocationingAddSignalStrength OBJECT-TYPE
			SYNTAX Integer32
			UNITS "dBm"
			MAX-ACCESS read-write
			STATUS current
			DESCRIPTION
				"Received Signal Strength in dBm by the Heard Portal."
			::= { apMuLocationingAddEntryToEntry 3 }

		
		-- 1.3.6.1.4.1.388.11.3.4.4.1.5.1.4
		apMuLocationingAddHeardChannel OBJECT-TYPE
			SYNTAX Integer32
			MAX-ACCESS read-write
			STATUS current
			DESCRIPTION
				"Describes on which channel probe is heard."
			::= { apMuLocationingAddEntryToEntry 4 }

		
		-- 1.3.6.1.4.1.388.11.3.4.4.1.5.1.5
		apMuLocationingAddHeardTime OBJECT-TYPE
			SYNTAX TimeTicks
			MAX-ACCESS read-write
			STATUS current
			DESCRIPTION
				"Describes the time when this probe is heard."
			::= { apMuLocationingAddEntryToEntry 5 }

		
		-- 1.3.6.1.4.1.388.11.3.4.5
		apIpFilter OBJECT IDENTIFIER ::= { apRf 5 }

		
		-- 1.3.6.1.4.1.388.11.3.4.5.1
		apIpFilterPolicyTable OBJECT-TYPE
			SYNTAX SEQUENCE OF ApIpFilterPolicyEntry
			MAX-ACCESS not-accessible
			STATUS current
			DESCRIPTION
				"Table of Global IP Filter Policies"
			::= { apIpFilter 1 }

		
		-- 1.3.6.1.4.1.388.11.3.4.5.1.1
		apIpFilterPolicyEntry OBJECT-TYPE
			SYNTAX ApIpFilterPolicyEntry
			MAX-ACCESS not-accessible
			STATUS current
			DESCRIPTION
				" "
			INDEX { apIpFilterPolicyIndex }
			::= { apIpFilterPolicyTable 1 }

		
		ApIpFilterPolicyEntry ::=
			SEQUENCE { 
				apIpFilterPolicyIndex
					Integer32,
				apIpFilterPolicyName
					DisplayString,
				apIpFilterPolicyProtocol
					INTEGER,
				apIpFilterPolicyStartPort
					Integer32,
				apIpFilterPolicyEndPort
					Integer32,
				apIpFilterPolicySrcStartIp
					IpAddress,
				apIpFilterPolicySrcEndIp
					IpAddress,
				apIpFilterPolicyDestStartIp
					IpAddress,
				apIpFilterPolicyDestEndIp
					IpAddress,
				apIpFilterPolicyUseStatus
					DisplayString,
				apIpFilterPolicyRowStatus
					AbbrevRowStatus,
                apIpFilterPolicySrcStartPort
                     Integer32,
                 apIpFilterPolicySrcEndPort
                     Integer32
    		 }

		-- 1.3.6.1.4.1.388.11.3.4.5.1.1.1
		apIpFilterPolicyIndex OBJECT-TYPE
			SYNTAX Integer32 (1..100)
			MAX-ACCESS accessible-for-notify
			STATUS current
			DESCRIPTION
				"Simple Index"
			::= { apIpFilterPolicyEntry 1 }

		
		-- 1.3.6.1.4.1.388.11.3.4.5.1.1.2
		apIpFilterPolicyName OBJECT-TYPE
			SYNTAX DisplayString
			MAX-ACCESS read-write
			STATUS current
			DESCRIPTION
				"IP Filter Policy Name.
				It has to be unique for every policy."
			::= { apIpFilterPolicyEntry 2 }

		
		-- 1.3.6.1.4.1.388.11.3.4.5.1.1.3
		apIpFilterPolicyProtocol OBJECT-TYPE
			SYNTAX INTEGER
				{
				icmp(1),
				igmp(2),
				ipip(4),
				tcp(6),
				egp(8),
				pup(12),
				udp(17),
				idp(22),
				ipv6(41),
				rsvp(46),
				gre(47),
				esp(50),
				ah(51),
				pim(103),
				comp(108),
				rawip(255),
				all(256)
				}
			MAX-ACCESS read-write
			STATUS current
			DESCRIPTION
				"IP Filter Policy Protocol Number."
			::= { apIpFilterPolicyEntry 3 }

		
		-- 1.3.6.1.4.1.388.11.3.4.5.1.1.4
		apIpFilterPolicyStartPort OBJECT-TYPE
			SYNTAX Integer32 (0..65535)
			MAX-ACCESS read-write
			STATUS current
			DESCRIPTION
				"IP Filter Policy Starting Port Number"
			::= { apIpFilterPolicyEntry 4 }

		
		-- 1.3.6.1.4.1.388.11.3.4.5.1.1.5
		apIpFilterPolicyEndPort OBJECT-TYPE
			SYNTAX Integer32 (0..65535)
			MAX-ACCESS read-write
			STATUS current
			DESCRIPTION
				"IP Filter Policy Ending Port Number"
			::= { apIpFilterPolicyEntry 5 }

		
		-- 1.3.6.1.4.1.388.11.3.4.5.1.1.6
		apIpFilterPolicySrcStartIp OBJECT-TYPE
			SYNTAX IpAddress
			MAX-ACCESS read-write
			STATUS current
			DESCRIPTION
				"IP Filter Policy Source Start IP Address."
			::= { apIpFilterPolicyEntry 6 }

		
		-- 1.3.6.1.4.1.388.11.3.4.5.1.1.7
		apIpFilterPolicySrcEndIp OBJECT-TYPE
			SYNTAX IpAddress
			MAX-ACCESS read-write
			STATUS current
			DESCRIPTION
				"IP Filter Policy Source End IP Address."
			::= { apIpFilterPolicyEntry 7 }

		
		-- 1.3.6.1.4.1.388.11.3.4.5.1.1.8
		apIpFilterPolicyDestStartIp OBJECT-TYPE
			SYNTAX IpAddress
			MAX-ACCESS read-write
			STATUS current
			DESCRIPTION
				"IP Filter Policy Dest Start IP Address."
			::= { apIpFilterPolicyEntry 8 }

		
		-- 1.3.6.1.4.1.388.11.3.4.5.1.1.9
		apIpFilterPolicyDestEndIp OBJECT-TYPE
			SYNTAX IpAddress
			MAX-ACCESS read-write
			STATUS current
			DESCRIPTION
				"IP Filter Policy Dest End IP Address."
			::= { apIpFilterPolicyEntry 9 }

		
		-- 1.3.6.1.4.1.388.11.3.4.5.1.1.10
		apIpFilterPolicyUseStatus OBJECT-TYPE
			SYNTAX DisplayString
			MAX-ACCESS read-only
			STATUS current
			DESCRIPTION
				"Description.Indicates whether filter is used by any of the
				    WLAN IP Filter Tables or the TRUNK IP Filter Table.
				    If got used then displays YES otherwise NO."
			::= { apIpFilterPolicyEntry 10 }

		
		-- 1.3.6.1.4.1.388.11.3.4.5.1.1.11
		apIpFilterPolicyRowStatus OBJECT-TYPE
			SYNTAX AbbrevRowStatus
			MAX-ACCESS read-write
			STATUS current
			DESCRIPTION
				"Row Status for creation and deletion of policies."
			::= { apIpFilterPolicyEntry 11 }

       -- 1.3.6.1.4.1.388.11.3.4.5.1.1.12
       apIpFilterPolicySrcStartPort OBJECT-TYPE
             SYNTAX Integer32 (0..65535)
             MAX-ACCESS read-write
             STATUS current
             DESCRIPTION
                 "IP Filter Policy Source Starting Port Number"
             ::= { apIpFilterPolicyEntry 12 }

       -- 1.3.6.1.4.1.388.11.3.4.5.1.1.13
         apIpFilterPolicySrcEndPort OBJECT-TYPE
             SYNTAX Integer32 (0..65535)
             MAX-ACCESS read-write
             STATUS current
             DESCRIPTION
                 "IP Filter Policy Source Ending Port Number"
             ::= { apIpFilterPolicyEntry 13 }
    
		-- 1.3.6.1.4.1.388.11.3.4.5.2
		apIpFilterWlan OBJECT IDENTIFIER ::= { apIpFilter 2 }

		
		-- 1.3.6.1.4.1.388.11.3.4.5.2.1
		apIpFilterWlanTable OBJECT-TYPE
			SYNTAX SEQUENCE OF ApIpFilterWlanEntry
			MAX-ACCESS not-accessible
			STATUS current
			DESCRIPTION
				"IP Filter for WLAN"
			::= { apIpFilterWlan 1 }

		
		-- 1.3.6.1.4.1.388.11.3.4.5.2.1.1
		apIpFilterWlanEntry OBJECT-TYPE
			SYNTAX ApIpFilterWlanEntry
			MAX-ACCESS not-accessible
			STATUS current
			DESCRIPTION
				" "
			INDEX { apWlanIndex }
			::= { apIpFilterWlanTable 1 }

		
		ApIpFilterWlanEntry ::=
			SEQUENCE { 
				apIpFilterWlanMode
					TruthValue,
				apIpFilterWlanDefInAction
					INTEGER,
				apIpFilterWlanDefOutAction
					INTEGER,
				apIpFilterWlanInPackets
					Counter32,
				apIpFilterWlanOutPackets
					Counter32
			 }

		-- 1.3.6.1.4.1.388.11.3.4.5.2.1.1.1
		apIpFilterWlanMode OBJECT-TYPE
			SYNTAX TruthValue
			MAX-ACCESS read-write
			STATUS current
			DESCRIPTION
				"IP Filter Mode."
			::= { apIpFilterWlanEntry 1 }

		
		-- 1.3.6.1.4.1.388.11.3.4.5.2.1.1.2
		apIpFilterWlanDefInAction OBJECT-TYPE
			SYNTAX INTEGER
				{
				allow(1),
				deny(2)
				}
			MAX-ACCESS read-write
			STATUS current
			DESCRIPTION
				"IP Filter Default IN Action."
			::= { apIpFilterWlanEntry 2 }

		
		-- 1.3.6.1.4.1.388.11.3.4.5.2.1.1.3
		apIpFilterWlanDefOutAction OBJECT-TYPE
			SYNTAX INTEGER
				{
				allow(1),
				deny(2)
				}
			MAX-ACCESS read-write
			STATUS current
			DESCRIPTION
				"IP Filter Default OUT Action."
			::= { apIpFilterWlanEntry 3 }

		
		-- 1.3.6.1.4.1.388.11.3.4.5.2.1.1.4
		apIpFilterWlanInPackets OBJECT-TYPE
			SYNTAX Counter32
			MAX-ACCESS read-only
			STATUS current
			DESCRIPTION
				"Number of incoming packets allowed or denied as a result of the default policy"
			::= { apIpFilterWlanEntry 4 }

		
		-- 1.3.6.1.4.1.388.11.3.4.5.2.1.1.5
		apIpFilterWlanOutPackets OBJECT-TYPE
			SYNTAX Counter32
			MAX-ACCESS read-only
			STATUS current
			DESCRIPTION
				"Number of outgoing packets allowed or denied as a result of the default policy"
			::= { apIpFilterWlanEntry 5 }

		
		-- 1.3.6.1.4.1.388.11.3.4.5.2.2
		apIpFilterWlanPolicyTable OBJECT-TYPE
			SYNTAX SEQUENCE OF ApIpFilterWlanPolicyEntry
			MAX-ACCESS not-accessible
			STATUS current
			DESCRIPTION
				"IP Filter Policy for WLANs."
			::= { apIpFilterWlan 2 }

		
		-- 1.3.6.1.4.1.388.11.3.4.5.2.2.1
		apIpFilterWlanPolicyEntry OBJECT-TYPE
			SYNTAX ApIpFilterWlanPolicyEntry
			MAX-ACCESS not-accessible
			STATUS current
			DESCRIPTION
				" "
			INDEX { apWlanIndex, apIpFilterWlanPolicyIndex }
			::= { apIpFilterWlanPolicyTable 1 }

		
		ApIpFilterWlanPolicyEntry ::=
			SEQUENCE { 
				apIpFilterWlanPolicyIndex
					Integer32,
				apIpFilterWlanPolicyPolicy
					DisplayString,
				apIpFilterWlanPolicyDirection
					INTEGER,
				apIpFilterWlanPolicyAction
					INTEGER,
				apIpFilterWlanPolicyRowStatus
					AbbrevRowStatus,
				apIpFilterWlanPolicyPackets
					Counter32
			 }

		-- 1.3.6.1.4.1.388.11.3.4.5.2.2.1.1
		apIpFilterWlanPolicyIndex OBJECT-TYPE
			SYNTAX Integer32 (1..20)
			MAX-ACCESS accessible-for-notify
			STATUS current
			DESCRIPTION
				"Simple Index."
			::= { apIpFilterWlanPolicyEntry 1 }

		
		-- 1.3.6.1.4.1.388.11.3.4.5.2.2.1.2
		apIpFilterWlanPolicyPolicy OBJECT-TYPE
			SYNTAX DisplayString
			MAX-ACCESS read-write
			STATUS current
			DESCRIPTION
				"Single Pointer to the Global IP Filter Policy."
			::= { apIpFilterWlanPolicyEntry 2 }

		
		-- 1.3.6.1.4.1.388.11.3.4.5.2.2.1.3
		apIpFilterWlanPolicyDirection OBJECT-TYPE
			SYNTAX INTEGER
				{
				incoming(1),
				outgoing(2)
				}
			MAX-ACCESS read-write
			STATUS current
			DESCRIPTION
				"IP Filter Policy Direction."
			::= { apIpFilterWlanPolicyEntry 3 }

		
		-- 1.3.6.1.4.1.388.11.3.4.5.2.2.1.4
		apIpFilterWlanPolicyAction OBJECT-TYPE
			SYNTAX INTEGER
				{
				allow(1),
				deny(2)
				}
			MAX-ACCESS read-write
			STATUS current
			DESCRIPTION
				"IP Filter Policy Action."
			::= { apIpFilterWlanPolicyEntry 4 }

		
		-- 1.3.6.1.4.1.388.11.3.4.5.2.2.1.5
		apIpFilterWlanPolicyRowStatus OBJECT-TYPE
			SYNTAX AbbrevRowStatus
			MAX-ACCESS read-write
			STATUS current
			DESCRIPTION
				"Row Status for creation and deletion."
			::= { apIpFilterWlanPolicyEntry 5 }

		
		-- 1.3.6.1.4.1.388.11.3.4.5.2.2.1.6
		apIpFilterWlanPolicyPackets OBJECT-TYPE
			SYNTAX Counter32
			MAX-ACCESS read-only
			STATUS current
			DESCRIPTION
				"Number of packets allowed or denied as a result of this policy."
			::= { apIpFilterWlanPolicyEntry 6 }

		
		-- 1.3.6.1.4.1.388.11.3.4.5.3
		apIpFilterLan OBJECT IDENTIFIER ::= { apIpFilter 3 }

		
		-- 1.3.6.1.4.1.388.11.3.4.5.3.1
		apIpFilterLanTable OBJECT-TYPE
			SYNTAX SEQUENCE OF ApIpFilterLanEntry
			MAX-ACCESS not-accessible
			STATUS current
			DESCRIPTION
				"IP Filter for WLAN"
			::= { apIpFilterLan 1 }

		
		-- 1.3.6.1.4.1.388.11.3.4.5.3.1.1
		apIpFilterLanEntry OBJECT-TYPE
			SYNTAX ApIpFilterLanEntry
			MAX-ACCESS not-accessible
			STATUS current
			DESCRIPTION
				" "
			INDEX { apIpFilterLanIndex }
			::= { apIpFilterLanTable 1 }

		
		ApIpFilterLanEntry ::=
			SEQUENCE { 
				apIpFilterLanIndex
					Integer32,
				apIpFilterLanMode
					TruthValue,
				apIpFilterLanDefInAction
					INTEGER,
				apIpFilterLanDefOutAction
					INTEGER,
				apIpFilterLanInPackets
					Counter32,
				apIpFilterLanOutPackets
					Counter32
			 }

		-- 1.3.6.1.4.1.388.11.3.4.5.3.1.1.1
		apIpFilterLanIndex OBJECT-TYPE
			SYNTAX Integer32 (1..2)
			MAX-ACCESS accessible-for-notify
			STATUS current
			DESCRIPTION
				"Description."
			::= { apIpFilterLanEntry 1 }

		
		-- 1.3.6.1.4.1.388.11.3.4.5.3.1.1.2
		apIpFilterLanMode OBJECT-TYPE
			SYNTAX TruthValue
			MAX-ACCESS read-write
			STATUS current
			DESCRIPTION
				"IP Filter Mode."
			::= { apIpFilterLanEntry 2 }

		
		-- 1.3.6.1.4.1.388.11.3.4.5.3.1.1.3
		apIpFilterLanDefInAction OBJECT-TYPE
			SYNTAX INTEGER
				{
				allow(1),
				deny(2)
				}
			MAX-ACCESS read-write
			STATUS current
			DESCRIPTION
				"IP Filter Default IN Action."
			::= { apIpFilterLanEntry 3 }

		
		-- 1.3.6.1.4.1.388.11.3.4.5.3.1.1.4
		apIpFilterLanDefOutAction OBJECT-TYPE
			SYNTAX INTEGER
				{
				allow(1),
				deny(2)
				}
			MAX-ACCESS read-write
			STATUS current
			DESCRIPTION
				"IP Filter Default OUT Action."
			::= { apIpFilterLanEntry 4 }

		
		-- 1.3.6.1.4.1.388.11.3.4.5.3.1.1.5
		apIpFilterLanInPackets OBJECT-TYPE
			SYNTAX Counter32
			MAX-ACCESS read-only
			STATUS current
			DESCRIPTION
				"Number of incoming packets allowed or denied as a result of the default policy"
			::= { apIpFilterLanEntry 5 }

		
		-- 1.3.6.1.4.1.388.11.3.4.5.3.1.1.6
		apIpFilterLanOutPackets OBJECT-TYPE
			SYNTAX Counter32
			MAX-ACCESS read-only
			STATUS current
			DESCRIPTION
				"Number of outgoing packets allowed or denied as a result of the default policy."
			::= { apIpFilterLanEntry 6 }

		
		-- 1.3.6.1.4.1.388.11.3.4.5.3.2
		apIpFilterLanPolicyTable OBJECT-TYPE
			SYNTAX SEQUENCE OF ApIpFilterLanPolicyEntry
			MAX-ACCESS not-accessible
			STATUS current
			DESCRIPTION
				"IP Filter Policy for WAN Trunk Port."
			::= { apIpFilterLan 2 }

		
		-- 1.3.6.1.4.1.388.11.3.4.5.3.2.1
		apIpFilterLanPolicyEntry OBJECT-TYPE
			SYNTAX ApIpFilterLanPolicyEntry
			MAX-ACCESS not-accessible
			STATUS current
			DESCRIPTION
				" "
			INDEX { apIpFilterLanIndex, apIpFilterLanPolicyIndex }
			::= { apIpFilterLanPolicyTable 1 }

		
		ApIpFilterLanPolicyEntry ::=
			SEQUENCE { 
				apIpFilterLanPolicyIndex
					Integer32,
				apIpFilterLanPolicyPolicy
					DisplayString,
				apIpFilterLanPolicyDirection
					INTEGER,
				apIpFilterLanPolicyAction
					INTEGER,
				apIpFilterLanPolicyRowStatus
					AbbrevRowStatus,
				apIpFilterLanPolicyPackets
					Counter32
			 }

		-- 1.3.6.1.4.1.388.11.3.4.5.3.2.1.1
		apIpFilterLanPolicyIndex OBJECT-TYPE
			SYNTAX Integer32 (1..20)
			MAX-ACCESS accessible-for-notify
			STATUS current
			DESCRIPTION
				"Simple Index."
			::= { apIpFilterLanPolicyEntry 1 }

		
		-- 1.3.6.1.4.1.388.11.3.4.5.3.2.1.2
		apIpFilterLanPolicyPolicy OBJECT-TYPE
			SYNTAX DisplayString
			MAX-ACCESS read-write
			STATUS current
			DESCRIPTION
				"Single Pointer to the Global IP Filter Policy."
			::= { apIpFilterLanPolicyEntry 2 }

		
		-- 1.3.6.1.4.1.388.11.3.4.5.3.2.1.3
		apIpFilterLanPolicyDirection OBJECT-TYPE
			SYNTAX INTEGER
				{
				incoming(1),
				outgoing(2)
				}
			MAX-ACCESS read-write
			STATUS current
			DESCRIPTION
				"IP Filter Policy Direction."
			::= { apIpFilterLanPolicyEntry 3 }

		
		-- 1.3.6.1.4.1.388.11.3.4.5.3.2.1.4
		apIpFilterLanPolicyAction OBJECT-TYPE
			SYNTAX INTEGER
				{
				allow(1),
				deny(2)
				}
			MAX-ACCESS read-write
			STATUS current
			DESCRIPTION
				"IP Filter Policy Action."
			::= { apIpFilterLanPolicyEntry 4 }

		
		-- 1.3.6.1.4.1.388.11.3.4.5.3.2.1.5
		apIpFilterLanPolicyRowStatus OBJECT-TYPE
			SYNTAX AbbrevRowStatus
			MAX-ACCESS read-write
			STATUS current
			DESCRIPTION
				"Row Status for creation and deletion."
			::= { apIpFilterLanPolicyEntry 5 }

		
		-- 1.3.6.1.4.1.388.11.3.4.5.3.2.1.6
		apIpFilterLanPolicyPackets OBJECT-TYPE
			SYNTAX Counter32
			MAX-ACCESS read-only
			STATUS current
			DESCRIPTION
				"Number of packets allowed or denied as a result of this policy."
			::= { apIpFilterLanPolicyEntry 6 }

		
-- Reliable Multicast related OIDs.
-- This feature converts multicast packets on a WLAN to unicast for reliable delivery.
-- This is done for confugred multicast addresses.
		-- 1.3.6.1.4.1.388.11.3.4.6
		apReliableMulticast OBJECT IDENTIFIER ::= { apRf 6 }

		
		-- 1.3.6.1.4.1.388.11.3.4.6.1
		apReliableMulticastMode OBJECT-TYPE
			SYNTAX TruthValue
			MAX-ACCESS read-write
			STATUS current
			DESCRIPTION
				"Enable / Disable Reliable Multicast feature."
			::= { apReliableMulticast 1 }

		
		-- 1.3.6.1.4.1.388.11.3.4.6.2
		apReliableMulticastWlan OBJECT-TYPE
			SYNTAX DisplayString
			MAX-ACCESS read-write
			STATUS current
			DESCRIPTION
				"WLAN (ESSID) on which reliable multicast feature will be enabled."
			::= { apReliableMulticast 2 }

		
		-- 1.3.6.1.4.1.388.11.3.4.6.3
		apReliableMulticastMaxStreams OBJECT-TYPE
			SYNTAX INTEGER (1..32)
			MAX-ACCESS read-write
			STATUS current
			DESCRIPTION
				"Maximum number of streams to be serviced by the reliable Multicast Feature."
			::= { apReliableMulticast 3 }

		
		-- 1.3.6.1.4.1.388.11.3.4.6.4
		apReliableMulticastStandaloneMode OBJECT-TYPE
			SYNTAX TruthValue
			MAX-ACCESS read-write
			STATUS current
			DESCRIPTION
				"Enable / Disable Standalone mode for Reliable Multicast.
				In this mode, the AP can operate without a Multicast Router on the network."
			::= { apReliableMulticast 4 }

		
		-- 1.3.6.1.4.1.388.11.3.4.6.5
		apReliableMulticastIgmpQueryVersion OBJECT-TYPE
			SYNTAX INTEGER
				{
				igmpv1(1),
				igmpv2(2),
				igmpv3(3)
				}
			MAX-ACCESS read-write
			STATUS current
			DESCRIPTION
				"IGMP version for the queries to be sent.
				IGMP query is sent on MU association and when standalone mode is enabled."
			::= { apReliableMulticast 5 }

		
		-- 1.3.6.1.4.1.388.11.3.4.6.6
		apReliableMulticastIgmpQueryInterval OBJECT-TYPE
			SYNTAX INTEGER (30..300)
			MAX-ACCESS read-write
			STATUS current
			DESCRIPTION
				"The IGMP query interval (in seconds) to be used in standalone mode."
			::= { apReliableMulticast 6 }

		
		-- 1.3.6.1.4.1.388.11.3.4.6.7
		apReliableMulticastTxMulticast OBJECT-TYPE
			SYNTAX TruthValue
			MAX-ACCESS read-write
			STATUS current
			DESCRIPTION
				"Description."
			::= { apReliableMulticast 7 }

		
		-- 1.3.6.1.4.1.388.11.3.4.6.8
		apReliableMulticastTable OBJECT-TYPE
			SYNTAX SEQUENCE OF ApReliableMulticastEntry
			MAX-ACCESS not-accessible
			STATUS current
			DESCRIPTION
				"Table of IPv4 Multicast addresses configured for Reliable Multicast"
			::= { apReliableMulticast 8 }

		
		-- 1.3.6.1.4.1.388.11.3.4.6.8.1
		apReliableMulticastEntry OBJECT-TYPE
			SYNTAX ApReliableMulticastEntry
			MAX-ACCESS not-accessible
			STATUS current
			DESCRIPTION
				"Entry of IPv4 Multicast addresses configured for Reliable Multicast"
			INDEX { apReliableMulticastAddrIndex }
			::= { apReliableMulticastTable 1 }

		
		ApReliableMulticastEntry ::=
			SEQUENCE { 
				apReliableMulticastAddrIndex
					INTEGER,
				apReliableMulticastAddress
					IpAddress,
				apReliableMulticastTableRowEnable
					TruthValue
			 }

		-- 1.3.6.1.4.1.388.11.3.4.6.8.1.1
		apReliableMulticastAddrIndex OBJECT-TYPE
			SYNTAX INTEGER (1..16)
			MAX-ACCESS accessible-for-notify
			STATUS current
			DESCRIPTION
				"Description."
			::= { apReliableMulticastEntry 1 }

		
		-- 1.3.6.1.4.1.388.11.3.4.6.8.1.2
		apReliableMulticastAddress OBJECT-TYPE
			SYNTAX IpAddress
			MAX-ACCESS read-write
			STATUS current
			DESCRIPTION
				"IPv4 Multicast Address"
			::= { apReliableMulticastEntry 2 }

		
		-- 1.3.6.1.4.1.388.11.3.4.6.8.1.3
		apReliableMulticastTableRowEnable OBJECT-TYPE
			SYNTAX TruthValue
			MAX-ACCESS read-write
			STATUS current
			DESCRIPTION
				"Row status for Reliable Multicast address table. Set to FALSE to delete a row. Should be TRUE while creating the row."
			::= { apReliableMulticastEntry 3 }

		
		-- 1.3.6.1.4.1.388.11.3.4.6.9
		apReliableMulticastMUTable OBJECT-TYPE
			SYNTAX SEQUENCE OF ApReliableMulticastMUEntry
			MAX-ACCESS not-accessible
			STATUS current
			DESCRIPTION
				"Table of MUs being serviced by the reliable multicast feature."
			::= { apReliableMulticast 9 }

		
		-- 1.3.6.1.4.1.388.11.3.4.6.9.1
		apReliableMulticastMUEntry OBJECT-TYPE
			SYNTAX ApReliableMulticastMUEntry
			MAX-ACCESS not-accessible
			STATUS current
			DESCRIPTION
				"Description."
			INDEX { apReliableMulticastMUStatsIndex }
			::= { apReliableMulticastMUTable 1 }

		
		ApReliableMulticastMUEntry ::=
			SEQUENCE { 
				apReliableMulticastMUStatsIndex
					INTEGER,
				apReliableMulticastMUStatsIPAddr
					IpAddress,
				apReliableMulticastMUMacAddr
					PhysAddress
			 }

		-- 1.3.6.1.4.1.388.11.3.4.6.9.1.1
		apReliableMulticastMUStatsIndex OBJECT-TYPE
			SYNTAX INTEGER (1..32)
			MAX-ACCESS accessible-for-notify
			STATUS current
			DESCRIPTION
				"Description."
			::= { apReliableMulticastMUEntry 1 }

		
		-- 1.3.6.1.4.1.388.11.3.4.6.9.1.2
		apReliableMulticastMUStatsIPAddr OBJECT-TYPE
			SYNTAX IpAddress
			MAX-ACCESS read-only
			STATUS current
			DESCRIPTION
				"IPv4 Multicast Address."
			::= { apReliableMulticastMUEntry 2 }

		
		-- 1.3.6.1.4.1.388.11.3.4.6.9.1.3
		apReliableMulticastMUMacAddr OBJECT-TYPE
			SYNTAX PhysAddress
			MAX-ACCESS read-only
			STATUS current
			DESCRIPTION
				"Mac Address of Mobile Units."
			::= { apReliableMulticastMUEntry 3 }

		
		-- 1.3.6.1.4.1.388.11.3.5
		apSwitch OBJECT IDENTIFIER ::= { abgAP 5 }

		
		-- 1.3.6.1.4.1.388.11.3.5.1
		apWan OBJECT IDENTIFIER ::= { apSwitch 1 }

		
		-- 1.3.6.1.4.1.388.11.3.5.1.1
		apWanVpn OBJECT IDENTIFIER ::= { apWan 1 }

		
		-- 1.3.6.1.4.1.388.11.3.5.1.1.1
		apWanVpnTunnelConfig OBJECT IDENTIFIER ::= { apWanVpn 1 }

		
		-- 1.3.6.1.4.1.388.11.3.5.1.1.1.1
		apWanVpnKeyAutoTable OBJECT-TYPE
			SYNTAX SEQUENCE OF ApWanVpnKeyAutoEntry
			MAX-ACCESS not-accessible
			STATUS current
			DESCRIPTION
				"Table of Auto Key Setting entries."
			::= { apWanVpnTunnelConfig 1 }

		
		-- 1.3.6.1.4.1.388.11.3.5.1.1.1.1.1
		apWanVpnKeyAutoEntry OBJECT-TYPE
			SYNTAX ApWanVpnKeyAutoEntry
			MAX-ACCESS not-accessible
			STATUS current
			DESCRIPTION
				" "
			AUGMENTS { ccWanVpnEntry }
			::= { apWanVpnKeyAutoTable 1 }

		
		ApWanVpnKeyAutoEntry ::=
			SEQUENCE { 
				apWanVpnKeyAutoSALifeTime
					Unsigned32
			 }

		-- 1.3.6.1.4.1.388.11.3.5.1.1.1.1.1.1
		apWanVpnKeyAutoSALifeTime OBJECT-TYPE
			SYNTAX Unsigned32 (300..4294967295)
			UNITS "seconds"
			MAX-ACCESS read-write
			STATUS current
			DESCRIPTION
				"The number of seconds that the security association is valid.
				This is an augumentation to ccWanVpnKeyAutoTable and this
				particular column for Security Association Life Time has been
				added as it was missing from the WS2000 MIB."
			DEFVAL { 3600 }
			::= { apWanVpnKeyAutoEntry 1 }

		
		-- 1.3.6.1.4.1.388.11.3.5.1.2
		apWanPppoe OBJECT IDENTIFIER ::= { apWan 2 }

		
		-- 1.3.6.1.4.1.388.11.3.5.1.2.1
		apWanPppoeClientTable OBJECT-TYPE
			SYNTAX SEQUENCE OF ApWanPppoeClientEntry
			MAX-ACCESS not-accessible
			STATUS current
			DESCRIPTION
				"Description."
			::= { apWanPppoe 1 }

		
		-- 1.3.6.1.4.1.388.11.3.5.1.2.1.1
		apWanPppoeClientEntry OBJECT-TYPE
			SYNTAX ApWanPppoeClientEntry
			MAX-ACCESS not-accessible
			STATUS current
			DESCRIPTION
				"Description."
			INDEX { apWanPppoeClientIndex }
			::= { apWanPppoeClientTable 1 }

		
		ApWanPppoeClientEntry ::=
			SEQUENCE { 
				apWanPppoeClientIndex
					Integer32,
				apWanPppoeClientIp
					IpAddress,
				apWanPppoeClientGateway
					IpAddress,
				apWanPppoeClientPrimaryDNSServer
					IpAddress,
				apWanPppoeClientSecondaryDNSServer
					IpAddress
			 }

		-- 1.3.6.1.4.1.388.11.3.5.1.2.1.1.1
		apWanPppoeClientIndex OBJECT-TYPE
			SYNTAX Integer32 (1)
			MAX-ACCESS accessible-for-notify
			STATUS current
			DESCRIPTION
				"Description."
			::= { apWanPppoeClientEntry 1 }

		
		-- 1.3.6.1.4.1.388.11.3.5.1.2.1.1.2
		apWanPppoeClientIp OBJECT-TYPE
			SYNTAX IpAddress
			MAX-ACCESS read-only
			STATUS current
			DESCRIPTION
				"Description."
			::= { apWanPppoeClientEntry 2 }

		
		-- 1.3.6.1.4.1.388.11.3.5.1.2.1.1.3
		apWanPppoeClientGateway OBJECT-TYPE
			SYNTAX IpAddress
			MAX-ACCESS read-only
			STATUS current
			DESCRIPTION
				"Description."
			::= { apWanPppoeClientEntry 3 }

		
		-- 1.3.6.1.4.1.388.11.3.5.1.2.1.1.4
		apWanPppoeClientPrimaryDNSServer OBJECT-TYPE
			SYNTAX IpAddress
			MAX-ACCESS read-only
			STATUS current
			DESCRIPTION
				"Description."
			::= { apWanPppoeClientEntry 4 }

		
		-- 1.3.6.1.4.1.388.11.3.5.1.2.1.1.5
		apWanPppoeClientSecondaryDNSServer OBJECT-TYPE
			SYNTAX IpAddress
			MAX-ACCESS read-only
			STATUS current
			DESCRIPTION
				"Description."
			::= { apWanPppoeClientEntry 5 }

		
		-- 1.3.6.1.4.1.388.11.3.5.1.3
		apWanPort OBJECT IDENTIFIER ::= { apWan 3 }

		
		-- 1.3.6.1.4.1.388.11.3.5.1.3.1
		apWanPortAutoNegotiation OBJECT-TYPE
			SYNTAX INTEGER
				{
				disabled(0),
				enabled(1)
				}
			MAX-ACCESS read-write
			STATUS current
			DESCRIPTION
				"Wan Ethernet Port Auto-Negotiation Value."
			::= { apWanPort 1 }

		
		-- 1.3.6.1.4.1.388.11.3.5.1.3.2
		apWanPortSpeed OBJECT-TYPE
			SYNTAX INTEGER
				{
				tenMbps(0),
				hundredMbps(1),
				oneGbps(2)
				}
			MAX-ACCESS read-write
			STATUS current
			DESCRIPTION
				"Wan Ethernet Port Speed Value.
				
				AP5131 does not support oneGbps."
			::= { apWanPort 2 }

		
		-- 1.3.6.1.4.1.388.11.3.5.1.3.3
		apWanPortDuplex OBJECT-TYPE
			SYNTAX INTEGER
				{
				half(0),
				full(1)
				}
			MAX-ACCESS read-write
			STATUS current
			DESCRIPTION
				"Wan Ethernet Port Duplex Value."
			::= { apWanPort 3 }

		
		-- 1.3.6.1.4.1.388.11.3.5.1.4
		apWanDynDNS OBJECT IDENTIFIER ::= { apWan 4 }

		
		-- 1.3.6.1.4.1.388.11.3.5.1.4.1
		apWanDynDNSMode OBJECT-TYPE
			SYNTAX TruthValue
			MAX-ACCESS read-write
			STATUS current
			DESCRIPTION
				"Enable/Disable DynDNS feature on WAN interface."
			::= { apWanDynDNS 1 }

		
		-- 1.3.6.1.4.1.388.11.3.5.1.4.2
		apWanDynDNSTable OBJECT-TYPE
			SYNTAX SEQUENCE OF ApWanDynDNSEntry
			MAX-ACCESS not-accessible
			STATUS current
			DESCRIPTION
				"Table of DynDNS configuration entries."
			::= { apWanDynDNS 2 }

		
		-- 1.3.6.1.4.1.388.11.3.5.1.4.2.1
		apWanDynDNSEntry OBJECT-TYPE
			SYNTAX ApWanDynDNSEntry
			MAX-ACCESS not-accessible
			STATUS current
			DESCRIPTION
				"Description."
			INDEX { apWanDynDNSIndex }
			::= { apWanDynDNSTable 1 }

		
		ApWanDynDNSEntry ::=
			SEQUENCE { 
				apWanDynDNSUsername
					DisplayString,
				apWanDynDNSPassword
					DisplayString,
				apWanDynDNSHostname
					DisplayString,
				apWanDynDNSIndex
					Integer32
			 }

		-- 1.3.6.1.4.1.388.11.3.5.1.4.2.1.1
		apWanDynDNSUsername OBJECT-TYPE
			SYNTAX DisplayString
			MAX-ACCESS read-write
			STATUS current
			DESCRIPTION
				"DynDNS Username which is used to access DynDNS service. 
				The user has to create an account in the DynDNS.org 
				site to get a username and password."
			::= { apWanDynDNSEntry 1 }

		
		-- 1.3.6.1.4.1.388.11.3.5.1.4.2.1.2
		apWanDynDNSPassword OBJECT-TYPE
			SYNTAX DisplayString
			MAX-ACCESS read-write
			STATUS current
			DESCRIPTION
				"DynDNS Password used to access DynDNS service. 
				The user has to create an account in the DynDNS.org 
				site to get a username and password"
			::= { apWanDynDNSEntry 2 }

		
		-- 1.3.6.1.4.1.388.11.3.5.1.4.2.1.3
		apWanDynDNSHostname OBJECT-TYPE
			SYNTAX DisplayString
			MAX-ACCESS read-write
			STATUS current
			DESCRIPTION
				"DynDNS Hostname which has be linked to the WAN IP address.
				The hostname entry has to be made in the DynDNS.org site."
			::= { apWanDynDNSEntry 3 }

		
		-- 1.3.6.1.4.1.388.11.3.5.1.4.2.1.4
		apWanDynDNSIndex OBJECT-TYPE
			SYNTAX Integer32 (1)
			MAX-ACCESS accessible-for-notify
			STATUS current
			DESCRIPTION
				"Index for apWanDynDNSTable."
			::= { apWanDynDNSEntry 4 }

		
		-- 1.3.6.1.4.1.388.11.3.5.1.4.3
		apWanDynDNSUpdateResponseTable OBJECT-TYPE
			SYNTAX SEQUENCE OF ApWanDynDNSUpdateResponseEntry
			MAX-ACCESS not-accessible
			STATUS current
			DESCRIPTION
				"Table to display the DynDNS update respone."
			::= { apWanDynDNS 3 }

		
		-- 1.3.6.1.4.1.388.11.3.5.1.4.3.1
		apWanDynDNSUpdateResponseEntry OBJECT-TYPE
			SYNTAX ApWanDynDNSUpdateResponseEntry
			MAX-ACCESS not-accessible
			STATUS current
			DESCRIPTION
				"Description."
			INDEX { apWanDynDNSUpdateResponseIndex }
			::= { apWanDynDNSUpdateResponseTable 1 }

		
		ApWanDynDNSUpdateResponseEntry ::=
			SEQUENCE { 
				apWanDynDNSUpdateHostname
					DisplayString,
				apWanDynDNSUpdateIp
					Integer32,
				apWanDynDNSUpdateStatus
					Integer32,
				apWanDynDNSUpdateResponseIndex
					Integer32
			 }

		-- 1.3.6.1.4.1.388.11.3.5.1.4.3.1.1
		apWanDynDNSUpdateHostname OBJECT-TYPE
			SYNTAX DisplayString
			MAX-ACCESS read-only
			STATUS current
			DESCRIPTION
				"The DynDNS hostname which is linked to the WAN IP Address
				in the DynDNS.org database."
			::= { apWanDynDNSUpdateResponseEntry 1 }

		
		-- 1.3.6.1.4.1.388.11.3.5.1.4.3.1.2
		apWanDynDNSUpdateIp OBJECT-TYPE
			SYNTAX Integer32
			MAX-ACCESS read-only
			STATUS current
			DESCRIPTION
				"The WAN IP address which is linked with the hostname 
				in the DynDNS.org site."
			::= { apWanDynDNSUpdateResponseEntry 2 }

		
		-- 1.3.6.1.4.1.388.11.3.5.1.4.3.1.3
		apWanDynDNSUpdateStatus OBJECT-TYPE
			SYNTAX Integer32
			MAX-ACCESS read-only
			STATUS current
			DESCRIPTION
				"DynDNS update response received from the DynDNS.org."
			::= { apWanDynDNSUpdateResponseEntry 3 }

		
		-- 1.3.6.1.4.1.388.11.3.5.1.4.3.1.4
		apWanDynDNSUpdateResponseIndex OBJECT-TYPE
			SYNTAX Integer32 (1)
			MAX-ACCESS accessible-for-notify
			STATUS current
			DESCRIPTION
				"Index for apWanDynDNSUpdateResponseTable."
			::= { apWanDynDNSUpdateResponseEntry 4 }

		
		-- 1.3.6.1.4.1.388.11.3.5.1.4.4
		apWanDynDNSPerformUpdate OBJECT-TYPE
			SYNTAX DoActionNow
			MAX-ACCESS read-write
			STATUS current
			DESCRIPTION
				"Perform Manual DynDNS Update. 
				An update request to update the WAN IP and hostname
				is sent to DynDNS.org."
			::= { apWanDynDNS 4 }

		
		-- 1.3.6.1.4.1.388.11.3.5.2
		apLan OBJECT IDENTIFIER ::= { apSwitch 2 }

		
		-- 1.3.6.1.4.1.388.11.3.5.2.1
		apLanEnable OBJECT-TYPE
			SYNTAX TruthValue
			MAX-ACCESS read-write
			STATUS deprecated
			DESCRIPTION
				"Enable LAN port."
			::= { apLan 1 }

		
		-- 1.3.6.1.4.1.388.11.3.5.2.2
		apLanTimeOut OBJECT-TYPE
			SYNTAX INTEGER
				{
				disabled(1),
				hardwareDefect(2),
				enabled(3)
				}
			MAX-ACCESS read-write
			STATUS current
			DESCRIPTION
				"LAN Timeout Status"
			::= { apLan 2 }

		
		-- 1.3.6.1.4.1.388.11.3.5.2.3
		apLanTimeOutValue OBJECT-TYPE
			SYNTAX Integer32
			MAX-ACCESS read-write
			STATUS current
			DESCRIPTION
				"If LAN is not connected after Timeout period (in seconds),
				stop the AP from sending beacons."
			::= { apLan 3 }

		
		-- 1.3.6.1.4.1.388.11.3.5.2.4
		apLanVlanEnable OBJECT-TYPE
			SYNTAX TruthValue
			MAX-ACCESS read-write
			STATUS obsolete
			DESCRIPTION
				"Enable VLAN."
			::= { apLan 4 }

		
		-- 1.3.6.1.4.1.388.11.3.5.2.5
		apLanAdminVlanTag OBJECT-TYPE
			SYNTAX Integer32
			MAX-ACCESS read-write
			STATUS obsolete
			DESCRIPTION
				"Management VLAN Tag."
			::= { apLan 5 }

		
		-- 1.3.6.1.4.1.388.11.3.5.2.6
		apLanNativeVlanTag OBJECT-TYPE
			SYNTAX Integer32
			MAX-ACCESS read-write
			STATUS obsolete
			DESCRIPTION
				"Native VLAN Tag."
			::= { apLan 6 }

		
-- 802.1x Port Authentication is used to provide 
-- security and authentication of all wired clients on 
-- a network. The WS 2000 supports 802.1x port 
-- authentication for the AP 300 Access Ports connected 
-- to it. It uses a username and password for all ports 
-- that can be configured from the wireless switch.
		-- 1.3.6.1.4.1.388.11.3.5.2.17
		apLan802dt1xAuth OBJECT IDENTIFIER ::= { apLan 17 }

		
		-- 1.3.6.1.4.1.388.11.3.5.2.17.2
		apLan802dt1xAuthLogin OBJECT-TYPE
			SYNTAX DisplayString (SIZE (0..64))
			MAX-ACCESS read-write
			STATUS current
			DESCRIPTION
				"802.1x AP Authentication username."
			::= { apLan802dt1xAuth 2 }

		
		-- 1.3.6.1.4.1.388.11.3.5.2.17.3
		apLan802dt1xAuthPass OBJECT-TYPE
			SYNTAX Password
			MAX-ACCESS read-write
			STATUS current
			DESCRIPTION
				"802.1x AP Authentication password."
			::= { apLan802dt1xAuth 3 }

		
		-- 1.3.6.1.4.1.388.11.3.5.2.18
		apLanVlan OBJECT IDENTIFIER ::= { apLan 18 }

		
		-- 1.3.6.1.4.1.388.11.3.5.2.18.1
		apVlanTable OBJECT-TYPE
			SYNTAX SEQUENCE OF ApVlanEntry
			MAX-ACCESS not-accessible
			STATUS current
			DESCRIPTION
				"Table of VLAN entries."
			::= { apLanVlan 1 }

		
		-- 1.3.6.1.4.1.388.11.3.5.2.18.1.1
		apVlanEntry OBJECT-TYPE
			SYNTAX ApVlanEntry
			MAX-ACCESS not-accessible
			STATUS current
			DESCRIPTION
				" "
			INDEX { apVlanIndex }
			::= { apVlanTable 1 }

		
		ApVlanEntry ::=
			SEQUENCE { 
				apVlanIndex
					Integer32,
				apVlanId
					Integer32,
				apVlanName
					DisplayString,
				apVlanPointerToWlan
					MultiPointer63,
				apVlanRowStatus
					AbbrevRowStatus
			 }

		-- 1.3.6.1.4.1.388.11.3.5.2.18.1.1.1
		apVlanIndex OBJECT-TYPE
			SYNTAX Integer32 (1..16)
			MAX-ACCESS accessible-for-notify
			STATUS current
			DESCRIPTION
				"Simple Index (1...16)"
			::= { apVlanEntry 1 }

		
		-- 1.3.6.1.4.1.388.11.3.5.2.18.1.1.2
		apVlanId OBJECT-TYPE
			SYNTAX Integer32 (1..4095)
			MAX-ACCESS read-write
			STATUS current
			DESCRIPTION
				"VLAN id."
			::= { apVlanEntry 2 }

		
		-- 1.3.6.1.4.1.388.11.3.5.2.18.1.1.3
		apVlanName OBJECT-TYPE
			SYNTAX DisplayString
			MAX-ACCESS read-write
			STATUS current
			DESCRIPTION
				"VLAN name."
			::= { apVlanEntry 3 }

		
		-- 1.3.6.1.4.1.388.11.3.5.2.18.1.1.4
		apVlanPointerToWlan OBJECT-TYPE
			SYNTAX MultiPointer63
			MAX-ACCESS read-only
			STATUS current
			DESCRIPTION
				"Pointer to WLAN associated with
				this particular VLAN."
			::= { apVlanEntry 4 }

		
		-- 1.3.6.1.4.1.388.11.3.5.2.18.1.1.5
		apVlanRowStatus OBJECT-TYPE
			SYNTAX AbbrevRowStatus
			MAX-ACCESS read-write
			STATUS current
			DESCRIPTION
				"Row Status."
			::= { apVlanEntry 5 }

		
		-- 1.3.6.1.4.1.388.11.3.5.2.19
		apSubnet OBJECT IDENTIFIER ::= { apLan 19 }

		
		-- 1.3.6.1.4.1.388.11.3.5.2.19.1
		apSubnetTable OBJECT-TYPE
			SYNTAX SEQUENCE OF ApSubnetEntry
			MAX-ACCESS not-accessible
			STATUS current
			DESCRIPTION
				"Table of Subnets."
			::= { apSubnet 1 }

		
		-- 1.3.6.1.4.1.388.11.3.5.2.19.1.1
		apSubnetEntry OBJECT-TYPE
			SYNTAX ApSubnetEntry
			MAX-ACCESS not-accessible
			STATUS current
			DESCRIPTION
				" "
			AUGMENTS { ccSubnetEntry }
			::= { apSubnetTable 1 }

		
		ApSubnetEntry ::=
			SEQUENCE { 
				apSubnetDhcpState
					INTEGER,
				apSubnetVlanEnable
					TruthValue,
				apSubnetTypeFilterAccessMode
					INTEGER,
				apSubnetAdminVlanTag
					Integer32,
				apSubnetNativeVlanTag
					Integer32
			 }

		-- 1.3.6.1.4.1.388.11.3.5.2.19.1.1.1
		apSubnetDhcpState OBJECT-TYPE
			SYNTAX INTEGER
				{
				dhcpClient(1),
				dhcpServer(2),
				dhcpNone(3),
				dhcpBootp(4)
				}
			MAX-ACCESS read-write
			STATUS current
			DESCRIPTION
				"Specifies how Subnet gets its IP address/mask."
			::= { apSubnetEntry 1 }

		
		-- 1.3.6.1.4.1.388.11.3.5.2.19.1.1.2
		apSubnetVlanEnable OBJECT-TYPE
			SYNTAX TruthValue
			MAX-ACCESS read-write
			STATUS current
			DESCRIPTION
				"Enable VLAN."
			::= { apSubnetEntry 2 }

		
		-- 1.3.6.1.4.1.388.11.3.5.2.19.1.1.3
		apSubnetTypeFilterAccessMode OBJECT-TYPE
			SYNTAX INTEGER
				{
				allow(1),
				deny(2)
				}
			MAX-ACCESS read-write
			STATUS current
			DESCRIPTION
				"Packets can either be Forwarded or
				Discarded."
			::= { apSubnetEntry 3 }

		
		-- 1.3.6.1.4.1.388.11.3.5.2.19.1.1.4
		apSubnetAdminVlanTag OBJECT-TYPE
			SYNTAX Integer32
			MAX-ACCESS read-write
			STATUS current
			DESCRIPTION
				"Management VLAN Tag."
			::= { apSubnetEntry 4 }

		
		-- 1.3.6.1.4.1.388.11.3.5.2.19.1.1.5
		apSubnetNativeVlanTag OBJECT-TYPE
			SYNTAX Integer32
			MAX-ACCESS read-write
			STATUS current
			DESCRIPTION
				"Native VLAN Tag."
			::= { apSubnetEntry 5 }

		
		-- 1.3.6.1.4.1.388.11.3.5.2.20
		apLanTypeFilterAccessMode OBJECT-TYPE
			SYNTAX INTEGER
				{
				allow(1),
				deny(2)
				}
			MAX-ACCESS read-write
			STATUS obsolete
			DESCRIPTION
				"Packets can either be Forwarded or
				Discarded."
			::= { apLan 20 }

		
		-- 1.3.6.1.4.1.388.11.3.5.2.21
		apLanTypeFilterTable OBJECT-TYPE
			SYNTAX SEQUENCE OF ApLanTypeFilterEntry
			MAX-ACCESS not-accessible
			STATUS current
			DESCRIPTION
				"Table describing ACLs for allowing or denying,
				(depending on default behavior for the WLAN
				specified in apLanTypeFilterAccessMode), MU
				association with each WLAN."
			::= { apLan 21 }

		
		-- 1.3.6.1.4.1.388.11.3.5.2.21.1
		apLanTypeFilterEntry OBJECT-TYPE
			SYNTAX ApLanTypeFilterEntry
			MAX-ACCESS not-accessible
			STATUS current
			DESCRIPTION
				" "
			INDEX { apLanTypeFilterSubnetIndex, apLanTypeFilterIndex }
			::= { apLanTypeFilterTable 1 }

		
		ApLanTypeFilterEntry ::=
			SEQUENCE { 
				apLanTypeFilterSubnetIndex
					Integer32,
				apLanTypeFilterIndex
					Integer32,
				apLanTypeFilter
					EthernetType,
				apLanTypeFilterRowStatus
					AbbrevRowStatus
			 }

		-- 1.3.6.1.4.1.388.11.3.5.2.21.1.1
		apLanTypeFilterSubnetIndex OBJECT-TYPE
			SYNTAX Integer32 (1..2)
			MAX-ACCESS accessible-for-notify
			STATUS current
			DESCRIPTION
				"Subnet Index for Type Filter"
			::= { apLanTypeFilterEntry 1 }

		
		-- 1.3.6.1.4.1.388.11.3.5.2.21.1.2
		apLanTypeFilterIndex OBJECT-TYPE
			SYNTAX Integer32 (1..16)
			MAX-ACCESS accessible-for-notify
			STATUS current
			DESCRIPTION
				"Simple index."
			::= { apLanTypeFilterEntry 2 }

		
		-- 1.3.6.1.4.1.388.11.3.5.2.21.1.3
		apLanTypeFilter OBJECT-TYPE
			SYNTAX EthernetType
			MAX-ACCESS read-write
			STATUS current
			DESCRIPTION
				"Ethernet type to be filtered."
			::= { apLanTypeFilterEntry 3 }

		
		-- 1.3.6.1.4.1.388.11.3.5.2.21.1.4
		apLanTypeFilterRowStatus OBJECT-TYPE
			SYNTAX AbbrevRowStatus
			MAX-ACCESS read-write
			STATUS current
			DESCRIPTION
				"Row status."
			::= { apLanTypeFilterEntry 4 }

		
		-- 1.3.6.1.4.1.388.11.3.5.2.22
		apLanEthernetPort OBJECT-TYPE
			SYNTAX INTEGER
				{
				lan1(1),
				lan2(2)
				}
			MAX-ACCESS read-write
			STATUS current
			DESCRIPTION
				"The Subnet to which the LAN ethernet port is mapped."
			::= { apLan 22 }

		
		-- 1.3.6.1.4.1.388.11.3.5.2.23
		apLanBridgeTable OBJECT-TYPE
			SYNTAX SEQUENCE OF ApLanBridgeEntry
			MAX-ACCESS not-accessible
			STATUS current
			DESCRIPTION
				"Table for Bridge Spanning Tree for a Subnet."
			::= { apLan 23 }

		
		-- 1.3.6.1.4.1.388.11.3.5.2.23.1
		apLanBridgeEntry OBJECT-TYPE
			SYNTAX ApLanBridgeEntry
			MAX-ACCESS not-accessible
			STATUS current
			DESCRIPTION
				" "
			AUGMENTS { ccSubnetEntry }
			::= { apLanBridgeTable 1 }

		
		ApLanBridgeEntry ::=
			SEQUENCE { 
				apLanBridgePriority
					Integer32,
				apLanBridgeMaxMsgAge
					Integer32,
				apLanBridgeHelloTime
					Integer32,
				apLanBridgeFwdDelay
					Integer32,
				apLanBridgeEntryAgeout
					Integer32
			 }

		-- 1.3.6.1.4.1.388.11.3.5.2.23.1.1
		apLanBridgePriority OBJECT-TYPE
			SYNTAX Integer32 (0..65535)
			MAX-ACCESS read-write
			STATUS current
			DESCRIPTION
				"Bridge Priority"
			::= { apLanBridgeEntry 1 }

		
		-- 1.3.6.1.4.1.388.11.3.5.2.23.1.2
		apLanBridgeMaxMsgAge OBJECT-TYPE
			SYNTAX Integer32 (6..40)
			UNITS "seconds"
			MAX-ACCESS read-write
			STATUS current
			DESCRIPTION
				"Bridge Max Message Age Time."
			::= { apLanBridgeEntry 2 }

		
		-- 1.3.6.1.4.1.388.11.3.5.2.23.1.3
		apLanBridgeHelloTime OBJECT-TYPE
			SYNTAX Integer32 (1..10)
			UNITS "seconds"
			MAX-ACCESS read-write
			STATUS current
			DESCRIPTION
				"Bridge Hello Time."
			::= { apLanBridgeEntry 3 }

		
		-- 1.3.6.1.4.1.388.11.3.5.2.23.1.4
		apLanBridgeFwdDelay OBJECT-TYPE
			SYNTAX Integer32 (4..30)
			UNITS "seconds"
			MAX-ACCESS read-write
			STATUS current
			DESCRIPTION
				"Bridge Forward Delay."
			::= { apLanBridgeEntry 4 }

		
		-- 1.3.6.1.4.1.388.11.3.5.2.23.1.5
		apLanBridgeEntryAgeout OBJECT-TYPE
			SYNTAX Integer32 (4..3600)
			UNITS "seconds"
			MAX-ACCESS read-write
			STATUS current
			DESCRIPTION
				"Bridge Forwarding Database Ageout value."
			::= { apLanBridgeEntry 5 }

		
		-- 1.3.6.1.4.1.388.11.3.5.2.24
		apLanPort OBJECT IDENTIFIER ::= { apLan 24 }

		
		-- 1.3.6.1.4.1.388.11.3.5.2.24.1
		apLanPortAutoNegotiation OBJECT-TYPE
			SYNTAX INTEGER
				{
				disabled(0),
				enabled(1)
				}
			MAX-ACCESS read-write
			STATUS current
			DESCRIPTION
				"Lan Ethernet Port Auto-Negotiation Value."
			::= { apLanPort 1 }

		
		-- 1.3.6.1.4.1.388.11.3.5.2.24.2
		apLanPortSpeed OBJECT-TYPE
			SYNTAX INTEGER
				{
				tenMbps(0),
				hundredMbps(1),
				oneGbps(2)
				}
			MAX-ACCESS read-write
			STATUS current
			DESCRIPTION
				"Lan Ethernet Port Speed Value.
				
				AP5131 does not support oneGbps."
			::= { apLanPort 2 }

		
		-- 1.3.6.1.4.1.388.11.3.5.2.24.3
		apLanPortDuplex OBJECT-TYPE
			SYNTAX INTEGER
				{
				half(0),
				full(1)
				}
			MAX-ACCESS read-write
			STATUS current
			DESCRIPTION
				"Lan Ethernet Port Duplex Value."
			::= { apLanPort 3 }

		
		-- 1.3.6.1.4.1.388.11.3.5.3
		apWnmpPing OBJECT IDENTIFIER ::= { apSwitch 3 }

		
		-- 1.3.6.1.4.1.388.11.3.5.3.1
		apWnmpPingDestMu OBJECT-TYPE
			SYNTAX PhysAddress
			MAX-ACCESS read-write
			STATUS current
			DESCRIPTION
				"Ping Destination MU Mac Address.  This address has to match
				one of the MU's in the ccMUInfo table."
			::= { apWnmpPing 1 }

		
		-- 1.3.6.1.4.1.388.11.3.5.3.2
		apWnmpPingDestAP OBJECT-TYPE
			SYNTAX PhysAddress
			MAX-ACCESS read-write
			STATUS current
			DESCRIPTION
				"Ping Destination AP Mac Address.  This address has to match
				one of the AP's in apKnownApTable."
			::= { apWnmpPing 2 }

		
		-- 1.3.6.1.4.1.388.11.3.5.3.3
		apWnmpPingDest OBJECT-TYPE
			SYNTAX INTEGER
				{
				mu(1),
				ap(2)
				}
			MAX-ACCESS read-write
			STATUS current
			DESCRIPTION
				"The destination type of the ping.  It can be either an MU 
				or an AP."
			::= { apWnmpPing 3 }

		
		-- 1.3.6.1.4.1.388.11.3.5.3.4
		apWnmpPingNum OBJECT-TYPE
			SYNTAX Integer32 (1..539)
			MAX-ACCESS read-write
			STATUS current
			DESCRIPTION
				"Number of pings."
			::= { apWnmpPing 4 }

		
		-- 1.3.6.1.4.1.388.11.3.5.3.5
		apWnmpPingPacketLength OBJECT-TYPE
			SYNTAX Integer32 (1..539)
			UNITS "byte"
			MAX-ACCESS read-write
			STATUS current
			DESCRIPTION
				"Length of the Wnmp ping packet."
			::= { apWnmpPing 5 }

		
		-- 1.3.6.1.4.1.388.11.3.5.3.6
		apWnmpPingPacketData OBJECT-TYPE
			SYNTAX OCTET STRING (SIZE (1))
			MAX-ACCESS read-write
			STATUS current
			DESCRIPTION
				"The one-byte data pattern used to fill the Wnmp ping packet."
			::= { apWnmpPing 6 }

		
		-- 1.3.6.1.4.1.388.11.3.5.3.7
		apWnmpPingAction OBJECT-TYPE
			SYNTAX TruthValue
			MAX-ACCESS read-write
			STATUS current
			DESCRIPTION
				"Start and stop ping.  Switching from stop to start state
				will reset apWnmpPingNumResponses to 0."
			::= { apWnmpPing 7 }

		
		-- 1.3.6.1.4.1.388.11.3.5.3.8
		apWnmpPingNumResponses OBJECT-TYPE
			SYNTAX Integer32
			MAX-ACCESS read-only
			STATUS current
			DESCRIPTION
				"Number of ping responses received from the destination."
			::= { apWnmpPing 8 }

		
		-- 1.3.6.1.4.1.388.11.3.5.4
		apFlashLed OBJECT IDENTIFIER ::= { apSwitch 4 }

		
		-- 1.3.6.1.4.1.388.11.3.5.4.1
		apFlashLedDestAP OBJECT-TYPE
			SYNTAX PhysAddress
			MAX-ACCESS read-write
			STATUS current
			DESCRIPTION
				"Led flash destination AP Mac Address.  This address has to 
				match one of the AP's in apKnownApTable."
			::= { apFlashLed 1 }

		
		-- 1.3.6.1.4.1.388.11.3.5.4.2
		apFlashLedAction OBJECT-TYPE
			SYNTAX TruthValue
			MAX-ACCESS read-write
			STATUS current
			DESCRIPTION
				"Turn the led action on or off."
			::= { apFlashLed 2 }

		
		-- 1.3.6.1.4.1.388.11.3.5.5
		apKnownAPList OBJECT IDENTIFIER ::= { apSwitch 5 }

		
		-- 1.3.6.1.4.1.388.11.3.5.5.1
		apKnownApTable OBJECT-TYPE
			SYNTAX SEQUENCE OF ApKnownApEntry
			MAX-ACCESS not-accessible
			STATUS current
			DESCRIPTION
				"Table of Known AP Lists."
			::= { apKnownAPList 1 }

		
		-- 1.3.6.1.4.1.388.11.3.5.5.1.1
		apKnownApEntry OBJECT-TYPE
			SYNTAX ApKnownApEntry
			MAX-ACCESS not-accessible
			STATUS current
			DESCRIPTION
				" "
			INDEX { apKnownApIndex }
			::= { apKnownApTable 1 }

		
		ApKnownApEntry ::=
			SEQUENCE { 
				apKnownApIndex
					Integer32,
				apKnownApMac
					PhysAddress,
				apKnownApIp
					IpAddress,
				apKnownApChannel1
					Integer32,
				apKnownApChannel2
					Integer32,
				apKnownApMu
					Integer32,
				apKnownApKbPerSec
					Integer32,
				apKnownApPktsPerSec
					Integer32,
				apKnownApRadioType1
					INTEGER,
				apKnownApRadioType2
					INTEGER,
				apKnownApType
					INTEGER,
				apKnownApFwVers
					DisplayString,
				apKnownApUnitName
					DisplayString,
				apKnownApEssName
					DisplayString,
				apKnownApSendCfg
					DoActionNow,
				apKnownApSendCfgStatus
					TruthValue,
				apKnownApRadio1ClientBridgeMac1
					PhysAddress,
				apKnownApRadio1ClientBridgeMac2
					PhysAddress,
				apKnownApRadio1ClientBridgeMac3
					PhysAddress,
				apKnownApRadio2ClientBridgeMac1
					PhysAddress,
				apKnownApRadio2ClientBridgeMac2
					PhysAddress,
				apKnownApRadio2ClientBridgeMac3
					PhysAddress
			 }

		-- 1.3.6.1.4.1.388.11.3.5.5.1.1.1
		apKnownApIndex OBJECT-TYPE
			SYNTAX Integer32 (1..128)
			MAX-ACCESS accessible-for-notify
			STATUS current
			DESCRIPTION
				"Simple Index."
			::= { apKnownApEntry 1 }

		
		-- 1.3.6.1.4.1.388.11.3.5.5.1.1.2
		apKnownApMac OBJECT-TYPE
			SYNTAX PhysAddress
			MAX-ACCESS read-only
			STATUS current
			DESCRIPTION
				"MAC Address of the LAN port"
			::= { apKnownApEntry 2 }

		
		-- 1.3.6.1.4.1.388.11.3.5.5.1.1.3
		apKnownApIp OBJECT-TYPE
			SYNTAX IpAddress
			MAX-ACCESS read-only
			STATUS current
			DESCRIPTION
				"IP Address of the LAN port"
			::= { apKnownApEntry 3 }

		
		-- 1.3.6.1.4.1.388.11.3.5.5.1.1.4
		apKnownApChannel1 OBJECT-TYPE
			SYNTAX Integer32
			MAX-ACCESS read-only
			STATUS current
			DESCRIPTION
				"Channel for Radio1 in Dual Radio setup"
			::= { apKnownApEntry 4 }

		
		-- 1.3.6.1.4.1.388.11.3.5.5.1.1.5
		apKnownApChannel2 OBJECT-TYPE
			SYNTAX Integer32
			MAX-ACCESS read-only
			STATUS current
			DESCRIPTION
				"Channel for Radio2 in Dual Radio setup"
			::= { apKnownApEntry 5 }

		
		-- 1.3.6.1.4.1.388.11.3.5.5.1.1.6
		apKnownApMu OBJECT-TYPE
			SYNTAX Integer32
			MAX-ACCESS read-only
			STATUS current
			DESCRIPTION
				"Number of MUs associated."
			::= { apKnownApEntry 6 }

		
		-- 1.3.6.1.4.1.388.11.3.5.5.1.1.7
		apKnownApKbPerSec OBJECT-TYPE
			SYNTAX Integer32
			MAX-ACCESS read-only
			STATUS current
			DESCRIPTION
				"Kilo Bytes in/out per second."
			::= { apKnownApEntry 7 }

		
		-- 1.3.6.1.4.1.388.11.3.5.5.1.1.8
		apKnownApPktsPerSec OBJECT-TYPE
			SYNTAX Integer32
			MAX-ACCESS read-only
			STATUS current
			DESCRIPTION
				"The number of combined input and output packets per sec"
			::= { apKnownApEntry 8 }

		
		-- 1.3.6.1.4.1.388.11.3.5.5.1.1.9
		apKnownApRadioType1 OBJECT-TYPE
			SYNTAX INTEGER
				{
				radioA(1),
				radioB(2),
				radioBG(3),
				radioFH(4),
				radioN(5)
				}
			MAX-ACCESS read-only
			STATUS current
			DESCRIPTION
				"Radio Type of the first radio in Dual Radio setup"
			::= { apKnownApEntry 9 }

		
		-- 1.3.6.1.4.1.388.11.3.5.5.1.1.10
		apKnownApRadioType2 OBJECT-TYPE
			SYNTAX INTEGER
				{
				radioA(1),
				radioB(2),
				radioBG(3),
				radioFH(4),
				radioN(5)
				}
			MAX-ACCESS read-only
			STATUS current
			DESCRIPTION
				"Radio Type of the second radio in Dual Radio setup"
			::= { apKnownApEntry 10 }

		
		-- 1.3.6.1.4.1.388.11.3.5.5.1.1.11
		apKnownApType OBJECT-TYPE
			SYNTAX INTEGER
				{
				unknown(0),
				ap5131(1),
				ap4131(2),
				ap41x1(3),
				ap302x(4),
				ap71x1(5)
				}
			MAX-ACCESS read-only
			STATUS current
			DESCRIPTION
				"Hardware Type."
			::= { apKnownApEntry 11 }

		
		-- 1.3.6.1.4.1.388.11.3.5.5.1.1.12
		apKnownApFwVers OBJECT-TYPE
			SYNTAX DisplayString
			MAX-ACCESS read-only
			STATUS current
			DESCRIPTION
				"Firmware Version"
			::= { apKnownApEntry 12 }

		
		-- 1.3.6.1.4.1.388.11.3.5.5.1.1.13
		apKnownApUnitName OBJECT-TYPE
			SYNTAX DisplayString
			MAX-ACCESS read-only
			STATUS current
			DESCRIPTION
				"System Name."
			::= { apKnownApEntry 13 }

		
		-- 1.3.6.1.4.1.388.11.3.5.5.1.1.14
		apKnownApEssName OBJECT-TYPE
			SYNTAX DisplayString
			MAX-ACCESS read-only
			STATUS current
			DESCRIPTION
				"ESSID of the particular WLAN."
			::= { apKnownApEntry 14 }

		
		-- 1.3.6.1.4.1.388.11.3.5.5.1.1.15
		apKnownApSendCfg OBJECT-TYPE
			SYNTAX DoActionNow
			MAX-ACCESS read-write
			STATUS current
			DESCRIPTION
				"Copy Configuration file button.
				When set to 1 the config file of our AP shall be copied
				onto the Known AP specified."
			::= { apKnownApEntry 15 }

		
		-- 1.3.6.1.4.1.388.11.3.5.5.1.1.16
		apKnownApSendCfgStatus OBJECT-TYPE
			SYNTAX TruthValue
			MAX-ACCESS read-only
			STATUS current
			DESCRIPTION
				"Whether a copy cfg operation succeeded. 
				"
			::= { apKnownApEntry 16 }

		
		-- 1.3.6.1.4.1.388.11.3.5.5.1.1.17
		apKnownApRadio1ClientBridgeMac1 OBJECT-TYPE
			SYNTAX PhysAddress
			MAX-ACCESS read-only
			STATUS current
			DESCRIPTION
				"Client Bridge MAC Address 1 on Radio 1."
			::= { apKnownApEntry 17 }

		
		-- 1.3.6.1.4.1.388.11.3.5.5.1.1.18
		apKnownApRadio1ClientBridgeMac2 OBJECT-TYPE
			SYNTAX PhysAddress
			MAX-ACCESS read-only
			STATUS current
			DESCRIPTION
				"Client Bridge MAC Address 2 on Radio 1."
			::= { apKnownApEntry 18 }

		
		-- 1.3.6.1.4.1.388.11.3.5.5.1.1.19
		apKnownApRadio1ClientBridgeMac3 OBJECT-TYPE
			SYNTAX PhysAddress
			MAX-ACCESS read-only
			STATUS current
			DESCRIPTION
				"Client Bridge MAC Address 3 on Radio 1."
			::= { apKnownApEntry 19 }

		
		-- 1.3.6.1.4.1.388.11.3.5.5.1.1.20
		apKnownApRadio2ClientBridgeMac1 OBJECT-TYPE
			SYNTAX PhysAddress
			MAX-ACCESS read-only
			STATUS current
			DESCRIPTION
				"Client Bridge MAC Address 1 on Radio 2."
			::= { apKnownApEntry 20 }

		
		-- 1.3.6.1.4.1.388.11.3.5.5.1.1.21
		apKnownApRadio2ClientBridgeMac2 OBJECT-TYPE
			SYNTAX PhysAddress
			MAX-ACCESS read-only
			STATUS current
			DESCRIPTION
				"Client Bridge MAC Address 2 on Radio 2."
			::= { apKnownApEntry 21 }

		
		-- 1.3.6.1.4.1.388.11.3.5.5.1.1.22
		apKnownApRadio2ClientBridgeMac3 OBJECT-TYPE
			SYNTAX PhysAddress
			MAX-ACCESS read-only
			STATUS current
			DESCRIPTION
				"Client Bridge MAC Address 3 on Radio 2."
			::= { apKnownApEntry 22 }

		
		-- 1.3.6.1.4.1.388.11.3.5.6
		apAap OBJECT IDENTIFIER ::= { apSwitch 6 }

		
		-- 1.3.6.1.4.1.388.11.3.5.6.1
		apAapSwitchAutoDiscoveryEnable OBJECT-TYPE
			SYNTAX TruthValue
			MAX-ACCESS read-write
			STATUS current
			DESCRIPTION
				"The value true means Hybrid AP Switch Auto Discovery 
				is enabled and false means it is disabled."
			::= { apAap 1 }

		
		-- 1.3.6.1.4.1.388.11.3.5.6.2
		apAapSwitchDiscoveryInterface OBJECT-TYPE
			SYNTAX INTEGER
				{
				wan(1),
				lan1(2),
				lan2(3)
				}
			MAX-ACCESS read-write
			STATUS current
			DESCRIPTION
				"Hybrid AP Switch Discovery Interface."
			::= { apAap 2 }

		
		-- 1.3.6.1.4.1.388.11.3.5.6.3
		apAapSwitchDiscoveryIPAddressTable OBJECT-TYPE
			SYNTAX SEQUENCE OF ApAapSwitchDiscoveryIPAddressEntry
			MAX-ACCESS not-accessible
			STATUS current
			DESCRIPTION
				"Table of static IP addresses used in Switch Discovery for Hybrid AP. "
			::= { apAap 3 }

		
		-- 1.3.6.1.4.1.388.11.3.5.6.3.1
		apAapSwitchDiscoveryIPAddressEntry OBJECT-TYPE
			SYNTAX ApAapSwitchDiscoveryIPAddressEntry
			MAX-ACCESS not-accessible
			STATUS current
			DESCRIPTION
				"apSwitchDiscoveryIPAddressEntry"
			INDEX { apAapSwitchDiscoveryIPAddressIndex }
			::= { apAapSwitchDiscoveryIPAddressTable 1 }

		
		ApAapSwitchDiscoveryIPAddressEntry ::=
			SEQUENCE { 
				apAapSwitchDiscoveryIPAddressIndex
					Integer32,
				apAapSwitchDiscoveryIPAddress
					IpAddress,
				apAapSwitchDiscoveryIPAddressRowStatus
					INTEGER
			 }

		-- 1.3.6.1.4.1.388.11.3.5.6.3.1.1
		apAapSwitchDiscoveryIPAddressIndex OBJECT-TYPE
			SYNTAX Integer32 (1..6)
			MAX-ACCESS accessible-for-notify
			STATUS current
			DESCRIPTION
				"Simple Index (1...6)"
			::= { apAapSwitchDiscoveryIPAddressEntry 1 }

		
		-- 1.3.6.1.4.1.388.11.3.5.6.3.1.2
		apAapSwitchDiscoveryIPAddress OBJECT-TYPE
			SYNTAX IpAddress
			MAX-ACCESS read-write
			STATUS current
			DESCRIPTION
				"Hybrid AP Switch Discovery IP Address."
			::= { apAapSwitchDiscoveryIPAddressEntry 2 }

		
		-- 1.3.6.1.4.1.388.11.3.5.6.3.1.3
		apAapSwitchDiscoveryIPAddressRowStatus OBJECT-TYPE
			SYNTAX INTEGER { destroy(1) }
			MAX-ACCESS read-write
			STATUS current
			DESCRIPTION
				"Simple Row Status."
			::= { apAapSwitchDiscoveryIPAddressEntry 3 }

		
		-- 1.3.6.1.4.1.388.11.3.5.6.4
		apAapSwitchDiscoveryDomainName OBJECT-TYPE
			SYNTAX DisplayString (SIZE (0..127))
			MAX-ACCESS read-write
			STATUS current
			DESCRIPTION
				"Hybrid AP Switch Discovery Domain Name."
			::= { apAap 4 }

		
		-- 1.3.6.1.4.1.388.11.3.5.6.5
		apAapSwitchDiscoveryPort OBJECT-TYPE
			SYNTAX Integer32 (1..65535)
			MAX-ACCESS read-write
			STATUS current
			DESCRIPTION
				"Hybrid AP Switch Discovery Port."
			::= { apAap 5 }

		
		-- 1.3.6.1.4.1.388.11.3.5.6.6
		apAapPassphrase OBJECT-TYPE
			SYNTAX Password (SIZE (0..63))
			MAX-ACCESS read-write
			STATUS current
			DESCRIPTION
				"Hybrid AP Passphrase. Before the AP sends the 
				first packet to request mode and configuration, 
				the switch and the AP should establish a 
				secure link with this pre-shared key or passphrase."
			::= { apAap 6 }

		
		-- 1.3.6.1.4.1.388.11.3.5.6.7
		apAapTunnelToSwitchEnable OBJECT-TYPE
			SYNTAX TruthValue
			MAX-ACCESS read-write
			STATUS current
			DESCRIPTION
				"This boolean is used by the AP to determine if it 
				needs to establish a secure IPSEC tunnel to the switch."
			::= { apAap 7 }

		
		-- 1.3.6.1.4.1.388.11.3.5.6.8
		apAapAcKeepAlive OBJECT-TYPE
			SYNTAX Integer32 (1..10)
			MAX-ACCESS read-write
			STATUS current
			DESCRIPTION
				"AC Keepalive Period."
			::= { apAap 8 }

		
		-- 1.3.6.1.4.1.388.11.3.5.6.9
		apAapAdoptionState OBJECT-TYPE
			SYNTAX INTEGER
				{
				standAlone(1),
				waiting(2),
				adoptionFailed(3),
				adopted(4),
				connectionLoss(5)
				}
			MAX-ACCESS read-only
			STATUS current
			DESCRIPTION
				"The adoption state of the hybrid AP."
			::= { apAap 9 }

		
		-- 1.3.6.1.4.1.388.11.3.5.6.10
		apAapAdoptingSwitchIP OBJECT-TYPE
			SYNTAX IpAddress
			MAX-ACCESS read-only
			STATUS current
			DESCRIPTION
				"The IP address of the switch that has currently adopted this 
				hybrid AP. 
				If the AP is not adopted it gives the IP address of 
				the switch that last adopted the AP. 
				This value is null if the AP has never been adopted."
			::= { apAap 10 }

		
		-- 1.3.6.1.4.1.388.11.3.6
		apNotifications OBJECT IDENTIFIER ::= { abgAP 6 }

		
		-- 1.3.6.1.4.1.388.11.3.6.1
		apMuVlan NOTIFICATION-TYPE
			OBJECTS { apTrapMuMac, apTrapRadioMac, apTrapVlanId }
			STATUS current
			DESCRIPTION 
				"A MU has been associated with this Radio Address."
			::= { apNotifications 1 }

		
		-- 1.3.6.1.4.1.388.11.3.6.2
		apLanMonitor NOTIFICATION-TYPE
			OBJECTS { apTrapLanMonitorMode, apTrapLanMonitorReason }
			STATUS current
			DESCRIPTION 
				"Radios are either been SHUTTING DOWN or RESTORING
				because of a certain activity at LAN Port."
			::= { apNotifications 2 }

		
		-- 1.3.6.1.4.1.388.11.3.6.3
		apWpaCounterMeasure NOTIFICATION-TYPE
			OBJECTS { apTrapWpaCounterMeasureEssid }
			STATUS current
			DESCRIPTION 
				"When a subsequent MIC failure occurs within 60 seconds
				of the preceding failure, the AP will disassociate all
				associated STAs. The AP will not deliver any class 3 TKIP
				encrypted data frames to or from any peer as well as 
				disallow new associations for a period of 60 seconds."
			::= { apNotifications 3 }

		
		-- 1.3.6.1.4.1.388.11.3.6.4
		apMuHotspotState NOTIFICATION-TYPE
			OBJECTS { apTrapCtrlMuMac, apTrapCtrlMuHotspotStateChange }
			STATUS current
			DESCRIPTION 
				"An MU is either Authenticated or Deauthenticated 
				on a Hotspot enabled WLAN. Upon authenticating with a
				Radius Server the state of the MU is changed from HOTSPOT
				to DATA_READY and the vice versa upon Time out or 
				Logging out of that particular MU."
			::= { apNotifications 4 }

		
		-- 1.3.6.1.4.1.388.11.3.6.5
		apDynDNSUpdate NOTIFICATION-TYPE
			OBJECTS { apTrapCtrlDynDNSUpdateIp, apTrapCtrlDynDNSUpdateHostname, apTrapCtrlDynDNSUpdateStatus }
			STATUS current
			DESCRIPTION 
				"A DynDNS Update has been sent to DynDns.org"
			::= { apNotifications 5 }

		
		-- 1.3.6.1.4.1.388.11.3.6.1000
		apTrapCtrl OBJECT IDENTIFIER ::= { apNotifications 1000 }

		
		-- 1.3.6.1.4.1.388.11.3.6.1000.1
		apTrapCtrlEnableTable OBJECT-TYPE
			SYNTAX SEQUENCE OF ApTrapCtrlEnableEntry
			MAX-ACCESS not-accessible
			STATUS current
			DESCRIPTION
				"Table of Trap Enable entries."
			::= { apTrapCtrl 1 }

		
		-- 1.3.6.1.4.1.388.11.3.6.1000.1.1
		apTrapCtrlEnableEntry OBJECT-TYPE
			SYNTAX ApTrapCtrlEnableEntry
			MAX-ACCESS not-accessible
			STATUS current
			DESCRIPTION
				" "
			INDEX { apTrapCtrlEnableIndex }
			::= { apTrapCtrlEnableTable 1 }

		
		ApTrapCtrlEnableEntry ::=
			SEQUENCE { 
				apTrapCtrlEnableIndex
					Integer32,
				apTrapCtrlEnableName
					DisplayString,
				apTrapCtrlEnable
					TruthValue
			 }

		-- 1.3.6.1.4.1.388.11.3.6.1000.1.1.1
		apTrapCtrlEnableIndex OBJECT-TYPE
			SYNTAX Integer32 (1..17)
			MAX-ACCESS accessible-for-notify
			STATUS current
			DESCRIPTION
				"Simple Index."
			::= { apTrapCtrlEnableEntry 1 }

		
		-- 1.3.6.1.4.1.388.11.3.6.1000.1.1.2
		apTrapCtrlEnableName OBJECT-TYPE
			SYNTAX DisplayString
			MAX-ACCESS read-only
			STATUS current
			DESCRIPTION
				"Name of the Trap."
			::= { apTrapCtrlEnableEntry 2 }

		
		-- 1.3.6.1.4.1.388.11.3.6.1000.1.1.3
		apTrapCtrlEnable OBJECT-TYPE
			SYNTAX TruthValue
			MAX-ACCESS read-write
			STATUS current
			DESCRIPTION
				"Enable/Disbale a particular Trap."
			::= { apTrapCtrlEnableEntry 3 }

		
		-- 1.3.6.1.4.1.388.11.3.6.1000.2
		apTrapCtrlRateLimit OBJECT-TYPE
			SYNTAX Unsigned32 (0..300)
			MAX-ACCESS read-write
			STATUS current
			DESCRIPTION
				"The max rate at which SNMP 
				traps/notifications will be sent from the switch.
				 	
				If the switch detects a particular condition and
				it has NOT been at least this many seconds since the
				last trap/notification, this current
				event will NOT result in a trap/notification.
				 	
				If this value is set to 0, every such event results in a
				trap/notification.
				 	
				Factory-default state is 10 [seconds].
				"
			::= { apTrapCtrl 2 }

		
		-- 1.3.6.1.4.1.388.11.3.6.1000.3
		apTrapCtrlSumStats OBJECT IDENTIFIER ::= { apTrapCtrl 3 }

		
		-- 1.3.6.1.4.1.388.11.3.6.1000.3.1
		apTrapCtrlSumStatsTable OBJECT-TYPE
			SYNTAX SEQUENCE OF ApTrapCtrlSumStatsEntry
			MAX-ACCESS not-accessible
			STATUS current
			DESCRIPTION
				"This table configures thresholds that can be monitored for
				- all MUs      and/or 
				- all Portals  and/or 
				- all WLANs    and/or 
				- for the entire switch
				
				When a given threshold is crossed, it generates the 
				appropriate corresponding notification, (ccSumStats_:
				_MU, _Portal, _WLAN, or _Switch).
				
				Some thresholds result in notifications when exceeded, and
				some when the current value sinks below the threshold.  
				This is indicated by the wording of the entry in
				the entry's _Descr value.
				
				In all cases, the summary stat being monitored is the Short
				value, never the Long value.
				
				Note that for thresholds of type thresholdsAvgMuSignal & 
				thresholdsAvgMuNoise, the values being 'watched' are 
				actually negative.  In these cases the threshold is 
				specified as a Unsigned32.  For example, if you wish to
				trap on Signal being worse than -75dBm, enter '70'.  This
				works since a user would never want to trap on a threshold
				of Sinal worse than +10dBm.  (SNR is not an issue, since
				that is a positive value).
				
				Any values reported as var-binds in the resultant trap(s)
				are likewise reported as positive values."
			::= { apTrapCtrlSumStats 1 }

		
		-- 1.3.6.1.4.1.388.11.3.6.1000.3.1.1
		apTrapCtrlSumStatsEntry OBJECT-TYPE
			SYNTAX ApTrapCtrlSumStatsEntry
			MAX-ACCESS not-accessible
			STATUS current
			DESCRIPTION
				"The rows/instances in this table occur at the exact same
				indices as the corresponding monitored data occurs in the
				_SumStats tables.
				
				For example, row #2 / instance .2 represents the
				threshold(s) for the _PktsPerSec values for MU, Portal,
				WLAN, and Switch.
				
				If a given threshold does not make sense for one of those
				4 entities, its corresponding TruthValue will be false."
			INDEX { apTrapCtrlSumStatsIndex }
			::= { apTrapCtrlSumStatsTable 1 }

		
		ApTrapCtrlSumStatsEntry ::=
			SEQUENCE { 
				apTrapCtrlSumStatsIndex
					INTEGER,
				apTrapCtrlSumStatsDescr
					DisplayString,
				apTrapCtrlSumStatsUnits
					DisplayString,
				apTrapCtrlSumStatsCanBeSetMu
					TruthValue,
				apTrapCtrlSumStatsThresholdMu
					Unsigned32,
				apTrapCtrlSumStatsCanBeSetRadioA
					TruthValue,
				apTrapCtrlSumStatsThresholdRadioA
					Unsigned32,
				apTrapCtrlSumStatsCanBeSetRadioBG
					TruthValue,
				apTrapCtrlSumStatsThresholdRadioBG
					Unsigned32,
				apTrapCtrlSumStatsCanBeSetWlan
					TruthValue,
				apTrapCtrlSumStatsThresholdWlans
					Unsigned32,
				apTrapCtrlSumStatsCanBeSetAccessPoint
					TruthValue,
				apTrapCtrlSumStatsThresholdAccessPoint
					Unsigned32,
				apTrapCtrlSumStatsCanBeSetRadioN5000MHz
					TruthValue,
				apTrapCtrlSumStatsThresholdRadioN5000MHz
					Unsigned32,
				apTrapCtrlSumStatsCanBeSetRadioN2400MHz
					TruthValue,
				apTrapCtrlSumStatsThresholdRadioN2400MHz
					Unsigned32
			 }

		-- 1.3.6.1.4.1.388.11.3.6.1000.3.1.1.1
		apTrapCtrlSumStatsIndex OBJECT-TYPE
			SYNTAX INTEGER
				{
				unusedTimestamp(1),
				unusedNumPkts(2),
				thresholdsPktsPerSec(3),
				unusedPktsPerSecTx(4),
				unusedPktsPerSecRx(5),
				thresholdsThroughput(6),
				unusedThroughputTx(7),
				unusedThroughputRx(8),
				thresholdsAvgBitSpeed(9),
				thresholdsAvgMuSignal(10),
				thresholdsAvgMuNoise(11),
				thresholdsAvgMuSnr(12),
				thresholdsPctNUcastPkts(13),
				thresholdsPpmTxWithRetires(14),
				thresholdsPpmTxDropped(15),
				thresholdsTxAvgRetries(16),
				thresholdsPpmRxUndecrypt(17),
				thresholdsTotalMus(18),
				thresholdsPctRfUtil(19),
				thresholdsPctDropped(20)
				}
			MAX-ACCESS accessible-for-notify
			STATUS current
			DESCRIPTION
				"Index into table.  Note that specific thresholds occur at
				specific instance values as denoted by the enumeration
				values assigned to this variable."
			::= { apTrapCtrlSumStatsEntry 1 }

		
		-- 1.3.6.1.4.1.388.11.3.6.1000.3.1.1.2
		apTrapCtrlSumStatsDescr OBJECT-TYPE
			SYNTAX DisplayString
			MAX-ACCESS read-only
			STATUS current
			DESCRIPTION
				"Description of the threshold."
			::= { apTrapCtrlSumStatsEntry 2 }

		
		-- 1.3.6.1.4.1.388.11.3.6.1000.3.1.1.3
		apTrapCtrlSumStatsUnits OBJECT-TYPE
			SYNTAX DisplayString
			MAX-ACCESS read-only
			STATUS current
			DESCRIPTION
				"Units of the threshold."
			::= { apTrapCtrlSumStatsEntry 3 }

		
		-- 1.3.6.1.4.1.388.11.3.6.1000.3.1.1.4
		apTrapCtrlSumStatsCanBeSetMu OBJECT-TYPE
			SYNTAX TruthValue
			MAX-ACCESS read-only
			STATUS current
			DESCRIPTION
				"If true, the threshold can be set for MUs.
				If false, attempting the threshold will return a READ-ONLY."
			::= { apTrapCtrlSumStatsEntry 4 }

		
		-- 1.3.6.1.4.1.388.11.3.6.1000.3.1.1.5
		apTrapCtrlSumStatsThresholdMu OBJECT-TYPE
			SYNTAX Unsigned32
			MAX-ACCESS read-write
			STATUS current
			DESCRIPTION
				"The threshold for all MUs.
				If 0, no threshold checking is performed.( multipled by 100)"
			::= { apTrapCtrlSumStatsEntry 5 }

		
		-- 1.3.6.1.4.1.388.11.3.6.1000.3.1.1.6
		apTrapCtrlSumStatsCanBeSetRadioA OBJECT-TYPE
			SYNTAX TruthValue
			MAX-ACCESS read-only
			STATUS current
			DESCRIPTION
				"If true, the threshold can be set for radio a.
				If false, attempting the threshold will return a READ-ONLY.
				
				Note that this object does not apply to 802.11n radios.
				
				Please use either apTrapCtrlSumStatsCanBeSetRadioN2400MHz or 
				apTrapCtrlSumStatsCanBeSetRadioN5000MHz for 802.11n radios."
			::= { apTrapCtrlSumStatsEntry 6 }

		
		-- 1.3.6.1.4.1.388.11.3.6.1000.3.1.1.7
		apTrapCtrlSumStatsThresholdRadioA OBJECT-TYPE
			SYNTAX Unsigned32
			MAX-ACCESS read-write
			STATUS current
			DESCRIPTION
				"The threshold for radio a.  
				If 0, no threshold checking is performed.( multipled by 100, 
				except for 'No. of MUs associated', index 9)
				
				Note that this object does not apply to 802.11n radios.
				
				Please use either apTrapCtrlSumStatsThresholdRadioN2400MHz or 
				apTrapCtrlSumStatsThresholdRadioN5000MHz for 802.11n radios."
			::= { apTrapCtrlSumStatsEntry 7 }

		
		-- 1.3.6.1.4.1.388.11.3.6.1000.3.1.1.8
		apTrapCtrlSumStatsCanBeSetRadioBG OBJECT-TYPE
			SYNTAX TruthValue
			MAX-ACCESS read-only
			STATUS current
			DESCRIPTION
				"If true, the threshold can be set for radio b/g.
				If false, attempting the threshold will return a READ-ONLY.
				
				Note that this object does not apply to 802.11n radios.
				
				Please use either apTrapCtrlSumStatsCanBeSetRadioN2400MHz or 
				apTrapCtrlSumStatsCanBeSetRadioN5000MHz for 802.11n radios."
			::= { apTrapCtrlSumStatsEntry 8 }

		
		-- 1.3.6.1.4.1.388.11.3.6.1000.3.1.1.9
		apTrapCtrlSumStatsThresholdRadioBG OBJECT-TYPE
			SYNTAX Unsigned32
			MAX-ACCESS read-write
			STATUS current
			DESCRIPTION
				"The threshold for radio b/g.  
				If 0, no threshold checking is performed.( multipled by 100, 
				except for 'No. of MUs associated', index 9)
				
				Note that this object does not apply to 802.11n radios.
				
				Please use either apTrapCtrlSumStatsThresholdRadioN2400MHz or 
				apTrapCtrlSumStatsThresholdRadioN5000MHz for 802.11n radios."
			::= { apTrapCtrlSumStatsEntry 9 }

		
		-- 1.3.6.1.4.1.388.11.3.6.1000.3.1.1.10
		apTrapCtrlSumStatsCanBeSetWlan OBJECT-TYPE
			SYNTAX TruthValue
			MAX-ACCESS read-only
			STATUS current
			DESCRIPTION
				"If true, the threshold can be set for Wlans.
				If false, attempting the threshold will return a READ-ONLY."
			::= { apTrapCtrlSumStatsEntry 10 }

		
		-- 1.3.6.1.4.1.388.11.3.6.1000.3.1.1.11
		apTrapCtrlSumStatsThresholdWlans OBJECT-TYPE
			SYNTAX Unsigned32
			MAX-ACCESS read-write
			STATUS current
			DESCRIPTION
				"The threshold for all Wlans.  
				If 0, no threshold checking is performed.( multipled by 100, except for 'No. of MUs associated', index 9)"
			::= { apTrapCtrlSumStatsEntry 11 }

		
		-- 1.3.6.1.4.1.388.11.3.6.1000.3.1.1.12
		apTrapCtrlSumStatsCanBeSetAccessPoint OBJECT-TYPE
			SYNTAX TruthValue
			MAX-ACCESS read-only
			STATUS current
			DESCRIPTION
				"If true, the threshold can be set for the entire access point.
				If false, attempting the threshold will return a READ-ONLY."
			::= { apTrapCtrlSumStatsEntry 12 }

		
		-- 1.3.6.1.4.1.388.11.3.6.1000.3.1.1.13
		apTrapCtrlSumStatsThresholdAccessPoint OBJECT-TYPE
			SYNTAX Unsigned32
			MAX-ACCESS read-write
			STATUS current
			DESCRIPTION
				"The threshold for the entire Access Point.  
				If 0, no threshold checking is performed.( multipled by 100, except for 'No. of MUs associated', index 9)"
			::= { apTrapCtrlSumStatsEntry 13 }

		
		-- 1.3.6.1.4.1.388.11.3.6.1000.3.1.1.14
		apTrapCtrlSumStatsCanBeSetRadioN5000MHz OBJECT-TYPE
			SYNTAX TruthValue
			MAX-ACCESS read-only
			STATUS current
			DESCRIPTION
				"If true, the threshold can be set for radio n, 5.0 GHz frequency band.
				If false, attempting the threshold will return a READ-ONLY."
			::= { apTrapCtrlSumStatsEntry 14 }

		
		-- 1.3.6.1.4.1.388.11.3.6.1000.3.1.1.15
		apTrapCtrlSumStatsThresholdRadioN5000MHz OBJECT-TYPE
			SYNTAX Unsigned32
			MAX-ACCESS read-write
			STATUS current
			DESCRIPTION
				"The threshold for radio n, 5.0 GHz frequency band.  
				If 0, no threshold checking is performed.( multipled by 100, 
				except for 'No. of MUs associated', index 9)."
			::= { apTrapCtrlSumStatsEntry 15 }

		
		-- 1.3.6.1.4.1.388.11.3.6.1000.3.1.1.16
		apTrapCtrlSumStatsCanBeSetRadioN2400MHz OBJECT-TYPE
			SYNTAX TruthValue
			MAX-ACCESS read-only
			STATUS current
			DESCRIPTION
				"If true, the threshold can be set for radio n, 2.4 GHz frequency band.
				If false, attempting the threshold will return a READ-ONLY."
			::= { apTrapCtrlSumStatsEntry 16 }

		
		-- 1.3.6.1.4.1.388.11.3.6.1000.3.1.1.17
		apTrapCtrlSumStatsThresholdRadioN2400MHz OBJECT-TYPE
			SYNTAX Unsigned32
			MAX-ACCESS read-write
			STATUS current
			DESCRIPTION
				"The threshold for radio n, 2.4 GHz frequency band.  
				If 0, no threshold checking is performed.( multipled by 100, 
				except for 'No. of MUs associated', index 9)."
			::= { apTrapCtrlSumStatsEntry 17 }

		
		-- 1.3.6.1.4.1.388.11.3.6.1000.4
		apTrapMuVlan OBJECT IDENTIFIER ::= { apTrapCtrl 4 }

		
		-- 1.3.6.1.4.1.388.11.3.6.1000.4.1
		apTrapMuMac OBJECT-TYPE
			SYNTAX PhysAddress
			MAX-ACCESS accessible-for-notify
			STATUS current
			DESCRIPTION
				"MU that has been associated."
			::= { apTrapMuVlan 1 }

		
		-- 1.3.6.1.4.1.388.11.3.6.1000.4.2
		apTrapRadioMac OBJECT-TYPE
			SYNTAX PhysAddress
			MAX-ACCESS accessible-for-notify
			STATUS current
			DESCRIPTION
				"Radio to be which MU has been associated."
			::= { apTrapMuVlan 2 }

		
		-- 1.3.6.1.4.1.388.11.3.6.1000.4.3
		apTrapVlanId OBJECT-TYPE
			SYNTAX Integer32
			MAX-ACCESS accessible-for-notify
			STATUS current
			DESCRIPTION
				"Dynamic VLAN ID assigned to the MU."
			::= { apTrapMuVlan 3 }

		
		-- 1.3.6.1.4.1.388.11.3.6.1000.5
		apTrapLanMonitor OBJECT IDENTIFIER ::= { apTrapCtrl 5 }

		
		-- 1.3.6.1.4.1.388.11.3.6.1000.5.1
		apTrapLanMonitorMode OBJECT-TYPE
			SYNTAX INTEGER
				{
				radioShutdown(1),
				radioRestore(2)
				}
			MAX-ACCESS read-write
			STATUS current
			DESCRIPTION
				"Action taken by the Radios either Shutting Down
				or Restoring Up."
			::= { apTrapLanMonitor 1 }

		
		-- 1.3.6.1.4.1.388.11.3.6.1000.5.2
		apTrapLanMonitorReason OBJECT-TYPE
			SYNTAX INTEGER
				{
				disabled(1),
				hardwareDetect(2),
				timeout(3)
				}
			MAX-ACCESS accessible-for-notify
			STATUS current
			DESCRIPTION
				"Activity at the LAN port which caused this
				event to happen."
			::= { apTrapLanMonitor 2 }

		
		-- 1.3.6.1.4.1.388.11.3.6.1000.6
		apTrapWpaCounterMeasure OBJECT IDENTIFIER ::= { apTrapCtrl 6 }

		
		-- 1.3.6.1.4.1.388.11.3.6.1000.6.1
		apTrapWpaCounterMeasureEssid OBJECT-TYPE
			SYNTAX DisplayString
			MAX-ACCESS accessible-for-notify
			STATUS current
			DESCRIPTION
				"ESSID for which MIC failure happened."
			::= { apTrapWpaCounterMeasure 1 }

		
		-- 1.3.6.1.4.1.388.11.3.6.1000.7
		apTrapCtrlMuHotspotState OBJECT IDENTIFIER ::= { apTrapCtrl 7 }

		
		-- 1.3.6.1.4.1.388.11.3.6.1000.7.1
		apTrapCtrlMuMac OBJECT-TYPE
			SYNTAX PhysAddress
			MAX-ACCESS accessible-for-notify
			STATUS current
			DESCRIPTION
				"The MAC Address of the MU which undergoes a state
				changed on a Hotspot enabled WLAN."
			::= { apTrapCtrlMuHotspotState 1 }

		
		-- 1.3.6.1.4.1.388.11.3.6.1000.7.2
		apTrapCtrlMuHotspotStateChange OBJECT-TYPE
			SYNTAX INTEGER
				{
				fromHotspotToDataReady(1),
				fromDataReadyToHotspot(2)
				}
			MAX-ACCESS accessible-for-notify
			STATUS current
			DESCRIPTION
				"The change in the state of an MU associated on
				a Hotspot enabled WLAN."
			::= { apTrapCtrlMuHotspotState 2 }

		
		-- 1.3.6.1.4.1.388.11.3.6.1000.8
		apTrapCtrlDynDNSUpdate OBJECT IDENTIFIER ::= { apTrapCtrl 8 }

		
		-- 1.3.6.1.4.1.388.11.3.6.1000.8.1
		apTrapCtrlDynDNSUpdateIp OBJECT-TYPE
			SYNTAX OCTET STRING
			MAX-ACCESS read-write
			STATUS current
			DESCRIPTION
				"Description."
			::= { apTrapCtrlDynDNSUpdate 1 }

		
		-- 1.3.6.1.4.1.388.11.3.6.1000.8.2
		apTrapCtrlDynDNSUpdateHostname OBJECT-TYPE
			SYNTAX OCTET STRING
			MAX-ACCESS read-write
			STATUS current
			DESCRIPTION
				"Description."
			::= { apTrapCtrlDynDNSUpdate 2 }

		
		-- 1.3.6.1.4.1.388.11.3.6.1000.8.3
		apTrapCtrlDynDNSUpdateStatus OBJECT-TYPE
			SYNTAX OCTET STRING
			MAX-ACCESS read-write
			STATUS current
			DESCRIPTION
				"Description."
			::= { apTrapCtrlDynDNSUpdate 3 }

		
		-- 1.3.6.1.4.1.388.11.3.7
		apRap OBJECT IDENTIFIER ::= { abgAP 7 }

		
		-- 1.3.6.1.4.1.388.11.3.7.1
		apRapControl OBJECT IDENTIFIER ::= { apRap 1 }

		
		-- 1.3.6.1.4.1.388.11.3.7.1.1
		apRapControlDetectors OBJECT IDENTIFIER ::= { apRapControl 1 }

		
		-- 1.3.6.1.4.1.388.11.3.7.1.1.1
		apRapDetectorMode OBJECT-TYPE
			SYNTAX INTEGER
				{
				scanDisable(1),
				scanA(2),
				scanBG(3)
				}
			MAX-ACCESS read-write
			STATUS current
			DESCRIPTION
				"Detector Mode and Band for RF scan.
				It can either be specified to A band or BG band.
				
				This setting does not apply to 802.11n radios."
			::= { apRapControlDetectors 1 }

		
		-- 1.3.6.1.4.1.388.11.3.7.1.1.2
		apRapDetectorABGMode OBJECT-TYPE
			SYNTAX INTEGER
				{
				disable(0),
				enable(1)
				}
			MAX-ACCESS read-write
			STATUS current
			DESCRIPTION
				"Detector Mode to scan both A and BG Bands.
				apRapDetectorMode is used to determine which radio to use.
				
				This setting does not apply to 802.11n radios."
			::= { apRapControlDetectors 2 }

		
-- Values used to initiate (via FTP only), a 
-- download of a configuration file to the switch, 
-- or an upload of a configuration file from the 
-- switch.
-- 
-- All items in this group persist across reboots,
-- except: _CfgOperation and _CfgStart.
		-- 1.3.6.1.4.1.388.11.3.8
		apLoadCfg OBJECT IDENTIFIER ::= { abgAP 8 }

		
		-- 1.3.6.1.4.1.388.11.3.8.1
		apLoadCfgOperation OBJECT-TYPE
			SYNTAX INTEGER
				{
				unspecified(1),
				ftpConfigServerToAP(2),
				ftpConfigAPToServer(3),
				tftpConfigServerToAP(4),
				tftpConfigAPToServer(5),
				sftpConfigServerToAP(6),
				sftpConfigAPToServer(7)
				}
			MAX-ACCESS read-write
			STATUS current
			DESCRIPTION
				"Specifies the type and direction of the transfer to 
				perform involving the configuration file."
			::= { apLoadCfg 1 }

		
		-- 1.3.6.1.4.1.388.11.3.8.2
		apLoadCfgServerPath OBJECT-TYPE
			SYNTAX DisplayString (SIZE (0..39))
			MAX-ACCESS read-write
			STATUS current
			DESCRIPTION
				"The path to the firmware on the SFTP/TFTP/FTP server.
				
				Remember that the type of separator varies 
				depending on the operating system of the server.
				For Windows, use '\', for Unix use '/'.
				
				No path need be specified, (in which case the 
				default directory for the SFTP/TFTP/FTP server 
				will be used);  if a path is specified, remember
				to terminate it with a trailing '/' or '\'."
			::= { apLoadCfg 2 }

		
		-- 1.3.6.1.4.1.388.11.3.8.3
		apLoadCfgServerFilename OBJECT-TYPE
			SYNTAX DisplayString (SIZE (0..39))
			MAX-ACCESS read-write
			STATUS current
			DESCRIPTION
				"The name, (on the server), of the configuration 
				file to load/store from/to the server."
			::= { apLoadCfg 3 }

		
		-- 1.3.6.1.4.1.388.11.3.8.4
		apLoadCfgServerIpAddr OBJECT-TYPE
			SYNTAX IpAddress
			MAX-ACCESS read-write
			STATUS current
			DESCRIPTION
				"IP address of the server used for a 
				configuration file load/store operation."
			::= { apLoadCfg 4 }

		
		-- 1.3.6.1.4.1.388.11.3.8.5
		apLoadCfgFtpUsername OBJECT-TYPE
			SYNTAX DisplayString (SIZE (0..39))
			MAX-ACCESS read-write
			STATUS current
			DESCRIPTION
				"Username for FTP LoadCfg operations."
			::= { apLoadCfg 5 }

		
		-- 1.3.6.1.4.1.388.11.3.8.6
		apLoadCfgFtpPassword OBJECT-TYPE
			SYNTAX DisplayString (SIZE (0..39))
			MAX-ACCESS read-write
			STATUS current
			DESCRIPTION
				"Password for FTP LoadCfg operations."
			::= { apLoadCfg 6 }

		
		-- 1.3.6.1.4.1.388.11.3.8.7
		apLoadCfgStart OBJECT-TYPE
			SYNTAX TruthValue
			MAX-ACCESS read-write
			STATUS current
			DESCRIPTION
				"Set this value to start the configuration file 
				operation.
				
				Note that unlike a firmware load, the actual FTP/TFTP/SFTP
				transfer does begin virtually immediately."
			::= { apLoadCfg 7 }

		
		-- 1.3.6.1.4.1.388.11.3.8.8
		apLoadCfgOperationsDone OBJECT-TYPE
			SYNTAX Counter32
			MAX-ACCESS read-only
			STATUS current
			DESCRIPTION
				"This value counts the total number of configuration
				file transfers completed, (whether they succeed or
				fail).
				
				The SNMP manager should save the value of this
				counter just before starting a LoadCfg operation,
				and then wait for this value to increment before
				checking the Result and/or Success values."
			::= { apLoadCfg 8 }

		
		-- 1.3.6.1.4.1.388.11.3.8.9
		apLoadCfgResult OBJECT-TYPE
			SYNTAX DisplayString
			MAX-ACCESS read-only
			STATUS current
			DESCRIPTION
				"This value reflects the result of the most-recent
				configuration file load/store."
			::= { apLoadCfg 9 }

		
		-- 1.3.6.1.4.1.388.11.3.8.10
		apLoadCfgSuccess OBJECT-TYPE
			SYNTAX TruthValue
			MAX-ACCESS read-only
			STATUS current
			DESCRIPTION
				"The success/failure status of the most recent
				configuration file load/store."
			::= { apLoadCfg 10 }

		
		-- 1.3.6.1.4.1.388.11.3.9
		apStats OBJECT IDENTIFIER ::= { abgAP 9 }

		
		-- 1.3.6.1.4.1.388.11.3.9.1
		apWanClearStats OBJECT-TYPE
			SYNTAX DoActionNow
			MAX-ACCESS read-write
			STATUS current
			DESCRIPTION
				"Clear the WAN stats."
			::= { apStats 1 }

		
		-- 1.3.6.1.4.1.388.11.3.9.2
		apLanClearStats OBJECT-TYPE
			SYNTAX INTEGER
				{
				lan1(1),
				lan2(2)
				}
			MAX-ACCESS read-write
			STATUS current
			DESCRIPTION
				"Clear the LAN stats.
				For clearing LAN1 stats set to lan1 (1) and
				for clearing LAN2 stats set to lan2 (2)."
			::= { apStats 2 }

		
		-- 1.3.6.1.4.1.388.11.3.9.3
		apRadioClearStats OBJECT-TYPE
			SYNTAX DoActionNow
			MAX-ACCESS read-write
			STATUS current
			DESCRIPTION
				"Clear the Radio stats."
			::= { apStats 3 }

		
		-- 1.3.6.1.4.1.388.11.3.9.4
		apWlanClearStats OBJECT-TYPE
			SYNTAX DoActionNow
			MAX-ACCESS read-write
			STATUS current
			DESCRIPTION
				"Clear the WLAN stats."
			::= { apStats 4 }

		
		-- 1.3.6.1.4.1.388.11.3.9.5
		apMuClearStats OBJECT-TYPE
			SYNTAX DoActionNow
			MAX-ACCESS read-write
			STATUS current
			DESCRIPTION
				"Clear the MU stats."
			::= { apStats 5 }

		
		-- 1.3.6.1.4.1.388.11.3.9.6
		apKnownAPClearStats OBJECT-TYPE
			SYNTAX DoActionNow
			MAX-ACCESS read-write
			STATUS current
			DESCRIPTION
				"Clear the Known AP List."
			::= { apStats 6 }

		
		-- 1.3.6.1.4.1.388.11.3.9.7
		apWirelessAPStats OBJECT IDENTIFIER ::= { apStats 7 }

		
		-- 1.3.6.1.4.1.388.11.3.9.7.1
		apMeshStatsTable OBJECT-TYPE
			SYNTAX SEQUENCE OF ApMeshStatsEntry
			MAX-ACCESS not-accessible
			STATUS current
			DESCRIPTION
				"MESH Bridge Statistics"
			::= { apWirelessAPStats 1 }

		
		-- 1.3.6.1.4.1.388.11.3.9.7.1.1
		apMeshStatsEntry OBJECT-TYPE
			SYNTAX ApMeshStatsEntry
			MAX-ACCESS not-accessible
			STATUS current
			DESCRIPTION
				" "
			INDEX { apMeshStatsIndex }
			::= { apMeshStatsTable 1 }

		
		ApMeshStatsEntry ::=
			SEQUENCE { 
				apMeshStatsIndex
					Integer32,
				apMeshStatsConnType
					INTEGER,
				apMeshStatsMac
					PhysAddress,
				apMeshStatsWlanPtr
					SinglePointer,
				apMeshStatsRadioType
					INTEGER,
				apMeshStatsThroughput
					Integer32,
				apMeshStatsAvgBitSpeed
					Integer32,
				apMeshStatsRetries
					Integer32
			 }

		-- 1.3.6.1.4.1.388.11.3.9.7.1.1.1
		apMeshStatsIndex OBJECT-TYPE
			SYNTAX Integer32 (1..127)
			MAX-ACCESS accessible-for-notify
			STATUS current
			DESCRIPTION
				"Simple Index."
			::= { apMeshStatsEntry 1 }

		
		-- 1.3.6.1.4.1.388.11.3.9.7.1.1.2
		apMeshStatsConnType OBJECT-TYPE
			SYNTAX INTEGER
				{
				none(1),
				baseBridge(2),
				clientBridge(3)
				}
			MAX-ACCESS read-only
			STATUS current
			DESCRIPTION
				"MESH Connection Type."
			::= { apMeshStatsEntry 2 }

		
		-- 1.3.6.1.4.1.388.11.3.9.7.1.1.3
		apMeshStatsMac OBJECT-TYPE
			SYNTAX PhysAddress
			MAX-ACCESS read-only
			STATUS current
			DESCRIPTION
				"MAC Address."
			::= { apMeshStatsEntry 3 }

		
		-- 1.3.6.1.4.1.388.11.3.9.7.1.1.4
		apMeshStatsWlanPtr OBJECT-TYPE
			SYNTAX SinglePointer
			MAX-ACCESS read-only
			STATUS current
			DESCRIPTION
				"WLAN Pointer."
			::= { apMeshStatsEntry 4 }

		
		-- 1.3.6.1.4.1.388.11.3.9.7.1.1.5
		apMeshStatsRadioType OBJECT-TYPE
			SYNTAX INTEGER
				{
				dot11a(1),
				dot11bg(2),
				dot11n2400MHz(3),
				dot11n5000MHz(4)
				}
			MAX-ACCESS read-only
			STATUS current
			DESCRIPTION
				"Radio Type.
				
				'dot11a' means an 802.11a standard radio 
				that uses the 5GHz band.
				'dot11bg' means an 802.11b and 802.11g standards radio 
				that uses the 2.4 GHz band.
				'dot11n' means an 802.11n radio can use both 2.4 GHz and/or 5 GHz bands."
			::= { apMeshStatsEntry 5 }

		
		-- 1.3.6.1.4.1.388.11.3.9.7.1.1.6
		apMeshStatsThroughput OBJECT-TYPE
			SYNTAX Integer32
			MAX-ACCESS read-only
			STATUS current
			DESCRIPTION
				"Throughput (x 100)."
			::= { apMeshStatsEntry 6 }

		
		-- 1.3.6.1.4.1.388.11.3.9.7.1.1.7
		apMeshStatsAvgBitSpeed OBJECT-TYPE
			SYNTAX Integer32
			MAX-ACCESS read-only
			STATUS current
			DESCRIPTION
				"Average Bit Speed (x 100)."
			::= { apMeshStatsEntry 7 }

		
		-- 1.3.6.1.4.1.388.11.3.9.7.1.1.8
		apMeshStatsRetries OBJECT-TYPE
			SYNTAX Integer32
			MAX-ACCESS read-only
			STATUS current
			DESCRIPTION
				"Retries (x 100)."
			::= { apMeshStatsEntry 8 }

		
		-- 1.3.6.1.4.1.388.11.3.9.7.2
		apMeshBridgeStatsTable OBJECT-TYPE
			SYNTAX SEQUENCE OF ApMeshBridgeStatsEntry
			MAX-ACCESS not-accessible
			STATUS current
			DESCRIPTION
				"MESH Wireless Bridge Statistics."
			::= { apWirelessAPStats 2 }

		
		-- 1.3.6.1.4.1.388.11.3.9.7.2.1
		apMeshBridgeStatsEntry OBJECT-TYPE
			SYNTAX ApMeshBridgeStatsEntry
			MAX-ACCESS not-accessible
			STATUS current
			DESCRIPTION
				" "
			INDEX { apMeshBridgeStatsIndex }
			::= { apMeshBridgeStatsTable 1 }

		
		ApMeshBridgeStatsEntry ::=
			SEQUENCE { 
				apMeshBridgeStatsIndex
					Integer32,
				apMeshBridgeStatsMac
					PhysAddress,
				apMeshBridgeStatsWlanPtr
					SinglePointer,
				apMeshBridgeStatsLanPtr
					SinglePointer,
				apMeshBridgeStatsRadioType
					INTEGER,
				apMeshBridgeStatsAuthType
					INTEGER,
				apMeshBridgeStatsEncType
					INTEGER,
				apMeshBridgeStatsPktsPerSecRx
					Integer32,
				apMeshBridgeStatsPksPerSecTx
					Integer32,
				apMeshBridgeStatsPktsPerSecTotal
					Integer32,
				apMeshBridgeStatsThroughputRx
					Integer32,
				apMeshBridgeStatsThroughputTx
					Integer32,
				apMeshBridgeStatsThroughputTotal
					Integer32,
				apMeshBridgeStatsAvgBitSpeed
					Integer32,
				apMeshBridgeStatsAvgMuSignal
					Integer32,
				apMeshBridgeStatsAvgMuNoise
					Integer32,
				apMeshBridgeStatsAvgMuSnr
					Integer32,
				apMeshBridgeStatsAvgRetries
					Integer32,
				apMeshBridgeStatsPktsDropped
					Integer32,
				apMeshBridgeStatsUndecryptablePkts
					Integer32
			 }

		-- 1.3.6.1.4.1.388.11.3.9.7.2.1.1
		apMeshBridgeStatsIndex OBJECT-TYPE
			SYNTAX Integer32 (1..127)
			MAX-ACCESS accessible-for-notify
			STATUS current
			DESCRIPTION
				"Simple Index."
			::= { apMeshBridgeStatsEntry 1 }

		
		-- 1.3.6.1.4.1.388.11.3.9.7.2.1.2
		apMeshBridgeStatsMac OBJECT-TYPE
			SYNTAX PhysAddress
			MAX-ACCESS read-only
			STATUS current
			DESCRIPTION
				"MAC Address."
			::= { apMeshBridgeStatsEntry 2 }

		
		-- 1.3.6.1.4.1.388.11.3.9.7.2.1.3
		apMeshBridgeStatsWlanPtr OBJECT-TYPE
			SYNTAX SinglePointer
			MAX-ACCESS read-only
			STATUS current
			DESCRIPTION
				"WLAN Pointer."
			::= { apMeshBridgeStatsEntry 3 }

		
		-- 1.3.6.1.4.1.388.11.3.9.7.2.1.4
		apMeshBridgeStatsLanPtr OBJECT-TYPE
			SYNTAX SinglePointer
			MAX-ACCESS read-only
			STATUS current
			DESCRIPTION
				"LAN Pointer."
			::= { apMeshBridgeStatsEntry 4 }

		
		-- 1.3.6.1.4.1.388.11.3.9.7.2.1.5
		apMeshBridgeStatsRadioType OBJECT-TYPE
			SYNTAX INTEGER
				{
				dot11a(1),
				dot11bg(2),
				dot11n2400MHz(3),
				dot11n5000MHz(4)
				}
			MAX-ACCESS read-only
			STATUS current
			DESCRIPTION
				"Radio Type.
				
				'dot11a' means an 802.11a standard radio 
				that uses the 5GHz band.
				'dot11bg' means an 802.11b and 802.11g standards radio 
				that uses the 2.4 GHz band.
				'dot11n' means an 802.11n radio can use both 2.4 GHz and/or 5 GHz bands."
			::= { apMeshBridgeStatsEntry 5 }

		
		-- 1.3.6.1.4.1.388.11.3.9.7.2.1.6
		apMeshBridgeStatsAuthType OBJECT-TYPE
			SYNTAX INTEGER
				{
				none(1),
				eap(2),
				kerberos(3)
				}
			MAX-ACCESS read-only
			STATUS current
			DESCRIPTION
				"Authentication method."
			::= { apMeshBridgeStatsEntry 6 }

		
		-- 1.3.6.1.4.1.388.11.3.9.7.2.1.7
		apMeshBridgeStatsEncType OBJECT-TYPE
			SYNTAX INTEGER
				{
				none(1),
				wep64(2),
				wep128(3),
				keyguard(4),
				wpaTkip(5),
				wpa2Ccmp(6)
				}
			MAX-ACCESS read-only
			STATUS current
			DESCRIPTION
				"Encryption method."
			::= { apMeshBridgeStatsEntry 7 }

		
		-- 1.3.6.1.4.1.388.11.3.9.7.2.1.8
		apMeshBridgeStatsPktsPerSecRx OBJECT-TYPE
			SYNTAX Integer32
			MAX-ACCESS read-only
			STATUS current
			DESCRIPTION
				"Packets received per second."
			::= { apMeshBridgeStatsEntry 8 }

		
		-- 1.3.6.1.4.1.388.11.3.9.7.2.1.9
		apMeshBridgeStatsPksPerSecTx OBJECT-TYPE
			SYNTAX Integer32
			MAX-ACCESS read-only
			STATUS current
			DESCRIPTION
				"Packets transmitted per second."
			::= { apMeshBridgeStatsEntry 9 }

		
		-- 1.3.6.1.4.1.388.11.3.9.7.2.1.10
		apMeshBridgeStatsPktsPerSecTotal OBJECT-TYPE
			SYNTAX Integer32
			MAX-ACCESS read-only
			STATUS current
			DESCRIPTION
				"Total Packets per second."
			::= { apMeshBridgeStatsEntry 10 }

		
		-- 1.3.6.1.4.1.388.11.3.9.7.2.1.11
		apMeshBridgeStatsThroughputRx OBJECT-TYPE
			SYNTAX Integer32
			MAX-ACCESS read-only
			STATUS current
			DESCRIPTION
				"Throughput received (x 100)."
			::= { apMeshBridgeStatsEntry 11 }

		
		-- 1.3.6.1.4.1.388.11.3.9.7.2.1.12
		apMeshBridgeStatsThroughputTx OBJECT-TYPE
			SYNTAX Integer32
			MAX-ACCESS read-only
			STATUS current
			DESCRIPTION
				"Throughput transmitted (x 100)."
			::= { apMeshBridgeStatsEntry 12 }

		
		-- 1.3.6.1.4.1.388.11.3.9.7.2.1.13
		apMeshBridgeStatsThroughputTotal OBJECT-TYPE
			SYNTAX Integer32
			MAX-ACCESS read-only
			STATUS current
			DESCRIPTION
				"Total Throughput (x 100)."
			::= { apMeshBridgeStatsEntry 13 }

		
		-- 1.3.6.1.4.1.388.11.3.9.7.2.1.14
		apMeshBridgeStatsAvgBitSpeed OBJECT-TYPE
			SYNTAX Integer32
			MAX-ACCESS read-only
			STATUS current
			DESCRIPTION
				"Average Bit Speed (x 100)."
			::= { apMeshBridgeStatsEntry 14 }

		
		-- 1.3.6.1.4.1.388.11.3.9.7.2.1.15
		apMeshBridgeStatsAvgMuSignal OBJECT-TYPE
			SYNTAX Integer32
			MAX-ACCESS read-only
			STATUS current
			DESCRIPTION
				"Average MU Signal (x 100)."
			::= { apMeshBridgeStatsEntry 15 }

		
		-- 1.3.6.1.4.1.388.11.3.9.7.2.1.16
		apMeshBridgeStatsAvgMuNoise OBJECT-TYPE
			SYNTAX Integer32
			MAX-ACCESS read-only
			STATUS current
			DESCRIPTION
				"Average MU Noise (x 100)."
			::= { apMeshBridgeStatsEntry 16 }

		
		-- 1.3.6.1.4.1.388.11.3.9.7.2.1.17
		apMeshBridgeStatsAvgMuSnr OBJECT-TYPE
			SYNTAX Integer32
			MAX-ACCESS read-only
			STATUS current
			DESCRIPTION
				"Average MU Signal to Noise ratio (x 100)."
			::= { apMeshBridgeStatsEntry 17 }

		
		-- 1.3.6.1.4.1.388.11.3.9.7.2.1.18
		apMeshBridgeStatsAvgRetries OBJECT-TYPE
			SYNTAX Integer32
			MAX-ACCESS read-only
			STATUS current
			DESCRIPTION
				"Average Retries (x 100)."
			::= { apMeshBridgeStatsEntry 18 }

		
		-- 1.3.6.1.4.1.388.11.3.9.7.2.1.19
		apMeshBridgeStatsPktsDropped OBJECT-TYPE
			SYNTAX Integer32
			MAX-ACCESS read-only
			STATUS current
			DESCRIPTION
				"Percentage of Packets dropped (x 100)."
			::= { apMeshBridgeStatsEntry 19 }

		
		-- 1.3.6.1.4.1.388.11.3.9.7.2.1.20
		apMeshBridgeStatsUndecryptablePkts OBJECT-TYPE
			SYNTAX Integer32
			MAX-ACCESS read-only
			STATUS current
			DESCRIPTION
				"Percentage of Undecryptable Packets (x 100)."
			::= { apMeshBridgeStatsEntry 20 }

		
		-- 1.3.6.1.4.1.388.11.3.9.7.3
		apLanSTPStatsTable OBJECT-TYPE
			SYNTAX SEQUENCE OF ApLanSTPStatsEntry
			MAX-ACCESS not-accessible
			STATUS current
			DESCRIPTION
				"Table of LAN Spanning Tree Statistics."
			::= { apWirelessAPStats 3 }

		
		-- 1.3.6.1.4.1.388.11.3.9.7.3.1
		apLanSTPStatsEntry OBJECT-TYPE
			SYNTAX ApLanSTPStatsEntry
			MAX-ACCESS not-accessible
			STATUS current
			DESCRIPTION
				" "
			AUGMENTS { ccSubnetEntry }
			::= { apLanSTPStatsTable 1 }

		
		ApLanSTPStatsEntry ::=
			SEQUENCE { 
				apLanSTPStatsDesignatedRoot
					OCTET STRING,
				apLanSTPStatsBridgeId
					OCTET STRING,
				apLanSTPStatsRootPort
					Integer32,
				apLanSTPStatsRootPathCost
					Integer32,
				apLanSTPStatsBridgeMaxMsgAge
					Integer32,
				apLanSTPStatsBridgeHelloTime
					Integer32,
				apLanSTPStatsBridgeFwDelay
					Integer32
			 }

		-- 1.3.6.1.4.1.388.11.3.9.7.3.1.1
		apLanSTPStatsDesignatedRoot OBJECT-TYPE
			SYNTAX OCTET STRING (SIZE (0..255))
			MAX-ACCESS read-only
			STATUS current
			DESCRIPTION
				"Designated Root."
			::= { apLanSTPStatsEntry 1 }

		
		-- 1.3.6.1.4.1.388.11.3.9.7.3.1.2
		apLanSTPStatsBridgeId OBJECT-TYPE
			SYNTAX OCTET STRING (SIZE (0..255))
			MAX-ACCESS read-only
			STATUS current
			DESCRIPTION
				"Bridge ID."
			::= { apLanSTPStatsEntry 2 }

		
		-- 1.3.6.1.4.1.388.11.3.9.7.3.1.3
		apLanSTPStatsRootPort OBJECT-TYPE
			SYNTAX Integer32
			MAX-ACCESS read-only
			STATUS current
			DESCRIPTION
				"Root Port."
			::= { apLanSTPStatsEntry 3 }

		
		-- 1.3.6.1.4.1.388.11.3.9.7.3.1.4
		apLanSTPStatsRootPathCost OBJECT-TYPE
			SYNTAX Integer32
			MAX-ACCESS read-only
			STATUS current
			DESCRIPTION
				"Root Path Cost."
			::= { apLanSTPStatsEntry 4 }

		
		-- 1.3.6.1.4.1.388.11.3.9.7.3.1.5
		apLanSTPStatsBridgeMaxMsgAge OBJECT-TYPE
			SYNTAX Integer32
			MAX-ACCESS read-only
			STATUS current
			DESCRIPTION
				"Bridge Max Message Age."
			::= { apLanSTPStatsEntry 5 }

		
		-- 1.3.6.1.4.1.388.11.3.9.7.3.1.6
		apLanSTPStatsBridgeHelloTime OBJECT-TYPE
			SYNTAX Integer32
			MAX-ACCESS read-only
			STATUS current
			DESCRIPTION
				"Bridge Hello Time."
			::= { apLanSTPStatsEntry 6 }

		
		-- 1.3.6.1.4.1.388.11.3.9.7.3.1.7
		apLanSTPStatsBridgeFwDelay OBJECT-TYPE
			SYNTAX Integer32
			MAX-ACCESS read-only
			STATUS current
			DESCRIPTION
				"Bridge Forward Delay."
			::= { apLanSTPStatsEntry 7 }

		
		-- 1.3.6.1.4.1.388.11.3.9.7.4
		apLanSTPStatsPortIntfTable OBJECT-TYPE
			SYNTAX SEQUENCE OF ApLanSTPStatsPortIntfEntry
			MAX-ACCESS not-accessible
			STATUS current
			DESCRIPTION
				"Table of LAN Spanning Tree Port Interface Statistics."
			::= { apWirelessAPStats 4 }

		
		-- 1.3.6.1.4.1.388.11.3.9.7.4.1
		apLanSTPStatsPortIntfEntry OBJECT-TYPE
			SYNTAX ApLanSTPStatsPortIntfEntry
			MAX-ACCESS not-accessible
			STATUS current
			DESCRIPTION
				" "
			INDEX { apLanSTPStatsPortIntfLanIndex, apLanSTPStatsPortIntfPortIndex }
			::= { apLanSTPStatsPortIntfTable 1 }

		
		ApLanSTPStatsPortIntfEntry ::=
			SEQUENCE { 
				apLanSTPStatsPortIntfLanIndex
					Integer32,
				apLanSTPStatsPortIntfPortIndex
					Integer32,
				apLanSTPStatsPortIntfPortName
					DisplayString,
				apLanSTPStatsPortIntfState
					INTEGER,
				apLanSTPStatsPortIntfPathCost
					Integer32,
				apLanSTPStatsPortIntfDsgRoot
					OCTET STRING,
				apLanSTPStatsPortIntfDsgBridge
					OCTET STRING,
				apLanSTPStatsPortIntfDsgPort
					OCTET STRING,
				apLanSTPStatsPortIntfDsgCost
					Integer32
			 }

		-- 1.3.6.1.4.1.388.11.3.9.7.4.1.1
		apLanSTPStatsPortIntfLanIndex OBJECT-TYPE
			SYNTAX Integer32 (1..2)
			MAX-ACCESS accessible-for-notify
			STATUS current
			DESCRIPTION
				"LAN index."
			::= { apLanSTPStatsPortIntfEntry 1 }

		
		-- 1.3.6.1.4.1.388.11.3.9.7.4.1.2
		apLanSTPStatsPortIntfPortIndex OBJECT-TYPE
			SYNTAX Integer32 (1..33)
			MAX-ACCESS read-write
			STATUS current
			DESCRIPTION
				"Port Index."
			::= { apLanSTPStatsPortIntfEntry 2 }

		
		-- 1.3.6.1.4.1.388.11.3.9.7.4.1.3
		apLanSTPStatsPortIntfPortName OBJECT-TYPE
			SYNTAX DisplayString
			MAX-ACCESS read-only
			STATUS current
			DESCRIPTION
				"Port Name."
			::= { apLanSTPStatsPortIntfEntry 3 }

		
		-- 1.3.6.1.4.1.388.11.3.9.7.4.1.4
		apLanSTPStatsPortIntfState OBJECT-TYPE
			SYNTAX INTEGER
				{
				disabled(1),
				listening(2),
				learning(3),
				forwarding(4),
				blocking(5),
				unknown(6)
				}
			MAX-ACCESS read-only
			STATUS current
			DESCRIPTION
				"State of the Port."
			::= { apLanSTPStatsPortIntfEntry 4 }

		
		-- 1.3.6.1.4.1.388.11.3.9.7.4.1.5
		apLanSTPStatsPortIntfPathCost OBJECT-TYPE
			SYNTAX Integer32
			MAX-ACCESS read-only
			STATUS current
			DESCRIPTION
				"Path Cost."
			::= { apLanSTPStatsPortIntfEntry 5 }

		
		-- 1.3.6.1.4.1.388.11.3.9.7.4.1.6
		apLanSTPStatsPortIntfDsgRoot OBJECT-TYPE
			SYNTAX OCTET STRING (SIZE (0..255))
			MAX-ACCESS read-only
			STATUS current
			DESCRIPTION
				"Designated Root."
			::= { apLanSTPStatsPortIntfEntry 6 }

		
		-- 1.3.6.1.4.1.388.11.3.9.7.4.1.7
		apLanSTPStatsPortIntfDsgBridge OBJECT-TYPE
			SYNTAX OCTET STRING (SIZE (0..255))
			MAX-ACCESS read-only
			STATUS current
			DESCRIPTION
				"Designated Bridge."
			::= { apLanSTPStatsPortIntfEntry 7 }

		
		-- 1.3.6.1.4.1.388.11.3.9.7.4.1.8
		apLanSTPStatsPortIntfDsgPort OBJECT-TYPE
			SYNTAX OCTET STRING (SIZE (0..255))
			MAX-ACCESS read-only
			STATUS current
			DESCRIPTION
				"Designated Port."
			::= { apLanSTPStatsPortIntfEntry 8 }

		
		-- 1.3.6.1.4.1.388.11.3.9.7.4.1.9
		apLanSTPStatsPortIntfDsgCost OBJECT-TYPE
			SYNTAX Integer32
			MAX-ACCESS read-only
			STATUS current
			DESCRIPTION
				"Designated Cost."
			::= { apLanSTPStatsPortIntfEntry 9 }

		
		-- 1.3.6.1.4.1.388.11.3.9.8
		apnStats OBJECT IDENTIFIER ::= { apStats 8 }

		
		-- 1.3.6.1.4.1.388.11.3.9.8.1
		apnRadioStatsTable OBJECT-TYPE
			SYNTAX SEQUENCE OF ApnRadioStatsEntry
			MAX-ACCESS not-accessible
			STATUS current
			DESCRIPTION
				"APN radio statistics table."
			::= { apnStats 1 }

		
		-- 1.3.6.1.4.1.388.11.3.9.8.1.1
		apnRadioStatsEntry OBJECT-TYPE
			SYNTAX ApnRadioStatsEntry
			MAX-ACCESS not-accessible
			STATUS current
			DESCRIPTION
				"APN radio statistics entry."
			INDEX { apnRadioStatsIndex }
			::= { apnRadioStatsTable 1 }

		
		ApnRadioStatsEntry ::=
			SEQUENCE { 
				apnRadioStatsIndex
					INTEGER,
				apnRadioStatsBssid
					PhysAddress,
				apnRadioStatsApSsid
					DisplayString,
				apnRadioStatsChannel
					INTEGER,
				apnRadioStatsExtnChannel
					INTEGER,
				apnRadioStatsRssiAvgAcrossAntennas
					Integer32,
				apnRadioStatsChannelWidthMode
					INTEGER,
				apnRadioStatsOpFreq
					INTEGER,
				apnRadioStatsNumPktsRxSGI400ns
					Counter32,
				apnRadioStatsNumPktsRxSGI800ns
					Counter32,
				apnRadioStatsNumPktsTxSGI400ns
					Counter32,
				apnRadioStatsNumPktsTxSGI800ns
					Counter32,
				apnRadioStatsNumPktsRxChanWidth20MHz
					Counter32,
				apnRadioStatsNumPktsRxChanWidth40MHz
					Counter32,
				apnRadioStatsNumPktsTxChanWidth20MHz
					Counter32,
				apnRadioStatsNumPktsTxChanWidth40MHz
					Counter32
			 }

		-- 1.3.6.1.4.1.388.11.3.9.8.1.1.2
		apnRadioStatsIndex OBJECT-TYPE
			SYNTAX INTEGER (1..256)
			MAX-ACCESS read-only
			STATUS current
			DESCRIPTION
				"A simple integer index to the apnRadioStatsTable."
			::= { apnRadioStatsEntry 2 }

		
		-- 1.3.6.1.4.1.388.11.3.9.8.1.1.3
		apnRadioStatsBssid OBJECT-TYPE
			SYNTAX PhysAddress
			MAX-ACCESS read-only
			STATUS current
			DESCRIPTION
				"The BSSID (MAC address) of the radio."
			::= { apnRadioStatsEntry 3 }

		
		-- 1.3.6.1.4.1.388.11.3.9.8.1.1.4
		apnRadioStatsApSsid OBJECT-TYPE
			SYNTAX DisplayString
			MAX-ACCESS read-only
			STATUS current
			DESCRIPTION
				"The SSID of the AP."
			::= { apnRadioStatsEntry 4 }

		
		-- 1.3.6.1.4.1.388.11.3.9.8.1.1.5
		apnRadioStatsChannel OBJECT-TYPE
			SYNTAX INTEGER
			MAX-ACCESS read-only
			STATUS current
			DESCRIPTION
				"The channel number for the radio."
			::= { apnRadioStatsEntry 5 }

		
		-- 1.3.6.1.4.1.388.11.3.9.8.1.1.6
		apnRadioStatsExtnChannel OBJECT-TYPE
			SYNTAX INTEGER
			MAX-ACCESS read-only
			STATUS current
			DESCRIPTION
				"The extension channel for the radio, when in 40MHz."
			::= { apnRadioStatsEntry 6 }

		
		-- 1.3.6.1.4.1.388.11.3.9.8.1.1.7
		apnRadioStatsRssiAvgAcrossAntennas OBJECT-TYPE
			SYNTAX Integer32
			UNITS "dBm"
			MAX-ACCESS read-only
			STATUS current
			DESCRIPTION
				"The average RSSI of all the antennas combined together."
			::= { apnRadioStatsEntry 7 }

		
		-- 1.3.6.1.4.1.388.11.3.9.8.1.1.8
		apnRadioStatsChannelWidthMode OBJECT-TYPE
			SYNTAX INTEGER
				{
				twentyMHz(1),
				fortyMHz(2),
				pco(3)
				}
			MAX-ACCESS read-only
			STATUS current
			DESCRIPTION
				"The channel bandwidth mode for the radio."
			::= { apnRadioStatsEntry 8 }

		
		-- 1.3.6.1.4.1.388.11.3.9.8.1.1.9
		apnRadioStatsOpFreq OBJECT-TYPE
			SYNTAX INTEGER
				{
				freq2400MHz(1),
				freq5000MHz(2),
				freq2400MHzAnd5000MHz(3)
				}
			MAX-ACCESS read-only
			STATUS current
			DESCRIPTION
				"The operational frequency for the radio."
			::= { apnRadioStatsEntry 9 }

		
		-- 1.3.6.1.4.1.388.11.3.9.8.1.1.10
		apnRadioStatsNumPktsRxSGI400ns OBJECT-TYPE
			SYNTAX Counter32
			MAX-ACCESS read-only
			STATUS current
			DESCRIPTION
				"Number of packets received by this radio with Short Guard Interval of 400ns."
			::= { apnRadioStatsEntry 10 }

		
		-- 1.3.6.1.4.1.388.11.3.9.8.1.1.11
		apnRadioStatsNumPktsRxSGI800ns OBJECT-TYPE
			SYNTAX Counter32
			MAX-ACCESS read-only
			STATUS current
			DESCRIPTION
				"Number of packets received by this radio with Short Guard Interval of 800ns."
			::= { apnRadioStatsEntry 11 }

		
		-- 1.3.6.1.4.1.388.11.3.9.8.1.1.12
		apnRadioStatsNumPktsTxSGI400ns OBJECT-TYPE
			SYNTAX Counter32
			MAX-ACCESS read-only
			STATUS current
			DESCRIPTION
				"Number of packets transmitted by this radio with Short Guard Interval of 400ns."
			::= { apnRadioStatsEntry 12 }

		
		-- 1.3.6.1.4.1.388.11.3.9.8.1.1.13
		apnRadioStatsNumPktsTxSGI800ns OBJECT-TYPE
			SYNTAX Counter32
			MAX-ACCESS read-only
			STATUS current
			DESCRIPTION
				"Number of packets transmitted by this radio with Short Guard Interval of 800ns."
			::= { apnRadioStatsEntry 13 }

		
		-- 1.3.6.1.4.1.388.11.3.9.8.1.1.14
		apnRadioStatsNumPktsRxChanWidth20MHz OBJECT-TYPE
			SYNTAX Counter32
			MAX-ACCESS read-only
			STATUS current
			DESCRIPTION
				"Number of packets received by this radio with channel width 20 MHz."
			::= { apnRadioStatsEntry 14 }

		
		-- 1.3.6.1.4.1.388.11.3.9.8.1.1.15
		apnRadioStatsNumPktsRxChanWidth40MHz OBJECT-TYPE
			SYNTAX Counter32
			MAX-ACCESS read-only
			STATUS current
			DESCRIPTION
				"Number of packets received by this radio with channel width 40 MHz."
			::= { apnRadioStatsEntry 15 }

		
		-- 1.3.6.1.4.1.388.11.3.9.8.1.1.16
		apnRadioStatsNumPktsTxChanWidth20MHz OBJECT-TYPE
			SYNTAX Counter32
			MAX-ACCESS read-only
			STATUS current
			DESCRIPTION
				"Number of packets transmitted by this radio with channel width 20 MHz."
			::= { apnRadioStatsEntry 16 }

		
		-- 1.3.6.1.4.1.388.11.3.9.8.1.1.17
		apnRadioStatsNumPktsTxChanWidth40MHz OBJECT-TYPE
			SYNTAX Counter32
			MAX-ACCESS read-only
			STATUS current
			DESCRIPTION
				"Number of packets transmitted by this radio with channel width 40 MHz."
			::= { apnRadioStatsEntry 17 }

		
		-- 1.3.6.1.4.1.388.11.3.9.8.2
		apnPortalRxPktsTable OBJECT-TYPE
			SYNTAX SEQUENCE OF ApnPortalRxPktsEntry
			MAX-ACCESS not-accessible
			STATUS current
			DESCRIPTION
				"For each 802.11n Portal on the AP, this table 
				describes counts of packets received at each 
				speed."
			::= { apnStats 2 }

		
		-- 1.3.6.1.4.1.388.11.3.9.8.2.1
		apnPortalRxPktsEntry OBJECT-TYPE
			SYNTAX ApnPortalRxPktsEntry
			MAX-ACCESS not-accessible
			STATUS current
			DESCRIPTION
				"An entry in the portal received packets table."
			INDEX { ccPortalIndex }
			::= { apnPortalRxPktsTable 1 }

		
		ApnPortalRxPktsEntry ::=
			SEQUENCE { 
				apnPortalRxPktsAt1Mb
					Counter32,
				apnPortalRxPktsAt2Mb
					Counter32,
				apnPortalRxPktsAt5pt5Mb
					Counter32,
				apnPortalRxPktsAt6Mb
					Counter32,
				apnPortalRxPktsAt9Mb
					Counter32,
				apnPortalRxPktsAt11Mb
					Counter32,
				apnPortalRxPktsAt12Mb
					Counter32,
				apnPortalRxPktsAt18Mb
					Counter32,
				apnPortalRxPktsAt24Mb
					Counter32,
				apnPortalRxPktsAt36Mb
					Counter32,
				apnPortalRxPktsAt48Mb
					Counter32,
				apnPortalRxPktsAt54Mb
					Counter32,
				apnPortalRxPktsAtMCS0
					Counter32,
				apnPortalRxPktsAtMCS1
					Counter32,
				apnPortalRxPktsAtMCS2
					Counter32,
				apnPortalRxPktsAtMCS3
					Counter32,
				apnPortalRxPktsAtMCS4
					Counter32,
				apnPortalRxPktsAtMCS5
					Counter32,
				apnPortalRxPktsAtMCS6
					Counter32,
				apnPortalRxPktsAtMCS7
					Counter32,
				apnPortalRxPktsAtMCS8
					Counter32,
				apnPortalRxPktsAtMCS9
					Counter32,
				apnPortalRxPktsAtMCS10
					Counter32,
				apnPortalRxPktsAtMCS11
					Counter32,
				apnPortalRxPktsAtMCS12
					Counter32,
				apnPortalRxPktsAtMCS13
					Counter32,
				apnPortalRxPktsAtMCS14
					Counter32,
				apnPortalRxPktsAtMCS15
					Counter32
			 }

		-- 1.3.6.1.4.1.388.11.3.9.8.2.1.1
		apnPortalRxPktsAt1Mb OBJECT-TYPE
			SYNTAX Counter32
			MAX-ACCESS read-only
			STATUS current
			DESCRIPTION
				"Number of pkts received via this Portal at 1 Mbps."
			::= { apnPortalRxPktsEntry 1 }

		
		-- 1.3.6.1.4.1.388.11.3.9.8.2.1.2
		apnPortalRxPktsAt2Mb OBJECT-TYPE
			SYNTAX Counter32
			MAX-ACCESS read-only
			STATUS current
			DESCRIPTION
				"Number of pkts received via this Portal at 2 Mbps."
			::= { apnPortalRxPktsEntry 2 }

		
		-- 1.3.6.1.4.1.388.11.3.9.8.2.1.3
		apnPortalRxPktsAt5pt5Mb OBJECT-TYPE
			SYNTAX Counter32
			MAX-ACCESS read-only
			STATUS current
			DESCRIPTION
				"Number of pkts received via this Portal at 5.5 Mbps."
			::= { apnPortalRxPktsEntry 3 }

		
		-- 1.3.6.1.4.1.388.11.3.9.8.2.1.4
		apnPortalRxPktsAt6Mb OBJECT-TYPE
			SYNTAX Counter32
			MAX-ACCESS read-only
			STATUS current
			DESCRIPTION
				"Number of pkts received via this Portal at 6 Mbps."
			::= { apnPortalRxPktsEntry 4 }

		
		-- 1.3.6.1.4.1.388.11.3.9.8.2.1.5
		apnPortalRxPktsAt9Mb OBJECT-TYPE
			SYNTAX Counter32
			MAX-ACCESS read-only
			STATUS current
			DESCRIPTION
				"Number of pkts received via this Portal at 9 Mbps."
			::= { apnPortalRxPktsEntry 5 }

		
		-- 1.3.6.1.4.1.388.11.3.9.8.2.1.6
		apnPortalRxPktsAt11Mb OBJECT-TYPE
			SYNTAX Counter32
			MAX-ACCESS read-only
			STATUS current
			DESCRIPTION
				"Number of pkts received via this Portal at 11 Mbps."
			::= { apnPortalRxPktsEntry 6 }

		
		-- 1.3.6.1.4.1.388.11.3.9.8.2.1.7
		apnPortalRxPktsAt12Mb OBJECT-TYPE
			SYNTAX Counter32
			MAX-ACCESS read-only
			STATUS current
			DESCRIPTION
				"Number of pkts received via this Portal at 12 Mbps."
			::= { apnPortalRxPktsEntry 7 }

		
		-- 1.3.6.1.4.1.388.11.3.9.8.2.1.8
		apnPortalRxPktsAt18Mb OBJECT-TYPE
			SYNTAX Counter32
			MAX-ACCESS read-only
			STATUS current
			DESCRIPTION
				"Number of pkts received via this Portal at 18 Mbps."
			::= { apnPortalRxPktsEntry 8 }

		
		-- 1.3.6.1.4.1.388.11.3.9.8.2.1.9
		apnPortalRxPktsAt24Mb OBJECT-TYPE
			SYNTAX Counter32
			MAX-ACCESS read-only
			STATUS current
			DESCRIPTION
				"Number of pkts received via this Portal at 24 Mbps."
			::= { apnPortalRxPktsEntry 9 }

		
		-- 1.3.6.1.4.1.388.11.3.9.8.2.1.10
		apnPortalRxPktsAt36Mb OBJECT-TYPE
			SYNTAX Counter32
			MAX-ACCESS read-only
			STATUS current
			DESCRIPTION
				"Number of pkts received via this Portal at 36 Mbps."
			::= { apnPortalRxPktsEntry 10 }

		
		-- 1.3.6.1.4.1.388.11.3.9.8.2.1.11
		apnPortalRxPktsAt48Mb OBJECT-TYPE
			SYNTAX Counter32
			MAX-ACCESS read-only
			STATUS current
			DESCRIPTION
				"Number of pkts received via this Portal at 48 Mbps."
			::= { apnPortalRxPktsEntry 11 }

		
		-- 1.3.6.1.4.1.388.11.3.9.8.2.1.12
		apnPortalRxPktsAt54Mb OBJECT-TYPE
			SYNTAX Counter32
			MAX-ACCESS read-only
			STATUS current
			DESCRIPTION
				"Number of pkts received via this Portal at 54 Mbps."
			::= { apnPortalRxPktsEntry 12 }

		
		-- 1.3.6.1.4.1.388.11.3.9.8.2.1.13
		apnPortalRxPktsAtMCS0 OBJECT-TYPE
			SYNTAX Counter32
			MAX-ACCESS read-only
			STATUS current
			DESCRIPTION
				"Number of pkts received via this Portal at MCS 0 rate."
			::= { apnPortalRxPktsEntry 13 }

		
		-- 1.3.6.1.4.1.388.11.3.9.8.2.1.14
		apnPortalRxPktsAtMCS1 OBJECT-TYPE
			SYNTAX Counter32
			MAX-ACCESS read-only
			STATUS current
			DESCRIPTION
				"Number of pkts received via this Portal at MCS 1 rate."
			::= { apnPortalRxPktsEntry 14 }

		
		-- 1.3.6.1.4.1.388.11.3.9.8.2.1.15
		apnPortalRxPktsAtMCS2 OBJECT-TYPE
			SYNTAX Counter32
			MAX-ACCESS read-only
			STATUS current
			DESCRIPTION
				"Number of pkts received via this Portal at MCS 2 rate."
			::= { apnPortalRxPktsEntry 15 }

		
		-- 1.3.6.1.4.1.388.11.3.9.8.2.1.16
		apnPortalRxPktsAtMCS3 OBJECT-TYPE
			SYNTAX Counter32
			MAX-ACCESS read-only
			STATUS current
			DESCRIPTION
				"Number of pkts received via this Portal at MCS 3 rate."
			::= { apnPortalRxPktsEntry 16 }

		
		-- 1.3.6.1.4.1.388.11.3.9.8.2.1.17
		apnPortalRxPktsAtMCS4 OBJECT-TYPE
			SYNTAX Counter32
			MAX-ACCESS read-only
			STATUS current
			DESCRIPTION
				"Number of pkts received via this Portal at MCS 4 rate."
			::= { apnPortalRxPktsEntry 17 }

		
		-- 1.3.6.1.4.1.388.11.3.9.8.2.1.18
		apnPortalRxPktsAtMCS5 OBJECT-TYPE
			SYNTAX Counter32
			MAX-ACCESS read-only
			STATUS current
			DESCRIPTION
				"Number of pkts received via this Portal at MCS 5 rate."
			::= { apnPortalRxPktsEntry 18 }

		
		-- 1.3.6.1.4.1.388.11.3.9.8.2.1.19
		apnPortalRxPktsAtMCS6 OBJECT-TYPE
			SYNTAX Counter32
			MAX-ACCESS read-only
			STATUS current
			DESCRIPTION
				"Number of pkts received via this Portal at MCS 6 rate."
			::= { apnPortalRxPktsEntry 19 }

		
		-- 1.3.6.1.4.1.388.11.3.9.8.2.1.20
		apnPortalRxPktsAtMCS7 OBJECT-TYPE
			SYNTAX Counter32
			MAX-ACCESS read-only
			STATUS current
			DESCRIPTION
				"Number of pkts received via this Portal at MCS 7 rate."
			::= { apnPortalRxPktsEntry 20 }

		
		-- 1.3.6.1.4.1.388.11.3.9.8.2.1.21
		apnPortalRxPktsAtMCS8 OBJECT-TYPE
			SYNTAX Counter32
			MAX-ACCESS read-only
			STATUS current
			DESCRIPTION
				"Number of pkts received via this Portal at MCS 8 rate."
			::= { apnPortalRxPktsEntry 21 }

		
		-- 1.3.6.1.4.1.388.11.3.9.8.2.1.22
		apnPortalRxPktsAtMCS9 OBJECT-TYPE
			SYNTAX Counter32
			MAX-ACCESS read-only
			STATUS current
			DESCRIPTION
				"Number of pkts received via this Portal at MCS 9 rate."
			::= { apnPortalRxPktsEntry 22 }

		
		-- 1.3.6.1.4.1.388.11.3.9.8.2.1.23
		apnPortalRxPktsAtMCS10 OBJECT-TYPE
			SYNTAX Counter32
			MAX-ACCESS read-only
			STATUS current
			DESCRIPTION
				"Number of pkts received via this Portal at MCS 10 rate."
			::= { apnPortalRxPktsEntry 23 }

		
		-- 1.3.6.1.4.1.388.11.3.9.8.2.1.24
		apnPortalRxPktsAtMCS11 OBJECT-TYPE
			SYNTAX Counter32
			MAX-ACCESS read-only
			STATUS current
			DESCRIPTION
				"Number of pkts received via this Portal at MCS 11 rate."
			::= { apnPortalRxPktsEntry 24 }

		
		-- 1.3.6.1.4.1.388.11.3.9.8.2.1.25
		apnPortalRxPktsAtMCS12 OBJECT-TYPE
			SYNTAX Counter32
			MAX-ACCESS read-only
			STATUS current
			DESCRIPTION
				"Number of pkts received via this Portal at MCS 12 rate."
			::= { apnPortalRxPktsEntry 25 }

		
		-- 1.3.6.1.4.1.388.11.3.9.8.2.1.26
		apnPortalRxPktsAtMCS13 OBJECT-TYPE
			SYNTAX Counter32
			MAX-ACCESS read-only
			STATUS current
			DESCRIPTION
				"Number of pkts received via this Portal at MCS 13 rate."
			::= { apnPortalRxPktsEntry 26 }

		
		-- 1.3.6.1.4.1.388.11.3.9.8.2.1.27
		apnPortalRxPktsAtMCS14 OBJECT-TYPE
			SYNTAX Counter32
			MAX-ACCESS read-only
			STATUS current
			DESCRIPTION
				"Number of pkts received via this Portal at MCS 14 rate."
			::= { apnPortalRxPktsEntry 27 }

		
		-- 1.3.6.1.4.1.388.11.3.9.8.2.1.28
		apnPortalRxPktsAtMCS15 OBJECT-TYPE
			SYNTAX Counter32
			MAX-ACCESS read-only
			STATUS current
			DESCRIPTION
				"Number of pkts received via this Portal at MCS 15 rate."
			::= { apnPortalRxPktsEntry 28 }

		
		-- 1.3.6.1.4.1.388.11.3.9.8.3
		apnPortalTxPktsTable OBJECT-TYPE
			SYNTAX SEQUENCE OF ApnPortalTxPktsEntry
			MAX-ACCESS not-accessible
			STATUS current
			DESCRIPTION
				"For each 802.11n Portal on the AP, this table 
				describes counts of packets transmitted at each 
				speed."
			::= { apnStats 3 }

		
		-- 1.3.6.1.4.1.388.11.3.9.8.3.1
		apnPortalTxPktsEntry OBJECT-TYPE
			SYNTAX ApnPortalTxPktsEntry
			MAX-ACCESS not-accessible
			STATUS current
			DESCRIPTION
				"An entry in the portal transmitted packets table."
			INDEX { ccPortalIndex }
			::= { apnPortalTxPktsTable 1 }

		
		ApnPortalTxPktsEntry ::=
			SEQUENCE { 
				apnPortalTxPktsAt1Mb
					Counter32,
				apnPortalTxPktsAt2Mb
					Counter32,
				apnPortalTxPktsAt5pt5Mb
					Counter32,
				apnPortalTxPktsAt6Mb
					Counter32,
				apnPortalTxPktsAt9Mb
					Counter32,
				apnPortalTxPktsAt11Mb
					Counter32,
				apnPortalTxPktsAt12Mb
					Counter32,
				apnPortalTxPktsAt18Mb
					Counter32,
				apnPortalTxPktsAt24Mb
					Counter32,
				apnPortalTxPktsAt36Mb
					Counter32,
				apnPortalTxPktsAt48Mb
					Counter32,
				apnPortalTxPktsAt54Mb
					Counter32,
				apnPortalTxPktsAtMCS0
					Counter32,
				apnPortalTxPktsAtMCS1
					Counter32,
				apnPortalTxPktsAtMCS2
					Counter32,
				apnPortalTxPktsAtMCS3
					Counter32,
				apnPortalTxPktsAtMCS4
					Counter32,
				apnPortalTxPktsAtMCS5
					Counter32,
				apnPortalTxPktsAtMCS6
					Counter32,
				apnPortalTxPktsAtMCS7
					Counter32,
				apnPortalTxPktsAtMCS8
					Counter32,
				apnPortalTxPktsAtMCS9
					Counter32,
				apnPortalTxPktsAtMCS10
					Counter32,
				apnPortalTxPktsAtMCS11
					Counter32,
				apnPortalTxPktsAtMCS12
					Counter32,
				apnPortalTxPktsAtMCS13
					Counter32,
				apnPortalTxPktsAtMCS14
					Counter32,
				apnPortalTxPktsAtMCS15
					Counter32
			 }

		-- 1.3.6.1.4.1.388.11.3.9.8.3.1.1
		apnPortalTxPktsAt1Mb OBJECT-TYPE
			SYNTAX Counter32
			MAX-ACCESS read-only
			STATUS current
			DESCRIPTION
				"Number of pkts transmitted via this Portal at 1 Mbps."
			::= { apnPortalTxPktsEntry 1 }

		
		-- 1.3.6.1.4.1.388.11.3.9.8.3.1.2
		apnPortalTxPktsAt2Mb OBJECT-TYPE
			SYNTAX Counter32
			MAX-ACCESS read-only
			STATUS current
			DESCRIPTION
				"Number of pkts transmitted via this Portal at 2 Mbps."
			::= { apnPortalTxPktsEntry 2 }

		
		-- 1.3.6.1.4.1.388.11.3.9.8.3.1.3
		apnPortalTxPktsAt5pt5Mb OBJECT-TYPE
			SYNTAX Counter32
			MAX-ACCESS read-only
			STATUS current
			DESCRIPTION
				"Number of pkts transmitted via this Portal at 5.5 Mbps."
			::= { apnPortalTxPktsEntry 3 }

		
		-- 1.3.6.1.4.1.388.11.3.9.8.3.1.4
		apnPortalTxPktsAt6Mb OBJECT-TYPE
			SYNTAX Counter32
			MAX-ACCESS read-only
			STATUS current
			DESCRIPTION
				"Number of pkts transmitted via this Portal at 6 Mbps."
			::= { apnPortalTxPktsEntry 4 }

		
		-- 1.3.6.1.4.1.388.11.3.9.8.3.1.5
		apnPortalTxPktsAt9Mb OBJECT-TYPE
			SYNTAX Counter32
			MAX-ACCESS read-only
			STATUS current
			DESCRIPTION
				"Number of pkts transmitted via this Portal at 9 Mbps."
			::= { apnPortalTxPktsEntry 5 }

		
		-- 1.3.6.1.4.1.388.11.3.9.8.3.1.6
		apnPortalTxPktsAt11Mb OBJECT-TYPE
			SYNTAX Counter32
			MAX-ACCESS read-only
			STATUS current
			DESCRIPTION
				"Number of pkts transmitted via this Portal at 11 Mbps."
			::= { apnPortalTxPktsEntry 6 }

		
		-- 1.3.6.1.4.1.388.11.3.9.8.3.1.7
		apnPortalTxPktsAt12Mb OBJECT-TYPE
			SYNTAX Counter32
			MAX-ACCESS read-only
			STATUS current
			DESCRIPTION
				"Number of pkts transmitted via this Portal at 12 Mbps."
			::= { apnPortalTxPktsEntry 7 }

		
		-- 1.3.6.1.4.1.388.11.3.9.8.3.1.8
		apnPortalTxPktsAt18Mb OBJECT-TYPE
			SYNTAX Counter32
			MAX-ACCESS read-only
			STATUS current
			DESCRIPTION
				"Number of pkts transmitted via this Portal at 18 Mbps."
			::= { apnPortalTxPktsEntry 8 }

		
		-- 1.3.6.1.4.1.388.11.3.9.8.3.1.9
		apnPortalTxPktsAt24Mb OBJECT-TYPE
			SYNTAX Counter32
			MAX-ACCESS read-only
			STATUS current
			DESCRIPTION
				"Number of pkts transmitted via this Portal at 24 Mbps."
			::= { apnPortalTxPktsEntry 9 }

		
		-- 1.3.6.1.4.1.388.11.3.9.8.3.1.10
		apnPortalTxPktsAt36Mb OBJECT-TYPE
			SYNTAX Counter32
			MAX-ACCESS read-only
			STATUS current
			DESCRIPTION
				"Number of pkts transmitted via this Portal at 36 Mbps."
			::= { apnPortalTxPktsEntry 10 }

		
		-- 1.3.6.1.4.1.388.11.3.9.8.3.1.11
		apnPortalTxPktsAt48Mb OBJECT-TYPE
			SYNTAX Counter32
			MAX-ACCESS read-only
			STATUS current
			DESCRIPTION
				"Number of pkts transmitted via this Portal at 48 Mbps."
			::= { apnPortalTxPktsEntry 11 }

		
		-- 1.3.6.1.4.1.388.11.3.9.8.3.1.12
		apnPortalTxPktsAt54Mb OBJECT-TYPE
			SYNTAX Counter32
			MAX-ACCESS read-only
			STATUS current
			DESCRIPTION
				"Number of pkts transmitted via this Portal at 54 Mbps."
			::= { apnPortalTxPktsEntry 12 }

		
		-- 1.3.6.1.4.1.388.11.3.9.8.3.1.13
		apnPortalTxPktsAtMCS0 OBJECT-TYPE
			SYNTAX Counter32
			MAX-ACCESS read-only
			STATUS current
			DESCRIPTION
				"Number of pkts transmitted via this Portal at MCS 0 rate."
			::= { apnPortalTxPktsEntry 13 }

		
		-- 1.3.6.1.4.1.388.11.3.9.8.3.1.14
		apnPortalTxPktsAtMCS1 OBJECT-TYPE
			SYNTAX Counter32
			MAX-ACCESS read-only
			STATUS current
			DESCRIPTION
				"Number of pkts transmitted via this Portal at MCS 1 rate."
			::= { apnPortalTxPktsEntry 14 }

		
		-- 1.3.6.1.4.1.388.11.3.9.8.3.1.15
		apnPortalTxPktsAtMCS2 OBJECT-TYPE
			SYNTAX Counter32
			MAX-ACCESS read-only
			STATUS current
			DESCRIPTION
				"Number of pkts transmitted via this Portal at MCS 2 rate."
			::= { apnPortalTxPktsEntry 15 }

		
		-- 1.3.6.1.4.1.388.11.3.9.8.3.1.16
		apnPortalTxPktsAtMCS3 OBJECT-TYPE
			SYNTAX Counter32
			MAX-ACCESS read-only
			STATUS current
			DESCRIPTION
				"Number of pkts transmitted via this Portal at MCS 3 rate."
			::= { apnPortalTxPktsEntry 16 }

		
		-- 1.3.6.1.4.1.388.11.3.9.8.3.1.17
		apnPortalTxPktsAtMCS4 OBJECT-TYPE
			SYNTAX Counter32
			MAX-ACCESS read-only
			STATUS current
			DESCRIPTION
				"Number of pkts transmitted via this Portal at MCS 4 rate."
			::= { apnPortalTxPktsEntry 17 }

		
		-- 1.3.6.1.4.1.388.11.3.9.8.3.1.18
		apnPortalTxPktsAtMCS5 OBJECT-TYPE
			SYNTAX Counter32
			MAX-ACCESS read-only
			STATUS current
			DESCRIPTION
				"Number of pkts transmitted via this Portal at MCS 5 rate."
			::= { apnPortalTxPktsEntry 18 }

		
		-- 1.3.6.1.4.1.388.11.3.9.8.3.1.19
		apnPortalTxPktsAtMCS6 OBJECT-TYPE
			SYNTAX Counter32
			MAX-ACCESS read-only
			STATUS current
			DESCRIPTION
				"Number of pkts transmitted via this Portal at MCS 6 rate."
			::= { apnPortalTxPktsEntry 19 }

		
		-- 1.3.6.1.4.1.388.11.3.9.8.3.1.20
		apnPortalTxPktsAtMCS7 OBJECT-TYPE
			SYNTAX Counter32
			MAX-ACCESS read-only
			STATUS current
			DESCRIPTION
				"Number of pkts transmitted via this Portal at MCS 7 rate."
			::= { apnPortalTxPktsEntry 20 }

		
		-- 1.3.6.1.4.1.388.11.3.9.8.3.1.21
		apnPortalTxPktsAtMCS8 OBJECT-TYPE
			SYNTAX Counter32
			MAX-ACCESS read-only
			STATUS current
			DESCRIPTION
				"Number of pkts transmitted via this Portal at MCS 8 rate."
			::= { apnPortalTxPktsEntry 21 }

		
		-- 1.3.6.1.4.1.388.11.3.9.8.3.1.22
		apnPortalTxPktsAtMCS9 OBJECT-TYPE
			SYNTAX Counter32
			MAX-ACCESS read-only
			STATUS current
			DESCRIPTION
				"Number of pkts transmitted via this Portal at MCS 9 rate."
			::= { apnPortalTxPktsEntry 22 }

		
		-- 1.3.6.1.4.1.388.11.3.9.8.3.1.23
		apnPortalTxPktsAtMCS10 OBJECT-TYPE
			SYNTAX Counter32
			MAX-ACCESS read-only
			STATUS current
			DESCRIPTION
				"Number of pkts transmitted via this Portal at MCS 10 rate."
			::= { apnPortalTxPktsEntry 23 }

		
		-- 1.3.6.1.4.1.388.11.3.9.8.3.1.24
		apnPortalTxPktsAtMCS11 OBJECT-TYPE
			SYNTAX Counter32
			MAX-ACCESS read-only
			STATUS current
			DESCRIPTION
				"Number of pkts transmitted via this Portal at MCS 11 rate."
			::= { apnPortalTxPktsEntry 24 }

		
		-- 1.3.6.1.4.1.388.11.3.9.8.3.1.25
		apnPortalTxPktsAtMCS12 OBJECT-TYPE
			SYNTAX Counter32
			MAX-ACCESS read-only
			STATUS current
			DESCRIPTION
				"Number of pkts transmitted via this Portal at MCS 12 rate."
			::= { apnPortalTxPktsEntry 25 }

		
		-- 1.3.6.1.4.1.388.11.3.9.8.3.1.26
		apnPortalTxPktsAtMCS13 OBJECT-TYPE
			SYNTAX Counter32
			MAX-ACCESS read-only
			STATUS current
			DESCRIPTION
				"Number of pkts transmitted via this Portal at MCS 13 rate."
			::= { apnPortalTxPktsEntry 26 }

		
		-- 1.3.6.1.4.1.388.11.3.9.8.3.1.27
		apnPortalTxPktsAtMCS14 OBJECT-TYPE
			SYNTAX Counter32
			MAX-ACCESS read-only
			STATUS current
			DESCRIPTION
				"Number of pkts transmitted via this Portal at MCS 14 rate."
			::= { apnPortalTxPktsEntry 27 }

		
		-- 1.3.6.1.4.1.388.11.3.9.8.3.1.28
		apnPortalTxPktsAtMCS15 OBJECT-TYPE
			SYNTAX Counter32
			MAX-ACCESS read-only
			STATUS current
			DESCRIPTION
				"Number of pkts transmitted via this Portal at MCS 15 rate."
			::= { apnPortalTxPktsEntry 28 }

		
		-- 1.3.6.1.4.1.388.11.3.9.8.4
		apnPortalRxOctetsTable OBJECT-TYPE
			SYNTAX SEQUENCE OF ApnPortalRxOctetsEntry
			MAX-ACCESS not-accessible
			STATUS current
			DESCRIPTION
				"For each 802.11n Portal on this AP, this table 
				describes counts of octets received at each 
				speed."
			::= { apnStats 4 }

		
		-- 1.3.6.1.4.1.388.11.3.9.8.4.1
		apnPortalRxOctetsEntry OBJECT-TYPE
			SYNTAX ApnPortalRxOctetsEntry
			MAX-ACCESS not-accessible
			STATUS current
			DESCRIPTION
				"An entry in the portal received octets table."
			INDEX { ccPortalIndex }
			::= { apnPortalRxOctetsTable 1 }

		
		ApnPortalRxOctetsEntry ::=
			SEQUENCE { 
				apnPortalRxOctetsAt1Mb
					Counter32,
				apnPortalRxOctetsAt2Mb
					Counter32,
				apnPortalRxOctetsAt5pt5Mb
					Counter32,
				apnPortalRxOctetsAt6Mb
					Counter32,
				apnPortalRxOctetsAt9Mb
					Counter32,
				apnPortalRxOctetsAt11Mb
					Counter32,
				apnPortalRxOctetsAt12Mb
					Counter32,
				apnPortalRxOctetsAt18Mb
					Counter32,
				apnPortalRxOctetsAt24Mb
					Counter32,
				apnPortalRxOctetsAt36Mb
					Counter32,
				apnPortalRxOctetsAt48Mb
					Counter32,
				apnPortalRxOctetsAt54Mb
					Counter32,
				apnPortalRxOctetsAtMCS0
					Counter32,
				apnPortalRxOctetsAtMCS1
					Counter32,
				apnPortalRxOctetsAtMCS2
					Counter32,
				apnPortalRxOctetsAtMCS3
					Counter32,
				apnPortalRxOctetsAtMCS4
					Counter32,
				apnPortalRxOctetsAtMCS5
					Counter32,
				apnPortalRxOctetsAtMCS6
					Counter32,
				apnPortalRxOctetsAtMCS7
					Counter32,
				apnPortalRxOctetsAtMCS8
					Counter32,
				apnPortalRxOctetsAtMCS9
					Counter32,
				apnPortalRxOctetsAtMCS10
					Counter32,
				apnPortalRxOctetsAtMCS11
					Counter32,
				apnPortalRxOctetsAtMCS12
					Counter32,
				apnPortalRxOctetsAtMCS13
					Counter32,
				apnPortalRxOctetsAtMCS14
					Counter32,
				apnPortalRxOctetsAtMCS15
					Counter32
			 }

		-- 1.3.6.1.4.1.388.11.3.9.8.4.1.1
		apnPortalRxOctetsAt1Mb OBJECT-TYPE
			SYNTAX Counter32
			MAX-ACCESS read-only
			STATUS current
			DESCRIPTION
				"Number of octets received via this Portal at 1 Mbps."
			::= { apnPortalRxOctetsEntry 1 }

		
		-- 1.3.6.1.4.1.388.11.3.9.8.4.1.2
		apnPortalRxOctetsAt2Mb OBJECT-TYPE
			SYNTAX Counter32
			MAX-ACCESS read-only
			STATUS current
			DESCRIPTION
				"Number of octets received via this Portal at 2 Mbps."
			::= { apnPortalRxOctetsEntry 2 }

		
		-- 1.3.6.1.4.1.388.11.3.9.8.4.1.3
		apnPortalRxOctetsAt5pt5Mb OBJECT-TYPE
			SYNTAX Counter32
			MAX-ACCESS read-only
			STATUS current
			DESCRIPTION
				"Number of octets received via this Portal at 5.5 Mbps."
			::= { apnPortalRxOctetsEntry 3 }

		
		-- 1.3.6.1.4.1.388.11.3.9.8.4.1.4
		apnPortalRxOctetsAt6Mb OBJECT-TYPE
			SYNTAX Counter32
			MAX-ACCESS read-only
			STATUS current
			DESCRIPTION
				"Number of octets received via this Portal at 6 Mbps."
			::= { apnPortalRxOctetsEntry 4 }

		
		-- 1.3.6.1.4.1.388.11.3.9.8.4.1.5
		apnPortalRxOctetsAt9Mb OBJECT-TYPE
			SYNTAX Counter32
			MAX-ACCESS read-only
			STATUS current
			DESCRIPTION
				"Number of octets received via this Portal at 9 Mbps."
			::= { apnPortalRxOctetsEntry 5 }

		
		-- 1.3.6.1.4.1.388.11.3.9.8.4.1.6
		apnPortalRxOctetsAt11Mb OBJECT-TYPE
			SYNTAX Counter32
			MAX-ACCESS read-only
			STATUS current
			DESCRIPTION
				"Number of octets received via this Portal at 11 Mbps."
			::= { apnPortalRxOctetsEntry 6 }

		
		-- 1.3.6.1.4.1.388.11.3.9.8.4.1.7
		apnPortalRxOctetsAt12Mb OBJECT-TYPE
			SYNTAX Counter32
			MAX-ACCESS read-only
			STATUS current
			DESCRIPTION
				"Number of octets received via this Portal at 12 Mbps."
			::= { apnPortalRxOctetsEntry 7 }

		
		-- 1.3.6.1.4.1.388.11.3.9.8.4.1.8
		apnPortalRxOctetsAt18Mb OBJECT-TYPE
			SYNTAX Counter32
			MAX-ACCESS read-only
			STATUS current
			DESCRIPTION
				"Number of octets received via this Portal at 18 Mbps."
			::= { apnPortalRxOctetsEntry 8 }

		
		-- 1.3.6.1.4.1.388.11.3.9.8.4.1.9
		apnPortalRxOctetsAt24Mb OBJECT-TYPE
			SYNTAX Counter32
			MAX-ACCESS read-only
			STATUS current
			DESCRIPTION
				"Number of octets received via this Portal at 24 Mbps."
			::= { apnPortalRxOctetsEntry 9 }

		
		-- 1.3.6.1.4.1.388.11.3.9.8.4.1.10
		apnPortalRxOctetsAt36Mb OBJECT-TYPE
			SYNTAX Counter32
			MAX-ACCESS read-only
			STATUS current
			DESCRIPTION
				"Number of octets received via this Portal at 36 Mbps."
			::= { apnPortalRxOctetsEntry 10 }

		
		-- 1.3.6.1.4.1.388.11.3.9.8.4.1.11
		apnPortalRxOctetsAt48Mb OBJECT-TYPE
			SYNTAX Counter32
			MAX-ACCESS read-only
			STATUS current
			DESCRIPTION
				"Number of octets received via this Portal at 48 Mbps."
			::= { apnPortalRxOctetsEntry 11 }

		
		-- 1.3.6.1.4.1.388.11.3.9.8.4.1.12
		apnPortalRxOctetsAt54Mb OBJECT-TYPE
			SYNTAX Counter32
			MAX-ACCESS read-only
			STATUS current
			DESCRIPTION
				"Number of octets received via this Portal at 54 Mbps."
			::= { apnPortalRxOctetsEntry 12 }

		
		-- 1.3.6.1.4.1.388.11.3.9.8.4.1.13
		apnPortalRxOctetsAtMCS0 OBJECT-TYPE
			SYNTAX Counter32
			MAX-ACCESS read-only
			STATUS current
			DESCRIPTION
				"Number of octets received via this Portal at MCS 0 rate."
			::= { apnPortalRxOctetsEntry 13 }

		
		-- 1.3.6.1.4.1.388.11.3.9.8.4.1.14
		apnPortalRxOctetsAtMCS1 OBJECT-TYPE
			SYNTAX Counter32
			MAX-ACCESS read-only
			STATUS current
			DESCRIPTION
				"Number of octets received via this Portal at MCS 1 rate."
			::= { apnPortalRxOctetsEntry 14 }

		
		-- 1.3.6.1.4.1.388.11.3.9.8.4.1.15
		apnPortalRxOctetsAtMCS2 OBJECT-TYPE
			SYNTAX Counter32
			MAX-ACCESS read-only
			STATUS current
			DESCRIPTION
				"Number of octets received via this Portal at MCS 2 rate."
			::= { apnPortalRxOctetsEntry 15 }

		
		-- 1.3.6.1.4.1.388.11.3.9.8.4.1.16
		apnPortalRxOctetsAtMCS3 OBJECT-TYPE
			SYNTAX Counter32
			MAX-ACCESS read-only
			STATUS current
			DESCRIPTION
				"Number of octets received via this Portal at MCS 3 rate."
			::= { apnPortalRxOctetsEntry 16 }

		
		-- 1.3.6.1.4.1.388.11.3.9.8.4.1.17
		apnPortalRxOctetsAtMCS4 OBJECT-TYPE
			SYNTAX Counter32
			MAX-ACCESS read-only
			STATUS current
			DESCRIPTION
				"Number of octets received via this Portal at MCS 4 rate."
			::= { apnPortalRxOctetsEntry 17 }

		
		-- 1.3.6.1.4.1.388.11.3.9.8.4.1.18
		apnPortalRxOctetsAtMCS5 OBJECT-TYPE
			SYNTAX Counter32
			MAX-ACCESS read-only
			STATUS current
			DESCRIPTION
				"Number of octets received via this Portal at MCS 5 rate."
			::= { apnPortalRxOctetsEntry 18 }

		
		-- 1.3.6.1.4.1.388.11.3.9.8.4.1.19
		apnPortalRxOctetsAtMCS6 OBJECT-TYPE
			SYNTAX Counter32
			MAX-ACCESS read-only
			STATUS current
			DESCRIPTION
				"Number of octets received via this Portal at MCS 6 rate."
			::= { apnPortalRxOctetsEntry 19 }

		
		-- 1.3.6.1.4.1.388.11.3.9.8.4.1.20
		apnPortalRxOctetsAtMCS7 OBJECT-TYPE
			SYNTAX Counter32
			MAX-ACCESS read-only
			STATUS current
			DESCRIPTION
				"Number of octets received via this Portal at MCS 7 rate."
			::= { apnPortalRxOctetsEntry 20 }

		
		-- 1.3.6.1.4.1.388.11.3.9.8.4.1.21
		apnPortalRxOctetsAtMCS8 OBJECT-TYPE
			SYNTAX Counter32
			MAX-ACCESS read-only
			STATUS current
			DESCRIPTION
				"Number of octets received via this Portal at MCS 8 rate."
			::= { apnPortalRxOctetsEntry 21 }

		
		-- 1.3.6.1.4.1.388.11.3.9.8.4.1.22
		apnPortalRxOctetsAtMCS9 OBJECT-TYPE
			SYNTAX Counter32
			MAX-ACCESS read-only
			STATUS current
			DESCRIPTION
				"Number of octets received via this Portal at MCS 9 rate."
			::= { apnPortalRxOctetsEntry 22 }

		
		-- 1.3.6.1.4.1.388.11.3.9.8.4.1.23
		apnPortalRxOctetsAtMCS10 OBJECT-TYPE
			SYNTAX Counter32
			MAX-ACCESS read-only
			STATUS current
			DESCRIPTION
				"Number of octets received via this Portal at MCS 10 rate."
			::= { apnPortalRxOctetsEntry 23 }

		
		-- 1.3.6.1.4.1.388.11.3.9.8.4.1.24
		apnPortalRxOctetsAtMCS11 OBJECT-TYPE
			SYNTAX Counter32
			MAX-ACCESS read-only
			STATUS current
			DESCRIPTION
				"Number of octets received via this Portal at MCS 11 rate."
			::= { apnPortalRxOctetsEntry 24 }

		
		-- 1.3.6.1.4.1.388.11.3.9.8.4.1.25
		apnPortalRxOctetsAtMCS12 OBJECT-TYPE
			SYNTAX Counter32
			MAX-ACCESS read-only
			STATUS current
			DESCRIPTION
				"Number of octets received via this Portal at MCS 12 rate."
			::= { apnPortalRxOctetsEntry 25 }

		
		-- 1.3.6.1.4.1.388.11.3.9.8.4.1.26
		apnPortalRxOctetsAtMCS13 OBJECT-TYPE
			SYNTAX Counter32
			MAX-ACCESS read-only
			STATUS current
			DESCRIPTION
				"Number of octets received via this Portal at MCS 13 rate."
			::= { apnPortalRxOctetsEntry 26 }

		
		-- 1.3.6.1.4.1.388.11.3.9.8.4.1.27
		apnPortalRxOctetsAtMCS14 OBJECT-TYPE
			SYNTAX Counter32
			MAX-ACCESS read-only
			STATUS current
			DESCRIPTION
				"Description.Number of octets received via this Portal at MCS 14 rate."
			::= { apnPortalRxOctetsEntry 27 }

		
		-- 1.3.6.1.4.1.388.11.3.9.8.4.1.28
		apnPortalRxOctetsAtMCS15 OBJECT-TYPE
			SYNTAX Counter32
			MAX-ACCESS read-only
			STATUS current
			DESCRIPTION
				"Number of octets received via this Portal at MCS 15 rate."
			::= { apnPortalRxOctetsEntry 28 }

		
		-- 1.3.6.1.4.1.388.11.3.9.8.5
		apnPortalTxOctetsTable OBJECT-TYPE
			SYNTAX SEQUENCE OF ApnPortalTxOctetsEntry
			MAX-ACCESS not-accessible
			STATUS current
			DESCRIPTION
				"For each 802.11n Portal on this AP, this table 
				describes counts of octets transmitted at each 
				speed."
			::= { apnStats 5 }

		
		-- 1.3.6.1.4.1.388.11.3.9.8.5.1
		apnPortalTxOctetsEntry OBJECT-TYPE
			SYNTAX ApnPortalTxOctetsEntry
			MAX-ACCESS not-accessible
			STATUS current
			DESCRIPTION
				"An entry in the portal transmitted octets table."
			INDEX { ccPortalIndex }
			::= { apnPortalTxOctetsTable 1 }

		
		ApnPortalTxOctetsEntry ::=
			SEQUENCE { 
				apnPortalTxOctetsAt1Mb
					Counter32,
				apnPortalTxOctetsAt2Mb
					Counter32,
				apnPortalTxOctetsAt5pt5Mb
					Counter32,
				apnPortalTxOctetsAt6Mb
					Counter32,
				apnPortalTxOctetsAt9Mb
					Counter32,
				apnPortalTxOctetsAt11Mb
					Counter32,
				apnPortalTxOctetsAt12Mb
					Counter32,
				apnPortalTxOctetsAt18Mb
					Counter32,
				apnPortalTxOctetsAt24Mb
					Counter32,
				apnPortalTxOctetsAt36Mb
					Counter32,
				apnPortalTxOctetsAt48Mb
					Counter32,
				apnPortalTxOctetsAt54Mb
					Counter32,
				apnPortalTxOctetsAtMCS0
					Counter32,
				apnPortalTxOctetsAtMCS1
					Counter32,
				apnPortalTxOctetsAtMCS2
					Counter32,
				apnPortalTxOctetsAtMCS3
					Counter32,
				apnPortalTxOctetsAtMCS4
					Counter32,
				apnPortalTxOctetsAtMCS5
					Counter32,
				apnPortalTxOctetsAtMCS6
					Counter32,
				apnPortalTxOctetsAtMCS7
					Counter32,
				apnPortalTxOctetsAtMCS8
					Counter32,
				apnPortalTxOctetsAtMCS9
					Counter32,
				apnPortalTxOctetsAtMCS10
					Counter32,
				apnPortalTxOctetsAtMCS11
					Counter32,
				apnPortalTxOctetsAtMCS12
					Counter32,
				apnPortalTxOctetsAtMCS13
					Counter32,
				apnPortalTxOctetsAtMCS14
					Counter32,
				apnPortalTxOctetsAtMCS15
					Counter32
			 }

		-- 1.3.6.1.4.1.388.11.3.9.8.5.1.2
		apnPortalTxOctetsAt1Mb OBJECT-TYPE
			SYNTAX Counter32
			MAX-ACCESS read-only
			STATUS current
			DESCRIPTION
				"Number of octets transmitted via this Portal at 1 Mbps."
			::= { apnPortalTxOctetsEntry 2 }

		
		-- 1.3.6.1.4.1.388.11.3.9.8.5.1.3
		apnPortalTxOctetsAt2Mb OBJECT-TYPE
			SYNTAX Counter32
			MAX-ACCESS read-only
			STATUS current
			DESCRIPTION
				"Number of octets transmitted via this Portal at 2 Mbps."
			::= { apnPortalTxOctetsEntry 3 }

		
		-- 1.3.6.1.4.1.388.11.3.9.8.5.1.4
		apnPortalTxOctetsAt5pt5Mb OBJECT-TYPE
			SYNTAX Counter32
			MAX-ACCESS read-only
			STATUS current
			DESCRIPTION
				"Number of octets transmitted via this Portal at 5.5 Mbps."
			::= { apnPortalTxOctetsEntry 4 }

		
		-- 1.3.6.1.4.1.388.11.3.9.8.5.1.5
		apnPortalTxOctetsAt6Mb OBJECT-TYPE
			SYNTAX Counter32
			MAX-ACCESS read-only
			STATUS current
			DESCRIPTION
				"Number of octets transmitted via this Portal at 6 Mbps."
			::= { apnPortalTxOctetsEntry 5 }

		
		-- 1.3.6.1.4.1.388.11.3.9.8.5.1.6
		apnPortalTxOctetsAt9Mb OBJECT-TYPE
			SYNTAX Counter32
			MAX-ACCESS read-only
			STATUS current
			DESCRIPTION
				"Number of octets transmitted via this Portal at 9 Mbps."
			::= { apnPortalTxOctetsEntry 6 }

		
		-- 1.3.6.1.4.1.388.11.3.9.8.5.1.7
		apnPortalTxOctetsAt11Mb OBJECT-TYPE
			SYNTAX Counter32
			MAX-ACCESS read-only
			STATUS current
			DESCRIPTION
				"Number of octets transmitted via this Portal at 11 Mbps."
			::= { apnPortalTxOctetsEntry 7 }

		
		-- 1.3.6.1.4.1.388.11.3.9.8.5.1.8
		apnPortalTxOctetsAt12Mb OBJECT-TYPE
			SYNTAX Counter32
			MAX-ACCESS read-only
			STATUS current
			DESCRIPTION
				"Number of octets transmitted via this Portal at 12 Mbps."
			::= { apnPortalTxOctetsEntry 8 }

		
		-- 1.3.6.1.4.1.388.11.3.9.8.5.1.9
		apnPortalTxOctetsAt18Mb OBJECT-TYPE
			SYNTAX Counter32
			MAX-ACCESS read-only
			STATUS current
			DESCRIPTION
				"Number of octets transmitted via this Portal at 18 Mbps."
			::= { apnPortalTxOctetsEntry 9 }

		
		-- 1.3.6.1.4.1.388.11.3.9.8.5.1.10
		apnPortalTxOctetsAt24Mb OBJECT-TYPE
			SYNTAX Counter32
			MAX-ACCESS read-only
			STATUS current
			DESCRIPTION
				"Number of octets transmitted via this Portal at 24 Mbps."
			::= { apnPortalTxOctetsEntry 10 }

		
		-- 1.3.6.1.4.1.388.11.3.9.8.5.1.11
		apnPortalTxOctetsAt36Mb OBJECT-TYPE
			SYNTAX Counter32
			MAX-ACCESS read-only
			STATUS current
			DESCRIPTION
				"Number of octets transmitted via this Portal at 36 Mbps."
			::= { apnPortalTxOctetsEntry 11 }

		
		-- 1.3.6.1.4.1.388.11.3.9.8.5.1.12
		apnPortalTxOctetsAt48Mb OBJECT-TYPE
			SYNTAX Counter32
			MAX-ACCESS read-only
			STATUS current
			DESCRIPTION
				"Number of octets transmitted via this Portal at 48 Mbps."
			::= { apnPortalTxOctetsEntry 12 }

		
		-- 1.3.6.1.4.1.388.11.3.9.8.5.1.13
		apnPortalTxOctetsAt54Mb OBJECT-TYPE
			SYNTAX Counter32
			MAX-ACCESS read-only
			STATUS current
			DESCRIPTION
				"Number of octets transmitted via this Portal at 54 Mbps."
			::= { apnPortalTxOctetsEntry 13 }

		
		-- 1.3.6.1.4.1.388.11.3.9.8.5.1.14
		apnPortalTxOctetsAtMCS0 OBJECT-TYPE
			SYNTAX Counter32
			MAX-ACCESS read-only
			STATUS current
			DESCRIPTION
				"Number of octets transmitted via this Portal at MCS 0 rate."
			::= { apnPortalTxOctetsEntry 14 }

		
		-- 1.3.6.1.4.1.388.11.3.9.8.5.1.15
		apnPortalTxOctetsAtMCS1 OBJECT-TYPE
			SYNTAX Counter32
			MAX-ACCESS read-only
			STATUS current
			DESCRIPTION
				"Number of octets transmitted via this Portal at MCS 1 rate."
			::= { apnPortalTxOctetsEntry 15 }

		
		-- 1.3.6.1.4.1.388.11.3.9.8.5.1.16
		apnPortalTxOctetsAtMCS2 OBJECT-TYPE
			SYNTAX Counter32
			MAX-ACCESS read-only
			STATUS current
			DESCRIPTION
				"Number of octets transmitted via this Portal at MCS 2 rate."
			::= { apnPortalTxOctetsEntry 16 }

		
		-- 1.3.6.1.4.1.388.11.3.9.8.5.1.17
		apnPortalTxOctetsAtMCS3 OBJECT-TYPE
			SYNTAX Counter32
			MAX-ACCESS read-only
			STATUS current
			DESCRIPTION
				"Number of octets transmitted via this Portal at MCS 3 rate."
			::= { apnPortalTxOctetsEntry 17 }

		
		-- 1.3.6.1.4.1.388.11.3.9.8.5.1.18
		apnPortalTxOctetsAtMCS4 OBJECT-TYPE
			SYNTAX Counter32
			MAX-ACCESS read-only
			STATUS current
			DESCRIPTION
				"Number of octets transmitted via this Portal at MCS 4 rate."
			::= { apnPortalTxOctetsEntry 18 }

		
		-- 1.3.6.1.4.1.388.11.3.9.8.5.1.19
		apnPortalTxOctetsAtMCS5 OBJECT-TYPE
			SYNTAX Counter32
			MAX-ACCESS read-only
			STATUS current
			DESCRIPTION
				"Number of octets transmitted via this Portal at MCS 5 rate."
			::= { apnPortalTxOctetsEntry 19 }

		
		-- 1.3.6.1.4.1.388.11.3.9.8.5.1.20
		apnPortalTxOctetsAtMCS6 OBJECT-TYPE
			SYNTAX Counter32
			MAX-ACCESS read-only
			STATUS current
			DESCRIPTION
				"Number of octets transmitted via this Portal at MCS 6 rate."
			::= { apnPortalTxOctetsEntry 20 }

		
		-- 1.3.6.1.4.1.388.11.3.9.8.5.1.21
		apnPortalTxOctetsAtMCS7 OBJECT-TYPE
			SYNTAX Counter32
			MAX-ACCESS read-only
			STATUS current
			DESCRIPTION
				"Number of octets transmitted via this Portal at MCS 7 rate."
			::= { apnPortalTxOctetsEntry 21 }

		
		-- 1.3.6.1.4.1.388.11.3.9.8.5.1.22
		apnPortalTxOctetsAtMCS8 OBJECT-TYPE
			SYNTAX Counter32
			MAX-ACCESS read-only
			STATUS current
			DESCRIPTION
				"Number of octets transmitted via this Portal at MCS 8 rate."
			::= { apnPortalTxOctetsEntry 22 }

		
		-- 1.3.6.1.4.1.388.11.3.9.8.5.1.23
		apnPortalTxOctetsAtMCS9 OBJECT-TYPE
			SYNTAX Counter32
			MAX-ACCESS read-only
			STATUS current
			DESCRIPTION
				"Number of octets transmitted via this Portal at MCS 9 rate."
			::= { apnPortalTxOctetsEntry 23 }

		
		-- 1.3.6.1.4.1.388.11.3.9.8.5.1.24
		apnPortalTxOctetsAtMCS10 OBJECT-TYPE
			SYNTAX Counter32
			MAX-ACCESS read-only
			STATUS current
			DESCRIPTION
				"Number of octets transmitted via this Portal at MCS 10 rate."
			::= { apnPortalTxOctetsEntry 24 }

		
		-- 1.3.6.1.4.1.388.11.3.9.8.5.1.25
		apnPortalTxOctetsAtMCS11 OBJECT-TYPE
			SYNTAX Counter32
			MAX-ACCESS read-only
			STATUS current
			DESCRIPTION
				"Number of octets transmitted via this Portal at MCS 11 rate."
			::= { apnPortalTxOctetsEntry 25 }

		
		-- 1.3.6.1.4.1.388.11.3.9.8.5.1.26
		apnPortalTxOctetsAtMCS12 OBJECT-TYPE
			SYNTAX Counter32
			MAX-ACCESS read-only
			STATUS current
			DESCRIPTION
				"Number of octets transmitted via this Portal at MCS 12 rate."
			::= { apnPortalTxOctetsEntry 26 }

		
		-- 1.3.6.1.4.1.388.11.3.9.8.5.1.27
		apnPortalTxOctetsAtMCS13 OBJECT-TYPE
			SYNTAX Counter32
			MAX-ACCESS read-only
			STATUS current
			DESCRIPTION
				"Number of octets transmitted via this Portal at MCS 13 rate."
			::= { apnPortalTxOctetsEntry 27 }

		
		-- 1.3.6.1.4.1.388.11.3.9.8.5.1.28
		apnPortalTxOctetsAtMCS14 OBJECT-TYPE
			SYNTAX Counter32
			MAX-ACCESS read-only
			STATUS current
			DESCRIPTION
				"Number of octets transmitted via this Portal at MCS 14 rate."
			::= { apnPortalTxOctetsEntry 28 }

		
		-- 1.3.6.1.4.1.388.11.3.9.8.5.1.29
		apnPortalTxOctetsAtMCS15 OBJECT-TYPE
			SYNTAX Counter32
			MAX-ACCESS read-only
			STATUS current
			DESCRIPTION
				"Number of octets transmitted via this Portal at MCS 15 rate."
			::= { apnPortalTxOctetsEntry 29 }

		
		-- 1.3.6.1.4.1.388.11.3.9.8.6
		apnMuRxPktsTable OBJECT-TYPE
			SYNTAX SEQUENCE OF ApnMuRxPktsEntry
			MAX-ACCESS not-accessible
			STATUS current
			DESCRIPTION
				"For each mobile unit associated to an 802.11n Portal 
				on the AP, this table describes counts of packets 
				received at each speed."
			::= { apnStats 6 }

		
		-- 1.3.6.1.4.1.388.11.3.9.8.6.1
		apnMuRxPktsEntry OBJECT-TYPE
			SYNTAX ApnMuRxPktsEntry
			MAX-ACCESS not-accessible
			STATUS current
			DESCRIPTION
				" "
			INDEX { ccMuMac }
			::= { apnMuRxPktsTable 1 }

		
		ApnMuRxPktsEntry ::=
			SEQUENCE { 
				apnMuRxPktsAt1Mb
					Counter32,
				apnMuRxPktsAt2Mb
					Counter32,
				apnMuRxPktsAt5pt5Mb
					Counter32,
				apnMuRxPktsAt6Mb
					Counter32,
				apnMuRxPktsAt9Mb
					Counter32,
				apnMuRxPktsAt11Mb
					Counter32,
				apnMuRxPktsAt12Mb
					Counter32,
				apnMuRxPktsAt18Mb
					Counter32,
				apnMuRxPktsAt24Mb
					Counter32,
				apnMuRxPktsAt36Mb
					Counter32,
				apnMuRxPktsAt48Mb
					Counter32,
				apnMuRxPktsAt54Mb
					Counter32,
				apnMuRxPktsAtMCS0
					Counter32,
				apnMuRxPktsAtMCS1
					Counter32,
				apnMuRxPktsAtMCS2
					Counter32,
				apnMuRxPktsAtMCS3
					Counter32,
				apnMuRxPktsAtMCS4
					Counter32,
				apnMuRxPktsAtMCS5
					Counter32,
				apnMuRxPktsAtMCS6
					Counter32,
				apnMuRxPktsAtMCS7
					Counter32,
				apnMuRxPktsAtMCS8
					Counter32,
				apnMuRxPktsAtMCS9
					Counter32,
				apnMuRxPktsAtMCS10
					Counter32,
				apnMuRxPktsAtMCS11
					Counter32,
				apnMuRxPktsAtMCS12
					Counter32,
				apnMuRxPktsAtMCS13
					Counter32,
				apnMuRxPktsAtMCS14
					Counter32,
				apnMuRxPktsAtMCS15
					Counter32
			 }

		-- 1.3.6.1.4.1.388.11.3.9.8.6.1.1
		apnMuRxPktsAt1Mb OBJECT-TYPE
			SYNTAX Counter32
			MAX-ACCESS read-only
			STATUS current
			DESCRIPTION
				"Number of pkts received via this Portal at 1 and 2 Mbps."
			::= { apnMuRxPktsEntry 1 }

		
		-- 1.3.6.1.4.1.388.11.3.9.8.6.1.2
		apnMuRxPktsAt2Mb OBJECT-TYPE
			SYNTAX Counter32
			MAX-ACCESS read-only
			STATUS current
			DESCRIPTION
				"Number of pkts received via this Portal at 1, 2, 5.5 and 11 Mbps."
			::= { apnMuRxPktsEntry 2 }

		
		-- 1.3.6.1.4.1.388.11.3.9.8.6.1.3
		apnMuRxPktsAt5pt5Mb OBJECT-TYPE
			SYNTAX Counter32
			MAX-ACCESS read-only
			STATUS current
			DESCRIPTION
				"Number of pkts received via this Portal at 1, 2, 5.5 and 11 Mbps, and, 
				6, 12 and 24 Mbps."
			::= { apnMuRxPktsEntry 3 }

		
		-- 1.3.6.1.4.1.388.11.3.9.8.6.1.4
		apnMuRxPktsAt6Mb OBJECT-TYPE
			SYNTAX Counter32
			MAX-ACCESS read-only
			STATUS current
			DESCRIPTION
				"Number of pkts received via this Portal at 1, 2, 5.5 and 11 Mbps, and, 
				6, 12 and 24 Mbps as well as at MCS 0 to 7 rates."
			::= { apnMuRxPktsEntry 4 }

		
		-- 1.3.6.1.4.1.388.11.3.9.8.6.1.5
		apnMuRxPktsAt9Mb OBJECT-TYPE
			SYNTAX Counter32
			MAX-ACCESS read-only
			STATUS current
			DESCRIPTION
				"Number of pkts received via this Portal at 6, 12 and 24 Mbps."
			::= { apnMuRxPktsEntry 5 }

		
		-- 1.3.6.1.4.1.388.11.3.9.8.6.1.6
		apnMuRxPktsAt11Mb OBJECT-TYPE
			SYNTAX Counter32
			MAX-ACCESS read-only
			STATUS current
			DESCRIPTION
				"Number of pkts received via this Portal at 6, 12 and 24 Mbps as well as 
				at MCS 0 to 7 rates."
			::= { apnMuRxPktsEntry 6 }

		
		-- 1.3.6.1.4.1.388.11.3.9.8.6.1.7
		apnMuRxPktsAt12Mb OBJECT-TYPE
			SYNTAX Counter32
			MAX-ACCESS read-only
			STATUS current
			DESCRIPTION
				"Number of pkts received via this Portal at MCS 0 to 7 rates."
			::= { apnMuRxPktsEntry 7 }

		
		-- 1.3.6.1.4.1.388.11.3.9.8.6.1.8
		apnMuRxPktsAt18Mb OBJECT-TYPE
			SYNTAX Counter32
			MAX-ACCESS read-only
			STATUS current
			DESCRIPTION
				"Description."
			::= { apnMuRxPktsEntry 8 }

		
		-- 1.3.6.1.4.1.388.11.3.9.8.6.1.9
		apnMuRxPktsAt24Mb OBJECT-TYPE
			SYNTAX Counter32
			MAX-ACCESS read-only
			STATUS current
			DESCRIPTION
				"Description."
			::= { apnMuRxPktsEntry 9 }

		
		-- 1.3.6.1.4.1.388.11.3.9.8.6.1.10
		apnMuRxPktsAt36Mb OBJECT-TYPE
			SYNTAX Counter32
			MAX-ACCESS read-only
			STATUS current
			DESCRIPTION
				"Description."
			::= { apnMuRxPktsEntry 10 }

		
		-- 1.3.6.1.4.1.388.11.3.9.8.6.1.11
		apnMuRxPktsAt48Mb OBJECT-TYPE
			SYNTAX Counter32
			MAX-ACCESS read-only
			STATUS current
			DESCRIPTION
				"Description."
			::= { apnMuRxPktsEntry 11 }

		
		-- 1.3.6.1.4.1.388.11.3.9.8.6.1.12
		apnMuRxPktsAt54Mb OBJECT-TYPE
			SYNTAX Counter32
			MAX-ACCESS read-only
			STATUS current
			DESCRIPTION
				"Description."
			::= { apnMuRxPktsEntry 12 }

		
		-- 1.3.6.1.4.1.388.11.3.9.8.6.1.13
		apnMuRxPktsAtMCS0 OBJECT-TYPE
			SYNTAX Counter32
			MAX-ACCESS read-only
			STATUS current
			DESCRIPTION
				"Description."
			::= { apnMuRxPktsEntry 13 }

		
		-- 1.3.6.1.4.1.388.11.3.9.8.6.1.14
		apnMuRxPktsAtMCS1 OBJECT-TYPE
			SYNTAX Counter32
			MAX-ACCESS read-only
			STATUS current
			DESCRIPTION
				"Description."
			::= { apnMuRxPktsEntry 14 }

		
		-- 1.3.6.1.4.1.388.11.3.9.8.6.1.15
		apnMuRxPktsAtMCS2 OBJECT-TYPE
			SYNTAX Counter32
			MAX-ACCESS read-only
			STATUS current
			DESCRIPTION
				"Description."
			::= { apnMuRxPktsEntry 15 }

		
		-- 1.3.6.1.4.1.388.11.3.9.8.6.1.16
		apnMuRxPktsAtMCS3 OBJECT-TYPE
			SYNTAX Counter32
			MAX-ACCESS read-only
			STATUS current
			DESCRIPTION
				"Description."
			::= { apnMuRxPktsEntry 16 }

		
		-- 1.3.6.1.4.1.388.11.3.9.8.6.1.17
		apnMuRxPktsAtMCS4 OBJECT-TYPE
			SYNTAX Counter32
			MAX-ACCESS read-only
			STATUS current
			DESCRIPTION
				"Description."
			::= { apnMuRxPktsEntry 17 }

		
		-- 1.3.6.1.4.1.388.11.3.9.8.6.1.18
		apnMuRxPktsAtMCS5 OBJECT-TYPE
			SYNTAX Counter32
			MAX-ACCESS read-only
			STATUS current
			DESCRIPTION
				"Description."
			::= { apnMuRxPktsEntry 18 }

		
		-- 1.3.6.1.4.1.388.11.3.9.8.6.1.19
		apnMuRxPktsAtMCS6 OBJECT-TYPE
			SYNTAX Counter32
			MAX-ACCESS read-only
			STATUS current
			DESCRIPTION
				"Description."
			::= { apnMuRxPktsEntry 19 }

		
		-- 1.3.6.1.4.1.388.11.3.9.8.6.1.20
		apnMuRxPktsAtMCS7 OBJECT-TYPE
			SYNTAX Counter32
			MAX-ACCESS read-only
			STATUS current
			DESCRIPTION
				"Description."
			::= { apnMuRxPktsEntry 20 }

		
		-- 1.3.6.1.4.1.388.11.3.9.8.6.1.21
		apnMuRxPktsAtMCS8 OBJECT-TYPE
			SYNTAX Counter32
			MAX-ACCESS read-only
			STATUS current
			DESCRIPTION
				"Description."
			::= { apnMuRxPktsEntry 21 }

		
		-- 1.3.6.1.4.1.388.11.3.9.8.6.1.22
		apnMuRxPktsAtMCS9 OBJECT-TYPE
			SYNTAX Counter32
			MAX-ACCESS read-only
			STATUS current
			DESCRIPTION
				"Description."
			::= { apnMuRxPktsEntry 22 }

		
		-- 1.3.6.1.4.1.388.11.3.9.8.6.1.23
		apnMuRxPktsAtMCS10 OBJECT-TYPE
			SYNTAX Counter32
			MAX-ACCESS read-only
			STATUS current
			DESCRIPTION
				"Description."
			::= { apnMuRxPktsEntry 23 }

		
		-- 1.3.6.1.4.1.388.11.3.9.8.6.1.24
		apnMuRxPktsAtMCS11 OBJECT-TYPE
			SYNTAX Counter32
			MAX-ACCESS read-only
			STATUS current
			DESCRIPTION
				"Description."
			::= { apnMuRxPktsEntry 24 }

		
		-- 1.3.6.1.4.1.388.11.3.9.8.6.1.25
		apnMuRxPktsAtMCS12 OBJECT-TYPE
			SYNTAX Counter32
			MAX-ACCESS read-only
			STATUS current
			DESCRIPTION
				"Description."
			::= { apnMuRxPktsEntry 25 }

		
		-- 1.3.6.1.4.1.388.11.3.9.8.6.1.26
		apnMuRxPktsAtMCS13 OBJECT-TYPE
			SYNTAX Counter32
			MAX-ACCESS read-only
			STATUS current
			DESCRIPTION
				"Description."
			::= { apnMuRxPktsEntry 26 }

		
		-- 1.3.6.1.4.1.388.11.3.9.8.6.1.27
		apnMuRxPktsAtMCS14 OBJECT-TYPE
			SYNTAX Counter32
			MAX-ACCESS read-only
			STATUS current
			DESCRIPTION
				"Description."
			::= { apnMuRxPktsEntry 27 }

		
		-- 1.3.6.1.4.1.388.11.3.9.8.6.1.28
		apnMuRxPktsAtMCS15 OBJECT-TYPE
			SYNTAX Counter32
			MAX-ACCESS read-only
			STATUS current
			DESCRIPTION
				"Description."
			::= { apnMuRxPktsEntry 28 }

		
		-- 1.3.6.1.4.1.388.11.3.9.8.7
		apnMuTxPktsTable OBJECT-TYPE
			SYNTAX SEQUENCE OF ApnMuTxPktsEntry
			MAX-ACCESS not-accessible
			STATUS current
			DESCRIPTION
				"For each mobile unit associated to an 802.11n Portal 
				on the AP, this table describes counts of packets 
				transmitted at each speed."
			::= { apnStats 7 }

		
		-- 1.3.6.1.4.1.388.11.3.9.8.7.1
		apnMuTxPktsEntry OBJECT-TYPE
			SYNTAX ApnMuTxPktsEntry
			MAX-ACCESS not-accessible
			STATUS current
			DESCRIPTION
				" "
			INDEX { ccMuMac }
			::= { apnMuTxPktsTable 1 }

		
		ApnMuTxPktsEntry ::=
			SEQUENCE { 
				apnMuTxPktsAt1Mb
					Counter32,
				apnMuTxPktsAt2Mb
					Counter32,
				apnMuTxPktsAt5pt5Mb
					Counter32,
				apnMuTxPktsAt6Mb
					Counter32,
				apnMuTxPktsAt9Mb
					Counter32,
				apnMuTxPktsAt11Mb
					Counter32,
				apnMuTxPktsAt12Mb
					Counter32,
				apnMuTxPktsAt18Mb
					Counter32,
				apnMuTxPktsAt24Mb
					Counter32,
				apnMuTxPktsAt36Mb
					Counter32,
				apnMuTxPktsAt48Mb
					Counter32,
				apnMuTxPktsAt54Mb
					Counter32,
				apnMuTxPktsAtMCS0
					Counter32,
				apnMuTxPktsAtMCS1
					Counter32,
				apnMuTxPktsAtMCS2
					Counter32,
				apnMuTxPktsAtMCS3
					Counter32,
				apnMuTxPktsAtMCS4
					Counter32,
				apnMuTxPktsAtMCS5
					Counter32,
				apnMuTxPktsAtMCS6
					Counter32,
				apnMuTxPktsAtMCS7
					Counter32,
				apnMuTxPktsAtMCS8
					Counter32,
				apnMuTxPktsAtMCS9
					Counter32,
				apnMuTxPktsAtMCS10
					Counter32,
				apnMuTxPktsAtMCS11
					Counter32,
				apnMuTxPktsAtMCS12
					Counter32,
				apnMuTxPktsAtMCS13
					Counter32,
				apnMuTxPktsAtMCS14
					Counter32,
				apnMuTxPktsAtMCS15
					Counter32
			 }

		-- 1.3.6.1.4.1.388.11.3.9.8.7.1.1
		apnMuTxPktsAt1Mb OBJECT-TYPE
			SYNTAX Counter32
			MAX-ACCESS read-only
			STATUS current
			DESCRIPTION
				"Number of pkts transmitted via this Portal at 1 and 2 Mbps."
			::= { apnMuTxPktsEntry 1 }

		
		-- 1.3.6.1.4.1.388.11.3.9.8.7.1.2
		apnMuTxPktsAt2Mb OBJECT-TYPE
			SYNTAX Counter32
			MAX-ACCESS read-only
			STATUS current
			DESCRIPTION
				"Number of pkts transmitted via this Portal at 1, 2, 5.5 and 11 Mbps."
			::= { apnMuTxPktsEntry 2 }

		
		-- 1.3.6.1.4.1.388.11.3.9.8.7.1.3
		apnMuTxPktsAt5pt5Mb OBJECT-TYPE
			SYNTAX Counter32
			MAX-ACCESS read-only
			STATUS current
			DESCRIPTION
				"Number of pkts transmitted via this Portal at 1, 2, 5.5 and 11 Mbps, and, 
				6, 12 and 24 Mbps."
			::= { apnMuTxPktsEntry 3 }

		
		-- 1.3.6.1.4.1.388.11.3.9.8.7.1.4
		apnMuTxPktsAt6Mb OBJECT-TYPE
			SYNTAX Counter32
			MAX-ACCESS read-only
			STATUS current
			DESCRIPTION
				"Number of pkts transmitted via this Portal at 1, 2, 5.5 and 11 Mbps, and, 
				6, 12 and 24 Mbps as well as at MCS 0 to 7 rates."
			::= { apnMuTxPktsEntry 4 }

		
		-- 1.3.6.1.4.1.388.11.3.9.8.7.1.5
		apnMuTxPktsAt9Mb OBJECT-TYPE
			SYNTAX Counter32
			MAX-ACCESS read-only
			STATUS current
			DESCRIPTION
				"Number of pkts transmitted via this Portal at 6, 12 and 24 Mbps."
			::= { apnMuTxPktsEntry 5 }

		
		-- 1.3.6.1.4.1.388.11.3.9.8.7.1.6
		apnMuTxPktsAt11Mb OBJECT-TYPE
			SYNTAX Counter32
			MAX-ACCESS read-only
			STATUS current
			DESCRIPTION
				"Number of pkts transmitted via this Portal at 6, 12 and 24 Mbps as well as 
				at MCS 0 to 7 rates."
			::= { apnMuTxPktsEntry 6 }

		
		-- 1.3.6.1.4.1.388.11.3.9.8.7.1.7
		apnMuTxPktsAt12Mb OBJECT-TYPE
			SYNTAX Counter32
			MAX-ACCESS read-only
			STATUS current
			DESCRIPTION
				"Number of pkts transmitted via this Portal at MCS 0 to 7 rates."
			::= { apnMuTxPktsEntry 7 }

		
		-- 1.3.6.1.4.1.388.11.3.9.8.7.1.8
		apnMuTxPktsAt18Mb OBJECT-TYPE
			SYNTAX Counter32
			MAX-ACCESS read-only
			STATUS current
			DESCRIPTION
				"Description."
			::= { apnMuTxPktsEntry 8 }

		
		-- 1.3.6.1.4.1.388.11.3.9.8.7.1.9
		apnMuTxPktsAt24Mb OBJECT-TYPE
			SYNTAX Counter32
			MAX-ACCESS read-only
			STATUS current
			DESCRIPTION
				"Description."
			::= { apnMuTxPktsEntry 9 }

		
		-- 1.3.6.1.4.1.388.11.3.9.8.7.1.10
		apnMuTxPktsAt36Mb OBJECT-TYPE
			SYNTAX Counter32
			MAX-ACCESS read-only
			STATUS current
			DESCRIPTION
				"Description."
			::= { apnMuTxPktsEntry 10 }

		
		-- 1.3.6.1.4.1.388.11.3.9.8.7.1.11
		apnMuTxPktsAt48Mb OBJECT-TYPE
			SYNTAX Counter32
			MAX-ACCESS read-only
			STATUS current
			DESCRIPTION
				"Description."
			::= { apnMuTxPktsEntry 11 }

		
		-- 1.3.6.1.4.1.388.11.3.9.8.7.1.12
		apnMuTxPktsAt54Mb OBJECT-TYPE
			SYNTAX Counter32
			MAX-ACCESS read-only
			STATUS current
			DESCRIPTION
				"Description."
			::= { apnMuTxPktsEntry 12 }

		
		-- 1.3.6.1.4.1.388.11.3.9.8.7.1.13
		apnMuTxPktsAtMCS0 OBJECT-TYPE
			SYNTAX Counter32
			MAX-ACCESS read-only
			STATUS current
			DESCRIPTION
				"Description."
			::= { apnMuTxPktsEntry 13 }

		
		-- 1.3.6.1.4.1.388.11.3.9.8.7.1.14
		apnMuTxPktsAtMCS1 OBJECT-TYPE
			SYNTAX Counter32
			MAX-ACCESS read-only
			STATUS current
			DESCRIPTION
				"Description."
			::= { apnMuTxPktsEntry 14 }

		
		-- 1.3.6.1.4.1.388.11.3.9.8.7.1.15
		apnMuTxPktsAtMCS2 OBJECT-TYPE
			SYNTAX Counter32
			MAX-ACCESS read-only
			STATUS current
			DESCRIPTION
				"Description."
			::= { apnMuTxPktsEntry 15 }

		
		-- 1.3.6.1.4.1.388.11.3.9.8.7.1.16
		apnMuTxPktsAtMCS3 OBJECT-TYPE
			SYNTAX Counter32
			MAX-ACCESS read-only
			STATUS current
			DESCRIPTION
				"Description."
			::= { apnMuTxPktsEntry 16 }

		
		-- 1.3.6.1.4.1.388.11.3.9.8.7.1.17
		apnMuTxPktsAtMCS4 OBJECT-TYPE
			SYNTAX Counter32
			MAX-ACCESS read-only
			STATUS current
			DESCRIPTION
				"Description."
			::= { apnMuTxPktsEntry 17 }

		
		-- 1.3.6.1.4.1.388.11.3.9.8.7.1.18
		apnMuTxPktsAtMCS5 OBJECT-TYPE
			SYNTAX Counter32
			MAX-ACCESS read-only
			STATUS current
			DESCRIPTION
				"Description."
			::= { apnMuTxPktsEntry 18 }

		
		-- 1.3.6.1.4.1.388.11.3.9.8.7.1.19
		apnMuTxPktsAtMCS6 OBJECT-TYPE
			SYNTAX Counter32
			MAX-ACCESS read-only
			STATUS current
			DESCRIPTION
				"Description."
			::= { apnMuTxPktsEntry 19 }

		
		-- 1.3.6.1.4.1.388.11.3.9.8.7.1.20
		apnMuTxPktsAtMCS7 OBJECT-TYPE
			SYNTAX Counter32
			MAX-ACCESS read-only
			STATUS current
			DESCRIPTION
				"Description."
			::= { apnMuTxPktsEntry 20 }

		
		-- 1.3.6.1.4.1.388.11.3.9.8.7.1.21
		apnMuTxPktsAtMCS8 OBJECT-TYPE
			SYNTAX Counter32
			MAX-ACCESS read-only
			STATUS current
			DESCRIPTION
				"Description."
			::= { apnMuTxPktsEntry 21 }

		
		-- 1.3.6.1.4.1.388.11.3.9.8.7.1.22
		apnMuTxPktsAtMCS9 OBJECT-TYPE
			SYNTAX Counter32
			MAX-ACCESS read-only
			STATUS current
			DESCRIPTION
				"Description."
			::= { apnMuTxPktsEntry 22 }

		
		-- 1.3.6.1.4.1.388.11.3.9.8.7.1.23
		apnMuTxPktsAtMCS10 OBJECT-TYPE
			SYNTAX Counter32
			MAX-ACCESS read-only
			STATUS current
			DESCRIPTION
				"Description."
			::= { apnMuTxPktsEntry 23 }

		
		-- 1.3.6.1.4.1.388.11.3.9.8.7.1.24
		apnMuTxPktsAtMCS11 OBJECT-TYPE
			SYNTAX Counter32
			MAX-ACCESS read-only
			STATUS current
			DESCRIPTION
				"Description."
			::= { apnMuTxPktsEntry 24 }

		
		-- 1.3.6.1.4.1.388.11.3.9.8.7.1.25
		apnMuTxPktsAtMCS12 OBJECT-TYPE
			SYNTAX Counter32
			MAX-ACCESS read-only
			STATUS current
			DESCRIPTION
				"Description."
			::= { apnMuTxPktsEntry 25 }

		
		-- 1.3.6.1.4.1.388.11.3.9.8.7.1.26
		apnMuTxPktsAtMCS13 OBJECT-TYPE
			SYNTAX Counter32
			MAX-ACCESS read-only
			STATUS current
			DESCRIPTION
				"Description."
			::= { apnMuTxPktsEntry 26 }

		
		-- 1.3.6.1.4.1.388.11.3.9.8.7.1.27
		apnMuTxPktsAtMCS14 OBJECT-TYPE
			SYNTAX Counter32
			MAX-ACCESS read-only
			STATUS current
			DESCRIPTION
				"Description."
			::= { apnMuTxPktsEntry 27 }

		
		-- 1.3.6.1.4.1.388.11.3.9.8.7.1.28
		apnMuTxPktsAtMCS15 OBJECT-TYPE
			SYNTAX Counter32
			MAX-ACCESS read-only
			STATUS current
			DESCRIPTION
				"Description."
			::= { apnMuTxPktsEntry 28 }

		
		-- 1.3.6.1.4.1.388.11.3.9.8.8
		apnMuRxOctetsTable OBJECT-TYPE
			SYNTAX SEQUENCE OF ApnMuRxOctetsEntry
			MAX-ACCESS not-accessible
			STATUS current
			DESCRIPTION
				"For each mobile unit associated to an 802.11n Portal 
				on the AP, this table describes counts of octets 
				received at each speed."
			::= { apnStats 8 }

		
		-- 1.3.6.1.4.1.388.11.3.9.8.8.1
		apnMuRxOctetsEntry OBJECT-TYPE
			SYNTAX ApnMuRxOctetsEntry
			MAX-ACCESS not-accessible
			STATUS current
			DESCRIPTION
				" "
			INDEX { ccMuMac }
			::= { apnMuRxOctetsTable 1 }

		
		ApnMuRxOctetsEntry ::=
			SEQUENCE { 
				apnMuRxOctetsAt1Mb
					Counter32,
				apnMuRxOctetsAt2Mb
					Counter32,
				apnMuRxOctetsAt5pt5Mb
					Counter32,
				apnMuRxOctetsAt6Mb
					Counter32,
				apnMuRxOctetsAt9Mb
					Counter32,
				apnMuRxOctetsAt11Mb
					Counter32,
				apnMuRxOctetsAt12Mb
					Counter32,
				apnMuRxOctetsAt18Mb
					Counter32,
				apnMuRxOctetsAt24Mb
					Counter32,
				apnMuRxOctetsAt36Mb
					Counter32,
				apnMuRxOctetsAt48Mb
					Counter32,
				apnMuRxOctetsAt54Mb
					Counter32,
				apnMuRxOctetsAtMCS0
					Counter32,
				apnMuRxOctetsAtMCS1
					Counter32,
				apnMuRxOctetsAtMCS2
					Counter32,
				apnMuRxOctetsAtMCS3
					Counter32,
				apnMuRxOctetsAtMCS4
					Counter32,
				apnMuRxOctetsAtMCS5
					Counter32,
				apnMuRxOctetsAtMCS6
					Counter32,
				apnMuRxOctetsAtMCS7
					Counter32,
				apnMuRxOctetsAtMCS8
					Counter32,
				apnMuRxOctetsAtMCS9
					Counter32,
				apnMuRxOctetsAtMCS10
					Counter32,
				apnMuRxOctetsAtMCS11
					Counter32,
				apnMuRxOctetsAtMCS12
					Counter32,
				apnMuRxOctetsAtMCS13
					Counter32,
				apnMuRxOctetsAtMCS14
					Counter32,
				apnMuRxOctetsAtMCS15
					Counter32
			 }

		-- 1.3.6.1.4.1.388.11.3.9.8.8.1.1
		apnMuRxOctetsAt1Mb OBJECT-TYPE
			SYNTAX Counter32
			MAX-ACCESS read-only
			STATUS current
			DESCRIPTION
				"Number of octets received via this Portal at 1 and 2 Mbps."
			::= { apnMuRxOctetsEntry 1 }

		
		-- 1.3.6.1.4.1.388.11.3.9.8.8.1.2
		apnMuRxOctetsAt2Mb OBJECT-TYPE
			SYNTAX Counter32
			MAX-ACCESS read-only
			STATUS current
			DESCRIPTION
				"Number of octets received via this Portal at 1, 2, 5.5 and 11 Mbps."
			::= { apnMuRxOctetsEntry 2 }

		
		-- 1.3.6.1.4.1.388.11.3.9.8.8.1.3
		apnMuRxOctetsAt5pt5Mb OBJECT-TYPE
			SYNTAX Counter32
			MAX-ACCESS read-only
			STATUS current
			DESCRIPTION
				"Number of octets received via this Portal at 1, 2, 5.5 and 11 Mbps, and, 
				6, 12 and 24 Mbps."
			::= { apnMuRxOctetsEntry 3 }

		
		-- 1.3.6.1.4.1.388.11.3.9.8.8.1.4
		apnMuRxOctetsAt6Mb OBJECT-TYPE
			SYNTAX Counter32
			MAX-ACCESS read-only
			STATUS current
			DESCRIPTION
				"Number of octets received via this Portal at 1, 2, 5.5 and 11 Mbps, and, 
				6, 12 and 24 Mbps as well as at MCS 0 to 7 rates."
			::= { apnMuRxOctetsEntry 4 }

		
		-- 1.3.6.1.4.1.388.11.3.9.8.8.1.5
		apnMuRxOctetsAt9Mb OBJECT-TYPE
			SYNTAX Counter32
			MAX-ACCESS read-only
			STATUS current
			DESCRIPTION
				"Number of octets received via this Portal at 6, 12 and 24 Mbps."
			::= { apnMuRxOctetsEntry 5 }

		
		-- 1.3.6.1.4.1.388.11.3.9.8.8.1.6
		apnMuRxOctetsAt11Mb OBJECT-TYPE
			SYNTAX Counter32
			MAX-ACCESS read-only
			STATUS current
			DESCRIPTION
				"Number of octets received via this Portal at 6, 12 and 24 Mbps as well as 
				at MCS 0 to 7 rates."
			::= { apnMuRxOctetsEntry 6 }

		
		-- 1.3.6.1.4.1.388.11.3.9.8.8.1.7
		apnMuRxOctetsAt12Mb OBJECT-TYPE
			SYNTAX Counter32
			MAX-ACCESS read-only
			STATUS current
			DESCRIPTION
				"Number of octets received via this Portal at MCS 0 to 7 rates."
			::= { apnMuRxOctetsEntry 7 }

		
		-- 1.3.6.1.4.1.388.11.3.9.8.8.1.8
		apnMuRxOctetsAt18Mb OBJECT-TYPE
			SYNTAX Counter32
			MAX-ACCESS read-only
			STATUS current
			DESCRIPTION
				"Description."
			::= { apnMuRxOctetsEntry 8 }

		
		-- 1.3.6.1.4.1.388.11.3.9.8.8.1.9
		apnMuRxOctetsAt24Mb OBJECT-TYPE
			SYNTAX Counter32
			MAX-ACCESS read-only
			STATUS current
			DESCRIPTION
				"Description."
			::= { apnMuRxOctetsEntry 9 }

		
		-- 1.3.6.1.4.1.388.11.3.9.8.8.1.10
		apnMuRxOctetsAt36Mb OBJECT-TYPE
			SYNTAX Counter32
			MAX-ACCESS read-only
			STATUS current
			DESCRIPTION
				"Description."
			::= { apnMuRxOctetsEntry 10 }

		
		-- 1.3.6.1.4.1.388.11.3.9.8.8.1.11
		apnMuRxOctetsAt48Mb OBJECT-TYPE
			SYNTAX Counter32
			MAX-ACCESS read-only
			STATUS current
			DESCRIPTION
				"Description."
			::= { apnMuRxOctetsEntry 11 }

		
		-- 1.3.6.1.4.1.388.11.3.9.8.8.1.12
		apnMuRxOctetsAt54Mb OBJECT-TYPE
			SYNTAX Counter32
			MAX-ACCESS read-only
			STATUS current
			DESCRIPTION
				"Description."
			::= { apnMuRxOctetsEntry 12 }

		
		-- 1.3.6.1.4.1.388.11.3.9.8.8.1.13
		apnMuRxOctetsAtMCS0 OBJECT-TYPE
			SYNTAX Counter32
			MAX-ACCESS read-only
			STATUS current
			DESCRIPTION
				"Description."
			::= { apnMuRxOctetsEntry 13 }

		
		-- 1.3.6.1.4.1.388.11.3.9.8.8.1.14
		apnMuRxOctetsAtMCS1 OBJECT-TYPE
			SYNTAX Counter32
			MAX-ACCESS read-only
			STATUS current
			DESCRIPTION
				"Description."
			::= { apnMuRxOctetsEntry 14 }

		
		-- 1.3.6.1.4.1.388.11.3.9.8.8.1.15
		apnMuRxOctetsAtMCS2 OBJECT-TYPE
			SYNTAX Counter32
			MAX-ACCESS read-only
			STATUS current
			DESCRIPTION
				"Description."
			::= { apnMuRxOctetsEntry 15 }

		
		-- 1.3.6.1.4.1.388.11.3.9.8.8.1.16
		apnMuRxOctetsAtMCS3 OBJECT-TYPE
			SYNTAX Counter32
			MAX-ACCESS read-only
			STATUS current
			DESCRIPTION
				"Description."
			::= { apnMuRxOctetsEntry 16 }

		
		-- 1.3.6.1.4.1.388.11.3.9.8.8.1.17
		apnMuRxOctetsAtMCS4 OBJECT-TYPE
			SYNTAX Counter32
			MAX-ACCESS read-only
			STATUS current
			DESCRIPTION
				"Description."
			::= { apnMuRxOctetsEntry 17 }

		
		-- 1.3.6.1.4.1.388.11.3.9.8.8.1.18
		apnMuRxOctetsAtMCS5 OBJECT-TYPE
			SYNTAX Counter32
			MAX-ACCESS read-only
			STATUS current
			DESCRIPTION
				"Description."
			::= { apnMuRxOctetsEntry 18 }

		
		-- 1.3.6.1.4.1.388.11.3.9.8.8.1.19
		apnMuRxOctetsAtMCS6 OBJECT-TYPE
			SYNTAX Counter32
			MAX-ACCESS read-only
			STATUS current
			DESCRIPTION
				"Description."
			::= { apnMuRxOctetsEntry 19 }

		
		-- 1.3.6.1.4.1.388.11.3.9.8.8.1.20
		apnMuRxOctetsAtMCS7 OBJECT-TYPE
			SYNTAX Counter32
			MAX-ACCESS read-only
			STATUS current
			DESCRIPTION
				"Description."
			::= { apnMuRxOctetsEntry 20 }

		
		-- 1.3.6.1.4.1.388.11.3.9.8.8.1.21
		apnMuRxOctetsAtMCS8 OBJECT-TYPE
			SYNTAX Counter32
			MAX-ACCESS read-only
			STATUS current
			DESCRIPTION
				"Description."
			::= { apnMuRxOctetsEntry 21 }

		
		-- 1.3.6.1.4.1.388.11.3.9.8.8.1.22
		apnMuRxOctetsAtMCS9 OBJECT-TYPE
			SYNTAX Counter32
			MAX-ACCESS read-only
			STATUS current
			DESCRIPTION
				"Description."
			::= { apnMuRxOctetsEntry 22 }

		
		-- 1.3.6.1.4.1.388.11.3.9.8.8.1.23
		apnMuRxOctetsAtMCS10 OBJECT-TYPE
			SYNTAX Counter32
			MAX-ACCESS read-only
			STATUS current
			DESCRIPTION
				"Description."
			::= { apnMuRxOctetsEntry 23 }

		
		-- 1.3.6.1.4.1.388.11.3.9.8.8.1.24
		apnMuRxOctetsAtMCS11 OBJECT-TYPE
			SYNTAX Counter32
			MAX-ACCESS read-only
			STATUS current
			DESCRIPTION
				"Description."
			::= { apnMuRxOctetsEntry 24 }

		
		-- 1.3.6.1.4.1.388.11.3.9.8.8.1.25
		apnMuRxOctetsAtMCS12 OBJECT-TYPE
			SYNTAX Counter32
			MAX-ACCESS read-only
			STATUS current
			DESCRIPTION
				"Description."
			::= { apnMuRxOctetsEntry 25 }

		
		-- 1.3.6.1.4.1.388.11.3.9.8.8.1.26
		apnMuRxOctetsAtMCS13 OBJECT-TYPE
			SYNTAX Counter32
			MAX-ACCESS read-only
			STATUS current
			DESCRIPTION
				"Description."
			::= { apnMuRxOctetsEntry 26 }

		
		-- 1.3.6.1.4.1.388.11.3.9.8.8.1.27
		apnMuRxOctetsAtMCS14 OBJECT-TYPE
			SYNTAX Counter32
			MAX-ACCESS read-only
			STATUS current
			DESCRIPTION
				"Description."
			::= { apnMuRxOctetsEntry 27 }

		
		-- 1.3.6.1.4.1.388.11.3.9.8.8.1.28
		apnMuRxOctetsAtMCS15 OBJECT-TYPE
			SYNTAX Counter32
			MAX-ACCESS read-only
			STATUS current
			DESCRIPTION
				"Description."
			::= { apnMuRxOctetsEntry 28 }

		
		-- 1.3.6.1.4.1.388.11.3.9.8.9
		apnMuTxOctetsTable OBJECT-TYPE
			SYNTAX SEQUENCE OF ApnMuTxOctetsEntry
			MAX-ACCESS not-accessible
			STATUS current
			DESCRIPTION
				"For each mobile unit associated to an 802.11n Portal 
				on the AP, this table describes counts of octets 
				transmitted at each speed."
			::= { apnStats 9 }

		
		-- 1.3.6.1.4.1.388.11.3.9.8.9.1
		apnMuTxOctetsEntry OBJECT-TYPE
			SYNTAX ApnMuTxOctetsEntry
			MAX-ACCESS not-accessible
			STATUS current
			DESCRIPTION
				" "
			INDEX { ccMuMac }
			::= { apnMuTxOctetsTable 1 }

		
		ApnMuTxOctetsEntry ::=
			SEQUENCE { 
				apnMuTxOctetsAt1Mb
					Counter32,
				apnMuTxOctetsAt2Mb
					Counter32,
				apnMuTxOctetsAt5pt5Mb
					Counter32,
				apnMuTxOctetsAt6Mb
					Counter32,
				apnMuTxOctetsAt9Mb
					Counter32,
				apnMuTxOctetsAt11Mb
					Counter32,
				apnMuTxOctetsAt12Mb
					Counter32,
				apnMuTxOctetsAt18Mb
					Counter32,
				apnMuTxOctetsAt24Mb
					Counter32,
				apnMuTxOctetsAt36Mb
					Counter32,
				apnMuTxOctetsAt48Mb
					Counter32,
				apnMuTxOctetsAt54Mb
					Counter32,
				apnMuTxOctetsAtMCS0
					Counter32,
				apnMuTxOctetsAtMCS1
					Counter32,
				apnMuTxOctetsAtMCS2
					Counter32,
				apnMuTxOctetsAtMCS3
					Counter32,
				apnMuTxOctetsAtMCS4
					Counter32,
				apnMuTxOctetsAtMCS5
					Counter32,
				apnMuTxOctetsAtMCS6
					Counter32,
				apnMuTxOctetsAtMCS7
					Counter32,
				apnMuTxOctetsAtMCS8
					Counter32,
				apnMuTxOctetsAtMCS9
					Counter32,
				apnMuTxOctetsAtMCS10
					Counter32,
				apnMuTxOctetsAtMCS11
					Counter32,
				apnMuTxOctetsAtMCS12
					Counter32,
				apnMuTxOctetsAtMCS13
					Counter32,
				apnMuTxOctetsAtMCS14
					Counter32,
				apnMuTxOctetsAtMCS15
					Counter32
			 }

		-- 1.3.6.1.4.1.388.11.3.9.8.9.1.2
		apnMuTxOctetsAt1Mb OBJECT-TYPE
			SYNTAX Counter32
			MAX-ACCESS read-only
			STATUS current
			DESCRIPTION
				"Number octets transmitted via this Portal at 1 and 2 Mbps."
			::= { apnMuTxOctetsEntry 2 }

		
		-- 1.3.6.1.4.1.388.11.3.9.8.9.1.3
		apnMuTxOctetsAt2Mb OBJECT-TYPE
			SYNTAX Counter32
			MAX-ACCESS read-only
			STATUS current
			DESCRIPTION
				"Number octets transmitted via this Portal at 1, 2, 5.5 and 11 Mbps."
			::= { apnMuTxOctetsEntry 3 }

		
		-- 1.3.6.1.4.1.388.11.3.9.8.9.1.4
		apnMuTxOctetsAt5pt5Mb OBJECT-TYPE
			SYNTAX Counter32
			MAX-ACCESS read-only
			STATUS current
			DESCRIPTION
				"Number octets transmitted via this Portal at 1, 2, 5.5 and 11 Mbps, and, 
				6, 12 and 24 Mbps."
			::= { apnMuTxOctetsEntry 4 }

		
		-- 1.3.6.1.4.1.388.11.3.9.8.9.1.5
		apnMuTxOctetsAt6Mb OBJECT-TYPE
			SYNTAX Counter32
			MAX-ACCESS read-only
			STATUS current
			DESCRIPTION
				"Number octets transmitted via this Portal at 1, 2, 5.5 and 11 Mbps, and, 
				6, 12 and 24 Mbps as well as at MCS 0 to 7 rates."
			::= { apnMuTxOctetsEntry 5 }

		
		-- 1.3.6.1.4.1.388.11.3.9.8.9.1.6
		apnMuTxOctetsAt9Mb OBJECT-TYPE
			SYNTAX Counter32
			MAX-ACCESS read-only
			STATUS current
			DESCRIPTION
				"Number octets transmitted via this Portal at 6, 12 and 24 Mbps."
			::= { apnMuTxOctetsEntry 6 }

		
		-- 1.3.6.1.4.1.388.11.3.9.8.9.1.7
		apnMuTxOctetsAt11Mb OBJECT-TYPE
			SYNTAX Counter32
			MAX-ACCESS read-only
			STATUS current
			DESCRIPTION
				"Number octets transmitted via this Portal at 6, 12 and 24 Mbps as well as 
				at MCS 0 to 7 rates."
			::= { apnMuTxOctetsEntry 7 }

		
		-- 1.3.6.1.4.1.388.11.3.9.8.9.1.8
		apnMuTxOctetsAt12Mb OBJECT-TYPE
			SYNTAX Counter32
			MAX-ACCESS read-only
			STATUS current
			DESCRIPTION
				"Number octets transmitted via this Portal at MCS 0 to 7 rates."
			::= { apnMuTxOctetsEntry 8 }

		
		-- 1.3.6.1.4.1.388.11.3.9.8.9.1.9
		apnMuTxOctetsAt18Mb OBJECT-TYPE
			SYNTAX Counter32
			MAX-ACCESS read-only
			STATUS current
			DESCRIPTION
				"Description."
			::= { apnMuTxOctetsEntry 9 }

		
		-- 1.3.6.1.4.1.388.11.3.9.8.9.1.10
		apnMuTxOctetsAt24Mb OBJECT-TYPE
			SYNTAX Counter32
			MAX-ACCESS read-only
			STATUS current
			DESCRIPTION
				"Description."
			::= { apnMuTxOctetsEntry 10 }

		
		-- 1.3.6.1.4.1.388.11.3.9.8.9.1.11
		apnMuTxOctetsAt36Mb OBJECT-TYPE
			SYNTAX Counter32
			MAX-ACCESS read-only
			STATUS current
			DESCRIPTION
				"Description."
			::= { apnMuTxOctetsEntry 11 }

		
		-- 1.3.6.1.4.1.388.11.3.9.8.9.1.12
		apnMuTxOctetsAt48Mb OBJECT-TYPE
			SYNTAX Counter32
			MAX-ACCESS read-only
			STATUS current
			DESCRIPTION
				"Description."
			::= { apnMuTxOctetsEntry 12 }

		
		-- 1.3.6.1.4.1.388.11.3.9.8.9.1.13
		apnMuTxOctetsAt54Mb OBJECT-TYPE
			SYNTAX Counter32
			MAX-ACCESS read-only
			STATUS current
			DESCRIPTION
				"Description."
			::= { apnMuTxOctetsEntry 13 }

		
		-- 1.3.6.1.4.1.388.11.3.9.8.9.1.14
		apnMuTxOctetsAtMCS0 OBJECT-TYPE
			SYNTAX Counter32
			MAX-ACCESS read-only
			STATUS current
			DESCRIPTION
				"Description."
			::= { apnMuTxOctetsEntry 14 }

		
		-- 1.3.6.1.4.1.388.11.3.9.8.9.1.15
		apnMuTxOctetsAtMCS1 OBJECT-TYPE
			SYNTAX Counter32
			MAX-ACCESS read-only
			STATUS current
			DESCRIPTION
				"Description."
			::= { apnMuTxOctetsEntry 15 }

		
		-- 1.3.6.1.4.1.388.11.3.9.8.9.1.16
		apnMuTxOctetsAtMCS2 OBJECT-TYPE
			SYNTAX Counter32
			MAX-ACCESS read-only
			STATUS current
			DESCRIPTION
				"Description."
			::= { apnMuTxOctetsEntry 16 }

		
		-- 1.3.6.1.4.1.388.11.3.9.8.9.1.17
		apnMuTxOctetsAtMCS3 OBJECT-TYPE
			SYNTAX Counter32
			MAX-ACCESS read-only
			STATUS current
			DESCRIPTION
				"Description."
			::= { apnMuTxOctetsEntry 17 }

		
		-- 1.3.6.1.4.1.388.11.3.9.8.9.1.18
		apnMuTxOctetsAtMCS4 OBJECT-TYPE
			SYNTAX Counter32
			MAX-ACCESS read-only
			STATUS current
			DESCRIPTION
				"Description."
			::= { apnMuTxOctetsEntry 18 }

		
		-- 1.3.6.1.4.1.388.11.3.9.8.9.1.19
		apnMuTxOctetsAtMCS5 OBJECT-TYPE
			SYNTAX Counter32
			MAX-ACCESS read-only
			STATUS current
			DESCRIPTION
				"Description."
			::= { apnMuTxOctetsEntry 19 }

		
		-- 1.3.6.1.4.1.388.11.3.9.8.9.1.20
		apnMuTxOctetsAtMCS6 OBJECT-TYPE
			SYNTAX Counter32
			MAX-ACCESS read-only
			STATUS current
			DESCRIPTION
				"Description."
			::= { apnMuTxOctetsEntry 20 }

		
		-- 1.3.6.1.4.1.388.11.3.9.8.9.1.21
		apnMuTxOctetsAtMCS7 OBJECT-TYPE
			SYNTAX Counter32
			MAX-ACCESS read-only
			STATUS current
			DESCRIPTION
				"Description."
			::= { apnMuTxOctetsEntry 21 }

		
		-- 1.3.6.1.4.1.388.11.3.9.8.9.1.22
		apnMuTxOctetsAtMCS8 OBJECT-TYPE
			SYNTAX Counter32
			MAX-ACCESS read-only
			STATUS current
			DESCRIPTION
				"Description."
			::= { apnMuTxOctetsEntry 22 }

		
		-- 1.3.6.1.4.1.388.11.3.9.8.9.1.23
		apnMuTxOctetsAtMCS9 OBJECT-TYPE
			SYNTAX Counter32
			MAX-ACCESS read-only
			STATUS current
			DESCRIPTION
				"Description."
			::= { apnMuTxOctetsEntry 23 }

		
		-- 1.3.6.1.4.1.388.11.3.9.8.9.1.24
		apnMuTxOctetsAtMCS10 OBJECT-TYPE
			SYNTAX Counter32
			MAX-ACCESS read-only
			STATUS current
			DESCRIPTION
				"Description."
			::= { apnMuTxOctetsEntry 24 }

		
		-- 1.3.6.1.4.1.388.11.3.9.8.9.1.25
		apnMuTxOctetsAtMCS11 OBJECT-TYPE
			SYNTAX Counter32
			MAX-ACCESS read-only
			STATUS current
			DESCRIPTION
				"Description."
			::= { apnMuTxOctetsEntry 25 }

		
		-- 1.3.6.1.4.1.388.11.3.9.8.9.1.26
		apnMuTxOctetsAtMCS12 OBJECT-TYPE
			SYNTAX Counter32
			MAX-ACCESS read-only
			STATUS current
			DESCRIPTION
				"Description."
			::= { apnMuTxOctetsEntry 26 }

		
		-- 1.3.6.1.4.1.388.11.3.9.8.9.1.27
		apnMuTxOctetsAtMCS13 OBJECT-TYPE
			SYNTAX Counter32
			MAX-ACCESS read-only
			STATUS current
			DESCRIPTION
				"Description."
			::= { apnMuTxOctetsEntry 27 }

		
		-- 1.3.6.1.4.1.388.11.3.9.8.9.1.28
		apnMuTxOctetsAtMCS14 OBJECT-TYPE
			SYNTAX Counter32
			MAX-ACCESS read-only
			STATUS current
			DESCRIPTION
				"Description."
			::= { apnMuTxOctetsEntry 28 }

		
		-- 1.3.6.1.4.1.388.11.3.9.8.9.1.29
		apnMuTxOctetsAtMCS15 OBJECT-TYPE
			SYNTAX Counter32
			MAX-ACCESS read-only
			STATUS current
			DESCRIPTION
				"Description."
			::= { apnMuTxOctetsEntry 29 }

		
		-- 1.3.6.1.4.1.388.11.3.9.8.10
		apnWlanRxPktsTable OBJECT-TYPE
			SYNTAX SEQUENCE OF ApnWlanRxPktsEntry
			MAX-ACCESS not-accessible
			STATUS current
			DESCRIPTION
				"For each wlan on the 802.11n Portal on the AP, 
				this table describes counts of packets received 
				at each speed."
			::= { apnStats 10 }

		
		-- 1.3.6.1.4.1.388.11.3.9.8.10.1
		apnWlanRxPktsEntry OBJECT-TYPE
			SYNTAX ApnWlanRxPktsEntry
			MAX-ACCESS not-accessible
			STATUS current
			DESCRIPTION
				" "
			INDEX { ccWlanIndex }
			::= { apnWlanRxPktsTable 1 }

		
		ApnWlanRxPktsEntry ::=
			SEQUENCE { 
				apnWlanRxPktsAt1Mb
					Counter32,
				apnWlanRxPktsAt2Mb
					Counter32,
				apnWlanRxPktsAt5pt5Mb
					Counter32,
				apnWlanRxPktsAt6Mb
					Counter32,
				apnWlanRxPktsAt9Mb
					Counter32,
				apnWlanRxPktsAt11Mb
					Counter32,
				apnWlanRxPktsAt12Mb
					Counter32,
				apnWlanRxPktsAt18Mb
					Counter32,
				apnWlanRxPktsAt24Mb
					Counter32,
				apnWlanRxPktsAt36Mb
					Counter32,
				apnWlanRxPktsAt48Mb
					Counter32,
				apnWlanRxPktsAt54Mb
					Counter32,
				apnWlanRxPktsAtMCS0
					Counter32,
				apnWlanRxPktsAtMCS1
					Counter32,
				apnWlanRxPktsAtMCS2
					Counter32,
				apnWlanRxPktsAtMCS3
					Counter32,
				apnWlanRxPktsAtMCS4
					Counter32,
				apnWlanRxPktsAtMCS5
					Counter32,
				apnWlanRxPktsAtMCS6
					Counter32,
				apnWlanRxPktsAtMCS7
					Counter32,
				apnWlanRxPktsAtMCS8
					Counter32,
				apnWlanRxPktsAtMCS9
					Counter32,
				apnWlanRxPktsAtMCS10
					Counter32,
				apnWlanRxPktsAtMCS11
					Counter32,
				apnWlanRxPktsAtMCS12
					Counter32,
				apnWlanRxPktsAtMCS13
					Counter32,
				apnWlanRxPktsAtMCS14
					Counter32,
				apnWlanRxPktsAtMCS15
					Counter32
			 }

		-- 1.3.6.1.4.1.388.11.3.9.8.10.1.1
		apnWlanRxPktsAt1Mb OBJECT-TYPE
			SYNTAX Counter32
			MAX-ACCESS read-only
			STATUS current
			DESCRIPTION
				"Number of pkts received via this Portal at 1 and 2 Mbps."
			::= { apnWlanRxPktsEntry 1 }

		
		-- 1.3.6.1.4.1.388.11.3.9.8.10.1.2
		apnWlanRxPktsAt2Mb OBJECT-TYPE
			SYNTAX Counter32
			MAX-ACCESS read-only
			STATUS current
			DESCRIPTION
				"Number of pkts received via this Portal at 1, 2, 5.5 and 11 Mbps."
			::= { apnWlanRxPktsEntry 2 }

		
		-- 1.3.6.1.4.1.388.11.3.9.8.10.1.3
		apnWlanRxPktsAt5pt5Mb OBJECT-TYPE
			SYNTAX Counter32
			MAX-ACCESS read-only
			STATUS current
			DESCRIPTION
				"Number of pkts received via this Portal at 1, 2, 5.5 and 11 Mbps, and, 
				6, 12 and 24 Mbps."
			::= { apnWlanRxPktsEntry 3 }

		
		-- 1.3.6.1.4.1.388.11.3.9.8.10.1.4
		apnWlanRxPktsAt6Mb OBJECT-TYPE
			SYNTAX Counter32
			MAX-ACCESS read-only
			STATUS current
			DESCRIPTION
				"Number of pkts received via this Portal at 1, 2, 5.5 and 11 Mbps, and, 
				6, 12 and 24 Mbps as well as at MCS 0 to 7 rates."
			::= { apnWlanRxPktsEntry 4 }

		
		-- 1.3.6.1.4.1.388.11.3.9.8.10.1.5
		apnWlanRxPktsAt9Mb OBJECT-TYPE
			SYNTAX Counter32
			MAX-ACCESS read-only
			STATUS current
			DESCRIPTION
				"Number of pkts received via this Portal at 6, 12 and 24 Mbps."
			::= { apnWlanRxPktsEntry 5 }

		
		-- 1.3.6.1.4.1.388.11.3.9.8.10.1.6
		apnWlanRxPktsAt11Mb OBJECT-TYPE
			SYNTAX Counter32
			MAX-ACCESS read-only
			STATUS current
			DESCRIPTION
				"Number of pkts received via this Portal at 6, 12 and 24 Mbps as well as 
				at MCS 0 to 7 rates."
			::= { apnWlanRxPktsEntry 6 }

		
		-- 1.3.6.1.4.1.388.11.3.9.8.10.1.7
		apnWlanRxPktsAt12Mb OBJECT-TYPE
			SYNTAX Counter32
			MAX-ACCESS read-only
			STATUS current
			DESCRIPTION
				"Number of pkts received via this Portal at MCS 0 to 7 rates."
			::= { apnWlanRxPktsEntry 7 }

		
		-- 1.3.6.1.4.1.388.11.3.9.8.10.1.8
		apnWlanRxPktsAt18Mb OBJECT-TYPE
			SYNTAX Counter32
			MAX-ACCESS read-only
			STATUS current
			DESCRIPTION
				"Description."
			::= { apnWlanRxPktsEntry 8 }

		
		-- 1.3.6.1.4.1.388.11.3.9.8.10.1.9
		apnWlanRxPktsAt24Mb OBJECT-TYPE
			SYNTAX Counter32
			MAX-ACCESS read-only
			STATUS current
			DESCRIPTION
				"Description."
			::= { apnWlanRxPktsEntry 9 }

		
		-- 1.3.6.1.4.1.388.11.3.9.8.10.1.10
		apnWlanRxPktsAt36Mb OBJECT-TYPE
			SYNTAX Counter32
			MAX-ACCESS read-only
			STATUS current
			DESCRIPTION
				"Description."
			::= { apnWlanRxPktsEntry 10 }

		
		-- 1.3.6.1.4.1.388.11.3.9.8.10.1.11
		apnWlanRxPktsAt48Mb OBJECT-TYPE
			SYNTAX Counter32
			MAX-ACCESS read-only
			STATUS current
			DESCRIPTION
				"Description."
			::= { apnWlanRxPktsEntry 11 }

		
		-- 1.3.6.1.4.1.388.11.3.9.8.10.1.12
		apnWlanRxPktsAt54Mb OBJECT-TYPE
			SYNTAX Counter32
			MAX-ACCESS read-only
			STATUS current
			DESCRIPTION
				"Description."
			::= { apnWlanRxPktsEntry 12 }

		
		-- 1.3.6.1.4.1.388.11.3.9.8.10.1.13
		apnWlanRxPktsAtMCS0 OBJECT-TYPE
			SYNTAX Counter32
			MAX-ACCESS read-only
			STATUS current
			DESCRIPTION
				"Description."
			::= { apnWlanRxPktsEntry 13 }

		
		-- 1.3.6.1.4.1.388.11.3.9.8.10.1.14
		apnWlanRxPktsAtMCS1 OBJECT-TYPE
			SYNTAX Counter32
			MAX-ACCESS read-only
			STATUS current
			DESCRIPTION
				"Description."
			::= { apnWlanRxPktsEntry 14 }

		
		-- 1.3.6.1.4.1.388.11.3.9.8.10.1.15
		apnWlanRxPktsAtMCS2 OBJECT-TYPE
			SYNTAX Counter32
			MAX-ACCESS read-only
			STATUS current
			DESCRIPTION
				"Description."
			::= { apnWlanRxPktsEntry 15 }

		
		-- 1.3.6.1.4.1.388.11.3.9.8.10.1.16
		apnWlanRxPktsAtMCS3 OBJECT-TYPE
			SYNTAX Counter32
			MAX-ACCESS read-only
			STATUS current
			DESCRIPTION
				"Description."
			::= { apnWlanRxPktsEntry 16 }

		
		-- 1.3.6.1.4.1.388.11.3.9.8.10.1.17
		apnWlanRxPktsAtMCS4 OBJECT-TYPE
			SYNTAX Counter32
			MAX-ACCESS read-only
			STATUS current
			DESCRIPTION
				"Description."
			::= { apnWlanRxPktsEntry 17 }

		
		-- 1.3.6.1.4.1.388.11.3.9.8.10.1.18
		apnWlanRxPktsAtMCS5 OBJECT-TYPE
			SYNTAX Counter32
			MAX-ACCESS read-only
			STATUS current
			DESCRIPTION
				"Description."
			::= { apnWlanRxPktsEntry 18 }

		
		-- 1.3.6.1.4.1.388.11.3.9.8.10.1.19
		apnWlanRxPktsAtMCS6 OBJECT-TYPE
			SYNTAX Counter32
			MAX-ACCESS read-only
			STATUS current
			DESCRIPTION
				"Description."
			::= { apnWlanRxPktsEntry 19 }

		
		-- 1.3.6.1.4.1.388.11.3.9.8.10.1.20
		apnWlanRxPktsAtMCS7 OBJECT-TYPE
			SYNTAX Counter32
			MAX-ACCESS read-only
			STATUS current
			DESCRIPTION
				"Description."
			::= { apnWlanRxPktsEntry 20 }

		
		-- 1.3.6.1.4.1.388.11.3.9.8.10.1.21
		apnWlanRxPktsAtMCS8 OBJECT-TYPE
			SYNTAX Counter32
			MAX-ACCESS read-only
			STATUS current
			DESCRIPTION
				"Description."
			::= { apnWlanRxPktsEntry 21 }

		
		-- 1.3.6.1.4.1.388.11.3.9.8.10.1.22
		apnWlanRxPktsAtMCS9 OBJECT-TYPE
			SYNTAX Counter32
			MAX-ACCESS read-only
			STATUS current
			DESCRIPTION
				"Description."
			::= { apnWlanRxPktsEntry 22 }

		
		-- 1.3.6.1.4.1.388.11.3.9.8.10.1.23
		apnWlanRxPktsAtMCS10 OBJECT-TYPE
			SYNTAX Counter32
			MAX-ACCESS read-only
			STATUS current
			DESCRIPTION
				"Description."
			::= { apnWlanRxPktsEntry 23 }

		
		-- 1.3.6.1.4.1.388.11.3.9.8.10.1.24
		apnWlanRxPktsAtMCS11 OBJECT-TYPE
			SYNTAX Counter32
			MAX-ACCESS read-only
			STATUS current
			DESCRIPTION
				"Description."
			::= { apnWlanRxPktsEntry 24 }

		
		-- 1.3.6.1.4.1.388.11.3.9.8.10.1.25
		apnWlanRxPktsAtMCS12 OBJECT-TYPE
			SYNTAX Counter32
			MAX-ACCESS read-only
			STATUS current
			DESCRIPTION
				"Description."
			::= { apnWlanRxPktsEntry 25 }

		
		-- 1.3.6.1.4.1.388.11.3.9.8.10.1.26
		apnWlanRxPktsAtMCS13 OBJECT-TYPE
			SYNTAX Counter32
			MAX-ACCESS read-only
			STATUS current
			DESCRIPTION
				"Description."
			::= { apnWlanRxPktsEntry 26 }

		
		-- 1.3.6.1.4.1.388.11.3.9.8.10.1.27
		apnWlanRxPktsAtMCS14 OBJECT-TYPE
			SYNTAX Counter32
			MAX-ACCESS read-only
			STATUS current
			DESCRIPTION
				"Description."
			::= { apnWlanRxPktsEntry 27 }

		
		-- 1.3.6.1.4.1.388.11.3.9.8.10.1.28
		apnWlanRxPktsAtMCS15 OBJECT-TYPE
			SYNTAX Counter32
			MAX-ACCESS read-only
			STATUS current
			DESCRIPTION
				"Description."
			::= { apnWlanRxPktsEntry 28 }

		
		-- 1.3.6.1.4.1.388.11.3.9.8.11
		apnWlanTxPktsTable OBJECT-TYPE
			SYNTAX SEQUENCE OF ApnWlanTxPktsEntry
			MAX-ACCESS not-accessible
			STATUS current
			DESCRIPTION
				"For each wlan on the 802.11n Portal on the AP, 
				this table describes counts of packets transmitted 
				at each speed."
			::= { apnStats 11 }

		
		-- 1.3.6.1.4.1.388.11.3.9.8.11.1
		apnWlanTxPktsEntry OBJECT-TYPE
			SYNTAX ApnWlanTxPktsEntry
			MAX-ACCESS not-accessible
			STATUS current
			DESCRIPTION
				" "
			INDEX { ccWlanIndex }
			::= { apnWlanTxPktsTable 1 }

		
		ApnWlanTxPktsEntry ::=
			SEQUENCE { 
				apnWlanTxPktsAt1Mb
					Counter32,
				apnWlanTxPktsAt2Mb
					Counter32,
				apnWlanTxPktsAt5pt5Mb
					Counter32,
				apnWlanTxPktsAt6Mb
					Counter32,
				apnWlanTxPktsAt9Mb
					Counter32,
				apnWlanTxPktsAt11Mb
					Counter32,
				apnWlanTxPktsAt12Mb
					Counter32,
				apnWlanTxPktsAt18Mb
					Counter32,
				apnWlanTxPktsAt24Mb
					Counter32,
				apnWlanTxPktsAt36Mb
					Counter32,
				apnWlanTxPktsAt48Mb
					Counter32,
				apnWlanTxPktsAt54Mb
					Counter32,
				apnWlanTxPktsAtMCS0
					Counter32,
				apnWlanTxPktsAtMCS1
					Counter32,
				apnWlanTxPktsAtMCS2
					Counter32,
				apnWlanTxPktsAtMCS3
					Counter32,
				apnWlanTxPktsAtMCS4
					Counter32,
				apnWlanTxPktsAtMCS5
					Counter32,
				apnWlanTxPktsAtMCS6
					Counter32,
				apnWlanTxPktsAtMCS7
					Counter32,
				apnWlanTxPktsAtMCS8
					Counter32,
				apnWlanTxPktsAtMCS9
					Counter32,
				apnWlanTxPktsAtMCS10
					Counter32,
				apnWlanTxPktsAtMCS11
					Counter32,
				apnWlanTxPktsAtMCS12
					Counter32,
				apnWlanTxPktsAtMCS13
					Counter32,
				apnWlanTxPktsAtMCS14
					Counter32,
				apnWlanTxPktsAtMCS15
					Counter32
			 }

		-- 1.3.6.1.4.1.388.11.3.9.8.11.1.1
		apnWlanTxPktsAt1Mb OBJECT-TYPE
			SYNTAX Counter32
			MAX-ACCESS read-only
			STATUS current
			DESCRIPTION
				"Number of pkts received via this Portal at 1 and 2 Mbps."
			::= { apnWlanTxPktsEntry 1 }

		
		-- 1.3.6.1.4.1.388.11.3.9.8.11.1.2
		apnWlanTxPktsAt2Mb OBJECT-TYPE
			SYNTAX Counter32
			MAX-ACCESS read-only
			STATUS current
			DESCRIPTION
				"Number of pkts received via this Portal at 1, 2, 5.5 and 11 Mbps."
			::= { apnWlanTxPktsEntry 2 }

		
		-- 1.3.6.1.4.1.388.11.3.9.8.11.1.3
		apnWlanTxPktsAt5pt5Mb OBJECT-TYPE
			SYNTAX Counter32
			MAX-ACCESS read-only
			STATUS current
			DESCRIPTION
				"Number of pkts received via this Portal at 1, 2, 5.5 and 11 Mbps, and, 
				6, 12 and 24 Mbps."
			::= { apnWlanTxPktsEntry 3 }

		
		-- 1.3.6.1.4.1.388.11.3.9.8.11.1.4
		apnWlanTxPktsAt6Mb OBJECT-TYPE
			SYNTAX Counter32
			MAX-ACCESS read-only
			STATUS current
			DESCRIPTION
				"Number of pkts received via this Portal at 1, 2, 5.5 and 11 Mbps, and, 
				6, 12 and 24 Mbps as well as at MCS 0 to 7 rates."
			::= { apnWlanTxPktsEntry 4 }

		
		-- 1.3.6.1.4.1.388.11.3.9.8.11.1.5
		apnWlanTxPktsAt9Mb OBJECT-TYPE
			SYNTAX Counter32
			MAX-ACCESS read-only
			STATUS current
			DESCRIPTION
				"Number of pkts received via this Portal at 6, 12 and 24 Mbps."
			::= { apnWlanTxPktsEntry 5 }

		
		-- 1.3.6.1.4.1.388.11.3.9.8.11.1.6
		apnWlanTxPktsAt11Mb OBJECT-TYPE
			SYNTAX Counter32
			MAX-ACCESS read-only
			STATUS current
			DESCRIPTION
				"Number of pkts received via this Portal at 6, 12 and 24 Mbps as well as 
				at MCS 0 to 7 rates."
			::= { apnWlanTxPktsEntry 6 }

		
		-- 1.3.6.1.4.1.388.11.3.9.8.11.1.7
		apnWlanTxPktsAt12Mb OBJECT-TYPE
			SYNTAX Counter32
			MAX-ACCESS read-only
			STATUS current
			DESCRIPTION
				"Number of pkts received via this Portal at MCS 0 to 7 rates."
			::= { apnWlanTxPktsEntry 7 }

		
		-- 1.3.6.1.4.1.388.11.3.9.8.11.1.8
		apnWlanTxPktsAt18Mb OBJECT-TYPE
			SYNTAX Counter32
			MAX-ACCESS read-only
			STATUS current
			DESCRIPTION
				"Description."
			::= { apnWlanTxPktsEntry 8 }

		
		-- 1.3.6.1.4.1.388.11.3.9.8.11.1.9
		apnWlanTxPktsAt24Mb OBJECT-TYPE
			SYNTAX Counter32
			MAX-ACCESS read-only
			STATUS current
			DESCRIPTION
				"Description."
			::= { apnWlanTxPktsEntry 9 }

		
		-- 1.3.6.1.4.1.388.11.3.9.8.11.1.10
		apnWlanTxPktsAt36Mb OBJECT-TYPE
			SYNTAX Counter32
			MAX-ACCESS read-only
			STATUS current
			DESCRIPTION
				"Description."
			::= { apnWlanTxPktsEntry 10 }

		
		-- 1.3.6.1.4.1.388.11.3.9.8.11.1.11
		apnWlanTxPktsAt48Mb OBJECT-TYPE
			SYNTAX Counter32
			MAX-ACCESS read-only
			STATUS current
			DESCRIPTION
				"Description."
			::= { apnWlanTxPktsEntry 11 }

		
		-- 1.3.6.1.4.1.388.11.3.9.8.11.1.12
		apnWlanTxPktsAt54Mb OBJECT-TYPE
			SYNTAX Counter32
			MAX-ACCESS read-only
			STATUS current
			DESCRIPTION
				"Description."
			::= { apnWlanTxPktsEntry 12 }

		
		-- 1.3.6.1.4.1.388.11.3.9.8.11.1.13
		apnWlanTxPktsAtMCS0 OBJECT-TYPE
			SYNTAX Counter32
			MAX-ACCESS read-only
			STATUS current
			DESCRIPTION
				"Description."
			::= { apnWlanTxPktsEntry 13 }

		
		-- 1.3.6.1.4.1.388.11.3.9.8.11.1.14
		apnWlanTxPktsAtMCS1 OBJECT-TYPE
			SYNTAX Counter32
			MAX-ACCESS read-only
			STATUS current
			DESCRIPTION
				"Description."
			::= { apnWlanTxPktsEntry 14 }

		
		-- 1.3.6.1.4.1.388.11.3.9.8.11.1.15
		apnWlanTxPktsAtMCS2 OBJECT-TYPE
			SYNTAX Counter32
			MAX-ACCESS read-only
			STATUS current
			DESCRIPTION
				"Description."
			::= { apnWlanTxPktsEntry 15 }

		
		-- 1.3.6.1.4.1.388.11.3.9.8.11.1.16
		apnWlanTxPktsAtMCS3 OBJECT-TYPE
			SYNTAX Counter32
			MAX-ACCESS read-only
			STATUS current
			DESCRIPTION
				"Description."
			::= { apnWlanTxPktsEntry 16 }

		
		-- 1.3.6.1.4.1.388.11.3.9.8.11.1.17
		apnWlanTxPktsAtMCS4 OBJECT-TYPE
			SYNTAX Counter32
			MAX-ACCESS read-only
			STATUS current
			DESCRIPTION
				"Description."
			::= { apnWlanTxPktsEntry 17 }

		
		-- 1.3.6.1.4.1.388.11.3.9.8.11.1.18
		apnWlanTxPktsAtMCS5 OBJECT-TYPE
			SYNTAX Counter32
			MAX-ACCESS read-only
			STATUS current
			DESCRIPTION
				"Description."
			::= { apnWlanTxPktsEntry 18 }

		
		-- 1.3.6.1.4.1.388.11.3.9.8.11.1.19
		apnWlanTxPktsAtMCS6 OBJECT-TYPE
			SYNTAX Counter32
			MAX-ACCESS read-only
			STATUS current
			DESCRIPTION
				"Description."
			::= { apnWlanTxPktsEntry 19 }

		
		-- 1.3.6.1.4.1.388.11.3.9.8.11.1.20
		apnWlanTxPktsAtMCS7 OBJECT-TYPE
			SYNTAX Counter32
			MAX-ACCESS read-only
			STATUS current
			DESCRIPTION
				"Description."
			::= { apnWlanTxPktsEntry 20 }

		
		-- 1.3.6.1.4.1.388.11.3.9.8.11.1.21
		apnWlanTxPktsAtMCS8 OBJECT-TYPE
			SYNTAX Counter32
			MAX-ACCESS read-only
			STATUS current
			DESCRIPTION
				"Description."
			::= { apnWlanTxPktsEntry 21 }

		
		-- 1.3.6.1.4.1.388.11.3.9.8.11.1.22
		apnWlanTxPktsAtMCS9 OBJECT-TYPE
			SYNTAX Counter32
			MAX-ACCESS read-only
			STATUS current
			DESCRIPTION
				"Description."
			::= { apnWlanTxPktsEntry 22 }

		
		-- 1.3.6.1.4.1.388.11.3.9.8.11.1.23
		apnWlanTxPktsAtMCS10 OBJECT-TYPE
			SYNTAX Counter32
			MAX-ACCESS read-only
			STATUS current
			DESCRIPTION
				"Description."
			::= { apnWlanTxPktsEntry 23 }

		
		-- 1.3.6.1.4.1.388.11.3.9.8.11.1.24
		apnWlanTxPktsAtMCS11 OBJECT-TYPE
			SYNTAX Counter32
			MAX-ACCESS read-only
			STATUS current
			DESCRIPTION
				"Description."
			::= { apnWlanTxPktsEntry 24 }

		
		-- 1.3.6.1.4.1.388.11.3.9.8.11.1.25
		apnWlanTxPktsAtMCS12 OBJECT-TYPE
			SYNTAX Counter32
			MAX-ACCESS read-only
			STATUS current
			DESCRIPTION
				"Description."
			::= { apnWlanTxPktsEntry 25 }

		
		-- 1.3.6.1.4.1.388.11.3.9.8.11.1.26
		apnWlanTxPktsAtMCS13 OBJECT-TYPE
			SYNTAX Counter32
			MAX-ACCESS read-only
			STATUS current
			DESCRIPTION
				"Description."
			::= { apnWlanTxPktsEntry 26 }

		
		-- 1.3.6.1.4.1.388.11.3.9.8.11.1.27
		apnWlanTxPktsAtMCS14 OBJECT-TYPE
			SYNTAX Counter32
			MAX-ACCESS read-only
			STATUS current
			DESCRIPTION
				"Description."
			::= { apnWlanTxPktsEntry 27 }

		
		-- 1.3.6.1.4.1.388.11.3.9.8.11.1.28
		apnWlanTxPktsAtMCS15 OBJECT-TYPE
			SYNTAX Counter32
			MAX-ACCESS read-only
			STATUS current
			DESCRIPTION
				"Description."
			::= { apnWlanTxPktsEntry 28 }

		
		-- 1.3.6.1.4.1.388.11.3.9.8.12
		apnWlanRxOctetsTable OBJECT-TYPE
			SYNTAX SEQUENCE OF ApnWlanRxOctetsEntry
			MAX-ACCESS not-accessible
			STATUS current
			DESCRIPTION
				"For each wlan on the 802.11n Portal on the AP, 
				this table describes counts of octets received 
				at each speed."
			::= { apnStats 12 }

		
		-- 1.3.6.1.4.1.388.11.3.9.8.12.1
		apnWlanRxOctetsEntry OBJECT-TYPE
			SYNTAX ApnWlanRxOctetsEntry
			MAX-ACCESS not-accessible
			STATUS current
			DESCRIPTION
				" "
			INDEX { ccWlanIndex }
			::= { apnWlanRxOctetsTable 1 }

		
		ApnWlanRxOctetsEntry ::=
			SEQUENCE { 
				apnWlanRxOctetsAt1Mb
					Counter32,
				apnWlanRxOctetsAt2Mb
					Counter32,
				apnWlanRxOctetsAt5pt5Mb
					Counter32,
				apnWlanRxOctetsAt6Mb
					Counter32,
				apnWlanRxOctetsAt9Mb
					Counter32,
				apnWlanRxOctetsAt11Mb
					Counter32,
				apnWlanRxOctetsAt12Mb
					Counter32,
				apnWlanRxOctetsAt18Mb
					Counter32,
				apnWlanRxOctetsAt24Mb
					Counter32,
				apnWlanRxOctetsAt36Mb
					Counter32,
				apnWlanRxOctetsAt48Mb
					Counter32,
				apnWlanRxOctetsAt54Mb
					Counter32,
				apnWlanRxOctetsAtMCS0
					Counter32,
				apnWlanRxOctetsAtMCS1
					Counter32,
				apnWlanRxOctetsAtMCS2
					Counter32,
				apnWlanRxOctetsAtMCS3
					Counter32,
				apnWlanRxOctetsAtMCS4
					Counter32,
				apnWlanRxOctetsAtMCS5
					Counter32,
				apnWlanRxOctetsAtMCS6
					Counter32,
				apnWlanRxOctetsAtMCS7
					Counter32,
				apnWlanRxOctetsAtMCS8
					Counter32,
				apnWlanRxOctetsAtMCS9
					Counter32,
				apnWlanRxOctetsAtMCS10
					Counter32,
				apnWlanRxOctetsAtMCS11
					Counter32,
				apnWlanRxOctetsAtMCS12
					Counter32,
				apnWlanRxOctetsAtMCS13
					Counter32,
				apnWlanRxOctetsAtMCS14
					Counter32,
				apnWlanRxOctetsAtMCS15
					Counter32
			 }

		-- 1.3.6.1.4.1.388.11.3.9.8.12.1.1
		apnWlanRxOctetsAt1Mb OBJECT-TYPE
			SYNTAX Counter32
			MAX-ACCESS read-only
			STATUS current
			DESCRIPTION
				"Number of pkts received via this Portal at 1 and 2 Mbps."
			::= { apnWlanRxOctetsEntry 1 }

		
		-- 1.3.6.1.4.1.388.11.3.9.8.12.1.2
		apnWlanRxOctetsAt2Mb OBJECT-TYPE
			SYNTAX Counter32
			MAX-ACCESS read-only
			STATUS current
			DESCRIPTION
				"Number of pkts received via this Portal at 1, 2, 5.5 and 11 Mbps."
			::= { apnWlanRxOctetsEntry 2 }

		
		-- 1.3.6.1.4.1.388.11.3.9.8.12.1.3
		apnWlanRxOctetsAt5pt5Mb OBJECT-TYPE
			SYNTAX Counter32
			MAX-ACCESS read-only
			STATUS current
			DESCRIPTION
				"Number of pkts received via this Portal at 1, 2, 5.5 and 11 Mbps, and, 
				6, 12 and 24 Mbps."
			::= { apnWlanRxOctetsEntry 3 }

		
		-- 1.3.6.1.4.1.388.11.3.9.8.12.1.4
		apnWlanRxOctetsAt6Mb OBJECT-TYPE
			SYNTAX Counter32
			MAX-ACCESS read-only
			STATUS current
			DESCRIPTION
				"Number of pkts received via this Portal at 1, 2, 5.5 and 11 Mbps, and, 
				6, 12 and 24 Mbps as well as at MCS 0 to 7 rates."
			::= { apnWlanRxOctetsEntry 4 }

		
		-- 1.3.6.1.4.1.388.11.3.9.8.12.1.5
		apnWlanRxOctetsAt9Mb OBJECT-TYPE
			SYNTAX Counter32
			MAX-ACCESS read-only
			STATUS current
			DESCRIPTION
				"Number of pkts received via this Portal at 6, 12 and 24 Mbps."
			::= { apnWlanRxOctetsEntry 5 }

		
		-- 1.3.6.1.4.1.388.11.3.9.8.12.1.6
		apnWlanRxOctetsAt11Mb OBJECT-TYPE
			SYNTAX Counter32
			MAX-ACCESS read-only
			STATUS current
			DESCRIPTION
				"Number of pkts received via this Portal at 6, 12 and 24 Mbps as well as 
				at MCS 0 to 7 rates."
			::= { apnWlanRxOctetsEntry 6 }

		
		-- 1.3.6.1.4.1.388.11.3.9.8.12.1.7
		apnWlanRxOctetsAt12Mb OBJECT-TYPE
			SYNTAX Counter32
			MAX-ACCESS read-only
			STATUS current
			DESCRIPTION
				"Number of pkts received via this Portal at MCS 0 to 7 rates."
			::= { apnWlanRxOctetsEntry 7 }

		
		-- 1.3.6.1.4.1.388.11.3.9.8.12.1.8
		apnWlanRxOctetsAt18Mb OBJECT-TYPE
			SYNTAX Counter32
			MAX-ACCESS read-only
			STATUS current
			DESCRIPTION
				"Description."
			::= { apnWlanRxOctetsEntry 8 }

		
		-- 1.3.6.1.4.1.388.11.3.9.8.12.1.9
		apnWlanRxOctetsAt24Mb OBJECT-TYPE
			SYNTAX Counter32
			MAX-ACCESS read-only
			STATUS current
			DESCRIPTION
				"Description."
			::= { apnWlanRxOctetsEntry 9 }

		
		-- 1.3.6.1.4.1.388.11.3.9.8.12.1.10
		apnWlanRxOctetsAt36Mb OBJECT-TYPE
			SYNTAX Counter32
			MAX-ACCESS read-only
			STATUS current
			DESCRIPTION
				"Description."
			::= { apnWlanRxOctetsEntry 10 }

		
		-- 1.3.6.1.4.1.388.11.3.9.8.12.1.11
		apnWlanRxOctetsAt48Mb OBJECT-TYPE
			SYNTAX Counter32
			MAX-ACCESS read-only
			STATUS current
			DESCRIPTION
				"Description."
			::= { apnWlanRxOctetsEntry 11 }

		
		-- 1.3.6.1.4.1.388.11.3.9.8.12.1.12
		apnWlanRxOctetsAt54Mb OBJECT-TYPE
			SYNTAX Counter32
			MAX-ACCESS read-only
			STATUS current
			DESCRIPTION
				"Description."
			::= { apnWlanRxOctetsEntry 12 }

		
		-- 1.3.6.1.4.1.388.11.3.9.8.12.1.13
		apnWlanRxOctetsAtMCS0 OBJECT-TYPE
			SYNTAX Counter32
			MAX-ACCESS read-only
			STATUS current
			DESCRIPTION
				"Description."
			::= { apnWlanRxOctetsEntry 13 }

		
		-- 1.3.6.1.4.1.388.11.3.9.8.12.1.14
		apnWlanRxOctetsAtMCS1 OBJECT-TYPE
			SYNTAX Counter32
			MAX-ACCESS read-only
			STATUS current
			DESCRIPTION
				"Description."
			::= { apnWlanRxOctetsEntry 14 }

		
		-- 1.3.6.1.4.1.388.11.3.9.8.12.1.15
		apnWlanRxOctetsAtMCS2 OBJECT-TYPE
			SYNTAX Counter32
			MAX-ACCESS read-only
			STATUS current
			DESCRIPTION
				"Description."
			::= { apnWlanRxOctetsEntry 15 }

		
		-- 1.3.6.1.4.1.388.11.3.9.8.12.1.16
		apnWlanRxOctetsAtMCS3 OBJECT-TYPE
			SYNTAX Counter32
			MAX-ACCESS read-only
			STATUS current
			DESCRIPTION
				"Description."
			::= { apnWlanRxOctetsEntry 16 }

		
		-- 1.3.6.1.4.1.388.11.3.9.8.12.1.17
		apnWlanRxOctetsAtMCS4 OBJECT-TYPE
			SYNTAX Counter32
			MAX-ACCESS read-only
			STATUS current
			DESCRIPTION
				"Description."
			::= { apnWlanRxOctetsEntry 17 }

		
		-- 1.3.6.1.4.1.388.11.3.9.8.12.1.18
		apnWlanRxOctetsAtMCS5 OBJECT-TYPE
			SYNTAX Counter32
			MAX-ACCESS read-only
			STATUS current
			DESCRIPTION
				"Description."
			::= { apnWlanRxOctetsEntry 18 }

		
		-- 1.3.6.1.4.1.388.11.3.9.8.12.1.19
		apnWlanRxOctetsAtMCS6 OBJECT-TYPE
			SYNTAX Counter32
			MAX-ACCESS read-only
			STATUS current
			DESCRIPTION
				"Description."
			::= { apnWlanRxOctetsEntry 19 }

		
		-- 1.3.6.1.4.1.388.11.3.9.8.12.1.20
		apnWlanRxOctetsAtMCS7 OBJECT-TYPE
			SYNTAX Counter32
			MAX-ACCESS read-only
			STATUS current
			DESCRIPTION
				"Description."
			::= { apnWlanRxOctetsEntry 20 }

		
		-- 1.3.6.1.4.1.388.11.3.9.8.12.1.21
		apnWlanRxOctetsAtMCS8 OBJECT-TYPE
			SYNTAX Counter32
			MAX-ACCESS read-only
			STATUS current
			DESCRIPTION
				"Description."
			::= { apnWlanRxOctetsEntry 21 }

		
		-- 1.3.6.1.4.1.388.11.3.9.8.12.1.22
		apnWlanRxOctetsAtMCS9 OBJECT-TYPE
			SYNTAX Counter32
			MAX-ACCESS read-only
			STATUS current
			DESCRIPTION
				"Description."
			::= { apnWlanRxOctetsEntry 22 }

		
		-- 1.3.6.1.4.1.388.11.3.9.8.12.1.23
		apnWlanRxOctetsAtMCS10 OBJECT-TYPE
			SYNTAX Counter32
			MAX-ACCESS read-only
			STATUS current
			DESCRIPTION
				"Description."
			::= { apnWlanRxOctetsEntry 23 }

		
		-- 1.3.6.1.4.1.388.11.3.9.8.12.1.24
		apnWlanRxOctetsAtMCS11 OBJECT-TYPE
			SYNTAX Counter32
			MAX-ACCESS read-only
			STATUS current
			DESCRIPTION
				"Description."
			::= { apnWlanRxOctetsEntry 24 }

		
		-- 1.3.6.1.4.1.388.11.3.9.8.12.1.25
		apnWlanRxOctetsAtMCS12 OBJECT-TYPE
			SYNTAX Counter32
			MAX-ACCESS read-only
			STATUS current
			DESCRIPTION
				"Description."
			::= { apnWlanRxOctetsEntry 25 }

		
		-- 1.3.6.1.4.1.388.11.3.9.8.12.1.26
		apnWlanRxOctetsAtMCS13 OBJECT-TYPE
			SYNTAX Counter32
			MAX-ACCESS read-only
			STATUS current
			DESCRIPTION
				"Description."
			::= { apnWlanRxOctetsEntry 26 }

		
		-- 1.3.6.1.4.1.388.11.3.9.8.12.1.27
		apnWlanRxOctetsAtMCS14 OBJECT-TYPE
			SYNTAX Counter32
			MAX-ACCESS read-only
			STATUS current
			DESCRIPTION
				"Description."
			::= { apnWlanRxOctetsEntry 27 }

		
		-- 1.3.6.1.4.1.388.11.3.9.8.12.1.28
		apnWlanRxOctetsAtMCS15 OBJECT-TYPE
			SYNTAX Counter32
			MAX-ACCESS read-only
			STATUS current
			DESCRIPTION
				"Description."
			::= { apnWlanRxOctetsEntry 28 }

		
		-- 1.3.6.1.4.1.388.11.3.9.8.13
		apnWlanTxOctetsTable OBJECT-TYPE
			SYNTAX SEQUENCE OF ApnWlanTxOctetsEntry
			MAX-ACCESS not-accessible
			STATUS current
			DESCRIPTION
				"For each wlan on the 802.11n Portal on the AP, 
				this table describes counts of octets transmitted 
				at each speed."
			::= { apnStats 13 }

		
		-- 1.3.6.1.4.1.388.11.3.9.8.13.1
		apnWlanTxOctetsEntry OBJECT-TYPE
			SYNTAX ApnWlanTxOctetsEntry
			MAX-ACCESS not-accessible
			STATUS current
			DESCRIPTION
				" "
			INDEX { ccWlanIndex }
			::= { apnWlanTxOctetsTable 1 }

		
		ApnWlanTxOctetsEntry ::=
			SEQUENCE { 
				apnWlanTxOctetsAt1Mb
					Counter32,
				apnWlanTxOctetsAt2Mb
					Counter32,
				apnWlanTxOctetsAt5pt5Mb
					Counter32,
				apnWlanTxOctetsAt6Mb
					Counter32,
				apnWlanTxOctetsAt9Mb
					Counter32,
				apnWlanTxOctetsAt11Mb
					Counter32,
				apnWlanTxOctetsAt12Mb
					Counter32,
				apnWlanTxOctetsAt18Mb
					Counter32,
				apnWlanTxOctetsAt24Mb
					Counter32,
				apnWlanTxOctetsAt36Mb
					Counter32,
				apnWlanTxOctetsAt48Mb
					Counter32,
				apnWlanTxOctetsAt54Mb
					Counter32,
				apnWlanTxOctetsAtMCS0
					Counter32,
				apnWlanTxOctetsAtMCS1
					Counter32,
				apnWlanTxOctetsAtMCS2
					Counter32,
				apnWlanTxOctetsAtMCS3
					Counter32,
				apnWlanTxOctetsAtMCS4
					Counter32,
				apnWlanTxOctetsAtMCS5
					Counter32,
				apnWlanTxOctetsAtMCS6
					Counter32,
				apnWlanTxOctetsAtMCS7
					Counter32,
				apnWlanTxOctetsAtMCS8
					Counter32,
				apnWlanTxOctetsAtMCS9
					Counter32,
				apnWlanTxOctetsAtMCS10
					Counter32,
				apnWlanTxOctetsAtMCS11
					Counter32,
				apnWlanTxOctetsAtMCS12
					Counter32,
				apnWlanTxOctetsAtMCS13
					Counter32,
				apnWlanTxOctetsAtMCS14
					Counter32,
				apnWlanTxOctetsAtMCS15
					Counter32
			 }

		-- 1.3.6.1.4.1.388.11.3.9.8.13.1.1
		apnWlanTxOctetsAt1Mb OBJECT-TYPE
			SYNTAX Counter32
			MAX-ACCESS read-only
			STATUS current
			DESCRIPTION
				"Number of pkts received via this Portal at 1 and 2 Mbps."
			::= { apnWlanTxOctetsEntry 1 }

		
		-- 1.3.6.1.4.1.388.11.3.9.8.13.1.2
		apnWlanTxOctetsAt2Mb OBJECT-TYPE
			SYNTAX Counter32
			MAX-ACCESS read-only
			STATUS current
			DESCRIPTION
				"Number of pkts received via this Portal at 1, 2, 5.5 and 11 Mbps."
			::= { apnWlanTxOctetsEntry 2 }

		
		-- 1.3.6.1.4.1.388.11.3.9.8.13.1.3
		apnWlanTxOctetsAt5pt5Mb OBJECT-TYPE
			SYNTAX Counter32
			MAX-ACCESS read-only
			STATUS current
			DESCRIPTION
				"Number of pkts received via this Portal at 1, 2, 5.5 and 11 Mbps, and, 
				6, 12 and 24 Mbps."
			::= { apnWlanTxOctetsEntry 3 }

		
		-- 1.3.6.1.4.1.388.11.3.9.8.13.1.4
		apnWlanTxOctetsAt6Mb OBJECT-TYPE
			SYNTAX Counter32
			MAX-ACCESS read-only
			STATUS current
			DESCRIPTION
				"Number of pkts received via this Portal at 1, 2, 5.5 and 11 Mbps, and, 
				6, 12 and 24 Mbps as well as at MCS 0 to 7 rates."
			::= { apnWlanTxOctetsEntry 4 }

		
		-- 1.3.6.1.4.1.388.11.3.9.8.13.1.5
		apnWlanTxOctetsAt9Mb OBJECT-TYPE
			SYNTAX Counter32
			MAX-ACCESS read-only
			STATUS current
			DESCRIPTION
				"Number of pkts received via this Portal at 6, 12 and 24 Mbps."
			::= { apnWlanTxOctetsEntry 5 }

		
		-- 1.3.6.1.4.1.388.11.3.9.8.13.1.6
		apnWlanTxOctetsAt11Mb OBJECT-TYPE
			SYNTAX Counter32
			MAX-ACCESS read-only
			STATUS current
			DESCRIPTION
				"Number of pkts received via this Portal at 6, 12 and 24 Mbps as well as 
				at MCS 0 to 7 rates."
			::= { apnWlanTxOctetsEntry 6 }

		
		-- 1.3.6.1.4.1.388.11.3.9.8.13.1.7
		apnWlanTxOctetsAt12Mb OBJECT-TYPE
			SYNTAX Counter32
			MAX-ACCESS read-only
			STATUS current
			DESCRIPTION
				"Number of pkts received via this Portal at MCS 0 to 7 rates."
			::= { apnWlanTxOctetsEntry 7 }

		
		-- 1.3.6.1.4.1.388.11.3.9.8.13.1.8
		apnWlanTxOctetsAt18Mb OBJECT-TYPE
			SYNTAX Counter32
			MAX-ACCESS read-only
			STATUS current
			DESCRIPTION
				"Description."
			::= { apnWlanTxOctetsEntry 8 }

		
		-- 1.3.6.1.4.1.388.11.3.9.8.13.1.9
		apnWlanTxOctetsAt24Mb OBJECT-TYPE
			SYNTAX Counter32
			MAX-ACCESS read-only
			STATUS current
			DESCRIPTION
				"Description."
			::= { apnWlanTxOctetsEntry 9 }

		
		-- 1.3.6.1.4.1.388.11.3.9.8.13.1.10
		apnWlanTxOctetsAt36Mb OBJECT-TYPE
			SYNTAX Counter32
			MAX-ACCESS read-only
			STATUS current
			DESCRIPTION
				"Description."
			::= { apnWlanTxOctetsEntry 10 }

		
		-- 1.3.6.1.4.1.388.11.3.9.8.13.1.11
		apnWlanTxOctetsAt48Mb OBJECT-TYPE
			SYNTAX Counter32
			MAX-ACCESS read-only
			STATUS current
			DESCRIPTION
				"Description."
			::= { apnWlanTxOctetsEntry 11 }

		
		-- 1.3.6.1.4.1.388.11.3.9.8.13.1.12
		apnWlanTxOctetsAt54Mb OBJECT-TYPE
			SYNTAX Counter32
			MAX-ACCESS read-only
			STATUS current
			DESCRIPTION
				"Description."
			::= { apnWlanTxOctetsEntry 12 }

		
		-- 1.3.6.1.4.1.388.11.3.9.8.13.1.13
		apnWlanTxOctetsAtMCS0 OBJECT-TYPE
			SYNTAX Counter32
			MAX-ACCESS read-only
			STATUS current
			DESCRIPTION
				"Description."
			::= { apnWlanTxOctetsEntry 13 }

		
		-- 1.3.6.1.4.1.388.11.3.9.8.13.1.14
		apnWlanTxOctetsAtMCS1 OBJECT-TYPE
			SYNTAX Counter32
			MAX-ACCESS read-only
			STATUS current
			DESCRIPTION
				"Description."
			::= { apnWlanTxOctetsEntry 14 }

		
		-- 1.3.6.1.4.1.388.11.3.9.8.13.1.15
		apnWlanTxOctetsAtMCS2 OBJECT-TYPE
			SYNTAX Counter32
			MAX-ACCESS read-only
			STATUS current
			DESCRIPTION
				"Description."
			::= { apnWlanTxOctetsEntry 15 }

		
		-- 1.3.6.1.4.1.388.11.3.9.8.13.1.16
		apnWlanTxOctetsAtMCS3 OBJECT-TYPE
			SYNTAX Counter32
			MAX-ACCESS read-only
			STATUS current
			DESCRIPTION
				"Description."
			::= { apnWlanTxOctetsEntry 16 }

		
		-- 1.3.6.1.4.1.388.11.3.9.8.13.1.17
		apnWlanTxOctetsAtMCS4 OBJECT-TYPE
			SYNTAX Counter32
			MAX-ACCESS read-only
			STATUS current
			DESCRIPTION
				"Description."
			::= { apnWlanTxOctetsEntry 17 }

		
		-- 1.3.6.1.4.1.388.11.3.9.8.13.1.18
		apnWlanTxOctetsAtMCS5 OBJECT-TYPE
			SYNTAX Counter32
			MAX-ACCESS read-only
			STATUS current
			DESCRIPTION
				"Description."
			::= { apnWlanTxOctetsEntry 18 }

		
		-- 1.3.6.1.4.1.388.11.3.9.8.13.1.19
		apnWlanTxOctetsAtMCS6 OBJECT-TYPE
			SYNTAX Counter32
			MAX-ACCESS read-only
			STATUS current
			DESCRIPTION
				"Description."
			::= { apnWlanTxOctetsEntry 19 }

		
		-- 1.3.6.1.4.1.388.11.3.9.8.13.1.20
		apnWlanTxOctetsAtMCS7 OBJECT-TYPE
			SYNTAX Counter32
			MAX-ACCESS read-only
			STATUS current
			DESCRIPTION
				"Description."
			::= { apnWlanTxOctetsEntry 20 }

		
		-- 1.3.6.1.4.1.388.11.3.9.8.13.1.21
		apnWlanTxOctetsAtMCS8 OBJECT-TYPE
			SYNTAX Counter32
			MAX-ACCESS read-only
			STATUS current
			DESCRIPTION
				"Description."
			::= { apnWlanTxOctetsEntry 21 }

		
		-- 1.3.6.1.4.1.388.11.3.9.8.13.1.22
		apnWlanTxOctetsAtMCS9 OBJECT-TYPE
			SYNTAX Counter32
			MAX-ACCESS read-only
			STATUS current
			DESCRIPTION
				"Description."
			::= { apnWlanTxOctetsEntry 22 }

		
		-- 1.3.6.1.4.1.388.11.3.9.8.13.1.23
		apnWlanTxOctetsAtMCS10 OBJECT-TYPE
			SYNTAX Counter32
			MAX-ACCESS read-only
			STATUS current
			DESCRIPTION
				"Description."
			::= { apnWlanTxOctetsEntry 23 }

		
		-- 1.3.6.1.4.1.388.11.3.9.8.13.1.24
		apnWlanTxOctetsAtMCS11 OBJECT-TYPE
			SYNTAX Counter32
			MAX-ACCESS read-only
			STATUS current
			DESCRIPTION
				"Description."
			::= { apnWlanTxOctetsEntry 24 }

		
		-- 1.3.6.1.4.1.388.11.3.9.8.13.1.25
		apnWlanTxOctetsAtMCS12 OBJECT-TYPE
			SYNTAX Counter32
			MAX-ACCESS read-only
			STATUS current
			DESCRIPTION
				"Description."
			::= { apnWlanTxOctetsEntry 25 }

		
		-- 1.3.6.1.4.1.388.11.3.9.8.13.1.26
		apnWlanTxOctetsAtMCS13 OBJECT-TYPE
			SYNTAX Counter32
			MAX-ACCESS read-only
			STATUS current
			DESCRIPTION
				"Description."
			::= { apnWlanTxOctetsEntry 26 }

		
		-- 1.3.6.1.4.1.388.11.3.9.8.13.1.27
		apnWlanTxOctetsAtMCS14 OBJECT-TYPE
			SYNTAX Counter32
			MAX-ACCESS read-only
			STATUS current
			DESCRIPTION
				"Description."
			::= { apnWlanTxOctetsEntry 27 }

		
		-- 1.3.6.1.4.1.388.11.3.9.8.13.1.28
		apnWlanTxOctetsAtMCS15 OBJECT-TYPE
			SYNTAX Counter32
			MAX-ACCESS read-only
			STATUS current
			DESCRIPTION
				"Description."
			::= { apnWlanTxOctetsEntry 28 }

		
		-- 1.3.6.1.4.1.388.11.3.9.9
		apDiagStats OBJECT IDENTIFIER ::= { apStats 9 }

		
		-- 1.3.6.1.4.1.388.11.3.9.9.1
		apDiagCpuStats OBJECT IDENTIFIER ::= { apDiagStats 1 }

		
		-- 1.3.6.1.4.1.388.11.3.9.9.1.1
		apDiagCpuLoad1Min OBJECT-TYPE
			SYNTAX Unsigned32 (0..1000)
			UNITS "%"
			MAX-ACCESS read-only
			STATUS current
			DESCRIPTION
				"% of CPU load averaged over 1 min."
			::= { apDiagCpuStats 1 }

		
		-- 1.3.6.1.4.1.388.11.3.9.9.1.2
		apDiagCpuLoad5Min OBJECT-TYPE
			SYNTAX Unsigned32 (0..1000)
			UNITS "%"
			MAX-ACCESS read-only
			STATUS current
			DESCRIPTION
				"% of CPU load averaged over 5 mins."
			::= { apDiagCpuStats 2 }

		
		-- 1.3.6.1.4.1.388.11.3.9.9.1.3
		apDiagCpuLoad15Min OBJECT-TYPE
			SYNTAX Unsigned32 (0..1000)
			UNITS "%"
			MAX-ACCESS read-only
			STATUS current
			DESCRIPTION
				"% of CPU load averaged over 15 mins."
			::= { apDiagCpuStats 3 }

		
		-- 1.3.6.1.4.1.388.11.3.9.9.2
		apDiagRamStats OBJECT IDENTIFIER ::= { apDiagStats 2 }

		
		-- 1.3.6.1.4.1.388.11.3.9.9.2.1
		apDiagRamTotal OBJECT-TYPE
			SYNTAX Unsigned32
			UNITS "megabytes"
			MAX-ACCESS read-only
			STATUS current
			DESCRIPTION
				"Total RAM available in the system
				"
			::= { apDiagRamStats 1 }

		
		-- 1.3.6.1.4.1.388.11.3.9.9.2.2
		apDiagRamUsed OBJECT-TYPE
			SYNTAX Unsigned32
			UNITS "megabytes"
			MAX-ACCESS read-only
			STATUS current
			DESCRIPTION
				"Total RAM used in the system
				"
			::= { apDiagRamStats 2 }

		
		-- 1.3.6.1.4.1.388.11.3.9.9.2.3
		apDiagRamPercentageUsed OBJECT-TYPE
			SYNTAX Unsigned32 (0..1000)
			UNITS "0.1%"
			MAX-ACCESS read-only
			STATUS current
			DESCRIPTION
				"% of total RAM used. Precision is to the degree of 0.1 %
				"
			::= { apDiagRamStats 3 }

		
		-- 1.3.6.1.4.1.388.11.3.9.10
		apLanStats OBJECT IDENTIFIER ::= { apStats 10 }

		
		-- 1.3.6.1.4.1.388.11.3.9.10.1
		apLanInfoTable OBJECT-TYPE
			SYNTAX SEQUENCE OF ApLanInfoEntry
			MAX-ACCESS not-accessible
			STATUS current
			DESCRIPTION
				"Description."
			::= { apLanStats 1 }

		
		-- 1.3.6.1.4.1.388.11.3.9.10.1.1
		apLanInfoEntry OBJECT-TYPE
			SYNTAX ApLanInfoEntry
			MAX-ACCESS not-accessible
			STATUS current
			DESCRIPTION
				"Description."
			INDEX { apLanInfoIndex }
			::= { apLanInfoTable 1 }

		
		ApLanInfoEntry ::=
			SEQUENCE { 
				apLanInfoIndex
					Integer32,
				apLanInfoEnabled
					TruthValue,
				apLanInfoIpAddress
					IpAddress,
				apLanInfoNetworkMask
					IpAddress,
				apLanInfoEthernetAddress
					PhysAddress,
				apLanInfoSpeed
					Unsigned32,
				apLanInfoDuplexMode
					INTEGER
			 }

		-- 1.3.6.1.4.1.388.11.3.9.10.1.1.1
		apLanInfoIndex OBJECT-TYPE
			SYNTAX Integer32 (1..2)
			MAX-ACCESS accessible-for-notify
			STATUS current
			DESCRIPTION
				"Description."
			::= { apLanInfoEntry 1 }

		
		-- 1.3.6.1.4.1.388.11.3.9.10.1.1.2
		apLanInfoEnabled OBJECT-TYPE
			SYNTAX TruthValue
			MAX-ACCESS read-only
			STATUS current
			DESCRIPTION
				"Is LAN enabled."
			::= { apLanInfoEntry 2 }

		
		-- 1.3.6.1.4.1.388.11.3.9.10.1.1.3
		apLanInfoIpAddress OBJECT-TYPE
			SYNTAX IpAddress
			MAX-ACCESS read-only
			STATUS current
			DESCRIPTION
				"LAN ip address"
			::= { apLanInfoEntry 3 }

		
		-- 1.3.6.1.4.1.388.11.3.9.10.1.1.4
		apLanInfoNetworkMask OBJECT-TYPE
			SYNTAX IpAddress
			MAX-ACCESS read-only
			STATUS current
			DESCRIPTION
				"LAN network mask."
			::= { apLanInfoEntry 4 }

		
		-- 1.3.6.1.4.1.388.11.3.9.10.1.1.5
		apLanInfoEthernetAddress OBJECT-TYPE
			SYNTAX PhysAddress
			MAX-ACCESS read-only
			STATUS current
			DESCRIPTION
				"Description."
			::= { apLanInfoEntry 5 }

		
		-- 1.3.6.1.4.1.388.11.3.9.10.1.1.6
		apLanInfoSpeed OBJECT-TYPE
			SYNTAX Unsigned32
			UNITS "mbps"
			MAX-ACCESS read-only
			STATUS current
			DESCRIPTION
				"Lan Ethernet Port Speed."
			::= { apLanInfoEntry 6 }

		
		-- 1.3.6.1.4.1.388.11.3.9.10.1.1.7
		apLanInfoDuplexMode OBJECT-TYPE
			SYNTAX INTEGER
				{
				half(0),
				full(1)
				}
			MAX-ACCESS read-only
			STATUS current
			DESCRIPTION
				"Lan ethernet port duplex mode."
			::= { apLanInfoEntry 7 }

		
		-- 1.3.6.1.4.1.388.11.3.9.10.2
		apLanRxPktsTable OBJECT-TYPE
			SYNTAX SEQUENCE OF ApLanRxPktsEntry
			MAX-ACCESS not-accessible
			STATUS current
			DESCRIPTION
				"Description."
			::= { apLanStats 2 }

		
		-- 1.3.6.1.4.1.388.11.3.9.10.2.1
		apLanRxPktsEntry OBJECT-TYPE
			SYNTAX ApLanRxPktsEntry
			MAX-ACCESS not-accessible
			STATUS current
			DESCRIPTION
				"Description."
			INDEX { apLanInfoIndex }
			::= { apLanRxPktsTable 1 }

		
		ApLanRxPktsEntry ::=
			SEQUENCE { 
				apLanRxPkts
					Counter32,
				apLanRxBytes
					Counter32,
				apLanRxErrors
					Counter32,
				apLanRxDropped
					Counter32,
				apLanRxFrameErrors
					Counter32
			 }

		-- 1.3.6.1.4.1.388.11.3.9.10.2.1.1
		apLanRxPkts OBJECT-TYPE
			SYNTAX Counter32
			MAX-ACCESS read-only
			STATUS current
			DESCRIPTION
				"Count of packets received."
			::= { apLanRxPktsEntry 1 }

		
		-- 1.3.6.1.4.1.388.11.3.9.10.2.1.2
		apLanRxBytes OBJECT-TYPE
			SYNTAX Counter32
			MAX-ACCESS read-only
			STATUS current
			DESCRIPTION
				"Count of bytes received."
			::= { apLanRxPktsEntry 2 }

		
		-- 1.3.6.1.4.1.388.11.3.9.10.2.1.3
		apLanRxErrors OBJECT-TYPE
			SYNTAX Counter32
			MAX-ACCESS read-only
			STATUS current
			DESCRIPTION
				"Count of errors received."
			::= { apLanRxPktsEntry 3 }

		
		-- 1.3.6.1.4.1.388.11.3.9.10.2.1.4
		apLanRxDropped OBJECT-TYPE
			SYNTAX Counter32
			MAX-ACCESS read-only
			STATUS current
			DESCRIPTION
				"Count of received packets dropped."
			::= { apLanRxPktsEntry 4 }

		
		-- 1.3.6.1.4.1.388.11.3.9.10.2.1.5
		apLanRxFrameErrors OBJECT-TYPE
			SYNTAX Counter32
			MAX-ACCESS read-only
			STATUS current
			DESCRIPTION
				"Count of received frame errors."
			::= { apLanRxPktsEntry 5 }

		
		-- 1.3.6.1.4.1.388.11.3.9.10.4
		apLanTxPktsTable OBJECT-TYPE
			SYNTAX SEQUENCE OF ApLanTxPktsEntry
			MAX-ACCESS not-accessible
			STATUS current
			DESCRIPTION
				"Description."
			::= { apLanStats 4 }

		
		-- 1.3.6.1.4.1.388.11.3.9.10.4.1
		apLanTxPktsEntry OBJECT-TYPE
			SYNTAX ApLanTxPktsEntry
			MAX-ACCESS not-accessible
			STATUS current
			DESCRIPTION
				"Description."
			INDEX { apLanInfoIndex }
			::= { apLanTxPktsTable 1 }

		
		ApLanTxPktsEntry ::=
			SEQUENCE { 
				apLanTxPkts
					Counter32,
				apLanTxBytes
					Counter32,
				apLanTxErrors
					Counter32,
				apLanTxDropped
					Counter32,
				apLanTxFrameErrors
					Counter32
			 }

		-- 1.3.6.1.4.1.388.11.3.9.10.4.1.1
		apLanTxPkts OBJECT-TYPE
			SYNTAX Counter32
			MAX-ACCESS read-only
			STATUS current
			DESCRIPTION
				"Count of packets transmitted."
			::= { apLanTxPktsEntry 1 }

		
		-- 1.3.6.1.4.1.388.11.3.9.10.4.1.2
		apLanTxBytes OBJECT-TYPE
			SYNTAX Counter32
			MAX-ACCESS read-only
			STATUS current
			DESCRIPTION
				"Count of bytes transmitted."
			::= { apLanTxPktsEntry 2 }

		
		-- 1.3.6.1.4.1.388.11.3.9.10.4.1.3
		apLanTxErrors OBJECT-TYPE
			SYNTAX Counter32
			MAX-ACCESS read-only
			STATUS current
			DESCRIPTION
				"Count of errors transmitted."
			::= { apLanTxPktsEntry 3 }

		
		-- 1.3.6.1.4.1.388.11.3.9.10.4.1.4
		apLanTxDropped OBJECT-TYPE
			SYNTAX Counter32
			MAX-ACCESS read-only
			STATUS current
			DESCRIPTION
				"Count of transmitted packets dropped."
			::= { apLanTxPktsEntry 4 }

		
		-- 1.3.6.1.4.1.388.11.3.9.10.4.1.5
		apLanTxFrameErrors OBJECT-TYPE
			SYNTAX Counter32
			MAX-ACCESS read-only
			STATUS current
			DESCRIPTION
				"Count of transmitted carrier errors."
			::= { apLanTxPktsEntry 5 }

		
-- MIB values to control network management access to the
-- switch.
		-- 1.3.6.1.4.1.388.11.3.10
		apMgmtAccess OBJECT IDENTIFIER ::= { abgAP 10 }

		
		-- 1.3.6.1.4.1.388.11.3.10.1
		apMgmtAccessToAllow OBJECT-TYPE
			SYNTAX BITS
				{
				fromLan1AppletHttp(0),
				fromLan1AppletHttps(1),
				fromLan1CliTelnet(2),
				fromLan1Ssh(3),
				fromLan1Snmp(4),
				fromLan2AppletHttp(5),
				fromLan2AppletHttps(6),
				fromLan2CliTelnet(7),
				fromLan2Ssh(8),
				fromLan2Snmp(9),
				fromWanAppletHttp(10),
				fromWanAppletHttps(11),
				fromWanCliTelnet(12),
				fromWanSsh(13),
				fromWanSnmp(14)
				}
			MAX-ACCESS read-write
			STATUS current
			DESCRIPTION
				"Types of network management access to permit."
			::= { apMgmtAccess 1 }

		
		-- 1.3.6.1.4.1.388.11.3.10.2
		apTrustedHost OBJECT IDENTIFIER ::= { apMgmtAccess 2 }

		
		-- 1.3.6.1.4.1.388.11.3.10.2.1
		apTrustedHostEnable OBJECT-TYPE
			SYNTAX TruthValue
			MAX-ACCESS read-write
			STATUS current
			DESCRIPTION
				"Enable trusted host feature."
			::= { apTrustedHost 1 }

		
		-- 1.3.6.1.4.1.388.11.3.10.2.2
		apTrustedHostRangeTable OBJECT-TYPE
			SYNTAX SEQUENCE OF ApTrustedHostRangeEntry
			MAX-ACCESS not-accessible
			STATUS current
			DESCRIPTION
				"Table of trusted host ip ranges."
			::= { apTrustedHost 2 }

		
		-- 1.3.6.1.4.1.388.11.3.10.2.2.1
		apTrustedHostRangeEntry OBJECT-TYPE
			SYNTAX ApTrustedHostRangeEntry
			MAX-ACCESS not-accessible
			STATUS current
			DESCRIPTION
				"Trusted host ip range table entry."
			INDEX { apTrustedHostRangeIndex }
			::= { apTrustedHostRangeTable 1 }

		
		ApTrustedHostRangeEntry ::=
			SEQUENCE { 
				apTrustedHostRangeIndex
					Integer32,
				apTrustedHostRangeLowerIp
					IpAddress,
				apTrustedHostRangeUpperIp
					IpAddress
			 }

		-- 1.3.6.1.4.1.388.11.3.10.2.2.1.1
		apTrustedHostRangeIndex OBJECT-TYPE
			SYNTAX Integer32 (1..8)
			MAX-ACCESS accessible-for-notify
			STATUS current
			DESCRIPTION
				"Trusted host ip range index."
			::= { apTrustedHostRangeEntry 1 }

		
		-- 1.3.6.1.4.1.388.11.3.10.2.2.1.2
		apTrustedHostRangeLowerIp OBJECT-TYPE
			SYNTAX IpAddress
			MAX-ACCESS read-write
			STATUS current
			DESCRIPTION
				"Lower bound of ip address range."
			::= { apTrustedHostRangeEntry 2 }

		
		-- 1.3.6.1.4.1.388.11.3.10.2.2.1.3
		apTrustedHostRangeUpperIp OBJECT-TYPE
			SYNTAX IpAddress
			MAX-ACCESS read-write
			STATUS current
			DESCRIPTION
				"Upper bound of ip address range."
			::= { apTrustedHostRangeEntry 3 }

		
		-- 1.3.6.1.4.1.388.11.3.11
		apRouter OBJECT IDENTIFIER ::= { abgAP 11 }

		
		-- 1.3.6.1.4.1.388.11.3.11.1
		apRouterDefaultGatewayInterface OBJECT-TYPE
			SYNTAX INTEGER
				{
				lan1(1),
				lan2(2),
				wan(3),
				none(4)
				}
			MAX-ACCESS read-write
			STATUS current
			DESCRIPTION
				"Interface whose Default Gateway is used
				when both LAN and WAN are DHCP clients."
			::= { apRouter 1 }

		
		-- 1.3.6.1.4.1.388.11.3.12
		apManualTime OBJECT IDENTIFIER ::= { abgAP 12 }

		
		-- 1.3.6.1.4.1.388.11.3.12.1
		apManualCurrSystemDateTime OBJECT-TYPE
			SYNTAX DisplayString
			MAX-ACCESS read-only
			STATUS current
			DESCRIPTION
				"Current System Time of the AP 5131."
			::= { apManualTime 1 }

		
		-- 1.3.6.1.4.1.388.11.3.12.2
		apManualTimeZoneSetting OBJECT IDENTIFIER ::= { apManualTime 2 }

		
		-- 1.3.6.1.4.1.388.11.3.12.2.1
		apManualTimeZoneTable OBJECT-TYPE
			SYNTAX SEQUENCE OF ApManualTimeZoneEntry
			MAX-ACCESS not-accessible
			STATUS current
			DESCRIPTION
				"Table of all the Time Zones."
			::= { apManualTimeZoneSetting 1 }

		
		-- 1.3.6.1.4.1.388.11.3.12.2.1.1
		apManualTimeZoneEntry OBJECT-TYPE
			SYNTAX ApManualTimeZoneEntry
			MAX-ACCESS not-accessible
			STATUS current
			DESCRIPTION
				" "
			INDEX { apManualTimeZoneIndex }
			::= { apManualTimeZoneTable 1 }

		
		ApManualTimeZoneEntry ::=
			SEQUENCE { 
				apManualTimeZoneIndex
					Integer32,
				apManualTimeZoneName
					DisplayString
			 }

		-- 1.3.6.1.4.1.388.11.3.12.2.1.1.1
		apManualTimeZoneIndex OBJECT-TYPE
			SYNTAX Integer32 (1..550)
			MAX-ACCESS accessible-for-notify
			STATUS current
			DESCRIPTION
				"Simple Index."
			::= { apManualTimeZoneEntry 1 }

		
		-- 1.3.6.1.4.1.388.11.3.12.2.1.1.2
		apManualTimeZoneName OBJECT-TYPE
			SYNTAX DisplayString
			MAX-ACCESS read-only
			STATUS current
			DESCRIPTION
				"Time Zone Name."
			::= { apManualTimeZoneEntry 2 }

		
		-- 1.3.6.1.4.1.388.11.3.12.2.2
		apManualExpectedTimeZone OBJECT-TYPE
			SYNTAX SinglePointer
			MAX-ACCESS read-write
			STATUS current
			DESCRIPTION
				"Expected Time Zone to be set.
				This is a pointer to an entry in the apManualTimeZoneTable."
			::= { apManualTimeZoneSetting 2 }

		
		-- 1.3.6.1.4.1.388.11.3.12.2.3
		apManualTimeZoneSet OBJECT-TYPE
			SYNTAX DoActionNow
			MAX-ACCESS read-write
			STATUS current
			DESCRIPTION
				"Set the expected time zone for the system."
			::= { apManualTimeZoneSetting 3 }

		
		-- 1.3.6.1.4.1.388.11.3.12.3
		apManualDateTimeSetting OBJECT IDENTIFIER ::= { apManualTime 3 }

		
		-- 1.3.6.1.4.1.388.11.3.12.3.1
		apManualExpectedYear OBJECT-TYPE
			SYNTAX Integer32 (1970..9999)
			MAX-ACCESS read-write
			STATUS current
			DESCRIPTION
				"Expected year to be SET."
			::= { apManualDateTimeSetting 1 }

		
		-- 1.3.6.1.4.1.388.11.3.12.3.2
		apManualExpectedMonth OBJECT-TYPE
			SYNTAX Integer32 (1..12)
			MAX-ACCESS read-write
			STATUS current
			DESCRIPTION
				"Expected month to be SET."
			::= { apManualDateTimeSetting 2 }

		
		-- 1.3.6.1.4.1.388.11.3.12.3.3
		apManualExpectedDay OBJECT-TYPE
			SYNTAX Integer32 (1..31)
			MAX-ACCESS read-write
			STATUS current
			DESCRIPTION
				"Expected day to be SET."
			::= { apManualDateTimeSetting 3 }

		
		-- 1.3.6.1.4.1.388.11.3.12.3.4
		apManualExpectedHour OBJECT-TYPE
			SYNTAX Integer32 (0..23)
			MAX-ACCESS read-write
			STATUS current
			DESCRIPTION
				"Expected hour to be SET."
			::= { apManualDateTimeSetting 4 }

		
		-- 1.3.6.1.4.1.388.11.3.12.3.5
		apManualExpectedMinutes OBJECT-TYPE
			SYNTAX Integer32 (0..59)
			MAX-ACCESS read-write
			STATUS current
			DESCRIPTION
				"Expected minutes to be SET."
			::= { apManualDateTimeSetting 5 }

		
		-- 1.3.6.1.4.1.388.11.3.12.3.6
		apManualExpectedSeconds OBJECT-TYPE
			SYNTAX Integer32 (0..59)
			MAX-ACCESS read-write
			STATUS current
			DESCRIPTION
				"Expected seconds to be SET."
			::= { apManualDateTimeSetting 6 }

		
		-- 1.3.6.1.4.1.388.11.3.12.3.7
		apManualDateTimeSet OBJECT-TYPE
			SYNTAX DoActionNow
			MAX-ACCESS read-write
			STATUS current
			DESCRIPTION
				"Set the expected values in System Date and Time."
			::= { apManualDateTimeSetting 7 }

		
		-- 1.3.6.1.4.1.388.11.3.13
		apAdmin OBJECT IDENTIFIER ::= { abgAP 13 }

		
		-- 1.3.6.1.4.1.388.11.3.13.1
		apLoginMessage OBJECT IDENTIFIER ::= { apAdmin 1 }

		
		-- 1.3.6.1.4.1.388.11.3.13.1.1
		apLoginMessageMode OBJECT-TYPE
			SYNTAX TruthValue
			MAX-ACCESS read-write
			STATUS current
			DESCRIPTION
				"Login Message Mode: Enabled/Disabled"
			::= { apLoginMessage 1 }

		
		-- 1.3.6.1.4.1.388.11.3.13.1.2
		apLoginMessageText OBJECT-TYPE
			SYNTAX DisplayString
			MAX-ACCESS read-write
			STATUS current
			DESCRIPTION
				"Login Message Text which gets displayed at the time of login, if Login Message mode is enabled.
				1-511 characters are allowed for Login Text Message.
				Note: Carriage Return (\0A) is not supported by SNMP."
			::= { apLoginMessage 2 }

		
		-- 1.3.6.1.4.1.388.11.3.14
		apRadiusServer OBJECT IDENTIFIER ::= { abgAP 14 }

		
		-- 1.3.6.1.4.1.388.11.3.14.1
		apRadiusUsers OBJECT IDENTIFIER ::= { apRadiusServer 1 }

		
		-- 1.3.6.1.4.1.388.11.3.14.1.1
		apRadiusUsersGroupTable OBJECT-TYPE
			SYNTAX SEQUENCE OF ApRadiusUsersGroupEntry
			MAX-ACCESS not-accessible
			STATUS current
			DESCRIPTION
				"Description."
			::= { apRadiusUsers 1 }

		
		-- 1.3.6.1.4.1.388.11.3.14.1.1.1
		apRadiusUsersGroupEntry OBJECT-TYPE
			SYNTAX ApRadiusUsersGroupEntry
			MAX-ACCESS not-accessible
			STATUS current
			DESCRIPTION
				"Description."
			INDEX { apRadiusUsersGroup }
			::= { apRadiusUsersGroupTable 1 }

		
		ApRadiusUsersGroupEntry ::=
			SEQUENCE { 
				apRadiusUsersGroup
					DisplayString,
				apRadiusUsersGroupRowStatus
					AbbrevRowStatus,
				apRadiusUsersGroupId
					Integer32
			 }

		-- 1.3.6.1.4.1.388.11.3.14.1.1.1.1
		apRadiusUsersGroup OBJECT-TYPE
			SYNTAX DisplayString
			MAX-ACCESS read-write
			STATUS current
			DESCRIPTION
				"Description."
			::= { apRadiusUsersGroupEntry 1 }

		
		-- 1.3.6.1.4.1.388.11.3.14.1.1.1.2
		apRadiusUsersGroupRowStatus OBJECT-TYPE
			SYNTAX AbbrevRowStatus
			MAX-ACCESS read-write
			STATUS current
			DESCRIPTION
				"Description."
			::= { apRadiusUsersGroupEntry 2 }

		
		-- 1.3.6.1.4.1.388.11.3.14.1.1.1.3
		apRadiusUsersGroupId OBJECT-TYPE
			SYNTAX Integer32
			MAX-ACCESS read-write
			STATUS current
			DESCRIPTION
				"Description."
			::= { apRadiusUsersGroupEntry 3 }

		
		-- 1.3.6.1.4.1.388.11.3.14.2
		apRadiusAccess OBJECT IDENTIFIER ::= { apRadiusServer 2 }

		
		-- 1.3.6.1.4.1.388.11.3.14.2.1
		apRadiusAccessTable OBJECT-TYPE
			SYNTAX SEQUENCE OF ApRadiusAccessEntry
			MAX-ACCESS not-accessible
			STATUS current
			DESCRIPTION
				"Description."
			::= { apRadiusAccess 1 }

		
		-- 1.3.6.1.4.1.388.11.3.14.2.1.1
		apRadiusAccessEntry OBJECT-TYPE
			SYNTAX ApRadiusAccessEntry
			MAX-ACCESS not-accessible
			STATUS current
			DESCRIPTION
				"Description."
			INDEX { apRadiusUsersGroup }
			::= { apRadiusAccessTable 1 }

		
		ApRadiusAccessEntry ::=
			SEQUENCE { 
				apRadiusAccessWlanPtrs
					BITS,
				apRadiusAccessTimeRule
					DisplayString
			 }

		-- 1.3.6.1.4.1.388.11.3.14.2.1.1.2
		apRadiusAccessWlanPtrs OBJECT-TYPE
			SYNTAX BITS
				{
				null(0),
				wlan1(1),
				wlan2(2),
				wlan3(3),
				wlan4(4)
				}
			MAX-ACCESS read-write
			STATUS current
			DESCRIPTION
				"Description."
			::= { apRadiusAccessEntry 2 }

		
		-- 1.3.6.1.4.1.388.11.3.14.2.1.1.3
		apRadiusAccessTimeRule OBJECT-TYPE
			SYNTAX DisplayString
			MAX-ACCESS read-write
			STATUS current
			DESCRIPTION
				"Description."
			::= { apRadiusAccessEntry 3 }

		
		-- 1.3.6.1.4.1.388.11.3.15
		apWips OBJECT IDENTIFIER ::= { abgAP 15 }

		
		-- 1.3.6.1.4.1.388.11.3.15.1
		apWipsPrimaryServerAddr OBJECT-TYPE
			SYNTAX IpAddress
			MAX-ACCESS read-write
			STATUS current
			DESCRIPTION
				"The IP address of the primary WIPS server.
				If the IP address is unknown, the value is 0.0.0.0."
			::= { apWips 1 }

		
		-- 1.3.6.1.4.1.388.11.3.15.2
		apWipsSecondaryServerAddr OBJECT-TYPE
			SYNTAX IpAddress
			MAX-ACCESS read-write
			STATUS current
			DESCRIPTION
				"The IP address of the secondary WIPS server.
				If the IP address is unknown, the value is 0.0.0.0."
			::= { apWips 2 }

		
		-- 1.3.6.1.4.1.388.11.3.16
		apPower OBJECT IDENTIFIER ::= { abgAP 16 }

		
		-- 1.3.6.1.4.1.388.11.3.16.1
		apPowerMode OBJECT-TYPE
			SYNTAX INTEGER
				{
				modeAuto(1),
				mode3af(2)
				}
			MAX-ACCESS read-write
			STATUS current
			DESCRIPTION
				"Set the power mode to auto(1) or 3af(2).
				NOTE WELL: Changing the power mode will restart the AP."
			::= { apPower 1 }

		
		-- 1.3.6.1.4.1.388.11.3.16.2
		apPowerDefRadio OBJECT-TYPE
			SYNTAX INTEGER
				{
				radio1(1),
				radio2(2)
				}
			MAX-ACCESS read-write
			STATUS current
			DESCRIPTION
				"Set the default radio to radio1(1) or radio2(2).
				NOTE WELL: Changing the default radio will restart the AP."
			::= { apPower 2 }

		
		-- 1.3.6.1.4.1.388.11.3.16.3
		apPowerStatus OBJECT-TYPE
			SYNTAX INTEGER
				{
				power3af(1),
				mid(2),
				fullAvailable(3)
				}
			MAX-ACCESS read-only
			STATUS current
			DESCRIPTION
				"Current power status - 3af(1), mid(2) or full available (3)"
			::= { apPower 3 }

		
-- !!- OID: located at .1000 to save room above.
		-- 1.3.6.1.4.1.388.11.3.1000
		apGroups OBJECT IDENTIFIER ::= { abgAP 1000 }

		
		-- 1.3.6.1.4.1.388.11.3.1000.1
		apGroupsV1dot0 OBJECT IDENTIFIER ::= { apGroups 1 }

		
		-- 1.3.6.1.4.1.388.11.3.1000.1.1
		dot1xGroup OBJECT-GROUP
			OBJECTS { dot1xPaePortNumber, dot1xPaeState, dot1xAuthBackendAuthState, dot1xAuthAdminControlledDirections, dot1xAuthOperControlledDirections, 
				dot1xAuthAuthControlledPortStatus, dot1xAuthAuthControlledPortControl, dot1xAuthQuietPeriod, dot1xAuthTxPeriod, dot1xAuthSuppTimeout, 
				dot1xAuthServerTimeout, dot1xAuthMaxReq, dot1xAuthReAuthPeriod, dot1xAuthReAuthEnabled, dot1xAuthKeyTxEnabled, 
				dot1xAuthEapolFramesRx, dot1xAuthEapolFramesTx, dot1xAuthEapolStartFramesRx, dot1xAuthEapolLogoffFramesRx, dot1xAuthEapolRespIdFramesRx, 
				dot1xAuthEapolRespFramesRx, dot1xAuthEapolReqIdFramesTx, dot1xAuthEapolReqFramesTx, dot1xAuthInvalidEapolFramesRx, dot1xAuthEapLengthErrorFramesRx, 
				dot1xAuthLastEapolFrameVersion, dot1xAuthLastEapolFrameSource, dot1xAuthEntersConnecting, dot1xAuthEapLogoffsWhileConnecting, dot1xAuthEntersAuthenticating, 
				dot1xAuthAuthSuccessWhileAuthenticating, dot1xAuthAuthTimeoutsWhileAuthenticating, dot1xAuthAuthFailWhileAuthenticating, dot1xAuthAuthReauthsWhileAuthenticating, dot1xAuthAuthEapStartsWhileAuthenticating, 
				dot1xAuthAuthEapLogoffWhileAuthenticating, dot1xAuthAuthReauthsWhileAuthenticated, dot1xAuthAuthEapStartsWhileAuthenticated, dot1xAuthAuthEapLogoffWhileAuthenticated, dot1xAuthBackendResponses, 
				dot1xAuthBackendAccessChallenges, dot1xAuthBackendOtherRequestsToSupplicant, dot1xAuthBackendNonNakResponsesFromSupplicant, dot1xAuthBackendAuthSuccesses, dot1xAuthBackendAuthFails, 
				dot1xAuthSessionOctetsRx, dot1xAuthSessionOctetsTx, dot1xAuthSessionFramesRx, dot1xAuthSessionFramesTx, dot1xAuthSessionId, 
				dot1xAuthSessionAuthenticMethod, dot1xAuthSessionTime, dot1xAuthSessionTerminateCause, dot1xAuthSessionUserName }
			STATUS current
			DESCRIPTION 
				" "
			::= { apGroupsV1dot0 1 }

		
		-- 1.3.6.1.4.1.388.11.3.1000.1.2
		apRfGroup OBJECT-GROUP
			OBJECTS { apRadioSettingsIndex, apRadioSettingsName, apRadioSettingsMacAddress, apRadioSettingsAntenna, apRadioSettingsShortPreamble, 
				apRadioSettingsRtsThresh, apRadioSettingsBeaconInt, apRadioSettingsEnable, apRadioSettingsBand, apRadioSettingsPointersToWlans, 
				apRadioCfgDesPlacement, apRadioCfgPosChannel, apRadioCfgDesChannel, apRadioCfgPosPowerLevel, apRadioCfgDesPowerLevel, 
				apRadioCfgPowerInMW, apRadioCfgSet, apRadioCfgReset, apRadioCfgPlacement, apRadioCfgChannel, 
				apRadioCfgPowerLevel, apRadioBssIndex, apRadioBssPrimaryWlan, apWlanMuAclPointerToAclPolicy, apRadioSettingsBasicRates, 
				apRadioSettingsSupportedRates, apRadioSettingsBackgroundCwMin, apRadioSettingsBackgroundCwMax, apRadioSettingsBackgroundAifsn, apRadioSettingsBackgroundTxopsTime, 
				apRadioSettingsBestEffortCwMin, apRadioSettingsBestEffortCwMax, apRadioSettingsBestEffortAifsn, apRadioSettingsBestEffortTxopsTime, apRadioSettingsVideoCwMin, 
				apRadioSettingsVideoCwMax, apRadioSettingsVideoAifsn, apRadioSettingsVideoTxopsTime, apRadioSettingsVoiceCwMin, apRadioSettingsVoiceCwMax, 
				apRadioSettingsVoiceAifsn, apRadioSettingsVoiceTxopsTime, apWlanIndex, apWlanName, apWlanEssid, 
				apWlanEnable, apWlanUseRadio, apWlanMaxMus, apWlanAclPolicy, apWlanSecurityPolicy, 
				apWlanQosPolicy, apWlanAuthKerberosPassword, apWlanDisallowMuToMu, apWlanUseSecureBeacon, apWlanAnswerBroadcastEss, 
				apWlanSecPolicyIndex, apWlanSecPolicyName, apWlanSecPolicyAuthentication, apWlanSecPolicyEncryption, apWlanAuthEapReauthenticationEnable, 
				apWlanAuthEapReauthenticationPeriod, apWlanAuthEapReauthenticationMaxRetries, apWlanAuthEapRadius1Server, apWlanAuthEapRadius1Port, apWlanAuthEapRadius1SharedSecret, 
				apWlanAuthEapRadius2Server, apWlanAuthEapRadius2Port, apWlanAuthEapRadius2SharedSecret, apWlanAuthEapMuQuietPeriod, apWlanAuthEapMuTimeout, 
				apWlanAuthEapMuTxPeriod, apWlanAuthEapMuMaxRetries, apWlanAuthEapServerTimeout, apWlanAuthEapServerMaxRetries, apWlanAuthKerberosRealmName, 
				apWlanAuthKerberosKdcServerIp1, apWlanAuthKerberosKdcPort1, apWlanAuthKerberosKdcServerIp2, apWlanAuthKerberosKdcPort2, apWlanAuthKerberosKdcServerIpR, 
				apWlanAuthKerberosKdcPortR, apWlanCryptoWepPassKey, apWlanCryptoWepKey1, apWlanCryptoWepKey2, apWlanCryptoWepKey3, 
				apWlanCryptoWepKey4, apWlanCryptoWepKeyToUse, apWlanCryptoTkipBcastKeyRotation, apWlanCryptoTkipKeyRotationInterval, apWlanCryptoTkipKeyToUse, 
				apWlanCryptoTkipPassphrase, apWlanCryptoTkipKey, apWlanCryptoCcmpBcastKeyRotation, apWlanCryptoCcmpKeyRotationInterval, apWlanCryptoCcmpKeyToUse, 
				apWlanCryptoCcmpPassphrase, apWlanCryptoCcmpKey, apWlanCryptoKeyguardKey1, apWlanCryptoKeyguardKey2, apWlanCryptoKeyguardKey3, 
				apWlanCryptoKeyguardKey4, apWlanCryptoKeyguardKeyToUse, apWlanMuAclPolicyIndex, apWlanMuAclPolicyName, apWlanMuAclPolicyAccessMode, 
				apWlanMuAclIndex, apWlanMuAclStartingMac, apWlanMuAclEndingMac, apWlanMuAclRowStatus, apWlanQosPolicyIndex, 
				apWlanQosPolicyName, apWlanEnableWMM, apWlanQosPolicyBackgroundCwMin, apWlanQosPolicyBackgroundCwMax, apWlanQosPolicyBackgroundAifsn, 
				apWlanQosPolicyBackgroundTxopsTime, apWlanQosPolicyBestEffortCwMin, apWlanQosPolicyBestEffortCwMax, apWlanQosPolicyBestEffortAifsn, apWlanQosPolicyBestEffortTxopsTime, 
				apWlanQosPolicyVideoCwMin, apWlanQosPolicyVideoCwMax, apWlanQosPolicyVideoAifsn, apWlanQosPolicyVideoTxopsTime, apWlanQosPolicyVoiceCwMin, 
				apWlanQosPolicyVoiceCwMax, apWlanQosPolicyVoiceAifsn, apWlanQosPolicyVoiceTxopsTime, apWlanVoicePrioritization, apWlanMulticastAddr1, 
				apWlanVlanId, apWlanSecPolicyRowStatus, apWlanMulticastAddr2, apWlanAuthEapRadiusAcctMode, apWlanAuthEapRadiusAcctMuTimeout, 
				apWlanAuthEapRadiusAcctMuRetries, apWlanAuthEapSyslogMode, apWlanAuthEapSyslogServerIp, apWlanSecPolicyPointerToWlan, apWlanMuAclPolicyPointerToWlan, 
				apWlanMuAclPolicyRowStatus, apWlanQosPolicyPointerToWlan, apWlanQosPolicyBackgroundTxopsTimeInMS, apWlanQosPolicyBestEffortTxopsTimeInMS, apWlanQosPolicyVideoTxopsTimeInMS, 
				apWlanQosPolicyVoiceTxopsTimeInMS, apRadioSettingsBGMode, apRadioSettingsBackgroundTxopsTimeInMS, apRadioSettingsVideoTxopsTimeInMS, apRadioCfgDesPowerInMW, 
				apWlanQosPolicyRowStatus, apWlanBwShareMode, apRadioE2BMapStatus, apRadioE2BMapStatusMessage, apWlanCryptoCcmpFastRoamPreAuth, 
				apWlanCryptoCcmpMixedMode, apRadioCfgChannelMode, apWlanAuthKerberosUsername, apRadioWlanBssid, apRadioSettingsE2BMapMessage, 
				apRadioCfgRfFunction, apIpFilterPolicyIndex, apIpFilterPolicyName, apIpFilterPolicyProtocol, apIpFilterPolicySrcStartIp, 
				apIpFilterPolicySrcEndIp, apIpFilterPolicyDestStartIp, apIpFilterPolicyDestEndIp, apIpFilterPolicyUseStatus, apIpFilterPolicyRowStatus, 
				apIpFilterWlanMode, apIpFilterWlanDefInAction, apIpFilterWlanDefOutAction, apIpFilterWlanPolicyIndex, apIpFilterWlanPolicyPolicy, 
				apIpFilterWlanPolicyDirection, apIpFilterWlanPolicyAction, apIpFilterWlanPolicyRowStatus, apIpFilterLanMode, apIpFilterLanDefInAction, 
				apIpFilterLanDefOutAction, apIpFilterLanPolicyIndex, apIpFilterLanPolicyPolicy, apIpFilterLanPolicyDirection, apIpFilterLanPolicyAction, 
				apIpFilterLanPolicyRowStatus, apIpFilterLanIndex, apWlanMuIdleTimeout, apRadioCfgExceptionChannel, apRadioNSettingsMode, 
				apRadioNSettingsHTProtectionStatus, apRadioNSettingsBasicRates, apRadioNCfgPosChannel, apRadioNCfgDesChannel, apRadioNCfgChannel, 
				apRadioNCfgChannelWidth, apRadioNCfgAmsduAggregationMaxRecvSize, apRadioNCfgAmsduTransmitEnabled, apRadioNCfgAmpduAggregationMaxRecvSize, apRadioNCfgAmpduAggregationDensity, 
				apRadioNCfgAmpduTransmitSizeLimit, apRadioNCfgShortGuardInterval, apRadioNCfgAmpduTransmitEnabled, apRadioNCfgChannelOffset, apRadioNMcsRateIndex, 
				apRadioNMcsRate20MHzChanSgiDisabled, apRadioNMcsRate40MHzChanSgiDisabled, apRadioNMcsRate40MHzChanSgiEnabled, apRadioNMcsRateType, apRadioNMcsRateEnabled, 
				apPowerMode, apPowerDefRadio, apPowerStatus, apIpFilterWlanInPackets, apIpFilterWlanOutPackets, 
				apIpFilterWlanPolicyPackets, apIpFilterLanInPackets, apIpFilterLanOutPackets, apIpFilterLanPolicyPackets, apWlanVlanMode, 
				apRadioSettingsBestEffortTxopsTimeInMS, apRadioSettingsVoiceTxopsTimeInMS, apRadioE2BMapStatusBcMcEncCipher, apWlanCryptoKeyguardPassKey, apIpFilterPolicyStartPort, 
				apIpFilterPolicyEndPort, apIpFilterPolicySrcStartPort, apIpFilterPolicySrcEndPort }
			STATUS current
			DESCRIPTION 
				" "
			::= { apGroupsV1dot0 2 }

		
		-- 1.3.6.1.4.1.388.11.3.1000.1.3
		apSwitchGroup OBJECT-GROUP
			OBJECTS { apVlanIndex, apVlanId, apVlanRowStatus, apVlanPointerToWlan, apVlanName, 
				apWnmpPingDestMu, apWnmpPingDestAP, apWnmpPingDest, apWnmpPingNum, apWnmpPingPacketLength, 
				apWnmpPingPacketData, apWnmpPingAction, apWnmpPingNumResponses, apFlashLedDestAP, apFlashLedAction, 
				apKnownApMac, apKnownApIndex, apKnownApIp, apKnownApMu, apKnownApType, 
				apKnownApUnitName, apKnownApPktsPerSec, apSubnetDhcpState, apLan802dt1xAuthLogin, apLan802dt1xAuthPass, 
				apKnownApKbPerSec, apKnownApFwVers, apLanTypeFilterIndex, apLanTypeFilter, apLanTypeFilterRowStatus, 
				apWanVpnKeyAutoSALifeTime, apLanTimeOutValue, apLanTimeOut, apKnownApEssName, apKnownApRadioType1, 
				apKnownApRadioType2, apKnownApChannel1, apKnownApChannel2, apKnownApSendCfgStatus, apKnownApSendCfg
				 }
			STATUS current
			DESCRIPTION 
				" "
			::= { apGroupsV1dot0 3 }

		
		-- 1.3.6.1.4.1.388.11.3.1000.1.4
		apTrapCtrlGroup OBJECT-GROUP
			OBJECTS { apTrapCtrlRateLimit, apTrapCtrlSumStatsIndex, apTrapCtrlSumStatsDescr, apTrapCtrlSumStatsUnits, apTrapCtrlSumStatsCanBeSetMu, 
				apTrapCtrlSumStatsThresholdMu, apTrapCtrlSumStatsCanBeSetRadioA, apTrapCtrlSumStatsThresholdRadioA, apTrapCtrlSumStatsCanBeSetRadioBG, apTrapCtrlSumStatsThresholdRadioBG, 
				apTrapCtrlSumStatsCanBeSetWlan, apTrapCtrlSumStatsThresholdWlans, apTrapCtrlSumStatsCanBeSetAccessPoint, apTrapCtrlSumStatsThresholdAccessPoint, apTrapCtrlEnableIndex, 
				apTrapCtrlEnableName, apTrapCtrlEnable, apTrapRadioMac, apTrapLanMonitorReason, apTrapWpaCounterMeasureEssid, 
				apTrapCtrlSumStatsCanBeSetRadioN2400MHz, apTrapCtrlSumStatsThresholdRadioN2400MHz, apTrapCtrlSumStatsCanBeSetRadioN5000MHz, apTrapCtrlSumStatsThresholdRadioN5000MHz, apTrapLanMonitorMode, 
				apTrapMuMac }
			STATUS current
			DESCRIPTION 
				" "
			::= { apGroupsV1dot0 4 }

		
		-- 1.3.6.1.4.1.388.11.3.1000.1.5
		apRapGroup OBJECT-GROUP
			OBJECTS { apRapDetectorMode }
			STATUS current
			DESCRIPTION 
				" "
			::= { apGroupsV1dot0 5 }

		
		-- 1.3.6.1.4.1.388.11.3.1000.1.6
		apLoadCfgGroup OBJECT-GROUP
			OBJECTS { apLoadCfgOperation, apLoadCfgServerPath, apLoadCfgServerFilename, apLoadCfgServerIpAddr, apLoadCfgFtpUsername, 
				apLoadCfgFtpPassword, apLoadCfgStart, apLoadCfgOperationsDone, apLoadCfgResult, apLoadCfgSuccess
				 }
			STATUS current
			DESCRIPTION 
				" "
			::= { apGroupsV1dot0 6 }

		
		-- 1.3.6.1.4.1.388.11.3.1000.1.7
		apStatsGroup OBJECT-GROUP
			OBJECTS { apWanClearStats, apLanClearStats, apRadioClearStats, apWlanClearStats, apMuClearStats, 
				apKnownAPClearStats, apDiagRamTotal, apnRadioStatsIndex, apnRadioStatsBssid, apnRadioStatsApSsid, 
				apnRadioStatsChannel, apnRadioStatsExtnChannel, apnRadioStatsRssiAvgAcrossAntennas, apnRadioStatsChannelWidthMode, apnRadioStatsOpFreq, 
				apnRadioStatsNumPktsRxSGI400ns, apnRadioStatsNumPktsRxSGI800ns, apnRadioStatsNumPktsTxSGI400ns, apnRadioStatsNumPktsTxSGI800ns, apnRadioStatsNumPktsRxChanWidth20MHz, 
				apnRadioStatsNumPktsRxChanWidth40MHz, apnRadioStatsNumPktsTxChanWidth20MHz, apnRadioStatsNumPktsTxChanWidth40MHz, apnPortalRxPktsAt1Mb, apnPortalRxPktsAt2Mb, 
				apnPortalRxPktsAt5pt5Mb, apnPortalRxPktsAt6Mb, apnPortalRxPktsAt9Mb, apnPortalRxPktsAt11Mb, apnPortalRxPktsAt12Mb, 
				apnPortalRxPktsAt18Mb, apnPortalRxPktsAt24Mb, apnPortalRxPktsAt36Mb, apnPortalRxPktsAt48Mb, apnPortalRxPktsAt54Mb, 
				apnPortalRxPktsAtMCS0, apnPortalRxPktsAtMCS1, apnPortalRxPktsAtMCS2, apnPortalRxPktsAtMCS3, apnPortalRxPktsAtMCS4, 
				apnPortalRxPktsAtMCS5, apnPortalRxPktsAtMCS6, apnPortalRxPktsAtMCS7, apnPortalRxPktsAtMCS8, apnPortalRxPktsAtMCS9, 
				apnPortalRxPktsAtMCS10, apnPortalRxPktsAtMCS11, apnPortalRxPktsAtMCS12, apnPortalRxPktsAtMCS13, apnPortalRxPktsAtMCS14, 
				apnPortalRxPktsAtMCS15, apnPortalTxPktsAt1Mb, apnPortalTxPktsAt2Mb, apnPortalTxPktsAt5pt5Mb, apnPortalTxPktsAt6Mb, 
				apnPortalTxPktsAt9Mb, apnPortalTxPktsAt11Mb, apnPortalTxPktsAt12Mb, apnPortalTxPktsAt18Mb, apnPortalTxPktsAt24Mb, 
				apnPortalTxPktsAt36Mb, apnPortalTxPktsAt48Mb, apnPortalTxPktsAt54Mb, apnPortalTxPktsAtMCS0, apnPortalTxPktsAtMCS1, 
				apnPortalTxPktsAtMCS2, apnPortalTxPktsAtMCS3, apnPortalTxPktsAtMCS4, apnPortalTxPktsAtMCS5, apnPortalTxPktsAtMCS6, 
				apnPortalTxPktsAtMCS7, apnPortalTxPktsAtMCS8, apnPortalTxPktsAtMCS9, apnPortalTxPktsAtMCS10, apnPortalTxPktsAtMCS11, 
				apnPortalTxPktsAtMCS12, apnPortalTxPktsAtMCS13, apnPortalTxPktsAtMCS14, apnPortalTxPktsAtMCS15, apnPortalRxOctetsAt1Mb, 
				apnPortalRxOctetsAt2Mb, apnPortalRxOctetsAt5pt5Mb, apnPortalRxOctetsAt6Mb, apnPortalRxOctetsAt9Mb, apnPortalRxOctetsAt11Mb, 
				apnPortalRxOctetsAt12Mb, apnPortalRxOctetsAt18Mb, apnPortalRxOctetsAt24Mb, apnPortalRxOctetsAt36Mb, apnPortalRxOctetsAt48Mb, 
				apnPortalRxOctetsAt54Mb, apnPortalRxOctetsAtMCS0, apnPortalRxOctetsAtMCS1, apnPortalRxOctetsAtMCS2, apnPortalRxOctetsAtMCS3, 
				apnPortalRxOctetsAtMCS4, apnPortalRxOctetsAtMCS5, apnPortalRxOctetsAtMCS6, apnPortalRxOctetsAtMCS7, apnPortalRxOctetsAtMCS8, 
				apnPortalRxOctetsAtMCS9, apnPortalRxOctetsAtMCS10, apnPortalRxOctetsAtMCS11, apnPortalRxOctetsAtMCS12, apnPortalRxOctetsAtMCS13, 
				apnPortalRxOctetsAtMCS14, apnPortalRxOctetsAtMCS15, apnPortalTxOctetsAt1Mb, apnPortalTxOctetsAt2Mb, apnPortalTxOctetsAt5pt5Mb, 
				apnPortalTxOctetsAt6Mb, apnPortalTxOctetsAt9Mb, apnPortalTxOctetsAt11Mb, apnPortalTxOctetsAt12Mb, apnPortalTxOctetsAt18Mb, 
				apnPortalTxOctetsAt24Mb, apnPortalTxOctetsAt36Mb, apnPortalTxOctetsAt48Mb, apnPortalTxOctetsAt54Mb, apnPortalTxOctetsAtMCS0, 
				apnPortalTxOctetsAtMCS1, apnPortalTxOctetsAtMCS2, apnPortalTxOctetsAtMCS3, apnPortalTxOctetsAtMCS4, apnPortalTxOctetsAtMCS5, 
				apnPortalTxOctetsAtMCS6, apnPortalTxOctetsAtMCS7, apnPortalTxOctetsAtMCS8, apnPortalTxOctetsAtMCS9, apnPortalTxOctetsAtMCS10, 
				apnPortalTxOctetsAtMCS11, apnPortalTxOctetsAtMCS12, apnPortalTxOctetsAtMCS13, apnPortalTxOctetsAtMCS14, apnPortalTxOctetsAtMCS15, 
				apnMuRxPktsAt1Mb, apnMuRxPktsAt2Mb, apnMuRxPktsAt5pt5Mb, apnMuRxPktsAt6Mb, apnMuRxPktsAt9Mb, 
				apnMuRxPktsAt11Mb, apnMuRxPktsAt12Mb, apnMuRxPktsAt18Mb, apnMuRxPktsAt24Mb, apnMuRxPktsAt36Mb, 
				apnMuRxPktsAt48Mb, apnMuRxPktsAt54Mb, apnMuRxPktsAtMCS0, apnMuRxPktsAtMCS1, apnMuRxPktsAtMCS2, 
				apnMuRxPktsAtMCS3, apnMuRxPktsAtMCS4, apnMuRxPktsAtMCS5, apnMuRxPktsAtMCS6, apnMuRxPktsAtMCS7, 
				apnMuRxPktsAtMCS8, apnMuRxPktsAtMCS9, apnMuRxPktsAtMCS10, apnMuRxPktsAtMCS11, apnMuRxPktsAtMCS12, 
				apnMuRxPktsAtMCS13, apnMuRxPktsAtMCS14, apnMuRxPktsAtMCS15, apnMuTxPktsAt1Mb, apnMuTxPktsAt2Mb, 
				apnMuTxPktsAt5pt5Mb, apnMuTxPktsAt6Mb, apnMuTxPktsAt9Mb, apnMuTxPktsAt11Mb, apnMuTxPktsAt12Mb, 
				apnMuTxPktsAt18Mb, apnMuTxPktsAt24Mb, apnMuTxPktsAt36Mb, apnMuTxPktsAt48Mb, apnMuTxPktsAt54Mb, 
				apnMuTxPktsAtMCS0, apnMuTxPktsAtMCS1, apnMuTxPktsAtMCS2, apnMuTxPktsAtMCS3, apnMuTxPktsAtMCS4, 
				apnMuTxPktsAtMCS5, apnMuTxPktsAtMCS6, apnMuTxPktsAtMCS7, apnMuTxPktsAtMCS8, apnMuTxPktsAtMCS9, 
				apnMuTxPktsAtMCS10, apnMuTxPktsAtMCS11, apnMuTxPktsAtMCS12, apnMuTxPktsAtMCS13, apnMuTxPktsAtMCS14, 
				apnMuTxPktsAtMCS15, apnMuRxOctetsAt1Mb, apnMuRxOctetsAt2Mb, apnMuRxOctetsAt5pt5Mb, apnMuRxOctetsAt6Mb, 
				apnMuRxOctetsAt9Mb, apnMuRxOctetsAt11Mb, apnMuRxOctetsAt12Mb, apnMuRxOctetsAt18Mb, apnMuRxOctetsAt24Mb, 
				apnMuRxOctetsAt36Mb, apnMuRxOctetsAt48Mb, apnMuRxOctetsAt54Mb, apnMuRxOctetsAtMCS0, apnMuRxOctetsAtMCS1, 
				apnMuRxOctetsAtMCS2, apnMuRxOctetsAtMCS3, apnMuRxOctetsAtMCS4, apnMuRxOctetsAtMCS5, apnMuRxOctetsAtMCS6, 
				apnMuRxOctetsAtMCS7, apnMuRxOctetsAtMCS8, apnMuRxOctetsAtMCS9, apnMuRxOctetsAtMCS10, apnMuRxOctetsAtMCS11, 
				apnMuRxOctetsAtMCS12, apnMuRxOctetsAtMCS13, apnMuRxOctetsAtMCS14, apnMuRxOctetsAtMCS15, apnMuTxOctetsAt1Mb, 
				apnMuTxOctetsAt2Mb, apnMuTxOctetsAt5pt5Mb, apnMuTxOctetsAt6Mb, apnMuTxOctetsAt9Mb, apnMuTxOctetsAt11Mb, 
				apnMuTxOctetsAt12Mb, apnMuTxOctetsAt18Mb, apnMuTxOctetsAt24Mb, apnMuTxOctetsAt36Mb, apnMuTxOctetsAt48Mb, 
				apnMuTxOctetsAt54Mb, apnMuTxOctetsAtMCS0, apnMuTxOctetsAtMCS1, apnMuTxOctetsAtMCS2, apnMuTxOctetsAtMCS3, 
				apnMuTxOctetsAtMCS4, apnMuTxOctetsAtMCS5, apnMuTxOctetsAtMCS6, apnMuTxOctetsAtMCS7, apnMuTxOctetsAtMCS8, 
				apnMuTxOctetsAtMCS9, apnMuTxOctetsAtMCS10, apnMuTxOctetsAtMCS11, apnMuTxOctetsAtMCS12, apnMuTxOctetsAtMCS13, 
				apnMuTxOctetsAtMCS14, apnMuTxOctetsAtMCS15, apnWlanRxPktsAt1Mb, apnWlanRxPktsAt2Mb, apnWlanRxPktsAt5pt5Mb, 
				apnWlanRxPktsAt6Mb, apnWlanRxPktsAt9Mb, apnWlanRxPktsAt11Mb, apnWlanRxPktsAt12Mb, apnWlanRxPktsAt18Mb, 
				apnWlanRxPktsAt24Mb, apnWlanRxPktsAt36Mb, apnWlanRxPktsAt48Mb, apnWlanRxPktsAt54Mb, apnWlanRxPktsAtMCS0, 
				apnWlanRxPktsAtMCS1, apnWlanRxPktsAtMCS2, apnWlanRxPktsAtMCS3, apnWlanRxPktsAtMCS4, apnWlanRxPktsAtMCS5, 
				apnWlanRxPktsAtMCS6, apnWlanRxPktsAtMCS7, apnWlanRxPktsAtMCS8, apnWlanRxPktsAtMCS9, apnWlanRxPktsAtMCS10, 
				apnWlanRxPktsAtMCS11, apnWlanRxPktsAtMCS12, apnWlanRxPktsAtMCS13, apnWlanRxPktsAtMCS14, apnWlanRxPktsAtMCS15, 
				apnWlanTxPktsAt1Mb, apnWlanTxPktsAt2Mb, apnWlanTxPktsAt5pt5Mb, apnWlanTxPktsAt6Mb, apnWlanTxPktsAt9Mb, 
				apnWlanTxPktsAt11Mb, apnWlanTxPktsAt12Mb, apnWlanTxPktsAt18Mb, apnWlanTxPktsAt24Mb, apnWlanTxPktsAt36Mb, 
				apnWlanTxPktsAt48Mb, apnWlanTxPktsAt54Mb, apnWlanTxPktsAtMCS0, apnWlanTxPktsAtMCS1, apnWlanTxPktsAtMCS2, 
				apnWlanTxPktsAtMCS3, apnWlanTxPktsAtMCS4, apnWlanTxPktsAtMCS5, apnWlanTxPktsAtMCS6, apnWlanTxPktsAtMCS7, 
				apnWlanTxPktsAtMCS8, apnWlanTxPktsAtMCS9, apnWlanTxPktsAtMCS10, apnWlanTxPktsAtMCS11, apnWlanTxPktsAtMCS12, 
				apnWlanTxPktsAtMCS13, apnWlanTxPktsAtMCS14, apnWlanTxPktsAtMCS15, apnWlanRxOctetsAt1Mb, apnWlanRxOctetsAt2Mb, 
				apnWlanRxOctetsAt5pt5Mb, apnWlanRxOctetsAt6Mb, apnWlanRxOctetsAt9Mb, apnWlanRxOctetsAt11Mb, apnWlanRxOctetsAt12Mb, 
				apnWlanRxOctetsAt18Mb, apnWlanRxOctetsAt24Mb, apnWlanRxOctetsAt36Mb, apnWlanRxOctetsAt48Mb, apnWlanRxOctetsAt54Mb, 
				apnWlanRxOctetsAtMCS0, apnWlanRxOctetsAtMCS1, apnWlanRxOctetsAtMCS2, apnWlanRxOctetsAtMCS3, apnWlanRxOctetsAtMCS4, 
				apnWlanRxOctetsAtMCS5, apnWlanRxOctetsAtMCS6, apnWlanRxOctetsAtMCS7, apnWlanRxOctetsAtMCS8, apnWlanRxOctetsAtMCS9, 
				apnWlanRxOctetsAtMCS10, apnWlanRxOctetsAtMCS11, apnWlanRxOctetsAtMCS12, apnWlanRxOctetsAtMCS13, apnWlanRxOctetsAtMCS14, 
				apnWlanRxOctetsAtMCS15, apnWlanTxOctetsAt1Mb, apnWlanTxOctetsAt2Mb, apnWlanTxOctetsAt5pt5Mb, apnWlanTxOctetsAt6Mb, 
				apnWlanTxOctetsAt9Mb, apnWlanTxOctetsAt11Mb, apnWlanTxOctetsAt12Mb, apnWlanTxOctetsAt18Mb, apnWlanTxOctetsAt24Mb, 
				apnWlanTxOctetsAt36Mb, apnWlanTxOctetsAt48Mb, apnWlanTxOctetsAt54Mb, apnWlanTxOctetsAtMCS0, apnWlanTxOctetsAtMCS1, 
				apnWlanTxOctetsAtMCS2, apnWlanTxOctetsAtMCS3, apnWlanTxOctetsAtMCS4, apnWlanTxOctetsAtMCS5, apnWlanTxOctetsAtMCS6, 
				apnWlanTxOctetsAtMCS7, apnWlanTxOctetsAtMCS8, apnWlanTxOctetsAtMCS9, apnWlanTxOctetsAtMCS10, apnWlanTxOctetsAtMCS11, 
				apnWlanTxOctetsAtMCS12, apnWlanTxOctetsAtMCS13, apnWlanTxOctetsAtMCS14, apnWlanTxOctetsAtMCS15, apLanRxDropped, 
				apLanRxFrameErrors, apLanInfoSpeed, apLanInfoDuplexMode, apLanRxPkts, apLanRxBytes, 
				apLanRxErrors, apLanInfoIndex, apLanInfoEnabled, apLanInfoIpAddress, apLanInfoNetworkMask, 
				apLanInfoEthernetAddress, apLanTxPkts, apLanTxBytes, apLanTxErrors, apLanTxDropped, 
				apLanTxFrameErrors, apDiagRamUsed, apDiagCpuLoad1Min, apDiagCpuLoad5Min, apDiagCpuLoad15Min, 
				apDiagRamPercentageUsed }
			STATUS current
			DESCRIPTION 
				" "
			::= { apGroupsV1dot0 7 }

		
		-- 1.3.6.1.4.1.388.11.3.1000.1.8
		apNotificationsGroup NOTIFICATION-GROUP
			NOTIFICATIONS { apWpaCounterMeasure, apLanMonitor, apMuVlan }
			STATUS current
			DESCRIPTION 
				" "
			::= { apGroupsV1dot0 8 }

		
		-- 1.3.6.1.4.1.388.11.3.1000.2
		apGroupsV1dot1 OBJECT IDENTIFIER ::= { apGroups 2 }

		
		-- 1.3.6.1.4.1.388.11.3.1000.2.1
		apGroupV1dot1variables OBJECT-GROUP
			OBJECTS { apSubnetTypeFilterAccessMode, apSubnetVlanEnable, apLanTypeFilterSubnetIndex, apMgmtAccessToAllow, apTrapCtrlMuMac, 
				apTrapCtrlMuHotspotStateChange, apHotSpotDefaultFileMode, apHotSpotExternalLoginPageUrl, apHotSpotExternalWelomePageUrl, apHotSpotExternalFailPageUrl, 
				apHotSpotRadiusAcctMode, apHotSpotRadiusAcctTimeout, apHotSpotRadiusAcctRetryCount, apHotSpotPriRadiusServerIp, apHotSpotPriRadiusPort, 
				apHotSpotPriRadiusSecret, apHotSpotSecRadiusServerIp, apHotSpotSecRadiusPort, apHotSpotSecRadiusSecret, apHotSpotWhiteListIndex, 
				apHotSpotWhiteListWalledGardenIp, apHotSpotWhiteListRowStatus, apLanEthernetPort, apWlanSubnet, apRouterDefaultGatewayInterface, 
				apWlanAuthEapRadiusExtAcctServer, apWlanAuthEapRadiusExtPort, apWlanAuthEapRadiusExtSharedSecret, apManualCurrSystemDateTime, apManualTimeZoneIndex, 
				apManualTimeZoneName, apManualExpectedTimeZone, apHotSpotRadiusAcctServerIp, apHotSpotRadiusAcctPort, apHotSpotRadiusAcctSecret, 
				apRadioSettingsERPProtectionStatus, apWlanClientBackHaul, apKnownApIndex, apKnownApRadio1ClientBridgeMac1, apKnownApRadio1ClientBridgeMac2, 
				apKnownApRadio1ClientBridgeMac3, apKnownApRadio2ClientBridgeMac1, apKnownApRadio2ClientBridgeMac2, apKnownApRadio2ClientBridgeMac3, apWanPppoeClientIndex, 
				apWanPppoeClientIp, apWanPppoeClientGateway, apWanPppoeClientPrimaryDNSServer, apWanPppoeClientSecondaryDNSServer, apSubnetAdminVlanTag, 
				apSubnetNativeVlanTag, apRadioBssDtimPrd, apWlanHotspot, apManualTimeZoneSet, apManualExpectedYear, 
				apManualExpectedMonth, apManualExpectedDay, apManualExpectedHour, apManualExpectedMinutes, apManualExpectedSeconds, 
				apManualDateTimeSet, apWlanWMMQosParam, apRadioSettingsWMMQosParam, apRadioMeshBaseBridgeMode, apRadioMeshMaxClients, 
				apRadioMeshClientBridgeMode, apRadioMeshWlanPtr, apLanBridgePriority, apLanBridgeMaxMsgAge, apMeshStatsIndex, 
				apMeshStatsConnType, apMeshStatsMac, apMeshStatsWlanPtr, apMeshStatsRadioType, apMeshStatsThroughput, 
				apMeshStatsAvgBitSpeed, apMeshStatsRetries, apMeshBridgeStatsIndex, apMeshBridgeStatsMac, apMeshBridgeStatsWlanPtr, 
				apMeshBridgeStatsLanPtr, apMeshBridgeStatsRadioType, apMeshBridgeStatsAuthType, apMeshBridgeStatsEncType, apMeshBridgeStatsPktsPerSecRx, 
				apMeshBridgeStatsPksPerSecTx, apMeshBridgeStatsPktsPerSecTotal, apMeshBridgeStatsThroughputRx, apMeshBridgeStatsThroughputTx, apMeshBridgeStatsThroughputTotal, 
				apMeshBridgeStatsAvgBitSpeed, apMeshBridgeStatsAvgMuSignal, apMeshBridgeStatsAvgMuNoise, apMeshBridgeStatsAvgMuSnr, apMeshBridgeStatsAvgRetries, 
				apMeshBridgeStatsPktsDropped, apLanSTPStatsDesignatedRoot, apLanSTPStatsBridgeId, apLanSTPStatsRootPort, apLanSTPStatsRootPathCost, 
				apLanSTPStatsBridgeMaxMsgAge, apLanSTPStatsBridgeHelloTime, apLanSTPStatsBridgeFwDelay, apLanSTPStatsPortIntfLanIndex, apLanSTPStatsPortIntfPortIndex, 
				apLanSTPStatsPortIntfPortName, apLanSTPStatsPortIntfState, apLanSTPStatsPortIntfPathCost, apLanSTPStatsPortIntfDsgRoot, apLanSTPStatsPortIntfDsgBridge, 
				apLanSTPStatsPortIntfDsgPort, apLanSTPStatsPortIntfDsgCost, apWlanCryptoKeyguardMixedMode, apWlanCryptoWepMixedMode, apRadioMeshConnAutoSelect, 
				apRadioMeshAvailableConnIndex, apRadioMeshAvailableConnMac, apRadioMeshAvailableConnChannel, apRadioMeshAvailableConnRssi, apRadioMeshPreferredConnPriority, 
				apRadioMeshPreferredConnMac, apRadioMeshPreferredConnRowStatus, apRadioMeshPreferredConnIndex, apTrapVlanId, apHotSpotRadiusSessMode, 
				apHotSpotRadiusSessTimeout, apLanPortDuplex, apLanPortSpeed, apLanPortAutoNegotiation, apWanPortDuplex, 
				apWanPortSpeed, apWanPortAutoNegotiation, apRadioMeshTimeout, apRadioMeshTimeoutValue, apWlanCryptoTkipFastRoamPreAuth, 
				apWlanCryptoTkipAllowWpa2Client, apWanDynDNSMode, apWanDynDNSUsername, apWanDynDNSPassword, apWanDynDNSHostname, 
				apWanDynDNSIndex, apWanDynDNSUpdateHostname, apWanDynDNSUpdateIp, apWanDynDNSUpdateStatus, apWanDynDNSUpdateResponseIndex, 
				apWanDynDNSPerformUpdate, apTrapCtrlDynDNSUpdateIp, apTrapCtrlDynDNSUpdateHostname, apTrapCtrlDynDNSUpdateStatus, apLoginMessageMode, 
				apLoginMessageText, apRadioSettingsQBSSChannelBeaconInt, apRadioWlanWeight, apRadiusUsersGroup, apRadiusUsersGroupRowStatus, 
				apRadiusUsersGroupId, apRadiusAccessWlanPtrs, apRadiusAccessTimeRule, apRadioSettingsQBSSLoadElementMode, apRapDetectorABGMode, 
				apMeshBridgeStatsUndecryptablePkts, apLanBridgeHelloTime, apLanBridgeFwdDelay, apLanBridgeEntryAgeout, apAapSwitchDiscoveryIPAddressRowStatus, 
				apAapSwitchDiscoveryIPAddress, apAapSwitchDiscoveryIPAddressIndex, apAapSwitchDiscoveryPort, apAapSwitchDiscoveryInterface, apAapSwitchDiscoveryDomainName, 
				apAapTunnelToSwitchEnable, apAapAcKeepAlive, apAapAdoptionState, apAapAdoptingSwitchIP, apMuLocationingIndex, 
				apMuLocationingMuMac, apMuLocationingPortalMac, apMuLocationingSignalStrength, apMuLocationingHeardChannel, apMuLocationingHeardTime, 
				apMuLocationingAddMuMac, apMuLocationingAddPortalMac, apMuLocationingAddSignalStrength, apMuLocationingAddHeardChannel, apMuLocationingAddHeardTime, 
				apAapPassphrase, apWipsSecondaryServerAddr, apWipsPrimaryServerAddr, apTrustedHostEnable, apTrustedHostRangeIndex, 
				apTrustedHostRangeLowerIp, apTrustedHostRangeUpperIp, apAapSwitchAutoDiscoveryEnable, apMuLocationingEnable, apMuLocationingClear, 
				apMuLocationingMaxMus }
			STATUS current
			DESCRIPTION 
				"Description."
			::= { apGroupsV1dot1 1 }

		
		-- 1.3.6.1.4.1.388.11.3.1000.2.2
		apGroupV1dot1obsoleted OBJECT-GROUP
			OBJECTS { apLanAdminVlanTag, apLanNativeVlanTag, apRadioSettingsDtimPrd, apRadioSettingsVoiceMode, apRadioSettingsVideoMode, 
				apRadioSettingsBestEffortMode, apRadioSettingsBackgroundMode, apWlanWeight, apLanTypeFilterAccessMode, apLanVlanEnable
				 }
			STATUS obsolete
			DESCRIPTION 
				"Description."
			::= { apGroupsV1dot1 2 }

		
		-- 1.3.6.1.4.1.388.11.3.1000.2.3
		apGroupV1dot1deprecated OBJECT-GROUP
			OBJECTS { apLanEnable, apRadioNMcsRate20MHzChanSgiEnabled }
			STATUS deprecated
			DESCRIPTION 
				"Description."
			::= { apGroupsV1dot1 3 }

		
		-- 1.3.6.1.4.1.388.11.3.1000.2.4
		apGroupV1dot1notifications NOTIFICATION-GROUP
			NOTIFICATIONS { apMuHotspotState, apDynDNSUpdate }
			STATUS current
			DESCRIPTION 
				"Description."
			::= { apGroupsV1dot1 4 }

		
		-- 1.3.6.1.4.1.388.11.3.1000.3
		apGroupsV2dot2 OBJECT IDENTIFIER ::= { apGroups 3 }

		
		-- 1.3.6.1.4.1.388.11.3.1000.3.1
		apGroupV2dot2variables OBJECT-GROUP
			OBJECTS { apReliableMulticastMode, apReliableMulticastWlan, apReliableMulticastStandaloneMode, apReliableMulticastIgmpQueryVersion, apReliableMulticastIgmpQueryInterval, 
				apReliableMulticastAddrIndex, apReliableMulticastAddress, apReliableMulticastMUStatsIPAddr, apReliableMulticastMUMacAddr, apReliableMulticastTxMulticast, 
				apReliableMulticastTableRowEnable, apReliableMulticastMUStatsIndex, apReliableMulticastMaxStreams }
			STATUS current
			DESCRIPTION 
				"Description."
			::= { apGroupsV2dot2 1 }

		
	
	END

--
-- SYMBOL-AP-MIB-01g13.mib
--
