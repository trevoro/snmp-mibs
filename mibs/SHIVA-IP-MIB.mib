-- 	$Id: shiva-ip.asn,v 1.12 1996/01/16 16:41:27 dfox Exp $

--
-- 	Copyright 1992, 1993, 1995, 1996 Shiva Corporation
--

--	Supplementary TCP/IP-related variables

SHIVA-IP-MIB DEFINITIONS ::= BEGIN

IMPORTS
	IpAddress
  		FROM RFC1155-SMI
	OBJECT-TYPE
		FROM RFC-1212		-- Concise MIB Definitions
	tIP
		FROM SHIVA-MIB;


    tARPClearCache OBJECT-TYPE
	SYNTAX	INTEGER { clear(1) }
	ACCESS  read-write
	STATUS  mandatory
	DESCRIPTION
		"Writing this variable clears the ARP Cache."
	::= { tIP 1 }

    tIPClearRedirects OBJECT-TYPE
	SYNTAX	INTEGER { clear(1) }
	ACCESS  read-write
	STATUS  mandatory
	DESCRIPTION
		"Writing this variable removes all ICMP from the
		IP routing table."
	::= { tIP 2 }

    tUDPChecksums OBJECT-TYPE
	SYNTAX INTEGER { enabled(1), disabled(2) }
	ACCESS read-write
	STATUS mandatory
	DESCRIPTION
		"Indicates whether checksums will be calculated
		and verified for locally generated and received UDP
		packets."
	::= { tIP 3 }

    tIPBroadCastFill OBJECT-TYPE
	SYNTAX INTEGER { ones(1), zeroes(2) }
	ACCESS read-write
	STATUS mandatory
	DESCRIPTION
		"Indicates whether locally calculated broadcast address
		will be one-fill or zero-fill."
	::= { tIP 4 }

-- time server table

    tTimeServerTable OBJECT-TYPE
	SYNTAX SEQUENCE OF TTimeServerEntry
	ACCESS not-accessible
	STATUS mandatory
	DESCRIPTION
		"Table of RFC858 UDP Time servers."
	::= { tIP 5 }

    tTimeServerEntry OBJECT-TYPE
	SYNTAX TTimeServerEntry
	ACCESS not-accessible
	STATUS mandatory
	DESCRIPTION
		"An entry in the Time Server table"
	INDEX { INTEGER }
	::= { tTimeServerTable 1 }

    TTimeServerEntry ::= SEQUENCE {
	tTimeServerAddress IpAddress
    }

    tTimeServerAddress OBJECT-TYPE
	SYNTAX IpAddress
	ACCESS read-write
	STATUS mandatory
	DESCRIPTION
		"The Address of the time server."
	::= { tTimeServerEntry 1 }

-- name server table

    tNameServerTable OBJECT-TYPE
	SYNTAX SEQUENCE OF TNameServerEntry
	ACCESS not-accessible
	STATUS mandatory
	DESCRIPTION
		"Table of Domain Name Servers."
	::= { tIP 6 }

    tNameServerEntry OBJECT-TYPE
	SYNTAX TNameServerEntry
	ACCESS not-accessible
	STATUS mandatory
	DESCRIPTION
		"An entry in the Name Server table"
	INDEX { INTEGER }
	::= { tNameServerTable 1 }

    TNameServerEntry ::= SEQUENCE {
	tNameServerAddress IpAddress
    }

    tNameServerAddress OBJECT-TYPE
	SYNTAX IpAddress
	ACCESS read-write
	STATUS mandatory
	DESCRIPTION
		"The Address of the name server."
	::= { tNameServerEntry 1 }

    tBootServerAddress OBJECT-TYPE
	SYNTAX IpAddress
	ACCESS read-only
	STATUS mandatory
	DESCRIPTION
		"The Address of the server from which the system last
		retrieved an image and configuration."
	::= { tIP 7 }

-- serial IP address table

    tSerialIpAddressTable OBJECT-TYPE
	SYNTAX SEQUENCE OF TSerialIpAddressEntry
	ACCESS not-accessible
	STATUS mandatory
	DESCRIPTION
		"Table of Serial IP addresses and default addresses
		indexed by serial line number."
	::= { tIP 8 }

    tSerialIpAddressEntry OBJECT-TYPE
	SYNTAX TSerialIpAddressEntry
	ACCESS not-accessible
	STATUS mandatory
	DESCRIPTION
		"An entry in the Serial IP Address table"
	INDEX { tSerialIpAddressIndex }
	::= { tSerialIpAddressTable 1 }

    TSerialIpAddressEntry ::= SEQUENCE {
	tSerialIpAddressIndex INTEGER,
	tSerialIpAddressLocalDefaultAddress IpAddress,
	tSerialIpAddressRemoteDefaultAddress IpAddress,
	tSerialIpAddressLocalAddress IpAddress,
	tSerialIpAddressRemoteAddress IpAddress
    }

    tSerialIpAddressIndex OBJECT-TYPE
	SYNTAX INTEGER
	ACCESS read-only
	STATUS mandatory
	DESCRIPTION
		"A serial line number."
	::= { tSerialIpAddressEntry 1 }

    tSerialIpAddressLocalDefaultAddress OBJECT-TYPE
	SYNTAX IpAddress
	ACCESS read-write
	STATUS mandatory
	DESCRIPTION
		"The default local IP address for this serial line."
	::= { tSerialIpAddressEntry 2 }

    tSerialIpAddressRemoteDefaultAddress OBJECT-TYPE
	SYNTAX IpAddress
	ACCESS read-write
	STATUS deprecated
	DESCRIPTION
		"The default remote IP address for this serial line.
		
		Deprecated, always 0."
	::= { tSerialIpAddressEntry 3 }

    tSerialIpAddressLocalAddress OBJECT-TYPE
	SYNTAX IpAddress
	ACCESS read-write
	STATUS deprecated
	DESCRIPTION
		"The local IP address in use on this serial line.
		
		Deprecated, always 0."
	::= { tSerialIpAddressEntry 4 }

    tSerialIpAddressRemoteAddress OBJECT-TYPE
	SYNTAX IpAddress
	ACCESS read-write
	STATUS mandatory
	DESCRIPTION
		"The remote IP address in use on this serial line."
	::= { tSerialIpAddressEntry 5 }

    tAcceptAnyClientAddr OBJECT-TYPE
	SYNTAX INTEGER { enabled(1), disabled(2) }
	ACCESS read-write
	STATUS mandatory
	DESCRIPTION
		"Indicates whether IP addresses proposed by the client
		will be accepted without checking against configured
		(per-port, per-user, etc) addresses."
	::= { tIP 9 }

    tNumIpRoutes OBJECT-TYPE
	SYNTAX INTEGER
	ACCESS read-only
	STATUS mandatory
	DESCRIPTION
		"Number of routes in the entity's IP routing table."
	::= { tIP 10 }

    tUseConfiguredUserAddr OBJECT-TYPE
	SYNTAX INTEGER { enabled(1), disabled(2) }
	ACCESS read-only
	STATUS mandatory
	DESCRIPTION
		"Indicates whether IP addresses configured for users
		will be a determinant in IP address assignment policy
 		for dialin clients.  The four possible sources 
		of IP addresses are as follows: 1) client-proposed
		address, 2) user record address, 3) address pool, and 
		4) address from Dynamic Host Configuration Protocol 
		(DHCP) server.  These sources are checked in order, but 
		a source is only checked if it is enabled as a
		determinant."
	::= { tIP 11 }

    tUseConfiguredPortAddr OBJECT-TYPE
	SYNTAX INTEGER { disabled(2) }
	ACCESS read-only
	STATUS deprecated
	DESCRIPTION
		"Indicates whether IP addresses configured for ports
		will be a determinant in IP address assignment policy 
		for dialin clients.  The four possible sources 
		of IP addresses are as follows: 1) client-proposed
		address, 2) user record address, 3) address pool, and 
		4) address from Dynamic Host Configuration Protocol 
		(DHCP) server.  These sources are checked in order, but 
		a source is only checked if it is enabled as a
		determinant.

		Deprecated, always returns disabled(2)"
	::= { tIP 12 }

    tUseDHCPAddr OBJECT-TYPE
	SYNTAX INTEGER { enabled(1), disabled(2) }
	ACCESS read-only
	STATUS mandatory
	DESCRIPTION
		"Indicates whether IP addresses will be obtained for
		dialin clients via the 	Dynamic Host Configuration 
		Protocol.  The four possible sources of IP addresses 
		are as follows: 1) client-proposed address, 2) user 
		record address, 3) address pool, and 4) address from 
		Dynamic Host Configuration Protocol (DHCP) server.  
		These sources are checked in order, but a source is 
		only checked if it is enabled as a determinant."
	::= { tIP 13 }

    tHomeIPAddr OBJECT-TYPE
	SYNTAX IpAddress
	ACCESS read-only
	STATUS mandatory
	DESCRIPTION
		"The IP Address of the home (main) IP interface.  It
		is implict that there is one main IP address which the
		device prefers to use as its source address for
		internally generated IP traffic which is not in
		response to received IP packets.  Technically this
		address is already available via the ipAddrTable, but
		since this table is indexed by IP address a GetNext
		is needed in order to access the table to determine
		an IP address, and this is not always practical."
	::= { tIP 14 }

    tUsePoolAddr OBJECT-TYPE
	SYNTAX INTEGER { enabled(1), disabled(2) }
	ACCESS read-only
	STATUS mandatory
	DESCRIPTION
		"Indicates whether IP addresses from the IP address pool
		will be a determinant in IP address assignment policy 
		for dialin clients.  The four possible sources 
		of IP addresses are as follows: 1) client-proposed
		address, 2) user record address, 3) address pool, and 
		4) address from Dynamic Host Configuration Protocol 
		(DHCP) server.  These sources are checked in order, but 
		a source is only checked if it is enabled as a
		determinant."
	::= { tIP 15 }

END
