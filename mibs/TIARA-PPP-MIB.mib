-- *****************************************************************
-- tiaranet-ppp.mib:  Tiara Networks PPP/MLPPP MIB
--
-- July,1st 1999, kumar
--
-- Copyright (c) 1999-2000 by Tiara Networks, Inc.
-- All rights reserved.
--
-- *****************************************************************


TIARA-PPP-MIB DEFINITIONS ::= BEGIN

IMPORTS
	MODULE-IDENTITY, OBJECT-TYPE, 
	IpAddress, Integer32, Counter32  
                    FROM SNMPv2-SMI
	DisplayString                 
                    FROM RFC1213-MIB
	bundleId
                    FROM TIARA-BUNDLE-MIB
        tiaraMgmt   
                    FROM TIARA-NETWORKS-SMI;


tiaraPppMib MODULE-IDENTITY
	LAST-UPDATED "0002010000Z" 
	ORGANIZATION "Tiara Networks Inc."
	CONTACT-INFO
		 "       Tiara Networks
                         Customer Support

                	 525 Race Street, Suite 100,
                         San Jose, CA 95126
                         USA

        	         Tel: +1 408-216-4700
                         Fax: +1 408-216-4701

                	 E-mail: support@tiaranetworks.com"

	DESCRIPTION
		"The MIB module defines the managed objects for Tiara
        enterrpise PPP/MLPPP. "
        REVISION     "0002010000Z"
        DESCRIPTION  
                "Initial Revision."
        ::= { tiaraMgmt 14 }

-- PPP Table definition
--
-- pppTable contains configurable parameters for PPP and
-- MLPPP configuration. The index to the table is bundleId which
-- uniquely identifies the PPP/MLPPP bundle. bundleId is an unique 
-- integer assigned to each bundle during creation and it has a 
-- one-to-one mapping to the name of the bundle. The entries in 
-- the pppTable are created implicitly once the bundle is encapsulated 
-- to PPP. MLPPP parameters can be configured only for MLPPP bundles. 

pppTable 	OBJECT-TYPE
	SYNTAX		SEQUENCE OF PppTableEntry
	MAX-ACCESS	not-accessible
	STATUS 		current
	DESCRIPTION
		"This table contains configurable parameters related to 
                PPP/MLPPP bundle."
	::= {tiaraPppMib 1}

pppTableEntry	OBJECT-TYPE
	SYNTAX			PppTableEntry
	MAX-ACCESS		not-accessible
	STATUS			current
	DESCRIPTION
                "An entry in the PPP Table which contains the configuration
                for a particular bundle instance identified by the bundleId." 
	INDEX	{ bundleId }
	::= {pppTable 1}

PppTableEntry ::= SEQUENCE {
        pppMtu    		DisplayString,
        pppMru    		DisplayString,
        mlpppMrru       	DisplayString,  
        mlpppSeq    	INTEGER,
        mlpppSegmentThreshold   Integer32,
        mlpppDiffDelay  Integer32,
        mlpppDiscriminator      IpAddress
	}

pppMtu	OBJECT-TYPE
	SYNTAX	DisplayString	
	MAX-ACCESS	read-write
	STATUS	current
	DESCRIPTION 
		"Minimum, default and maximum packet sizes to be sent 
		separated by hyphens."
	DEFVAL { "64-1500-4096" }
	::= { pppTableEntry 1}

pppMru	OBJECT-TYPE
	SYNTAX	DisplayString	
	MAX-ACCESS	read-write
	STATUS	current
	DESCRIPTION 
		"Minimum, default and maximum packet sizes to be  
		received separated by hyphens."
	DEFVAL { "46-1500-4096" }
	::= { pppTableEntry 2}

mlpppMrru	OBJECT-TYPE
	SYNTAX	DisplayString	
	MAX-ACCESS	read-write
	STATUS	current
	DESCRIPTION 
		"Maximum received reconstructed unit - maximum number 
		of octets in the information fields of reassembled packets.
                This variable can be set only if the bundle is multi-link."
	DEFVAL { "1500-1524-8192" }
	::= {pppTableEntry 3}

mlpppSeq	OBJECT-TYPE
	SYNTAX INTEGER {
		short(1),
		long(2)
		}
	MAX-ACCESS	read-write
	STATUS	current
	DESCRIPTION 
		"MLPPP sequence number length (short = 12 bits ; long = 
		24 bits. This variable can be set only if the bundle is 
                multi-link."
	DEFVAL { long }
	::= { pppTableEntry 4}


mlpppSegmentThreshold	OBJECT-TYPE
	SYNTAX	Integer32 
	MAX-ACCESS	read-write
	STATUS	current
	DESCRIPTION 
		"Segmentation threshold - number of octets a packet must 
		exceed before being fragmented for transmission. This 
                variable can be set only if the bundle is multi-link."
	DEFVAL { 512 }
	::= { pppTableEntry 5}


mlpppDiffDelay	OBJECT-TYPE
	SYNTAX	Integer32 (0..128)
	MAX-ACCESS	read-write
	STATUS	current
	DESCRIPTION 
		"Tolerance, in milliseconds, to differential delay 
		between links. If The differential delay exceeds this 
                limit, the corresponding link will be removed from the 
                bundle. This variable can be set only if the bundle is 
                multi-link."
	DEFVAL {128}
	::= { pppTableEntry 6}


mlpppDiscriminator	OBJECT-TYPE
	SYNTAX	IpAddress
	MAX-ACCESS	read-write
	STATUS	current
	DESCRIPTION 
		"IP address of MLPPP discriminator. This variable can 
                 be set only if the bundle is multi-link."
	::= { pppTableEntry 7}

-- PppStatsTable Definition
--
-- pppStats Table contains the statistics counters for the PPP/MLPPP 
-- encapsulated bundles. 

pppStatsTable 	OBJECT-TYPE
	SYNTAX		SEQUENCE OF PppStatsTableEntry
	MAX-ACCESS	not-accessible
	STATUS 		current
	DESCRIPTION
		"This table contains the statistics for PPP/MLPPP bundles."
	::= {tiaraPppMib 2}

pppStatsTableEntry	OBJECT-TYPE
	SYNTAX			PppStatsTableEntry
	MAX-ACCESS		not-accessible
	STATUS			current
	DESCRIPTION
		"An entry in the PPP Statistics Table which contains 
                the statistics for a particular bundle instance 
                identified by the bundleId." 
	INDEX	{ bundleId }
	::= {pppStatsTable 1}

PppStatsTableEntry ::= SEQUENCE {
        pppStatsBytesRxLastBootOrClear    Counter32,
        pppStatsBytesTxLastBootOrClear    Counter32,
        pppStatsPktsRxLastBootOrClear  Counter32,
        pppStatsPktsTxLastBootOrClear  Counter32,
        pppStatsErrPktsRxLastBootOrClear  Counter32,
        pppStatsUpDownStatesLastBootOrClear  Counter32,
        pppStatsBytesRxLastFiveMins  Counter32,
        pppStatsBytesTxLastFiveMins  Counter32,
        pppStatsPktsRxLastFiveMins  Counter32,
        pppStatsPktsTxLastFiveMins Counter32,
        pppStatsErrPktsRxLastFiveMins  Counter32,
        pppStatsUpDownStatesLastFiveMins Counter32
	}
	
pppStatsBytesRxLastBootOrClear	OBJECT-TYPE
	SYNTAX	Counter32
	MAX-ACCESS	read-only
	STATUS	current
	DESCRIPTION 
		"This counter has the number of bytes received 
                on this bundle since it was last booted or cleared."
	::= { pppStatsTableEntry 1 }

pppStatsBytesTxLastBootOrClear	OBJECT-TYPE
	SYNTAX	Counter32
	MAX-ACCESS	read-only
	STATUS	current
	DESCRIPTION 
		"This counter has the number of bytes transmitted 
                on this bundle since it was last booted or cleared."
	::= { pppStatsTableEntry 2 }

pppStatsPktsRxLastBootOrClear	OBJECT-TYPE
	SYNTAX	Counter32
	MAX-ACCESS	read-only
	STATUS	current
	DESCRIPTION 
		"This counter has the number of packets received 
                on this bundle since it was last booted or cleared."
	::= { pppStatsTableEntry 3 }

pppStatsPktsTxLastBootOrClear	OBJECT-TYPE
	SYNTAX	Counter32
	MAX-ACCESS	read-only
	STATUS	current
	DESCRIPTION 
		"This counter has the number of packets transmitted 
                on this bundle since it was last booted or cleared."
	::= { pppStatsTableEntry 4 }

pppStatsErrPktsRxLastBootOrClear	OBJECT-TYPE
	SYNTAX	Counter32
	MAX-ACCESS	read-only
	STATUS	current
	DESCRIPTION 
		"This counter has the number of error packets 
                received on this bundle since it was last booted 
                or cleared."
	::= { pppStatsTableEntry 5 }

pppStatsUpDownStatesLastBootOrClear	OBJECT-TYPE
	SYNTAX	Counter32
	MAX-ACCESS	read-only
	STATUS	current
	DESCRIPTION 
		"This variable has the count on the number of 
                times this PPP/MLPPP bundle have made the 'Down' 
                to 'Up' and 'Up' to 'Down' transitions  since it 
                was last booted or cleared."
	::= { pppStatsTableEntry 6 }

pppStatsBytesRxLastFiveMins	OBJECT-TYPE
	SYNTAX	Counter32
	MAX-ACCESS	read-only
	STATUS	current
	DESCRIPTION 
		"This counter has the number of bytes received on 
                 this bundle in the last 5 minutes."
	::= { pppStatsTableEntry 7 }

pppStatsBytesTxLastFiveMins	OBJECT-TYPE
	SYNTAX	Counter32
	MAX-ACCESS	read-only
	STATUS	current
	DESCRIPTION 
		"This counter has the number of bytes transmitted 
                on this bundle in the last 5 minutes."
	::= { pppStatsTableEntry 8 }

pppStatsPktsRxLastFiveMins	OBJECT-TYPE
	SYNTAX	Counter32
	MAX-ACCESS	read-only
	STATUS	current
	DESCRIPTION 
		"This counter has the number of packets received on 
                this bundle in the last 5 minutes."
	::= { pppStatsTableEntry 9 }

pppStatsPktsTxLastFiveMins	OBJECT-TYPE
	SYNTAX	Counter32
	MAX-ACCESS	read-only
	STATUS	current
	DESCRIPTION 
		"This counter has the number of packets transmitted on 
                this bundle in the last 5 minutes."
	::= { pppStatsTableEntry 10 }

pppStatsErrPktsRxLastFiveMins	OBJECT-TYPE
	SYNTAX	Counter32
	MAX-ACCESS	read-only
	STATUS	current
	DESCRIPTION 
		"This counter has the number of error packets received 
                on this bundle in the last 5 minutes."
	::= { pppStatsTableEntry 11 }

pppStatsUpDownStatesLastFiveMins	OBJECT-TYPE
	SYNTAX	Counter32
	MAX-ACCESS	read-only
	STATUS	current
	DESCRIPTION 
		"This variable has the count on the number of times 
                this PPP/MLPPP bundle have made the 'Down' to 'Up' 
                and 'Up' to 'Down' transitions  in the last 5 minutes."
	::= { pppStatsTableEntry 12 }

END
