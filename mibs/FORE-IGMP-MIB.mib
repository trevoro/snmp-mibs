--
-- Copyright 1999 by Fore Systems, Inc.
-- Converted to SMIv2 rfc 2578,2579,2580 - STD 58
--
-- Copyright 1996 by Fore Systems, Inc.  All rights reserved.

-- This file contains definitions for management information for extensions to
-- the Bridge MIB (RFC-1493) needed for products produced by FORE Systems, Inc.

--------------------------------------------------------------------------------

FORE-IGMP-MIB DEFINITIONS ::= BEGIN

IMPORTS
    OBJECT-TYPE,
    MODULE-IDENTITY,
    IpAddress		    FROM SNMPv2-SMI
    DisplayString           FROM SNMPv2-TC
    preDot1qVlanMIB         FROM Fore-Common-MIB;
    
foreIgmpModule		MODULE-IDENTITY
    LAST-UPDATED        "9911050000Z"
    ORGANIZATION        "MARCONI"
    CONTACT-INFO
			"      Postal:   Marconi plc.
					 1000 FORE Drive
					 Warrendale, PA 15086-7502
					 Tel:      +1 724 742 6900
					 Email:    nm_mibs@fore.com
					 Web:      http://www.marconi.com"
    DESCRIPTION 	"Fore ethernet igmp mib."
::= { preDot1qVlanMIB 3 }

--------------------------------------------------------------------------------

igmpIpmcTable OBJECT-TYPE
    SYNTAX  	SEQUENCE OF IgmpIpmcEntry
    MAX-ACCESS  not-accessible
    STATUS  	current
    DESCRIPTION
	"Table that contains information IP Multicast addresses and the 
	 associated ports in a given vlan."
    ::= { foreIgmpModule 1 }

igmpIpmcEntry OBJECT-TYPE
    SYNTAX  	IgmpIpmcEntry
    MAX-ACCESS  not-accessible
    STATUS  	current
    DESCRIPTION
	"A list of information maintained for each IP Multicast address."
    INDEX   { vlan,
	      ipMulticastAddress
	    }
    ::= { igmpIpmcTable 1 }

IgmpIpmcEntry ::= SEQUENCE {
	vlan			DisplayString,
	ipMulticastAddress	IpAddress,
	ipmcPortGroup		DisplayString
    }

ipMulticastAddress OBJECT-TYPE
    SYNTAX 	IpAddress
    MAX-ACCESS  read-only
    STATUS      current
    DESCRIPTION
	"The IP multicast address for which the port group is needed."
    ::= { igmpIpmcEntry 1}

ipmcPortGroup OBJECT-TYPE
    SYNTAX  	DisplayString (SIZE (1..100))
    MAX-ACCESS  read-only
    STATUS  	current
    DESCRIPTION
	"The port group for which this entry contains IP multicast info."
    ::= { igmpIpmcEntry 2}

igmpRouterTable OBJECT-TYPE
    SYNTAX  	SEQUENCE OF IgmpRouterEntry
    MAX-ACCESS  not-accessible
    STATUS  	current
    DESCRIPTION
	"Table that contains multicast router port groups."
    ::= { foreIgmpModule 2 }

igmpRouterEntry OBJECT-TYPE
    SYNTAX  	IgmpRouterEntry
    MAX-ACCESS  not-accessible
    STATUS  	current
    DESCRIPTION
	"A list of information maintained for each vlan."
    INDEX   { vlan }
    ::= { igmpRouterTable 1 }

IgmpRouterEntry ::= SEQUENCE {
	vlan			DisplayString,
	routerPortGroup		DisplayString
    }

vlan OBJECT-TYPE
    SYNTAX 	DisplayString (SIZE (1..32))
    MAX-ACCESS  read-only
    STATUS      current
    DESCRIPTION
	"The vlan name for which the router port group is needed."
    ::= { igmpRouterEntry 1}

routerPortGroup OBJECT-TYPE
    SYNTAX  	DisplayString (SIZE (1..100))
    MAX-ACCESS  read-only
    STATUS  	current
    DESCRIPTION
	"The port group consisting all the multicast routers."
    ::= { igmpRouterEntry 2 }


END
