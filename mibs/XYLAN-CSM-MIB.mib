XYLAN-CSM-MIB DEFINITIONS ::= BEGIN

IMPORTS
    DisplayString, ifIndex
        FROM RFC1213-MIB
    OBJECT-TYPE
        FROM RFC-1212
    IpAddress, Counter
        FROM RFC1155-SMI
    xylanCsmArch
        FROM XYLAN-BASE-MIB;

-- This is the RFC1695 mib...with the descriptions at the front being stripped
-- The tree structure that is intended for atmMIB is iso(1), org(3), dod(6)
-- internet(1), management(2), mib2 (1), atmMIB(37) ie 1.3.6.1.2.1.37 as per
-- rfc1695.. This has been changed to a private location 
-- Note: There are 2 forms of syntax. Everything starting with atmx is 
--       basically from the forum mib but changed to accomadate slot/port
--       instead of ifIndex or since NMS could not set obj ids, they have
--       been changed to integers.
--       Everything beggining with xyln are private objects defined exclusively
--       for our architecture and implementation

--Note: The reason why we stagger the vcCross or VpCross is for the sake
--      of the next function. If there are only VC's available (no VP's)
--      our implementation stores them irrespective of type and the next
--      function times out on most managers.

-- New variables atmxVplBidirect and atmxVclBidirect are added
-- Jayashree 19jul1999

				-- The MIB Groups
		xylanCsmMIB		OBJECT IDENTIFIER	::= { xylanCsmArch 1 }

--		atmTrafficDescriptorTypes OBJECT IDENTIFIER ::= { xylanCsmMIB 1 }
		atmxVplGroup         	  OBJECT IDENTIFIER ::= { xylanCsmMIB 1 }
		atmxInterfaceConfGroup     OBJECT IDENTIFIER ::= { xylanCsmMIB 2 }
		atmxVclGroup         	  OBJECT IDENTIFIER ::= { xylanCsmMIB 3 }
		xylnatmInterfaceConfGroup OBJECT IDENTIFIER ::= { xylanCsmMIB 4 }
		atmxVpCrossConnectGroup	  OBJECT IDENTIFIER ::= { xylanCsmMIB 5 }
		xylnatmInterfaceStatGroup OBJECT IDENTIFIER ::= { xylanCsmMIB 6 }
		atmxVcCrossConnectGroup	  OBJECT IDENTIFIER ::= { xylanCsmMIB 7 }
		atmxTrafficDescrGroup      OBJECT IDENTIFIER ::= { xylanCsmMIB 8 }
		xylnatmVplGroup			  OBJECT IDENTIFIER ::= { xylanCsmMIB 9 }
		xylnatmVclGroup			  OBJECT IDENTIFIER ::= { xylanCsmMIB 10 }
		xylnatmVplStatGroup		  OBJECT IDENTIFIER ::= { xylanCsmMIB 11 }
		xylnatmVclStatGroup		  OBJECT IDENTIFIER ::= { xylanCsmMIB 12 }
		xylnatmVcCrossConnectGroup OBJECT IDENTIFIER ::= {xylanCsmMIB 13 }
	 	xylnatmVpCrossConnectGroup OBJECT IDENTIFIER ::= {xylanCsmMIB 14 }
		xylnatmVclModGroup         OBJECT IDENTIFIER ::= {xylanCsmMIB 15 }
		xylnatmVplModGroup         OBJECT IDENTIFIER ::= {xylanCsmMIB 16 }
                xylnatmClockingxCtrlGroup  OBJECT IDENTIFIER ::= {xylanCsmMIB 17 }
                xylnatmTrafficShaperConfGroup  OBJECT IDENTIFIER ::= {xylanCsmMIB 18 }
                xylnatmTrafficShaperMemGroup   OBJECT IDENTIFIER ::= {xylanCsmMIB 19 }

               AtmxTrafficDescrParamIndex ::=
					INTEGER (0..2147483647)

               -- The following values are defined for use as
               -- possible values of the ATM traffic descriptor type.
               -- ATM Forum specified seven types of ATM traffic
               -- descriptors.

--               atmNoTrafficDescriptor  OBJECT IDENTIFIER
--                    ::= { atmTrafficDescriptorTypes 1}

--               atmNoClpNoScr  OBJECT IDENTIFIER
--                  ::= { atmTrafficDescriptorTypes 2}

--               atmClpNoTaggingNoScr OBJECT IDENTIFIER
--                    ::= { atmTrafficDescriptorTypes 3}

--               atmClpTaggingNoScr OBJECT IDENTIFIER
--                   ::= { atmTrafficDescriptorTypes 4}

--               atmNoClpScr OBJECT IDENTIFIER
--                   ::= { atmTrafficDescriptorTypes 5}

--               atmClpNoTaggingScr OBJECT IDENTIFIER
--                   ::= { atmTrafficDescriptorTypes 6}

--               atmClpTaggingScr OBJECT IDENTIFIER
--                    ::= { atmTrafficDescriptorTypes 7}


               --    ATM Interface Configuration Parameters Group

               -- This ATM MIB Module consists of the following groups:

               -- (1) ATM Interface configuration group
               -- (2) ATM Interface DS3 PLCP group
               -- (3) ATM Interface TC Sublayer group
               -- (4) ATM Interface VPL configuration group
               -- (5) ATM Interface VCL configuration group
               -- (6) ATM VP Cross Connect group
               -- (7) ATM VC Cross Connect group
               -- (8) ATM Interface AAL5 VCC performance statistics
               --     group

               --    ATM Interface Configuration Parameters Group
               -- This group contains ATM specific
               -- configuration information associated with
               -- an ATM interface beyond those
               -- supported using the ifTable.


               atmxInterfaceConfTable    OBJECT-TYPE
                    SYNTAX      SEQUENCE OF AtmxInterfaceConfEntry
                    ACCESS   not-accessible
                    STATUS       mandatory
                    DESCRIPTION
                     "This table contains ATM local interface
                      configuration parameters, one entry per ATM
                      interface port."
                    ::= { atmxInterfaceConfGroup 1 }

               atmxInterfaceConfEntry    OBJECT-TYPE
                    SYNTAX         AtmxInterfaceConfEntry
                    ACCESS     not-accessible
                    STATUS         mandatory
                    DESCRIPTION
                     "This list contains ATM interface configuration
                      parameters and state variables."
                    INDEX { atmxInterfaceSlotIndex, atmxInterfacePortIndex }
                    ::= { atmxInterfaceConfTable  1}

               AtmxInterfaceConfEntry    ::= SEQUENCE  {
					atmxInterfaceSlotIndex      INTEGER,
	   				atmxInterfacePortIndex      INTEGER,
                    atmxInterfaceMaxVpcs             INTEGER,
                    atmxInterfaceMaxVccs             INTEGER,
                    atmxInterfaceConfVpcs            INTEGER,
                    atmxInterfaceConfVccs            INTEGER,
                    atmxInterfaceMaxActiveVpiBits    INTEGER,
                    atmxInterfaceMaxActiveVciBits    INTEGER,
                    atmxInterfaceIlmiVpi             INTEGER,
                    atmxInterfaceIlmiVci             INTEGER,
                    atmxInterfaceAddressType         INTEGER
--                    atmxInterfaceAdminAddress        OCTET STRING,
--                    atmxInterfaceMyNeighborIpAddress IpAddress,
--                    atmxInterfaceMyNeighborIfName    DisplayString
                         }

               atmxInterfaceSlotIndex    OBJECT-TYPE
                    SYNTAX       INTEGER  (1..9)
                    ACCESS    read-only
                    STATUS         mandatory
                    DESCRIPTION
                     "The slot number of the chassis"
                    ::= { atmxInterfaceConfEntry 1}

               atmxInterfacePortIndex    OBJECT-TYPE
                    SYNTAX       INTEGER  (1..64)
                    ACCESS     read-only
                    STATUS         mandatory
                    DESCRIPTION
                     "The slot number for the CSM board"
                    ::= { atmxInterfaceConfEntry 2}


               atmxInterfaceMaxVpcs    OBJECT-TYPE
                    SYNTAX       INTEGER  (0..4096)
                    ACCESS    read-only
                    STATUS         mandatory
                    DESCRIPTION
                     "The maximum number of VPCs (PVCs and SVCs)
                      supported at this ATM interface.  At the ATM UNI,
                      the maximum number of VPCs (PVCs and SVCs)
                      ranges from 0 to 256 only."
                    ::= { atmxInterfaceConfEntry 3}

               atmxInterfaceMaxVccs    OBJECT-TYPE
                    SYNTAX       INTEGER  (0..65536)
                    ACCESS     read-only
                    STATUS         mandatory
                    DESCRIPTION
                     "The maximum number of VCCs (PVCs and SVCs)
                      supported at this ATM interface."
                    ::= { atmxInterfaceConfEntry 4}

               atmxInterfaceConfVpcs    OBJECT-TYPE
                    SYNTAX       INTEGER  (0..4096)
                    ACCESS     read-only
                    STATUS         mandatory
                    DESCRIPTION
                     "The number of VPCs (PVCs and SVCs)
                      configured for use at this ATM interface.
                      At the ATM UNI, the configured number of
                      VPCs (PVCs and SVCs) can range from
                      0 to 256 only."
                    ::= { atmxInterfaceConfEntry 5}

               atmxInterfaceConfVccs    OBJECT-TYPE
                    SYNTAX       INTEGER  (0..65536)
                    ACCESS    read-only
                    STATUS        mandatory
                    DESCRIPTION
                     "The number of VCCs (PVCs and SVCs)
                      configured for use at the ATM interface."
                    ::= { atmxInterfaceConfEntry 6}

               atmxInterfaceMaxActiveVpiBits    OBJECT-TYPE
                    SYNTAX           INTEGER  (0..12)
                    ACCESS         read-write
                    STATUS             mandatory
                    DESCRIPTION
                     "The  maximum number of active VPI bits
                      configured for use at the ATM interface.
                      At the ATM UNI, the maximum number of active
                      VPI bits configured for use ranges from
                      0 to 8 only."
                    ::= { atmxInterfaceConfEntry 7}

               atmxInterfaceMaxActiveVciBits    OBJECT-TYPE
                    SYNTAX             INTEGER  (0..16)
                    ACCESS         read-write
                    STATUS             mandatory
                    DESCRIPTION
                     "The maximum number of active VCI bits
                      configured for use at this ATM interface."
                    ::= { atmxInterfaceConfEntry 8}

               atmxInterfaceIlmiVpi         OBJECT-TYPE
                    SYNTAX          INTEGER (0..255)
                    ACCESS       read-only
                    STATUS           mandatory
                    DESCRIPTION
                     "The VPI value of the VCC supporting
                      the ILMI at this ATM interface.  If the values of
                      atmInterfaceIlmiVpi and atmInterfaceIlmiVci are
                      both equal to zero then the ILMI is not
                      supported at this ATM interface."
                    DEFVAL { 0 }
                    ::= { atmxInterfaceConfEntry 9}

               atmxInterfaceIlmiVci         OBJECT-TYPE
                    SYNTAX          INTEGER (0..65535)
                    ACCESS       read-only
                    STATUS           mandatory
                    DESCRIPTION
                     "The VCI value of the VCC supporting
                      the ILMI at this ATM interface.  If the values of
                      atmInterfaceIlmiVpi and atmInterfaceIlmiVci are
                      both equal to zero then the ILMI is not
                      supported at this ATM interface."
                    DEFVAL { 16 }
                    ::= { atmxInterfaceConfEntry 10}

               atmxInterfaceAddressType    OBJECT-TYPE
                    SYNTAX      INTEGER {
                                         private(1),
                                         nsapE164(2),
                                         nativeE164(3),
                                         other(4)
                                        }
                    ACCESS    read-only
                    STATUS        mandatory
                    DESCRIPTION
                     "The type of primary ATM address configured
                      for use at this ATM interface."
                    ::= { atmxInterfaceConfEntry 11 }

--               atmInterfaceAdminAddress    OBJECT-TYPE
--                    SYNTAX      OCTET STRING (SIZE(0..255))
--                    ACCESS    read-only
--                    STATUS        mandatory
--                    DESCRIPTION
--                     "An address assigned for administrative purposes,
--                      for example, an address associated with the
--                      service provider side of a public network UNI.
--                      If this interface has no assigned administrative
--                      address, or when the address used for
--                      administrative  purposes is the same as that used
--                      for ifPhysAddress, then this is an octet string of
--                      zero length."
--                    ::= { atmInterfaceConfEntry 12 }
--
--               atmInterfaceMyNeighborIpAddress OBJECT-TYPE
--                    SYNTAX       IpAddress
--                    ACCESS   read-write
--                    STATUS       mandatory
--                    DESCRIPTION
--                     "The IP address of the neighbor system connected to
--                      the  far end of this interface, to which a Network
--                      Management Station can send SNMP messages, as IP
--                      datagrams sent to UDP port 161, in order to access
--                      network management information concerning the
--                      operation of that system.  Note that the value
--                      of this object may be obtained in different ways,
--                      e.g., by manual configuration, or through ILMI
--                      interaction with the neighbor system."
--                    ::= { atmInterfaceConfEntry 13 }
--
--               atmInterfaceMyNeighborIfName    OBJECT-TYPE
--                    SYNTAX       DisplayString
--                    ACCESS   read-write
--                    STATUS       mandatory
--                    DESCRIPTION
--                     "The textual name of the interface on the neighbor
--                      system on the far end of this interface, and to
--                      which this interface connects.  If the neighbor
--                      system is manageable through SNMP and supports
--                      the object ifName, the value of this object must
--                      be identical with that of ifName for the ifEntry
--                      of the lowest level physical interface
--                      for this port.  If this interface does not have a
--                      textual name, the value of this object is a zero
--                      length string.  Note that the value of this object
--                      may be obtained in different ways, e.g., by manual
--                      configuration, or through ILMI interaction with
--                      the neighbor system."
--                    ::= { atmInterfaceConfEntry 14 }


               --  ATM Traffic Descriptor Parameter Group

               -- This group contains a set of self-consistent
               -- ATM traffic parameters including the
               -- ATM traffic QoS Class.

               -- The ATM virtual link tables (i.e., VPL and VCL tables)
               -- will use this ATM Traffic Descriptor table
               -- to assign traffic parameters and QoS Class
               -- to the receive and transmit directions of
               -- the ATM virtual links (i.e., VPLs and VCLs).
               -- The ATM VPL or VCL table will indicate a row
               -- in the atmxTrafficDescrParamTable
               -- using its atmxTrafficDescrParamIndex value.
               -- The management application can then compare a set of
               -- ATM traffic parameters with a single value.

               -- If no suitable row(s) in the atmxTrafficDescrParamTable
               -- exists, the manager must create a new row(s) in this
               -- table. If such a row is created, agent checks the
               -- sanity of that set of ATM traffic parameter values.

               -- When creating a new row, the parameter values
               -- will be checked for self-consistency.
               -- Predefined/template rows may be supported.

               -- A row in the atmxTrafficDescrParamTable is deleted
               -- by setting the atmxTrafficDescrRowStatus to destroy(6).
               -- The agent will check whether this row is still in use
               -- by any entry of the atmxVplTable or atmxVclTable.
               -- The agent denies the request if the row is still in
               -- use.

               --  The ATM Traffic Descriptor Parameter Table


               atmxTrafficDescrParamTable    OBJECT-TYPE
                    SYNTAX      SEQUENCE OF AtmxTrafficDescrParamEntry
                    ACCESS   not-accessible
                    STATUS       mandatory
                    DESCRIPTION
                     "This table contains information on ATM traffic
                      descriptor type and the associated parameters."
                    ::= { atmxTrafficDescrGroup 1}

               atmxTrafficDescrParamEntry    OBJECT-TYPE
                    SYNTAX           AtmxTrafficDescrParamEntry
                    ACCESS       not-accessible
                    STATUS           mandatory
                    DESCRIPTION
                     "This list contains ATM traffic descriptor
                      type and the associated parameters."
                    INDEX  {atmxTrafficDescrParamIndex}
                    ::= { atmxTrafficDescrParamTable  1}

               AtmxTrafficDescrParamEntry    ::= SEQUENCE  {
                 atmxTrafficDescrParamIndex   AtmxTrafficDescrParamIndex,
                 atmxTrafficDescrType         INTEGER,
                 atmxTrafficDescrParam1       INTEGER,
                 atmxTrafficDescrParam2       INTEGER,
                 atmxTrafficDescrParam3       INTEGER,
                 atmxTrafficDescrParam4       INTEGER,
                 atmxTrafficDescrParam5       INTEGER,
                 atmxTrafficQoSClass          INTEGER,
                 atmxTrafficDescrRowStatus    INTEGER
                              }

               atmxTrafficDescrParamIndex    OBJECT-TYPE
                    SYNTAX           AtmxTrafficDescrParamIndex
                    ACCESS       read-only
                    STATUS        mandatory
                    DESCRIPTION
                     "This object is used by the virtual link
                      table (i.e., VPL or VCL table)
                      to identify the row of this table. For NMS to
                      create a specific entry, the index is limited from
                      1-16000. Instances greater than 16000 are created
                      internally by the switch for use by SVC's etc"
                    ::= { atmxTrafficDescrParamEntry  1}

               atmxTrafficDescrType    OBJECT-TYPE
                    SYNTAX             INTEGER {
											atmxNoTrafficDescriptor(1),
											atmxNoClpNoScr (2),
											atmxClpNoTaggingNoScr(3),
											atmxClpTaggingNoScr(4),
											atmxNoClpScr(5),
											atmxClpNoTaggingScr(6),
											atmxClpTaggingScr(7)
												}
                    ACCESS         	   read-write
                    STATUS             mandatory
                    DESCRIPTION
                     "The value of this object identifies the type
                      of ATM traffic descriptor.
                      The type may indicate no traffic descriptor or
                      traffic descriptor with one or more parameters.
                      These parameters are specified as a parameter
                      vector, in the corresponding instances of the
                      objects:
                          atmxTrafficDescrParam1
                          atmxTrafficDescrParam2
                          atmxTrafficDescrParam3
                          atmxTrafficDescrParam4
                          atmxTrafficDescrParam5."
                     ::= { atmxTrafficDescrParamEntry 2}

               atmxTrafficDescrParam1    OBJECT-TYPE
                    SYNTAX             INTEGER
                    ACCESS          read-write
                    STATUS              mandatory
                    DESCRIPTION
                     "The first parameter of the ATM traffic descriptor
                      used according to the value of
                      atmxTrafficDescrType."
                    DEFVAL  { 0 }
                    ::= { atmxTrafficDescrParamEntry 3}

               atmxTrafficDescrParam2    OBJECT-TYPE
                    SYNTAX             INTEGER
                    ACCESS          read-write
                    STATUS              mandatory
                    DESCRIPTION
                     "The second parameter of the ATM traffic descriptor
                      used according to the value of
                      atmxTrafficDescrType."
                    DEFVAL  { 0 }
                    ::= { atmxTrafficDescrParamEntry 4}

               atmxTrafficDescrParam3    OBJECT-TYPE
                    SYNTAX             INTEGER
                    ACCESS          read-write
                    STATUS              mandatory
                    DESCRIPTION
                     "The third parameter of the ATM traffic descriptor
                      used according to the value of
                      atmxTrafficDescrType."
                    DEFVAL  { 0 }
                    ::= { atmxTrafficDescrParamEntry 5}

               atmxTrafficDescrParam4    OBJECT-TYPE
                    SYNTAX             INTEGER
                    ACCESS          read-write
                    STATUS              mandatory
                    DESCRIPTION
                     "The fourth parameter of the ATM traffic descriptor
                      used according to the value of
                      atmxTrafficDescrType."
                    DEFVAL  { 0 }
                    ::= { atmxTrafficDescrParamEntry 6}

               atmxTrafficDescrParam5    OBJECT-TYPE
                    SYNTAX             INTEGER
                    ACCESS          read-write
                    STATUS              mandatory
                    DESCRIPTION
                     "The fifth parameter of the ATM traffic descriptor
                      used according to the value of
                      atmxTrafficDescrType."
                    DEFVAL  { 0 }
                    ::= { atmxTrafficDescrParamEntry 7}

               atmxTrafficQoSClass   OBJECT-TYPE
                    SYNTAX         INTEGER (0..255)
                    ACCESS      read-write
                    STATUS          mandatory
                    DESCRIPTION
                     "The value of this object identifies the QoS Class.
                      Four Service classes have been
                      specified in the ATM Forum UNI Specification:
                      Service Class A: Constant bit rate video and
                                       Circuit emulation
                      Service Class B: Variable bit rate video/audio
                      Service Class C: Connection-oriented data
                      Service Class D: Connectionless data
                      Four QoS classes numbered 1, 2, 3, and 4 have
                      been specified with the aim to support service
                      classes A, B, C, and D respectively.
                      An unspecified QoS Class numbered `0' is used
                      for best effort traffic."
                    DEFVAL  { 0 }
                    ::= { atmxTrafficDescrParamEntry 8}


               atmxTrafficDescrRowStatus       OBJECT-TYPE
                    SYNTAX    INTEGER {
										create (1),
										modify (2),
										delete (3),
										active (4),
										notActive (5)
									}
                    ACCESS   read-write
                    STATUS          mandatory
                    DESCRIPTION
                     "This object is used to create
                      a new row or modify or delete an
                      existing row in this table. An entry cannot be
                      deleted or modified if any VC/VP is using the row"
                    ::= {atmxTrafficDescrParamEntry 9}


               --  ATM Interface Virtual Path Link (VPL) Group

               -- This group contains configuration and state
               -- information of a bi-directional Virtual Path Link
               -- (VPL)

               -- This table can be used to create, delete or modify
               -- a VPL that is terminated in an ATM host or switch.
               -- This table can also be used to create, delete or
               -- modify a VPL which is cross-connected to another
               -- VPL.

               -- In the example below, the traffic flows on the receive
               -- and transmit directions of the VPLs are characterized
               -- by atmxVplReceiveTrafficDescrIndex and
               -- atmxVplTransmitTrafficDescrIndex respectively.
               -- The cross-connected VPLs are identified by
               -- atmxVplCrossConnectIdentifier.



               --           ________________________________
               --           |                              |
               --  VPL      | ATM Host, Switch, or Network |   VPL
               -- receive   |                              |  receive
               -- ========> X                              X <=======
               -- <======== X                              X ========>
               -- transmit  |                              |  transmit
               --           |______________________________|



               --  The ATM Interface VPL Table


               atmxVplTable    OBJECT-TYPE
                    SYNTAX      SEQUENCE OF AtmxVplEntry
                    ACCESS   not-accessible
                    STATUS       mandatory
                    DESCRIPTION
                     "The Virtual Path Link (VPL) table.  A
                      bi-directional VPL is modeled as one entry
                      in this table."
                    ::= { atmxVplGroup 1 }

               atmxVplEntry    OBJECT-TYPE
                    SYNTAX           AtmxVplEntry
                    ACCESS       not-accessible
                    STATUS           mandatory
                    DESCRIPTION
                     "An entry in the VPL table.  This entry is
                      used to model a bi-directional VPL.
                      To create a VPL at an ATM interface,
                      either of the following procedures are used:
                      Negotiated VPL establishment

                    (1) The management application creates
                        a VPL entry in the atmxVplTable
                        by setting atmxVplRowStatus to createAndWait(5).
                        This may fail for the following reasons:
                        - The selected VPI value is unavailable,
                        - The selected VPI value is in use.
                        Otherwise, the agent creates a row and
                        reserves the VPI value on that port.

                    (2) The manager selects an existing row(s) in the
                        atmxTrafficDescrParamTable,
                        thereby, selecting a set of self-consistent
                        ATM traffic parameters and the QoS Class
                        for receive and transmit directions of the VPL.

                   (2a) If no suitable row(s) in the
                        atmxTrafficDescrParamTable exists,
                        the manager must create a new row(s)
                        in that table.

                   (2b) The manager characterizes the VPL's traffic
                        parameters through setting the
                        atmxVplReceiveTrafficDescrIndex and the
                        atmxVplTransmitTrafficDescrIndex values
                        in the VPL table, which point to the rows
                        containing desired ATM traffic parameter values
                        in the atmxTrafficDescrParamTable.  The agent
                        will check the availability of resources and
                        may refuse the request.

                    (3) The manager activates the VPL by setting the
                        the atmxVplRowStatus to active(1).
                        If this set is successful, the agent has
                        reserved the resources to satisfy the requested
                        traffic parameter values and the QoS Class
                        for that VPL.
                    (4) If the VPL terminates a VPC in the ATM host
                        or switch, the manager turns on the
                        atmxVplAdminStatus to up(1) to turn the VPL
                        traffic flow on.  Otherwise, the
                        atmxVpCrossConnectTable  must be used
                        to cross-connect the VPL to another VPL(s)
                        in an ATM switch or network.

                      One-Shot VPL Establishment
                      A VPL may also be established in one step by a
                      set-request with all necessary VPL parameter
                      values and atmxVplRowStatus set to createAndGo(4).

                      In contrast to the negotiated VPL establishment
                      which allows for detailed error checking
                      (i.e., set errors are explicitly linked to
                      particular resource acquisition failures),
                      the one-shot VPL establishment
                      performs the setup on one operation but
                      does not have the advantage of step-wise
                      error checking.

                      VPL Retirement

                      A VPL is released by setting atmxVplRowStatus to
                      destroy(6), and the agent may release all
                      associated resources."
                    INDEX  {atmxVplSlotIndex,atmxVplPortIndex, atmxVplVpi }
                    ::= { atmxVplTable  1}

               AtmxVplEntry    ::= SEQUENCE  {
					atmxVplSlotIndex			INTEGER,
					atmxVplPortIndex			INTEGER,
                    atmxVplVpi                       INTEGER,
                    atmxVplAdminStatus               INTEGER,
                    atmxVplOperStatus                INTEGER,
                    atmxVplLastChange                DisplayString,
                    atmxVplReceiveTrafficDescrIndex
                                    AtmxTrafficDescrParamIndex,
                    atmxVplTransmitTrafficDescrIndex
                                    AtmxTrafficDescrParamIndex,
                    atmxVplCrossConnectIdentifier    INTEGER,
                    atmxVplRowStatus                 INTEGER,
                    atmxVplBidirect                  INTEGER
                       }


               atmxVplSlotIndex    OBJECT-TYPE
                    SYNTAX    INTEGER  (1..9)
                    ACCESS     read-only
                    STATUS         mandatory
                    DESCRIPTION
                     "The slot number of the chassis"
                    ::= { atmxVplEntry 1}

               atmxVplPortIndex    OBJECT-TYPE
                    SYNTAX    INTEGER  (1..64)
                    ACCESS     read-only
                    STATUS         mandatory
                    DESCRIPTION
                     "The port number of the csm board"
                    ::= { atmxVplEntry 2}

               atmxVplVpi    OBJECT-TYPE
                    SYNTAX    INTEGER  (1..4095)
                    ACCESS     read-only
                    STATUS         mandatory
                    DESCRIPTION
                     "The VPI value of the VPL.
                      Note that the VPI=0 is not used
                      for a VPL not associated with a VCL.
                      The maximum VPI value cannot
                      exceed the value allowable by the
                      atmInterfaceMaxVpiBits."
                    ::= { atmxVplEntry 3}

               atmxVplAdminStatus   OBJECT-TYPE
                    SYNTAX   INTEGER  {
                                       up(1),
                                       down(2)
                                           }
                    ACCESS   read-write
                    STATUS       mandatory
                    DESCRIPTION
                     "This object is implemented only for a VPL which
                      terminates a VPC (i.e.,
                      one which is NOT cross-connected to other VPLs).
                      Its value specifies the desired administrative
                      state of the VPL.  The up and down states indicate
                      that the traffic flow is enabled and disabled
                      respectively for this VPL."
                    DEFVAL { down }
                    ::= { atmxVplEntry 4}


-- This is a Xylan Specific change to accomadate the rest of the stuff..

               atmxVplOperStatus   OBJECT-TYPE
                    SYNTAX   INTEGER  {
										unknown(1),
										end2endup (2),
										end2endDown(3),
										localUpEndToEndUnknown(4),
										localDown(5)
                                           }
                    ACCESS   read-only
                    STATUS       mandatory
                    DESCRIPTION
                     "This object indicates the current operational
                      status of the VPL.  The up and down states
                      indicate that the VPL is currently
                      operational, or not operational, respectively.
                      The unknown state indicates that the status of
                      this VPL cannot be determined."
                    ::= { atmxVplEntry 5}

               atmxVplLastChange     OBJECT-TYPE
                    SYNTAX  DisplayString
                    ACCESS  read-only
                    STATUS  mandatory
                    DESCRIPTION
                     "The value of MIB II's sysUpTime object
                      at the time this VPL entered its current
                      operational state.  If the current state was
                      entered prior to the last re-initialization of the
                      agent, then this object contains a zero value."
                    ::= { atmxVplEntry 6 }

               atmxVplReceiveTrafficDescrIndex    OBJECT-TYPE
                    SYNTAX             AtmxTrafficDescrParamIndex
                    ACCESS         read-write
                    STATUS             mandatory
                    DESCRIPTION
                     "The value of this object identifies the row
                      in the atmxTrafficDescrParamTable which
                      applies to the receive direction of the VPL."
                     ::= { atmxVplEntry 7}

               atmxVplTransmitTrafficDescrIndex    OBJECT-TYPE
                    SYNTAX             AtmxTrafficDescrParamIndex
                    ACCESS         read-write
                    STATUS             mandatory
                    DESCRIPTION
                     "The value of this object identifies the row
                      in the atmxTrafficDescrParamTable which
                      applies to the transmit direction of the VPL."
                     ::= { atmxVplEntry 8}

               atmxVplCrossConnectIdentifier   OBJECT-TYPE
                    SYNTAX         INTEGER (0..2147483647)
                    ACCESS      read-only
                    STATUS          mandatory
                    DESCRIPTION
                     "This object is implemented only for a VPL
                      which is cross-connected to other VPLs
                      that belong to the same VPC.  All such
                      associated VPLs have the same value of this
                      object, and all their cross-connections are
                      identified by entries in the
                      atmxVpCrossConnectTable for which
                      atmxVpCrossConnectIndex has the same value.
                      The value of this object is initialized by the
                      agent after the associated entries in the
                      atmxVpCrossConnectTable have been created."
                    ::= {atmxVplEntry 9}

               atmxVplRowStatus       OBJECT-TYPE
                    SYNTAX    INTEGER {
										create (1),
										modify (2),
										delete (3),
										active (4),
										notActive (5)
										}
                    ACCESS   read-write
                    STATUS          mandatory
                    DESCRIPTION
                     "This object is used to create, delete
                      or modify a row in this table.
                      To create a new VCL, this object is
                      initially set to 'createAndWait' or
                      'createAndGo'.  This object must not be
                      set to 'active' unless the following columnar
                      objects exist in this row:
                      atmxVplReceiveTrafficDescrIndex and
                      atmxVplTransmitTrafficDescrIndex. Xylan implemnts
					  createAndWait and createAndGo as just Create.."
                    ::= {atmxVplEntry 10}



               atmxVplBidirect        OBJECT-TYPE
                    SYNTAX            INTEGER {
                                                 off  (1),
                                                 on   (2)     
                                              }
                    ACCESS            read-write
                    STATUS            mandatory
                    DESCRIPTION 
                     " Indicates whether the same traffic parameters are used
                     for both the transmit and receive sides of a virtual 
                     connection."
                     DEFVAL { on }
                    ::= { atmxVplEntry 11 } 
                    
                   
                    


                    
               --  ATM Interface Virtual Channel Link (VCL) Group

               -- This group contains configuration and state
               -- information of a bi-directional Virtual Channel
               -- Link (VCL) at an ATM interface.

               -- This table can be used to create, delete or modify
               -- a VCL that is terminated in an ATM host or switch.
               -- This table can also be
               -- used to create, delete or modify a VCL that is
               -- cross-connected to another VCL.


               --  The ATM Interface VCL Table


               atmxVclTable    OBJECT-TYPE
                    SYNTAX      SEQUENCE OF AtmxVclEntry
                    ACCESS   not-accessible
                    STATUS       mandatory
                    DESCRIPTION
                     "The Virtual Channel Link (VCL) table.  A
                      bi-directional VCL is modeled as one entry
                      in this table."
                    ::= { atmxVclGroup 1 }

               atmxVclEntry    OBJECT-TYPE
                    SYNTAX           AtmxVclEntry
                    ACCESS       not-accessible
                    STATUS           mandatory
                    DESCRIPTION
                     "An entry in the VCL table.  This entry is
                      used to model a bi-directional VCL.
                      To create a VCL at an ATM interface,
                      either of the following procedures are used:

                      Negotiated VCL establishment

                    (1) The management application creates
                        a VCL entry in the atmxVclTable
                        by setting atmxVclRowStatus to createAndWait(5).
                        This may fail for the following reasons:
                        - The selected VPI/VCI values are unavailable,
                        - The selected VPI/VCI values are in use.
                        Otherwise, the agent creates a row and
                        reserves the VPI/VCI values on that port.

                    (2) The manager selects an existing row(s) in the
                        atmxTrafficDescrParamTable,
                        thereby, selecting a set of self-consistent
                        ATM traffic parameters and the QoS Class
                        for receive and transmit directions of the VCL.

                   (2a) If no suitable row(s) in the
                        atmxTrafficDescrParamTable exists,
                        the manager must create a new row(s)
                        in that table.

                   (2b) The manager characterizes the VCL's traffic
                        parameters through setting the
                        atmxVclReceiveTrafficDescrIndex and the
                        atmxVclTransmitTrafficDescrIndex values
                        in the VCL table, which point to the rows
                        containing desired ATM traffic parameter values
                        in the atmxTrafficDescrParamTable.  The agent
                        will check the availability of resources and
                        may refuse the request.

                    (3) The manager activates the VCL by setting the
                        the atmxVclRowStatus to active(1).
                        If this set is successful, the agent has
                        reserved the resources to satisfy the requested
                        traffic parameter values and the QoS Class
                        for that VCL.
                    (4) If the VCL terminates a VCC in the ATM host
                        or switch, the manager turns on the
                        atmxVclAdminStatus to up(1) to turn the VCL
                        traffic flow on.  Otherwise, the
                        atmxVcCrossConnectTable  must be used
                        to cross-connect the VCL to another VCL(s)
                        in an ATM switch or network.

                     One-Shot VCL Establishment

                     A VCL may also be established in one step by a
                     set-request with all necessary VCL parameter
                     values and atmxVclRowStatus set to createAndGo(4).
                     In contrast to the negotiated VCL establishment
                     which allows for detailed error checking
                     (i.e., set errors are explicitly linked to
                     particular resource acquisition failures),
                     the one-shot VCL establishment
                     performs the setup on one operation but
                     does not have the advantage of step-wise
                     error checking.

                     VCL Retirement

                     A VCL is released by setting atmxVclRowStatus to
                     destroy(6), and the agent may release all
                     associated resources."
                    INDEX  {atmxVclSlotIndex,atmxVclPortIndex, atmxVclVpi, 	
							atmxVclVci }
                    ::= { atmxVclTable  1}

               AtmxVclEntry    ::= SEQUENCE  {
					atmxVclSlotIndex            INTEGER,
					atmxVclPortIndex            INTEGER,
                    atmxVclVpi                       INTEGER,
                    atmxVclVci                       INTEGER,
                    atmxVclAdminStatus               INTEGER,
                    atmxVclOperStatus                INTEGER,
                    atmxVclLastChange                DisplayString,
                    atmxVclReceiveTrafficDescrIndex
                                    AtmxTrafficDescrParamIndex,
                    atmxVclTransmitTrafficDescrIndex
                                    AtmxTrafficDescrParamIndex,
                    atmxVccAalType                   INTEGER,
                    atmxVccAal5CpcsTransmitSduSize   INTEGER,
                    atmxVccAal5CpcsReceiveSduSize    INTEGER,
                    atmxVccAal5EncapsType            INTEGER,
                    atmxVclCrossConnectIdentifier    INTEGER,
                    atmxVclRowStatus                 INTEGER,
                    atmxVclBidirect                  INTEGER
                           }

               atmxVclSlotIndex    OBJECT-TYPE
                    SYNTAX    INTEGER  (1..9)
                    ACCESS     read-only
                    STATUS         mandatory
                    DESCRIPTION
                     "The slot number"
                    ::= { atmxVclEntry 1}

               atmxVclPortIndex    OBJECT-TYPE
                    SYNTAX    INTEGER  (1..64)
                    ACCESS     read-only
                    STATUS         mandatory
                    DESCRIPTION
                     "The port number of the csm board"
                    ::= { atmxVclEntry 2}

               atmxVclVpi    OBJECT-TYPE
                    SYNTAX    INTEGER  (0..4095)
                    ACCESS     read-only
                    STATUS         mandatory
                    DESCRIPTION
                     "The VPI value of the VCL.
                      The maximum VPI value cannot
                      exceed the value allowable by the
                      atmInterfaceMaxVpiBits."
                    ::= { atmxVclEntry 3}

               atmxVclVci    OBJECT-TYPE
                    SYNTAX    INTEGER  (0..65535)
                    ACCESS     read-only
                    STATUS         mandatory
                    DESCRIPTION
                     "The VCI value of the VCL.
                      The maximum VCI value cannot
                      exceed the value allowable by the
                      atmInterfaceMaxVciBits."
                    ::= { atmxVclEntry 4}

               atmxVclAdminStatus   OBJECT-TYPE
                    SYNTAX   INTEGER  {
                                       up(1),
                                       down(2)
                                           }
                    ACCESS   read-write
                    STATUS       mandatory
                    DESCRIPTION
                     "This object is implemented only for a VCL which
                      terminates a VCC (i.e.,
                      one which is NOT cross-connected to other VCLs).
                      Its value specifies the desired administrative
                      state of the VCL.  The up and down states indicate
                      that the traffic flow is enabled and disabled
                      respectively for this VCL."
                    ::= { atmxVclEntry 5}

--Changed from the def 
               atmxVclOperStatus   OBJECT-TYPE
                    SYNTAX   INTEGER  {
										unknown(1),
										end2endup (2),
										end2endDown(3),
										localUpEndToEndUnknown(4),
										localDown(5)
                                           }
                    ACCESS   read-only
                    STATUS       mandatory
                    DESCRIPTION
                     "This object indicates the current operational
                      status of the VCL.  The up and down states
                      indicate that the VCL is currently
                      operational, or not operational, respectively.
                      The unknown state indicates that the status of
                      this VCL cannot be determined."
                    ::= { atmxVclEntry 6}

               atmxVclLastChange     OBJECT-TYPE
                    SYNTAX  DisplayString
                    ACCESS  read-only
                    STATUS  mandatory
                    DESCRIPTION
                     "The value of MIB II's sysUpTime object
                      at the time this VCL entered its current
                      operational state.  If the current state was
                      entered prior to the last re-initialization of the
                      agent, then this object contains a zero value."
                    ::= { atmxVclEntry 7 }

               atmxVclReceiveTrafficDescrIndex    OBJECT-TYPE
                    SYNTAX             AtmxTrafficDescrParamIndex
                    ACCESS         read-write
                    STATUS             mandatory
                    DESCRIPTION
                     "The value of this object identifies the row
                      in the ATM Traffic Descriptor Table which
                      applies to the receive direction of this VCL."
                     ::= { atmxVclEntry 8}

               atmxVclTransmitTrafficDescrIndex    OBJECT-TYPE
                    SYNTAX             AtmxTrafficDescrParamIndex
                    ACCESS         read-write
                    STATUS             mandatory
                    DESCRIPTION
                     "The value of this object identifies the row
                      of the ATM Traffic Descriptor Table which applies
                      to the transmit direction of this VCL."
                     ::= { atmxVclEntry 9}

               atmxVccAalType    OBJECT-TYPE
                    SYNTAX      INTEGER {
                                         aal1(1),
                                         aal34(2),
                                         aal5(3),
                                         other(4),
                                         unknown(5)
                                        }
                    ACCESS    read-write
                    STATUS        mandatory
                    DESCRIPTION
                     "An instance of this object only exists when the
                      local VCL end-point is also the VCC end-point,
                      and AAL is in use.
                      The type of AAL used on this VCC.
                      The AAL type includes AAL1, AAL3/4,
                      and AAL5. The other(4) may be user-defined
                      AAL type.  The unknown type indicates that
                      the AAL type cannot be determined."
                    ::= { atmxVclEntry 10 }

               atmxVccAal5CpcsTransmitSduSize OBJECT-TYPE
                    SYNTAX      INTEGER (1..65535)
                    ACCESS   read-write
                    STATUS       mandatory
                    DESCRIPTION
                     "An instance of this object only exists when the
                      local VCL end-point is also the VCC end-point,
                      and AAL5 is in use.
                      The maximum AAL5 CPCS SDU size in octets that is
                      supported on the transmit direction of this VCC."
                    DEFVAL { 9188 }
                          ::= { atmxVclEntry 11 }

               atmxVccAal5CpcsReceiveSduSize OBJECT-TYPE
                    SYNTAX      INTEGER (1..65535)
                    ACCESS   read-write
                    STATUS       mandatory
                    DESCRIPTION
                     "An instance of this object only exists when the
                      local VCL end-point is also the VCC end-point,
                      and AAL5 is in use.
                      The maximum AAL5 CPCS SDU size in octets that is
                      supported on the receive direction of this VCC."
                    DEFVAL { 9188 }
                          ::= { atmxVclEntry 12 }

               atmxVccAal5EncapsType  OBJECT-TYPE
                    SYNTAX   INTEGER {
                                   vcMultiplexRoutedProtocol(1),
                                   vcMultiplexBridgedProtocol8023(2),
                                   vcMultiplexBridgedProtocol8025(3),
                                   vcMultiplexBridgedProtocol8026(4),
                                   vcMultiplexLANemulation8023(5),
                                   vcMultiplexLANemulation8025(6),
                                   llcEncapsulation(7),
                                   multiprotocolFrameRelaySscs(8),
                                   other(9),
                                   unknown(10)
                                      }
                    ACCESS   read-write
                    STATUS        mandatory
                    DESCRIPTION
                     "An instance of this object only exists when the
                      local VCL end-point is also the VCC end-point,
                      and AAL5 is in use.
                      The type of data encapsulation used over
                      the AAL5 SSCS layer. The definitions reference
                      RFC 1483 Multiprotocol Encapsulation
                      over ATM AAL5 and to the ATM Forum
                      LAN Emulation specification."
                    DEFVAL { llcEncapsulation }
                          ::= { atmxVclEntry 13 }

               atmxVclCrossConnectIdentifier   OBJECT-TYPE
                    SYNTAX         INTEGER (0..2147483647)
                    ACCESS      read-only
                    STATUS          mandatory
                    DESCRIPTION
                     "This object is implemented only for a VCL
                      which is cross-connected to other VCLs
                      that belong to the same VCC.  All such
                      associated VCLs have the same value of this
                      object, and all their cross-connections are
                      identified by entries in the
                      atmxVcCrossConnectTable for which
                      atmxVcCrossConnectIndex has the same value.
                      The value of this object is initialized by the
                      agent after the associated entries in the
                      atmxVcCrossConnectTable have been created."
                    ::= {atmxVclEntry 14}

               atmxVclRowStatus          OBJECT-TYPE
                    SYNTAX       INTEGER {
										create (1),
										modify (2),
										delete (3),
										active (4),
										notActive (5)
										}
                    ACCESS   read-write
                    STATUS       mandatory
                    DESCRIPTION
                     "This object is used to create, delete or
                      modify a row in this table.  To create
                      a new VCL, this object is initially set
                      to 'createAndWait' or 'createAndGo'.
                      This object must not be set to 'active'
                      unless the following columnar objects exist
                      in this row:
                      atmxVclReceiveTrafficDescrIndex,
                      atmxVclTransmitTrafficDescrIndex.
					  Xylan implements createAndWait along with create&Go
					  as create. Create is basically a superset.
                      In addition, if the local VCL end-point
                      is also the VCC end-point:
                      atmVccAalType.
                      In addition, for AAL5 connections only:
                      atmVccAal5CpcsTransmitSduSize,
                      atmVccAal5CpcsReceiveSduSize, and
                      atmVccAal5EncapsType."
                          ::= {atmxVclEntry 15}



               atmxVclBidirect      OBJECT-TYPE
                    SYNTAX          INTEGER {
                                               off  (1),
                                               on   (2)
                                            }
                    ACCESS          read-write
                    STATUS          mandatory
                    DESCRIPTION
                    " Indicates whether the same traffic parameters are used 
                    for both the transmit and receive sides of a virtual 
                    connection. "
                    DEFVAL { on }
                   ::= { atmxVclEntry 16 }

               --     ATM Virtual Path (VP) Cross Connect Group

               -- This group contains configuration and state
               -- information of all point-to-point,
               -- point-to-multipoint, or multipoint-to-multipoint
               -- VP cross-connects.

               -- This table has read-write access and can be used
               -- to cross-connect the VPLs together in an ATM switch
               -- or network. The atmxVpCrossConnectIndex
               -- is used to associate the related
               -- VPLs that are cross-connected together.

               -- The ATM VP Cross Connect Group
               -- models each bi-directional VPC
               -- cross-connect as a set of entries in
               -- the atmxVpCrossConnectTable. A
               -- point-to-point VPC cross-connect is modeled
               -- as one entry; a point-to-multipoint (N leafs) VPC
               -- cross-connect as N entries in this table; and
               -- a multipoint-to-multipoint (N parties) VPC cross-
               -- connect as N(N-1)/2 entries in this table.
               -- In the latter cases, all the N (or N(N-1)/2) entries
               -- are associated with a single VPC cross-connect by
               -- having the same value of atmxVpCrossConnectIndex.


               --      _________________________________________
               --      |                                       |
               --  Low |         ATM Switch or Network         | High
               --  port|                                       | port
               -- _____|>> from low to high VPC traffic flow >>|______
               --      |<< from high to low VPC traffic flow <<|
               --      |                                       |
               --      |_______________________________________|
               --

               -- The terms low and high are chosen to represent
               -- numerical ordering of the two interfaces associated
               -- with a VPC cross-connect. That is, the ATM interface
               -- with the lower value of slot/port is termed 'low',
               -- while the other ATM interface associated with the
               -- VPC cross-connect is termed 'high'. This terminology
               -- is used to provide directional information; for
               -- example, the atmxVpCrossConnectL2HOperStatus applies
               -- to the low->high direction, and
               -- atmxVpCrossConnectH2LOperStatus applies to the
               -- high->low  direction, as illustrated above.

               --  The ATM VP Cross Connect Table


               atmxVpCrossConnectTable OBJECT-TYPE
                    SYNTAX  SEQUENCE OF AtmxVpCrossConnectEntry
                    ACCESS  not-accessible
                    STATUS  mandatory
                    DESCRIPTION
                     "The ATM VP Cross Connect table.  A bi-
                      directional VP cross-connect which
                      cross-connects two VPLs is modeled
                      as one entry in this table."
                    ::= { atmxVpCrossConnectGroup 1 }


               atmxVpCrossConnectEntry OBJECT-TYPE
                    SYNTAX  AtmxVpCrossConnectEntry
                    ACCESS  not-accessible
                    STATUS  mandatory
                    DESCRIPTION
                     "An entry in the ATM VP Cross Connect table.
                      This entry is used to model a bi-directional
                      ATM VP cross-connect which cross-connects
                      two VPLs.

                      Step-wise Procedures to set up a VP Cross-connect

                      Once the entries in the atmxVplTable are created,
                      the following procedures are used
                      to cross-connect the VPLs together.
                     (1) The manager obtains a unique
                         atmxVpCrossConnectIndex by reading the
                         atmxVpCrossConnectIndexNext object.

                     (2) Next, the manager creates a set of one
                         or more rows in the ATM VP Cross Connect
                         Table, one for each cross-connection between
                         two VPLs.  Each row is indexed by the ATM
                         interface port numbers and VPI values of the
                         two ends of that cross-connection.
                         This set of rows specifies the topology of the
                         VPC cross-connect and is identified by a single
                         value of atmxVpCrossConnectIndex.

                      Negotiated VP Cross-Connect Establishment

                    (2a) The manager creates a row in this table by
                         setting atmxVpCrossConnectRowStatus to
                         createAndWait(5).  The agent checks the
                         requested topology and the mutual sanity of
                         the ATM traffic parameters and
                         QoS Classes, i.e., the row creation fails if:
                         - the requested topology is not supported
                           by the agent,
                         - the traffic/QoS parameter values
                           associated with the requested row are
                           incompatible with those of already existing
                           rows for this VP cross-connect.
                         [For example, for setting up
                         a point-to-point VP cross-connect, the
                         ATM traffic parameters in the receive direction
                         of a VPL at the low end of the cross-connect
                         must equal to the traffic parameters in the
                         transmit direction of the other VPL at the
                         high end of the cross-connect,
                         otherwise, the row creation fails.]
                         The agent also checks for internal errors
                         in building the cross-connect.

                         The atmxVpCrossConnectIndex values in the
                         corresponding atmxVplTable rows are filled
                         in by the agent at this point.

                    (2b) The manager promotes the row in the
                         atmxVpCrossConnectTable by setting
                         atmxVpCrossConnectRowStatus to active(1).  If
                         this set is successful, the agent has reserved
                         the resources specified by the ATM traffic
                         parameter and QoS Class values
                         for each direction of the VP cross-connect
                         in an ATM switch or network.

                     (3) The manager sets the
                         atmxVpCrossConnectAdminStatus to up(1) in all
                         rows of this VP cross-connect to turn the
                         traffic flow on.


                      One-Shot VP Cross-Connect Establishment

                      A VP cross-connect may also be established in
                      one step by a set-request with all necessary
                      parameter values and atmxVpCrossConnectRowStatus
                      set to createAndGo(4).

                      In contrast to the negotiated VP cross-connect
                      establishment which allows for detailed error
                      checking (i.e., set errors are explicitly linked
                      to particular resource acquisition failures),
                      the one-shot VP cross-connect establishment
                      performs the setup on one operation but does not
                      have the advantage of step-wise error checking.

                      VP Cross-Connect Retirement

                      A VP cross-connect identified by a particular
                      value of atmxVpCrossConnectIndex is released by:

                     (1) Setting atmxVpCrossConnectRowStatus of all
                         rows identified by this value of
                         atmxVpCrossConnectIndex to destroy(6).
                         The agent may release all
                         associated resources, and the
                         atmxVpCrossConnectIndex values in the
                         corresponding atmxVplTable row are removed.
                         Note that a situation when only a subset of
                         the associated rows are deleted corresponds
                         to a VP topology change.

                     (2) After deletion of the appropriate
                         atmxVpCrossConnectEntries, the manager may
                         set atmxVplRowStatus to destroy(6) the
                         associated VPLs.  The agent releases
                         the resources and removes the associated
                         rows in the atmxVplTable.
                      VP Cross-connect Reconfiguration

                      At the discretion of the agent, a VP
                      cross-connect may be reconfigured by
                      adding and/or deleting leafs to/from
                      the VP topology as per the VP cross-connect
                      establishment/retirement procedures.
                      Reconfiguration of traffic/QoS parameter
                      values requires release of the VP cross-connect
                      before those parameter values may by changed
                      for individual VPLs."
                    INDEX { atmxVpCrossConnectLowSlotIndex,
                          atmxVpCrossConnectLowPortIndex,
                          atmxVpCrossConnectLowVpi,
						  atmxVpCrossConnectHighSlotIndex,
                          atmxVpCrossConnectHighPortIndex,
                          atmxVpCrossConnectHighVpi }
                    ::= { atmxVpCrossConnectTable 1 }

               AtmxVpCrossConnectEntry ::= SEQUENCE {
					atmxVpCrossConnectIndex			INTEGER,
                    atmxVpCrossConnectLowSlotIndex   INTEGER,
                    atmxVpCrossConnectLowPortIndex   INTEGER,
                    atmxVpCrossConnectLowVpi         INTEGER,
					atmxVpCrossConnectHighSlotIndex  INTEGER,
                    atmxVpCrossConnectHighPortIndex  INTEGER,
                    atmxVpCrossConnectHighVpi        INTEGER,
                    atmxVpCrossConnectAdminStatus    INTEGER,
                    atmxVpCrossConnectL2HOperStatus  INTEGER,
                    atmxVpCrossConnectH2LOperStatus  INTEGER,
                    atmxVpCrossConnectL2HLastChange  DisplayString,
                    atmxVpCrossConnectH2LLastChange  DisplayString,
                    atmxVpCrossConnectRowStatus      INTEGER
                            }

			  atmxVpCrossConnectIndex OBJECT-TYPE
                    SYNTAX  INTEGER (1..2147483647)
                    ACCESS  read-only
                    STATUS  mandatory
                    DESCRIPTION
                     "A unique value to identify this VP Cross Connect"
                    ::= { atmxVpCrossConnectEntry 1 }
				

               atmxVpCrossConnectLowSlotIndex OBJECT-TYPE
                    SYNTAX  INTEGER (1..9)
                    ACCESS  read-only
                    STATUS  mandatory
                    DESCRIPTION
                     "The low slot number"
                    ::= { atmxVpCrossConnectEntry 2 }

               atmxVpCrossConnectLowPortIndex OBJECT-TYPE
                    SYNTAX  INTEGER
                    ACCESS  read-only
                    STATUS  mandatory
                    DESCRIPTION
                     "The low physical port number"
                    ::= { atmxVpCrossConnectEntry 3 }

               atmxVpCrossConnectLowVpi OBJECT-TYPE
                    SYNTAX  INTEGER  (1..4095)
                    ACCESS  read-only
                    STATUS  mandatory
                    DESCRIPTION
                     "The value of this object is equal to the VPI
                      value at the ATM interface
                      associated with the VP cross-connect that is
                      identified by atmxVpCrossConnectLow (Slot/Port)Index.
                      The VPI value cannot exceed the number
                      supported by the atmInterfaceMaxVpiBits
                      at the low ATM interface port."
                    ::= { atmxVpCrossConnectEntry 4 }

               atmxVpCrossConnectHighSlotIndex OBJECT-TYPE
                    SYNTAX  INTEGER
                    ACCESS  read-only
                    STATUS  mandatory
                    DESCRIPTION
                     "The value of the high slot number"
                    ::= { atmxVpCrossConnectEntry 5 }

               atmxVpCrossConnectHighPortIndex OBJECT-TYPE
                    SYNTAX  INTEGER
                    ACCESS  read-only
                    STATUS  mandatory
                    DESCRIPTION
                     "The high physical port number"
                    ::= { atmxVpCrossConnectEntry 6 }

               atmxVpCrossConnectHighVpi OBJECT-TYPE
                    SYNTAX  INTEGER   (1..4095)
                    ACCESS  read-only
                    STATUS  mandatory
                    DESCRIPTION
                     "The value of this object is equal to the VPI
                      value at the ATM interface associated with
                      the VP cross-connect that is identified
                      by atmxVpCrossConnectHigh(Slot/Port)Index.
                      The VPI value cannot exceed the number
                      supported by the atmInterfaceMaxVpiBits
                      at the high ATM interface port."
                    ::= { atmxVpCrossConnectEntry 7 }

               atmxVpCrossConnectAdminStatus OBJECT-TYPE
                    SYNTAX  INTEGER {
                                    up(1),
                                    down(2)
                            }
                    ACCESS  read-write
                    STATUS  mandatory
                    DESCRIPTION
                     "The value of this object identifies the desired
                      administrative status of this bi-directional
                      VP cross-connect.  The up and down states
                      indicate that the traffic flow is enabled
                      and disabled respectively on this VP
                      cross-connect."
                    ::= { atmxVpCrossConnectEntry 8 }

--Changed from the def 
               atmxVpCrossConnectL2HOperStatus OBJECT-TYPE
                    SYNTAX  INTEGER {
										unknown(1),
										end2endup (2),
										end2endDown(3),
										localUpEndToEndUnknown(4),
										localDown(5)
                                }
                    ACCESS  read-only
                    STATUS  mandatory
                    DESCRIPTION
                     "The value of this object identifies the current
                      operational status of the VP cross-connect
                      in one direction; (i.e., from the low to
                      high direction).  The up and down states indicate
                      that this ATM VP cross-connect from low
                      to high direction is operational or not
                      operational respectively.
                      The unknown state indicates that
                      the state of it cannot be determined."
                    ::= { atmxVpCrossConnectEntry 9 }

--Changed from the def 
               atmxVpCrossConnectH2LOperStatus OBJECT-TYPE
                    SYNTAX  INTEGER {
										unknown(1),
										end2endup (2),
										end2endDown(3),
										localUpEndToEndUnknown(4),
										localDown(5)
                                 }
                    ACCESS  read-only
                    STATUS  mandatory
                    DESCRIPTION
                     "The value of this object identifies the current
                      operational status of the VP cross-connect
                      in one direction; (i.e., from the high to
                      low direction).  The up and down states indicate
                      that this ATM VP cross-connect from high
                      to low direction is operational or not
                      operational respectively.  The
                      unknown state indicates that the state
                      of it cannot be determined."
                    ::= { atmxVpCrossConnectEntry 10 }

               atmxVpCrossConnectL2HLastChange OBJECT-TYPE
                    SYNTAX  DisplayString
                    ACCESS  read-only
                    STATUS  mandatory
                    DESCRIPTION
                     "The value of MIB II's sysUpTime object
                      at the time this VP cross-connect entered
                      its current operational state in the low to
                      high direction.  If the current state was
                      entered prior to the last re-initialization of the
                      agent, then this object contains a zero value."
                    ::= { atmxVpCrossConnectEntry 11 }

               atmxVpCrossConnectH2LLastChange OBJECT-TYPE
                    SYNTAX  DisplayString
                    ACCESS  read-only
                    STATUS  mandatory
                    DESCRIPTION
                     "The value of MIB II's sysUpTime object at the
                      time this VP cross-connect entered its current
                      operational state in the high to low direction.
                      If the current state was entered prior to the
                      last re-initialization of the agent,
                      then this object contains a zero value."
                    ::= { atmxVpCrossConnectEntry 12 }

               atmxVpCrossConnectRowStatus OBJECT-TYPE
                    SYNTAX  INTEGER {
										create (1),
										modify (2),
										delete (3),
										active (4),
										notActive (5)
									}
                    ACCESS  read-write
                    STATUS  mandatory
                    DESCRIPTION
                     "The status of this entry in the
                      atmxVpCrossConnectTable.  This object is used to
                      create a cross-connect for cross-connecting
                      VPLs which are created using the atmxVplTable
                      or to change or delete an existing cross-connect.
                      This object must be initially set
                      to `createAndWait' or 'createAndGo'.
                      This object cannot be set to `active'
                      unless the following columnar object exists
                      in this row: atmxVpCrossConnectAdminStatus.
                      To turn on a VP cross-connect,
                      the atmxVpCrossConnectAdminStatus
                      is set to `up'.
					  Xylan implements createAndWait along with create&Go
					  as create. Create is basically a superset."
                    ::= { atmxVpCrossConnectEntry 13 }


			   -- Note: This was taken from the draft-ietf-atommib-2.06.txt
			   --  "this" implies the SVC Vp/Vc tables


               -- 1. ATM VPL SVC Cross-Connect Table
               -- This group contains configuration and state
               -- information of all SVC point-to-point,
               -- point-to-multipoint, or multipoint-to-multipoint
               -- VP cross-connects.

               -- This table has read-only access and can be used
               -- to monitor the cross-connects which connect
               -- the VPLs together in an ATM switch
               -- or network. The atmSvcVpCrossConnectIndex
               -- is used to associate the related SVC
               -- VPLs that are cross-connected together.
               -- The atmSvcVpCrossConnectAdminStatus object
               -- has read-write access to allow for tear-down.

               -- The ATM SVC VP Cross Connect Table
               -- models each bi-directional Switched
               -- Virtual Circuit (SVC) VPC
               -- cross-connect as a set of entries in
               -- the atmSvcVpCrossConnectTable. A
               -- point-to-point VPC cross-connect is modeled
               -- as one entry; a point-to-multipoint (N leafs) VPC
               -- cross-connect as N entries in this table; and
               -- a multipoint-to-multipoint (N parties) VPC cross-
               -- connect as N(N-1)/2 entries in this table.
               -- In the latter cases, all the N (or N(N-1)/2) entries
               -- are associated with a single VPC cross-connect by
               -- having the same value of atmSvcVpCrossConnectIndex.

               --      _________________________________________
               --      |                                       |
               --  Low |         ATM Switch or Network         | High
               --  port|                                       | port
               -- _____|>> from low to high VPC traffic flow >>|______
               --      |<< from high to low VPC traffic flow <<|
               --      |                                       |
               --      |_______________________________________|
               --
               --          Figure 9: VPC Cross-Connect Model

               -- The terms low and high are chosen to represent
               -- numerical ordering of the two interfaces associated
               -- with a VPC cross-connect. That is, the ATM interface
               -- with the lower value of slot/port is termed 'low',
               -- while the other ATM interface associated with the
               -- VPC cross-connect is termed 'high'. This terminology
               -- is used to provide directional information; for
               -- example, the atmSvcVpCrossConnectL2HOperStatus
               -- applies to the low->high direction, and
               -- atmSvcVpCrossConnectH2LOperStatus applies to the
               -- high->low  direction, as illustrated in Figure 9.


               --  The ATM VP Cross Connect Table


               atmxSvcVpCrossConnectTable OBJECT-TYPE
                    SYNTAX            SEQUENCE OF AtmxSvcVpCrossConnectEntry
                    ACCESS        not-accessible
                    STATUS            mandatory
                    DESCRIPTION
                    "The ATM SVC VP Cross Connect table.  A bi-
                    directional VP cross-connect which
                    cross-connects two SVC VPLs is modeled
                    as one entry in this table."
                    ::= { atmxVpCrossConnectGroup 2 }


               atmxSvcVpCrossConnectEntry OBJECT-TYPE
                    SYNTAX  AtmxSvcVpCrossConnectEntry
                    ACCESS  not-accessible
                    STATUS  mandatory
                    DESCRIPTION
                    "An entry in the ATM SVC VP Cross Connect table.
                    This entry is used to model a bi-directional
                    ATM SVC VP cross-connect which cross-connects
                    two VPLs."
                    INDEX { atmxSvcVpCrossConnectLowSlotIndex,
							atmxSvcVpCrossConnectLowPortIndex,
                            atmxSvcVpCrossConnectLowVpi,
							atmxSvcVpCrossConnectHighSlotIndex,
                            atmxSvcVpCrossConnectHighPortIndex,
                            atmxSvcVpCrossConnectHighVpi }
                    ::= { atmxSvcVpCrossConnectTable 1 }

               AtmxSvcVpCrossConnectEntry ::= SEQUENCE {
					atmxSvcVpCrossConnectLowSlotIndex   INTEGER,
                    atmxSvcVpCrossConnectLowPortIndex   INTEGER,
                    atmxSvcVpCrossConnectLowVpi         INTEGER,
					atmxSvcVpCrossConnectHighSlotIndex  INTEGER,
					atmxSvcVpCrossConnectHighPortIndex  INTEGER,
                    atmxSvcVpCrossConnectHighVpi        INTEGER,
					atmxSvcVpCrossConnectLowTDIndex     INTEGER,
					atmxSvcVpCrossConnectHighTDIndex	   INTEGER,
                    atmxSvcVpCrossConnectCreationTime   DisplayString,
                    atmxSvcVpCrossConnectRowStatus      INTEGER
                                 }

              atmxSvcVpCrossConnectLowSlotIndex  OBJECT-TYPE
                    SYNTAX  INTEGER (1..9)
                    ACCESS  not-accessible
                    STATUS  mandatory
                    DESCRIPTION
                    "The low slot of the SVC VP cross-connect."
                    ::= { atmxSvcVpCrossConnectEntry 1 }

               atmxSvcVpCrossConnectLowPortIndex OBJECT-TYPE
                    SYNTAX  INTEGER (1..25)
                    ACCESS  not-accessible
                    STATUS  mandatory
                    DESCRIPTION
                    "The incoming slot for this SVC"
                    ::= { atmxSvcVpCrossConnectEntry 2 }

               atmxSvcVpCrossConnectLowVpi OBJECT-TYPE
                    SYNTAX  INTEGER  (1..4095)
                    ACCESS  not-accessible
                    STATUS  mandatory
                    DESCRIPTION
                    "The value of this object is equal to the VPI
                    value at the ATM interface
                    associated with the SVC VP cross-connect that is
                    identified by atmSvcVpCrossConnectLow(Slot/Port)Index.
                    The VPI value cannot exceed the number
                    supported by the atmInterfaceMaxVpiBits
                    at the low ATM interface port."
                    ::= { atmxSvcVpCrossConnectEntry 3 }

               atmxSvcVpCrossConnectHighSlotIndex OBJECT-TYPE
                    SYNTAX  INTEGER (1..9)
                    ACCESS  not-accessible
                    STATUS  mandatory
                    DESCRIPTION
                     "The outgoing slot for this SVC"
                    ::= { atmxSvcVpCrossConnectEntry 4 }

               atmxSvcVpCrossConnectHighPortIndex OBJECT-TYPE
                    SYNTAX  INTEGER (1..25)
                    ACCESS  not-accessible
                    STATUS  mandatory
                    DESCRIPTION
                     "The outgoing port for this SVC"
                    ::= { atmxSvcVpCrossConnectEntry 5 }

               atmxSvcVpCrossConnectHighVpi OBJECT-TYPE
                    SYNTAX  INTEGER   (1..4095)
                    ACCESS  not-accessible
                    STATUS  mandatory
                    DESCRIPTION
                     "The value of this object is equal to the VPI
                      value at the ATM interface associated with
                      the SVC VP cross-connect that is identified
                      by atmSvcVpCrossConnectHigh(Slot/Port)Index.
                      The VPI value cannot exceed the number
                      supported by the atmInterfaceMaxVpiBits
                      at the high ATM interface port."
                    ::= { atmxSvcVpCrossConnectEntry 6 }

               atmxSvcVpCrossConnectCreationTime OBJECT-TYPE
                    SYNTAX  DisplayString
                    ACCESS  read-only
                    STATUS  mandatory
                    DESCRIPTION
                     "The value of MIB II's sysUpTime object
                      at the time this bi-directional SVC VP
                      cross-connect was created.  If the current
                      state was entered prior to the last
                      re-initialization of the agent, then this
                      object contains a zero value."
                    ::= { atmxSvcVpCrossConnectEntry 7 }

               atmxSvcVpCrossConnectLowTDIndex OBJECT-TYPE
                    SYNTAX  INTEGER   
                    ACCESS  read-only
                    STATUS  mandatory
                    DESCRIPTION
                     "The low end connections Traffic Descriptor Index"
                    ::= { atmxSvcVpCrossConnectEntry 8 }

               atmxSvcVpCrossConnectHighTDIndex OBJECT-TYPE
                    SYNTAX  INTEGER   
                    ACCESS  read-only
                    STATUS  mandatory
                    DESCRIPTION
                     "The high connections traffic descriptor index"
                    ::= { atmxSvcVpCrossConnectEntry 9 }

               atmxSvcVpCrossConnectRowStatus OBJECT-TYPE
                    SYNTAX             INTEGER
                    ACCESS             read-only
                    STATUS             mandatory
                    DESCRIPTION
                      "This object can be used to delete rows in the
                      atmSvcVpCrossConnectTable. But unless we require it
                      for specific reasons we will not allow creation/deletion"
                   ::= { atmxSvcVpCrossConnectEntry 10 }


               --     ATM Virtual Channel (VC) Cross Connect Group

               -- This group contains configuration and state
               -- information of a bi-directional VC cross-connect.

               -- This group is used to model a bi-directional
               -- point-to-point, point-to-multipoint or
               -- multipoint-to-multipoint VC cross-connects.

               -- This table has read-write access and is used
               -- to cross-connect the VCLs together in an ATM switch
               -- or network that belong to a VC connection.
               -- The atmxVcCrossConnectIndex is used to associate
               -- the related VCLs that are cross-connected together.


               -- The step-wise procedures described for setting
               -- up a VP cross-connect are also used for setting up
               -- a VC cross-connect.


--               atmxVcCrossConnectIndexNext    OBJECT-TYPE
--                    SYNTAX  INTEGER (0..2147483647)
--                    ACCESS  read-only
--                    STATUS  current
--                    DESCRIPTION
--                     "This object contains an appropriate value to
--                      be used for atmxVcCrossConnectIndex when creating
--                      entries in the atmxVcCrossConnectTable.  The value
--                      0 indicates that no unassigned entries are
--                      available. To obtain the atmxVpCrossConnectIndex
--                      value for a new entry, the manager issues a
--                      management protocol retrieval operation to obtain
--                      the current value of this object.  After each
--                      retrieval, the agent should modify the value to
--                      the next unassigned index."
--                    ::= { xylanAtmMIB 10 }


               --  The ATM VC Cross Connect Table

               atmxVcCrossConnectTable OBJECT-TYPE
                    SYNTAX  SEQUENCE OF AtmxVcCrossConnectEntry
                    ACCESS  not-accessible
                    STATUS  mandatory
                    DESCRIPTION
                     "The ATM VC Cross Connect table.  A bi-
                      directional VC cross-connect which
                      cross-connects two end points (i.e., VCLs)
                      is modeled as one entry in this table."
                    ::= { atmxVcCrossConnectGroup 1 }


               atmxVcCrossConnectEntry OBJECT-TYPE
                    SYNTAX  AtmxVcCrossConnectEntry
                    ACCESS  not-accessible
                    STATUS  mandatory
                    DESCRIPTION
                     "An entry in the ATM VC Cross Connect table.
                      This entry is used to model a bi-directional ATM
                      VC cross-connect cross-connecting two end points.

                      Step-wise Procedures to set up a VC Cross-connect

                      Once the entries in the atmxVclTable are created,
                      the following procedures are used
                      to cross-connect the VCLs together to
                      form a VCC segment.

                     (1) The manager obtains a unique
                         atmxVcCrossConnectIndex by reading the
                         atmxVcCrossConnectIndexNext object.

                     (2) Next, the manager creates a set of one
                         or more rows in the ATM VC Cross Connect
                         Table, one for each cross-connection between
                         two VCLs.  Each row is indexed by the ATM
                         interface port numbers and VPI/VCI values of
                         the two ends of that cross-connection.
                         This set of rows specifies the topology of the
                         VCC cross-connect and is identified by a single
                         value of atmxVcCrossConnectIndex.

                      Negotiated VC Cross-Connect Establishment

                    (2a) The manager creates a row in this table by
                         setting atmxVcCrossConnectRowStatus to
                         createAndWait(5).  The agent checks the
                         requested topology and the mutual sanity of
                         the ATM traffic parameters and
                         QoS Classes, i.e., the row creation fails if:
                         - the requested topology is not supported
                           by the agent,
                         - the traffic/QoS parameter values
                           associated with the requested row are
                           incompatible with those of already existing
                           rows for this VC cross-connect.
                         [For example, for setting up
                         a point-to-point VC cross-connect, the
                         ATM traffic parameters in the receive direction
                         of a VCL at the low end of the cross-connect
                         must equal to the traffic parameters in the
                         transmit direction of the other VCL at the
                         high end of the cross-connect,
                         otherwise, the row creation fails.]
                         The agent also checks for internal errors
                         in building the cross-connect.

                         The atmxVcCrossConnectIndex values in the
                         corresponding atmxVclTable rows are filled
                         in by the agent at this point.

                    (2b) The manager promotes the row in the
                         atmxVcCrossConnectTable by setting
                         atmxVcCrossConnectRowStatus to active(1).  If
                         this set is successful, the agent has reserved
                         the resources specified by the ATM traffic
                         parameter and QoS Class values
                         for each direction of the VC cross-connect
                         in an ATM switch or network.

                     (3) The manager sets the
                         atmxVcCrossConnectAdminStatus to up(1)
                         in all rows of this VC cross-connect to
                         turn the traffic flow on.


                      One-Shot VC Cross-Connect Establishment

                      A VC cross-connect may also be established in
                      one step by a set-request with all necessary
                      parameter values and atmxVcCrossConnectRowStatus
                      set to createAndGo(4).

                      In contrast to the negotiated VC cross-connect
                      establishment which allows for detailed error
                      checking i.e., set errors are explicitly linked to
                      particular resource acquisition failures), the
                      one-shot VC cross-connect establishment
                      performs the setup on one operation but does
                      not have the advantage of step-wise error
                      checking.

                      VC Cross-Connect Retirement

                      A VC cross-connect identified by a particular
                      value of atmxVcCrossConnectIndex is released by:

                     (1) Setting atmxVcCrossConnectRowStatus of all rows
                         identified by this value of
                         atmxVcCrossConnectIndex to destroy(6).
                         The agent may release all
                         associated resources, and the
                         atmxVcCrossConnectIndex values in the
                         corresponding atmxVclTable row are removed.
                         Note that a situation when only a subset of
                         the associated rows are deleted corresponds
                         to a VC topology change.

                     (2) After deletion of the appropriate
                         atmxVcCrossConnectEntries, the manager may
                         set atmxVclRowStatus to destroy(6) the
                         associated VCLs.  The agent releases
                         the resources and removes the associated
                         rows in the atmxVclTable.

                      VC Cross-Connect Reconfiguration

                      At the discretion of the agent, a VC
                      cross-connect may be reconfigured by
                      adding and/or deleting leafs to/from
                      the VC topology as per the VC cross-connect
                      establishment/retirement procedures.
                      Reconfiguration of traffic/QoS parameter
                      values requires release of the VC cross-connect
                      before those parameter values may by changed
                      for individual VCLs."
                    INDEX { atmxVcCrossConnectLowSlotIndex,
                          atmxVcCrossConnectLowPortIndex,
                          atmxVcCrossConnectLowVpi,
                          atmxVcCrossConnectLowVci,
					      atmxVcCrossConnectHighSlotIndex,
                          atmxVcCrossConnectHighPortIndex,
                          atmxVcCrossConnectHighVpi,
                          atmxVcCrossConnectHighVci }
                    ::= { atmxVcCrossConnectTable 1 }

               AtmxVcCrossConnectEntry ::= SEQUENCE {
					atmxVcCrossConnectIndex			INTEGER,
                    atmxVcCrossConnectLowSlotIndex   INTEGER,
                    atmxVcCrossConnectLowPortIndex   INTEGER,
                    atmxVcCrossConnectLowVpi         INTEGER,
                    atmxVcCrossConnectLowVci         INTEGER,
					atmxVcCrossConnectHighSlotIndex  INTEGER,
                    atmxVcCrossConnectHighPortIndex  INTEGER,
                    atmxVcCrossConnectHighVpi        INTEGER,
                    atmxVcCrossConnectHighVci        INTEGER,
                    atmxVcCrossConnectAdminStatus    INTEGER,
                    atmxVcCrossConnectL2HOperStatus  INTEGER,
                    atmxVcCrossConnectH2LOperStatus  INTEGER,
                    atmxVcCrossConnectL2HLastChange  DisplayString,
                    atmxVcCrossConnectH2LLastChange  DisplayString,
                    atmxVcCrossConnectRowStatus      INTEGER
                            }

			  atmxVcCrossConnectIndex OBJECT-TYPE
                    SYNTAX  INTEGER (1..2147483647)
                    ACCESS  read-only
                    STATUS  mandatory
                    DESCRIPTION
                     "A unique value to identify this VC Cross Connect"
                    ::= { atmxVcCrossConnectEntry 1 }
	
               atmxVcCrossConnectLowSlotIndex OBJECT-TYPE
                    SYNTAX  INTEGER (1..9)
                    ACCESS  read-only
                    STATUS  mandatory
                    DESCRIPTION
                     "The low port number"
                    ::= { atmxVcCrossConnectEntry 2 }

               atmxVcCrossConnectLowPortIndex OBJECT-TYPE
                    SYNTAX  INTEGER
                    ACCESS  read-only
                    STATUS  mandatory
                    DESCRIPTION
                     "The value of this object is equal to
                      the ATM interface port in this slot for this
                      VC cross-connect.  The term low implies
                      that this ATM interface has the numerically lower
                      PortIndex value than the other ATM interface
                      identified in the same atmxVcCrossConnectEntry."
                    ::= { atmxVcCrossConnectEntry 3 }

               atmxVcCrossConnectLowVpi OBJECT-TYPE
                    SYNTAX  INTEGER  (0..4095)
                    ACCESS  read-only
                    STATUS  mandatory
                    DESCRIPTION
                     "The value of this object is equal to the VPI
                      value at the ATM interface
                      associated with the VC cross-connect that is
                      identified by atmxVcCrossConnectLow(Slot/Port)Index.
                      The VPI value cannot exceed the number
                      supported by the atmInterfaceMaxVpiBits
                      at the low ATM interface port."
                    ::= { atmxVcCrossConnectEntry 4 }

               atmxVcCrossConnectLowVci OBJECT-TYPE
                    SYNTAX  INTEGER  (0..65535)
                    ACCESS  read-only
                    STATUS  mandatory
                    DESCRIPTION
                     "The value of this object is equal to the VCI
                      value at the ATM interface
                      associated with this VC cross-connect that is
                      identified by atmxVcCrossConnectLow(Slot/Port)index.
                      The VCI value cannot exceed the number
                      supported by the atmInterfaceMaxVciBits
                      at the low ATM interface port."
                    ::= { atmxVcCrossConnectEntry 5 }


               atmxVcCrossConnectHighSlotIndex OBJECT-TYPE
                    SYNTAX  INTEGER (1..9)
                    ACCESS  read-only
                    STATUS  mandatory
                    DESCRIPTION
                     "The high port number"
                    ::= { atmxVcCrossConnectEntry 6 }

               atmxVcCrossConnectHighPortIndex OBJECT-TYPE
                    SYNTAX  INTEGER
                    ACCESS  read-only
                    STATUS  mandatory
                    DESCRIPTION
                     "The value of this object is equal to 
                      the ATM interface port in this slot for
                      this VC cross-connect.  The term high
                      implies that this VC cross-connect
                      that this ATM interface has the numerically higher
                      slot/port value than the other ATM interface
                      identified in the same atmxVcCrossConnectEntry."
                    ::= { atmxVcCrossConnectEntry 7 }

               atmxVcCrossConnectHighVpi OBJECT-TYPE
                    SYNTAX  INTEGER   (0..4095)
                    ACCESS  read-only
                    STATUS  mandatory
                    DESCRIPTION
                     "The value of this object is equal to the VPI
                      value at the ATM interface
                      associated with the VC cross-connect that is
                      identified by atmxVcCrossConnectHigh(slot/port)index.
                      The VPI value cannot exceed
                      the number supported by the atmInterfaceMaxVpiBits
                      at the high ATM interface port."
                    ::= { atmxVcCrossConnectEntry 8 }

               atmxVcCrossConnectHighVci OBJECT-TYPE
                    SYNTAX  INTEGER   (0..65535)
                    ACCESS  read-only
                    STATUS  mandatory
                    DESCRIPTION
                     "The value of this object is equal to the VCI
                      value at the ATM interface
                      associated with the VC cross-connect that is
                      identified by atmxVcCrossConnectHigh(Slot/port)Index.
                      The VCI value cannot exceed
                      the number supported by the atmInterfaceMaxVciBits
                      at the high ATM interface port."
                    ::= { atmxVcCrossConnectEntry 9 }

               atmxVcCrossConnectAdminStatus OBJECT-TYPE
                    SYNTAX  INTEGER {
                              up(1),
                              down(2)
                              }
                    ACCESS  read-write
                    STATUS  mandatory
                    DESCRIPTION
                     "The value of this object identifies the desired
                      administrative status of this bi-directional
                      VC cross-connect. The up and down states
                      indicate that the traffic flow is enabled or
                      disabled respectively on this VC cross-connect."
                    ::= { atmxVcCrossConnectEntry 10 }
--Changed from rfc
               atmxVcCrossConnectL2HOperStatus OBJECT-TYPE
                    SYNTAX  INTEGER {
										unknown(1),
										end2endup (2),
										end2endDown(3),
										localUpEndToEndUnknown(4),
										localDown(5)
                            }
                    ACCESS  read-only
                    STATUS  mandatory
                    DESCRIPTION
                     "The value of this object identifies the current
                      operational status of the VC cross-connect
                      in one direction; (i.e., from the low to
                      high direction).  The up and down states indicate
                      that this ATM VC cross-connect from low
                      to high direction is operational or not
                      operational respectively.  The unknown state
                      indicates that the state of it cannot be
                      determined."
                    ::= { atmxVcCrossConnectEntry 11 }

--Changed from rfc
               atmxVcCrossConnectH2LOperStatus OBJECT-TYPE
                    SYNTAX  INTEGER {
										unknown(1),
										end2endup (2),
										end2endDown(3),
										localUpEndToEndUnknown(4),
										localDown(5)
                            }
                    ACCESS  read-only
                    STATUS  mandatory
                    DESCRIPTION
                     "The value of this object identifies the current
                      operational status of the VC cross-connect
                      in one direction; (i.e., from the high to
                      low direction).  The up and down states indicate
                      that this ATM VC cross-connect from high
                      to low direction is operational or not
                      operational respectively.  The unknown state
                      indicates that the state of it cannot be
                      determined."
                    ::= { atmxVcCrossConnectEntry 12 }

               atmxVcCrossConnectL2HLastChange OBJECT-TYPE
                    SYNTAX  DisplayString
                    ACCESS  read-only
                    STATUS  mandatory
                    DESCRIPTION
                     "The value of MIB II's sysUpTime object
                      at the time this VC cross-connect entered
                      its current operational state in low to high
                      direction.  If the current state was
                      entered prior to the last re-initialization of the
                      agent, then this object contains a zero value."
                    ::= { atmxVcCrossConnectEntry 13 }

               atmxVcCrossConnectH2LLastChange OBJECT-TYPE
                    SYNTAX  DisplayString
                    ACCESS  read-only
                    STATUS  mandatory
                    DESCRIPTION
                     "The value of MIB II's sysUpTime object
                      at the time this VC cross-connect entered
                      its current operational state in high to low
                      direction.  If the current state was
                      entered prior to the last re-initialization of the
                      agent, then this object contains a zero value."
                    ::= { atmxVcCrossConnectEntry 14 }

               atmxVcCrossConnectRowStatus OBJECT-TYPE
                    SYNTAX  INTEGER {
										create (1),
										modify (2),
										delete (3),
										active (4),
										notActive (5)
									}

                    ACCESS  read-write
                    STATUS  mandatory
                    DESCRIPTION
                     "The status of this entry in the
                      atmxVcCrossConnectTable.  This object is used to
                      create a new cross-connect for cross-connecting
                      VCLs which are created using the atmxVclTable
                      or to change or delete existing cross-connect.
                      This object must be initially set to
                      `createAndWait' or 'createAndGo'.  This object
                      cannot be set to `active' unless the following
                      columnar object exists in this row:
                      atmxVcCrossConnectAdminStatus.
                      To turn on a VC cross-connect,
                      the atmxVcCrossConnectAdminStatus
                      is set to `up'.
					  Xylan implements createAndWait along with create&Go
					  as create. Create is basically a superset."
                    ::= { atmxVcCrossConnectEntry 15 }



              -- 2. ATM Virtual Channel (VC) Cross Connect Group

              -- This group contains configuration and state
              -- information of a bi-directional SVC VC cross-connect.

              -- This group is used to model a bi-directional
              -- point-to-point, point-to-multipoint or
              -- multipoint-to-multipoint SVC VC cross-connect.

              -- This table has read-only access and is used
              -- to monitor the cross-connects which connect
              -- the VCLs together in an ATM switch
              -- or network that belong to a VC connection. The
              -- atmSvcVcCrossConnectIndex is used to associate
              -- the related SVC VCLs that are cross-connected together.
              -- The atmSvcVcCrossConnectAdminStatus object
              -- has read-write access to allow for tear-down.


              --  The ATM VC Cross Connect Table

              atmxSvcVcCrossConnectTable OBJECT-TYPE
                   SYNTAX  SEQUENCE OF AtmxSvcVcCrossConnectEntry
                   ACCESS  not-accessible
                   STATUS  mandatory
                   DESCRIPTION
                    "The ATM SVC VC Cross Connect table.  A bi-
                     directional SVC VC cross-connect which
                     cross-connects two end points (i.e., VCLs)
                     is modeled as one entry in this table."
                   ::= { atmxVcCrossConnectGroup 2 }


              atmxSvcVcCrossConnectEntry OBJECT-TYPE
                   SYNTAX  AtmxSvcVcCrossConnectEntry
                   ACCESS  not-accessible
                   STATUS  mandatory
                   DESCRIPTION
                    "An entry in the ATM SVC VC Cross Connect table.
                     This entry is used to model a bi-directional ATM
                     SVC VC cross-connect cross-connecting two end points."
                   INDEX { atmxSvcVcCrossConnectLowSlotIndex,
                           atmxSvcVcCrossConnectLowPortIndex,
                           atmxSvcVcCrossConnectLowVpi,
                           atmxSvcVcCrossConnectLowVci,
                           atmxSvcVcCrossConnectHighSlotIndex,
						   atmxSvcVcCrossConnectHighPortIndex,
                           atmxSvcVcCrossConnectHighVpi,
                           atmxSvcVcCrossConnectHighVci }
                   ::= { atmxSvcVcCrossConnectTable 1 }

              AtmxSvcVcCrossConnectEntry ::= SEQUENCE {
                   atmxSvcVcCrossConnectLowSlotIndex          INTEGER,
                   atmxSvcVcCrossConnectLowPortIndex          INTEGER,
                   atmxSvcVcCrossConnectLowVpi                INTEGER,
                   atmxSvcVcCrossConnectLowVci                INTEGER,
                   atmxSvcVcCrossConnectHighSlotIndex         INTEGER,
                   atmxSvcVcCrossConnectHighPortIndex         INTEGER,
                   atmxSvcVcCrossConnectHighVpi               INTEGER,
                   atmxSvcVcCrossConnectHighVci               INTEGER,
				   atmxSvcVcCrossConnectLowTDIndex			 INTEGER,
				   atmxSvcVcCrossConnectHighTDIndex			 INTEGER,
                   atmxSvcVcCrossConnectCreationTime          DisplayString,
                   atmxSvcVcCrossConnectRowStatus             INTEGER
                           }

              atmxSvcVcCrossConnectLowSlotIndex OBJECT-TYPE
                   SYNTAX  INTEGER (1..9)
                   ACCESS  not-accessible
                   STATUS  mandatory
                   DESCRIPTION
                    "The incoming slot for this SVC."
                   ::= { atmxSvcVcCrossConnectEntry 1 }

              atmxSvcVcCrossConnectLowPortIndex OBJECT-TYPE
                   SYNTAX  INTEGER (1..25)
                   ACCESS  not-accessible
                   STATUS  mandatory
                   DESCRIPTION
                    "The incoming port for this SVC."
                   ::= { atmxSvcVcCrossConnectEntry 2 }

              atmxSvcVcCrossConnectLowVpi OBJECT-TYPE
                   SYNTAX  INTEGER  (0..4095)
                   ACCESS  not-accessible
                   STATUS  mandatory
                   DESCRIPTION
                    "The value of this object is equal to the VPI
                     value at the ATM interface
                     associated with the SVC VC cross-connect that is
                     identified by atmSvcVcCrossConnectLow(Slot/Port)Index.
                     The VPI value cannot exceed the number
                     supported by the atmInterfaceMaxVpiBits
                     at the low ATM interface port."
                   ::= { atmxSvcVcCrossConnectEntry 3 }

              atmxSvcVcCrossConnectLowVci OBJECT-TYPE
                   SYNTAX  INTEGER  (0..65535)
                   ACCESS  not-accessible
                   STATUS  mandatory
                   DESCRIPTION
                    "The value of this object is equal to the VCI
                     value at the ATM interface
                     associated with this SVC VC cross-connect that is
                     identified by atmSvcVcCrossConnectLow(Slot/Port)Index.
                     The VCI value cannot exceed the number
                     supported by the atmInterfaceMaxVciBits
                     at the low ATM interface port."
                   ::= { atmxSvcVcCrossConnectEntry 4 }

              atmxSvcVcCrossConnectHighSlotIndex OBJECT-TYPE
                   SYNTAX  INTEGER (1..9)
                   ACCESS  not-accessible
                   STATUS  mandatory
                   DESCRIPTION
                    "The outgoing slot for this SVC"
                   ::= { atmxSvcVcCrossConnectEntry 5 }

              atmxSvcVcCrossConnectHighPortIndex OBJECT-TYPE
                   SYNTAX  INTEGER
                   ACCESS  not-accessible
                   STATUS  mandatory
                   DESCRIPTION
                    "The outgoing port for this SVC"
                   ::= { atmxSvcVcCrossConnectEntry 6 }


              atmxSvcVcCrossConnectHighVpi OBJECT-TYPE
                   SYNTAX  INTEGER   (0..4095)
                   ACCESS  not-accessible
                   STATUS  mandatory
                   DESCRIPTION
                    "The value of this object is equal to the VPI
                     value at the ATM interface
                     associated with the SVC VC cross-connect that is
                     identified by atmSvcVcCrossConnectHigh(Slot/Port)Index.
                     The VPI value cannot exceed
                     the number supported by the atmInterfaceMaxVpiBits
                     at the high ATM interface port."
                   ::= { atmxSvcVcCrossConnectEntry 7 }

              atmxSvcVcCrossConnectHighVci OBJECT-TYPE
                   SYNTAX  INTEGER   (0..65535)
                   ACCESS  not-accessible
                   STATUS  mandatory
                   DESCRIPTION
                    "The value of this object is equal to the VCI
                     value at the ATM interface
                     associated with the SVC VC cross-connect that is
                     identified by atmSvcVcCrossConnectHigh(Slot/Port)Index.
                     The VCI value cannot exceed
                     the number supported by the atmInterfaceMaxVciBits
                     at the high ATM interface port."
                   ::= { atmxSvcVcCrossConnectEntry 8 }

              atmxSvcVcCrossConnectCreationTime OBJECT-TYPE
                   SYNTAX  DisplayString
                   ACCESS  read-only
                   STATUS  mandatory
                   DESCRIPTION
                    "The value of MIB II's sysUpTime object
                     at the time this bi-directional SVC VC
                     cross-connect was created.  If the current
                     state was entered prior to the last
                     re-initialization of the agent, then this
                     object contains a zero value."
                   ::= { atmxSvcVcCrossConnectEntry 9 }

               atmxSvcVcCrossConnectLowTDIndex OBJECT-TYPE
                    SYNTAX  INTEGER   
                    ACCESS  read-only
                    STATUS  mandatory
                    DESCRIPTION
                     "The low end connections Traffic Descriptor Index"
                    ::= { atmxSvcVcCrossConnectEntry 10 }

               atmxSvcVcCrossConnectHighTDIndex OBJECT-TYPE
                    SYNTAX  INTEGER   
                    ACCESS  read-only
                    STATUS  mandatory
                    DESCRIPTION
                     "The high connections traffic descriptor index"
                    ::= { atmxSvcVcCrossConnectEntry 11 }


              atmxSvcVcCrossConnectRowStatus OBJECT-TYPE
                   SYNTAX             INTEGER
                   ACCESS         read-only
                   STATUS             mandatory
                   DESCRIPTION
                     "This object is used to indicate the status of the SVC in
                     the atmSvcVcCrossConnectTable."
                  ::= { atmxSvcVcCrossConnectEntry 12 }



-- These are the additions to the rfc695 mib...All the objects are added as
-- additions to the groups....So all the private per port/slot objects are
-- atmInterfaceConfGroup 2....Ditto with the VCL connections and VPL
-- connections...So this mib will be appended at the end of the 1695 mib..


              xylnatmInterfaceConfTable    OBJECT-TYPE
              		SYNTAX      SEQUENCE OF XylnAtmInterfaceConfEntry
                    ACCESS   	not-accessible
                    STATUS       mandatory
                    DESCRIPTION
                     "This table contains the private ATM local interface
                      configuration parameters, one entry per ATM
                      interface port."
                    ::= { xylnatmInterfaceConfGroup 1 }

               xylnatmInterfaceConfEntry    OBJECT-TYPE
                    SYNTAX         	XylnAtmInterfaceConfEntry
                    ACCESS     		not-accessible
                    STATUS         	mandatory
                    DESCRIPTION
                     "This list contains xyln specific ATM interface 
					  configuration parameters and state variables."
                    INDEX { xylnatmInterfaceSlotIndex, 
							xylnatmInterfacePortIndex }
                    ::= { xylnatmInterfaceConfTable  1}

               XylnAtmInterfaceConfEntry    ::= SEQUENCE  {
					xylnatmInterfaceSlotIndex      INTEGER,
	   				xylnatmInterfacePortIndex      INTEGER,
                    xylnatmInterfaceDescription		DisplayString,
					xylnatmInterfaceTransType		INTEGER,
					xylnatmInterfaceType	INTEGER,
					xylnatmInterfaceMediaType		INTEGER,
					xylnatmInterfaceAtmAddress		DisplayString,
					xylnatmInterfacePortMode		INTEGER,
					xylnatmInterfaceOperStatus		INTEGER,
					xylnatmInterfaceQsaalStatus		INTEGER,
					xylnatmInterfaceIlmiStatus		INTEGER,
					xylnatmInterfaceTpRedirect		INTEGER,
					xylnatmInterfaceCutOverSlot		INTEGER,
					xylnatmInterfaceCutOverPort		INTEGER,
					xylnatmInterfaceClearPortStats  INTEGER,
					xylnatmInterfaceClearChanStats  INTEGER,
					xylnatmInterfaceClearSlotStats  INTEGER,
					xylnatmInterfaceTransmissionType INTEGER,
					xylnatmInterfaceIlmiState	INTEGER,
                                        xylnatmInterfaceTimingMode      INTEGER,
                                        xylnatmInterfaceLocalSrc        INTEGER,
                                        xylnatmInterfaceUniVersion      INTEGER
                         }

               xylnatmInterfaceSlotIndex    OBJECT-TYPE
                    SYNTAX      INTEGER  (1..9)
                    ACCESS    	read-only
                    STATUS         mandatory
                    DESCRIPTION
                     "The slot number of the chassis"
                    ::= { xylnatmInterfaceConfEntry 1}

               xylnatmInterfacePortIndex    OBJECT-TYPE
                    SYNTAX      INTEGER  (1..25)
                    ACCESS    	read-only
                    STATUS         mandatory
                    DESCRIPTION
                     "The port number of the chassis"
                    ::= { xylnatmInterfaceConfEntry 2}

               xylnatmInterfaceDescription    OBJECT-TYPE
                    SYNTAX      DisplayString
                    ACCESS    	read-write
                    STATUS         mandatory
                    DESCRIPTION
                     "The name in ascii characters describing the interface"
                    ::= { xylnatmInterfaceConfEntry 3}

               xylnatmInterfaceTransType    OBJECT-TYPE
                    SYNTAX      INTEGER { 
				unknown(1), 
				sonetSts3(2),
				ds3(3),
				fourb5b(4),
				eightb10b(5),
				e3(6),
				sonetSts12(7),
				ds1(8),
				e1(9),
				internal(20)
			     }	
                    ACCESS    	read-only
                    STATUS      mandatory
                    DESCRIPTION
                     "The transmission type at this interface. The type is
   		      either an unknown type or sonet/ds3/ds12/4b-5b/8b_10b
  		      encoding method."
                    ::= { xylnatmInterfaceConfEntry 4}

               xylnatmInterfaceType    OBJECT-TYPE
                    SYNTAX      INTEGER { 
				public(1),
				private(2),
				pnni10(3),
				nni-iisp-network(4),
				nni-iisp-user(5),
				other(6)
			        }	
                    ACCESS    	read-write
                    STATUS      mandatory
                    DESCRIPTION
                     "The signaling type at this interface." 
                    ::= { xylnatmInterfaceConfEntry 5}

               xylnatmInterfaceMediaType    OBJECT-TYPE
                    SYNTAX      INTEGER {
				unknown(1),
				coax(2),
				singlemode(3),
				multimode(4),
				stp(5),
				utp(6),
		                internal(7)
                             }
                    ACCESS    	read-only
                    STATUS         mandatory
                    DESCRIPTION
					"The physical media type from this physical port"
                    ::= { xylnatmInterfaceConfEntry 6}

               xylnatmInterfaceAtmAddress    OBJECT-TYPE
                    SYNTAX      DisplayString
                    ACCESS    	read-write
                    STATUS         mandatory
                    DESCRIPTION
                     "The AtmAddress @ this interface. The AtmAddress should
					  be a 20 octet hex number."
                    ::= { xylnatmInterfaceConfEntry 7 }

               xylnatmInterfacePortMode    OBJECT-TYPE
                    SYNTAX      INTEGER	{
											off(1),
											passthru(2),
											normal(3) 
										}
                    ACCESS    	read-only
                    STATUS         mandatory
                    DESCRIPTION
                     "This object describes whether this interface is
					  switched off or allowing traffic to pass thru or
					  is in normal mode."
                    ::= { xylnatmInterfaceConfEntry 8}

               xylnatmInterfaceOperStatus    OBJECT-TYPE
                    SYNTAX      INTEGER  {
											up(1),
											down(2)
										}
                    ACCESS    	read-only
                    STATUS         mandatory
                    DESCRIPTION
                     "The Oper status @ this interface is reflected by
					  the status of the object."
                    ::= { xylnatmInterfaceConfEntry 9}

               xylnatmInterfaceQsaalStatus    OBJECT-TYPE
                    SYNTAX      INTEGER  {
											up(1),
											down(2)
										}
                    ACCESS    	read-only
                    STATUS         mandatory
                    DESCRIPTION
                     "The QSAAL status @ this interface is reflected by
					  the status of the object."
                    ::= { xylnatmInterfaceConfEntry 10}

               xylnatmInterfaceIlmiStatus    OBJECT-TYPE
                    SYNTAX      INTEGER	{
											up(1),
											down(2)
										}
                    ACCESS    	read-only
                    STATUS         mandatory
                    DESCRIPTION
                     "The Ilmi Status @ this interface."
                    ::= { xylnatmInterfaceConfEntry 11}

               xylnatmInterfaceTpRedirect    OBJECT-TYPE
                    SYNTAX      INTEGER		{
												enabled(1),
												disabled(2)
											}
                    ACCESS    	read-only
                    STATUS         mandatory
                    DESCRIPTION
                     "This object indicates whether Cut-Over is enabled or
					  disabled @ this interface"
                    ::= { xylnatmInterfaceConfEntry 12}

               xylnatmInterfaceCutOverSlot    OBJECT-TYPE
                    SYNTAX      INTEGER  (1..9)
                    ACCESS    	read-write
                    STATUS         mandatory
                    DESCRIPTION
                     "The Cut-Over slot number of the chassis"
                    ::= { xylnatmInterfaceConfEntry 13}

               xylnatmInterfaceCutOverPort    OBJECT-TYPE
                    SYNTAX      INTEGER  (1..25)
                    ACCESS    	read-write
                    STATUS         mandatory
                    DESCRIPTION
                     "The Cut Over Port number of the chassis"
                    ::= { xylnatmInterfaceConfEntry 14}

               xylnatmInterfaceClearPortStats    OBJECT-TYPE
                    SYNTAX      INTEGER {
											true(1),
											false (2) 
										}
                    ACCESS    	read-write
                    STATUS         mandatory
                    DESCRIPTION
                     "True clears the stats for this port"
                    ::= { xylnatmInterfaceConfEntry 15}

               xylnatmInterfaceClearChanStats    OBJECT-TYPE
                    SYNTAX      INTEGER  {
											true(1),
											false(2)
										 }
                    ACCESS    	read-write
                    STATUS         mandatory
                    DESCRIPTION
                     "True clears the chan stats"
                    ::= { xylnatmInterfaceConfEntry 16}

               xylnatmInterfaceClearSlotStats    OBJECT-TYPE
                    SYNTAX      INTEGER  {
											true(1),
											false(2)
										}
                    ACCESS    	read-write
                    STATUS         mandatory
                    DESCRIPTION
                     "True clears all the port stats in this slot."
                    ::= { xylnatmInterfaceConfEntry 17}

               xylnatmInterfaceTransmissionType    OBJECT-TYPE
                    SYNTAX      INTEGER  {
											sonet3c(1),
											sdh(2),
											sonet12c(3),
											notApplicable(4)
										}
                    ACCESS    	read-write
                    STATUS         mandatory
                    DESCRIPTION
                     "The type of physical media for transmission on the port
					  Sonet or SDH. SDH is primarily used in Europe and Sonet
					  in the US. The S bit in the payload pointer is 00 for
					  Sonet and 01 for SDH"
                    ::= { xylnatmInterfaceConfEntry 18}

               xylnatmInterfaceIlmiState    OBJECT-TYPE
                    SYNTAX      INTEGER  {
											enable(1),
											disable(2)
										}
                    ACCESS    	read-write
                    STATUS         mandatory
                    DESCRIPTION
                     "The state of Ilmi for the instanced port. Setting this
					  object to disable, would prevent any ILMI queries being
                      sent out on this port. "
                    ::= { xylnatmInterfaceConfEntry 19}

               xylnatmInterfaceTimingMode    OBJECT-TYPE
                    SYNTAX      INTEGER  {
                       local(1),
                       loop(2)
                    }
                    ACCESS    	read-write
                    STATUS      mandatory
                    DESCRIPTION
                        "This object selects the method used
                         by the port to generate the clock used for 
                         transmit data.
 
                         local(1) selects local clock source.

                         loop(2) selects the derived clock from the
                         receive data."                        
                    ::= { xylnatmInterfaceConfEntry 20}

               xylnatmInterfaceLocalSrc    OBJECT-TYPE
                    SYNTAX      INTEGER  {
                       oscillator(1),
                       busLine8K(2),
                       busLine19M(3)
                    }
                    ACCESS    	read-write
                    STATUS      mandatory
                    DESCRIPTION
                        "This object selects which local clock source
                         used to drive the transmit data for the port.
                         This option is not available when the port's
                         timing mode is loop.  

                         oscillator(1) selects the on board oscillator.
   
                         busLine8K(2) selects the 8 KHz clocking
                         bus line.  All CSM-interface types except
                         for OC3 and OC12 can use an 8 KHz clock
                         from the bus to generate their local timing.

                         busLine19M(3) selects the 19.44 MHz
                         clocking bus line.  All CSM OC3, OC12 and 
                         CSM-AB-CE-T1 and CSM-AB-CE-E1 interface types can
                         use a 19.44 Mhz clock from the bus
                         to generate their local timing.  In
                         the case of the CSM-AB-CE the adapter
                         board does a divide operation on the
                         19.44 Mhz clock to get an 8 Khz clock
                         to use.

                         Currently, only the CSM-AB-CE T1 and E1
                         adapter boards have the ability to support
                         either busLine8K and busLine19M options."

                    ::= { xylnatmInterfaceConfEntry 21}

			xylnatmInterfaceUniVersion		OBJECT-TYPE
				SYNTAX	INTEGER {
							uni30(1),
							uni31(2),
							uniIisp(3)
								}
				ACCESS	read-write
				STATUS	mandatory
				DESCRIPTION
					"UNI Version used in the chassis"
                    ::= { xylnatmInterfaceConfEntry 22}

--      This is in a seperate MIB file xylan-vuninni.mib
--      xylnatmVUniConfGroup OBJECT IDENTIFIER ::= { xylnatmInterfaceConfGroup 2 }

--      ATM Interface ILMI parameters table( For CSM only )
--      This table contains CSM specific ILMI configuration information
--      CSM auto configuration parameters are included

        xylnatmILMIConfTable  OBJECT-TYPE
		SYNTAX SEQUENCE OF XylnatmILMIConfEntry
		ACCESS not-accessible
                STATUS       mandatory
                DESCRIPTION
		  " This table contains CSM ILMI configuration parameters,
		    one entry per CSM physical interface, or per virtual 
		    UNI/NNI instance"
		::= {  xylnatmInterfaceConfGroup 3 }

	xylnatmILMIConfEntry OBJECT-TYPE
		SYNTAX XylnatmILMIConfEntry
                ACCESS     not-accessible
                STATUS         mandatory
                DESCRIPTION
		  "This list contains CSM ILMI configuration and state
		   variables"
		INDEX { ifIndex }
		::= { xylnatmILMIConfTable 1 }

	XylnatmILMIConfEntry ::= SEQUENCE {
		xylnatmILMIConfSlot			INTEGER,
		xylnatmILMIConfPort			INTEGER,
		xylnatmILMIConfInstance			INTEGER,
		xylnatmILMIConfILMIEnable		INTEGER,
		xylnatmILMIConfILMIPollEnable		INTEGER,
		xylnatmILMIConfAutoCfgEnable		INTEGER,
		xylnatmILMIConfAutoCfgStatus		INTEGER,	
		xylnatmILMIConfAutoCfgTrigg		INTEGER,	
		xylnatmILMIConfAutoCfgDfltIf		INTEGER,
		xylnatmILMIConfAutoCfgDfltSigVer	INTEGER,
		xylnatmILMIConfAutoCfgCurIf		INTEGER,
		xylnatmILMIConfAutoCfgCurSigVer		INTEGER,
		xylnatmILMIConfAutoCfgCurILMIVer	INTEGER,
		xylnatmILMIConfPeerUniType		INTEGER,
		xylnatmILMIConfPeerUniVer		INTEGER,
		xylnatmILMIConfPeerDevType		INTEGER,
		xylnatmILMIConfPeerNNISigVer		INTEGER,
		xylnatmILMIConfPeerILMIVer		INTEGER
		}

	xylnatmILMIConfSlot	OBJECT-TYPE 
	SYNTAX INTEGER  
	ACCESS read-only 
	STATUS mandatory 
	DESCRIPTION 
	  " The slot number this entry represents"
	::= { xylnatmILMIConfEntry 1 }

	
	xylnatmILMIConfPort	OBJECT-TYPE 
	SYNTAX INTEGER  
	ACCESS read-only 
	STATUS mandatory 
	DESCRIPTION 
	  " The port number this entry represents"
	::= { xylnatmILMIConfEntry 2 }

	xylnatmILMIConfInstance		OBJECT-TYPE 
	SYNTAX INTEGER  
	ACCESS read-only 
	STATUS mandatory 
	DESCRIPTION 
	  " The Virtual UNI/NNI instance this entry represents"
	::= { xylnatmILMIConfEntry 3 }

	xylnatmILMIConfILMIEnable 	OBJECT-TYPE 
	SYNTAX INTEGER  { disable(1), enable(2) }
	ACCESS read-write 
	STATUS mandatory 
	DESCRIPTION 
	  " Indicate whether ILMI is enabled on this port, or on
	    this Virtual UNI/NNI instance"
	::= { xylnatmILMIConfEntry 4 }

	xylnatmILMIConfILMIPollEnable	OBJECT-TYPE 
	SYNTAX INTEGER  { disable(1), enable(2) }
	ACCESS read-write
	STATUS mandatory 
	DESCRIPTION 
	  " Indicate whether ILMI polling is enabled on this port, or
	    on this Virtual UNI/NNI instance"
	::= { xylnatmILMIConfEntry 5 }

	xylnatmILMIConfAutoCfgEnable	OBJECT-TYPE 
	SYNTAX INTEGER  { disable(1),enable(2) }
	ACCESS read-write 
	STATUS mandatory 
	DESCRIPTION 
	  " Indicate whether CSM auto cfg is enabled on this port, or 
	    on this Virtual UNI/NNI instance"
	::= { xylnatmILMIConfEntry 6 }

	xylnatmILMIConfAutoCfgStatus	OBJECT-TYPE 
	SYNTAX INTEGER  { cfgDone(1),idle(2),inProgress(3) }
	ACCESS read-only 
	STATUS mandatory 
	DESCRIPTION 
	  " The status of auto configuration procedure on this port, or
	    this Virtual UNI/NNI instance"
	::= { xylnatmILMIConfEntry 7 }

	xylnatmILMIConfAutoCfgTrigg	OBJECT-TYPE 
	SYNTAX INTEGER  { unknown(1),
  			  phyLogic(2),
			  phy(3),
			  logic(4)
			}	
	ACCESS read-write 
	STATUS mandatory 
	DESCRIPTION 
	  " Indicate how auto configuration procedure is triggerred on this
	    port or virtual UNI/NNI instance, phy indicates auto configuration
	    is only triggered when the port detects physical layer connection
	    is from down to up, logic indicates auto configuration procedure 
	    is triggerred when CSM port receives trap from peer port, while 
	    phy_logic indicate auto configuration procedure is triggerred by 
	    both phy and logic, which are situations described by above 
	    narrative "
	::= { xylnatmILMIConfEntry 8 }

	xylnatmILMIConfAutoCfgDfltIf	OBJECT-TYPE 
	SYNTAX INTEGER  { privateUNI(1),
			  pnni(2),
			  iispNetwork(3),
			  iispUser(4),
			  publicUNI(5)
			}
	ACCESS read-write 
	STATUS mandatory 
	DESCRIPTION 
	  " The default interface type this port or virtual UNI/NNI instance
	    will take when auto configuration procedure fails to detect its
	    peer port's interface type"
	::= { xylnatmILMIConfEntry 9 }

	xylnatmILMIConfAutoCfgDfltSigVer	OBJECT-TYPE 
	SYNTAX INTEGER  { uni30(1),uni31(2),uni40(3) }
	ACCESS read-write 
	STATUS mandatory 
	DESCRIPTION 
	  " The default signaling version this port or virtual UNI/NNI instance
	    will take when auto configuration procedure fails to detect its
	    peer port's signaling version"
	::= { xylnatmILMIConfEntry 10 }

	xylnatmILMIConfAutoCfgCurIf		OBJECT-TYPE
	SYNTAX INTEGER  { privateUNI(1),
			  pnni(2),
			  iispNetwork(3),
			  iispUser(4),
			  publicUNI(5)
			}
	ACCESS read-write 
	STATUS mandatory 
	DESCRIPTION 
	  " Current operational interface type for this CSM port or virtual 
	    UNI/NNI instance"
	::= { xylnatmILMIConfEntry 11 }


	xylnatmILMIConfAutoCfgCurSigVer 	OBJECT-TYPE
	SYNTAX INTEGER  { uni30(1),uni31(2),uni40(3) }
	ACCESS read-only 
	STATUS mandatory 
	DESCRIPTION 
	  " Current operational signaling version for this CSM port or virtual
	    UNI/NNI instance"
	::= { xylnatmILMIConfEntry 12 }

	xylnatmILMIConfAutoCfgCurILMIVer	OBJECT-TYPE 
	SYNTAX INTEGER  { unsupported(1),ilmi40(2) }
	ACCESS read-only 
	STATUS mandatory 
	DESCRIPTION 
	  " Current ILMI version running on this CSM port or virtual UNI/NNI
	    instance"
	::= { xylnatmILMIConfEntry 13 }

	xylnatmILMIConfPeerUniType	OBJECT-TYPE 
	SYNTAX INTEGER  { public(1),private(2) }
	ACCESS read-only 
	STATUS mandatory 
	DESCRIPTION 
	  " The UNI type this port gathered from its peer port through ILMI"
	::= { xylnatmILMIConfEntry 14 }

	xylnatmILMIConfPeerUniVer	OBJECT-TYPE 
	SYNTAX INTEGER  { uni30(1),uni31(2),uni40(3) }
	ACCESS read-only 
	STATUS mandatory 
	DESCRIPTION 
	  " The signaling version this port gathered from its peer port through ILMI"
	::= { xylnatmILMIConfEntry 15 }

	xylnatmILMIConfPeerDevType	OBJECT-TYPE 
	SYNTAX INTEGER  { user(1), node(2) }
	ACCESS read-only 
	STATUS mandatory 
	DESCRIPTION 
	  " The device type this port gathered from its peer port through ILMI"
	::= { xylnatmILMIConfEntry 16 }

	xylnatmILMIConfPeerNNISigVer	OBJECT-TYPE 
	SYNTAX INTEGER  { unsupported(1),iisp(2),pnni10(3) }
	ACCESS read-only 
	STATUS mandatory 
	DESCRIPTION 
	  " The NNI signaling version this port gathered from its peer port through ILMI"
	::= { xylnatmILMIConfEntry 17 }

	xylnatmILMIConfPeerILMIVer	OBJECT-TYPE 
	SYNTAX INTEGER  { unsupported(1), ilmi40(2) }
	ACCESS read-only 
	STATUS mandatory 
	DESCRIPTION 
	  " The ILMI version this port gathered from its peer port through ILMI"
	::= { xylnatmILMIConfEntry 18 }


              xylnatmInterfaceStatTable    OBJECT-TYPE
					SYNTAX		SEQUENCE OF XylnatmInterfaceStatEntry
					ACCESS		not-accessible
					STATUS		mandatory
					DESCRIPTION
						"This table contains the statistical information about
						 the interface"
                    ::= { xylnatmInterfaceStatGroup 1 }

               xylnatmInterfaceStatEntry    OBJECT-TYPE
					SYNTAX	XylnatmInterfaceStatEntry
					ACCESS	not-accessible
					STATUS	mandatory
					DESCRIPTION
						" This list contains xylan specific ATM interface
						  configuration parameters and state variables"
					INDEX { xylnatmInterfaceStatSlotIndex,
							xylnatmInterfaceStatPortIndex }
                    ::= { xylnatmInterfaceStatTable  1}

				XylnatmInterfaceStatEntry 	::=	SEQUENCE {
					xylnatmInterfaceStatSlotIndex	      INTEGER,
					xylnatmInterfaceStatPortIndex	      INTEGER,
					xylnatmInterfaceStatRxCells		      Counter,
					xylnatmInterfaceStatRxClp0Cells	      Counter,
					xylnatmInterfaceStatRxClp1Cells	      Counter,
					xylnatmInterfaceStatTxCells		      Counter,
					xylnatmInterfaceStatMarkEfciCells	  Counter,
					xylnatmInterfaceStatMarkGcraCells	  Counter,
					xylnatmInterfaceStatTotalDiscardCells Counter,
					xylnatmInterfaceStatDxCongClp0Cells	  Counter,
					xylnatmInterfaceStatDxCongClp1Cells	  Counter,
					xylnatmInterfaceStatDxGcraClp0Cells	  Counter,
					xylnatmInterfaceStatDxGcraClp1Cells	  Counter,
					xylnatmInterfaceStatDxGcrabClp0Cells  Counter,
					xylnatmInterfaceStatDxGcrabClp1Cells  Counter,
					xylnatmInterfaceStatUnknownVpVcCells  Counter,
					xylnatmInterfaceStatUnknownVpiCells	  Counter,
					xylnatmInterfaceStatUnknownVciCells	  Counter,
					xylnatmInterfaceStatUniType           INTEGER,
					xylnatmInterfaceStatUniVersion        INTEGER,
					xylnatmInterfaceStatRemainingRxBandwidth Counter,
					xylnatmInterfaceStatRemainingTxBandwidth Counter
						}


			xylnatmInterfaceStatSlotIndex		OBJECT-TYPE
				SYNTAX	INTEGER
				ACCESS	read-only
				STATUS	mandatory
				DESCRIPTION
					"The slot number in the switch"
				::= { xylnatmInterfaceStatEntry 1}

			xylnatmInterfaceStatPortIndex		OBJECT-TYPE
				SYNTAX	INTEGER
				ACCESS	read-only
				STATUS	mandatory
				DESCRIPTION
					"The port number in this slot"
				::= { xylnatmInterfaceStatEntry 2}


			xylnatmInterfaceStatRxCells		OBJECT-TYPE
				SYNTAX	Counter
				ACCESS	read-only
				STATUS	mandatory
				DESCRIPTION
					"The total number of Received Cells at this interface
                     (OC3, OC12, ATM25...)"
				::= { xylnatmInterfaceStatEntry 3}

			xylnatmInterfaceStatRxClp0Cells		OBJECT-TYPE
				SYNTAX	Counter
				ACCESS	read-only
				STATUS	mandatory
				DESCRIPTION
					"The total number of received cells at this interface
					 with Cell loss priority of zero"
				::= { xylnatmInterfaceStatEntry 4}


			xylnatmInterfaceStatRxClp1Cells		OBJECT-TYPE
				SYNTAX	Counter
				ACCESS	read-only
				STATUS	mandatory
				DESCRIPTION
					"The total number of received cells at this interface with
					 Cell loss Priority of zero or one"
				::= { xylnatmInterfaceStatEntry 5}

			xylnatmInterfaceStatTxCells			OBJECT-TYPE
				SYNTAX	Counter
				ACCESS	read-only
				STATUS	mandatory
				DESCRIPTION
					"The total number of transmitted cells at this interface"
				::= { xylnatmInterfaceStatEntry 6}


			xylnatmInterfaceStatMarkEfciCells	OBJECT-TYPE
				SYNTAX	Counter
				ACCESS	read-only
				STATUS	mandatory
				DESCRIPTION
					"The number of cells that are marked with efci (explicit
					 forward congestion notification) in the payload type
					 identifier field of the atm cell. This EFCI notification
					 is used in conjunction with backward RM cells so that
					 the destination can notify the source that there is
					 congestion on the path to the destination"
				::= { xylnatmInterfaceStatEntry 7}

			xylnatmInterfaceStatMarkGcraCells		OBJECT-TYPE
				SYNTAX	Counter
				ACCESS	read-only
				STATUS	mandatory
				DESCRIPTION
					"The number of cells marked by policing that violated
					 their traffic contract for clp0+1 cells"
				::= { xylnatmInterfaceStatEntry 8}

			xylnatmInterfaceStatTotalDiscardCells	OBJECT-TYPE
				SYNTAX	Counter
				ACCESS	read-only
				STATUS	mandatory
				DESCRIPTION
					"The total number of cells discarded at this interface due
					 to congestion, policing and unknown vpi/vci's"
				::= { xylnatmInterfaceStatEntry 9}

			xylnatmInterfaceStatDxCongClp0Cells		OBJECT-TYPE
				SYNTAX	Counter
				ACCESS	read-only
				STATUS	mandatory
				DESCRIPTION
					"The number of Clp0 cells discarded due to congestion"
				::= { xylnatmInterfaceStatEntry 10}

			xylnatmInterfaceStatDxCongClp1Cells		OBJECT-TYPE
				SYNTAX	Counter
				ACCESS	read-only
				STATUS	mandatory
				DESCRIPTION
					"The number of Clp1 cells discarded due to congestion"
				::= { xylnatmInterfaceStatEntry 11}

			xylnatmInterfaceStatDxGcraClp0Cells		OBJECT-TYPE
				SYNTAX	Counter
				ACCESS	read-only
				STATUS	mandatory
				DESCRIPTION
					"The total number of Clp0 cells discarded due to policing
					 on Clp0+1 cells"
				::= { xylnatmInterfaceStatEntry 12}

			xylnatmInterfaceStatDxGcraClp1Cells		OBJECT-TYPE
				SYNTAX	Counter
				ACCESS	read-only
				STATUS	mandatory
				DESCRIPTION
					"The total number of cell loss priority one cells discarded
					 due to policing on Clp0+1 cells"
				::= { xylnatmInterfaceStatEntry 13}


			xylnatmInterfaceStatDxGcrabClp0Cells	OBJECT-TYPE
				SYNTAX	Counter
				ACCESS	read-only
				STATUS	mandatory
				DESCRIPTION
					"The total number of Clp0 cells discarded due to policing
					 on cell loss priority zero cells"
				::= { xylnatmInterfaceStatEntry 14}

			xylnatmInterfaceStatDxGcrabClp1Cells	OBJECT-TYPE
				SYNTAX	Counter
				ACCESS	read-only
				STATUS	mandatory
				DESCRIPTION
					"The total number of cell loss prioity one cells discarded
					 due to policing on Clp0+1 cells"
				::= { xylnatmInterfaceStatEntry 15}

			xylnatmInterfaceStatUnknownVpVcCells	OBJECT-TYPE
				SYNTAX	Counter
				ACCESS	read-only
				STATUS	mandatory
				DESCRIPTION
					"The total number of cells received on this interface 
					 which has a vpi/vci combination that doesnt correspond
					 to any channels vpi/vci for this physical interface"
				::= { xylnatmInterfaceStatEntry 16}

			xylnatmInterfaceStatUnknownVpiCells		OBJECT-TYPE
				SYNTAX	Counter
				ACCESS	read-only
				STATUS	mandatory
				DESCRIPTION
					"The total number of unknown Vpi cells recieved at this
                     interface that dont correspond to any channels vpi"
				::= { xylnatmInterfaceStatEntry 17}

			xylnatmInterfaceStatUnknownVciCells		OBJECT-TYPE
				SYNTAX	Counter
				ACCESS	read-only
				STATUS	mandatory
				DESCRIPTION
					"The total number of unknown Vci cells recieved at this
                     interface that dont correspond to any channels vci"
				::= { xylnatmInterfaceStatEntry 18}

			xylnatmInterfaceStatUniType		OBJECT-TYPE
				SYNTAX	INTEGER {
									public (1),
									private(2)							
								}
				ACCESS	read-only
				STATUS	mandatory
				DESCRIPTION
					"Type of UNI used on this interface...Public or Private"
				::= { xylnatmInterfaceStatEntry 19}

			xylnatmInterfaceStatUniVersion		OBJECT-TYPE
				SYNTAX	INTEGER {
							uni30(1),
							uni31(2)
								}
				ACCESS	read-only
				STATUS	mandatory
				DESCRIPTION
					"UNI Version used in the chassis"
				::= { xylnatmInterfaceStatEntry 20}

            xylnatmInterfaceStatRemainingRxBandwidth   OBJECT-TYPE
                    SYNTAX    Counter
                    ACCESS     read-only
                    STATUS     mandatory
                    DESCRIPTION
                     "The remaining bandwidth available on this port thru 
					  which connections can be created and cells can be
					  received."
                    ::= { xylnatmInterfaceStatEntry 21}


                xylnatmInterfaceStatRemainingTxBandwidth   OBJECT-TYPE
                    SYNTAX    Counter
                    ACCESS     read-only
                    STATUS     mandatory
                    DESCRIPTION
                     "The remaining bandwidth available on this port thru
					  which connections can be created for cells to be
					  transmitted"
                    ::= { xylnatmInterfaceStatEntry 22}

             xylnatmVclTable    OBJECT-TYPE
				SYNTAX		SEQUENCE OF XylnatmVclEntry
				ACCESS		not-accessible
				STATUS		mandatory
				DESCRIPTION
					"This table contains xylan implementation specific
					 objects"
                    ::= { xylnatmVclGroup 1 }

               xylnatmVclEntry    OBJECT-TYPE
				SYNTAX		XylnatmVclEntry
				ACCESS		not-accessible
				STATUS		mandatory
				DESCRIPTION
					"List of xylan specific objects"
				INDEX	 {xylnatmVclSlotIndex,
						  xylnatmVclPortIndex,
						  xylnatmVclVpi,
						  xylnatmVclVci }
                    ::= { xylnatmVclTable  1}

				XylnatmVclEntry		::=	SEQUENCE {
					xylnatmVclSlotIndex		INTEGER,
					xylnatmVclPortIndex		INTEGER,
					xylnatmVclVpi			INTEGER,
					xylnatmVclVci			INTEGER,
					xylnatmVclConnectionDescr	DisplayString,
					xylnatmVclChanType				INTEGER,
					xylnatmVclTransportPriority		INTEGER,
					xylnatmVclUserPriority			INTEGER,
					xylnatmVclStatsMode				INTEGER,
					xylnatmVclPrTrackPortBase		INTEGER,
					xylnatmVclPrTrackPort1			INTEGER,
					xylnatmVclPrTrackPort2			INTEGER,
					xylnatmVclPrTrackPort3			INTEGER,
					xylnatmVclAltTrackPortBase		INTEGER,
					xylnatmVclAltTrackPort1			INTEGER,
					xylnatmVclAltTrackPort2			INTEGER,
					xylnatmVclAltTrackPort3			INTEGER,
					xylnatmVclLgclChanRedirect		INTEGER,
					xylnatmVclAAL5Discard			INTEGER,
					xylnatmVclF4F5SegEndpt			INTEGER,
					xylnatmVclF4F5CopySeg			INTEGER,
					xylnatmVclF4F5End2EndEndpt		INTEGER,
					xylnatmVclF4F5CopyEnd2End		INTEGER,
					xylnatmVclOamEndpt				INTEGER,
					xylnatmVclOamCopy				INTEGER,
					xylnatmVclRmFwdEndpt			INTEGER,
					xylnatmVclRmFwdCopy				INTEGER,
					xylnatmVclRmFwdGcraAdv			INTEGER,
					xylnatmVclRmBkwdEndpt			INTEGER,
					xylnatmVclRmBkwdCopy			INTEGER,
					xylnatmVclRmBkwdGcraAdv			INTEGER,
					xylnatmVclRmDiscard 			INTEGER,
					xylnatmVclGcraAPoliceMode		INTEGER,
					xylnatmVclGcraBPoliceMode		INTEGER,
					xylnatmVclMcGroupId				INTEGER,
					xylnatmVclMcIngressEgress		INTEGER
                       }
				

               xylnatmVclSlotIndex    OBJECT-TYPE
					SYNTAX		INTEGER
					ACCESS		read-only
					STATUS		mandatory
					DESCRIPTION
						"Slot Instance"
                    ::= { xylnatmVclEntry 1}

               xylnatmVclPortIndex    OBJECT-TYPE
					SYNTAX		INTEGER
					ACCESS		read-only
					STATUS		mandatory
					DESCRIPTION
						"Port Instance"
                    ::= { xylnatmVclEntry 2}

               xylnatmVclVpi    OBJECT-TYPE
					SYNTAX		INTEGER
					ACCESS		read-only
					STATUS		mandatory
					DESCRIPTION
						"Vpi instance"
                   ::= { xylnatmVclEntry 3}

				xylnatmVclVci	OBJECT-TYPE
					SYNTAX		INTEGER
					ACCESS		read-only
					STATUS		mandatory
					DESCRIPTION
						"Vcl instance"
					::= { xylnatmVclEntry 4 }

				xylnatmVclConnectionDescr OBJECT-TYPE
					SYNTAX		DisplayString
					ACCESS		read-write
					STATUS		mandatory
					DESCRIPTION
						"An ascii value for the connection"
					::= { xylnatmVclEntry 5 }
--Changed from rfc
               xylnatmVclChanType    OBJECT-TYPE
					SYNTAX		INTEGER {
									unknown(1),
									vcNni(3),
									vcUni(4)
--									xylanOam(7)
										}
					ACCESS		read-write
					STATUS		mandatory
					DESCRIPTION
						"The type of Virtual path"
                    ::= { xylnatmVclEntry 6}


               xylnatmVclTransportPriority	 OBJECT-TYPE
                    SYNTAX    INTEGER  {
--											qosCbrMc(1),
											qosCbrPrs(2),
											qosCbr(3),
--											qosVbrMc(4),
											qosVbrRt(5),
											qosVbrNrt(6),
											qosAbr(7),
											qosUbr(8)
										}
                    ACCESS     read-write
                    STATUS         mandatory
                    DESCRIPTION
                     "The transport priority..."
                    ::= { xylnatmVclEntry 7}

               xylnatmVclUserPriority	 OBJECT-TYPE
                    SYNTAX    INTEGER  
                    ACCESS    read-write
                    STATUS    mandatory
                    DESCRIPTION
                     " The user priority 0-15, with 0 being the highest"
                    ::= { xylnatmVclEntry 8}

               xylnatmVclStatsMode    OBJECT-TYPE
                    SYNTAX    INTEGER  {
											cntGcraDxCell(1),
											mrkGcraDxCell(2),
											cntGcraPsCell(3),
											mrkGcraPsCell(4)
										}
                    ACCESS     read-write
                    STATUS         mandatory
                    DESCRIPTION
                  "This allows the user one of the 4 choices. When the
                   user selects 
                   cntGcraDxCell = count clp0 & 1 and discard cell
                   mrkGcraDxCell = count clp0 & 1, mark efci &clp, discard cell
                   cntGcraPsCell = count clp0 &1 and pass the cell
                   mrkGcraPsCell = count clp0 &1, mark efci and clp, pass cell"
                    ::= { xylnatmVclEntry 9}

               xylnatmVclPrTrackPortBase    OBJECT-TYPE
                    SYNTAX    INTEGER  
                    ACCESS     read-only
                    STATUS         mandatory
                    DESCRIPTION
                     "The dest internal pport"
                    ::= { xylnatmVclEntry 10}

               xylnatmVclPrTrackPort1    OBJECT-TYPE
                    SYNTAX    INTEGER 
                    ACCESS     read-only
                    STATUS         mandatory
                    DESCRIPTION
                     "Used under multicast conditions and will be supported
                      in future releases for load balancing"
                    ::= { xylnatmVclEntry 11}

               xylnatmVclPrTrackPort2    OBJECT-TYPE
                    SYNTAX    INTEGER 
                    ACCESS     read-only
                    STATUS         mandatory
                    DESCRIPTION
                     "Used under multicast conditions and will be supported
                      in future releases for load balancing"
                    ::= { xylnatmVclEntry 12}

               xylnatmVclPrTrackPort3    OBJECT-TYPE
                    SYNTAX    INTEGER 
                    ACCESS     read-only 
                    STATUS         mandatory
                    DESCRIPTION
                     "Used under multicast conditions and will be supported
                      in future releases for load balancing"
                    ::= { xylnatmVclEntry 13}

               xylnatmVclAltTrackPortBase    OBJECT-TYPE
                    SYNTAX    INTEGER 
                    ACCESS     read-only 
                    STATUS         mandatory
                    DESCRIPTION
                     "Alternate port under failure conditions and will be
                      supported in future release"
                    ::= { xylnatmVclEntry 14}

               xylnatmVclAltTrackPort1    OBJECT-TYPE
                    SYNTAX    INTEGER 
                    ACCESS     read-only 
                    STATUS         mandatory
                    DESCRIPTION
                     "Alternate port under failure conditions and will be
                      supported in future release"
                    ::= { xylnatmVclEntry 15}

               xylnatmVclAltTrackPort2    OBJECT-TYPE
                    SYNTAX    INTEGER 
                    ACCESS     read-only
                    STATUS         mandatory
                    DESCRIPTION
                     "Alternate port under failure conditions and will be
                      supported in future release"
                    ::= { xylnatmVclEntry 16}

              xylnatmVclAltTrackPort3     OBJECT-TYPE
                    SYNTAX    INTEGER 
                    ACCESS     read-only 
                    STATUS         mandatory
                    DESCRIPTION
                     "Alternate port under failure conditions and will be
                      supported in future release"
                    ::= { xylnatmVclEntry 17}

                xylnatmVclLgclChanRedirect   OBJECT-TYPE
                    SYNTAX    INTEGER {
										notAllowed(1),
										allowed(2)
									}
                    ACCESS     read-write
                    STATUS         mandatory
                    DESCRIPTION
                     "Permits the user to allow or not allow logical channel
                      redirects"
                    ::= { xylnatmVclEntry 18}

               xylnatmVclAAL5Discard    OBJECT-TYPE
                    SYNTAX    INTEGER  {
			earlyPktDiscard(1),
                        disable(2),
			partialPktDiscard(3)
	        	}
                    ACCESS     read-write
                    STATUS         mandatory
                    DESCRIPTION
                      "This field configures an action that IOP should take
                       against cells when traffic congestion occurs.
                       
                       earlyPktDiscard(1) is treated as 'enable'
                       for IOP version 1 since it doesn't support early packet discard
                       feature.   Early packet discard is an IOP 2 feature.
                       In this mode, IOP either passes or discards all the cells
                       of a packet.  It passes all cells of a packet during congestion if
                       the first cell of the packet has been passed.  
                       Cells are marked when GCRA contract is violated.
                       This option does not apply to VBR_RT and CBR and CBR_PRS.
                     
                       disable(2) is selected to disable early packet discard and
                       partial discard feature.  Cells are discarded when needed 
                       during congestion.  Cells are marked when GCRA contract
                       is violated.
                   
                       partialPktDiscard(3) is an IOP 2 feature.   IOP starts discarding
                       cells--all of the remaining cells except for the last cell of
                       the packet-when congestion occurs.
                       When congestion ends, the first cell of a new packet is passed.
                       Cells are marked when GCRA contract is violated. 
                       This option does not apply to VBR_RT and CBR and CBR_PRS.
    
                       The default value for IOP 1 is 'disable'.
                       The default value is 'earlyPktDiscard'
                       for IOP 2 if the transport type of the circuit is UBR,
                       ABR, and VBR_NRT. 
                       'disable' is the default for VBR_RT and CBR and CBR_PRS."
                    ::= { xylnatmVclEntry 19}

               xylnatmVclF4F5SegEndpt    OBJECT-TYPE
                    SYNTAX    INTEGER {
										enable(1),
										disable(2)
									}
                    ACCESS     read-write
                    STATUS         mandatory
                    DESCRIPTION
                     "Future release"
                    ::= { xylnatmVclEntry 20}

               xylnatmVclF4F5CopySeg    OBJECT-TYPE
                    SYNTAX    INTEGER {
										enable(1),
										disable(2)
									}
                    ACCESS     read-write
                    STATUS         mandatory
                    DESCRIPTION
                     "Future release"
                    ::= { xylnatmVclEntry 21}

                xylnatmVclF4F5End2EndEndpt   OBJECT-TYPE
                    SYNTAX    INTEGER {
										enable(1),
										disable(2)
									}
                    ACCESS     read-write
                    STATUS         mandatory
                    DESCRIPTION
                     "Future release"
                    ::= { xylnatmVclEntry 22}

               xylnatmVclF4F5CopyEnd2End    OBJECT-TYPE
                    SYNTAX    INTEGER {
										enable(1),
										disable(2)
									}
                    ACCESS     read-write
                    STATUS         mandatory
                    DESCRIPTION
                     "Future release"
                    ::= { xylnatmVclEntry 23}

                xylnatmVclOamEndpt   OBJECT-TYPE
                    SYNTAX    INTEGER {
										enable(1),
										disable(2)
									}
                    ACCESS     read-write
                    STATUS         mandatory
                    DESCRIPTION
                     "Future release"
                    ::= { xylnatmVclEntry 24}

                xylnatmVclOamCopy   OBJECT-TYPE
                    SYNTAX    INTEGER {
										enable(1),
										disable(2)
									}
                    ACCESS     read-write
                    STATUS         mandatory
                    DESCRIPTION
                     "Future release"
                    ::= { xylnatmVclEntry 25}

                xylnatmVclRmFwdEndpt   OBJECT-TYPE
                    SYNTAX    INTEGER {
										enable(1),
										disable(2)
									}
                    ACCESS     read-write
                    STATUS         mandatory
                    DESCRIPTION
                     "Future release"
                    ::= { xylnatmVclEntry 26}

               xylnatmVclRmFwdCopy    OBJECT-TYPE
                    SYNTAX    INTEGER {
										enable(1),
										disable(2)
									}
                    ACCESS     read-write
                    STATUS         mandatory
                    DESCRIPTION
                     "Future release"
                    ::= { xylnatmVclEntry 27}

              xylnatmVclRmFwdGcraAdv     OBJECT-TYPE
                    SYNTAX    INTEGER {
										enable(1),
										disable(2)
									}
                    ACCESS     read-write
                    STATUS         mandatory
                    DESCRIPTION
                     "Future release"
                    ::= { xylnatmVclEntry 28}

               xylnatmVclRmBkwdEndpt    OBJECT-TYPE
                    SYNTAX    INTEGER {
										enable(1),
										disable(2)
									}
                    ACCESS     read-write
                    STATUS         mandatory
                    DESCRIPTION
                     "Future release"
                    ::= { xylnatmVclEntry 29}

               xylnatmVclRmBkwdCopy    OBJECT-TYPE
                    SYNTAX    INTEGER {
										enable(1),
										disable(2)
									}
                    ACCESS     read-write
                    STATUS         mandatory
                    DESCRIPTION
                     "Future release"
                    ::= { xylnatmVclEntry 30}

               xylnatmVclRmBkwdGcraAdv    OBJECT-TYPE
                    SYNTAX    INTEGER {
										enable(1),
										disable(2)
									}
                    ACCESS     read-write
                    STATUS         mandatory
                    DESCRIPTION
                     "Future release"
                    ::= { xylnatmVclEntry 31}

               xylnatmVclRmDiscard    OBJECT-TYPE
                    SYNTAX    INTEGER {
										enable(1),
										disable(2)
									}
                    ACCESS     read-write
                    STATUS         mandatory
                    DESCRIPTION
                     "Future release"
                    ::= { xylnatmVclEntry 32}

               xylnatmVclGcraAPoliceMode    OBJECT-TYPE
                    SYNTAX    INTEGER {
										gcraEmDxAll(1),
										gcraEmMarkClp0DxClp1(2),
										gcraEmMarkAllDxAll(3),
										gcraEmMarkClp0DxAll(4)
									}
                    ACCESS     read-only
                    STATUS         mandatory
                    DESCRIPTION
                     "Enforcement mode of GcraA as following
                      gcraEmDxAll = Discard all cells on congestion
                      gcraEmMarkClp0DxClp1 = On congestion discard Clp1 cells
                      gcraEmMarkAllDxAll = On congestion mark all
                      gcraEmMarkClp0DxAll = on congestion mark clp0 and discard
                                            all"
                    ::= { xylnatmVclEntry 33}

               xylnatmVclGcraBPoliceMode    OBJECT-TYPE
                    SYNTAX    INTEGER  {
										gcraEmDxAll(1),
										gcraEmMarkClp0DxClp1(2),
										gcraEmMarkAllDxAll(3),
										gcraEmMarkClp0DxAll(4)
									}
                    ACCESS     read-only
                    STATUS         mandatory
                    DESCRIPTION
                     "Enforcement mode of GcraB as following
                      gcraEmDxAll = Discard all cells on congestion
                      gcraEmMarkClp0DxClp1 = On congestion discard Clp1 cells
                      gcraEmMarkAllDxAll = On congestion mark all
                      gcraEmMarkClp0DxAll = on congestion mark clp0 and discard
                                            all"
                    ::= { xylnatmVclEntry 34}

                xylnatmVclMcGroupId   OBJECT-TYPE
                    SYNTAX    INTEGER
                    ACCESS     read-only
                    STATUS         mandatory
                    DESCRIPTION
                     "Internal use of multicast group id"
                    ::= { xylnatmVclEntry 35}


               xylnatmVclMcIngressEgress    OBJECT-TYPE
                    SYNTAX    INTEGER {
										ingress(1),
										egress(2)
									}
                    ACCESS     read-only
                    STATUS         mandatory
                    DESCRIPTION
                     "Always ingress in this release"
                    ::= { xylnatmVclEntry 36}


			xylnatmVclStatTable		OBJECT-TYPE
				SYNTAX		SEQUENCE OF XylnatmVclStatEntry
				ACCESS		not-accessible
				STATUS		mandatory
				DESCRIPTION
					"This table contains the xylan specific statistical object"
				::= { xylnatmVclStatGroup 1}

			xylnatmVclStatEntry		OBJECT-TYPE
				SYNTAX		XylnatmVclStatEntry
				ACCESS		not-accessible
				STATUS		mandatory
				DESCRIPTION
					"Contains the stats objects"
				INDEX	{xylnatmVclStatSlotIndex,
						 xylnatmVclStatPortIndex,
						 xylnatmVclStatVpi,
						 xylnatmVclStatVci }
				::= { xylnatmVclStatTable 1}

			XylnatmVclStatEntry		::=	SEQUENCE {
				xylnatmVclStatSlotIndex		INTEGER,
				xylnatmVclStatPortIndex		INTEGER,
				xylnatmVclStatVpi			INTEGER,
				xylnatmVclStatVci			INTEGER,
				xylnatmVclStatRxCells		Counter,
				xylnatmVclStatTxCells			Counter,
				xylnatmVclStatRxClp0Cells		Counter,
				xylnatmVclStatRxClp1Cells		Counter,
				xylnatmVclStatDxCongClp0Cells	Counter,
				xylnatmVclStatDxCongClp1Cells	Counter,
				xylnatmVclStatDxGcraClp0Cells	Counter,
				xylnatmVclStatDxGcraClp1Cells	Counter,
				xylnatmVclStatDxGcraBClp0Cells	Counter,
				xylnatmVclStatDxGcraBClp1Cells	Counter
					}

			xylnatmVclStatSlotIndex	OBJECT-TYPE
				SYNTAX		INTEGER
				ACCESS		read-only
				STATUS		mandatory
				DESCRIPTION
					"The slot number of the chassis"
				::= { xylnatmVclStatEntry 1}

               xylnatmVclStatPortIndex    OBJECT-TYPE
                    SYNTAX    INTEGER  (1..25)
                    ACCESS     read-only
                    STATUS     mandatory
                    DESCRIPTION
                     "The port number of this slot"
                    ::= { xylnatmVclStatEntry 2}

               xylnatmVclStatVpi    OBJECT-TYPE
                    SYNTAX    INTEGER  
                    ACCESS     read-only
                    STATUS     mandatory
                    DESCRIPTION
                     "The Vpi number for this connection"
                    ::= { xylnatmVclStatEntry 3}

                xylnatmVclStatVci   OBJECT-TYPE
                    SYNTAX    INTEGER  
                    ACCESS     read-only
                    STATUS     mandatory
                    DESCRIPTION
                     "The Vci number for the connection"
                    ::= { xylnatmVclStatEntry 4}

                xylnatmVclStatRxCells   OBJECT-TYPE
                    SYNTAX    Counter
                    ACCESS     read-only
                    STATUS     mandatory
                    DESCRIPTION
                     " The total number of cells received on this connection
					   identified by the slot/port/vpi/vci"
                    ::= { xylnatmVclStatEntry 5}


                xylnatmVclStatTxCells   OBJECT-TYPE
                    SYNTAX    Counter
                    ACCESS     read-only
                    STATUS     mandatory
                    DESCRIPTION
                     "The total number of cells transmitted on this connection
					  identified by the slot/port/vpi/vci"
                    ::= { xylnatmVclStatEntry 6}

                xylnatmVclStatRxClp0Cells   OBJECT-TYPE
                    SYNTAX    Counter
                    ACCESS     read-only
                    STATUS     mandatory
                    DESCRIPTION
                     "The total number of received cells with Clp0 received
					  on this connection identified by slot/port/vpi/vci"
                    ::= { xylnatmVclStatEntry 7}


                xylnatmVclStatRxClp1Cells   OBJECT-TYPE
                    SYNTAX    Counter
                    ACCESS     read-only
                    STATUS     mandatory
                    DESCRIPTION
                     "The total number of received cells with Clp1 received
					  on this connection identified by slot/port/vpi/vci"
                    ::= { xylnatmVclStatEntry 8}


                xylnatmVclStatDxCongClp0Cells   OBJECT-TYPE
                    SYNTAX    Counter
                    ACCESS     read-only
                    STATUS     mandatory
                    DESCRIPTION
                     "The total number of cell loss priority zero cells 
				      discarded on this connection at this interface identified
					  by the slot/port due to congestion"
                    ::= { xylnatmVclStatEntry 9}

                xylnatmVclStatDxCongClp1Cells   OBJECT-TYPE
                    SYNTAX    Counter
                    ACCESS     read-only
                    STATUS     mandatory
                    DESCRIPTION
                     "The total number of cell loss priority one cells 
					  discarded on this connection at this interface identified
					  by the slot/port due to congestion"
                    ::= { xylnatmVclStatEntry 10}


               xylnatmVclStatDxGcraClp0Cells    OBJECT-TYPE
                    SYNTAX    Counter
                    ACCESS     read-only
                    STATUS     mandatory
                    DESCRIPTION
                     "The number of Clp0 cells discarded on this connection
					  due to policing on Clp0+1 cells"
                    ::= { xylnatmVclStatEntry 11}


               xylnatmVclStatDxGcraClp1Cells    OBJECT-TYPE
                    SYNTAX    Counter
                    ACCESS     read-only
                    STATUS     mandatory
                    DESCRIPTION
                     "The total number of Clp1 cells discarded due to policing
					  on Clp0+1 cells"
                    ::= { xylnatmVclStatEntry 12}


                xylnatmVclStatDxGcraBClp0Cells   OBJECT-TYPE
                    SYNTAX    Counter
                    ACCESS     read-only
                    STATUS     mandatory
                    DESCRIPTION
                     "The total number of Clp0 cells discarded due to policing
					  on Clp0+1 cells"
                    ::= { xylnatmVclStatEntry 13}


                xylnatmVclStatDxGcraBClp1Cells   OBJECT-TYPE
                    SYNTAX    Counter
                    ACCESS     read-only
                    STATUS     mandatory
                    DESCRIPTION
                     "The total number of Clp1 cells discarded due to policing
					  on Clp0+1 cells"
                    ::= { xylnatmVclStatEntry 14}


             xylnatmVplTable    OBJECT-TYPE
				SYNTAX		SEQUENCE OF XylnatmVplEntry
				ACCESS		not-accessible
				STATUS		mandatory
				DESCRIPTION
					"This table contains xylan implementation specific
					 objects"
                    ::= { xylnatmVplGroup 1 }

               xylnatmVplEntry    OBJECT-TYPE
				SYNTAX		XylnatmVplEntry
				ACCESS		not-accessible
				STATUS		mandatory
				DESCRIPTION
					"List of xylan specific objects"
				INDEX	 {xylnatmVplSlotIndex,
						  xylnatmVplPortIndex,
						  xylnatmVplVpi }
                    ::= { xylnatmVplTable  1}

				XylnatmVplEntry		::=	SEQUENCE {
					xylnatmVplSlotIndex		INTEGER,
					xylnatmVplPortIndex		INTEGER,
					xylnatmVplVpi			INTEGER,
					xylnatmVplConnectionDescr	DisplayString,
					xylnatmVplChanType				INTEGER,
					xylnatmVplTransportPriority		INTEGER,
					xylnatmVplUserPriority			INTEGER,
					xylnatmVplStatsMode				INTEGER,
					xylnatmVplPrTrackPortBase		INTEGER,
					xylnatmVplPrTrackPort1			INTEGER,
					xylnatmVplPrTrackPort2			INTEGER,
					xylnatmVplPrTrackPort3			INTEGER,
					xylnatmVplAltTrackPortBase		INTEGER,
					xylnatmVplAltTrackPort1			INTEGER,
					xylnatmVplAltTrackPort2			INTEGER,
					xylnatmVplAltTrackPort3			INTEGER,
					xylnatmVplLgclChanRedirect		INTEGER,
					xylnatmVplAAL5Discard			INTEGER,
					xylnatmVplF4F5SegEndpt			INTEGER,
					xylnatmVplF4F5CopySeg			INTEGER,
					xylnatmVplF4F5End2EndEndpt		INTEGER,
					xylnatmVplF4F5CopyEnd2End		INTEGER,
					xylnatmVplOamEndpt				INTEGER,
					xylnatmVplOamCopy				INTEGER,
					xylnatmVplRmFwdEndpt			INTEGER,
					xylnatmVplRmFwdCopy				INTEGER,
					xylnatmVplRmFwdGcraAdv			INTEGER,
					xylnatmVplRmBkwdEndpt			INTEGER,
					xylnatmVplRmBkwdCopy			INTEGER,
					xylnatmVplRmBkwdGcraAdv			INTEGER,
					xylnatmVplRmDiscard 			INTEGER,
					xylnatmVplGcraAPoliceMode		INTEGER,
					xylnatmVplGcraBPoliceMode		INTEGER,
					xylnatmVplMcGroupId				INTEGER,
					xylnatmVplMcIngressEgress		INTEGER
                       }
				

               xylnatmVplSlotIndex    OBJECT-TYPE
					SYNTAX		INTEGER
					ACCESS		read-only
					STATUS		mandatory
					DESCRIPTION
						"Slot Instance"
                    ::= { xylnatmVplEntry 1}

               xylnatmVplPortIndex    OBJECT-TYPE
					SYNTAX		INTEGER
					ACCESS		read-only
					STATUS		mandatory
					DESCRIPTION
						"Port Instance"
                    ::= { xylnatmVplEntry 2}

               xylnatmVplVpi    OBJECT-TYPE
					SYNTAX		INTEGER
					ACCESS		read-only
					STATUS		mandatory
					DESCRIPTION
						"Vpi instance"
                   ::= { xylnatmVplEntry 3}

				xylnatmVplConnectionDescr OBJECT-TYPE
					SYNTAX		DisplayString
					ACCESS		read-write
					STATUS		mandatory
					DESCRIPTION
						"An ascii value for the connection"
					::= { xylnatmVplEntry 4 }

               xylnatmVplChanType    OBJECT-TYPE
					SYNTAX		INTEGER {
									unknown(1),
--									vpSegmentEndToEnd(2),
									vpNNI(5),
									vpUni(6)
--									xylanOam(7)
										}
					ACCESS		read-write
					STATUS		mandatory
					DESCRIPTION
						"The type of Virtual path"
                    ::= { xylnatmVplEntry 5}


               xylnatmVplTransportPriority	 OBJECT-TYPE
                    SYNTAX    INTEGER  {
--											qosCbrMc(1),
											qosCbrPrs(2),
											qosCbr(3),
--											qosVbrMc(4),
											qosVbrRt(5),
											qosVbrNrt(6),
											qosAbr(7),
											qosUbr(8)
										}
                    ACCESS     read-write
                    STATUS         mandatory
                    DESCRIPTION
                     "The transport priority..."
                    ::= { xylnatmVplEntry 6}

               xylnatmVplUserPriority	 OBJECT-TYPE
                    SYNTAX    INTEGER  
                    ACCESS    read-write
                    STATUS    mandatory
                    DESCRIPTION
                     "The user priority 0-15 with 0 being the highest"
                    ::= { xylnatmVplEntry 7}

               xylnatmVplStatsMode    OBJECT-TYPE
                    SYNTAX    INTEGER  {
											cntGcraDxCell(1),
											mrkGcraDxCell(2),
											cntGcraPsCell(3),
											mrkGcraPsCell(4)
										}
                    ACCESS     read-write
                    STATUS         mandatory
                    DESCRIPTION
                  "This allows the user one of the 4 choices. When the
                   user selects 
                   cntGcraDxCell = count clp0 & 1 and discard cell
                   mrkGcraDxCell = count clp0 & 1, mark efci &clp, discard cell
                   cntGcraPsCell = count clp0 &1 and pass the cell
                   mrkGcraPsCell = count clp0 &1, mark efci and clp, pass cell"
                    ::= { xylnatmVplEntry 8}

               xylnatmVplPrTrackPortBase    OBJECT-TYPE
                    SYNTAX    INTEGER  
                    ACCESS     read-only
                    STATUS         mandatory
                    DESCRIPTION
                     "The destination internal pport"
                    ::= { xylnatmVplEntry 9}

               xylnatmVplPrTrackPort1    OBJECT-TYPE
                    SYNTAX    INTEGER 
                    ACCESS     read-only
                    STATUS         mandatory
                    DESCRIPTION
                     "Used under multicast conditions and will be supported
                      in future releases for load balancing"
                    ::= { xylnatmVplEntry 10}

               xylnatmVplPrTrackPort2    OBJECT-TYPE
                    SYNTAX    INTEGER 
                    ACCESS     read-only
                    STATUS         mandatory
                    DESCRIPTION
                     "Used under multicast conditions and will be supported
                      in future releases for load balancing"
                    ::= { xylnatmVplEntry 11}

               xylnatmVplPrTrackPort3    OBJECT-TYPE
                    SYNTAX    INTEGER 
                    ACCESS     read-only 
                    STATUS         mandatory
                    DESCRIPTION
                     "Used under multicast conditions and will be supported
                      in future releases for load balancing"
                    ::= { xylnatmVplEntry 12}

               xylnatmVplAltTrackPortBase    OBJECT-TYPE
                    SYNTAX    INTEGER 
                    ACCESS     read-only 
                    STATUS         mandatory
                    DESCRIPTION
                     "Alternate port under failure conditions and will be
                      supported in future release"
                    ::= { xylnatmVplEntry 13}

               xylnatmVplAltTrackPort1    OBJECT-TYPE
                    SYNTAX    INTEGER 
                    ACCESS     read-only 
                    STATUS         mandatory
                    DESCRIPTION
                     "Alternate port under failure conditions and will be
                      supported in future release"
                    ::= { xylnatmVplEntry 14}

               xylnatmVplAltTrackPort2    OBJECT-TYPE
                    SYNTAX    INTEGER 
                    ACCESS     read-only
                    STATUS         mandatory
                    DESCRIPTION
                     "Alternate port under failure conditions and will be
                      supported in future release"
                    ::= { xylnatmVplEntry 15}

              xylnatmVplAltTrackPort3     OBJECT-TYPE
                    SYNTAX    INTEGER 
                    ACCESS     read-only 
                    STATUS         mandatory
                    DESCRIPTION
                     "Alternate port under failure conditions and will be
                      supported in future release"
                    ::= { xylnatmVplEntry 16}

                xylnatmVplLgclChanRedirect   OBJECT-TYPE
                    SYNTAX    INTEGER {
										notAllowed(1),
										allowed(2)
									}
                    ACCESS     read-write
                    STATUS         mandatory
                    DESCRIPTION
                     "Permits the user to allow or not allow logical channel
                      redirects"
                    ::= { xylnatmVplEntry 17}

               xylnatmVplAAL5Discard    OBJECT-TYPE
                    SYNTAX    INTEGER  {
			earlyPktDiscard(1),
			disable(2),
			partialPktDiscard(3)
			}
                    ACCESS     read-write
                    STATUS         mandatory
                    DESCRIPTION
                       "This field configures an action that IOP should take
                       against cells when traffic congestion occurs.
                       
                       earlyPktDiscard(1) is treated as 'enable'
                       for IOP version 1 since it doesn't support early packet discard
                       feature.   Early packet discard is an IOP 2 feature.
                       In this mode, IOP either passes or discards all the cells
                       of a packet.  It passes all cells of a packet during congestion if
                       the first cell of the packet has been passed.  
                       Cells are marked when GCRA contract is violated.
                       This option does not apply to VBR_RT and CBR and CBR_PRS.

                       disable(2) is selected to disable early packet discard and
                       partial discard feature.  Cells are discarded when needed 
                       during congestion.  Cells are marked when GCRA contract
                       is violated.
                   
                       partialPktDiscard(3) is an IOP 2 feature.   IOP starts discarding
                       cells--all of the remaining cells except for the last cell of
                       the packet-when congestion occurs.
                       When congestion ends, the first cell of a new packet is passed.
                       Cells are marked when GCRA contract is violated. 
                       This option does not apply to VBR_RT and CBR and CBR_PRS.
    
                       The default value for IOP 1 is 'disable'.
                       The default value is 'earlyPktDiscard'
                       for IOP 2 if the transport type of the circuit is UBR,
                       ABR, and VBR_NRT. 
                       'disable' is the default VBR_RT and CBR."
                    ::= { xylnatmVplEntry 18}

               xylnatmVplF4F5SegEndpt    OBJECT-TYPE
                    SYNTAX    INTEGER {
										enable(1),
										disable(2)
									}
                    ACCESS     read-write
                    STATUS         mandatory
                    DESCRIPTION
                     "Future release"
                    ::= { xylnatmVplEntry 19}

               xylnatmVplF4F5CopySeg    OBJECT-TYPE
                    SYNTAX    INTEGER {
										enable(1),
										disable(2)
									}
                    ACCESS     read-write
                    STATUS         mandatory
                    DESCRIPTION
                     "Future release"
                    ::= { xylnatmVplEntry 20}

                xylnatmVplF4F5End2EndEndpt   OBJECT-TYPE
                    SYNTAX    INTEGER {
										enable(1),
										disable(2)
									}
                    ACCESS     read-write
                    STATUS         mandatory
                    DESCRIPTION
                     "Future release"
                    ::= { xylnatmVplEntry 21}

               xylnatmVplF4F5CopyEnd2End    OBJECT-TYPE
                    SYNTAX    INTEGER {
										enable(1),
										disable(2)
									}
                    ACCESS     read-write
                    STATUS         mandatory
                    DESCRIPTION
                     "Future release"
                    ::= { xylnatmVplEntry 22}

                xylnatmVplOamEndpt   OBJECT-TYPE
                    SYNTAX    INTEGER {
										enable(1),
										disable(2)
									}
                    ACCESS     read-write
                    STATUS         mandatory
                    DESCRIPTION
                     "Future release"
                    ::= { xylnatmVplEntry 23}

                xylnatmVplOamCopy   OBJECT-TYPE
                    SYNTAX    INTEGER {
										enable(1),
										disable(2)
									}
                    ACCESS     read-write
                    STATUS         mandatory
                    DESCRIPTION
                     "Future release"
                    ::= { xylnatmVplEntry 24}

                xylnatmVplRmFwdEndpt   OBJECT-TYPE
                    SYNTAX    INTEGER {
										enable(1),
										disable(2)
									}
                    ACCESS     read-write
                    STATUS         mandatory
                    DESCRIPTION
                     "Future release"
                    ::= { xylnatmVplEntry 25}

               xylnatmVplRmFwdCopy    OBJECT-TYPE
                    SYNTAX    INTEGER {
										enable(1),
										disable(2)
									}
                    ACCESS     read-write
                    STATUS         mandatory
                    DESCRIPTION
                     "Future release"
                    ::= { xylnatmVplEntry 26}

              xylnatmVplRmFwdGcraAdv     OBJECT-TYPE
                    SYNTAX    INTEGER {
										enable(1),
										disable(2)
									}
                    ACCESS     read-write
                    STATUS         mandatory
                    DESCRIPTION
                     "Future release"
                    ::= { xylnatmVplEntry 27}

               xylnatmVplRmBkwdEndpt    OBJECT-TYPE
                    SYNTAX    INTEGER {
										enable(1),
										disable(2)
									}
                    ACCESS     read-write
                    STATUS         mandatory
                    DESCRIPTION
                     "Future release"
                    ::= { xylnatmVplEntry 28}

               xylnatmVplRmBkwdCopy    OBJECT-TYPE
                    SYNTAX    INTEGER {
										enable(1),
										disable(2)
									}
                    ACCESS     read-write
                    STATUS         mandatory
                    DESCRIPTION
                     "Future release"
                    ::= { xylnatmVplEntry 29}

               xylnatmVplRmBkwdGcraAdv    OBJECT-TYPE
                    SYNTAX    INTEGER {
										enable(1),
										disable(2)
									}
                    ACCESS     read-write
                    STATUS         mandatory
                    DESCRIPTION
                     "Future release"
                    ::= { xylnatmVplEntry 30}

               xylnatmVplRmDiscard    OBJECT-TYPE
                    SYNTAX    INTEGER {
										enable(1),
										disable(2)
									}
                    ACCESS     read-write
                    STATUS         mandatory
                    DESCRIPTION
                     "Future release"
                    ::= { xylnatmVplEntry 31}

               xylnatmVplGcraAPoliceMode    OBJECT-TYPE
                    SYNTAX    INTEGER {
										gcraEmDxAll(1),
										gcraEmMarkClp0DxClp1(2),
										gcraEmMarkAllDxAll(3),
										gcraEmMarkClp0DxAll(4)
									}
                    ACCESS     read-only
                    STATUS         mandatory
                    DESCRIPTION
                     "Enforcement mode of GcraA as following
                      gcraEmDxAll = Discard all cells on congestion
                      gcraEmMarkClp0DxClp1 = On congestion discard Clp1 cells
                      gcraEmMarkAllDxAll = On congestion mark all
                      gcraEmMarkClp0DxAll = on congestion mark clp0 and discard
                                            all"
                    ::= { xylnatmVplEntry 32}

               xylnatmVplGcraBPoliceMode    OBJECT-TYPE
                    SYNTAX    INTEGER  {
										gcraEmDxAll(1),
										gcraEmMarkClp0DxClp1(2),
										gcraEmMarkAllDxAll(3),
										gcraEmMarkClp0DxAll(4)
									}
                    ACCESS     read-only
                    STATUS         mandatory
                    DESCRIPTION
                     "Enforcement mode of GcraB as following
                      gcraEmDxAll = Discard all cells on congestion
                      gcraEmMarkClp0DxClp1 = On congestion discard Clp1 cells
                      gcraEmMarkAllDxAll = On congestion mark all
                      gcraEmMarkClp0DxAll = on congestion mark clp0 and discard
                                            all"
                    ::= { xylnatmVplEntry 33}

                xylnatmVplMcGroupId   OBJECT-TYPE
                    SYNTAX    INTEGER
                    ACCESS     read-only
                    STATUS         mandatory
                    DESCRIPTION
                     "Internal use of multicast group id"
                    ::= { xylnatmVplEntry 34}

               xylnatmVplMcIngressEgress    OBJECT-TYPE
                    SYNTAX    INTEGER {
										ingress(1),
										egress(2)
									}
                    ACCESS     read-only
                    STATUS         mandatory
                    DESCRIPTION
                     "Always ingress in this release"
                    ::= { xylnatmVplEntry 35}


			xylnatmVplStatTable		OBJECT-TYPE
				SYNTAX		SEQUENCE OF XylnatmVplStatEntry
				ACCESS		not-accessible
				STATUS		mandatory
				DESCRIPTION
					"This table contains the xylan specific statistical object"
				::= { xylnatmVplStatGroup 1}

			xylnatmVplStatEntry		OBJECT-TYPE
				SYNTAX		XylnatmVplStatEntry
				ACCESS		not-accessible
				STATUS		mandatory
				DESCRIPTION
					"Contains the stats objects"
				INDEX	{xylnatmVplStatSlotIndex,
						 xylnatmVplStatPortIndex,
						 xylnatmVplStatVpi }
				::= { xylnatmVplStatTable 1}

			XylnatmVplStatEntry		::=	SEQUENCE {
				xylnatmVplStatSlotIndex		INTEGER,
				xylnatmVplStatPortIndex		INTEGER,
				xylnatmVplStatVpi			INTEGER,
				xylnatmVplStatRxCells		Counter,
				xylnatmVplStatTxCells			Counter,
				xylnatmVplStatRxClp0Cells		Counter,
				xylnatmVplStatRxClp1Cells		Counter,
				xylnatmVplStatDxCongClp0Cells	Counter,
				xylnatmVplStatDxCongClp1Cells	Counter,
				xylnatmVplStatDxGcraClp0Cells	Counter,
				xylnatmVplStatDxGcraClp1Cells	Counter,
				xylnatmVplStatDxGcraBClp0Cells	Counter,
				xylnatmVplStatDxGcraBClp1Cells	Counter
					}

			xylnatmVplStatSlotIndex	OBJECT-TYPE
				SYNTAX		INTEGER
				ACCESS		read-only
				STATUS		mandatory
				DESCRIPTION
					"The slot number of the chassis"
				::= { xylnatmVplStatEntry 1}

               xylnatmVplStatPortIndex    OBJECT-TYPE
                    SYNTAX    INTEGER  (1..25)
                    ACCESS     read-only
                    STATUS     mandatory
                    DESCRIPTION
                     "The port number on this slot"
                    ::= { xylnatmVplStatEntry 2}

               xylnatmVplStatVpi    OBJECT-TYPE
                    SYNTAX    INTEGER  
                    ACCESS     read-only
                    STATUS     mandatory
                    DESCRIPTION
                     "The Vpi number for this connection"
                    ::= { xylnatmVplStatEntry 3}

                xylnatmVplStatRxCells   OBJECT-TYPE
                    SYNTAX    Counter
                    ACCESS     read-only
                    STATUS     mandatory
                    DESCRIPTION
                     " The total number of cells received on this connection
					   identified by the slot/port/vpi"
                    ::= { xylnatmVplStatEntry 4}


                xylnatmVplStatTxCells   OBJECT-TYPE
                    SYNTAX    Counter
                    ACCESS     read-only
                    STATUS     mandatory
                    DESCRIPTION
                     "The total number of cells transmitted on this connection
					  identified by the slot/port/vpi"
                    ::= { xylnatmVplStatEntry 5}

                xylnatmVplStatRxClp0Cells   OBJECT-TYPE
                    SYNTAX    Counter
                    ACCESS     read-only
                    STATUS     mandatory
                    DESCRIPTION
                     "The total number of received cells with Clp0 received
					  on this connection identified by slot/port/vpi"
                    ::= { xylnatmVplStatEntry 6}


                xylnatmVplStatRxClp1Cells   OBJECT-TYPE
                    SYNTAX    Counter
                    ACCESS     read-only
                    STATUS     mandatory
                    DESCRIPTION
                     "The total number of received cells with Clp1 received
					  on this connection identified by slot/port/vpi"
                    ::= { xylnatmVplStatEntry 7}


                xylnatmVplStatDxCongClp0Cells   OBJECT-TYPE
                    SYNTAX    Counter
                    ACCESS     read-only
                    STATUS     mandatory
                    DESCRIPTION
                     "The total number of cell loss priority zero cells 
				      discarded on this connection at this interface identified
					  by the slot/port due to congestion"
                    ::= { xylnatmVplStatEntry 8}

                xylnatmVplStatDxCongClp1Cells   OBJECT-TYPE
                    SYNTAX    Counter
                    ACCESS     read-only
                    STATUS     mandatory
                    DESCRIPTION
                     "The total number of cell loss priority one cells 
					  discarded on this connection at this interface identified
					  by the slot/port due to congestion"
                    ::= { xylnatmVplStatEntry 9}


               xylnatmVplStatDxGcraClp0Cells    OBJECT-TYPE
                    SYNTAX    Counter
                    ACCESS     read-only
                    STATUS     mandatory
                    DESCRIPTION
                     "The number of Clp0 cells discarded on this connection
					  due to policing on Clp0+1 cells"
                    ::= { xylnatmVplStatEntry 10}


               xylnatmVplStatDxGcraClp1Cells    OBJECT-TYPE
                    SYNTAX    Counter
                    ACCESS     read-only
                    STATUS     mandatory
                    DESCRIPTION
                     "The total number of Clp1 cells discarded due to policing
					  on Clp0+1 cells"
                    ::= { xylnatmVplStatEntry 11}


                xylnatmVplStatDxGcraBClp0Cells   OBJECT-TYPE
                    SYNTAX    Counter
                    ACCESS     read-only
                    STATUS     mandatory
                    DESCRIPTION
                     "The number of Clp0 cells discarded on this connection
					  due to policing on Clp0+1 cells"
                    ::= { xylnatmVplStatEntry 12}


                xylnatmVplStatDxGcraBClp1Cells   OBJECT-TYPE
                    SYNTAX    Counter
                    ACCESS     read-only
                    STATUS     mandatory
                    DESCRIPTION
                     "The total number of Clp1 cells discarded due to policing
					  on Clp0+1 cells"
                    ::= { xylnatmVplStatEntry 13}


               xylnatmVpCrossConnectTable OBJECT-TYPE
                    SYNTAX  SEQUENCE OF XylnatmVpCrossConnectEntry
                    ACCESS  not-accessible
                    STATUS  mandatory
                    DESCRIPTION
                     "The Xyln specific ATM VP Cross Connect table.  A bi-
                      directional VP cross-connect which
                      cross-connects two end points (i.e., VPLs)
                      is modeled as one entry in this table.
					  This table along with the xylan VcCrossConnect Table
                      contains all the objects which would enable xylan NMS
 					  to create a cross connection without creating VCL's and
 					  then cross connecting them. The reason why we prefer
					  this approach is to prevent creation of VCL's which
					  in our architecture is actually a cross connect with
					  all the cells coming in on that vc going to the fabric
					  and then getting switched back on the same vc that it
					  came in.
					  We have also duplicated all the objects in the Vcl
					  table so that they can be set in a single set request."
                    ::= { xylnatmVpCrossConnectGroup 1 }


               xylnatmVpCrossConnectEntry OBJECT-TYPE
                    SYNTAX  XylnatmVpCrossConnectEntry
                    ACCESS  not-accessible
                    STATUS  mandatory
                    DESCRIPTION
                     "An entry in the ATM VP Cross Connect table.
                      This entry is used to model a bi-directional ATM
                      VP cross-connect cross-connecting two end points."
                    INDEX { xylnatmVpCrossConnectLowSlotIndex,
                          xylnatmVpCrossConnectLowPortIndex,
                          xylnatmVpCrossConnectLowVpi,
                          xylnatmVpCrossConnectHighSlotIndex,
                          xylnatmVpCrossConnectHighPortIndex,
                          xylnatmVpCrossConnectHighVpi}
                    ::= { xylnatmVpCrossConnectTable 1 }

               XylnatmVpCrossConnectEntry ::= SEQUENCE {
                    xylnatmVpCrossConnectLowSlotIndex   INTEGER,
                    xylnatmVpCrossConnectLowPortIndex     INTEGER,
                    xylnatmVpCrossConnectLowVpi         INTEGER,
                    xylnatmVpCrossConnectHighSlotIndex  INTEGER,
                    xylnatmVpCrossConnectHighPortIndex    INTEGER,
                    xylnatmVpCrossConnectHighVpi        INTEGER,
                    xylnatmVpCrossConnectConnectionId   		INTEGER,
					xylnatmVpCrossConnectLowRxTrafficDescrIndex INTEGER,
					xylnatmVpCrossConnectLowTxTrafficDescrIndex INTEGER,
					xylnatmVpCrossConnectMCastEnable			INTEGER,
                    xylnatmVpCrossConnectL2HLastChange 			DisplayString,
                    xylnatmVpCrossConnectH2LLastChange			DisplayString,
                    xylnatmVpCrossConnectL2HOperStatus 			INTEGER,
                    xylnatmVpCrossConnectH2LOperStatus 			INTEGER,
					xylnatmVpCrossConnectVcType					INTEGER,
                    xylnatmVpCrossConnectPvcIdentifier          INTEGER,
					xylnatmVpCrossConnectRowStatus		   		INTEGER
                            }

               xylnatmVpCrossConnectLowSlotIndex OBJECT-TYPE
                    SYNTAX  INTEGER (1..9)
                    ACCESS  read-only
                    STATUS  mandatory
                    DESCRIPTION
                     "The low slot number"
                    ::= { xylnatmVpCrossConnectEntry 1 }

               xylnatmVpCrossConnectLowPortIndex OBJECT-TYPE
                    SYNTAX  INTEGER
                    ACCESS  read-only
                    STATUS  mandatory
                    DESCRIPTION
                     "The low physical port number"
                    ::= { xylnatmVpCrossConnectEntry 2 }

               xylnatmVpCrossConnectLowVpi OBJECT-TYPE
                    SYNTAX  INTEGER  (0..4095)
                    ACCESS  read-only
                    STATUS  mandatory
                    DESCRIPTION
                     "The value of this object is equal to the VPI
                      value at the ATM interface
                      associated with the VP cross-connect that is
                      identified by atmVpCrossConnectLow(Slot/Port)Index.
                      The VPI value cannot exceed the number
                      supported by the atmInterfaceMaxVpiBits
                      at the low ATM interface port."
                    ::= { xylnatmVpCrossConnectEntry 3 }

               xylnatmVpCrossConnectHighSlotIndex OBJECT-TYPE
                    SYNTAX  INTEGER (1..9)
                    ACCESS  read-only
                    STATUS  mandatory
                    DESCRIPTION
                     "The value of the high slot number"
                    ::= { xylnatmVpCrossConnectEntry 4 }

               xylnatmVpCrossConnectHighPortIndex OBJECT-TYPE
                    SYNTAX  INTEGER
                    ACCESS  read-only
                    STATUS  mandatory
                    DESCRIPTION
                     "The high physical port number"
                    ::= { xylnatmVpCrossConnectEntry 5}

               xylnatmVpCrossConnectHighVpi OBJECT-TYPE
                    SYNTAX  INTEGER   (0..4095)
                    ACCESS  read-only
                    STATUS  mandatory
                    DESCRIPTION
                     "The value of this object is equal to the VPI
                      value at the ATM interface associated with
                      the VP cross-connect that is identified
                      by atmVpCrossConnectHigh(Slot/Port)Index.
                      The VPI value cannot exceed the number
                      supported by the atmInterfaceMaxVpiBits
                      at the high ATM interface port."
                    ::= { xylnatmVpCrossConnectEntry 6 }


            xylnatmVpCrossConnectConnectionId OBJECT-TYPE
                     SYNTAX	INTEGER {
                                multicastParent(1),
                                multicastChild(2),
								nonMulticastParent(3),
                                unknown(4)
                                   }
                    ACCESS	read-only
                    STATUS	mandatory
                    DESCRIPTION
                         "The status of this object indicates whether
                         the said Vc Cross Connection is the parent or
                         a child. If the connection status is unknown, then
                         the value of this object is unknown. Only deletion
                         of the parent is possible when all the child 
                         connections have been disconnected. To delete all
                         all parent and child connections, use the VCL table
                         to delete the low VCL."
                    ::= {xylnatmVpCrossConnectEntry 7 }

			xylnatmVpCrossConnectLowRxTrafficDescrIndex OBJECT-TYPE
					SYNTAX INTEGER
					ACCESS read-write
					STATUS mandatory
					DESCRIPTION
						"The receive traffic descriptor index. The reason why
						 we duplicate this index is to allow the user to change
						 the traffic descriptor without deleting the connection
						 AND without any changes to the RFC1695.mib. RFC1695
						 describes the traffic descriptor indices only the 
						 vcl/vpl tables. Hence if the user wishes to change 
						 the TD after creating the cross-connection, then the 
						 user has to 
						 delete the cross connection to ensire that the receive
						 direction of the low end of the cross connect is equal
						 to the transmit direction of the other VCL at the high
						 end of the cross connect.
						 10/18/96. Since we dont want to create Vcl without
						 cross connecting them, NMS will now call this table
						 which would allow the creation/deletion and 
						 modification of Cross Connect Entries. "
					::= {xylnatmVpCrossConnectEntry 8}

			xylnatmVpCrossConnectLowTxTrafficDescrIndex OBJECT-TYPE
					SYNTAX INTEGER
					ACCESS read-write
					STATUS mandatory
					DESCRIPTION
						"The transmit traffic descriptor index. The reason why
						 we duplicate this index is to allow the user to change
						 the traffic descriptor without deleting the connection
						 AND without any changes to the RFC1695.mib. RFC1695
						 describes the traffic descriptor indices only the 
						 vcl/vpl tables. Hence if the user wishes to change 
						 the TD after creating the cross-connection, then the 
						 user has to 
						 delete the cross connection to ensire that the receive
						 direction of the low end of the cross connect is equal
						 to the transmit direction of the other VCL at the high
						 end of the cross connect.
						 10/18/96. Since we dont want to create Vcl without
						 cross connecting them, NMS will now call this table
						 which would allow the creation/deletion and 
						 modification of Cross Connect Entries. "
					::= {xylnatmVpCrossConnectEntry 9}


               xylnatmVpCrossConnectMCastEnable OBJECT-TYPE
                    SYNTAX  INTEGER {
										enable(1),
										disable(2) 
									}
                    ACCESS  read-write
                    STATUS  mandatory
                    DESCRIPTION
                     "Whether Mcast should be enabled/disabled for this
 					  connection"
                    ::= { xylnatmVpCrossConnectEntry 10 }

               xylnatmVpCrossConnectL2HLastChange OBJECT-TYPE
                    SYNTAX  DisplayString
                    ACCESS  read-only
                    STATUS  mandatory
                    DESCRIPTION
                     "The value of MIB II's sysUpTime object
                      at the time this VC cross-connect entered
                      its current operational state in low to high
                      direction.  If the current state was
                      entered prior to the last re-initialization of the
                      agent, then this object contains a zero value."
                    ::= { xylnatmVpCrossConnectEntry 11 }

               xylnatmVpCrossConnectH2LLastChange OBJECT-TYPE
                    SYNTAX  DisplayString
                    ACCESS  read-only
                    STATUS  mandatory
                    DESCRIPTION
                     "The value of MIB II's sysUpTime object
                      at the time this VC cross-connect entered
                      its current operational state in high to low
                      direction.  If the current state was
                      entered prior to the last re-initialization of the
                      agent, then this object contains a zero value."
                    ::= { xylnatmVpCrossConnectEntry 12 }

               xylnatmVpCrossConnectL2HOperStatus OBJECT-TYPE
                    SYNTAX  INTEGER {
										unknown(1),
										end2endup (2),
										end2endDown(3),
										localUpEndToEndUnknown(4),
										localDown(5)
                            }
                    ACCESS  read-only
                    STATUS  mandatory
                    DESCRIPTION
                     "The value of this object identifies the current
                      operational status of the VC cross-connect
                      in one direction; (i.e., from the low to
                      high direction).  The up and down states indicate
                      that this ATM VC cross-connect from low
                      to high direction is operational or not
                      operational respectively.  The unknown state
                      indicates that the state of it cannot be
                      determined."
                    ::= { xylnatmVpCrossConnectEntry 13 }


               xylnatmVpCrossConnectH2LOperStatus OBJECT-TYPE
                    SYNTAX  INTEGER {
										unknown(1),
										end2endup (2),
										end2endDown(3),
										localUpEndToEndUnknown(4),
										localDown(5)
                            }
                    ACCESS  read-only
                    STATUS  mandatory
                    DESCRIPTION
                     "The value of this object identifies the current
                      operational status of the VC cross-connect
                      in one direction; (i.e., from the high to
                      low direction).  The up and down states indicate
                      that this ATM VC cross-connect from high
                      to low direction is operational or not
                      operational respectively.  The unknown state
                      indicates that the state of it cannot be
                      determined."
                    ::= { xylnatmVpCrossConnectEntry 14 }


               xylnatmVpCrossConnectVcType          OBJECT-TYPE
                    SYNTAX       INTEGER {
											pvc (1),
											svc (2),
											softPvc (3),
											control (4)
                                        }
                    ACCESS   read-only
                    STATUS       mandatory
                    DESCRIPTION
                     "The type of VC...Permanent/Switched/Soft/control"
                          ::= {xylnatmVpCrossConnectEntry 15}

               xylnatmVpCrossConnectPvcIdentifier          OBJECT-TYPE
                    SYNTAX       INTEGER 
                    ACCESS   read-write
                    STATUS       mandatory
                    DESCRIPTION
                     "This is required by NMS to id PVC's across networks"
                          ::= {xylnatmVpCrossConnectEntry 16}

               xylnatmVpCrossConnectRowStatus          OBJECT-TYPE
                    SYNTAX       INTEGER {
                                        create (1),
                                        modify (2),
                                        delete (3),
                                        active (4),
                                        notActive (5)
                                        }
                    ACCESS   read-write
                    STATUS       mandatory
                    DESCRIPTION
                     "This object is used to create, delete or
                      modify a row in this table.  To create
                      a new CrossConnect, this object is initially set
                      to 'createAndWait' or 'createAndGo'.
                      This object must not be set to 'active'
                      unless the following columnar objects exist
                      in this row:
                      xylnatmVcCrossConnectLowRxTrafficDescrIndex,
                      xylnatmVcCrossConnectLowTxTrafficDescrIndex.
                      Xylan implements createAndWait along with create&Go
                      as create. Create is basically a superset.
                      In addition, if the local VCL end-point
                      is also the VCC end-point"
                          ::= {xylnatmVpCrossConnectEntry 17 }


               xylnatmVcCrossConnectTable OBJECT-TYPE
                    SYNTAX  SEQUENCE OF XylnatmVcCrossConnectEntry
                    ACCESS  not-accessible
                    STATUS  mandatory
                    DESCRIPTION
                     "The ATM VC Cross Connect table.  A bi-
                      directional VC cross-connect which
                      cross-connects two end points (i.e., VCLs)
                      is modeled as one entry in this table."
                    ::= { xylnatmVcCrossConnectGroup 1 }


               xylnatmVcCrossConnectEntry OBJECT-TYPE
                    SYNTAX  XylnatmVcCrossConnectEntry
                    ACCESS  not-accessible
                    STATUS  mandatory
                    DESCRIPTION
                     "An entry in the ATM VC Cross Connect table.
                      This entry is used to model a bi-directional ATM
                      VC cross-connect cross-connecting two end points."
                    INDEX { xylnatmVcCrossConnectLowSlotIndex,
                          xylnatmVcCrossConnectLowPortIndex,
                          xylnatmVcCrossConnectLowVpi,
                          xylnatmVcCrossConnectLowVci,
                          xylnatmVcCrossConnectHighSlotIndex,
                          xylnatmVcCrossConnectHighPortIndex,
                          xylnatmVcCrossConnectHighVpi,
                          xylnatmVcCrossConnectHighVci }
                    ::= { xylnatmVcCrossConnectTable 1 }

               XylnatmVcCrossConnectEntry ::= SEQUENCE {
                    xylnatmVcCrossConnectLowSlotIndex   		INTEGER,
                    xylnatmVcCrossConnectLowPortIndex     		INTEGER,
                    xylnatmVcCrossConnectLowVpi         		INTEGER,
                    xylnatmVcCrossConnectLowVci         		INTEGER,
                    xylnatmVcCrossConnectHighSlotIndex  		INTEGER,
                    xylnatmVcCrossConnectHighPortIndex    		INTEGER,
                    xylnatmVcCrossConnectHighVpi        		INTEGER,
                    xylnatmVcCrossConnectHighVci        		INTEGER,
                    xylnatmVcCrossConnectConnectionId   		INTEGER,
					xylnatmVcCrossConnectLowRxTrafficDescrIndex INTEGER,
					xylnatmVcCrossConnectLowTxTrafficDescrIndex INTEGER,
					xylnatmVcCrossConnectMCastEnable            INTEGER,
                    xylnatmVcCrossConnectL2HLastChange 			DisplayString,
                    xylnatmVcCrossConnectH2LLastChange			DisplayString,
                    xylnatmVcCrossConnectL2HOperStatus 			INTEGER,
                    xylnatmVcCrossConnectH2LOperStatus 			INTEGER,
					xylnatmVcCrossConnectVcType					INTEGER,
                    xylnatmVcCrossConnectPvcIdentifier          INTEGER,
					xylnatmVcCrossConnectRowStatus		   		INTEGER
                            }

              xylnatmVcCrossConnectLowSlotIndex OBJECT-TYPE
                    SYNTAX  INTEGER
                    ACCESS	read-only
                    STATUS	mandatory
                    DESCRIPTION
                        "The incoming slot number"
                   ::= { xylnatmVcCrossConnectEntry 1 }

               xylnatmVcCrossConnectLowPortIndex OBJECT-TYPE
                    SYNTAX  INTEGER
                    ACCESS  read-only
                    STATUS  mandatory
                    DESCRIPTION
                     "The value of this object is equal to 
                      the ATM interface port in this slot for this
                      VC cross-connect.  The term low implies
                      that this ATM interface has the numerically lower
                      slot/port value than the other ATM interface
                      identified in the same atmVcCrossConnectEntry."
                    ::= { xylnatmVcCrossConnectEntry 2 }

               xylnatmVcCrossConnectLowVpi OBJECT-TYPE
                    SYNTAX  INTEGER  (0..4095)
                    ACCESS  read-only
                    STATUS  mandatory
                    DESCRIPTION
                     "The value of this object is equal to the VPI
                      value at the ATM interface
                      associated with the VC cross-connect that is
                      identified by atmVcCrossConnectLow(Slot/Port)Index.
                      The VPI value cannot exceed the number
                      supported by the atmInterfaceMaxVpiBits
                      at the low ATM interface port."
                    ::= { xylnatmVcCrossConnectEntry 3 }

               xylnatmVcCrossConnectLowVci OBJECT-TYPE
                    SYNTAX  INTEGER  (0..65535)
                    ACCESS  read-only
                    STATUS  mandatory
                    DESCRIPTION
                     "The value of this object is equal to the VCI
                      value at the ATM interface
                      associated with this VC cross-connect that is
                      identified by atmVcCrossConnectLow(Slot/Port)Index.
                      The VCI value cannot exceed the number
                      supported by the atmInterfaceMaxVciBits
                      at the low ATM interface port."
                    ::= { xylnatmVcCrossConnectEntry 4 }


               xylnatmVcCrossConnectHighSlotIndex OBJECT-TYPE
                    SYNTAX  INTEGER (1..9)
                    ACCESS  read-only
                    STATUS  mandatory
                    DESCRIPTION
                     "The high port number"
                    ::= { xylnatmVcCrossConnectEntry 5 }

               xylnatmVcCrossConnectHighPortIndex OBJECT-TYPE
                    SYNTAX  INTEGER
                    ACCESS  read-only
                    STATUS  mandatory
                    DESCRIPTION
                     "The value of this object is equal to
                      the ATM interface port in this slot for
                      this VC cross-connect.  The term high
                      implies that this VC cross-connect
                      that this ATM interface has the numerically higher
                      slot/port value than the other ATM interface
                      identified in the same atmVcCrossConnectEntry."
                    ::= { xylnatmVcCrossConnectEntry 6 }

               xylnatmVcCrossConnectHighVpi OBJECT-TYPE
                    SYNTAX  INTEGER   (0..4095)
                    ACCESS  read-only
                    STATUS  mandatory
                    DESCRIPTION
                     "The value of this object is equal to the VPI
                      value at the ATM interface
                      associated with the VC cross-connect that is
                      identified by atmVcCrossConnectHigh(Slot/Port)Index.
                      The VPI value cannot exceed
                      the number supported by the atmInterfaceMaxVpiBits
                      at the high ATM interface port."
                    ::= { xylnatmVcCrossConnectEntry 7 }

               xylnatmVcCrossConnectHighVci OBJECT-TYPE
                    SYNTAX  INTEGER   (0..65535)
                    ACCESS  read-only
                    STATUS  mandatory
                    DESCRIPTION
                     "The value of this object is equal to the VCI
                      value at the ATM interface
                      associated with the VC cross-connect that is
                      identified by atmVcCrossConnectHigh(Slot/Port)Index.
                      The VCI value cannot exceed
                      the number supported by the atmInterfaceMaxVciBits
                      at the high ATM interface port."
                    ::= { xylnatmVcCrossConnectEntry 8 }

            xylnatmVcCrossConnectConnectionId OBJECT-TYPE
                     SYNTAX	INTEGER {
                                multicastParent(1),
                                multicastChild(2),
								nonMulticastParent(3),
                                unknown(4)
                                   }
                    ACCESS	read-only
                    STATUS	mandatory
                    DESCRIPTION
                         "The status of this object indicates whether
                         the said Vc Cross Connection is the parent or
                         a child. If the connection status is unknown, then
                         the value of this object is unknown. Only deletion
                         of the parent is possible when all the child 
                         connections have been disconnected. To delete all
                         all parent and child connections, use the VCL table
                         to delete the low VCL."
                    ::= {xylnatmVcCrossConnectEntry 9 }

			xylnatmVcCrossConnectLowRxTrafficDescrIndex OBJECT-TYPE
					SYNTAX INTEGER
					ACCESS read-write
					STATUS mandatory
					DESCRIPTION
						"The receive traffic descriptor index. The reason why
						 we duplicate this index is to allow the user to change
						 the traffic descriptor without deleting the connection
						 AND without any changes to the RFC1695.mib. RFC1695
						 describes the traffic descriptor indices only the 
						 vcl/vpl tables. Hence if the user wishes to change 
						 the TD after creating the cross-connection, then the 
						 user has to 
						 delete the cross connection to ensire that the receive
						 direction of the low end of the cross connect is equal
						 to the transmit direction of the other VCL at the high
						 end of the cross connect.
						 10/18/96. Since we dont want to create Vcl without
						 cross connecting them, NMS will now call this table
						 which would allow the creation/deletion and 
						 modification of Cross Connect Entries. "
					::= {xylnatmVcCrossConnectEntry 10}

			xylnatmVcCrossConnectLowTxTrafficDescrIndex OBJECT-TYPE
					SYNTAX INTEGER
					ACCESS read-write
					STATUS mandatory
					DESCRIPTION
						"The transmit traffic descriptor index. The reason why
						 we duplicate this index is to allow the user to change
						 the traffic descriptor without deleting the connection
						 AND without any changes to the RFC1695.mib. RFC1695
						 describes the traffic descriptor indices only the 
						 vcl/vpl tables. Hence if the user wishes to change 
						 the TD after creating the cross-connection, then the 
						 user has to 
						 delete the cross connection to ensire that the receive
						 direction of the low end of the cross connect is equal
						 to the transmit direction of the other VCL at the high
						 end of the cross connect.
						 10/18/96. Since we dont want to create Vcl without
						 cross connecting them, NMS will now call this table
						 which would allow the creation/deletion and 
						 modification of Cross Connect Entries. "
					::= {xylnatmVcCrossConnectEntry 11}

			xylnatmVcCrossConnectMCastEnable OBJECT-TYPE
					SYNTAX INTEGER {
										enabled(1),
										disabled(2)	
									}
					ACCESS read-write
					STATUS mandatory
					DESCRIPTION
						"Enable/disable multicast as per the ui"
					::= {xylnatmVcCrossConnectEntry 12}


               xylnatmVcCrossConnectL2HLastChange OBJECT-TYPE
                    SYNTAX  DisplayString
                    ACCESS  read-only
                    STATUS  mandatory
                    DESCRIPTION
                     "The value of MIB II's sysUpTime object
                      at the time this VC cross-connect entered
                      its current operational state in low to high
                      direction.  If the current state was
                      entered prior to the last re-initialization of the
                      agent, then this object contains a zero value."
                    ::= { xylnatmVcCrossConnectEntry 13 }

               xylnatmVcCrossConnectH2LLastChange OBJECT-TYPE
                    SYNTAX  DisplayString
                    ACCESS  read-only
                    STATUS  mandatory
                    DESCRIPTION
                     "The value of MIB II's sysUpTime object
                      at the time this VC cross-connect entered
                      its current operational state in high to low
                      direction.  If the current state was
                      entered prior to the last re-initialization of the
                      agent, then this object contains a zero value."
                    ::= { xylnatmVcCrossConnectEntry 14 }

               xylnatmVcCrossConnectL2HOperStatus OBJECT-TYPE
                    SYNTAX  INTEGER {
										unknown(1),
										end2endup (2),
										end2endDown(3),
										localUpEndToEndUnknown(4),
										localDown(5)
                            }
                    ACCESS  read-only
                    STATUS  mandatory
                    DESCRIPTION
                     "The value of this object identifies the current
                      operational status of the VC cross-connect
                      in one direction; (i.e., from the low to
                      high direction).  The up and down states indicate
                      that this ATM VC cross-connect from low
                      to high direction is operational or not
                      operational respectively.  The unknown state
                      indicates that the state of it cannot be
                      determined."
                    ::= { xylnatmVcCrossConnectEntry 15 }


               xylnatmVcCrossConnectH2LOperStatus OBJECT-TYPE
                    SYNTAX  INTEGER {
										unknown(1),
										end2endup (2),
										end2endDown(3),
										localUpEndToEndUnknown(4),
										localDown(5)
                            }
                    ACCESS  read-only
                    STATUS  mandatory
                    DESCRIPTION
                     "The value of this object identifies the current
                      operational status of the VC cross-connect
                      in one direction; (i.e., from the high to
                      low direction).  The up and down states indicate
                      that this ATM VC cross-connect from high
                      to low direction is operational or not
                      operational respectively.  The unknown state
                      indicates that the state of it cannot be
                      determined."
                    ::= { xylnatmVcCrossConnectEntry 16 }


               xylnatmVcCrossConnectVcType          OBJECT-TYPE
                    SYNTAX       INTEGER {
											pvc (1),
											svc (2),
											softPvc (3),
											control (4)
                                        }
                    ACCESS   read-only
                    STATUS       mandatory
                    DESCRIPTION
                     "The type of VC...Permanent/Switched/ Soft/control"
                          ::= {xylnatmVcCrossConnectEntry 17}

               xylnatmVcCrossConnectPvcIdentifier          OBJECT-TYPE
                    SYNTAX       INTEGER 
                    ACCESS   read-write
                    STATUS       mandatory
                    DESCRIPTION
                     "This is required by NMS to identify PVC's across networks"
                          ::= {xylnatmVcCrossConnectEntry 18}

               xylnatmVcCrossConnectRowStatus          OBJECT-TYPE
                    SYNTAX       INTEGER {
                                        create (1),
                                        modify (2),
                                        delete (3),
                                        active (4),
                                        notActive (5)
                                        }
                    ACCESS   read-write
                    STATUS       mandatory
                    DESCRIPTION
                     "This object is used to create, delete or
                      modify a row in this table.  To create
                      a new CrossConnect, this object is initially set
                      to 'createAndWait' or 'createAndGo'.
                      This object must not be set to 'active'
                      unless the following columnar objects exist
                      in this row:
                      xylnatmVcCrossConnectLowRxTrafficDescrIndex,
                      xylnatmVcCrossConnectLowTxTrafficDescrIndex.
                      Xylan implements createAndWait along with create&Go
                      as create. Create is basically a superset.
                      In addition, if the local VCL end-point
                      is also the VCC end-point"
                          ::= {xylnatmVcCrossConnectEntry 19}

             xylnatmVplModTable    OBJECT-TYPE
				SYNTAX		SEQUENCE OF XylnatmVplModEntry
				ACCESS		not-accessible
				STATUS		mandatory
				DESCRIPTION
					"This table contains xylan implementation specific
					 objects"
                    ::= { xylnatmVplModGroup 1 }

               xylnatmVplModEntry    OBJECT-TYPE
				SYNTAX		XylnatmVplModEntry
				ACCESS		not-accessible
				STATUS		mandatory
				DESCRIPTION
					"List of xylan specific objects"
				INDEX	 {xylnatmVplModSlotIndex,
						  xylnatmVplModPortIndex,
						  xylnatmVplModVplVpi }
                    ::= { xylnatmVplModTable  1}

				XylnatmVplModEntry		::=	SEQUENCE {
					xylnatmVplModSlotIndex		INTEGER,
					xylnatmVplModPortIndex		INTEGER,
					xylnatmVplModVplVpi			INTEGER,
					xylnatmVplModDestSlotIndex     INTEGER,
					xylnatmVplModDestPortIndex     INTEGER,
					xylnatmVplModDestVplVpi        INTEGER,
					xylnatmVplModDestStatus        INTEGER
                       }
				
               xylnatmVplModSlotIndex    OBJECT-TYPE
					SYNTAX		INTEGER
					ACCESS		read-only
					STATUS		mandatory
					DESCRIPTION
						"Slot Instance"
                    ::= { xylnatmVplModEntry 1}

               xylnatmVplModPortIndex    OBJECT-TYPE
					SYNTAX		INTEGER
					ACCESS		read-only
					STATUS		mandatory
					DESCRIPTION
						"Port Instance"
                    ::= { xylnatmVplModEntry 2}

               xylnatmVplModVplVpi    OBJECT-TYPE
					SYNTAX		INTEGER
					ACCESS		read-only
					STATUS		mandatory
					DESCRIPTION
						"Vpi instance"
                   ::= { xylnatmVplModEntry 3}

               xylnatmVplModDestSlotIndex    OBJECT-TYPE
					SYNTAX		INTEGER
					ACCESS		read-write
					STATUS		mandatory
					DESCRIPTION
						"Slot Instance"
                    ::= { xylnatmVplModEntry 4}

               xylnatmVplModDestPortIndex    OBJECT-TYPE
					SYNTAX		INTEGER
					ACCESS		read-write
					STATUS		mandatory
					DESCRIPTION
						"Port Instance"
                    ::= { xylnatmVplModEntry 5}

               xylnatmVplModDestVplVpi    OBJECT-TYPE
					SYNTAX		INTEGER
					ACCESS		read-write
					STATUS		mandatory
					DESCRIPTION
						"Vpi instance"
                   ::= { xylnatmVplModEntry 6}

				xylnatmVplModDestStatus   OBJECT-TYPE
					SYNTAX		INTEGER {
											create(1),
											modify(2),
											delete(3),
											active(4)
										}
					ACCESS		read-write
					STATUS		mandatory
					DESCRIPTION
						"To be in sync with the ui we allow modification"
					::= { xylnatmVplModEntry 7 }


             xylnatmVclModTable    OBJECT-TYPE
				SYNTAX		SEQUENCE OF XylnatmVclModEntry
				ACCESS		not-accessible
				STATUS		mandatory
				DESCRIPTION
					"This table contains xylan implementation specific
					 objects"
                    ::= { xylnatmVclModGroup 1 }

               xylnatmVclModEntry    OBJECT-TYPE
				SYNTAX		XylnatmVclModEntry
				ACCESS		not-accessible
				STATUS		mandatory
				DESCRIPTION
					"List of xylan specific objects"
				INDEX	 {xylnatmVclModSlotIndex,
						  xylnatmVclModPortIndex,
						  xylnatmVclModVclVpi,
						  xylnatmVclModVclVci }
                    ::= { xylnatmVclModTable  1}

				XylnatmVclModEntry		::=	SEQUENCE {
					xylnatmVclModSlotIndex		INTEGER,
					xylnatmVclModPortIndex		INTEGER,
					xylnatmVclModVclVpi			INTEGER,
					xylnatmVclModVclVci			INTEGER,
					xylnatmVclModDestSlotIndex     INTEGER,
					xylnatmVclModDestPortIndex     INTEGER,
					xylnatmVclModDestVclVpi        INTEGER,
					xylnatmVclModDestVclVci        INTEGER,
					xylnatmVclModDestStatus		   INTEGER
                       }
				
               xylnatmVclModSlotIndex    OBJECT-TYPE
					SYNTAX		INTEGER
					ACCESS		read-only
					STATUS		mandatory
					DESCRIPTION
						"Slot Instance"
                    ::= { xylnatmVclModEntry 1}

               xylnatmVclModPortIndex    OBJECT-TYPE
					SYNTAX		INTEGER
					ACCESS		read-only
					STATUS		mandatory
					DESCRIPTION
						"Port Instance"
                    ::= { xylnatmVclModEntry 2}

               xylnatmVclModVclVpi    OBJECT-TYPE
					SYNTAX		INTEGER
					ACCESS		read-only
					STATUS		mandatory
					DESCRIPTION
						"Vpi instance"
                   ::= { xylnatmVclModEntry 3}

               xylnatmVclModVclVci    OBJECT-TYPE
					SYNTAX		INTEGER
					ACCESS		read-only
					STATUS		mandatory
					DESCRIPTION
						"Vci instance"
                   ::= { xylnatmVclModEntry 4}
	
               xylnatmVclModDestSlotIndex    OBJECT-TYPE
					SYNTAX		INTEGER
					ACCESS		read-write
					STATUS		mandatory
					DESCRIPTION
						"Slot Instance"
                    ::= { xylnatmVclModEntry 5}

               xylnatmVclModDestPortIndex    OBJECT-TYPE
					SYNTAX		INTEGER
					ACCESS		read-write
					STATUS		mandatory
					DESCRIPTION
						"Port Instance"
                    ::= { xylnatmVclModEntry 6}

               xylnatmVclModDestVclVpi    OBJECT-TYPE
					SYNTAX		INTEGER
					ACCESS		read-write
					STATUS		mandatory
					DESCRIPTION
						"Vpi instance"
                   ::= { xylnatmVclModEntry 7}

               xylnatmVclModDestVclVci    OBJECT-TYPE
					SYNTAX		INTEGER
					ACCESS		read-write
					STATUS		mandatory
					DESCRIPTION
						"Vci instance"
                   ::= { xylnatmVclModEntry 8}

               xylnatmVclModDestStatus   OBJECT-TYPE
                    SYNTAX      INTEGER {
                                            create(1),
                                            modify(2),
                                            delete(3),
                                            active(4)
                                        }
                    ACCESS      read-write
                    STATUS      mandatory
                    DESCRIPTION
                        "To be in sync with the ui we allow modification"
                    ::= { xylnatmVclModEntry 9 }
 
               -- The Clocking Service Configuration Group

               xylnatmClockingxCtrlTable   OBJECT-TYPE
                    SYNTAX   SEQUENCE OF XylnatmClockingxCtrlEntry 
                    ACCESS   not-accessible
                    STATUS   mandatory
                    DESCRIPTION
                        "A table of Clocking configuration and control information." 
                    ::= { xylnatmClockingxCtrlGroup 1 }

               xylnatmClockingxCtrlEntry   OBJECT-TYPE
                    SYNTAX   XylnatmClockingxCtrlEntry
                    ACCESS   not-accessible
                    STATUS   mandatory
                    DESCRIPTION
            	        "An entry in the Clocking Configuration/control table, 
                         containing information about Cell Switching Module
                         (CSM) clocking." 
                    INDEX   { xylnatmClockingxCtrlBusLine, 
				xylnatmClockingxCtrlSrcLevel }
                    ::= { xylnatmClockingxCtrlTable 1 }

                        XylnatmClockingxCtrlEntry ::=
                             SEQUENCE {
                                xylnatmClockingxCtrlBusLine   INTEGER,
             		        xylnatmClockingxCtrlSrcLevel  INTEGER,
	                        xylnatmClockingxSrcOperState  INTEGER,
	                        xylnatmClockingxSrcType	      INTEGER,
                                xylnatmClockingxCtrlSlot      INTEGER,
                                xylnatmClockingxCtrlPort      INTEGER
                           }	

                    xylnatmClockingxCtrlBusLine OBJECT-TYPE
                         SYNTAX   INTEGER {
                            eightKhz(1),
                            nineteenMhz(2)
                         }
                         ACCESS   read-only
                         STATUS   mandatory
                         DESCRIPTION
                             "The Bus Signal function used for clocking CSM modules.

                              This is used as a unique
                              ID to identify a clocking line on the bus."
                         ::= { xylnatmClockingxCtrlEntry 1 }

	            xylnatmClockingxCtrlSrcLevel OBJECT-TYPE
                         SYNTAX   INTEGER {
                            primary(1),
                            secondary(2),
                            tertiary(3)
                         }
                         ACCESS   read-only
                         STATUS   mandatory
                         DESCRIPTION
                             "This object identifies which source entry type
                              for this row in the table.

                              Primary is the preffered source, if the primary
                              source clock is not available, then the secondary
                              source (if configured) will be used to drive the bus line.
                              If the primary and secondary are both configured
                              but not available, then the tertiary (if configured)
                              source will be used.

                              If no clock sources are available for this bus line,
                              then all port configured to use the bus line for
                              their local (transmit) clocking, then those
                              ports will switch to their local on-board oscillator."
                         ::= { xylnatmClockingxCtrlEntry 2 }

           	    xylnatmClockingxSrcOperState OBJECT-TYPE
                         SYNTAX   INTEGER {
                            inactive(1),
                            active(2),
                            standby(3)
                         }
                         ACCESS   read-only
                         STATUS   mandatory
                         DESCRIPTION
                             "This object identifies the state of the
                              clock source.

                              inactive(1) indicates the source is not available
                              for use.

                              active(2) indicates the source is currently
                              being used to drive the bus.

                              standby(3) indicates the source is currently
                              availble for use, but another source is
                              currently being used."
                         ::= { xylnatmClockingxCtrlEntry 3 }

 	            xylnatmClockingxSrcType OBJECT-TYPE
                         SYNTAX   INTEGER {
                            notConfigured(1),
                            receiveDataDerived(2),
                            onboardOscillator(3)
                         }
                         ACCESS   read-write
                         STATUS   mandatory
                         DESCRIPTION
                             "This object controls the type of clock used
                              as the source for the bus line.

                              If 'notConfigured', then this source isn't
                              configured.

                              If 'receiveDataDerived' then the source of
                              the clock comes from the specified port's
                              receive data (e.g. calculated using a Phase
                              Lock loop off the receive data line).

                              If 'onboardOscillator' then the source of
                              the clock comes from the on-board oscillator
                              associated with this port.   Currently (as of
                              release 3.2) this is only valid with 19.44 Mhz
                              clocking, and not valid for 8 Khz clocking."

                         ::= { xylnatmClockingxCtrlEntry 4 }

                    xylnatmClockingxCtrlSlot OBJECT-TYPE
                         SYNTAX   INTEGER (0..9)
                         ACCESS   read-write
                         STATUS   mandatory
                         DESCRIPTION
                             "This object is used to configure the slot
                              of the port used to drive the bus.

                              This object will return 0 if not configured.

                              For setting this object only a non-zero value
                              is allowed and it must be a valid CSM slot."
                    ::= { xylnatmClockingxCtrlEntry 5 }

	            xylnatmClockingxCtrlPort OBJECT-TYPE
                         SYNTAX   INTEGER (0..64)
                         ACCESS   read-write
                         STATUS   mandatory
                         DESCRIPTION
                             "This object is used to configure the port number
                              used to drive the bus.

                              This object will return 0 if not configured.

                              For setting this object only a non-zero value
                              is allowed and it must be a valid CSM port that
                              can drive the bus at the proper 8 Khz or 19.44 Mhz
                              speed."
                    ::= { xylnatmClockingxCtrlEntry 6 }

               -- The clocking switch time (a global object for the 
               -- whole clocking system)
               xylnatmClockingxGlobalCST  OBJECT-TYPE
	                 SYNTAX  INTEGER (1..10000)
                         ACCESS   read-write
		         STATUS   mandatory
                         DESCRIPTION	
	                     "This object is used to specify the time period
                              (in seconds) that the primary clock source
                              should be up before the switching software
                              resumes its role in driving the bus line.
                              If the clock source goes down within this
                              time period, the secondary source continues
                              to drive the bus line.   This prevents the
                              software from doing the switching too often when
                              the clock source isn't stable."

                 ::= { xylnatmClockingxCtrlGroup 2 }

          -- The Traffic Shaper (for outgoing traffic)  Configuration Group	

                xylnatmTrafficShaperConfTable   OBJECT-TYPE
                    SYNTAX   SEQUENCE OF XylnatmTrafficShaperConfEntry 
                    ACCESS   not-accessible
                    STATUS   mandatory
                    DESCRIPTION
                        "A table of Traffic Shapers' configuration information.

                         Currently, traffic shaping function is available
                         on module types CSM-AB-OC3 and CSM-AB-DS3/E3 only."

                    ::= { xylnatmTrafficShaperConfGroup 1 }

               xylnatmTrafficShaperConfEntry   OBJECT-TYPE
                    SYNTAX   XylnatmTrafficShaperConfEntry
                    ACCESS   not-accessible
                    STATUS   mandatory
                    DESCRIPTION
            	        "An entry in the Traffic Shaper Configuration table 
                         containing parameters of the traffic shapers of
                         cell switching module."

                    INDEX   { xylnatmTrafficShaperConfSlotIndex, 
			      xylnatmTrafficShaperConfPortIndex,
                              xylnatmTrafficShaperConfTsNumIndex }
                    ::= { xylnatmTrafficShaperConfTable 1 }

                        XylnatmTrafficShaperConfEntry ::=
                             SEQUENCE {
                                xylnatmTrafficShaperConfSlotIndex   INTEGER,
             		        xylnatmTrafficShaperConfPortIndex   INTEGER,
                                xylnatmTrafficShaperConfTsNumIndex  INTEGER,
                                xylnatmTrafficShaperConfCDV         INTEGER,
                                xylnatmTrafficShaperConfPCR         INTEGER,
                                xylnatmTrafficShaperConfSCR         INTEGER,
                                xylnatmTrafficShaperConfMBS         INTEGER
                           }	

                    xylnatmTrafficShaperConfSlotIndex OBJECT-TYPE
                         SYNTAX   INTEGER (1..9)
                         ACCESS   read-only
                         STATUS   mandatory
                         DESCRIPTION
                             "The slot on which the traffic shaping module
                              resides."

                         ::= { xylnatmTrafficShaperConfEntry 1 }

	            xylnatmTrafficShaperConfPortIndex OBJECT-TYPE
                         SYNTAX   INTEGER (1..64)
                         ACCESS   read-only
                         STATUS   mandatory
                         DESCRIPTION
                             "The port on which traffic shaping circuitry
                              resides.

                              A CSM-AB module can have either one or two
                              traffic shaping ports.   If the module has one 
                              traffic shaping port, then the traffic shaping
                              circuitry is always installed on the first port
                              of the module."

                         ::= { xylnatmTrafficShaperConfEntry 2 }

           	    xylnatmTrafficShaperConfTsNumIndex OBJECT-TYPE
                         SYNTAX   INTEGER (1..8)
                         ACCESS   read-only
                         STATUS   mandatory
                         DESCRIPTION
                             "This object identifies the traffic shaper
                              number on the port.

                              On each port, there are eight traffic
                              shapers whose bandwidth are allocated based
                              on configurabled parameters Cell Delay 
                              Variation (CDV), Peak Cell Rate (PCR),
                              Sustainable Cell Rate (SCR) and Maximum
                              Brust Size (MBS)."
                              
                         ::= { xylnatmTrafficShaperConfEntry 3 }

                    xylnatmTrafficShaperConfCDV OBJECT-TYPE
                         SYNTAX   INTEGER (7..1000)
                         ACCESS   read-write
                         STATUS   mandatory
                         DESCRIPTION
                             "This object is used to specify the 
                              Cell Delay Variation of the outgoing
                              cell stream of a shaper.    

                              CDV is one of the parameters configured 
                              to alter the characteristics of the 
                              cell streams to acquire a desired
                              QOS objective.   It is the variation 
                              in the delay time, induced by buffering
                              cell scheduling, experienced by a cell
                              at network entry and exit points.

                              CDV must be between 7 and 1000 uSec."

                    ::= { xylnatmTrafficShaperConfEntry 4 }

	            xylnatmTrafficShaperConfPCR OBJECT-TYPE
                         SYNTAX   INTEGER 
                         ACCESS   read-write
                         STATUS   mandatory
                         DESCRIPTION
                             "This object is used to configure the
                              Peak Cell Rate of a shaper.

                              PCR is one of the parameters set to
                              alter the characteristics of the 
                              cell streams to acquire a desired
                              QOS objective.   It is the maximum
                              instantaneous cell rate at which the
                              cell streams are transmited.

                              PCR must be greater than 0 and not
                              exceeds the maximum bandwidth of
                              the physical interface.  The bandwidth
                              of the physical interface is devided
                              up to 8 shapers, by default, shaper 8
                              has the highest bandwidth.   PCR value
                              must not exceed the remaining bandwidth
                              of the interface."

                    ::= { xylnatmTrafficShaperConfEntry 5 }

	            xylnatmTrafficShaperConfSCR OBJECT-TYPE
                         SYNTAX   INTEGER 
                         ACCESS   read-write
                         STATUS   mandatory
                         DESCRIPTION
                             "This object is used to configure the
                              Sustainable Cell Rate of a shaper.

                              SCR is the average conforming cell rate
                              an ATM connection measured over a time
                              interval.  This measurement allows the 
                              network to allocate sufficient resources
                              that are less than those based on PCR
                              and still ensure the achievement of the
                              desired QOS.

                              SCR could be unspecified, value set to 0.
                              If specified, SCR value must be less than
                              the PCR value."

                    ::= { xylnatmTrafficShaperConfEntry 6 }

	            xylnatmTrafficShaperConfMBS OBJECT-TYPE
                         SYNTAX   INTEGER 
                         ACCESS   read-write
                         STATUS   mandatory
                         DESCRIPTION
                             "This object is used to configure the
                              Maximum Brust Size of the outgoing
                              cell streams of a shaper.

                              MBS is one of the parameters set to
                              alter the characteristics of the 
                              cell streams to acquire a desired
                              QOS objective.   It is the maximum
                              number of back to back cells that can
                              be sent at the peak cell rate.
                              
                              MBS could be unspecified, value set to 0."
        
                    ::= { xylnatmTrafficShaperConfEntry 7 }

                xylnatmTrafficShaperMemTable   OBJECT-TYPE
                    SYNTAX   SEQUENCE OF XylnatmTrafficShaperMemEntry 
                    ACCESS   not-accessible
                    STATUS   mandatory
                    DESCRIPTION
                        "A table of Traffic Shapers' VPI/VCI Membership information.

                         Currently, traffic shaping function is available
                         on module types CSM-AB-OC3 and CSM-AB-DS3/E3 only.

                         To have the outgoing cell streams of a connection
                         shaped to a desired characteristic of a
                         shaper, its VPI/VCI needs to be registered to 
                         one of the traffic shapers (1..7) of the port.
                         Shaper number eight is designated as the
                         default shaper where cell streams of
                         non-specified VPI/VCI's are routed to.  Therefore,
                         VPI/VCI is not registrable to shaper eight."

                    ::= { xylnatmTrafficShaperMemGroup 1 }

               xylnatmTrafficShaperMemEntry   OBJECT-TYPE
                    SYNTAX   XylnatmTrafficShaperMemEntry
                    ACCESS   not-accessible
                    STATUS   mandatory
                    DESCRIPTION
            	        "An entry in the Traffic Shaper Membership table 
                         containing a VPI/VCI number mapping to a traffic shaper
                         number."

                    INDEX   { xylnatmTrafficShaperMemSlotIndex, 
			      xylnatmTrafficShaperMemPortIndex,
                              xylnatmTrafficShaperMemTsNumIndex,
                              xylnatmTrafficShaperMemVpiNumIndex, 
                              xylnatmTrafficShaperMemVciNumIndex }
                    ::= { xylnatmTrafficShaperMemTable 1 }

                        XylnatmTrafficShaperMemEntry ::=
                             SEQUENCE {
                                xylnatmTrafficShaperMemSlotIndex   INTEGER,
             		        xylnatmTrafficShaperMemPortIndex   INTEGER,
                                xylnatmTrafficShaperMemTsNumIndex  INTEGER,
                                xylnatmTrafficShaperMemVpiNumIndex INTEGER,
                                xylnatmTrafficShaperMemVciNumIndex INTEGER,
                                xylnatmTrafficShaperMemVpiOper     INTEGER
                           }

                    xylnatmTrafficShaperMemSlotIndex OBJECT-TYPE
                         SYNTAX   INTEGER (1..9)
                         ACCESS   read-only
                         STATUS   mandatory
                         DESCRIPTION
                             "The slot on which the traffic shaping module
                              resides."

                         ::= { xylnatmTrafficShaperMemEntry 1 }

	            xylnatmTrafficShaperMemPortIndex OBJECT-TYPE
                         SYNTAX   INTEGER (1..64)
                         ACCESS   read-only
                         STATUS   mandatory
                         DESCRIPTION
                             "The port on which traffic shaping circuitry
                              resides.

                              A CSM-AB module can have either one or two
                              traffic shaping ports.   If the module has one 
                              traffic shaping port, then the traffic shaping
                              circuitry is always installed on the first port
                              of the module."

                         ::= { xylnatmTrafficShaperMemEntry 2 }

           	    xylnatmTrafficShaperMemTsNumIndex OBJECT-TYPE
                         SYNTAX   INTEGER (1..7)
                         ACCESS   read-only
                         STATUS   mandatory
                         DESCRIPTION
                             "This object identifies the traffic shaper
                              number on the port.

                              Each port provides mapping of up to 512
                              VPI/VCI to the eight shapers.  Non-specified
                              VPI/VCI is logically mapped to the default 
                              shaper (shaper 8).  Therefore, VPI/VCI 
                              is not registrable to shaper 8."

                         ::= { xylnatmTrafficShaperMemEntry 3 }

 	            xylnatmTrafficShaperMemVpiNumIndex OBJECT-TYPE
                         SYNTAX   INTEGER 
                         ACCESS   read-write
                         STATUS   mandatory
                         DESCRIPTION
                             "This object is used to register a VPI to 
                              a traffic shaper.  The outgoing cell
                              streams with this VPI is shaped by the
                              traffic shaper it registers to.
                              The valid range is 1-[2^(max_vpi_bits of slot/port) -1]."
                              
                         ::= { xylnatmTrafficShaperMemEntry 4 }

                    xylnatmTrafficShaperMemVciNumIndex OBJECT-TYPE
                         SYNTAX   INTEGER 
                         ACCESS   read-write
                         STATUS   mandatory
                         DESCRIPTION
                             "This object is used to register a VCI to 
                              a traffic shaper.  The outgoing cell
                              streams with this VCI is shaped by the
                              traffic shaper it registers to.
                              The valid range is 1-[2^(9-max_vpi_bits of slot port) -1]."
                    
                         ::= { xylnatmTrafficShaperMemEntry 5 }

 	            xylnatmTrafficShaperMemVpiOper OBJECT-TYPE
                         SYNTAX   INTEGER {
                            none(1),
                            add(2),
                            rem(3)
                         }
                         ACCESS   read-write
                         STATUS   mandatory
                         DESCRIPTION
                             "This object is used to register or 
                              de-register a VPI/VCI to or out of 
                              a traffic shaper.

                              none(1) when VPI/VCI is not registered/
                              de-register to/from the shaper.  No
                              operation.

                              add(2) registers the VPI/VCI to the shaper.
                              Its outgoing cell stream is shaped
                              based on the characteristics of the shaper.

                              rem(3) de-registers the VPI/VCI out of 
                              the shaper.

                              When a VPI/VCI is not register to one
                              of the seven shapers (1..7), its outgoing
                              traffic is logically routed to the
                              default shaper (shaper 8) and shaped based
                              on  traffic characteristics of shaper 8."
                              
                         ::= { xylnatmTrafficShaperMemEntry 6 }

               END
