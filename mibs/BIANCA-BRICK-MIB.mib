-- This file is corresponding to Release 6.1.2.100 from 2001/09/26 00:00:00
-- (C)opyright 1991-1999 BinTec Communications AG, All Rights Reserved
-- $Revision: 1.81 $ 

BIANCA-BRICK-MIB DEFINITIONS ::= BEGIN


	IMPORTS
	TRAP-TYPE FROM RFC-1215
	    NetworkAddress, IpAddress, Counter, Gauge, TimeTicks
		FROM RFC1155-SMI
	sysDescr, sysName FROM RFC1213-MIB

	    OBJECT-TYPE
		FROM RFC-1212;

	--  This MIB module uses the extended OBJECT-TYPE macro as
	--  defined in [14];


	--  MIB-II (same prefix as MIB-I)
	org          	OBJECT IDENTIFIER ::= { iso 3 }
	dod          	OBJECT IDENTIFIER ::= { org 6 }
	internet     	OBJECT IDENTIFIER ::= { dod 1 }

	private 	OBJECT IDENTIFIER ::= { internet 4 }
	enterprises 	OBJECT IDENTIFIER ::= { private 1 }
	bintec 		OBJECT IDENTIFIER ::= { enterprises 272 }
	bibo		OBJECT IDENTIFIER ::= { bintec 4 }
	admin		OBJECT IDENTIFIER
	    ::= { bibo 1 }

	-- textual conventions

	DisplayString ::= OCTET STRING
	    -- This data type is used to model textual information taken
	    -- from the NVT ASCII character set.  By convention, objects
	    -- with this syntax are declared as having
	    --
	    --      SIZE (0..255)

	PhysAddress ::= OCTET STRING
	    -- This data type is used to model media addresses.  For many
	    -- types of media, this will be in a binary representation.
	    -- For example, an ethernet address would be represented as
	    -- a string of 6 octets.

	Date ::= INTEGER
	HexValue ::= INTEGER


    -- Admin Group

    -- Some variables for administration of the BIANCA/BRICK

	biboAdmTrapCommunity OBJECT-TYPE
	    SYNTAX  DisplayString (SIZE (0..255))
	    ACCESS  read-write
	    STATUS  mandatory

	    DESCRIPTION
		"Community name for sending traps."
	::= { admin 4 }

	biboAdmSnmpVersion OBJECT-TYPE
	    SYNTAX  INTEGER { version1(1),
                              version1-compat(2),
                              version1p1(3),
                              version1p1-compat(4),
                              version1p1-auto(5)
                            }
	    ACCESS  read-write
	    STATUS  mandatory

	    DESCRIPTION
		"SNMP Version.
		    version1        : SNMP version V1
		    version1_compat : SNMP version V1 compatibility mode
				      without the appending private OID 
				      part (.i). This is for some SNMP managers
				      that cannot handle this extension.
				      In this mode rows with identical
				      index variable content cannot be read
				      correctly.
		    p1 (patch1)     : getnext returns the lexicographical next
                                      OID (ever!)
		    version1p1_auto : use version1p1_compat if possible
		                      use version1p1 if nessesary

		 Usually the OIDs have the format:
		    .1.3.6.x.x   .y.y .i
			    			
		.1.3.6.x.x: is the constant part of the OID of the 
			    variable specified in MIB-source
		.y.y      : is the specific part of the OID to identify 
			    exactly a row.
			    It is the content of all index variables.
		.i        : is a consecutively incremented index number, 
			    to distinguish rows with identical index variables
	       "
	::= { admin 5 }

	biboAdmSnmpPort OBJECT-TYPE
	    SYNTAX  INTEGER
	    ACCESS  read-write
	    STATUS  mandatory

	    DESCRIPTION
		"SNMP listen port."
	::= { admin 6 }

	biboAdmSnmpTrapPort OBJECT-TYPE
	    SYNTAX  INTEGER
	    ACCESS  read-write
	    STATUS  mandatory

	    DESCRIPTION
		"SNMP trap port."
	::= { admin 7 }
 
	biboAdmIpAddr OBJECT-TYPE
	    SYNTAX  IpAddress
	    ACCESS  read-write
	    STATUS  mandatory

	    DESCRIPTION
		"Local IP address. If this object is set, it's value will be
                used as the source address for all IP packets that are sent.
                Otherwise, the IP address used will be retrieved from the
                ipRouteTable, for the interface the IP packet is to be 
                transmitted over."
	::= { admin 8 }
 
	biboAdmTrapBrdCast OBJECT-TYPE
	    SYNTAX  INTEGER { on(1), off(2) }
	    ACCESS  read-write
	    STATUS  mandatory

	    DESCRIPTION
		"Enable/disable trap broadcasting."
	::= { admin 9 }
 
 	biboAdmTrapHostTable OBJECT-TYPE
 	    SYNTAX  SEQUENCE OF BiboAdmTrapHostEntry
 	    ACCESS  not-accessible
 	    STATUS  mandatory
 
 	    DESCRIPTION
 		"The biboAdmTrapHostTable defines where traps are sent
                (i.e., which hosts). If the table is empty traps are 
                broadcasted.
                
                Creating entries: Entries are added by assigning an IP
                address value to the biboAdmTrapHostAddr field.
                
                Deleting entries: Entries can be removed by assigning
                ing the respective biboAdmTrapHostStatus field to 
                'delete'."
 	::= { admin 10 }

        biboAdmTrapHostEntry OBJECT-TYPE
	    SYNTAX  BiboAdmTrapHostEntry
 	    ACCESS  not-accessible
 	    STATUS  mandatory
 	    DESCRIPTION
 		  ""
 	    INDEX   { biboAdmTrapHostAddr }
 	::= { biboAdmTrapHostTable 1 }

 	BiboAdmTrapHostEntry ::= SEQUENCE {
 	    biboAdmTrapHostAddr   IpAddress,
	    biboAdmTrapHostStatus INTEGER
 	}
 
 	biboAdmTrapHostAddr OBJECT-TYPE
 	    SYNTAX  IpAddress
 	    ACCESS  read-write
 	    STATUS  mandatory
 
 	    DESCRIPTION
 		"Ip-Address where traps are sent."
 	::= { biboAdmTrapHostEntry 1 }
 
 	biboAdmTrapHostStatus OBJECT-TYPE
	    SYNTAX  INTEGER { 
		valid(1), 
		delete(2)
	    }
 	    ACCESS  read-write
 	    STATUS  mandatory
 
 	    DESCRIPTION
 		"Status is always valid, and set to delete only to discard
		 the whole entry."
 	::= { biboAdmTrapHostEntry 2 }
 
        biboAdmSyslogMaxEntries OBJECT-TYPE
            SYNTAX  INTEGER
            ACCESS  read-write
            STATUS  mandatory
 
            DESCRIPTION
                "Maximum Number of syslog messages stored in memory."
        ::= { admin 11 }

	biboAdmSyslogTable OBJECT-TYPE
	    SYNTAX  SEQUENCE OF BiboAdmSyslogEntry
	    ACCESS  not-accessible
	    STATUS  mandatory
	    DESCRIPTION
		"The biboAdmSyslogTable keeps track of syslog messages
                received. The size of the table (number of entries), is 
                limited by the value of biboAdmSyslogMaxEntries. The 
                columns specify attributes for each message generated. As
                this information only reports events on the system, all
                fields are read-only.

                Creating entries: Entries can only be created by the
                system and are made each time a syslog message is 
                generated.

                Deleting entries: Entries are removed by the system
                once the size limit (biboAdmSyslogMaxEntries) is reached."
	::= { admin 12 }

	biboAdmSyslogEntry OBJECT-TYPE
	    SYNTAX  BiboAdmSyslogEntry
	    ACCESS  not-accessible
	    STATUS  mandatory
	    DESCRIPTION
		""
	    INDEX { biboAdmSyslogTimeStamp, biboAdmSyslogLevel }
	::= { biboAdmSyslogTable 1 }

	BiboAdmSyslogEntry ::=
	    SEQUENCE {
		biboAdmSyslogTimeStamp			Date,
		biboAdmSyslogLevel			INTEGER,
		biboAdmSyslogMessage			DisplayString,
		biboAdmSyslogSubject			INTEGER
	    }

	biboAdmSyslogTimeStamp OBJECT-TYPE
	    SYNTAX  Date 
	    ACCESS  read-only
	    STATUS  mandatory

	    DESCRIPTION
		"Time message was generated."
	::= { biboAdmSyslogEntry 1 }

	biboAdmSyslogLevel OBJECT-TYPE
	    SYNTAX  INTEGER { 
		emerg(1), 
		alert(2), 
		crit(3), 
		err(4), 
		warning(5), 
		notice(6), 
		info(7), 
		debug(8) 
	    } 
	    ACCESS  read-only
	    STATUS  mandatory

	    DESCRIPTION
		"Level of syslog message."
	::= { biboAdmSyslogEntry 2 }

	biboAdmSyslogMessage OBJECT-TYPE
	    SYNTAX  DisplayString 
	    ACCESS  read-only
	    STATUS  mandatory

	    DESCRIPTION
		"The text of the syslog message."
	::= { biboAdmSyslogEntry 4 }

	biboAdmSyslogSubject OBJECT-TYPE
	    SYNTAX  INTEGER { 
		acct(1), 
		isdn(2), 
		inet(3), 
		x25(4), 
		ipx(5), 
		capi(6), 
		ppp(7), 
		bridge(8),
		config(9),
		snmp(10),
	        x21(11),
	        token(12),
	        ether(13),
	        radius(14),
	        tapi(15),
		ospf(16),
		fr(17),
		modem(18),
		rip(19),
		atm(20),
		pabx(21),
		ipsec(22)
	    } 
	    ACCESS  read-only
	    STATUS  mandatory

	    DESCRIPTION
		"Subject of the syslog message."
	::= { biboAdmSyslogEntry 5 }


 	biboAdmLogHostTable OBJECT-TYPE
 	    SYNTAX  SEQUENCE OF BiboAdmLogHostEntry
 	    ACCESS  not-accessible
 	    STATUS  mandatory
 
 	    DESCRIPTION
 		"The biboAdmLogHostTable lists hosts which are to 
                receive syslog messages. This table also defines which
                types and levels of messages to send.

                Creating entries: Entries are created by setting a IP address
                to biboAdmLogHostAddr.

                Deleting entries: Entries are removed by setting the
                appropriate biboAdmLogHostLevel field to 'delete'."
 	::= { admin 13 }
 
        biboAdmLogHostEntry OBJECT-TYPE
	    SYNTAX  BiboAdmLogHostEntry
 	    ACCESS  not-accessible
 	    STATUS  mandatory
 	    DESCRIPTION
 		  ""
 	    INDEX   { biboAdmLogHostAddr }
 	::= { biboAdmLogHostTable 1 }

 	BiboAdmLogHostEntry ::= SEQUENCE {
 	    biboAdmLogHostAddr 					IpAddress,
	    biboAdmLogHostLevel					INTEGER,
	    biboAdmLogHostFacility				INTEGER,
	    biboAdmLogHostType					INTEGER,
	    biboAdmLogHostTimestamp				INTEGER
 	}
 
 	biboAdmLogHostAddr OBJECT-TYPE
 	    SYNTAX  IpAddress
 	    ACCESS  read-write
 	    STATUS  mandatory
 
 	    DESCRIPTION
 		"Ip-Address where syslog messages are sent. If the
		 facility is set to memory or console, this field is
		 not used."
 	::= { biboAdmLogHostEntry 1 }

	biboAdmLogHostLevel OBJECT-TYPE
	    SYNTAX  INTEGER { 
		emerg(1), 
		alert(2), 
		crit(3), 
		err(4), 
		warning(5), 
		notice(6), 
		info(7), 
		debug(8), 
		delete(9)
	    } 
	    ACCESS  read-write
	    STATUS  mandatory

	    DESCRIPTION
		"Priorities lower or equal this level are sent to loghost.
                 The delete priority is used to discard the whole entry."
	::= { biboAdmLogHostEntry 2 }

	biboAdmLogHostFacility OBJECT-TYPE
	    SYNTAX  INTEGER { 
		local0(1), 
		local1(2), 
		local2(3), 
		local3(4), 
		local4(5), 
		local5(6), 
		local6(7), 
		local7(8)
	    } 
	    ACCESS  read-write
	    STATUS  mandatory

	    DESCRIPTION
		"The facility used for the syslog messages being generated."
	::= { biboAdmLogHostEntry 4 }

	biboAdmLogHostType OBJECT-TYPE
	    SYNTAX  INTEGER {
	        system(1),
                acct(2),
                all(3)
            }
	    ACCESS  read-write
	    STATUS  mandatory
	
	    DESCRIPTION
                "The subject of the messages that are to be generated. system
                 means all subjects except accounting, all means all subjects."
         ::= { biboAdmLogHostEntry 5 }

	biboAdmLogHostTimestamp OBJECT-TYPE
	    SYNTAX  INTEGER {
	       	none(1),
		time(2),
		all(3)
	    }
	    ACCESS  read-write
	    STATUS  mandatory
	
	    DESCRIPTION
                "This object describes the format of the timestamp.
		   none(1)  = no timestamp,
		   time(2)  = only time is printed,
		   all(3)   = date and time is printed."
         ::= { biboAdmLogHostEntry 6 }


--  Configuration 

 	biboAdmConfigTable OBJECT-TYPE
 	    SYNTAX  SEQUENCE OF BiboAdmConfigEntry
 	    ACCESS  not-accessible
 	    STATUS  mandatory
 
 	    DESCRIPTION
 		"The biboAdmConfigTable is used for assigning 
                parameters for managing configuration files.

                Creating entries: Entries are added to this table by 
                assigning a value to the biboAdmConfigCmd object. (i.e., The
                intermediate result of executing, cmd=save, creates an
                entry to this table.).

                Deleting entries: Entries can only be removed by the
                system and is done only after the requested action has
                been performed (i.e. Once the cmd=save action is 
                complete.)."
 	::= { admin 14 }

        biboAdmConfigEntry OBJECT-TYPE
	    SYNTAX  BiboAdmConfigEntry
 	    ACCESS  not-accessible
 	    STATUS  mandatory
 	    DESCRIPTION
 		  ""
 	    INDEX   { biboAdmConfigCmd }
 	::= { biboAdmConfigTable 1 }

 	BiboAdmConfigEntry ::= SEQUENCE {
 	    biboAdmConfigCmd 				INTEGER,
	    biboAdmConfigObject				OBJECT IDENTIFIER,
	    biboAdmConfigPath				DisplayString,
	    biboAdmConfigPathNew			DisplayString,
	    biboAdmConfigHost				IpAddress,
	    biboAdmConfigState				INTEGER,
	    biboAdmConfigFile				DisplayString
 	}

 	biboAdmConfigDirTable OBJECT-TYPE
 	    SYNTAX  SEQUENCE OF BiboAdmConfigDirEntry
 	    ACCESS  not-accessible
 	    STATUS  mandatory
 
 	    DESCRIPTION
 		"Configuration directory table. This table contains
		all available configuration files in flash memory."
 	::= { admin 15 }

        biboAdmConfigDirEntry OBJECT-TYPE
	    SYNTAX  BiboAdmConfigDirEntry
 	    ACCESS  not-accessible
 	    STATUS  mandatory
 	    DESCRIPTION
 		  ""
 	    INDEX   { biboAdmConfigDirName }
 	::= { biboAdmConfigDirTable 1 }

 	BiboAdmConfigDirEntry ::= SEQUENCE {
	    biboAdmConfigDirName			DisplayString,
 	    biboAdmConfigDirCount 			INTEGER,
	    biboAdmConfigDirContent			DisplayString
 	}

        biboAdmConfigCmd OBJECT-TYPE
            SYNTAX  INTEGER  { save(1), load(2), put(3), get(4), state(5),
				delete(6), move(7), copy(8), reboot(9), reorg(10) }
            ACCESS  read-write
            STATUS  mandatory
            DESCRIPTION
                "Command for configuration handling. Possible values are :
	
		save(1)		= save configuration (to FLASH)
		load(2)		= load configuration (from FLASH)
		put(3)		= write configuration (via TFTP)
		get(4)		= read configuration (via TFTP)
		state(5)	= write complete configuration (via TFTP)
                delete(6)	= delete configuration (within FLASH)
		move(7)		= move configuration (within FLASH)
		copy(8)		= copy configuration (within FLASH)
		reboot(9)	= reboot the system
		reorg(10)	= reorganizes the flash"

        ::= { biboAdmConfigEntry 1 }

        biboAdmConfigObject OBJECT-TYPE
            SYNTAX  OBJECT IDENTIFIER
            ACCESS  read-write
            STATUS  mandatory
            DESCRIPTION
                "Table object id (OID) to save/load. If this field is
		set, only this table is saved/loaded. Otherwise all tables
		are saved/loaded."
        ::= { biboAdmConfigEntry 2 }

        biboAdmConfigPath OBJECT-TYPE
            SYNTAX  DisplayString
            ACCESS  read-write
            STATUS  mandatory
            DESCRIPTION
                "NAme of the configuration file in flash memory to save/load."
        ::= { biboAdmConfigEntry 3 }

        biboAdmConfigPathNew OBJECT-TYPE
            SYNTAX  DisplayString
            ACCESS  read-write
            STATUS  mandatory
            DESCRIPTION
                "New name of configuration file in flash memory to move/copy"
        ::= { biboAdmConfigEntry 4 }

        biboAdmConfigHost OBJECT-TYPE
            SYNTAX  IpAddress
            ACCESS  read-write
            STATUS  mandatory
            DESCRIPTION
                "TFTP host's IP address to send/receive the file to/from.
		The configuration is transfered directly from flash
		memory (biboAdmConfigPath) to TFTP-file (biboAdmConfigFile)."
        ::= { biboAdmConfigEntry 5 }

        biboAdmConfigState OBJECT-TYPE
            SYNTAX  INTEGER  { 
		todo(1),	-- The command has not started
	        running(2),	-- The command is executing
	        done(3),	-- The command successfully
				-- completed
	        error(4)	-- The command failed (see
				-- the biboAdmSyslogTable).
	     }
            ACCESS  read-only
            STATUS  mandatory
            DESCRIPTION
                "The state of this command (i.e., biboAdmConfigCmd).

		todo(1)		= The command has not started;
	        running(2)	= The command is executing;
	        done(3)		= The command successfully
				  completed;
	        error(4)	= The command failed (see
				   the biboAdmSyslogTable)."
        ::= { biboAdmConfigEntry 6 }

        biboAdmConfigFile OBJECT-TYPE
            SYNTAX  DisplayString
            ACCESS  read-write
            STATUS  mandatory
            DESCRIPTION
                "TFTP filename to read/write from/to the specified host.
		The configuration file received is stored in flash memory
		specified by biboAdmConfigPath. The actual configuration
		is not changed."
        ::= { biboAdmConfigEntry 7 }

        biboAdmConfigDirName OBJECT-TYPE
            SYNTAX  DisplayString
            ACCESS  read-only
            STATUS  mandatory
            DESCRIPTION
                "Name of the configuration file in flash memory."
        ::= { biboAdmConfigDirEntry 1 }

        biboAdmConfigDirCount OBJECT-TYPE
            SYNTAX  INTEGER
            ACCESS  read-only
            STATUS  mandatory
            DESCRIPTION
                "Number of tables saved in the file."
        ::= { biboAdmConfigDirEntry 2 }

        biboAdmConfigDirContent OBJECT-TYPE
            SYNTAX  DisplayString
            ACCESS  read-only
            STATUS  mandatory
            DESCRIPTION
                "Description of directory's contents (e.g., <all> or a 
                series of table numbers)."
        ::= { biboAdmConfigDirEntry 3 }


-- Board Table

	biboAdmBoardTable OBJECT-TYPE
	    SYNTAX  SEQUENCE OF BiboAdmBoardEntry
	    ACCESS  not-accessible
	    STATUS  mandatory
	    DESCRIPTION
		"The biboAdmBoardTable lists information about the 
                installed communications modules. This table is updated
                after every system boot up.

                Creating entries: Entries are created by the system
                upon detecting the installed hardware.

                Deleting entries: Entries are removed by the system
                as a result of removed hardware."
	::= { admin 17 }

	biboAdmBoardEntry OBJECT-TYPE
	    SYNTAX  BiboAdmBoardEntry
	    ACCESS  not-accessible
	    STATUS  mandatory
	    DESCRIPTION
		""
	    INDEX { biboABrdSlot, biboABrdUnit }
	::= { biboAdmBoardTable 1 }

	BiboAdmBoardEntry ::=
	    SEQUENCE {
		biboABrdSlot				INTEGER,
		biboABrdType				DisplayString,
		biboABrdHWRelease			DisplayString,
		biboABrdFWRelease			DisplayString,
		
		biboABrdPartNo				DisplayString,
		biboABrdConnector                       INTEGER,
		biboABrdUnit				INTEGER,
		biboABrdSerialNo			DisplayString
	    }

	biboABrdSlot OBJECT-TYPE
	    SYNTAX  INTEGER (0..31) 
	    ACCESS  read-only
	    STATUS  mandatory

	    DESCRIPTION
		"The slot, or location of this module."
	::= { biboAdmBoardEntry 1 }

	biboABrdType OBJECT-TYPE
	    SYNTAX  DisplayString 
	    ACCESS  read-only
	    STATUS  mandatory

	    DESCRIPTION
		"The name of this module."
	::= { biboAdmBoardEntry 2 }

	biboABrdHWRelease OBJECT-TYPE
	    SYNTAX  DisplayString 
	    ACCESS  read-only
	    STATUS  mandatory

	    DESCRIPTION
		"The hardware release of this module."
	::= { biboAdmBoardEntry 3 }

	biboABrdFWRelease OBJECT-TYPE
	    SYNTAX  DisplayString 
	    ACCESS  read-only
	    STATUS  mandatory

	    DESCRIPTION
		"The firmware release of this module."
	::= { biboAdmBoardEntry 4 }

	biboABrdPartNo OBJECT-TYPE
	    SYNTAX  DisplayString 
	    ACCESS  read-only
	    STATUS  mandatory

	    DESCRIPTION
		"The part number of this module."
	::= { biboAdmBoardEntry 5 }

	biboABrdConnector OBJECT-TYPE
	    SYNTAX  INTEGER { auto(1), rj45(2), bnc(3), subd15(4),
			      rj45-10mbit-hdup(5), rj45-10mbit-fdup(6), 
			      rj45-100mbit-hdup(7), rj45-100mbit-fdup(8) }
	    ACCESS  read-write
	    STATUS  mandatory

	    DESCRIPTION
		"The type of connector used for this module. For 
                modules with more than one connector this value can be
                changed/switched by setting this object. For example,
                the CM-BNCTP module supports both twisted pair
                (RJ45) and 10Base2 (BNC) connectors. If this object is set
                to 'AUTO' then the BRICK will automatically detect
                which connector type is being used."
	::= { biboAdmBoardEntry 6 }

	biboABrdUnit OBJECT-TYPE
	    SYNTAX  INTEGER (0..15) 
	    ACCESS  read-only
	    STATUS  mandatory

	    DESCRIPTION
		"The logical unit number of this interface."
	::= { biboAdmBoardEntry 7 }

	biboABrdSerialNo OBJECT-TYPE
	    SYNTAX  DisplayString 
	    ACCESS  read-only
	    STATUS  mandatory

	    DESCRIPTION
		"The serial number of this module."
	::= { biboAdmBoardEntry 8 }

-- user defined traps

	biboAdmUsrTrapTable OBJECT-TYPE
	    SYNTAX  SEQUENCE OF BiboAdmUsrTrapEntry
	    ACCESS  not-accessible
	    STATUS  mandatory
	    DESCRIPTION
		"The biboAdmUsrTrapTable lists user-defined objects that
                are used to create traps. These traps are sent locally, but
                can also be sent to remote hosts using the 
                biboAdmTrapHostTable.

                Creating entries: Entries are created by assigning the
                biboATrpObj object a valid object identifier.

                Deleting entries: Entries are removed by setting the
                entry's biboATrpStatus object to 'delete'."
	::= { admin 18 }

	biboAdmUsrTrapEntry OBJECT-TYPE
	    SYNTAX  BiboAdmUsrTrapEntry
	    ACCESS  not-accessible
	    STATUS  mandatory
	    DESCRIPTION
		""
	    INDEX { biboATrpObj }
	::= { biboAdmUsrTrapTable 1 }

	BiboAdmUsrTrapEntry ::=
	    SEQUENCE {
		biboATrpObj		OBJECT IDENTIFIER,
		biboATrpStatus 		INTEGER
	    }

	biboATrpObj OBJECT-TYPE
	    SYNTAX  OBJECT IDENTIFIER
	    ACCESS  read-write
	    STATUS  mandatory

	    DESCRIPTION
		"The object identifier of an object to use. Each time this
                object's value changes, a trap is created and sent. Either a
                single leaf (single variable) or a table (of objects) can be
                specified."
	::= { biboAdmUsrTrapEntry 1 }

	biboATrpStatus OBJECT-TYPE
	    SYNTAX  INTEGER { valid(1), delete(2) }
	    ACCESS  read-write
	    STATUS  mandatory

	    DESCRIPTION
		"The status of this entry. Upon creation of a new entry,
                this object's value is set to 'valid'."
	::= { biboAdmUsrTrapEntry 2 }

	biboAdmDomainName OBJECT-TYPE
	    SYNTAX  DisplayString
	    ACCESS  read-write
	    STATUS  mandatory
	    DESCRIPTION
		"Domain name."
	::= { admin 19 }

	biboAdmNameServer OBJECT-TYPE
	    SYNTAX  IpAddress
	    ACCESS  read-write
	    STATUS  mandatory
	    DESCRIPTION
		"IP address of name server."
	::= { admin 20 }

	biboAdmNameServ2 OBJECT-TYPE
	    SYNTAX  IpAddress
	    ACCESS  read-write
	    STATUS  mandatory
	    DESCRIPTION
		"IP address of second name server."
	::= { admin 21 }

	biboAdmBridgeEnable OBJECT-TYPE
	    SYNTAX  INTEGER { enabled(1), disabled (2) }
	    ACCESS  read-write
	    STATUS  mandatory
	    DESCRIPTION
		"Sets bridging to enable / disable status."
	::= { admin 22 }

	biboAdmCapiTcpPort OBJECT-TYPE
	    SYNTAX  INTEGER
	    ACCESS  read-write
	    STATUS  mandatory
	    DESCRIPTION
		"TCP port for remote CAPI demon."
	::= { admin 23 }

	biboAdmTraceTcpPort OBJECT-TYPE
	    SYNTAX  INTEGER
	    ACCESS  read-write
	    STATUS  mandatory
	    DESCRIPTION
		"TCP port for trace demon."
	::= { admin 24 }

	biboAdmRipUdpPort OBJECT-TYPE
	    SYNTAX  INTEGER 
	    ACCESS  read-write
	    STATUS  mandatory
	    DESCRIPTION
		"UDP port for RIP. Setting this object 
		 to zero disables RIP."
	::= { admin 25 }

        biboAdmSWVersion OBJECT-TYPE
            SYNTAX  DisplayString (SIZE (0..255))
            ACCESS  read-only
            STATUS  mandatory
            DESCRIPTION
                "This is the software release version"
        ::= { admin 26 }
 
	biboAdmTimeServer OBJECT-TYPE
	    SYNTAX  IpAddress
	    ACCESS  read-write
	    STATUS  mandatory
	    DESCRIPTION
		"The IP address of the time server."
	::= { admin 27 }

	biboAdmTimeOffset OBJECT-TYPE
	    SYNTAX  INTEGER
	    ACCESS  read-write
	    STATUS  mandatory
	    DESCRIPTION
		"This is the time offset from GMT in seconds.
		 If the set value is in the range from -24 to 24,
		 it means hours, and is automatically converted
		 to seconds."
	::= { admin 28 }

	biboAdmConsoleSyslog OBJECT-TYPE
	    SYNTAX  INTEGER { enable(1), disable(2) }
	    ACCESS  read-write
	    STATUS  mandatory
	    DESCRIPTION
		"Specifies whether to direct syslog messages to the
                console."
	::= { admin 29 }
 
	biboAdmSyslogTableLevel OBJECT-TYPE
	    SYNTAX  INTEGER { 
		emerg(1), 
		alert(2), 
		crit(3), 
		err(4), 
		warning(5), 
		notice(6), 
		info(7), 
		debug(8) 
	    } 
	    ACCESS  read-write
	    STATUS  mandatory
	    DESCRIPTION
		"Specifies which message levels to post to the
                biboAdmSyslogTable and the console, if applicable."
	::= { admin 30 }

	biboAdmSystemId OBJECT-TYPE
	    SYNTAX  DisplayString
	    ACCESS  read-only
	    STATUS  mandatory
	    DESCRIPTION
		"This object contains the system Identification String."
	::= { admin 31 }

	biboAdmLicInfoTable OBJECT-TYPE
	    SYNTAX  SEQUENCE OF BiboAdmLicInfoEntry
	    ACCESS  not-accessible
	    STATUS  mandatory
	    DESCRIPTION
		"This table contains an entry for each feature, that
		 can be activated by a license. The licenses have to
		 be entered in the biboAdmLicenseTable. This tabl
		 indicates the current state of the different licenses."
	::= { admin 32 }

	biboAdmLicInfoEntry OBJECT-TYPE
	    SYNTAX  BiboAdmLicInfoEntry
	    ACCESS  not-accessible
	    STATUS  mandatory
	    DESCRIPTION
		""
	    INDEX { biboAdmLicInfoType, biboAdmLicInfoStatus }
	::= { biboAdmLicInfoTable 1 }

	BiboAdmLicInfoEntry ::=
	    SEQUENCE {
		biboAdmLicInfoType			INTEGER,
		biboAdmLicInfoStatus			INTEGER,
		biboAdmLicInfoId			DisplayString,
		biboAdmLicInfoSlot			INTEGER,

		biboAdmLicInfoMaxLic			Counter,
		biboAdmLicInfoInUse			Counter,
		biboAdmLicInfoHwSerial			DisplayString,
		biboAdmLicInfoUnit			INTEGER
	    }

	biboAdmLicInfoType OBJECT-TYPE
	    SYNTAX  INTEGER {
		ip(1), capi(2), bridge(3), x25(4), ipx(5), stac(6),
		frame-relay(7), tapi(8), ospf(9), extended-lan(10),
		tunneling(11), taf(12), extended-wan(13), leased-line(14),
		ipsec(33),
		ethernet(128), bri(129), g703(130), pri(131), modem(132)
	    }
	    ACCESS  read-only
	    STATUS  mandatory

	    DESCRIPTION
		"The licenseable feature."
	::= { biboAdmLicInfoEntry 1 }

	biboAdmLicInfoStatus OBJECT-TYPE
	    SYNTAX  INTEGER  {
		builtin(1), valid-license(2), invalid-license(3), no-license(4),
		erase-internal(5)
	    }
	    ACCESS  read-only
	    STATUS  mandatory

	    DESCRIPTION
		"The current state of the license."
	::= { biboAdmLicInfoEntry 2 }

	biboAdmLicInfoId OBJECT-TYPE
	    SYNTAX DisplayString
	    ACCESS  read-only
	    STATUS  mandatory

	    DESCRIPTION
		"The complete serial id string of the special license."
	::= { biboAdmLicInfoEntry 3 }

	biboAdmLicInfoSlot OBJECT-TYPE
	    SYNTAX INTEGER (0..255)
	    ACCESS  read-only
	    STATUS  mandatory

	    DESCRIPTION
		"In case of a hardware license corresponding to a dedicated
		 module serial number, it is the slot number of the module."
	::= { biboAdmLicInfoEntry 4 }

	biboAdmLicInfoMaxLic OBJECT-TYPE
	    SYNTAX Counter
	    ACCESS  read-only
	    STATUS  mandatory

	    DESCRIPTION
		"The max number of allowed chunks."
	::= { biboAdmLicInfoEntry 5 }

	biboAdmLicInfoInUse OBJECT-TYPE
	    SYNTAX Counter
	    ACCESS  read-only
	    STATUS  mandatory

	    DESCRIPTION
		"The current number of chunks in use."
	::= { biboAdmLicInfoEntry 6 }

	biboAdmLicInfoHwSerial OBJECT-TYPE
	    SYNTAX DisplayString
	    ACCESS  read-only
	    STATUS  mandatory

	    DESCRIPTION
		"The complete serial id string of the special license."
	::= { biboAdmLicInfoEntry 7 }

	biboAdmLicInfoUnit OBJECT-TYPE
	    SYNTAX INTEGER (0..255)
	    ACCESS  read-only
	    STATUS  mandatory

	    DESCRIPTION
		"In case of a hardware license corresponding to a dedicated
		 module serial number, it is the unit number of the module."
	::= { biboAdmLicInfoEntry 8 }




	biboAdmBootpRelayServer OBJECT-TYPE
	    SYNTAX  IpAddress
	    ACCESS  read-write
	    STATUS  mandatory
	    DESCRIPTION
		"This object contains the destination IP address to 
		 which BOOTP/DHCP request are forwarded by the 
		 BIANCA/BRICK BOOTP relay agent.

                 If this entry is empty no BOOTP forwarding is done."
	::= { admin 33 }

	biboAdmRadiusServer OBJECT-TYPE
	    SYNTAX  IpAddress
	    ACCESS  read-write
	    STATUS  mandatory
	    DESCRIPTION
		"This object contains the IP address of the RADIUS
		 server (remote dial in user service). If set to 0.0.0.0
		 RADIUS services are generally disabled (default).
		 The corresponding Radius password is configured in the
		 biboAdmRadiusSecret variable."
	::= { admin 34 }

	biboAdmLocalPPPIdent OBJECT-TYPE
	    SYNTAX  DisplayString
	    ACCESS  read-write
	    STATUS  mandatory
	    DESCRIPTION
		"This is the local ID string used for PPP authentication
		 (PAP/CHAP). In pre4.3 versions the sysName has been used
		 as the local ID string. This is, for increased ease and
		 transparency of system configuration, no longer true."
	::= { admin 35 }

	biboAdmHttpTcpPort OBJECT-TYPE
	    SYNTAX  INTEGER
	    ACCESS  read-write
	    STATUS  mandatory
	    DESCRIPTION
		"TCP port for the HTTP server. Default port is 80, 0 disables
		 the HTTP server."
	::= { admin 36 }

	biboAdmTapiTcpPort OBJECT-TYPE
	    SYNTAX  INTEGER
	    ACCESS  read-write
	    STATUS  mandatory
	    DESCRIPTION
		"TCP port for remote TAPI demon."
	::= { admin 37 }

	biboAdmTimeProtocol OBJECT-TYPE
	    SYNTAX  INTEGER {
		none(1),
		time-udp(2),
		time-tcp(3),
		time-sntp(4),
		isdn(5)
	    }
	    ACCESS  read-write
	    STATUS  mandatory
	    DESCRIPTION
		"This field specifies from which source the bricks internal
		 clock is synchronised:
		 none(1)      = no time synchronisation
		 time-udp(2)  = UDP/TIME (RFC 868), from biboAdmTimeServer
		 time-tcp(3)  = TCP/TIME (RFC 868), from biboAdmTimeServer
		 time-sntp(4) = SNTP (RFC 1769),    from biboAdmTimeServer
		 isdn(5)      = examines ISDN time, from controller stack 0"
	::= { admin 38 }

	biboAdmTimeUpdate OBJECT-TYPE
	    SYNTAX  INTEGER
	    ACCESS  read-write
	    STATUS  mandatory
	    DESCRIPTION
		"This is the intervall for timeserver requests (in seconds).
		 If the set value is in the range from -24 to 24,
		 it means hours, and is automatically converted
		 to seconds.
		 If the time comes from ISDN, the time is updated
		 with the next call after this intervall."
	::= { admin 39 }


	biboAdmWINS1 OBJECT-TYPE
	    SYNTAX  IpAddress
	    ACCESS  read-write
	    STATUS  mandatory
	    DESCRIPTION
		"The IP address of the WINS server (NetBIOS Name Server)."
	::= { admin 40 }


	biboAdmWINS2 OBJECT-TYPE
	    SYNTAX  IpAddress
	    ACCESS  read-write
	    STATUS  mandatory
	    DESCRIPTION
		"The IP address of the alternate WINS server."
	::= { admin 41 }

	admin-2 OBJECT IDENTIFIER
	    ::= { bibo 22 }

-- Card Table

	biboAdmCardTable OBJECT-TYPE
	    SYNTAX  SEQUENCE OF BiboAdmCardEntry
	    ACCESS  not-accessible
	    STATUS  mandatory
	    DESCRIPTION
		"The biboAdmCardTable lists installed cards."
	::= { admin 42 }

	biboAdmCardEntry OBJECT-TYPE
	    SYNTAX  BiboAdmCardEntry
	    ACCESS  not-accessible
	    STATUS  mandatory
	    DESCRIPTION
		""
	    INDEX { biboACrdSlot }
	::= { biboAdmCardTable 1 }

	BiboAdmCardEntry ::=
	    SEQUENCE {
		biboACrdSlot				INTEGER,
		biboACrdType				DisplayString,
		biboACrdState				INTEGER,
		biboACrdCpldVersion			DisplayString,
		biboACrdFpgaVersion			DisplayString,
		biboACrdTemp				INTEGER,
		biboACrdTempAlarmThreshold		INTEGER,
		biboACrdTempAlarmTrap			INTEGER
	    }

	biboACrdSlot OBJECT-TYPE
	    SYNTAX  INTEGER (0..31) 
	    ACCESS  read-only
	    STATUS  mandatory

	    DESCRIPTION
		"The slot, or location of this card."
	::= { biboAdmCardEntry 1 }

	biboACrdType OBJECT-TYPE
	    SYNTAX  DisplayString 
	    ACCESS  read-only
	    STATUS  mandatory

	    DESCRIPTION
		"The name of this card."
	::= { biboAdmCardEntry 2 }
	
	biboACrdState OBJECT-TYPE
	    SYNTAX  INTEGER { down(1), running(2), fail(3), stopped(4) }
	    ACCESS  read-write
	    STATUS  mandatory

	    DESCRIPTION
		"State of the card."
	::= { biboAdmCardEntry 3 }

	biboACrdCpldVersion OBJECT-TYPE
	    SYNTAX  DisplayString 
	    ACCESS  read-only
	    STATUS  mandatory

	    DESCRIPTION
		"Version of onboard CPLD."
	::= { biboAdmCardEntry 4 }
	
	biboACrdFpgaVersion OBJECT-TYPE
	    SYNTAX  DisplayString 
	    ACCESS  read-only
	    STATUS  mandatory

	    DESCRIPTION
		"Version of loaded FPGA firmware."
	::= { biboAdmCardEntry 5 }

	biboACrdTemp OBJECT-TYPE
	    SYNTAX  INTEGER (0..250)
	    ACCESS  read-only
	    STATUS  mandatory

	    DESCRIPTION
                "This variable shows the actual card temperature
                in the unit Celsius."
	::= { biboAdmCardEntry 6 }

	biboACrdTempAlarmThreshold OBJECT-TYPE
	    SYNTAX  INTEGER (0..250)
	    ACCESS  read-write
	    STATUS  mandatory

	    DESCRIPTION
                "Card temperature threshold."
	::= { biboAdmCardEntry 7 }

	biboACrdTempAlarmTrap OBJECT-TYPE
	    SYNTAX  INTEGER { normal(1), critical(2) }
	    ACCESS  read-only
	    STATUS  mandatory

	    DESCRIPTION
                "If the card temperature raises above the threshold,
                a trap is generated every 60 seconds."
	::= { biboAdmCardEntry 8 }

        biboAdmTraps	OBJECT IDENTIFIER ::= { admin 43 }

	biboAdmTrapACrdTempCritical TRAP-TYPE
	    ENTERPRISE    biboAdmTraps
	    VARIABLES     {
	        sysDescr,
	        sysName,
	        biboACrdSlot,
	        biboACrdType,
	        biboACrdState,
	        biboACrdTemp,
	        biboACrdTempAlarmThreshold
	    }
	    DESCRIPTION   "This trap signifies that the Card temperature raises
	                   above the critical alarm-threshold"
	::= 1

	biboAdmTrapACrdTempOk TRAP-TYPE
	    ENTERPRISE    biboAdmTraps
	    VARIABLES     {
	        sysDescr,
	        sysName,
	        biboACrdSlot,
	        biboACrdType,
	        biboACrdState,
	        biboACrdTemp,
	        biboACrdTempAlarmThreshold
	    }
	    DESCRIPTION   "A normal Card temperature has been restored."
	::= 2

	biboAdmTrapACrdDown TRAP-TYPE
	    ENTERPRISE    biboAdmTraps
	    VARIABLES     {
	        sysDescr,
	        sysName,
	        biboACrdSlot,
	        biboACrdType,
	        biboACrdState,
	        biboACrdTemp
	    }
	    DESCRIPTION   "This trap signifies that the specified Card is down"
	::= 3

	biboAdmTrapACrdRunning TRAP-TYPE
	    ENTERPRISE    biboAdmTraps
	    VARIABLES     {
	        sysDescr,
	        sysName,
	        biboACrdSlot,
	        biboACrdType,
	        biboACrdState,
	        biboACrdTemp
	    }
	    DESCRIPTION   "This trap signifies that the specified Card
	                   is up/running"
	::= 4

	biboAdmTrapACrdFailed TRAP-TYPE
	    ENTERPRISE    biboAdmTraps
	    VARIABLES     {
	        sysDescr,
	        sysName,
	        biboACrdSlot,
	        biboACrdType,
	        biboACrdState,
	        biboACrdTemp
	    }
	    DESCRIPTION   "This trap signifies that the specified Card
	                   has failed"
	::= 5

	biboAdmTrapACrdStopped TRAP-TYPE
	    ENTERPRISE    biboAdmTraps
	    VARIABLES     {
	        sysDescr,
	        sysName,
	        biboACrdSlot,
	        biboACrdType,
	        biboACrdState,
	        biboACrdTemp
	    }
	    DESCRIPTION   "This trap signifies that the specified Card
	                   is stopped"
	::= 6

	biboAdmSnmpLinkTrapEvent OBJECT-TYPE
	    SYNTAX  INTEGER { none(1),
			      any(2),
			      up(3),
                              down(4)
                            }
	    ACCESS  read-write
	    STATUS  mandatory

	    DESCRIPTION
                "Defines the ifOperStatus transition(s) of an ifTable object
                 that generates a SNMP linkUp/linkDown trap:

                   none : disable linkUp/linkDown trap generation.

		    any : enable bintec like trap generation.
                          - entering the up state generates a up trap
                          - any other state change generates a down trap

		     up : enable rfc1157 like trap generation.
                          - entering the up state generates a up trap
                          - leaving the up state generates a down trap

		   down : enable rfc2233 like trap generation.
                          - leaving the down state generates a up trap
                          - entering the down state generates a down trap

                 Seven parameters are sent in each linkUp/linkDown trap pdu:
                   1. ifEntry.ifIndex       (mandatory for linkUp/Down traps)
                   2. ifEntry.ifDescr
                   3. ifEntry.ifType
                   4. ifEntry.ifAdminStatus
                   5. ifEntry.ifOperStatus
                   6. system.Description
                   7. system.Name"
	::= { admin 44 }

	extadmin	OBJECT IDENTIFIER
	    ::= { admin-2 1 }

	biboExtAdmMonAddress OBJECT-TYPE
	    SYNTAX  IpAddress
	    ACCESS  read-write
	    STATUS  mandatory
	    DESCRIPTION
		"The IP address of the host machine running the Activity
		 Monitor program. This program displays the information
		 about the current state of all interfaces.
		 Periodically UDP packets are send to this IP address,
		 to refresh the data automatically on the target host.
		 The value 255.255.255.255 represents the broadcast address
		 of the first LAN interface (e.g. 10.255.255.255), so
		 more than one Activity Monitor on different hosts can 
		 receive the data."
	::= { extadmin 1 }

	biboExtAdmMonPort OBJECT-TYPE
	    SYNTAX  INTEGER (0 .. 65535)
	    ACCESS  read-write
	    STATUS  mandatory
	    DESCRIPTION
		"UDP port for the Activity Monitor protocol."
	::= { extadmin 2 }

	biboExtAdmMonType OBJECT-TYPE
	    SYNTAX  INTEGER { 
			off(1), physical(2), physical-virt(3)
		    }
	    ACCESS  read-write
	    STATUS  mandatory
	    DESCRIPTION
		"This parameter configures the content of the Activity Monitor 
		 packets, or disables it:
		    off          : Activity Monitor disabled
		    physical     : send only physical interfaces information
		    physical-virt: send physical and virtual interface
                                   information."
	::= { extadmin 3 }

	biboExtAdmMonUpdate OBJECT-TYPE
	    SYNTAX  INTEGER (0 .. 60)
	    ACCESS  read-write
	    STATUS  mandatory
	    DESCRIPTION
		"This is the time interval for the Activity Monitor 
		 for sending packets (in seconds) to the specified IP address.
		 The value of 0 disables sending Activity Monitor packets."
	::= { extadmin 4 }

END		-- of BIANCA-BRICK definitions
