Nortel-MsCarrier-MscPassport-DprsMcsEpMIB
DEFINITIONS ::= BEGIN



IMPORTS

      OBJECT-TYPE
   FROM RFC-1212

      mscPassportMIBs
   FROM Nortel-MsCarrier-MscPassport-UsefulDefinitionsMIB

      Counter32,
      RowPointer,
      DisplayString,
      StorageType,
      RowStatus,
      Gauge32,
      Integer32,
      Unsigned32
   FROM Nortel-MsCarrier-MscPassport-StandardTextualConventionsMIB

      AsciiString,
      NonReplicated,
      HexString,
      EnterpriseDateAndTime,
      PassportCounter64,
      Link,
      Unsigned64,
      FixedPoint2
   FROM Nortel-MsCarrier-MscPassport-TextualConventionsMIB

      mscMcsMgrIndex,
      mscMcsMgr
   FROM Nortel-MsCarrier-MscPassport-McsMgrMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     DprsMcsEp Enterprise MIB."

dprsMcsEpMIB OBJECT IDENTIFIER ::= { mscPassportMIBs 125 }










-- McsMgr DprsMcsEndPointGroup/n
-- The DprsMcsEndPointGroup component contains all of the 
-- provisioned End Points or all of the dynamic End Points that share a 
-- common destination NSAP address, thereby terminating on the 
-- same destination node. 
-- This means that there could be at most two 
-- DprsMcsEndPointGroups to the same destination, a provisioned 
-- DprsMcsEpG and a dynamic DprsMcsEpG.
-- The associated group is indicated by the associatedEpGroupName 
-- attribute. 
-- DprsMcsEpG component instances in the 1-4096 range can be 
-- provisioned. 
-- DprsMcsEpG component instances in the 4097-8191 range are 
-- dynamic.

mscMcsMgrDprsMcsEpG OBJECT IDENTIFIER ::= { mscMcsMgr 2 }



mscMcsMgrDprsMcsEpGRowStatusTable OBJECT-TYPE
   SYNTAX     SEQUENCE OF MscMcsMgrDprsMcsEpGRowStatusEntry
   ACCESS     not-accessible
   STATUS     mandatory
   DESCRIPTION
     "This entry controls the addition and deletion of 
      mscMcsMgrDprsMcsEpG components."
::= { mscMcsMgrDprsMcsEpG 1 }

mscMcsMgrDprsMcsEpGRowStatusEntry OBJECT-TYPE
   SYNTAX     MscMcsMgrDprsMcsEpGRowStatusEntry
   ACCESS     not-accessible
   STATUS     mandatory
   DESCRIPTION
     "A single entry in the table represents a single 
      mscMcsMgrDprsMcsEpG component."
   INDEX {
      mscMcsMgrIndex,
      mscMcsMgrDprsMcsEpGIndex }
::= { mscMcsMgrDprsMcsEpGRowStatusTable 1 }

MscMcsMgrDprsMcsEpGRowStatusEntry ::= SEQUENCE {
   mscMcsMgrDprsMcsEpGRowStatus
      RowStatus,
   mscMcsMgrDprsMcsEpGComponentName
      DisplayString,
   mscMcsMgrDprsMcsEpGStorageType
      StorageType,
   mscMcsMgrDprsMcsEpGIndex
      Integer32 }

mscMcsMgrDprsMcsEpGRowStatus OBJECT-TYPE
   SYNTAX     RowStatus 
   ACCESS     read-write
   STATUS     mandatory
   DESCRIPTION
     "This variable is used as the basis for SNMP naming of
      mscMcsMgrDprsMcsEpG components.
      These components can be added and deleted."
::= { mscMcsMgrDprsMcsEpGRowStatusEntry 1 }

mscMcsMgrDprsMcsEpGComponentName OBJECT-TYPE
   SYNTAX     DisplayString 
   ACCESS     read-only
   STATUS     mandatory
   DESCRIPTION
     "This variable provides the component's string name for
      use with the ASCII Console Interface"
::= { mscMcsMgrDprsMcsEpGRowStatusEntry 2 }

mscMcsMgrDprsMcsEpGStorageType OBJECT-TYPE
   SYNTAX     StorageType 
   ACCESS     read-only
   STATUS     mandatory
   DESCRIPTION
     "This variable represents the storage type value for the
      mscMcsMgrDprsMcsEpG tables."
::= { mscMcsMgrDprsMcsEpGRowStatusEntry 4 }

mscMcsMgrDprsMcsEpGIndex OBJECT-TYPE
   SYNTAX     Integer32 (1..8191)
   ACCESS     not-accessible
   STATUS     mandatory
   DESCRIPTION
     "This variable represents the index for the mscMcsMgrDprsMcsEpG tables."
::= { mscMcsMgrDprsMcsEpGRowStatusEntry 10 }

mscMcsMgrDprsMcsEpGOperTable OBJECT-TYPE
   SYNTAX     SEQUENCE OF MscMcsMgrDprsMcsEpGOperEntry
   ACCESS     not-accessible
   STATUS     mandatory
   DESCRIPTION
     "This group contains the operational attributes of the DprsMcsEpG 
      component."
::= { mscMcsMgrDprsMcsEpG 10 }

mscMcsMgrDprsMcsEpGOperEntry OBJECT-TYPE
   SYNTAX     MscMcsMgrDprsMcsEpGOperEntry
   ACCESS     not-accessible
   STATUS     mandatory
   DESCRIPTION
     "An entry in the mscMcsMgrDprsMcsEpGOperTable."
   INDEX {
      mscMcsMgrIndex,
      mscMcsMgrDprsMcsEpGIndex }
::= { mscMcsMgrDprsMcsEpGOperTable 1 }

MscMcsMgrDprsMcsEpGOperEntry ::= SEQUENCE {
   mscMcsMgrDprsMcsEpGRemoteAddress
      AsciiString,
   mscMcsMgrDprsMcsEpGAssociatedEpGroupName
      RowPointer }

mscMcsMgrDprsMcsEpGRemoteAddress OBJECT-TYPE
   SYNTAX     AsciiString (SIZE (0..44))
   ACCESS     read-only
   STATUS     mandatory
   DESCRIPTION
     "This attribute indicates the NSAP address of the McsMgr at the 
      destination module to which all EndPoints of this group are 
      connected."
::= { mscMcsMgrDprsMcsEpGOperEntry 1 }

mscMcsMgrDprsMcsEpGAssociatedEpGroupName OBJECT-TYPE
   SYNTAX     RowPointer 
   ACCESS     read-only
   STATUS     mandatory
   DESCRIPTION
     "For a provisioned DprsMcsEpG, this attribute indicates the name of 
      the DprsMcsEpG that contains the dynamic Eps to the same 
      destination.
      For a dynamic DprsMcsEpG, this attribute indicates the name of the 
      DprsMcsEpG that contains the provisioned Eps to the same 
      destination.
      A null component name indicates that there is no DprsMcsEpG 
      associated with this group."
::= { mscMcsMgrDprsMcsEpGOperEntry 2 }


-- McsMgr DprsMcsEpG/n Address
-- This component contains the destination NSAP address used by all 
-- DPRS MCS End Points provisioned under a DprsMcsEpG.

mscMcsMgrDprsMcsEpGAddr OBJECT IDENTIFIER ::= { mscMcsMgrDprsMcsEpG 2 }



mscMcsMgrDprsMcsEpGAddrRowStatusTable OBJECT-TYPE
   SYNTAX     SEQUENCE OF MscMcsMgrDprsMcsEpGAddrRowStatusEntry
   ACCESS     not-accessible
   STATUS     mandatory
   DESCRIPTION
     "This entry controls the addition and deletion of 
      mscMcsMgrDprsMcsEpGAddr components."
::= { mscMcsMgrDprsMcsEpGAddr 1 }

mscMcsMgrDprsMcsEpGAddrRowStatusEntry OBJECT-TYPE
   SYNTAX     MscMcsMgrDprsMcsEpGAddrRowStatusEntry
   ACCESS     not-accessible
   STATUS     mandatory
   DESCRIPTION
     "A single entry in the table represents a single 
      mscMcsMgrDprsMcsEpGAddr component."
   INDEX {
      mscMcsMgrIndex,
      mscMcsMgrDprsMcsEpGIndex,
      mscMcsMgrDprsMcsEpGAddrIndex }
::= { mscMcsMgrDprsMcsEpGAddrRowStatusTable 1 }

MscMcsMgrDprsMcsEpGAddrRowStatusEntry ::= SEQUENCE {
   mscMcsMgrDprsMcsEpGAddrRowStatus
      RowStatus,
   mscMcsMgrDprsMcsEpGAddrComponentName
      DisplayString,
   mscMcsMgrDprsMcsEpGAddrStorageType
      StorageType,
   mscMcsMgrDprsMcsEpGAddrIndex
      NonReplicated }

mscMcsMgrDprsMcsEpGAddrRowStatus OBJECT-TYPE
   SYNTAX     RowStatus 
   ACCESS     read-only
   STATUS     mandatory
   DESCRIPTION
     "This variable is used as the basis for SNMP naming of
      mscMcsMgrDprsMcsEpGAddr components.
      These components cannot be added nor deleted."
::= { mscMcsMgrDprsMcsEpGAddrRowStatusEntry 1 }

mscMcsMgrDprsMcsEpGAddrComponentName OBJECT-TYPE
   SYNTAX     DisplayString 
   ACCESS     read-only
   STATUS     mandatory
   DESCRIPTION
     "This variable provides the component's string name for
      use with the ASCII Console Interface"
::= { mscMcsMgrDprsMcsEpGAddrRowStatusEntry 2 }

mscMcsMgrDprsMcsEpGAddrStorageType OBJECT-TYPE
   SYNTAX     StorageType 
   ACCESS     read-only
   STATUS     mandatory
   DESCRIPTION
     "This variable represents the storage type value for the
      mscMcsMgrDprsMcsEpGAddr tables."
::= { mscMcsMgrDprsMcsEpGAddrRowStatusEntry 4 }

mscMcsMgrDprsMcsEpGAddrIndex OBJECT-TYPE
   SYNTAX     NonReplicated 
   ACCESS     not-accessible
   STATUS     mandatory
   DESCRIPTION
     "This variable represents the index for the mscMcsMgrDprsMcsEpGAddr tables."
::= { mscMcsMgrDprsMcsEpGAddrRowStatusEntry 10 }

mscMcsMgrDprsMcsEpGAddrProvTable OBJECT-TYPE
   SYNTAX     SEQUENCE OF MscMcsMgrDprsMcsEpGAddrProvEntry
   ACCESS     not-accessible
   STATUS     mandatory
   DESCRIPTION
     "This group contains the provisionable attributes of the Address 
      component."
::= { mscMcsMgrDprsMcsEpGAddr 10 }

mscMcsMgrDprsMcsEpGAddrProvEntry OBJECT-TYPE
   SYNTAX     MscMcsMgrDprsMcsEpGAddrProvEntry
   ACCESS     not-accessible
   STATUS     mandatory
   DESCRIPTION
     "An entry in the mscMcsMgrDprsMcsEpGAddrProvTable."
   INDEX {
      mscMcsMgrIndex,
      mscMcsMgrDprsMcsEpGIndex,
      mscMcsMgrDprsMcsEpGAddrIndex }
::= { mscMcsMgrDprsMcsEpGAddrProvTable 1 }

MscMcsMgrDprsMcsEpGAddrProvEntry ::= SEQUENCE {
   mscMcsMgrDprsMcsEpGAddrRemoteAddress
      AsciiString,
   mscMcsMgrDprsMcsEpGAddrCommentText
      AsciiString }

mscMcsMgrDprsMcsEpGAddrRemoteAddress OBJECT-TYPE
   SYNTAX     AsciiString (SIZE (1..44))
   ACCESS     read-write
   STATUS     mandatory
   DESCRIPTION
     "This attribute specifies the NSAP address of the McsMgr at the 
      destination module. This address is used by the EndPoints 
      provisioned under this DprsMcsEpG to establish a DPRS MCS  
      Switched Path."
::= { mscMcsMgrDprsMcsEpGAddrProvEntry 1 }

mscMcsMgrDprsMcsEpGAddrCommentText OBJECT-TYPE
   SYNTAX     AsciiString (SIZE (0..60))
   ACCESS     read-write
   STATUS     mandatory
   DESCRIPTION
     "This attribute specifies additional textual information to be added by 
      the network operator. Typical use of this attribute is to specify the 
      destination module name."
   DEFVAL     { ''H }  -- ""
::= { mscMcsMgrDprsMcsEpGAddrProvEntry 2 }


-- McsMgr DprsMcsEpG/n EndPoint/n
-- The EndPoint component represents the DPRS MCS  Switched 
-- Path. It multiplexes multiple Frame Relay DLCIs and transports 
-- them over an underlying PORS or ATM connection.

mscMcsMgrDprsMcsEpGEp OBJECT IDENTIFIER ::= { mscMcsMgrDprsMcsEpG 3 }



mscMcsMgrDprsMcsEpGEpRowStatusTable OBJECT-TYPE
   SYNTAX     SEQUENCE OF MscMcsMgrDprsMcsEpGEpRowStatusEntry
   ACCESS     not-accessible
   STATUS     mandatory
   DESCRIPTION
     "This entry controls the addition and deletion of 
      mscMcsMgrDprsMcsEpGEp components."
::= { mscMcsMgrDprsMcsEpGEp 1 }

mscMcsMgrDprsMcsEpGEpRowStatusEntry OBJECT-TYPE
   SYNTAX     MscMcsMgrDprsMcsEpGEpRowStatusEntry
   ACCESS     not-accessible
   STATUS     mandatory
   DESCRIPTION
     "A single entry in the table represents a single 
      mscMcsMgrDprsMcsEpGEp component."
   INDEX {
      mscMcsMgrIndex,
      mscMcsMgrDprsMcsEpGIndex,
      mscMcsMgrDprsMcsEpGEpIndex }
::= { mscMcsMgrDprsMcsEpGEpRowStatusTable 1 }

MscMcsMgrDprsMcsEpGEpRowStatusEntry ::= SEQUENCE {
   mscMcsMgrDprsMcsEpGEpRowStatus
      RowStatus,
   mscMcsMgrDprsMcsEpGEpComponentName
      DisplayString,
   mscMcsMgrDprsMcsEpGEpStorageType
      StorageType,
   mscMcsMgrDprsMcsEpGEpIndex
      Integer32 }

mscMcsMgrDprsMcsEpGEpRowStatus OBJECT-TYPE
   SYNTAX     RowStatus 
   ACCESS     read-write
   STATUS     mandatory
   DESCRIPTION
     "This variable is used as the basis for SNMP naming of
      mscMcsMgrDprsMcsEpGEp components.
      These components can be added and deleted."
::= { mscMcsMgrDprsMcsEpGEpRowStatusEntry 1 }

mscMcsMgrDprsMcsEpGEpComponentName OBJECT-TYPE
   SYNTAX     DisplayString 
   ACCESS     read-only
   STATUS     mandatory
   DESCRIPTION
     "This variable provides the component's string name for
      use with the ASCII Console Interface"
::= { mscMcsMgrDprsMcsEpGEpRowStatusEntry 2 }

mscMcsMgrDprsMcsEpGEpStorageType OBJECT-TYPE
   SYNTAX     StorageType 
   ACCESS     read-only
   STATUS     mandatory
   DESCRIPTION
     "This variable represents the storage type value for the
      mscMcsMgrDprsMcsEpGEp tables."
::= { mscMcsMgrDprsMcsEpGEpRowStatusEntry 4 }

mscMcsMgrDprsMcsEpGEpIndex OBJECT-TYPE
   SYNTAX     Integer32 (1..256)
   ACCESS     not-accessible
   STATUS     mandatory
   DESCRIPTION
     "This variable represents the index for the mscMcsMgrDprsMcsEpGEp tables."
::= { mscMcsMgrDprsMcsEpGEpRowStatusEntry 10 }

mscMcsMgrDprsMcsEpGEpStateTable OBJECT-TYPE
   SYNTAX     SEQUENCE OF MscMcsMgrDprsMcsEpGEpStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscMcsMgrDprsMcsEpGEp 10 }

mscMcsMgrDprsMcsEpGEpStateEntry OBJECT-TYPE
   SYNTAX     MscMcsMgrDprsMcsEpGEpStateEntry
   ACCESS     not-accessible
   STATUS     mandatory
   DESCRIPTION
     "An entry in the mscMcsMgrDprsMcsEpGEpStateTable."
   INDEX {
      mscMcsMgrIndex,
      mscMcsMgrDprsMcsEpGIndex,
      mscMcsMgrDprsMcsEpGEpIndex }
::= { mscMcsMgrDprsMcsEpGEpStateTable 1 }

MscMcsMgrDprsMcsEpGEpStateEntry ::= SEQUENCE {
   mscMcsMgrDprsMcsEpGEpAdminState
      INTEGER,
   mscMcsMgrDprsMcsEpGEpOperationalState
      INTEGER,
   mscMcsMgrDprsMcsEpGEpUsageState
      INTEGER,
   mscMcsMgrDprsMcsEpGEpAvailabilityStatus
      OCTET STRING,
   mscMcsMgrDprsMcsEpGEpProceduralStatus
      OCTET STRING,
   mscMcsMgrDprsMcsEpGEpControlStatus
      OCTET STRING,
   mscMcsMgrDprsMcsEpGEpAlarmStatus
      OCTET STRING,
   mscMcsMgrDprsMcsEpGEpStandbyStatus
      INTEGER,
   mscMcsMgrDprsMcsEpGEpUnknownStatus
      INTEGER }

mscMcsMgrDprsMcsEpGEpAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscMcsMgrDprsMcsEpGEpStateEntry 1 }

mscMcsMgrDprsMcsEpGEpOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscMcsMgrDprsMcsEpGEpStateEntry 2 }

mscMcsMgrDprsMcsEpGEpUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscMcsMgrDprsMcsEpGEpStateEntry 3 }

mscMcsMgrDprsMcsEpGEpAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscMcsMgrDprsMcsEpGEpStateEntry 4 }

mscMcsMgrDprsMcsEpGEpProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscMcsMgrDprsMcsEpGEpStateEntry 5 }

mscMcsMgrDprsMcsEpGEpControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscMcsMgrDprsMcsEpGEpStateEntry 6 }

mscMcsMgrDprsMcsEpGEpAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscMcsMgrDprsMcsEpGEpStateEntry 7 }

mscMcsMgrDprsMcsEpGEpStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscMcsMgrDprsMcsEpGEpStateEntry 8 }

mscMcsMgrDprsMcsEpGEpUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscMcsMgrDprsMcsEpGEpStateEntry 9 }

mscMcsMgrDprsMcsEpGEpOperTable OBJECT-TYPE
   SYNTAX     SEQUENCE OF MscMcsMgrDprsMcsEpGEpOperEntry
   ACCESS     not-accessible
   STATUS     mandatory
   DESCRIPTION
     "This group contains the operational attributes of the EndPoint 
      component."
::= { mscMcsMgrDprsMcsEpGEp 11 }

mscMcsMgrDprsMcsEpGEpOperEntry OBJECT-TYPE
   SYNTAX     MscMcsMgrDprsMcsEpGEpOperEntry
   ACCESS     not-accessible
   STATUS     mandatory
   DESCRIPTION
     "An entry in the mscMcsMgrDprsMcsEpGEpOperTable."
   INDEX {
      mscMcsMgrIndex,
      mscMcsMgrDprsMcsEpGIndex,
      mscMcsMgrDprsMcsEpGEpIndex }
::= { mscMcsMgrDprsMcsEpGEpOperTable 1 }

MscMcsMgrDprsMcsEpGEpOperEntry ::= SEQUENCE {
   mscMcsMgrDprsMcsEpGEpLastTransportConnectionClearCause
      Unsigned32,
   mscMcsMgrDprsMcsEpGEpType
      INTEGER,
   mscMcsMgrDprsMcsEpGEpSupportedTransferPriorities
      OCTET STRING,
   mscMcsMgrDprsMcsEpGEpConnectionTransferPriority
      Unsigned32,
   mscMcsMgrDprsMcsEpGEpServiceCategory
      INTEGER,
   mscMcsMgrDprsMcsEpGEpBandwidth
      Unsigned32,
   mscMcsMgrDprsMcsEpGEpRemoteComponentName
      AsciiString,
   mscMcsMgrDprsMcsEpGEpRemoteRoutingId
      Unsigned32,
   mscMcsMgrDprsMcsEpGEpRemoteModuleId
      Unsigned32,
   mscMcsMgrDprsMcsEpGEpLastTrConnDiagCode
      HexString,
   mscMcsMgrDprsMcsEpGEpForwardBandwith
      Unsigned32,
   mscMcsMgrDprsMcsEpGEpReverseBandwidth
      Unsigned32 }

mscMcsMgrDprsMcsEpGEpLastTransportConnectionClearCause OBJECT-TYPE
   SYNTAX     Unsigned32 (0..1000)
   ACCESS     read-only
   STATUS     mandatory
   DESCRIPTION
     "This attribute indicates the most recent clear cause for the transport 
      connection.
      This indicates the causes provided by the network. 
      A value of zero indicates that the transport connection has never 
      been cleared.
      A value of 1000 indicates that the network has not provided a clear 
      cause for the transport connection clearing.
      Section 5.4.5.15 of the ATMF UNI 3.1 specification lists the clear 
      causes provided by the network."
::= { mscMcsMgrDprsMcsEpGEpOperEntry 3 }

mscMcsMgrDprsMcsEpGEpType OBJECT-TYPE
   SYNTAX     INTEGER  {
                 originating(0),
                 terminating(1) }
   ACCESS     read-only
   STATUS     mandatory
   DESCRIPTION
     "This attribute indicates the type of the end point. If the value is 
      originating, this Ep is provisioned and is responsible for initiating 
      the SPVC call to set up the PORS or ATM connection. If the value 
      is terminating, this Ep is created dynamically by the McsMgr at the 
      destination node when it receives a call setup request."
   DEFVAL     { originating }
::= { mscMcsMgrDprsMcsEpGEpOperEntry 4 }

mscMcsMgrDprsMcsEpGEpSupportedTransferPriorities OBJECT-TYPE
   SYNTAX     OCTET STRING (SIZE (2))
   ACCESS     read-only
   STATUS     mandatory
   DESCRIPTION
     "This attribute indicates the Frame Relay transfer priorities 
      supported by the transport connection.

      Description of bits:
      n0(0)
      n1(1)
      n2(2)
      n3(3)
      n4(4)
      n5(5)
      n6(6)
      n7(7)
      n8(8)
      n9(9)
      n10(10)
      n11(11)
      n12(12)
      n13(13)
      n14(14)
      n15(15)"
::= { mscMcsMgrDprsMcsEpGEpOperEntry 5 }

mscMcsMgrDprsMcsEpGEpConnectionTransferPriority OBJECT-TYPE
   SYNTAX     Unsigned32 (0..15)
   ACCESS     read-only
   STATUS     mandatory
   DESCRIPTION
     "This attribute indicates the transfer priority used to establish the 
      transport connection."
::= { mscMcsMgrDprsMcsEpGEpOperEntry 6 }

mscMcsMgrDprsMcsEpGEpServiceCategory OBJECT-TYPE
   SYNTAX     INTEGER  {
                 ubr(0),
                 cbr(1),
                 rtVbr(2),
                 nrtVbr(3) }
   ACCESS     read-only
   STATUS     mandatory
   DESCRIPTION
     "This attribute indicates the ATM service category of the transport 
      connection."
::= { mscMcsMgrDprsMcsEpGEpOperEntry 7 }

mscMcsMgrDprsMcsEpGEpBandwidth OBJECT-TYPE
   SYNTAX     Unsigned32 (0..155000000)
   ACCESS     read-only
   STATUS     obsolete
   DESCRIPTION
     "This attribute indicates the bandwidth at which the transport 
      connection agrees to transfer information. 
      This attribute has been replaced by the forwardBandwidth and 
      backwardBandwidth attributes."
::= { mscMcsMgrDprsMcsEpGEpOperEntry 8 }

mscMcsMgrDprsMcsEpGEpRemoteComponentName OBJECT-TYPE
   SYNTAX     AsciiString (SIZE (0..46))
   ACCESS     read-only
   STATUS     mandatory
   DESCRIPTION
     "This attribute indicates the component name of the remote Ep, 
      learned from the remote end.
      For example: 'EM/NODEY2D0 McsMgr DprsMcsEpG/1 Ep/1'.
      The value is a null string if the transport connection is down."
::= { mscMcsMgrDprsMcsEpGEpOperEntry 9 }

mscMcsMgrDprsMcsEpGEpRemoteRoutingId OBJECT-TYPE
   SYNTAX     Unsigned32 (0..126)
   ACCESS     read-only
   STATUS     mandatory
   DESCRIPTION
     "This attribute indicates the routing identifier (RID) associated with 
      the Passport node on which the remote Ep resides. The remote RID 
      is learned from the remote Ep.
      The value is valid when the transport connection is up and zero 
      otherwise."
::= { mscMcsMgrDprsMcsEpGEpOperEntry 10 }

mscMcsMgrDprsMcsEpGEpRemoteModuleId OBJECT-TYPE
   SYNTAX     Unsigned32 (0..1909)
   ACCESS     read-only
   STATUS     mandatory
   DESCRIPTION
     "This attribute indicates the module identifier (MID) associated with 
      the Passport node on which the remote Ep resides. The remote MID 
      is learned from the remote Ep.
      The value is valid when the transport connection is up and zero 
      otherwise."
::= { mscMcsMgrDprsMcsEpGEpOperEntry 11 }

mscMcsMgrDprsMcsEpGEpLastTrConnDiagCode OBJECT-TYPE
   SYNTAX     HexString (SIZE (0..10))
   ACCESS     read-only
   STATUS     mandatory
   DESCRIPTION
     "This attribute indicates the diagnostic code of the most recently 
      cleared transport connection.
      This indicates the diagnostic code (associated with the 
      lastTransportConnectionClearCause) provided by the network. 
      A string containing only a 0 or 00 (zero) indicates that the network 
      has not provided a diagnostic code for the most recently cleared 
      transport connection.
      Section 5.4.5.15 of the ATMF UNI 3.1 specification lists the 
      diagnostic codes that can be provided by the network."
::= { mscMcsMgrDprsMcsEpGEpOperEntry 12 }

mscMcsMgrDprsMcsEpGEpForwardBandwith OBJECT-TYPE
   SYNTAX     Unsigned32 (0..155000000)
   ACCESS     read-only
   STATUS     mandatory
   DESCRIPTION
     "This attribute indicates the bandwidth at which the transport 
      connection agrees to transfer information in the forward (from the 
      originating to the dynamic End Point) direction."
::= { mscMcsMgrDprsMcsEpGEpOperEntry 13 }

mscMcsMgrDprsMcsEpGEpReverseBandwidth OBJECT-TYPE
   SYNTAX     Unsigned32 (0..155000000)
   ACCESS     read-only
   STATUS     mandatory
   DESCRIPTION
     "This attribute indicates the bandwidth at which the transport 
      connection agrees to transfer information in the reverse (from the 
      dynamic to the to the originating End Point) direction."
::= { mscMcsMgrDprsMcsEpGEpOperEntry 14 }

mscMcsMgrDprsMcsEpGEpStatsTable OBJECT-TYPE
   SYNTAX     SEQUENCE OF MscMcsMgrDprsMcsEpGEpStatsEntry
   ACCESS     not-accessible
   STATUS     mandatory
   DESCRIPTION
     "This group contains statistics of traffic received on the DPRS MCS 
      Switched Path."
::= { mscMcsMgrDprsMcsEpGEp 12 }

mscMcsMgrDprsMcsEpGEpStatsEntry OBJECT-TYPE
   SYNTAX     MscMcsMgrDprsMcsEpGEpStatsEntry
   ACCESS     not-accessible
   STATUS     mandatory
   DESCRIPTION
     "An entry in the mscMcsMgrDprsMcsEpGEpStatsTable."
   INDEX {
      mscMcsMgrIndex,
      mscMcsMgrDprsMcsEpGIndex,
      mscMcsMgrDprsMcsEpGEpIndex }
::= { mscMcsMgrDprsMcsEpGEpStatsTable 1 }

MscMcsMgrDprsMcsEpGEpStatsEntry ::= SEQUENCE {
   mscMcsMgrDprsMcsEpGEpSetupAttempts
      Counter32,
   mscMcsMgrDprsMcsEpGEpPktDiscErroredFromMcs
      Counter32 }

mscMcsMgrDprsMcsEpGEpSetupAttempts OBJECT-TYPE
   SYNTAX     Counter32 
   ACCESS     read-only
   STATUS     mandatory
   DESCRIPTION
     "This attribute counts the number of attempts made to set up the 
      transport connection. The counter wraps around to zero when the 
      maximum value is exceeded."
::= { mscMcsMgrDprsMcsEpGEpStatsEntry 1 }

mscMcsMgrDprsMcsEpGEpPktDiscErroredFromMcs OBJECT-TYPE
   SYNTAX     Counter32 
   ACCESS     read-only
   STATUS     mandatory
   DESCRIPTION
     "This attribute counts errored packets received on the DPRS MCS 
      Switched Path; these packets are discarded. 
      The counter wraps around to zero when the maximum value is 
      exceeded."
::= { mscMcsMgrDprsMcsEpGEpStatsEntry 2 }

mscMcsMgrDprsMcsEpGEpPktFromMcsTable OBJECT-TYPE
   SYNTAX     SEQUENCE OF MscMcsMgrDprsMcsEpGEpPktFromMcsEntry
   ACCESS     not-accessible
   STATUS     mandatory
   DESCRIPTION
     "This attribute counts the packets received on the DPRS MCS 
      Switched Path for each discard priority.
      This attribute is a vector with four entries. Each vector entry is a 
      counter indexed by one of four discard priorities, namely, discard 
      priority 0 (dp0), discard priority 1 (dp1), discard priority 2 (dp2),
      or discard priority 3 (dp3).
      Each entry (counter) wraps around to zero when the maximum 
      value is exceeded."
::= { mscMcsMgrDprsMcsEpGEp 402 }

mscMcsMgrDprsMcsEpGEpPktFromMcsEntry OBJECT-TYPE
   SYNTAX     MscMcsMgrDprsMcsEpGEpPktFromMcsEntry
   ACCESS     not-accessible
   STATUS     mandatory
   DESCRIPTION
     "An entry in the mscMcsMgrDprsMcsEpGEpPktFromMcsTable."
   INDEX {
      mscMcsMgrIndex,
      mscMcsMgrDprsMcsEpGIndex,
      mscMcsMgrDprsMcsEpGEpIndex,
      mscMcsMgrDprsMcsEpGEpPktFromMcsIndex }
::= { mscMcsMgrDprsMcsEpGEpPktFromMcsTable 1 }

MscMcsMgrDprsMcsEpGEpPktFromMcsEntry ::= SEQUENCE {
   mscMcsMgrDprsMcsEpGEpPktFromMcsIndex
      INTEGER,
   mscMcsMgrDprsMcsEpGEpPktFromMcsValue
      PassportCounter64 }

mscMcsMgrDprsMcsEpGEpPktFromMcsIndex OBJECT-TYPE
   SYNTAX     INTEGER  {
                 discardPriority0(0),
                 discardPriority1(1),
                 discardPriority2(2),
                 discardPriority3(3) }
   ACCESS     not-accessible
   STATUS     mandatory
   DESCRIPTION
     "This variable represents the mscMcsMgrDprsMcsEpGEpPktFromMcsTable
      specific index for the mscMcsMgrDprsMcsEpGEpPktFromMcsTable."
::= { mscMcsMgrDprsMcsEpGEpPktFromMcsEntry 1 }

mscMcsMgrDprsMcsEpGEpPktFromMcsValue OBJECT-TYPE
   SYNTAX     PassportCounter64 
   ACCESS     read-only
   STATUS     mandatory
   DESCRIPTION
     "This variable represents an individual value for the
      mscMcsMgrDprsMcsEpGEpPktFromMcsTable."
::= { mscMcsMgrDprsMcsEpGEpPktFromMcsEntry 2 }

mscMcsMgrDprsMcsEpGEpOctetsFromMcsTable OBJECT-TYPE
   SYNTAX     SEQUENCE OF MscMcsMgrDprsMcsEpGEpOctetsFromMcsEntry
   ACCESS     not-accessible
   STATUS     mandatory
   DESCRIPTION
     "This attribute counts the octets received on the DPRS MCS 
      Switched Path for each discard priority. 
      This attribute is a vector with four entries. Each vector entry is a 
      counter indexed by one of four discard priorities, namely, discard 
      priority 0 (dp0), discard priority 1 (dp1), discard priority 2 (dp2), or 
      discard priority 3 (dp3).
      Each entry (counter) wraps around to zero when the maximum 
      value is exceeded."
::= { mscMcsMgrDprsMcsEpGEp 403 }

mscMcsMgrDprsMcsEpGEpOctetsFromMcsEntry OBJECT-TYPE
   SYNTAX     MscMcsMgrDprsMcsEpGEpOctetsFromMcsEntry
   ACCESS     not-accessible
   STATUS     mandatory
   DESCRIPTION
     "An entry in the mscMcsMgrDprsMcsEpGEpOctetsFromMcsTable."
   INDEX {
      mscMcsMgrIndex,
      mscMcsMgrDprsMcsEpGIndex,
      mscMcsMgrDprsMcsEpGEpIndex,
      mscMcsMgrDprsMcsEpGEpOctetsFromMcsIndex }
::= { mscMcsMgrDprsMcsEpGEpOctetsFromMcsTable 1 }

MscMcsMgrDprsMcsEpGEpOctetsFromMcsEntry ::= SEQUENCE {
   mscMcsMgrDprsMcsEpGEpOctetsFromMcsIndex
      INTEGER,
   mscMcsMgrDprsMcsEpGEpOctetsFromMcsValue
      PassportCounter64 }

mscMcsMgrDprsMcsEpGEpOctetsFromMcsIndex OBJECT-TYPE
   SYNTAX     INTEGER  {
                 discardPriority0(0),
                 discardPriority1(1),
                 discardPriority2(2),
                 discardPriority3(3) }
   ACCESS     not-accessible
   STATUS     mandatory
   DESCRIPTION
     "This variable represents the mscMcsMgrDprsMcsEpGEpOctetsFromMcsTable
      specific index for the mscMcsMgrDprsMcsEpGEpOctetsFromMcsTable."
::= { mscMcsMgrDprsMcsEpGEpOctetsFromMcsEntry 1 }

mscMcsMgrDprsMcsEpGEpOctetsFromMcsValue OBJECT-TYPE
   SYNTAX     PassportCounter64 
   ACCESS     read-only
   STATUS     mandatory
   DESCRIPTION
     "This variable represents an individual value for the
      mscMcsMgrDprsMcsEpGEpOctetsFromMcsTable."
::= { mscMcsMgrDprsMcsEpGEpOctetsFromMcsEntry 2 }

mscMcsMgrDprsMcsEpGEpPktDiscCongestedFromMcsTable OBJECT-TYPE
   SYNTAX     SEQUENCE OF MscMcsMgrDprsMcsEpGEpPktDiscCongestedFromMcsEntry
   ACCESS     not-accessible
   STATUS     mandatory
   DESCRIPTION
     "This attribute counts packets received on the DPRS MCS 
      Switched Path for each discard priority that have been discarded at 
      the transport card due to congestion at the access card. 
      This attribute is a vector with four entries. Each vector entry is a 
      counter indexed by one of four discard priorities, namely, discard 
      priority 0 (dp0), discard priority 1 (dp1), discard priority 2 (dp2), or 
      discard priority 3 (dp3). 
      Each entry (counter) wraps around to zero when the maximum 
      value is exceeded."
::= { mscMcsMgrDprsMcsEpGEp 404 }

mscMcsMgrDprsMcsEpGEpPktDiscCongestedFromMcsEntry OBJECT-TYPE
   SYNTAX     MscMcsMgrDprsMcsEpGEpPktDiscCongestedFromMcsEntry
   ACCESS     not-accessible
   STATUS     mandatory
   DESCRIPTION
     "An entry in the mscMcsMgrDprsMcsEpGEpPktDiscCongestedFromMcsTable."
   INDEX {
      mscMcsMgrIndex,
      mscMcsMgrDprsMcsEpGIndex,
      mscMcsMgrDprsMcsEpGEpIndex,
      mscMcsMgrDprsMcsEpGEpPktDiscCongestedFromMcsIndex }
::= { mscMcsMgrDprsMcsEpGEpPktDiscCongestedFromMcsTable 1 }

MscMcsMgrDprsMcsEpGEpPktDiscCongestedFromMcsEntry ::= SEQUENCE {
   mscMcsMgrDprsMcsEpGEpPktDiscCongestedFromMcsIndex
      INTEGER,
   mscMcsMgrDprsMcsEpGEpPktDiscCongestedFromMcsValue
      Counter32 }

mscMcsMgrDprsMcsEpGEpPktDiscCongestedFromMcsIndex OBJECT-TYPE
   SYNTAX     INTEGER  {
                 discardPriority0(0),
                 discardPriority1(1),
                 discardPriority2(2),
                 discardPriority3(3) }
   ACCESS     not-accessible
   STATUS     mandatory
   DESCRIPTION
     "This variable represents the mscMcsMgrDprsMcsEpGEpPktDiscCongestedFromMcsTable
      specific index for the mscMcsMgrDprsMcsEpGEpPktDiscCongestedFromMcsTable."
::= { mscMcsMgrDprsMcsEpGEpPktDiscCongestedFromMcsEntry 1 }

mscMcsMgrDprsMcsEpGEpPktDiscCongestedFromMcsValue OBJECT-TYPE
   SYNTAX     Counter32 
   ACCESS     read-only
   STATUS     mandatory
   DESCRIPTION
     "This variable represents an individual value for the
      mscMcsMgrDprsMcsEpGEpPktDiscCongestedFromMcsTable."
::= { mscMcsMgrDprsMcsEpGEpPktDiscCongestedFromMcsEntry 2 }


-- McsMgr DprsMcsEpG/n Ep/n EndPointDescriptor
-- This component establishes the underlying PORS or ATM 
-- connection. There can only be one DPRS MCS Switched Path for a 
-- given Frame Relay transfer priority between a pair of nodes.
-- Therefore, the supportedTransferPriorities on this EndPoint must 
-- be mutually exclusive with the supportedTransferPriorities of all 
-- other EndPoints within this DprsMcsEndPointGroup. 

mscMcsMgrDprsMcsEpGEpEpD OBJECT IDENTIFIER ::= { mscMcsMgrDprsMcsEpGEp 2 }



mscMcsMgrDprsMcsEpGEpEpDRowStatusTable OBJECT-TYPE
   SYNTAX     SEQUENCE OF MscMcsMgrDprsMcsEpGEpEpDRowStatusEntry
   ACCESS     not-accessible
   STATUS     mandatory
   DESCRIPTION
     "This entry controls the addition and deletion of 
      mscMcsMgrDprsMcsEpGEpEpD components."
::= { mscMcsMgrDprsMcsEpGEpEpD 1 }

mscMcsMgrDprsMcsEpGEpEpDRowStatusEntry OBJECT-TYPE
   SYNTAX     MscMcsMgrDprsMcsEpGEpEpDRowStatusEntry
   ACCESS     not-accessible
   STATUS     mandatory
   DESCRIPTION
     "A single entry in the table represents a single 
      mscMcsMgrDprsMcsEpGEpEpD component."
   INDEX {
      mscMcsMgrIndex,
      mscMcsMgrDprsMcsEpGIndex,
      mscMcsMgrDprsMcsEpGEpIndex,
      mscMcsMgrDprsMcsEpGEpEpDIndex }
::= { mscMcsMgrDprsMcsEpGEpEpDRowStatusTable 1 }

MscMcsMgrDprsMcsEpGEpEpDRowStatusEntry ::= SEQUENCE {
   mscMcsMgrDprsMcsEpGEpEpDRowStatus
      RowStatus,
   mscMcsMgrDprsMcsEpGEpEpDComponentName
      DisplayString,
   mscMcsMgrDprsMcsEpGEpEpDStorageType
      StorageType,
   mscMcsMgrDprsMcsEpGEpEpDIndex
      NonReplicated }

mscMcsMgrDprsMcsEpGEpEpDRowStatus OBJECT-TYPE
   SYNTAX     RowStatus 
   ACCESS     read-only
   STATUS     mandatory
   DESCRIPTION
     "This variable is used as the basis for SNMP naming of
      mscMcsMgrDprsMcsEpGEpEpD components.
      These components cannot be added nor deleted."
::= { mscMcsMgrDprsMcsEpGEpEpDRowStatusEntry 1 }

mscMcsMgrDprsMcsEpGEpEpDComponentName OBJECT-TYPE
   SYNTAX     DisplayString 
   ACCESS     read-only
   STATUS     mandatory
   DESCRIPTION
     "This variable provides the component's string name for
      use with the ASCII Console Interface"
::= { mscMcsMgrDprsMcsEpGEpEpDRowStatusEntry 2 }

mscMcsMgrDprsMcsEpGEpEpDStorageType OBJECT-TYPE
   SYNTAX     StorageType 
   ACCESS     read-only
   STATUS     mandatory
   DESCRIPTION
     "This variable represents the storage type value for the
      mscMcsMgrDprsMcsEpGEpEpD tables."
::= { mscMcsMgrDprsMcsEpGEpEpDRowStatusEntry 4 }

mscMcsMgrDprsMcsEpGEpEpDIndex OBJECT-TYPE
   SYNTAX     NonReplicated 
   ACCESS     not-accessible
   STATUS     mandatory
   DESCRIPTION
     "This variable represents the index for the mscMcsMgrDprsMcsEpGEpEpD tables."
::= { mscMcsMgrDprsMcsEpGEpEpDRowStatusEntry 10 }

mscMcsMgrDprsMcsEpGEpEpDProvTable OBJECT-TYPE
   SYNTAX     SEQUENCE OF MscMcsMgrDprsMcsEpGEpEpDProvEntry
   ACCESS     not-accessible
   STATUS     mandatory
   DESCRIPTION
     "This group contains the parameters used to establish the transport 
      connection for this Ep."
::= { mscMcsMgrDprsMcsEpGEpEpD 10 }

mscMcsMgrDprsMcsEpGEpEpDProvEntry OBJECT-TYPE
   SYNTAX     MscMcsMgrDprsMcsEpGEpEpDProvEntry
   ACCESS     not-accessible
   STATUS     mandatory
   DESCRIPTION
     "An entry in the mscMcsMgrDprsMcsEpGEpEpDProvTable."
   INDEX {
      mscMcsMgrIndex,
      mscMcsMgrDprsMcsEpGIndex,
      mscMcsMgrDprsMcsEpGEpIndex,
      mscMcsMgrDprsMcsEpGEpEpDIndex }
::= { mscMcsMgrDprsMcsEpGEpEpDProvTable 1 }

MscMcsMgrDprsMcsEpGEpEpDProvEntry ::= SEQUENCE {
   mscMcsMgrDprsMcsEpGEpEpDBandwidth
      Unsigned32,
   mscMcsMgrDprsMcsEpGEpEpDConnectionTransferPriority
      Unsigned32,
   mscMcsMgrDprsMcsEpGEpEpDTransportConnectionPreference
      INTEGER,
   mscMcsMgrDprsMcsEpGEpEpDProfile
      Link,
   mscMcsMgrDprsMcsEpGEpEpDPorsManualPath
      Link,
   mscMcsMgrDprsMcsEpGEpEpDSupportedTransferPriorities
      OCTET STRING,
   mscMcsMgrDprsMcsEpGEpEpDForwardBandwidth
      Unsigned32,
   mscMcsMgrDprsMcsEpGEpEpDReverseBandwidth
      Unsigned32 }

mscMcsMgrDprsMcsEpGEpEpDBandwidth OBJECT-TYPE
   SYNTAX     Unsigned32 (56000..155000000)
   ACCESS     read-write
   STATUS     obsolete
   DESCRIPTION
     "This attribute specifies the bandwidth at which the transport 
      connection agrees to transfer information. 
      A conservative value would be the sum of the committed 
      information rates (CIRs) of all individual Frame Relay DLCIs 
      multiplexed on the transport connection.
      For ATM connections, the value is converted to an equivalent Peak 
      Cell Rate (PCR01) for all cells with Cell Loss Priority (CLP), CLP 
      = 0 and CLP = 1. 
      Note that the conversion to an equivalent cell rate for ATM 
      connections may result in some wasted bandwidth depending on the 
      average frame size to cell ratio.
      This attribute is obosolete and on a migration the value that is 
      provisioned for this attribute is copied to both the 
      forwardBandwidth and reverseBandwidth attributes creating a 
      switched path with symmetrical bandwidth."
   DEFVAL     { 512000 }
::= { mscMcsMgrDprsMcsEpGEpEpDProvEntry 1 }

mscMcsMgrDprsMcsEpGEpEpDConnectionTransferPriority OBJECT-TYPE
   SYNTAX     Unsigned32 (0..15)
   ACCESS     read-write
   STATUS     mandatory
   DESCRIPTION
     "This attribute specifies the transfer priority used to establish the 
      transport connection. It references the ModuleData Frs AtmNet Tpm 
      to determine the ATM service category to be used by the transport 
      connection.
      This attribute is used by the Ep solely for the purpose of 
      determining the service category that should be used to establish the 
      transport connection."
::= { mscMcsMgrDprsMcsEpGEpEpDProvEntry 2 }

mscMcsMgrDprsMcsEpGEpEpDTransportConnectionPreference OBJECT-TYPE
   SYNTAX     INTEGER  {
                 atmOnly(1),
                 porsOnly(3) }
   ACCESS     read-write
   STATUS     mandatory
   DESCRIPTION
     "This attribute specifies the preference of routing system to be used 
      to set up the transport connection. 
      If a value of atmOnly is specified, attempts to set up the transport 
      connection will be made using only the ATM routing system's 
      network facilities.
      If a value of porsOnly is specified, attempts to set up the transport 
      connection will be made using only PORS network facilities."
   DEFVAL     { porsOnly }
::= { mscMcsMgrDprsMcsEpGEpEpDProvEntry 3 }

mscMcsMgrDprsMcsEpGEpEpDProfile OBJECT-TYPE
   SYNTAX     Link 
   ACCESS     read-write
   STATUS     mandatory
   DESCRIPTION
     "This attribute specifies the PORS profile to be used for the transport 
      connection when it is set up using PORS. This attribute is ignored if 
      the transportConnectionPreference is atmOnly."
::= { mscMcsMgrDprsMcsEpGEpEpDProvEntry 4 }

mscMcsMgrDprsMcsEpGEpEpDPorsManualPath OBJECT-TYPE
   SYNTAX     Link 
   ACCESS     read-write
   STATUS     mandatory
   DESCRIPTION
     "This attribute specifies the PORS manual path to be used for the 
      transport connection when it is set up using PORS. The manual path 
      that this attribute is linked to specifies the sequence of Trunks that 
      will be used when PORS chooses and instantiates the route. 
      This attribute is ignored if the transportConnectionPreference is 
      atmOnly."
::= { mscMcsMgrDprsMcsEpGEpEpDProvEntry 5 }

mscMcsMgrDprsMcsEpGEpEpDSupportedTransferPriorities OBJECT-TYPE
   SYNTAX     OCTET STRING (SIZE (2))
   ACCESS     read-write
   STATUS     mandatory
   DESCRIPTION
     "This attribute specifies the Frame Relay transfer priorities that are 
      supported through the transport connection. It is used to determine 
      which EndPoint within a DprsMcsEndPointGroup is to multiplex a 
      particular Frame Relay DLCI.
      A particular transfer priority can be specified on at most one 
      EndPoint within a DprsMcsEndPointGroup.

      Description of bits:
      n0(0)
      n1(1)
      n2(2)
      n3(3)
      n4(4)
      n5(5)
      n6(6)
      n7(7)
      n8(8)
      n9(9)
      n10(10)
      n11(11)
      n12(12)
      n13(13)
      n14(14)
      n15(15)"
   DEFVAL     { '8000'H }
::= { mscMcsMgrDprsMcsEpGEpEpDProvEntry 6 }

mscMcsMgrDprsMcsEpGEpEpDForwardBandwidth OBJECT-TYPE
   SYNTAX     Unsigned32 (56000..155000000)
   ACCESS     read-write
   STATUS     mandatory
   DESCRIPTION
     "This attribute specifies the bandwidth this End Point will request 
      when setting up a transfer connection which the transport in the 
      forward (from the originating to the terminating End Point) 
      direction. 
      A conservative value would be the sum of the committed 
      information rates (CIRs) of all individual Frame Relay DLCIs 
      multiplexed on the transport connection.
      For ATM connections, the value is converted to an equivalent Peak 
      Cell Rate (PCR01) for all cells with Cell Loss Priority (CLP), CLP 
      = 0 and CLP = 1. 
      Note that the conversion to an equivalent cell rate for ATM 
      connections may result in some wasted bandwidth depending on the 
      average frame size to cell ratio."
   DEFVAL     { 512000 }
::= { mscMcsMgrDprsMcsEpGEpEpDProvEntry 7 }

mscMcsMgrDprsMcsEpGEpEpDReverseBandwidth OBJECT-TYPE
   SYNTAX     Unsigned32 (56000..155000000 | 155000002)
   ACCESS     read-write
   STATUS     mandatory
   DESCRIPTION
     "This attribute specifies the bandwidth this End Point will request 
      when setting up a transfer connection which the transport in the 
      reverse (from the terminating to the originating End Point) 
      direction. 
      A conservative value would be the sum of the committed 
      information rates (CIRs) of all individual Frame Relay DLCIs 
      multiplexed on the transport connection.
      For ATM connections, the value is converted to an equivalent Peak 
      Cell Rate (PCR01) for all cells with Cell Loss Priority (CLP), CLP 
      = 0 and CLP = 1. 
      Note that the conversion to an equivalent cell rate for ATM 
      connections may result in some wasted bandwidth depending on the 
      average frame size to cell ratio.

      VALUES (

      155000002 = sameAsForward

      )"
   DEFVAL     { 155000002 }
::= { mscMcsMgrDprsMcsEpGEpEpDProvEntry 8 }


-- An AtmConnection component is created for each ATM connection 
-- established by an application. It shows where the data traffic for this 
-- connection is directed.

mscMcsMgrDprsMcsEpGEpAtmCon OBJECT IDENTIFIER ::= { mscMcsMgrDprsMcsEpGEp 3 }



mscMcsMgrDprsMcsEpGEpAtmConRowStatusTable OBJECT-TYPE
   SYNTAX     SEQUENCE OF MscMcsMgrDprsMcsEpGEpAtmConRowStatusEntry
   ACCESS     not-accessible
   STATUS     mandatory
   DESCRIPTION
     "This entry controls the addition and deletion of 
      mscMcsMgrDprsMcsEpGEpAtmCon components."
::= { mscMcsMgrDprsMcsEpGEpAtmCon 1 }

mscMcsMgrDprsMcsEpGEpAtmConRowStatusEntry OBJECT-TYPE
   SYNTAX     MscMcsMgrDprsMcsEpGEpAtmConRowStatusEntry
   ACCESS     not-accessible
   STATUS     mandatory
   DESCRIPTION
     "A single entry in the table represents a single 
      mscMcsMgrDprsMcsEpGEpAtmCon component."
   INDEX {
      mscMcsMgrIndex,
      mscMcsMgrDprsMcsEpGIndex,
      mscMcsMgrDprsMcsEpGEpIndex,
      mscMcsMgrDprsMcsEpGEpAtmConIndex }
::= { mscMcsMgrDprsMcsEpGEpAtmConRowStatusTable 1 }

MscMcsMgrDprsMcsEpGEpAtmConRowStatusEntry ::= SEQUENCE {
   mscMcsMgrDprsMcsEpGEpAtmConRowStatus
      RowStatus,
   mscMcsMgrDprsMcsEpGEpAtmConComponentName
      DisplayString,
   mscMcsMgrDprsMcsEpGEpAtmConStorageType
      StorageType,
   mscMcsMgrDprsMcsEpGEpAtmConIndex
      NonReplicated }

mscMcsMgrDprsMcsEpGEpAtmConRowStatus OBJECT-TYPE
   SYNTAX     RowStatus 
   ACCESS     read-only
   STATUS     mandatory
   DESCRIPTION
     "This variable is used as the basis for SNMP naming of
      mscMcsMgrDprsMcsEpGEpAtmCon components.
      These components cannot be added nor deleted."
::= { mscMcsMgrDprsMcsEpGEpAtmConRowStatusEntry 1 }

mscMcsMgrDprsMcsEpGEpAtmConComponentName OBJECT-TYPE
   SYNTAX     DisplayString 
   ACCESS     read-only
   STATUS     mandatory
   DESCRIPTION
     "This variable provides the component's string name for
      use with the ASCII Console Interface"
::= { mscMcsMgrDprsMcsEpGEpAtmConRowStatusEntry 2 }

mscMcsMgrDprsMcsEpGEpAtmConStorageType OBJECT-TYPE
   SYNTAX     StorageType 
   ACCESS     read-only
   STATUS     mandatory
   DESCRIPTION
     "This variable represents the storage type value for the
      mscMcsMgrDprsMcsEpGEpAtmCon tables."
::= { mscMcsMgrDprsMcsEpGEpAtmConRowStatusEntry 4 }

mscMcsMgrDprsMcsEpGEpAtmConIndex OBJECT-TYPE
   SYNTAX     NonReplicated 
   ACCESS     not-accessible
   STATUS     mandatory
   DESCRIPTION
     "This variable represents the index for the mscMcsMgrDprsMcsEpGEpAtmCon tables."
::= { mscMcsMgrDprsMcsEpGEpAtmConRowStatusEntry 10 }

mscMcsMgrDprsMcsEpGEpAtmConOperTable OBJECT-TYPE
   SYNTAX     SEQUENCE OF MscMcsMgrDprsMcsEpGEpAtmConOperEntry
   ACCESS     not-accessible
   STATUS     mandatory
   DESCRIPTION
     "This attribute group contains the operational attributes for the 
      NapAtmConnection component."
::= { mscMcsMgrDprsMcsEpGEpAtmCon 10 }

mscMcsMgrDprsMcsEpGEpAtmConOperEntry OBJECT-TYPE
   SYNTAX     MscMcsMgrDprsMcsEpGEpAtmConOperEntry
   ACCESS     not-accessible
   STATUS     mandatory
   DESCRIPTION
     "An entry in the mscMcsMgrDprsMcsEpGEpAtmConOperTable."
   INDEX {
      mscMcsMgrIndex,
      mscMcsMgrDprsMcsEpGIndex,
      mscMcsMgrDprsMcsEpGEpIndex,
      mscMcsMgrDprsMcsEpGEpAtmConIndex }
::= { mscMcsMgrDprsMcsEpGEpAtmConOperTable 1 }

MscMcsMgrDprsMcsEpGEpAtmConOperEntry ::= SEQUENCE {
   mscMcsMgrDprsMcsEpGEpAtmConNextHop
      RowPointer }

mscMcsMgrDprsMcsEpGEpAtmConNextHop OBJECT-TYPE
   SYNTAX     RowPointer 
   ACCESS     read-only
   STATUS     mandatory
   DESCRIPTION
     "This attribute shows the component name of the AtmIf Vcc Ep or 
      AtmCon component to which this switched connection is 
      established."
::= { mscMcsMgrDprsMcsEpGEpAtmConOperEntry 1 }


-- ...Lc
-- This component contains all of the operation attributes for a Path 
-- Oriented Logical Connection.

mscMcsMgrDprsMcsEpGEpLCo OBJECT IDENTIFIER ::= { mscMcsMgrDprsMcsEpGEp 4 }



mscMcsMgrDprsMcsEpGEpLCoRowStatusTable OBJECT-TYPE
   SYNTAX     SEQUENCE OF MscMcsMgrDprsMcsEpGEpLCoRowStatusEntry
   ACCESS     not-accessible
   STATUS     mandatory
   DESCRIPTION
     "This entry controls the addition and deletion of 
      mscMcsMgrDprsMcsEpGEpLCo components."
::= { mscMcsMgrDprsMcsEpGEpLCo 1 }

mscMcsMgrDprsMcsEpGEpLCoRowStatusEntry OBJECT-TYPE
   SYNTAX     MscMcsMgrDprsMcsEpGEpLCoRowStatusEntry
   ACCESS     not-accessible
   STATUS     mandatory
   DESCRIPTION
     "A single entry in the table represents a single 
      mscMcsMgrDprsMcsEpGEpLCo component."
   INDEX {
      mscMcsMgrIndex,
      mscMcsMgrDprsMcsEpGIndex,
      mscMcsMgrDprsMcsEpGEpIndex,
      mscMcsMgrDprsMcsEpGEpLCoIndex }
::= { mscMcsMgrDprsMcsEpGEpLCoRowStatusTable 1 }

MscMcsMgrDprsMcsEpGEpLCoRowStatusEntry ::= SEQUENCE {
   mscMcsMgrDprsMcsEpGEpLCoRowStatus
      RowStatus,
   mscMcsMgrDprsMcsEpGEpLCoComponentName
      DisplayString,
   mscMcsMgrDprsMcsEpGEpLCoStorageType
      StorageType,
   mscMcsMgrDprsMcsEpGEpLCoIndex
      NonReplicated }

mscMcsMgrDprsMcsEpGEpLCoRowStatus OBJECT-TYPE
   SYNTAX     RowStatus 
   ACCESS     read-only
   STATUS     mandatory
   DESCRIPTION
     "This variable is used as the basis for SNMP naming of
      mscMcsMgrDprsMcsEpGEpLCo components.
      These components cannot be added nor deleted."
::= { mscMcsMgrDprsMcsEpGEpLCoRowStatusEntry 1 }

mscMcsMgrDprsMcsEpGEpLCoComponentName OBJECT-TYPE
   SYNTAX     DisplayString 
   ACCESS     read-only
   STATUS     mandatory
   DESCRIPTION
     "This variable provides the component's string name for
      use with the ASCII Console Interface"
::= { mscMcsMgrDprsMcsEpGEpLCoRowStatusEntry 2 }

mscMcsMgrDprsMcsEpGEpLCoStorageType OBJECT-TYPE
   SYNTAX     StorageType 
   ACCESS     read-only
   STATUS     mandatory
   DESCRIPTION
     "This variable represents the storage type value for the
      mscMcsMgrDprsMcsEpGEpLCo tables."
::= { mscMcsMgrDprsMcsEpGEpLCoRowStatusEntry 4 }

mscMcsMgrDprsMcsEpGEpLCoIndex OBJECT-TYPE
   SYNTAX     NonReplicated 
   ACCESS     not-accessible
   STATUS     mandatory
   DESCRIPTION
     "This variable represents the index for the mscMcsMgrDprsMcsEpGEpLCo tables."
::= { mscMcsMgrDprsMcsEpGEpLCoRowStatusEntry 10 }

mscMcsMgrDprsMcsEpGEpLCoPathDataTable OBJECT-TYPE
   SYNTAX     SEQUENCE OF MscMcsMgrDprsMcsEpGEpLCoPathDataEntry
   ACCESS     not-accessible
   STATUS     mandatory
   DESCRIPTION
     "This group contains all operational attributes for the path oriented 
      LCo."
::= { mscMcsMgrDprsMcsEpGEpLCo 10 }

mscMcsMgrDprsMcsEpGEpLCoPathDataEntry OBJECT-TYPE
   SYNTAX     MscMcsMgrDprsMcsEpGEpLCoPathDataEntry
   ACCESS     not-accessible
   STATUS     mandatory
   DESCRIPTION
     "An entry in the mscMcsMgrDprsMcsEpGEpLCoPathDataTable."
   INDEX {
      mscMcsMgrIndex,
      mscMcsMgrDprsMcsEpGIndex,
      mscMcsMgrDprsMcsEpGEpIndex,
      mscMcsMgrDprsMcsEpGEpLCoIndex }
::= { mscMcsMgrDprsMcsEpGEpLCoPathDataTable 1 }

MscMcsMgrDprsMcsEpGEpLCoPathDataEntry ::= SEQUENCE {
   mscMcsMgrDprsMcsEpGEpLCoState
      INTEGER,
   mscMcsMgrDprsMcsEpGEpLCoOverrideRemoteName
      AsciiString,
   mscMcsMgrDprsMcsEpGEpLCoEnd
      INTEGER,
   mscMcsMgrDprsMcsEpGEpLCoCostMetric
      Unsigned32,
   mscMcsMgrDprsMcsEpGEpLCoDelayMetric
      Unsigned32,
   mscMcsMgrDprsMcsEpGEpLCoRoundTripDelay
      Unsigned32,
   mscMcsMgrDprsMcsEpGEpLCoSetupPriority
      Unsigned32,
   mscMcsMgrDprsMcsEpGEpLCoHoldingPriority
      Unsigned32,
   mscMcsMgrDprsMcsEpGEpLCoRequiredTxBandwidth
      Gauge32,
   mscMcsMgrDprsMcsEpGEpLCoRequiredRxBandwidth
      Gauge32,
   mscMcsMgrDprsMcsEpGEpLCoRequiredTrafficType
      INTEGER,
   mscMcsMgrDprsMcsEpGEpLCoPermittedTrunkTypes
      OCTET STRING,
   mscMcsMgrDprsMcsEpGEpLCoRequiredSecurity
      Unsigned32,
   mscMcsMgrDprsMcsEpGEpLCoRequiredCustomerParameter
      Unsigned32,
   mscMcsMgrDprsMcsEpGEpLCoEmissionPriority
      Unsigned32,
   mscMcsMgrDprsMcsEpGEpLCoDiscardPriority
      Unsigned32,
   mscMcsMgrDprsMcsEpGEpLCoPathType
      INTEGER,
   mscMcsMgrDprsMcsEpGEpLCoRetryCount
      Unsigned32,
   mscMcsMgrDprsMcsEpGEpLCoPathFailureCount
      Unsigned32,
   mscMcsMgrDprsMcsEpGEpLCoReasonForNoRoute
      INTEGER,
   mscMcsMgrDprsMcsEpGEpLCoLastTearDownReason
      INTEGER,
   mscMcsMgrDprsMcsEpGEpLCoPathFailureAction
      INTEGER,
   mscMcsMgrDprsMcsEpGEpLCoBumpPreference
      INTEGER,
   mscMcsMgrDprsMcsEpGEpLCoOptimization
      INTEGER,
   mscMcsMgrDprsMcsEpGEpLCoPathUpDateTime
      EnterpriseDateAndTime }

mscMcsMgrDprsMcsEpGEpLCoState OBJECT-TYPE
   SYNTAX     INTEGER  {
                 pathDown(0),
                 selectingRoute(1),
                 connecting(2),
                 pathUp(3),
                 pathDownRetrying(4) }
   ACCESS     read-only
   STATUS     mandatory
   DESCRIPTION
     "This attribute reflects the current state of the connection. The 
      pathDown state indicates a connection that has no remote end 
      provisioned or the application has not yet signalled for a path. The 
      selectingRoute state occurs when a request has been sent to route 
      selector and it has not yet responded. The connectingState occurs 
      while a path is being established. The pathUp state is the normal 
      operational state of a path. The pathDownRetrying state indicates a 
      path that attempted route selection but received no route and is now 
      waiting to retry route selection again."
::= { mscMcsMgrDprsMcsEpGEpLCoPathDataEntry 1 }

mscMcsMgrDprsMcsEpGEpLCoOverrideRemoteName OBJECT-TYPE
   SYNTAX     AsciiString (SIZE (0..40))
   ACCESS     read-write
   STATUS     mandatory
   DESCRIPTION
     "If set and the current PLC remoteName is blank this remoteName 
      will override the blank PLC remoteName. Usually you would set 
      this attribute and then lock/unlock the service component which 
      will result in this new overrideRemoteName being used as if it had 
      been provisioned into the PLC remoteName. The advantage of this 
      attribute is that the connection's remoteName can be changed 
      immediately without having to 'activate prov' but the disadvantage 
      is that the overrideRemoteName is not permanent and if the card or 
      switch is reset the override will be lost."
::= { mscMcsMgrDprsMcsEpGEpLCoPathDataEntry 2 }

mscMcsMgrDprsMcsEpGEpLCoEnd OBJECT-TYPE
   SYNTAX     INTEGER  {
                 calling(0),
                 called(1) }
   ACCESS     read-only
   STATUS     mandatory
   DESCRIPTION
     "This attribute identifies whether this is the calling or called end of 
      the path."
::= { mscMcsMgrDprsMcsEpGEpLCoPathDataEntry 3 }

mscMcsMgrDprsMcsEpGEpLCoCostMetric OBJECT-TYPE
   SYNTAX     Unsigned32 (0..65535)
   ACCESS     read-only
   STATUS     mandatory
   DESCRIPTION
     "This attribute gives the route's total cost metric. It is calculated as 
      the sum of the cost metric of all trunks in the path at the time the 
      connection was established. The cost metric of a trunk is defined by 
      the trunkCost attribute of the Trunk component. The costMetric for 
      an LCo that is originated and terminated on the same module is 0."
::= { mscMcsMgrDprsMcsEpGEpLCoPathDataEntry 4 }

mscMcsMgrDprsMcsEpGEpLCoDelayMetric OBJECT-TYPE
   SYNTAX     Unsigned32 (0..100000)
   ACCESS     read-only
   STATUS     mandatory
   DESCRIPTION
     "This attribute gives the total delay of the route as the one way delay 
      for a 512 byte packet. It is calculated as the sum of the delays of all 
      trunks in the path stored in topology at the time the connection was 
      established. The delay for an LCo that is originated and terminated 
      on the same module is 0."
::= { mscMcsMgrDprsMcsEpGEpLCoPathDataEntry 5 }

mscMcsMgrDprsMcsEpGEpLCoRoundTripDelay OBJECT-TYPE
   SYNTAX     Unsigned32 (0..200000)
   ACCESS     read-only
   STATUS     mandatory
   DESCRIPTION
     "This attribute contains the time taken for a packet (cell) of 44 bytes 
      to be transmitted to the remote LCo and return to this LCo. The 
      number reported is given in milliseconds to the nearest millisecond. 
      A value of one millisecond is reported if the time is less than 1 
      millisecond even though the delay may be less than 1 Millisecond 
      when the LCo is originated and terminated on the same module."
::= { mscMcsMgrDprsMcsEpGEpLCoPathDataEntry 6 }

mscMcsMgrDprsMcsEpGEpLCoSetupPriority OBJECT-TYPE
   SYNTAX     Unsigned32 (0..4)
   ACCESS     read-only
   STATUS     mandatory
   DESCRIPTION
     "This attribute gives the priority at which the current path is 
      established. Zero is the highest priority and four is the lowest. The 
      holdingPriority, a complementary attribute of this component, 
      indicates the priority a path maintains once it is established."
::= { mscMcsMgrDprsMcsEpGEpLCoPathDataEntry 7 }

mscMcsMgrDprsMcsEpGEpLCoHoldingPriority OBJECT-TYPE
   SYNTAX     Unsigned32 (0..4)
   ACCESS     read-only
   STATUS     mandatory
   DESCRIPTION
     "This attribute gives the priority at which a path holds its current 
      path once the path is established. Zero is the highest priority and 
      four is the lowest. The setupPriority, a complementary attribute, 
      indicates the priority of a path at establishment time."
::= { mscMcsMgrDprsMcsEpGEpLCoPathDataEntry 8 }

mscMcsMgrDprsMcsEpGEpLCoRequiredTxBandwidth OBJECT-TYPE
   SYNTAX     Gauge32 (0..4294967295)
   ACCESS     read-only
   STATUS     mandatory
   DESCRIPTION
     "This attribute gives the actual bandwidth (in bits per second) 
      reserved by this path on each of the trunks of its route. This attribute 
      represents the bandwidth for traffic outgoing to the remote end 
      point. The originating end of the connection determines this value."
::= { mscMcsMgrDprsMcsEpGEpLCoPathDataEntry 9 }

mscMcsMgrDprsMcsEpGEpLCoRequiredRxBandwidth OBJECT-TYPE
   SYNTAX     Gauge32 (0..4294967295)
   ACCESS     read-only
   STATUS     mandatory
   DESCRIPTION
     "This attribute gives the actual bandwidth (in bits per second) 
      reserved by this path on each of trunks of its route. This attribute 
      represents the bandwidth for traffic incoming from the remote end 
      point. The originating end of the connection determines this value"
::= { mscMcsMgrDprsMcsEpGEpLCoPathDataEntry 10 }

mscMcsMgrDprsMcsEpGEpLCoRequiredTrafficType OBJECT-TYPE
   SYNTAX     INTEGER  {
                 voice(0),
                 data(1),
                 video(2),
                 trafficType1(3),
                 trafficType2(4),
                 trafficType3(5),
                 trafficType4(6),
                 trafficType5(7) }
   ACCESS     read-only
   STATUS     mandatory
   DESCRIPTION
     "This operational attribute indicates the type of traffic transmitted 
      over the path. There are eight possible traffic types, and the path can 
      transmit only one of them. The originating end of the connection 
      determines the type. These are arbitrary designations for traffic 
      type. The voice, data and video traffic types are defined, and five 
      other arbitrary traffic types can be defined by the network 
      administration. This attribute is used in the route selection process 
      to restrict the route to trunks that support this traffic type. The 
      supportedTrafficType trunk attribute lists all the types of traffic 
      allowed on the trunk. For example, if requiredTrafficType is 
      specified as trafficType1 then only trunks that include trafficType1 
      in supportedTrafficType, will be candidates for this connection."
::= { mscMcsMgrDprsMcsEpGEpLCoPathDataEntry 11 }

mscMcsMgrDprsMcsEpGEpLCoPermittedTrunkTypes OBJECT-TYPE
   SYNTAX     OCTET STRING (SIZE (1))
   ACCESS     read-only
   STATUS     mandatory
   DESCRIPTION
     "This operational attribute lists up to eight types of trunk that can be 
      used on the route. The originating end of the connection determines 
      the types. The terrestrial and satellite trunk types have been 
      defined, leaving six remaining arbitrary types that can be defined by 
      the network administration. The trunk's type is indicated in the 
      trunkType attribute of the Trunk component. When selecting a 
      route, PORS only chooses trunks whose trunkType are in the 
      permittedTrunkTypes for the path.

      Description of bits:
      terrestrial(0)
      satellite(1)
      trunkType1(2)
      trunkType2(3)
      trunkType3(4)
      trunkType4(5)
      trunkType5(6)
      trunkType6(7)"
::= { mscMcsMgrDprsMcsEpGEpLCoPathDataEntry 12 }

mscMcsMgrDprsMcsEpGEpLCoRequiredSecurity OBJECT-TYPE
   SYNTAX     Unsigned32 (0..7)
   ACCESS     read-only
   STATUS     mandatory
   DESCRIPTION
     "This attribute indicates the required minimum level of security of 
      the trunks on the route. Zero represents the most secure and seven 
      represents the least secure. The trunk's security is indicated by the 
      trunkSecurity attribute of the Trunk component, and has values 
      identical in range and meaning to the requiredSecurity attribute. 
      PORS ensures that any route selected does not contain a trunk 
      whose trunkSecurity attribute is numerically greater than the 
      requiredSecurity."
::= { mscMcsMgrDprsMcsEpGEpLCoPathDataEntry 13 }

mscMcsMgrDprsMcsEpGEpLCoRequiredCustomerParameter OBJECT-TYPE
   SYNTAX     Unsigned32 (0..7)
   ACCESS     read-only
   STATUS     mandatory
   DESCRIPTION
     "This attribute indicates the allowed customer defined parameter of 
      the trunks on the route.The originating end of the connection 
      determines the customer defined parameter. Its value, a number 
      from zero to seven, is chosen by a network administration to have a 
      meaning specific to their network, thus allowing them to customize 
      the use of their trunks. A complementary trunk attribute, 
      customerParameter, also has a value from zero to seven. The route 
      selection process does not consider trunks whose 
      customerParameter is greater than the requiredCustomerParameter 
      of the path."
::= { mscMcsMgrDprsMcsEpGEpLCoPathDataEntry 14 }

mscMcsMgrDprsMcsEpGEpLCoEmissionPriority OBJECT-TYPE
   SYNTAX     Unsigned32 (0..2)
   ACCESS     read-only
   STATUS     mandatory
   DESCRIPTION
     "This attribute indicates the urgency with which packets on the path 
      are emitted by the trunks on the route. The originating end of the 
      connection selects the emissionPriority. EmissionPriority of zero 
      indicates the highest emission priority, while two indicates the 
      lowest emission priority. Packets with a higher emissionPriority (or 
      numerically less) are serviced and sent out before the packets of 
      lower emissionPriority (or numerically higher)."
::= { mscMcsMgrDprsMcsEpGEpLCoPathDataEntry 15 }

mscMcsMgrDprsMcsEpGEpLCoDiscardPriority OBJECT-TYPE
   SYNTAX     Unsigned32 (1..3)
   ACCESS     read-only
   STATUS     mandatory
   DESCRIPTION
     "This attribute indicates the importance of the packets on the 
      path.The originating end of the connection sets discardPriority. One 
      is used for paths carrying the most important traffic, and three is 
      used for paths carrying the least important traffic. Packets with 
      lower discardPriority(numerically lower) are discarded after 
      packets with a higher discardPriority(numerically higher)."
::= { mscMcsMgrDprsMcsEpGEpLCoPathDataEntry 16 }

mscMcsMgrDprsMcsEpGEpLCoPathType OBJECT-TYPE
   SYNTAX     INTEGER  {
                 normal(0),
                 manual(1),
                 forced(2) }
   ACCESS     read-only
   STATUS     mandatory
   DESCRIPTION
     "This attribute indicates whether the path for this PLC was 
      determined automatically or by static provisioning. Normal 
      pathTypes are selected automatically by Route Selector.The other 
      pathTypes are both manual pathTypes where the operator must 
      specify, through provisioning, a static route termed the manualPath. 
      A manual pathType connection is nearly identical to a normal path 
      type connection with the exception that the route is pre-provisioned. 
      For a manual pathType, bandwidth reservations are respected along 
      the path exactly as in a normal path. The last type, the forced 
      pathType, is also a manual path but regardless of the bandwidth 
      available the route is granted provided the trunks are operational 
      and there are sufficient Logical Channels (LChs).
      
      The forced pathType could result in over committing the reserved 
      bandwidth allowed on a trunk. A better way to achieve the effects of 
      a forced pathType is to use a manual pathType with setupPriority = 
      0 and holdingPriority = 0. In this manner the path will reserve 
      correct bandwidth and it will bump other paths if required while not 
      being bumped itself."
::= { mscMcsMgrDprsMcsEpGEpLCoPathDataEntry 17 }

mscMcsMgrDprsMcsEpGEpLCoRetryCount OBJECT-TYPE
   SYNTAX     Unsigned32 (0..255)
   ACCESS     read-only
   STATUS     mandatory
   DESCRIPTION
     "This attribute is the count of the number of times the path chosen 
      during route selection could not be instantiated. This count should 
      be three or below if the network is performing adequately. A high 
      value indicates that the route selection is often performed using an 
      out-of-date view of available network bandwidth and/or topology.
      This attribute will only increase at the calling end of the connection.
      This attribute is reset each time a path reconnects and stops 
      counting when it reaches its maximum value."
::= { mscMcsMgrDprsMcsEpGEpLCoPathDataEntry 18 }

mscMcsMgrDprsMcsEpGEpLCoPathFailureCount OBJECT-TYPE
   SYNTAX     Unsigned32 (0..65535)
   ACCESS     read-only
   STATUS     mandatory
   DESCRIPTION
     "This attribute is the count of the number of times the path has 
      successfully connected. It is set to zero the first time the path is up. 
      If a path fails anytime after connecting this count will be 
      incremented when the path is up again. Failed route requests do not 
      count in this statistic. See retryCount above. This attribute stops 
      counting at its maximum value."
::= { mscMcsMgrDprsMcsEpGEpLCoPathDataEntry 19 }

mscMcsMgrDprsMcsEpGEpLCoReasonForNoRoute OBJECT-TYPE
   SYNTAX     INTEGER  {
                 none(0),
                 destinationNameTooLong(1),
                 destinationNotSpecified(2),
                 unknownDestinationName(3),
                 incorrectDestination(4),
                 incorrectDestinationEndPoint(5),
                 unknownSource(6),
                 unknownDestination(7),
                 sameNode(8),
                 routeCostTooMuch(9),
                 routesDelayTooLong(10),
                 attributesNotMet(11),
                 anError(12),
                 attributeProfileProblem(13),
                 manualPathIndexProblem(14) }
   ACCESS     read-only
   STATUS     mandatory
   DESCRIPTION
     "This attribute is the route selection's reasonForNoRoute and 
      provides a brief reason for which a route was not selected. The 
      reasons are essentially self-explanatory. Perhaps two reasons for no 
      route require some explanation. The reason 
      unknownRemoteNodeName is issued when the remote node name 
      is not in the topological database. The reason plcAttributesNotMet 
      is issued when there is no network connectivity at a level specified 
      by the PLC attributes. This reason is also issued when there is no 
      physical connectivity between two end nodes."
   DEFVAL     { none }
::= { mscMcsMgrDprsMcsEpGEpLCoPathDataEntry 20 }

mscMcsMgrDprsMcsEpGEpLCoLastTearDownReason OBJECT-TYPE
   SYNTAX     INTEGER  {
                 none(0),
                 normalShutDown(1),
                 insufficientTxLcOrBandwidth(2),
                 insufficientRxLcOrBandwidth(3),
                 trunkFailure(4),
                 trunkCardFailure(5),
                 operatorForced(6),
                 lostLcnClash(7),
                 networkCongestion(8),
                 trunkNotFound(9),
                 farEndNotFound(10),
                 wrongModuleReached(11),
                 farEndBusy(12),
                 callLoopedBack(13),
                 unknownReason(14),
                 farEndNotReady(15),
                 remoteNameMismatch(16),
                 serviceTypeMismatch(17),
                 reconnectFromFarEnd(18),
                 bumped(19),
                 accessCardFailure(20),
                 optimized(21),
                 overrideRemoteName(22),
                 trunkOrFarEndDidNotSupportMode(23) }
   ACCESS     read-only
   STATUS     mandatory
   DESCRIPTION
     "This attribute reflects the last tear down reason for a connection 
      (LCo). In many cases this displays the reason for a momentary 
      service interruption. This attribute applies to the last path failure 
      only. If a path is no longer up, this may give an indication to the 
      reason that the path has failed. In many cases an alarm will also be 
      generated with more specific information. The following is a brief 
      description of the reasons:
      none - This path has no information for the teardown this is typical 
      of a path provisioned with no remoteName that has not been up.
      normalShutDown - This path has gone down due to normal call 
      termination.
      insufficientTxLcOrBandwidth - At present there is either no 
      available bandwidth or logical channel numbers available on one or 
      more of the trunks for this path in the transmit direction.
      insufficientRxLcOrBandwidth - At present there is either no 
      available bandwidth or logical channel numbers available on one or 
      more of the trunks for this path in the receive direction.
      trunkFailure- A trunk on the path has failed or has gone down due 
      to a provisioning change of a critical attribute.
      trunkCardFailure- A trunk FP card has failed along the path.
      accessCardFailure- The FP on which the peer access service was 
      running has failed.
      operatorForced- The path has terminated due to the operator 
      locking a trunk along the path.
      lostLcnClash- The path has terminated because the PA's at both 
      ends of an intermediate trunk have allocated the same LC to 
      different calls. When this happens both calls must go down and then 
      try to come up again a fraction of a second later (effectively 
      ensuring that they will now be assigned different LC's). It is normal 
      to get the odd clash especially when the PA's usedLC is 
      approaching the PA's maxLC.
      networkCongestion - The path has failed due to control information 
      being lost and not recoverable.
      trunkNotFound - Occurs on a manual path usually. Check for 
      trunks not up or names provisioned incorrectly.
      farEndNotFound - The far end is not provisioned or is not up. 
      Check remote Name.
      wrongModuleReached - This may occur on a manual path. Check 
      provisioning for correct trunk and service names. For a normal 
      path, the network Topology may be changing check remoteName.
      farEndBusy - The far end has been reached but it is busy. Check 
      remoteName and remote end provisioning.
      callLoopedBack - This LCo is provisioned to call itself. Re-
      provision since this is invalid.
      unknownReason - The failure was not resolved.
      farEndNotReady - The remote end was reached but the connection 
      was refused due to the remote end not being enabled.
      remoteNameMismatch - The remote end has alarmed and rejected 
      this setup due to remoteName provisioning.
      serviceTypeMismatch - The remote Service Type does not match 
      this service type. Check provisioning.
      reconnectFromFarEnd - The remote end re-established this 
      connection. Check the remote end lastTearDownReason to 
      determine the real reason.
      bumped - Another call bumped this path from a trunk to get 
      bandwidth (or an LC) which it required to come up. This other path 
      had a higher setupPriority than this path's holdingPriority hence it 
      was allowed to steal the bandwidth (or LC) from this path.
      optimized - This call has been rerouted due to the optimization 
      feature. The call is still active this just indicates why the path 
      changed.
      trunkOrFarEndDidNotSupportMode - This call was unable to 
      complete because a mode required by the service was not supported 
      by one of the trunks the route went through or by the far end service 
      it connected to. Currently the only mode that this applies to is the 
      map/mux mode on TRUNK PA ATM component. Map mode was 
      required by the application (CES/FrAtm etc.) but was not available 
      on the TRUNK PA ATM component through which the call was 
      routed or the far end CES/FrAtm component did not specify the 
      same mode."
   DEFVAL     { none }
::= { mscMcsMgrDprsMcsEpGEpLCoPathDataEntry 21 }

mscMcsMgrDprsMcsEpGEpLCoPathFailureAction OBJECT-TYPE
   SYNTAX     INTEGER  {
                 disconnectConnection(0),
                 reRoutePath(1) }
   ACCESS     read-only
   STATUS     mandatory
   DESCRIPTION
     "This attribute displays whether the application is set to tolerate 
      momentary interruption of a path while a new path is selected. If 
      disconnectConnection is displayed, the application is informed as 
      soon as possible about a failure by disconnection. If the attribute 
      displays reRoutePath, the path may attempt an immediate reroute, 
      provided the failure is a recoverable failure. If rerouting fails the 
      application is informed of the failure. 
      With this option set to reRoutePath the LCo may wait up to 30 
      seconds before informing the service of complete disconnection in 
      order to allow both ends to attempt to reconnect. Note that if PLC 
      components are different at both ends only the calling end is 
      allowed to reconnect.
      
      All pathTypes respect this attribute. Also on a manualPath with 
      both ends provisioned with independent paths (at least with respect 
      to the failure) this option will have the desired effect that the path is 
      rerouted without complete disconnection at both ends"
::= { mscMcsMgrDprsMcsEpGEpLCoPathDataEntry 22 }

mscMcsMgrDprsMcsEpGEpLCoBumpPreference OBJECT-TYPE
   SYNTAX     INTEGER  {
                 bumpWhenNecessary(0),
                 bumpToObtainBestRoute(1) }
   ACCESS     read-only
   STATUS     mandatory
   DESCRIPTION
     "This attribute specifies when bumping will occur during route 
      selection process. Bumping may occur when necessary or always. It 
      will be necessary for a connection to bump if there is not enough 
      resources for the connection to be established and these resources 
      are occupied by a connection whose setupPriority is lower 
      (numerically higher) than the connection's setupPriority. A 
      connection may also always bump in order to obtain the best route."
::= { mscMcsMgrDprsMcsEpGEpLCoPathDataEntry 23 }

mscMcsMgrDprsMcsEpGEpLCoOptimization OBJECT-TYPE
   SYNTAX     INTEGER  {
                 disabled(0),
                 enabled(1) }
   ACCESS     read-only
   STATUS     mandatory
   DESCRIPTION
     "This attribute is used to specify whether this connection should 
      attempt to optimize its path when requested by the routing PORS 
      component. Every path is as optimal as it can be when it is 
      established, but as network traffic patterns and configurations 
      change this path may no longer be as optimal as it could be. The 
      PORS connection manager on a module requests circuits to 
      optimize at the optimization interval."
::= { mscMcsMgrDprsMcsEpGEpLCoPathDataEntry 24 }

mscMcsMgrDprsMcsEpGEpLCoPathUpDateTime OBJECT-TYPE
   SYNTAX     EnterpriseDateAndTime (SIZE (0 | 19))
   ACCESS     read-only
   STATUS     mandatory
   DESCRIPTION
     "This is the time stamp when the current path was established or 
      reestablished."
::= { mscMcsMgrDprsMcsEpGEpLCoPathDataEntry 25 }

mscMcsMgrDprsMcsEpGEpLCoStatsTable OBJECT-TYPE
   SYNTAX     SEQUENCE OF MscMcsMgrDprsMcsEpGEpLCoStatsEntry
   ACCESS     not-accessible
   STATUS     mandatory
   DESCRIPTION
     "This group contains the operational statistics attributes for the path 
      oriented LCo."
::= { mscMcsMgrDprsMcsEpGEpLCo 11 }

mscMcsMgrDprsMcsEpGEpLCoStatsEntry OBJECT-TYPE
   SYNTAX     MscMcsMgrDprsMcsEpGEpLCoStatsEntry
   ACCESS     not-accessible
   STATUS     mandatory
   DESCRIPTION
     "An entry in the mscMcsMgrDprsMcsEpGEpLCoStatsTable."
   INDEX {
      mscMcsMgrIndex,
      mscMcsMgrDprsMcsEpGIndex,
      mscMcsMgrDprsMcsEpGEpIndex,
      mscMcsMgrDprsMcsEpGEpLCoIndex }
::= { mscMcsMgrDprsMcsEpGEpLCoStatsTable 1 }

MscMcsMgrDprsMcsEpGEpLCoStatsEntry ::= SEQUENCE {
   mscMcsMgrDprsMcsEpGEpLCoPktsToNetwork
      PassportCounter64,
   mscMcsMgrDprsMcsEpGEpLCoBytesToNetwork
      PassportCounter64,
   mscMcsMgrDprsMcsEpGEpLCoPktsFromNetwork
      PassportCounter64,
   mscMcsMgrDprsMcsEpGEpLCoBytesFromNetwork
      PassportCounter64 }

mscMcsMgrDprsMcsEpGEpLCoPktsToNetwork OBJECT-TYPE
   SYNTAX     PassportCounter64 
   ACCESS     read-only
   STATUS     mandatory
   DESCRIPTION
     "This attribute counts the number of packets transmitted to the 
      network over this Logical Connection."
::= { mscMcsMgrDprsMcsEpGEpLCoStatsEntry 1 }

mscMcsMgrDprsMcsEpGEpLCoBytesToNetwork OBJECT-TYPE
   SYNTAX     PassportCounter64 
   ACCESS     read-only
   STATUS     mandatory
   DESCRIPTION
     "This attribute counts the number of bytes sent to the network over 
      this Logical Connection."
::= { mscMcsMgrDprsMcsEpGEpLCoStatsEntry 2 }

mscMcsMgrDprsMcsEpGEpLCoPktsFromNetwork OBJECT-TYPE
   SYNTAX     PassportCounter64 
   ACCESS     read-only
   STATUS     mandatory
   DESCRIPTION
     "This attribute counts the number of packets received from the 
      remote LCo via the network."
::= { mscMcsMgrDprsMcsEpGEpLCoStatsEntry 3 }

mscMcsMgrDprsMcsEpGEpLCoBytesFromNetwork OBJECT-TYPE
   SYNTAX     PassportCounter64 
   ACCESS     read-only
   STATUS     mandatory
   DESCRIPTION
     "This attribute counts the number of bytes received from the remote 
      LCo via the network."
::= { mscMcsMgrDprsMcsEpGEpLCoStatsEntry 4 }

mscMcsMgrDprsMcsEpGEpLCoPathTable OBJECT-TYPE
   SYNTAX     SEQUENCE OF MscMcsMgrDprsMcsEpGEpLCoPathEntry
   ACCESS     not-accessible
   STATUS     mandatory
   DESCRIPTION
     "This attribute contains the trunk component names over which the 
      path has been instantiated and the remote end point name 
      terminating the path."
::= { mscMcsMgrDprsMcsEpGEpLCo 264 }

mscMcsMgrDprsMcsEpGEpLCoPathEntry OBJECT-TYPE
   SYNTAX     MscMcsMgrDprsMcsEpGEpLCoPathEntry
   ACCESS     not-accessible
   STATUS     mandatory
   DESCRIPTION
     "An entry in the mscMcsMgrDprsMcsEpGEpLCoPathTable."
   INDEX {
      mscMcsMgrIndex,
      mscMcsMgrDprsMcsEpGIndex,
      mscMcsMgrDprsMcsEpGEpIndex,
      mscMcsMgrDprsMcsEpGEpLCoIndex,
      mscMcsMgrDprsMcsEpGEpLCoPathValue }
::= { mscMcsMgrDprsMcsEpGEpLCoPathTable 1 }

MscMcsMgrDprsMcsEpGEpLCoPathEntry ::= SEQUENCE {
   mscMcsMgrDprsMcsEpGEpLCoPathValue
      AsciiString }

mscMcsMgrDprsMcsEpGEpLCoPathValue OBJECT-TYPE
   SYNTAX     AsciiString (SIZE (0..40))
   ACCESS     read-only
   STATUS     mandatory
   DESCRIPTION
     "This variable represents both the value and the index for the
      mscMcsMgrDprsMcsEpGEpLCoPathTable."
::= { mscMcsMgrDprsMcsEpGEpLCoPathEntry 1 }


-- McsMgr DprsMcsEpG/n Ep/n CallAdmissionControl
-- This component indicates the operational values of the attributes 
-- specified by the McsMgr DprsMcsEpG/n Ep/n Cac Cacd 
-- component.
-- Provisioning this component under an EndPoint forces each Frame 
-- Relay service connection using the switched path created by the 
-- given EndPoint to perform a service level CAC as the VC for the 
-- Frame Relay service connection is being established. Each Frame 
-- Relay service connection is either accepted or rejected based on the 
-- CAC attributes specified through the Cacd subcomponent.
-- This component is optional on the originating End Point and Call 
-- Admission Control is not performed when this component is not 
-- provisioned on the originating End Point.
-- This component is dynamic on the dynamic End Point and is 
-- present when there is a provisioned instance of the 
-- CallAdmissionControl component on the originating End Point. 

mscMcsMgrDprsMcsEpGEpCac OBJECT IDENTIFIER ::= { mscMcsMgrDprsMcsEpGEp 5 }



mscMcsMgrDprsMcsEpGEpCacRowStatusTable OBJECT-TYPE
   SYNTAX     SEQUENCE OF MscMcsMgrDprsMcsEpGEpCacRowStatusEntry
   ACCESS     not-accessible
   STATUS     mandatory
   DESCRIPTION
     "This entry controls the addition and deletion of 
      mscMcsMgrDprsMcsEpGEpCac components."
::= { mscMcsMgrDprsMcsEpGEpCac 1 }

mscMcsMgrDprsMcsEpGEpCacRowStatusEntry OBJECT-TYPE
   SYNTAX     MscMcsMgrDprsMcsEpGEpCacRowStatusEntry
   ACCESS     not-accessible
   STATUS     mandatory
   DESCRIPTION
     "A single entry in the table represents a single 
      mscMcsMgrDprsMcsEpGEpCac component."
   INDEX {
      mscMcsMgrIndex,
      mscMcsMgrDprsMcsEpGIndex,
      mscMcsMgrDprsMcsEpGEpIndex,
      mscMcsMgrDprsMcsEpGEpCacIndex }
::= { mscMcsMgrDprsMcsEpGEpCacRowStatusTable 1 }

MscMcsMgrDprsMcsEpGEpCacRowStatusEntry ::= SEQUENCE {
   mscMcsMgrDprsMcsEpGEpCacRowStatus
      RowStatus,
   mscMcsMgrDprsMcsEpGEpCacComponentName
      DisplayString,
   mscMcsMgrDprsMcsEpGEpCacStorageType
      StorageType,
   mscMcsMgrDprsMcsEpGEpCacIndex
      NonReplicated }

mscMcsMgrDprsMcsEpGEpCacRowStatus OBJECT-TYPE
   SYNTAX     RowStatus 
   ACCESS     read-write
   STATUS     mandatory
   DESCRIPTION
     "This variable is used as the basis for SNMP naming of
      mscMcsMgrDprsMcsEpGEpCac components.
      These components can be added and deleted."
::= { mscMcsMgrDprsMcsEpGEpCacRowStatusEntry 1 }

mscMcsMgrDprsMcsEpGEpCacComponentName OBJECT-TYPE
   SYNTAX     DisplayString 
   ACCESS     read-only
   STATUS     mandatory
   DESCRIPTION
     "This variable provides the component's string name for
      use with the ASCII Console Interface"
::= { mscMcsMgrDprsMcsEpGEpCacRowStatusEntry 2 }

mscMcsMgrDprsMcsEpGEpCacStorageType OBJECT-TYPE
   SYNTAX     StorageType 
   ACCESS     read-only
   STATUS     mandatory
   DESCRIPTION
     "This variable represents the storage type value for the
      mscMcsMgrDprsMcsEpGEpCac tables."
::= { mscMcsMgrDprsMcsEpGEpCacRowStatusEntry 4 }

mscMcsMgrDprsMcsEpGEpCacIndex OBJECT-TYPE
   SYNTAX     NonReplicated 
   ACCESS     not-accessible
   STATUS     mandatory
   DESCRIPTION
     "This variable represents the index for the mscMcsMgrDprsMcsEpGEpCac tables."
::= { mscMcsMgrDprsMcsEpGEpCacRowStatusEntry 10 }

mscMcsMgrDprsMcsEpGEpCacOperTable OBJECT-TYPE
   SYNTAX     SEQUENCE OF MscMcsMgrDprsMcsEpGEpCacOperEntry
   ACCESS     not-accessible
   STATUS     mandatory
   DESCRIPTION
     "This group contains the operational attributes of the 
      CallAdmissionControl component."
::= { mscMcsMgrDprsMcsEpGEpCac 10 }

mscMcsMgrDprsMcsEpGEpCacOperEntry OBJECT-TYPE
   SYNTAX     MscMcsMgrDprsMcsEpGEpCacOperEntry
   ACCESS     not-accessible
   STATUS     mandatory
   DESCRIPTION
     "An entry in the mscMcsMgrDprsMcsEpGEpCacOperTable."
   INDEX {
      mscMcsMgrIndex,
      mscMcsMgrDprsMcsEpGIndex,
      mscMcsMgrDprsMcsEpGEpIndex,
      mscMcsMgrDprsMcsEpGEpCacIndex }
::= { mscMcsMgrDprsMcsEpGEpCacOperTable 1 }

MscMcsMgrDprsMcsEpGEpCacOperEntry ::= SEQUENCE {
   mscMcsMgrDprsMcsEpGEpCacEffectiveBandwidth
      Unsigned64,
   mscMcsMgrDprsMcsEpGEpCacEffectiveBandwidthAvailable
      Unsigned64,
   mscMcsMgrDprsMcsEpGEpCacNumberOfCallsActive
      Unsigned32,
   mscMcsMgrDprsMcsEpGEpCacCacPolicy
      INTEGER,
   mscMcsMgrDprsMcsEpGEpCacCacType
      INTEGER,
   mscMcsMgrDprsMcsEpGEpCacMaximumSvcBandwidth
      Unsigned32,
   mscMcsMgrDprsMcsEpGEpCacMaximumPvcBandwidth
      Unsigned32,
   mscMcsMgrDprsMcsEpGEpCacNumberOfCacFailures
      Counter32,
   mscMcsMgrDprsMcsEpGEpCacLastFailedFrDlci
      RowPointer,
   mscMcsMgrDprsMcsEpGEpCacLastFailedReason
      INTEGER,
   mscMcsMgrDprsMcsEpGEpCacOverSubscriptionFactor
      FixedPoint2 }

mscMcsMgrDprsMcsEpGEpCacEffectiveBandwidth OBJECT-TYPE
   SYNTAX     Unsigned64 (SIZE (8))
   ACCESS     read-only
   STATUS     mandatory
   DESCRIPTION
     "This attribute indicates the total bandwidth which is used as the 
      bandwidth pool for tracking call admission requests.
      On the originating End Point the effectiveBandwidth is equal to the 
      forwardBandwidth attribute specified in this End Point's Epd 
      component multiplied by the forwardOversubFactor specified in 
      the Cacd subcomponent.
      On the terminating End Point the effectiveBandwidth is equal to the 
      reverseBandwidth attribute specified in this End Point's Epd 
      component multiplied by this End Point's reverseOversubFactor 
      specified in the Cacd subcomponent.
      This value indicates CIR bandwidth when the cacType attribute of 
      the Cacd subcomponent is specified as cir.
      This value indicates EIR bandwidth when the cacType attribute of 
      the Cacd subcomponent is specified as eir."
::= { mscMcsMgrDprsMcsEpGEpCacOperEntry 1 }

mscMcsMgrDprsMcsEpGEpCacEffectiveBandwidthAvailable OBJECT-TYPE
   SYNTAX     Unsigned64 (SIZE (8))
   ACCESS     read-only
   STATUS     mandatory
   DESCRIPTION
     "This attribute indicates the effective bandwidth that is still available 
      in the bandwidth pool for use by Frame Relay service connections 
      requesting bandwidth. This value is the amount of 
      effectiveBandwith less the amount reserved by Frame Relay service 
      connections that have been admitted.
      To display the specific Frame Relay service connections which have 
      successfully completed call admission and to see the amount of 
      bandwidth they have reserved, the network operator can use the 
      following command:
      Display McsMgr DprsMcsEpG/n Ep/n Connection/*
      This value indicates CIR bandwidth when the cacType attribute of 
      the Cac subcomponent is specified as cir.
      This value indicates EIR bandwidth when the cacType attribute of 
      the Cac subcomponent is specified as eir."
::= { mscMcsMgrDprsMcsEpGEpCacOperEntry 2 }

mscMcsMgrDprsMcsEpGEpCacNumberOfCallsActive OBJECT-TYPE
   SYNTAX     Unsigned32 (0..512)
   ACCESS     read-only
   STATUS     mandatory
   DESCRIPTION
     "This attribute indicates the total number of Frame Relay service 
      connections which have successfully completed call admission and 
      are currently in service. 
      To display the specific Frame Relay service connections which have 
      successfully completed call admission and to see the amount of 
      bandwidth they have reserved the network operator can use the 
      following command:
      Display McsMgr DprsMcsEpG/n Ep/n Connection/*"
::= { mscMcsMgrDprsMcsEpGEpCacOperEntry 3 }

mscMcsMgrDprsMcsEpGEpCacCacPolicy OBJECT-TYPE
   SYNTAX     INTEGER  {
                 enforced(0),
                 monitored(1) }
   ACCESS     read-only
   STATUS     mandatory
   DESCRIPTION
     "This attribute indicates the CAC policy in use at this end of the 
      switched path. 
      For the originating End Point this is the value specified by the 
      forwardCacPolicy attribute of the Cacd subcomponent.
      For the terminating End Point this is the value specified by the 
      reverseCacPolicy attribute of the Cacd subcomponent of the 
      originating End Point at the other end of the switched path. To 
      determine the component name of the originating End Point, the 
      following command can be used:
      Display McsMgr DprsMcsEpG/n Ep/n remoteComponentName"
::= { mscMcsMgrDprsMcsEpGEpCacOperEntry 4 }

mscMcsMgrDprsMcsEpGEpCacCacType OBJECT-TYPE
   SYNTAX     INTEGER  {
                 eir(0),
                 cir(1) }
   ACCESS     read-only
   STATUS     mandatory
   DESCRIPTION
     "This attribute indicates the CAC type in use at this end of the 
      switched path. 
      For the originating End Point this is the value specified by the 
      forwardCacType attribute of the Cacd subcomponent.
      For the terminating End Point this is the value specified by the 
      reverseCacType attribute of the Cacd subcomponent of the 
      originating End Point at the other end of the switched path.To 
      determine the component name of the originating End Point, the 
      following command can be used:
      Display McsMgr DprsMcsEpG/n Ep/n remoteComponentName"
::= { mscMcsMgrDprsMcsEpGEpCacOperEntry 5 }

mscMcsMgrDprsMcsEpGEpCacMaximumSvcBandwidth OBJECT-TYPE
   SYNTAX     Unsigned32 (0..155000000 | 155000001)
   ACCESS     read-only
   STATUS     mandatory
   DESCRIPTION
     "This attribute indicates the largest amount of SVC bandwidth which 
      can be reserved for a single Frame Relay service connection using 
      the switched path.
      For the originating End Point this is the value specified by the 
      forwardMaximumSvcBw attribute of the Cacd subcomponent.
      For the terminating End Point this is the value specified by the 
      reverseMaximumSvcBw attribute of the Cacd subcomponent by the 
      originating End Point at the other end of the switched path.
      This value indicates CIR bandwidth when the cacType attribute of 
      the Cac subcomponent is cir.
      This value indicates EIR bandwidth when the cacType attribute of 
      the Cac subcomponent is eir.
      The value of noMaximum for this attribute indicates that this 
      attribute has either been provisioned not to have a maximum value 
      or that the cacPolicy is monitored.

      VALUES (

      155000001 = noMaximum

      )"
::= { mscMcsMgrDprsMcsEpGEpCacOperEntry 6 }

mscMcsMgrDprsMcsEpGEpCacMaximumPvcBandwidth OBJECT-TYPE
   SYNTAX     Unsigned32 (0..155000000 | 155000001)
   ACCESS     read-only
   STATUS     mandatory
   DESCRIPTION
     "This attribute indicates the largest amount of PVC bandwidth 
      allowed to be reserved for a single Frame Relay service connection 
      using the switched path. For the originating End Point this is the 
      value specified by the forwardMaximumSvcBw attribute of the Cacd 
      subcomponent.
      For the terminating End Point this is the value specified by the 
      reverseMaximumSvcBw attribute of the Cacd subcomponent by the 
      originating End Point at the other end of the switched path.
      This value indicates CIR bandwidth when the cacType attribute of 
      the Cac subcomponent is cir.
      This value indicates EIR bandwidth when the cacType attribute of 
      the Cac subcomponent is eir.
      The value of noMaximum for this attribute indicates that this 
      attribute has either been provisioned not to have a maximum value 
      or that the cacPolicy is monitored.

      VALUES (

      155000001 = noMaximum

      )"
::= { mscMcsMgrDprsMcsEpGEpCacOperEntry 7 }

mscMcsMgrDprsMcsEpGEpCacNumberOfCacFailures OBJECT-TYPE
   SYNTAX     Counter32 
   ACCESS     read-only
   STATUS     mandatory
   DESCRIPTION
     "This attribute counts the total number of Frame Relay service 
      connections which have failed to successfully complete call 
      admission on the given switched path. This number does not 
      increase if the cacPolicy attribute of the McsMgr DprsMcsEpG/n 
      EndPoint/m Cac component is set to monitored.
      This value wraps back to 0 when its maximum value is exceeded."
::= { mscMcsMgrDprsMcsEpGEpCacOperEntry 8 }

mscMcsMgrDprsMcsEpGEpCacLastFailedFrDlci OBJECT-TYPE
   SYNTAX     RowPointer 
   ACCESS     read-only
   STATUS     mandatory
   DESCRIPTION
     "This attribute indicates the component name of the last Frame Relay 
      service connection which did not successfully complete call 
      admission. This value is empty if no call admission failure has 
      occurred."
::= { mscMcsMgrDprsMcsEpGEpCacOperEntry 9 }

mscMcsMgrDprsMcsEpGEpCacLastFailedReason OBJECT-TYPE
   SYNTAX     INTEGER  {
                 none(0),
                 noBandwidthAvailable(1),
                 maxSvcExceeded(2),
                 maxPvcExceeded(3),
                 epCacUnavailable(4),
                 maxConsExceeded(5) }
   ACCESS     read-only
   STATUS     mandatory
   DESCRIPTION
     "This attribute indicates the reason for the failure of the last Frame 
      Relay service connection's attempt at call admission.
      none indicates that there has been no call admission failure.
      noBandwidthAvailable indicates that there was insufficient 
      effectiveBandwidthAvailable to admit the Frame Relay service 
      connection.
      maxSvcExceeded indicates that an SVC was attempting to reserve 
      more bandwidth than that specified by maximumSvcBandwidth 
      attribute.
      maxPvcExceeded indicates that an SVC was attempting to reserve 
      more bandwidth than that specified by maximumPvcBandwidth 
      attribute.
      endPointCacUnavailable indicates that the End Point was not in a 
      state in which it could process the call admission request. The 
      Frame Relay service should attempt call admission again after a 
      suitable backoff period.
      maxConsExceeded indicates that 512 call admission connections 
      have already been accepted on this End Point."
   DEFVAL     { none }
::= { mscMcsMgrDprsMcsEpGEpCacOperEntry 10 }

mscMcsMgrDprsMcsEpGEpCacOverSubscriptionFactor OBJECT-TYPE
   SYNTAX     FixedPoint2 (0..10000)
   ACCESS     read-only
   STATUS     mandatory
   DESCRIPTION
     "This attribute indicates the oversubscription factor that is applied to 
      the forward and reverse bandwidth attributes of the parent 
      component to determine the effectiveBandwidth.
      On the originating side of the switched path this value is equal to 
      the forwardOsFactor specified in the Cacd subcomponent.
      On the terminating side of the switched path this value is equal to 
      the reverseOsFactor attribute of the Cacd subcomponent at the 
      originating end of the switched path."
::= { mscMcsMgrDprsMcsEpGEpCacOperEntry 11 }

mscMcsMgrDprsMcsEpGEpCacAlarmThresholdTable OBJECT-TYPE
   SYNTAX     SEQUENCE OF MscMcsMgrDprsMcsEpGEpCacAlarmThresholdEntry
   ACCESS     not-accessible
   STATUS     mandatory
   DESCRIPTION
     "This attribute indicates the alarm threshold values that are used at 
      this end of the switched path.
      On the originating end of the switch path these values are those 
      specified by the forwardAlarmThresholds attribute of the Cacd 
      subcomponent.
      On the terminating end of the switched path these values are those 
      specified by the reverseAlarmThresholds attribute of the Cacd 
      subcomponent on the originating end of the switched path"
::= { mscMcsMgrDprsMcsEpGEpCac 802 }

mscMcsMgrDprsMcsEpGEpCacAlarmThresholdEntry OBJECT-TYPE
   SYNTAX     MscMcsMgrDprsMcsEpGEpCacAlarmThresholdEntry
   ACCESS     not-accessible
   STATUS     mandatory
   DESCRIPTION
     "An entry in the mscMcsMgrDprsMcsEpGEpCacAlarmThresholdTable."
   INDEX {
      mscMcsMgrIndex,
      mscMcsMgrDprsMcsEpGIndex,
      mscMcsMgrDprsMcsEpGEpIndex,
      mscMcsMgrDprsMcsEpGEpCacIndex,
      mscMcsMgrDprsMcsEpGEpCacAlarmThresholdIndex }
::= { mscMcsMgrDprsMcsEpGEpCacAlarmThresholdTable 1 }

MscMcsMgrDprsMcsEpGEpCacAlarmThresholdEntry ::= SEQUENCE {
   mscMcsMgrDprsMcsEpGEpCacAlarmThresholdIndex
      INTEGER,
   mscMcsMgrDprsMcsEpGEpCacAlarmThresholdValue
      Unsigned32 }

mscMcsMgrDprsMcsEpGEpCacAlarmThresholdIndex OBJECT-TYPE
   SYNTAX     INTEGER  {
                 minor(0),
                 major(1),
                 critical(2) }
   ACCESS     not-accessible
   STATUS     mandatory
   DESCRIPTION
     "This variable represents the mscMcsMgrDprsMcsEpGEpCacAlarmThresholdTable
      specific index for the mscMcsMgrDprsMcsEpGEpCacAlarmThresholdTable."
::= { mscMcsMgrDprsMcsEpGEpCacAlarmThresholdEntry 1 }

mscMcsMgrDprsMcsEpGEpCacAlarmThresholdValue OBJECT-TYPE
   SYNTAX     Unsigned32 (0..100)
   ACCESS     read-only
   STATUS     mandatory
   DESCRIPTION
     "This variable represents an individual value for the
      mscMcsMgrDprsMcsEpGEpCacAlarmThresholdTable."
::= { mscMcsMgrDprsMcsEpGEpCacAlarmThresholdEntry 2 }


-- The component allows the network operator to specify the CAC 
-- attributes used for call admission for the originating and terminating 
-- End Points of this switched path. This component is provisioned at 
-- the originating End Point only.

mscMcsMgrDprsMcsEpGEpCacCacd OBJECT IDENTIFIER ::= { mscMcsMgrDprsMcsEpGEpCac 2 }



mscMcsMgrDprsMcsEpGEpCacCacdRowStatusTable OBJECT-TYPE
   SYNTAX     SEQUENCE OF MscMcsMgrDprsMcsEpGEpCacCacdRowStatusEntry
   ACCESS     not-accessible
   STATUS     mandatory
   DESCRIPTION
     "This entry controls the addition and deletion of 
      mscMcsMgrDprsMcsEpGEpCacCacd components."
::= { mscMcsMgrDprsMcsEpGEpCacCacd 1 }

mscMcsMgrDprsMcsEpGEpCacCacdRowStatusEntry OBJECT-TYPE
   SYNTAX     MscMcsMgrDprsMcsEpGEpCacCacdRowStatusEntry
   ACCESS     not-accessible
   STATUS     mandatory
   DESCRIPTION
     "A single entry in the table represents a single 
      mscMcsMgrDprsMcsEpGEpCacCacd component."
   INDEX {
      mscMcsMgrIndex,
      mscMcsMgrDprsMcsEpGIndex,
      mscMcsMgrDprsMcsEpGEpIndex,
      mscMcsMgrDprsMcsEpGEpCacIndex,
      mscMcsMgrDprsMcsEpGEpCacCacdIndex }
::= { mscMcsMgrDprsMcsEpGEpCacCacdRowStatusTable 1 }

MscMcsMgrDprsMcsEpGEpCacCacdRowStatusEntry ::= SEQUENCE {
   mscMcsMgrDprsMcsEpGEpCacCacdRowStatus
      RowStatus,
   mscMcsMgrDprsMcsEpGEpCacCacdComponentName
      DisplayString,
   mscMcsMgrDprsMcsEpGEpCacCacdStorageType
      StorageType,
   mscMcsMgrDprsMcsEpGEpCacCacdIndex
      NonReplicated }

mscMcsMgrDprsMcsEpGEpCacCacdRowStatus OBJECT-TYPE
   SYNTAX     RowStatus 
   ACCESS     read-only
   STATUS     mandatory
   DESCRIPTION
     "This variable is used as the basis for SNMP naming of
      mscMcsMgrDprsMcsEpGEpCacCacd components.
      These components cannot be added nor deleted."
::= { mscMcsMgrDprsMcsEpGEpCacCacdRowStatusEntry 1 }

mscMcsMgrDprsMcsEpGEpCacCacdComponentName OBJECT-TYPE
   SYNTAX     DisplayString 
   ACCESS     read-only
   STATUS     mandatory
   DESCRIPTION
     "This variable provides the component's string name for
      use with the ASCII Console Interface"
::= { mscMcsMgrDprsMcsEpGEpCacCacdRowStatusEntry 2 }

mscMcsMgrDprsMcsEpGEpCacCacdStorageType OBJECT-TYPE
   SYNTAX     StorageType 
   ACCESS     read-only
   STATUS     mandatory
   DESCRIPTION
     "This variable represents the storage type value for the
      mscMcsMgrDprsMcsEpGEpCacCacd tables."
::= { mscMcsMgrDprsMcsEpGEpCacCacdRowStatusEntry 4 }

mscMcsMgrDprsMcsEpGEpCacCacdIndex OBJECT-TYPE
   SYNTAX     NonReplicated 
   ACCESS     not-accessible
   STATUS     mandatory
   DESCRIPTION
     "This variable represents the index for the mscMcsMgrDprsMcsEpGEpCacCacd tables."
::= { mscMcsMgrDprsMcsEpGEpCacCacdRowStatusEntry 10 }

mscMcsMgrDprsMcsEpGEpCacCacdFrwdTable OBJECT-TYPE
   SYNTAX     SEQUENCE OF MscMcsMgrDprsMcsEpGEpCacCacdFrwdEntry
   ACCESS     not-accessible
   STATUS     mandatory
   DESCRIPTION
     "This group contains the parameters that are used to specify the call 
      admission control characteristics for the given End Point in the 
      forward direction."
::= { mscMcsMgrDprsMcsEpGEpCacCacd 10 }

mscMcsMgrDprsMcsEpGEpCacCacdFrwdEntry OBJECT-TYPE
   SYNTAX     MscMcsMgrDprsMcsEpGEpCacCacdFrwdEntry
   ACCESS     not-accessible
   STATUS     mandatory
   DESCRIPTION
     "An entry in the mscMcsMgrDprsMcsEpGEpCacCacdFrwdTable."
   INDEX {
      mscMcsMgrIndex,
      mscMcsMgrDprsMcsEpGIndex,
      mscMcsMgrDprsMcsEpGEpIndex,
      mscMcsMgrDprsMcsEpGEpCacIndex,
      mscMcsMgrDprsMcsEpGEpCacCacdIndex }
::= { mscMcsMgrDprsMcsEpGEpCacCacdFrwdTable 1 }

MscMcsMgrDprsMcsEpGEpCacCacdFrwdEntry ::= SEQUENCE {
   mscMcsMgrDprsMcsEpGEpCacCacdForwardCacPolicy
      INTEGER,
   mscMcsMgrDprsMcsEpGEpCacCacdForwardCacType
      INTEGER,
   mscMcsMgrDprsMcsEpGEpCacCacdForwardOversubFactor
      FixedPoint2,
   mscMcsMgrDprsMcsEpGEpCacCacdForwardMaximumSvcBw
      Unsigned32,
   mscMcsMgrDprsMcsEpGEpCacCacdForwardMaximumPvcBw
      Unsigned32 }

mscMcsMgrDprsMcsEpGEpCacCacdForwardCacPolicy OBJECT-TYPE
   SYNTAX     INTEGER  {
                 enforced(0),
                 monitored(1) }
   ACCESS     read-write
   STATUS     mandatory
   DESCRIPTION
     "This attribute specifies the call admission policy which is to be used 
      in the forward direction. 
      When this attribute is set to enforced, a Frame Relay service 
      connection fails call admission if there is insufficient 
      effectiveBandwidth available in the forward direction, the 
      forwardMaximumSvcBw is exceeded, or the 
      forwardMaximumPvcBw is exceeded. Call admission failure causes 
      the Frame Relay service connection to clear.
      When this attribute is set to monitored no Frame Relay service call 
      will ever fail call admission."
   DEFVAL     { monitored }
::= { mscMcsMgrDprsMcsEpGEpCacCacdFrwdEntry 1 }

mscMcsMgrDprsMcsEpGEpCacCacdForwardCacType OBJECT-TYPE
   SYNTAX     INTEGER  {
                 eir(0),
                 cir(1) }
   ACCESS     read-write
   STATUS     mandatory
   DESCRIPTION
     "This attributes specifies whether the effectiveBandwidth in the 
      forward direction is treated as eir or cir bandwidth."
   DEFVAL     { cir }
::= { mscMcsMgrDprsMcsEpGEpCacCacdFrwdEntry 2 }

mscMcsMgrDprsMcsEpGEpCacCacdForwardOversubFactor OBJECT-TYPE
   SYNTAX     FixedPoint2 (0..10000)
   ACCESS     read-write
   STATUS     mandatory
   DESCRIPTION
     "This attribute specifies the level of oversubscription to be used when 
      calculating the parent component's effectiveBandwidth in the 
      forward direction. The forwardBandwidth attribute of the McsMgr 
      DprsMcsEpG/m Ep/n Epd subcomponent is multiplied by this 
      attribute to determine the effectiveBandwidth attribute."
   DEFVAL     { 100 }
::= { mscMcsMgrDprsMcsEpGEpCacCacdFrwdEntry 3 }

mscMcsMgrDprsMcsEpGEpCacCacdForwardMaximumSvcBw OBJECT-TYPE
   SYNTAX     Unsigned32 (0..155000000 | 155000001)
   ACCESS     read-write
   STATUS     mandatory
   DESCRIPTION
     "This attribute specifies the maximum bandwidth that can be 
      reserved by a Frame Relay SVC. The forwardCacType parameter 
      specifies if this value is to be treated as an EIR or CIR value.
      If this attribute is set to noMaximum or the forwardCacPolicy is set 
      to monitored this check is not made.

      VALUES (

      155000001 = noMaximum

      )"
   DEFVAL     { 155000001 }
::= { mscMcsMgrDprsMcsEpGEpCacCacdFrwdEntry 4 }

mscMcsMgrDprsMcsEpGEpCacCacdForwardMaximumPvcBw OBJECT-TYPE
   SYNTAX     Unsigned32 (0..155000000 | 155000001)
   ACCESS     read-write
   STATUS     mandatory
   DESCRIPTION
     "This attribute specifies the maximum bandwidth that can be 
      reserved by a Frame Relay PVC. The forwardCacType parameter 
      specifies if this value is to be treated as an EIR or CIR value.
      If this attribute is set to noMaximum or the forwardCacPolicy is set 
      to monitored this check is not made.

      VALUES (

      155000001 = noMaximum

      )"
   DEFVAL     { 155000001 }
::= { mscMcsMgrDprsMcsEpGEpCacCacdFrwdEntry 5 }

mscMcsMgrDprsMcsEpGEpCacCacdRvrsTable OBJECT-TYPE
   SYNTAX     SEQUENCE OF MscMcsMgrDprsMcsEpGEpCacCacdRvrsEntry
   ACCESS     not-accessible
   STATUS     mandatory
   DESCRIPTION
     "This group contains the parameters that are used to specify the call 
      admission control characteristics for the given End Point in the 
      reverse direction."
::= { mscMcsMgrDprsMcsEpGEpCacCacd 11 }

mscMcsMgrDprsMcsEpGEpCacCacdRvrsEntry OBJECT-TYPE
   SYNTAX     MscMcsMgrDprsMcsEpGEpCacCacdRvrsEntry
   ACCESS     not-accessible
   STATUS     mandatory
   DESCRIPTION
     "An entry in the mscMcsMgrDprsMcsEpGEpCacCacdRvrsTable."
   INDEX {
      mscMcsMgrIndex,
      mscMcsMgrDprsMcsEpGIndex,
      mscMcsMgrDprsMcsEpGEpIndex,
      mscMcsMgrDprsMcsEpGEpCacIndex,
      mscMcsMgrDprsMcsEpGEpCacCacdIndex }
::= { mscMcsMgrDprsMcsEpGEpCacCacdRvrsTable 1 }

MscMcsMgrDprsMcsEpGEpCacCacdRvrsEntry ::= SEQUENCE {
   mscMcsMgrDprsMcsEpGEpCacCacdReverseCacPolicy
      INTEGER,
   mscMcsMgrDprsMcsEpGEpCacCacdReverseCacType
      INTEGER,
   mscMcsMgrDprsMcsEpGEpCacCacdReverseCacOverSub
      FixedPoint2,
   mscMcsMgrDprsMcsEpGEpCacCacdReverseMaxSvcBw
      Unsigned32,
   mscMcsMgrDprsMcsEpGEpCacCacdReverseMaxPvcBw
      Unsigned32 }

mscMcsMgrDprsMcsEpGEpCacCacdReverseCacPolicy OBJECT-TYPE
   SYNTAX     INTEGER  {
                 enforced(0),
                 monitored(1),
                 sameAsForward(2) }
   ACCESS     read-write
   STATUS     mandatory
   DESCRIPTION
     "This attribute is used to specify the CAC policy to be used in the 
      reverse direction. 
      When this attribute is set to enforced a Frame Relay service 
      connection will fail call admission if there insufficient 
      effectiveBandwidth in the reverse direction, the 
      reverseMaximumSvcBw is exceeded or the reverseMaximumPvcBw 
      is exceeded. Call admission failure causes the Frame Relay service 
      connection clear.
      When this attribute is set to monitored no Frame Relay service call 
      is ever rejected.
      When this attribute is set to sameAsForward the reverseCacPolicy 
      is the same as that specified by the forwardCacPolicy attribute."
   DEFVAL     { sameAsForward }
::= { mscMcsMgrDprsMcsEpGEpCacCacdRvrsEntry 1 }

mscMcsMgrDprsMcsEpGEpCacCacdReverseCacType OBJECT-TYPE
   SYNTAX     INTEGER  {
                 eir(0),
                 cir(1),
                 sameAsForward(2) }
   ACCESS     read-write
   STATUS     mandatory
   DESCRIPTION
     "This attributes specifies if the effectiveBandwidth in the reverse 
      direction is treated as eir or cir bandwidth.
      When this attribute is set to sameAsForward the reverseCacType is 
      the same as that specified by the forwardCacType attribute."
   DEFVAL     { sameAsForward }
::= { mscMcsMgrDprsMcsEpGEpCacCacdRvrsEntry 2 }

mscMcsMgrDprsMcsEpGEpCacCacdReverseCacOverSub OBJECT-TYPE
   SYNTAX     FixedPoint2 (0..10000 | 10100)
   ACCESS     read-write
   STATUS     mandatory
   DESCRIPTION
     "This attribute specifies the level of over subscription to be used 
      when calculating the parent component's effectiveBandwidth in the 
      reverse direction.
      The reverseBandwidth attribute of the McsMgr DprsMcsEpG/m Ep/
      n Epd subcomponent is multiplied by this attribute to determine the 
      effectiveBandwidth in the reverse direction.
      When this attribute is set to sameAsForward the 
      reverseCacOverSub is the same as that specified by the 
      forwardCacOverSub attribute.

      VALUES (

      10100 = sameAsForward

      )"
   DEFVAL     { 10100 }
::= { mscMcsMgrDprsMcsEpGEpCacCacdRvrsEntry 3 }

mscMcsMgrDprsMcsEpGEpCacCacdReverseMaxSvcBw OBJECT-TYPE
   SYNTAX     Unsigned32 (0..155000000 | 155000001 | 155000002)
   ACCESS     read-write
   STATUS     mandatory
   DESCRIPTION
     "This attribute specifies the maximum bandwidth that can be 
      reserved by a Frame Relay SVC. The reverseCacType parameter 
      specifies if this value is to be treated as an EIR or CIR value.
      If the reverseCacPolicy is set to monitored or the value of this 
      attribute is set to noMaximum this check is not made.
      When this attribute is set to sameAsForward the reverseMaxSvcBw 
      is the same as that specified by the forwardMaxSvcBw attribute.

      VALUES (

      155000001 = noMaximum

      155000002 = sameAsForward

      )"
   DEFVAL     { 155000002 }
::= { mscMcsMgrDprsMcsEpGEpCacCacdRvrsEntry 4 }

mscMcsMgrDprsMcsEpGEpCacCacdReverseMaxPvcBw OBJECT-TYPE
   SYNTAX     Unsigned32 (0..155000000 | 155000001 | 155000002)
   ACCESS     read-write
   STATUS     mandatory
   DESCRIPTION
     "This attribute specifies the maximum bandwidth that can be 
      reserved by a Frame Relay PVC. The reverseCacType parameter 
      specifies if this value is to be treated as an EIR or CIR value.
      If the reverseCacPolicy is set to monitored or the value of this 
      attribute is set to noMaximum this check is not made.
      When this attribute is set to sameAsForward the reverseMaxPvcBw 
      is the same as that specified by the forwardMaxPvcBw attribute.

      VALUES (

      155000001 = noMaximum

      155000002 = sameAsForward

      )"
   DEFVAL     { 155000002 }
::= { mscMcsMgrDprsMcsEpGEpCacCacdRvrsEntry 5 }

mscMcsMgrDprsMcsEpGEpCacCacdFAlarmThreshTable OBJECT-TYPE
   SYNTAX     SEQUENCE OF MscMcsMgrDprsMcsEpGEpCacCacdFAlarmThreshEntry
   ACCESS     not-accessible
   STATUS     mandatory
   DESCRIPTION
     "This attribute specifies the bandwidth reservation level at which the 
      minor, major, and critical alarms are raised at in the forward 
      direction. By default all alarms are set to 0 disables alarm 
      generation.
      Each of these threshold alarms is cleared when the reservation level 
      falls 10% below the respective threshold level."
::= { mscMcsMgrDprsMcsEpGEpCacCacd 800 }

mscMcsMgrDprsMcsEpGEpCacCacdFAlarmThreshEntry OBJECT-TYPE
   SYNTAX     MscMcsMgrDprsMcsEpGEpCacCacdFAlarmThreshEntry
   ACCESS     not-accessible
   STATUS     mandatory
   DESCRIPTION
     "An entry in the mscMcsMgrDprsMcsEpGEpCacCacdFAlarmThreshTable."
   INDEX {
      mscMcsMgrIndex,
      mscMcsMgrDprsMcsEpGIndex,
      mscMcsMgrDprsMcsEpGEpIndex,
      mscMcsMgrDprsMcsEpGEpCacIndex,
      mscMcsMgrDprsMcsEpGEpCacCacdIndex,
      mscMcsMgrDprsMcsEpGEpCacCacdFAlarmThreshIndex }
::= { mscMcsMgrDprsMcsEpGEpCacCacdFAlarmThreshTable 1 }

MscMcsMgrDprsMcsEpGEpCacCacdFAlarmThreshEntry ::= SEQUENCE {
   mscMcsMgrDprsMcsEpGEpCacCacdFAlarmThreshIndex
      INTEGER,
   mscMcsMgrDprsMcsEpGEpCacCacdFAlarmThreshValue
      Unsigned32 }

mscMcsMgrDprsMcsEpGEpCacCacdFAlarmThreshIndex OBJECT-TYPE
   SYNTAX     INTEGER  {
                 minor(0),
                 major(1),
                 critical(2) }
   ACCESS     not-accessible
   STATUS     mandatory
   DESCRIPTION
     "This variable represents the mscMcsMgrDprsMcsEpGEpCacCacdFAlarmThreshTable
      specific index for the mscMcsMgrDprsMcsEpGEpCacCacdFAlarmThreshTable."
::= { mscMcsMgrDprsMcsEpGEpCacCacdFAlarmThreshEntry 1 }

mscMcsMgrDprsMcsEpGEpCacCacdFAlarmThreshValue OBJECT-TYPE
   SYNTAX     Unsigned32 (0..100)
   ACCESS     read-write
   STATUS     mandatory
   DESCRIPTION
     "This variable represents an individual value for the
      mscMcsMgrDprsMcsEpGEpCacCacdFAlarmThreshTable."
::= { mscMcsMgrDprsMcsEpGEpCacCacdFAlarmThreshEntry 2 }

mscMcsMgrDprsMcsEpGEpCacCacdRAlarmThreshTable OBJECT-TYPE
   SYNTAX     SEQUENCE OF MscMcsMgrDprsMcsEpGEpCacCacdRAlarmThreshEntry
   ACCESS     not-accessible
   STATUS     mandatory
   DESCRIPTION
     "This attribute specifies the reservation level at which the minor, 
      major, and critical alarms are raised in the reverse direction. By 
      default all alarms are set to 0 which is the off setting.
      Each of these threshold alarms are cleared when the reservation 
      level falls 10% below each respective threshold level."
::= { mscMcsMgrDprsMcsEpGEpCacCacd 801 }

mscMcsMgrDprsMcsEpGEpCacCacdRAlarmThreshEntry OBJECT-TYPE
   SYNTAX     MscMcsMgrDprsMcsEpGEpCacCacdRAlarmThreshEntry
   ACCESS     not-accessible
   STATUS     mandatory
   DESCRIPTION
     "An entry in the mscMcsMgrDprsMcsEpGEpCacCacdRAlarmThreshTable."
   INDEX {
      mscMcsMgrIndex,
      mscMcsMgrDprsMcsEpGIndex,
      mscMcsMgrDprsMcsEpGEpIndex,
      mscMcsMgrDprsMcsEpGEpCacIndex,
      mscMcsMgrDprsMcsEpGEpCacCacdIndex,
      mscMcsMgrDprsMcsEpGEpCacCacdRAlarmThreshIndex }
::= { mscMcsMgrDprsMcsEpGEpCacCacdRAlarmThreshTable 1 }

MscMcsMgrDprsMcsEpGEpCacCacdRAlarmThreshEntry ::= SEQUENCE {
   mscMcsMgrDprsMcsEpGEpCacCacdRAlarmThreshIndex
      INTEGER,
   mscMcsMgrDprsMcsEpGEpCacCacdRAlarmThreshValue
      Unsigned32 }

mscMcsMgrDprsMcsEpGEpCacCacdRAlarmThreshIndex OBJECT-TYPE
   SYNTAX     INTEGER  {
                 minor(0),
                 major(1),
                 critical(2) }
   ACCESS     not-accessible
   STATUS     mandatory
   DESCRIPTION
     "This variable represents the mscMcsMgrDprsMcsEpGEpCacCacdRAlarmThreshTable
      specific index for the mscMcsMgrDprsMcsEpGEpCacCacdRAlarmThreshTable."
::= { mscMcsMgrDprsMcsEpGEpCacCacdRAlarmThreshEntry 1 }

mscMcsMgrDprsMcsEpGEpCacCacdRAlarmThreshValue OBJECT-TYPE
   SYNTAX     Unsigned32 (0..100)
   ACCESS     read-write
   STATUS     mandatory
   DESCRIPTION
     "This variable represents an individual value for the
      mscMcsMgrDprsMcsEpGEpCacCacdRAlarmThreshTable."
::= { mscMcsMgrDprsMcsEpGEpCacCacdRAlarmThreshEntry 2 }

-- 
-- *** THIS SUBTREE CURRENTLY NOT IMPLEMENTED ***
-- 

-- McsMgr DprsMcsEpG/n Ep/n Connection/n
-- This component represents a Frame Relay service connection which 
-- has successfully completed call admission on a given switched path. 

mscMcsMgrDprsMcsEpGEpCon OBJECT IDENTIFIER ::= { mscMcsMgrDprsMcsEpGEp 6 }



mscMcsMgrDprsMcsEpGEpConRowStatusTable OBJECT-TYPE
   SYNTAX     SEQUENCE OF MscMcsMgrDprsMcsEpGEpConRowStatusEntry
   ACCESS     not-accessible
   STATUS     mandatory
   DESCRIPTION
     "*** THIS TABLE CURRENTLY NOT IMPLEMENTED ***

      This entry controls the addition and deletion of 
      mscMcsMgrDprsMcsEpGEpCon components."
::= { mscMcsMgrDprsMcsEpGEpCon 1 }

mscMcsMgrDprsMcsEpGEpConRowStatusEntry OBJECT-TYPE
   SYNTAX     MscMcsMgrDprsMcsEpGEpConRowStatusEntry
   ACCESS     not-accessible
   STATUS     mandatory
   DESCRIPTION
     "A single entry in the table represents a single 
      mscMcsMgrDprsMcsEpGEpCon component."
   INDEX {
      mscMcsMgrIndex,
      mscMcsMgrDprsMcsEpGIndex,
      mscMcsMgrDprsMcsEpGEpIndex,
      mscMcsMgrDprsMcsEpGEpConIndex }
::= { mscMcsMgrDprsMcsEpGEpConRowStatusTable 1 }

MscMcsMgrDprsMcsEpGEpConRowStatusEntry ::= SEQUENCE {
   mscMcsMgrDprsMcsEpGEpConRowStatus
      RowStatus,
   mscMcsMgrDprsMcsEpGEpConComponentName
      DisplayString,
   mscMcsMgrDprsMcsEpGEpConStorageType
      StorageType,
   mscMcsMgrDprsMcsEpGEpConIndex
      Integer32 }

mscMcsMgrDprsMcsEpGEpConRowStatus OBJECT-TYPE
   SYNTAX     RowStatus 
   ACCESS     read-only
   STATUS     mandatory
   DESCRIPTION
     "This variable is used as the basis for SNMP naming of
      mscMcsMgrDprsMcsEpGEpCon components.
      These components cannot be added nor deleted."
::= { mscMcsMgrDprsMcsEpGEpConRowStatusEntry 1 }

mscMcsMgrDprsMcsEpGEpConComponentName OBJECT-TYPE
   SYNTAX     DisplayString 
   ACCESS     read-only
   STATUS     mandatory
   DESCRIPTION
     "This variable provides the component's string name for
      use with the ASCII Console Interface"
::= { mscMcsMgrDprsMcsEpGEpConRowStatusEntry 2 }

mscMcsMgrDprsMcsEpGEpConStorageType OBJECT-TYPE
   SYNTAX     StorageType 
   ACCESS     read-only
   STATUS     mandatory
   DESCRIPTION
     "This variable represents the storage type value for the
      mscMcsMgrDprsMcsEpGEpCon tables."
::= { mscMcsMgrDprsMcsEpGEpConRowStatusEntry 4 }

mscMcsMgrDprsMcsEpGEpConIndex OBJECT-TYPE
   SYNTAX     Integer32 (1..512)
   ACCESS     not-accessible
   STATUS     mandatory
   DESCRIPTION
     "This variable represents the index for the mscMcsMgrDprsMcsEpGEpCon tables."
::= { mscMcsMgrDprsMcsEpGEpConRowStatusEntry 10 }

mscMcsMgrDprsMcsEpGEpConOperTable OBJECT-TYPE
   SYNTAX     SEQUENCE OF MscMcsMgrDprsMcsEpGEpConOperEntry
   ACCESS     not-accessible
   STATUS     mandatory
   DESCRIPTION
     "*** THIS TABLE CURRENTLY NOT IMPLEMENTED ***

      This group contains the operational attributes of the Connection 
      component."
::= { mscMcsMgrDprsMcsEpGEpCon 10 }

mscMcsMgrDprsMcsEpGEpConOperEntry OBJECT-TYPE
   SYNTAX     MscMcsMgrDprsMcsEpGEpConOperEntry
   ACCESS     not-accessible
   STATUS     mandatory
   DESCRIPTION
     "An entry in the mscMcsMgrDprsMcsEpGEpConOperTable."
   INDEX {
      mscMcsMgrIndex,
      mscMcsMgrDprsMcsEpGIndex,
      mscMcsMgrDprsMcsEpGEpIndex,
      mscMcsMgrDprsMcsEpGEpConIndex }
::= { mscMcsMgrDprsMcsEpGEpConOperTable 1 }

MscMcsMgrDprsMcsEpGEpConOperEntry ::= SEQUENCE {
   mscMcsMgrDprsMcsEpGEpConFrameRelayDlci
      RowPointer,
   mscMcsMgrDprsMcsEpGEpConReservedBandwidth
      Unsigned32 }

mscMcsMgrDprsMcsEpGEpConFrameRelayDlci OBJECT-TYPE
   SYNTAX     RowPointer 
   ACCESS     read-only
   STATUS     mandatory
   DESCRIPTION
     "This attribute indicates the DLCI of a Frame Relay service 
      connection that has successfully completed call admission and has 
      reserved bandwidth on this switched path."
::= { mscMcsMgrDprsMcsEpGEpConOperEntry 1 }

mscMcsMgrDprsMcsEpGEpConReservedBandwidth OBJECT-TYPE
   SYNTAX     Unsigned32 (0..155000000)
   ACCESS     read-only
   STATUS     mandatory
   DESCRIPTION
     "This attribute indicates the amount of bandwidth reserved by the 
      given Frame Relay service connection. To determine if this is EIR 
      or CIR bandwidth see the cacType attribute for this EndPoint."
::= { mscMcsMgrDprsMcsEpGEpConOperEntry 2 }




-- 
-- Version and Compliance statements
-- 



-- Object-Group Statement:
-- A list of all current accessible leaf objects.

-- OBJECTS { mscMcsMgrDprsMcsEpGEpLCoEmissionPriority,
--           mscMcsMgrDprsMcsEpGEpComponentName,
--           mscMcsMgrDprsMcsEpGEpLCoReasonForNoRoute,
--           mscMcsMgrDprsMcsEpGEpAtmConRowStatus,
--           mscMcsMgrDprsMcsEpGEpEpDForwardBandwidth,
--           mscMcsMgrDprsMcsEpGEpCacLastFailedReason,
--           mscMcsMgrDprsMcsEpGEpLCoPathType,
--           mscMcsMgrDprsMcsEpGEpLCoBytesToNetwork,
--           mscMcsMgrDprsMcsEpGEpEpDRowStatus,
--           mscMcsMgrDprsMcsEpGEpCacEffectiveBandwidth,
--           mscMcsMgrDprsMcsEpGEpEpDTransportConnectionPreference,
--           mscMcsMgrDprsMcsEpGAddrComponentName,
--           mscMcsMgrDprsMcsEpGComponentName,
--           mscMcsMgrDprsMcsEpGEpCacOverSubscriptionFactor,
--           mscMcsMgrDprsMcsEpGEpCacCacdReverseMaxSvcBw,
--           mscMcsMgrDprsMcsEpGEpLCoLastTearDownReason,
--           mscMcsMgrDprsMcsEpGEpConFrameRelayDlci,
--           mscMcsMgrDprsMcsEpGEpEpDPorsManualPath,
--           mscMcsMgrDprsMcsEpGEpLCoPktsToNetwork,
--           mscMcsMgrDprsMcsEpGEpLCoRequiredSecurity,
--           mscMcsMgrDprsMcsEpGEpLCoPathFailureCount,
--           mscMcsMgrDprsMcsEpGEpRemoteRoutingId,
--           mscMcsMgrDprsMcsEpGEpCacMaximumSvcBandwidth,
--           mscMcsMgrDprsMcsEpGEpEpDStorageType,
--           mscMcsMgrDprsMcsEpGEpCacAlarmThresholdValue,
--           mscMcsMgrDprsMcsEpGAssociatedEpGroupName,
--           mscMcsMgrDprsMcsEpGAddrRemoteAddress,
--           mscMcsMgrDprsMcsEpGRemoteAddress,
--           mscMcsMgrDprsMcsEpGEpLCoPathFailureAction,
--           mscMcsMgrDprsMcsEpGEpCacComponentName,
--           mscMcsMgrDprsMcsEpGEpLCoRequiredTrafficType,
--           mscMcsMgrDprsMcsEpGEpLCoHoldingPriority,
--           mscMcsMgrDprsMcsEpGEpLCoRetryCount,
--           mscMcsMgrDprsMcsEpGEpUnknownStatus,
--           mscMcsMgrDprsMcsEpGEpStandbyStatus,
--           mscMcsMgrDprsMcsEpGEpLCoPermittedTrunkTypes,
--           mscMcsMgrDprsMcsEpGEpLCoBytesFromNetwork,
--           mscMcsMgrDprsMcsEpGEpCacCacdForwardCacPolicy,
--           mscMcsMgrDprsMcsEpGEpStorageType,
--           mscMcsMgrDprsMcsEpGEpPktDiscErroredFromMcs,
--           mscMcsMgrDprsMcsEpGEpCacCacType,
--           mscMcsMgrDprsMcsEpGEpLCoEnd,
--           mscMcsMgrDprsMcsEpGEpLCoState,
--           mscMcsMgrDprsMcsEpGAddrStorageType,
--           mscMcsMgrDprsMcsEpGStorageType,
--           mscMcsMgrDprsMcsEpGEpCacCacdReverseMaxPvcBw,
--           mscMcsMgrDprsMcsEpGEpLCoStorageType,
--           mscMcsMgrDprsMcsEpGEpControlStatus,
--           mscMcsMgrDprsMcsEpGEpAdminState,
--           mscMcsMgrDprsMcsEpGEpConComponentName,
--           mscMcsMgrDprsMcsEpGEpLCoPktsFromNetwork,
--           mscMcsMgrDprsMcsEpGEpCacMaximumPvcBandwidth,
--           mscMcsMgrDprsMcsEpGEpCacNumberOfCacFailures,
--           mscMcsMgrDprsMcsEpGEpCacCacdReverseCacType,
--           mscMcsMgrDprsMcsEpGEpRowStatus,
--           mscMcsMgrDprsMcsEpGEpLCoDiscardPriority,
--           mscMcsMgrDprsMcsEpGEpCacCacdComponentName,
--           mscMcsMgrDprsMcsEpGEpRemoteModuleId,
--           mscMcsMgrDprsMcsEpGEpForwardBandwith,
--           mscMcsMgrDprsMcsEpGEpCacCacdReverseCacOverSub,
--           mscMcsMgrDprsMcsEpGAddrRowStatus,
--           mscMcsMgrDprsMcsEpGRowStatus,
--           mscMcsMgrDprsMcsEpGEpLCoDelayMetric,
--           mscMcsMgrDprsMcsEpGEpUsageState,
--           mscMcsMgrDprsMcsEpGEpLCoCostMetric,
--           mscMcsMgrDprsMcsEpGEpEpDReverseBandwidth,
--           mscMcsMgrDprsMcsEpGEpServiceCategory,
--           mscMcsMgrDprsMcsEpGEpCacLastFailedFrDlci,
--           mscMcsMgrDprsMcsEpGAddrCommentText,
--           mscMcsMgrDprsMcsEpGEpCacStorageType,
--           mscMcsMgrDprsMcsEpGEpSetupAttempts,
--           mscMcsMgrDprsMcsEpGEpAtmConNextHop,
--           mscMcsMgrDprsMcsEpGEpLCoComponentName,
--           mscMcsMgrDprsMcsEpGEpOctetsFromMcsValue,
--           mscMcsMgrDprsMcsEpGEpCacCacdForwardMaximumSvcBw,
--           mscMcsMgrDprsMcsEpGEpLCoOverrideRemoteName,
--           mscMcsMgrDprsMcsEpGEpOperationalState,
--           mscMcsMgrDprsMcsEpGEpCacEffectiveBandwidthAvailable,
--           mscMcsMgrDprsMcsEpGEpLastTrConnDiagCode,
--           mscMcsMgrDprsMcsEpGEpLCoRoundTripDelay,
--           mscMcsMgrDprsMcsEpGEpCacCacdForwardOversubFactor,
--           mscMcsMgrDprsMcsEpGEpReverseBandwidth,
--           mscMcsMgrDprsMcsEpGEpAtmConComponentName,
--           mscMcsMgrDprsMcsEpGEpConReservedBandwidth,
--           mscMcsMgrDprsMcsEpGEpCacRowStatus,
--           mscMcsMgrDprsMcsEpGEpLCoPathValue,
--           mscMcsMgrDprsMcsEpGEpLCoRequiredCustomerParameter,
--           mscMcsMgrDprsMcsEpGEpConStorageType,
--           mscMcsMgrDprsMcsEpGEpEpDConnectionTransferPriority,
--           mscMcsMgrDprsMcsEpGEpLCoRequiredTxBandwidth,
--           mscMcsMgrDprsMcsEpGEpLCoSetupPriority,
--           mscMcsMgrDprsMcsEpGEpAvailabilityStatus,
--           mscMcsMgrDprsMcsEpGEpCacCacdStorageType,
--           mscMcsMgrDprsMcsEpGEpEpDSupportedTransferPriorities,
--           mscMcsMgrDprsMcsEpGEpEpDComponentName,
--           mscMcsMgrDprsMcsEpGEpCacCacdForwardMaximumPvcBw,
--           mscMcsMgrDprsMcsEpGEpEpDProfile,
--           mscMcsMgrDprsMcsEpGEpAlarmStatus,
--           mscMcsMgrDprsMcsEpGEpCacCacPolicy,
--           mscMcsMgrDprsMcsEpGEpCacCacdFAlarmThreshValue,
--           mscMcsMgrDprsMcsEpGEpCacCacdRAlarmThreshValue,
--           mscMcsMgrDprsMcsEpGEpConnectionTransferPriority,
--           mscMcsMgrDprsMcsEpGEpConRowStatus,
--           mscMcsMgrDprsMcsEpGEpCacNumberOfCallsActive,
--           mscMcsMgrDprsMcsEpGEpSupportedTransferPriorities,
--           mscMcsMgrDprsMcsEpGEpPktFromMcsValue,
--           mscMcsMgrDprsMcsEpGEpCacCacdReverseCacPolicy,
--           mscMcsMgrDprsMcsEpGEpLastTransportConnectionClearCause,
--           mscMcsMgrDprsMcsEpGEpCacCacdRowStatus,
--           mscMcsMgrDprsMcsEpGEpLCoRequiredRxBandwidth,
--           mscMcsMgrDprsMcsEpGEpPktDiscCongestedFromMcsValue,
--           mscMcsMgrDprsMcsEpGEpLCoBumpPreference,
--           mscMcsMgrDprsMcsEpGEpRemoteComponentName,
--           mscMcsMgrDprsMcsEpGEpLCoOptimization,
--           mscMcsMgrDprsMcsEpGEpAtmConStorageType,
--           mscMcsMgrDprsMcsEpGEpType,
--           mscMcsMgrDprsMcsEpGEpCacCacdForwardCacType,
--           mscMcsMgrDprsMcsEpGEpProceduralStatus,
--           mscMcsMgrDprsMcsEpGEpLCoRowStatus,
--           mscMcsMgrDprsMcsEpGEpLCoPathUpDateTime }
-- STATUS  mandatory
-- DESCRIPTION
--   "A list of all current accessible leaf objects."

dprsMcsEpGroup OBJECT IDENTIFIER ::= { dprsMcsEpMIB 1 }
dprsMcsEpGroupCA OBJECT IDENTIFIER ::= { dprsMcsEpGroup 1 }
dprsMcsEpGroupCA02 OBJECT IDENTIFIER ::= { dprsMcsEpGroupCA 3 }
dprsMcsEpGroupCA02A OBJECT IDENTIFIER ::= { dprsMcsEpGroupCA02 2 }



-- Agent-Capabilities Statement:

-- PRODUCT-RELEASE "MscPassport Release 1.2 DprsMcsEp."
-- STATUS          mandatory
-- DESCRIPTION     "Carrier Passport DprsMcsEp MIB: MIB Version CA02A,
--                  Software Version CA02S9C."
-- SUPPORTS        Nortel-MsCarrier-MscPassport-DprsMcsEpMIB
--    INCLUDES     { dprsMcsEpGroupCA02A }

dprsMcsEpCapabilities OBJECT IDENTIFIER ::= { dprsMcsEpMIB 3 }
dprsMcsEpCapabilitiesCA OBJECT IDENTIFIER ::= { dprsMcsEpCapabilities 1 }
dprsMcsEpCapabilitiesCA02 OBJECT IDENTIFIER ::= { dprsMcsEpCapabilitiesCA 3 }
dprsMcsEpCapabilitiesCA02A OBJECT IDENTIFIER ::= { dprsMcsEpCapabilitiesCA02 2 }





END
