-- Memotec Enterprise MIB
-- October 1993
-- Draft 2.0
-- C. Rocray and C. Poirier 

MEMOTEC-SMI

DEFINITIONS ::= BEGIN

IMPORTS
  enterprises
    FROM RFC1155-SMI;

memotec
OBJECT IDENTIFIER 
::= { enterprises 495 }

memotecExperimental 
OBJECT IDENTIFIER 
::= { memotec 1 }

memotecProducts
OBJECT IDENTIFIER 
::= { memotec 2 }

memotecAdmin
OBJECT IDENTIFIER 
::= { memotec 3 }

ems221Trap
OBJECT IDENTIFIER   
::= { memotec  4 }

cxProduct 
OBJECT IDENTIFIER   
::= { memotecProducts  1 }


-- Other product must be added here

END
