--			Ascend mibscrty MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBSCRTY-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibsecurityProfile  OBJECT IDENTIFIER ::= { configuration 107}

	-- The mibsecurityProfile table
	--
	-- This table contains parameters for the mibsecurityProfile profile
	--

    mibsecurityProfileTable	OBJECT-TYPE
	SYNTAX		SEQUENCE OF MibsecurityProfileEntry
	ACCESS		not-accessible
	STATUS		mandatory
	DESCRIPTION	"A list of mibsecurityProfile profile entries."
	::= { mibsecurityProfile 1 }

    mibsecurityProfileEntry	OBJECT-TYPE
	SYNTAX		MibsecurityProfileEntry
	ACCESS		not-accessible
	STATUS		mandatory
	DESCRIPTION	"A mibsecurityProfile entry containing objects that
			 maps to the parameters of mibsecurityProfile profile."
	INDEX		{ securityProfile-Name }
	::= { mibsecurityProfileTable 1 }

    MibsecurityProfileEntry ::=
	SEQUENCE {
	    securityProfile-Name
		DisplayString,
	    securityProfile-Password
		DisplayString,
	    securityProfile-Operations
		INTEGER,
	    securityProfile-EditSecurity
		INTEGER,
	    securityProfile-EditSystem
		INTEGER,
	    securityProfile-EditLine
		INTEGER,
	    securityProfile-EditOwnPort
		INTEGER,
	    securityProfile-EditAllPort
		INTEGER,
	    securityProfile-EditCurCall
		INTEGER,
	    securityProfile-EditOwnCall
		INTEGER,
	    securityProfile-EditComCall
		INTEGER,
	    securityProfile-EditAllCall
		INTEGER,
	    securityProfile-SysDiag
		INTEGER,
	    securityProfile-OwnPortDiag
		INTEGER,
	    securityProfile-AllPortDiag
		INTEGER,
	    securityProfile-Download
		INTEGER,
	    securityProfile-Upload
		INTEGER,
	    securityProfile-FieldService
		INTEGER,
	    securityProfile-UseTacacsPlus
		INTEGER,
	    securityProfile-Action-o
		INTEGER
	}

    securityProfile-Name	OBJECT-TYPE
	SYNTAX	DisplayString
	ACCESS	read-only
	STATUS	mandatory
	DESCRIPTION	"Profile name."
	::= { mibsecurityProfileEntry 1 }

    securityProfile-Password	OBJECT-TYPE
	SYNTAX	DisplayString
	ACCESS	read-write
	STATUS	mandatory
	DESCRIPTION	"Password to access the security levels defined by this profile."
	::= { mibsecurityProfileEntry 2 }

    securityProfile-Operations	OBJECT-TYPE
	SYNTAX	INTEGER {
		    no (1),
		    yes (2)
		}
	ACCESS	read-write
	STATUS	mandatory
	DESCRIPTION	"TRUE = able to do things other than look."
	::= { mibsecurityProfileEntry 3 }

    securityProfile-EditSecurity	OBJECT-TYPE
	SYNTAX	INTEGER {
		    no (1),
		    yes (2)
		}
	ACCESS	read-write
	STATUS	mandatory
	DESCRIPTION	"TRUE = able to edit the security profiles."
	::= { mibsecurityProfileEntry 4 }

    securityProfile-EditSystem	OBJECT-TYPE
	SYNTAX	INTEGER {
		    no (1),
		    yes (2)
		}
	ACCESS	read-write
	STATUS	mandatory
	DESCRIPTION	"TRUE = able to edit the system profiles."
	::= { mibsecurityProfileEntry 5 }

    securityProfile-EditLine	OBJECT-TYPE
	SYNTAX	INTEGER {
		    no (1),
		    yes (2)
		}
	ACCESS	read-write
	STATUS	mandatory
	DESCRIPTION	"TRUE = able to edit the line profile."
	::= { mibsecurityProfileEntry 6 }

    securityProfile-EditOwnPort	OBJECT-TYPE
	SYNTAX	INTEGER {
		    no (1),
		    yes (2)
		}
	ACCESS	read-write
	STATUS	mandatory
	DESCRIPTION	"TRUE = able to edit port associated port profile (for remote terminal)."
	::= { mibsecurityProfileEntry 7 }

    securityProfile-EditAllPort	OBJECT-TYPE
	SYNTAX	INTEGER {
		    no (1),
		    yes (2)
		}
	ACCESS	read-write
	STATUS	mandatory
	DESCRIPTION	"TRUE = able to edit all port profiles."
	::= { mibsecurityProfileEntry 8 }

    securityProfile-EditCurCall	OBJECT-TYPE
	SYNTAX	INTEGER {
		    no (1),
		    yes (2)
		}
	ACCESS	read-write
	STATUS	mandatory
	DESCRIPTION	"TRUE = able to edit the current call profile."
	::= { mibsecurityProfileEntry 9 }

    securityProfile-EditOwnCall	OBJECT-TYPE
	SYNTAX	INTEGER {
		    no (1),
		    yes (2)
		}
	ACCESS	read-write
	STATUS	mandatory
	DESCRIPTION	"TRUE = able to edit port associated call profiles (for remote terminal)."
	::= { mibsecurityProfileEntry 10 }

    securityProfile-EditComCall	OBJECT-TYPE
	SYNTAX	INTEGER {
		    no (1),
		    yes (2)
		}
	ACCESS	read-write
	STATUS	mandatory
	DESCRIPTION	"TRUE = able to edit the common call profiles (for remote terminal)."
	::= { mibsecurityProfileEntry 11 }

    securityProfile-EditAllCall	OBJECT-TYPE
	SYNTAX	INTEGER {
		    no (1),
		    yes (2)
		}
	ACCESS	read-write
	STATUS	mandatory
	DESCRIPTION	"TRUE = able to edit all call profiles."
	::= { mibsecurityProfileEntry 12 }

    securityProfile-SysDiag	OBJECT-TYPE
	SYNTAX	INTEGER {
		    no (1),
		    yes (2)
		}
	ACCESS	read-write
	STATUS	mandatory
	DESCRIPTION	"TRUE = able to perform system diagnostics."
	::= { mibsecurityProfileEntry 13 }

    securityProfile-OwnPortDiag	OBJECT-TYPE
	SYNTAX	INTEGER {
		    no (1),
		    yes (2)
		}
	ACCESS	read-write
	STATUS	mandatory
	DESCRIPTION	"TRUE = able to perform port associated port diagnostics (for remote terminal)."
	::= { mibsecurityProfileEntry 14 }

    securityProfile-AllPortDiag	OBJECT-TYPE
	SYNTAX	INTEGER {
		    no (1),
		    yes (2)
		}
	ACCESS	read-write
	STATUS	mandatory
	DESCRIPTION	"TRUE = able to perform port diagnostics for all ports."
	::= { mibsecurityProfileEntry 15 }

    securityProfile-Download	OBJECT-TYPE
	SYNTAX	INTEGER {
		    no (1),
		    yes (2)
		}
	ACCESS	read-write
	STATUS	mandatory
	DESCRIPTION	"TRUE = able to download configuration."
	::= { mibsecurityProfileEntry 16 }

    securityProfile-Upload	OBJECT-TYPE
	SYNTAX	INTEGER {
		    no (1),
		    yes (2)
		}
	ACCESS	read-write
	STATUS	mandatory
	DESCRIPTION	"TRUE = able to upload configuration."
	::= { mibsecurityProfileEntry 17 }

    securityProfile-FieldService	OBJECT-TYPE
	SYNTAX	INTEGER {
		    no (1),
		    yes (2)
		}
	ACCESS	read-write
	STATUS	mandatory
	DESCRIPTION	"TRUE = able to perform field service."
	::= { mibsecurityProfileEntry 18 }

    securityProfile-UseTacacsPlus	OBJECT-TYPE
	SYNTAX	INTEGER {
		    no (1),
		    yes (2)
		}
	ACCESS	read-write
	STATUS	mandatory
	DESCRIPTION	"Use TACACS+ to authenticate security level changes"
	::= { mibsecurityProfileEntry 19 }

    securityProfile-Action-o	OBJECT-TYPE
	SYNTAX	INTEGER {
		    noAction (1),
		    createProfile (2),
		    deleteProfile (3)
		}
	ACCESS	read-write
	STATUS	mandatory
	DESCRIPTION	""
	::= { mibsecurityProfileEntry 20 }

END
