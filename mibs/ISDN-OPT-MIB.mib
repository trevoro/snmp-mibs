-- Version 2.15.1.2, modified  2001-07-13 16:38:05-04 

        ISDN-OPT-MIB DEFINITIONS ::= BEGIN

        IMPORTS
				enterprises FROM RFC1155-SMI
            OBJECT-TYPE
                FROM RFC-1212;

        -- Codex MIB Group definitions

                      codex OBJECT IDENTIFIER ::= { enterprises 449 }
         cdxProductSpecific OBJECT IDENTIFIER ::= { codex 2 }
                    cdx6500 OBJECT IDENTIFIER ::= { cdxProductSpecific 1 }

      cdx6500Configuration  OBJECT IDENTIFIER ::= { cdx6500 2 }
     cdx6500CfgGeneralGroup OBJECT IDENTIFIER ::= { cdx6500Configuration 2 }
            isgIsdnCfgGroup OBJECT IDENTIFIER ::= { cdx6500CfgGeneralGroup 19 }

          cdx6500Statistics OBJECT IDENTIFIER ::= { cdx6500 3 }
 cdx6500StatOtherStatsGroup OBJECT IDENTIFIER ::= { cdx6500Statistics 2 }
          isgIsdnStatsGroup OBJECT IDENTIFIER ::= { cdx6500StatOtherStatsGroup 9 }

            cdx6500Controls OBJECT IDENTIFIER ::= { cdx6500 4 }
           isgIsdnCtrlGroup OBJECT IDENTIFIER ::= { cdx6500Controls 8 }

        -- Textual Conventions

        DisplayString ::= OCTET STRING

        -- Configuration objects 

        isgVGIsdnCfgChanTable OBJECT-TYPE
            SYNTAX SEQUENCE OF IsgVGIsdnCfgChanTableEntry
            ACCESS not-accessible
            STATUS mandatory
            DESCRIPTION
                "This table contains ISDN Channel Configuration parameters."
        ::= { isgIsdnCfgGroup 1 }

        isgVGIsdnCfgChanTableEntry OBJECT-TYPE
            SYNTAX SEQUENCE OF IsgVGIsdnCfgChanTableEntry
            ACCESS not-accessible
            STATUS mandatory
            DESCRIPTION
                "An ISDN Channel Configuration Table Entry."
            INDEX { isgVGIsdnCfgEntryNum }
        ::= { isgVGIsdnCfgChanTable 1 }

        IsgVGIsdnCfgChanTableEntry ::=
            SEQUENCE {
                isgVGIsdnCfgEntryNum
                    INTEGER,
                isgVGIsdnCfgChanType
                    INTEGER,
                isgVGIsdnCfgDChanPort
                    INTEGER,
                isgVGIsdnCfgSwitchType
                    INTEGER,
                isgVGIsdnCfgDChanTEI
                    INTEGER,
                isgVGIsdnCfgDPckTraffic
                    INTEGER,
                isgVGIsdnCfgDChanDN
                    DisplayString,
                isgVGIsdnCfgDSPID
                    DisplayString,
                isgVGIsdnCfgFirstBChanPort
                    INTEGER,
                isgVGIsdnCfgFirstAccType
                    INTEGER,
                isgVGIsdnCfgFirstCallDisablSTm
                    DisplayString,
                isgVGIsdnCfgFirstCallEnablSTm
                    DisplayString,
                isgVGIsdnCfgFirstSPBU
                    INTEGER,
                isgVGIsdnCfgFirstSPBUOpt
                    DisplayString,
                isgVGIsdnCfgFirstSPBUTmOut
                    INTEGER,
                isgVGIsdnCfgFirstRate
                    INTEGER,
                isgVGIsdnCfgFirstTEI
                    INTEGER,
                isgVGIsdnCfgFirstSPID
                    DisplayString,
                isgVGIsdnCfgFirstDN
                    DisplayString,
                isgVGIsdnCfgFirstSubAddr
                    DisplayString,
                isgVGIsdnCfgFirstOutDialNum1
                    DisplayString,
                isgVGIsdnCfgFirstOutDialNum2
                    DisplayString,
                isgVGIsdnCfgFirstDialRetryIntrvl
                    INTEGER,
                isgVGIsdnCfgFirstNumCallRetries
                    INTEGER,
                isgVGIsdnCfgSecondChanPort
                    INTEGER,
                isgVGIsdnCfgSecondAccType
                    INTEGER,
                isgVGIsdnCfgSecondCallDisablSTm
                    DisplayString,
                isgVGIsdnCfgSecondCallEnablSTm
                    DisplayString,
                isgVGIsdnCfgSecondSPBU
                    INTEGER,
                isgVGIsdnCfgSecondSPBUOpt
                    DisplayString,
                isgVGIsdnCfgSecondSPBUTmOut
                    INTEGER,
                isgVGIsdnCfgSecondRate
                    INTEGER,
                isgVGIsdnCfgSecondTEI
                    INTEGER,
                isgVGIsdnCfgSecondSPID
                    DisplayString,
                isgVGIsdnCfgSecondDN
                    DisplayString,
                isgVGIsdnCfgSecondSubAddr
                    DisplayString,
                isgVGIsdnCfgSecondOutDialNum1
                    DisplayString,
                isgVGIsdnCfgSecondOutDialNum2
                    DisplayString,
                isgVGIsdnCfgSecondDialRetryIntrvl
                    INTEGER,
                isgVGIsdnCfgSecondNumCallRetries
                    INTEGER,
		isgVGIsdnCfgFirstPlainOldTelSet
                    DisplayString,
		isgVGIsdnCfgFirstCallPerm
                    DisplayString,
		isgVGIsdnCfgFirstChSelect 
                    INTEGER,
		isgVGIsdnCfgSecondPlainOldTelSet
                    DisplayString,
		isgVGIsdnCfgSecondCallPerm
                    DisplayString,
		isgVGIsdnCfgSecondChSelect 
                    INTEGER
                }

        isgVGIsdnCfgEntryNum OBJECT-TYPE
            SYNTAX INTEGER
            ACCESS read-only
            STATUS mandatory
            DESCRIPTION
                "This indicates the Channel Configuration Table Entry Number."
        ::= { isgVGIsdnCfgChanTableEntry 1 }

        isgVGIsdnCfgChanType OBJECT-TYPE
            SYNTAX INTEGER {
                    isdnNone (1),
                    isdnD    (2),
                    isdnB1   (3),
                    isdnB2   (4),
                    isdn2B   (5),
                    isdnB    (6)
                    }
            ACCESS read-only
            STATUS mandatory
            DESCRIPTION
                "ISDN Channel Type."
        ::= { isgVGIsdnCfgChanTableEntry 2 }

        isgVGIsdnCfgDChanPort OBJECT-TYPE
            SYNTAX INTEGER {
                   dchanzero (1),
                   dchanone  (2),
                   dchanfour (5),
                   nc        (100)
                   } 
            ACCESS read-write
            STATUS mandatory
            DESCRIPTION
                "The associated port for the ISDN D-channel.
                 dchanzero  : Both B channels have access type Permanent.
                              No D Channel data.
                 dchanone   : Packet Data on D-channel (Port 1 Type = X25) or 
                              B-channel access type is Switched type.
                 dchanfour  : Packet Data on D-Channel (Port 4 Type = X25).
                 nc         : Skipped during configuration. "
        ::= { isgVGIsdnCfgChanTableEntry 3 }

        isgVGIsdnCfgSwitchType OBJECT-TYPE
            SYNTAX INTEGER {
                    bri1tr6Stype   (2),
                    bri5essStype   (3),
                    briDms100Stype (6),
                    briKddStype    (8),
                    briEtsiStype   (9),
                    briNi1Stype    (11),
                    briNttStype    (13),
                    briTs013Stype  (14),
                    briVnStype     (15)
                    }
            ACCESS read-write
            STATUS mandatory
            DESCRIPTION
                "Specifies switch type for the central office.
                 bri1tr6Stype   : German National ISDN.
                 bri5essStype   : AT&T switch
                 briDms100Stype : DMS 100.
                 briKddStype    : Japanese International Access ISDN.
                 briEtsiStype   : Euro ISDB BRI (NET3).
                 briNi1Stype    : National ISDN version 1.
                 briNttStype    : Japanese National ISDN.
                 briTs013Stype  : Australian National ISDN.
                 briVnStype     : France National ISDN."
        ::= { isgVGIsdnCfgChanTableEntry 4 }

        isgVGIsdnCfgDChanTEI OBJECT-TYPE
            SYNTAX INTEGER
            ACCESS read-write
            STATUS mandatory
            DESCRIPTION
                "The Terminal Endpoint Identifier value is provided by 
                 the service provider. The range for TEI is 0..63, 127,
                 255. If the Switch Type is configured as DMS-1, the 
                 possible range for TEI selection will be limited to 
                 1..63. If TEI is configured to 255, the next valid TEI 
                 will be used and if TEI is configured to 127, automatic 
                 TEI negotiation will take place."
        ::= { isgVGIsdnCfgChanTableEntry 5 }

        isgVGIsdnCfgDPckTraffic OBJECT-TYPE
            SYNTAX INTEGER {
                    disable (1),
                    enable  (2)
                    }
            ACCESS read-write
            STATUS mandatory
            DESCRIPTION
                "enable  : Signalling and X.25 data over the D Channel.
                 disable : Only signalling data over the D Channel."
        ::= { isgVGIsdnCfgChanTableEntry 6 }

        isgVGIsdnCfgDChanDN OBJECT-TYPE
            SYNTAX DisplayString (SIZE(0..17))
            ACCESS read-write
            STATUS mandatory
            DESCRIPTION
                "Local Subscriber Directory Number (DN)
                 DN is provided by the ISDN service provider."
        ::= { isgVGIsdnCfgChanTableEntry 7 }

        isgVGIsdnCfgDSPID OBJECT-TYPE
            SYNTAX DisplayString (SIZE(0..21))
            ACCESS read-write
            STATUS mandatory
            DESCRIPTION
                "The Service Profile ID identifies the service profile 
                 and is provided by the ISDN service provider."
        ::= { isgVGIsdnCfgChanTableEntry 8 }
        
        isgVGIsdnCfgFirstBChanPort OBJECT-TYPE
            SYNTAX INTEGER (0..3)
            ACCESS read-write
            STATUS mandatory
            DESCRIPTION
                "0   : No call or TEI activity for the following objects
                       prefixed by `isgVGIsdnCfgFirst'
                 1-3 : The associated port whose traffic will be on the
                       ISDN B-channel which has the call and TEI objects
                       prefixed by `isgVGIsdnCfgFirst'."
        ::= { isgVGIsdnCfgChanTableEntry 9 }

        isgVGIsdnCfgFirstAccType OBJECT-TYPE
            SYNTAX INTEGER {
                    perm (1),
                    cmd  (2),
                    pmd  (3),
                    cvl  (4),
                    dov  (5)
                    }
            ACCESS read-write
            STATUS mandatory
            DESCRIPTION
                "perm : Dedicated (nailed-down) B-channel service.
                 cmd  : Dialed B-channel service: Circuit Mode.
                 pmd  : Dialed B-channel service: Packet Mode.
                 cvl  : Dialed B-channel service: Circuit Mode 
                        (Virtual Leased Line).
                 dov  : dialed B-channel service: Circuit Mode 
                        (Data over voice)."
        ::= { isgVGIsdnCfgChanTableEntry 10 }

        isgVGIsdnCfgFirstCallDisablSTm OBJECT-TYPE
            SYNTAX DisplayString (SIZE(0..5))
            ACCESS read-only
            STATUS mandatory
            DESCRIPTION
                "The Call Disable Start Time indicates whether ISDN 
                 calls will/will-not be blocked. This field is 
                 blank or displayed in the format `HHMM'.
                 blank : ISDN calls will not be blocked.
                 HHMM  : ISDN calls will be blocked starting at 
                         HH hour MM minutes."
        ::= { isgVGIsdnCfgChanTableEntry 11 }

        isgVGIsdnCfgFirstCallEnablSTm OBJECT-TYPE
            SYNTAX DisplayString (SIZE(0..5))
            ACCESS read-only
            STATUS mandatory
            DESCRIPTION
                "The Call Enable Start Time indicates whether ISDN 
                 calls will/will-not be blocked. This field is 
                 blank or displayed in the format `HHMM'.
                 blank : ISDN calls will not be blocked.
                 HHMM  : ISDN calls will be blocked starting at 
                         HH hour MM minutes."
        ::= { isgVGIsdnCfgChanTableEntry 12 }

        isgVGIsdnCfgFirstSPBU OBJECT-TYPE
            SYNTAX INTEGER {
                    disable (1),
                    enable  (2)
                    }
            ACCESS read-write
            STATUS mandatory
            DESCRIPTION
                "This port is configured to carry Same Port Backup 
                 (SPBU) feature. This feature requires the corresponding 
                 Port's Connection Type be SIMP."
        ::= { isgVGIsdnCfgChanTableEntry 13 }

        isgVGIsdnCfgFirstSPBUOpt OBJECT-TYPE
            SYNTAX DisplayString (SIZE(3..18))
            ACCESS read-write
            STATUS mandatory
            DESCRIPTION
                "Same Port Backup (SPBU) feature options
                 This defines the switch back criteria for the backup 
                 ISDN line.
                 NONE    : No SPBU feature options.
                 TIMEOUT : Based on a pre-configured timeout period.
                 CALL    : Based on the status of the Backup ISDN call.
                 Any combination of the above can be specified by 
                 summing (e.g. TIMEOUT+CALL)."
        ::= { isgVGIsdnCfgChanTableEntry 14 }

        isgVGIsdnCfgFirstSPBUTmOut OBJECT-TYPE
            SYNTAX INTEGER (1..240)
            ACCESS read-write
            STATUS mandatory
            DESCRIPTION
                "Same Port Backup (SPBU) Timeout Counter.
                 This defines the ISDN call duration time before a return 
                 to the leased line is attempted. This parameter is valid 
                 when TIMEOUT option is selected. The timeout period is a
                 1 minute interval."
        ::= { isgVGIsdnCfgChanTableEntry 15 }

        isgVGIsdnCfgFirstRate OBJECT-TYPE
            SYNTAX INTEGER {
                    rate64k  (1),
                    rate128k (2),
                    rate56k  (3),
                    rate112k (4)
                    }
            ACCESS read-write
            STATUS mandatory
            DESCRIPTION
                "This parameter specifies the line speed for this channel.
                 rate64k  : No Adaptation
                 rate128k : Bonded, no adaptation
                 rate56k  : Rate Adapted to 64K
                 rate112k : Rate Adapted to 12D8K."
        ::= { isgVGIsdnCfgChanTableEntry 16 }

        isgVGIsdnCfgFirstTEI OBJECT-TYPE
            SYNTAX INTEGER
            ACCESS read-write
            STATUS mandatory
            DESCRIPTION
                "The value for the TEI (Terminal Endpoint Identifier).
                 is provided by the service provider. The range is 
                 0..63, 127, 255. Select 127 for automatic TEI 
                 negotiation and 255 to use Packet D TEI."
        ::= { isgVGIsdnCfgChanTableEntry 17 }

        isgVGIsdnCfgFirstSPID OBJECT-TYPE
            SYNTAX DisplayString (SIZE(0..21))
            ACCESS read-write
            STATUS mandatory
            DESCRIPTION
                "The Service Profile ID identifies the service profile 
                 and is provided by the ISDN service provider."
        ::= { isgVGIsdnCfgChanTableEntry 18 }
        
        isgVGIsdnCfgFirstDN OBJECT-TYPE
            SYNTAX DisplayString (SIZE(0..17))
            ACCESS read-write
            STATUS mandatory
            DESCRIPTION
                "Local Subscriber Directory Number (DN)
                 DN is provided by the ISDN service provider."
        ::= { isgVGIsdnCfgChanTableEntry 19 }

        isgVGIsdnCfgFirstSubAddr OBJECT-TYPE
            SYNTAX DisplayString (SIZE(0..21))
            ACCESS read-write
            STATUS mandatory
            DESCRIPTION
                "Outgoing call : This subaddress will be sent in the call
                                 setup message.
                 Incoming call : This subaddress will be used for call
                                 verification if provided."
        ::= { isgVGIsdnCfgChanTableEntry 20 }

        isgVGIsdnCfgFirstOutDialNum1 OBJECT-TYPE
            SYNTAX DisplayString (SIZE(0..17))
            ACCESS read-write
            STATUS mandatory
            DESCRIPTION
                "The phone number to dial when establishing an ISDN 
                 outbound call."
        ::= { isgVGIsdnCfgChanTableEntry 21 }

        isgVGIsdnCfgFirstOutDialNum2 OBJECT-TYPE
            SYNTAX DisplayString (SIZE(0..17))
            ACCESS read-write
            STATUS mandatory
            DESCRIPTION
                "The phone number to dial if B1 Outbound Dial Number #1
                 is not available. Alternate attempts will be made between
                 Number#1 and Number#2."
        ::= { isgVGIsdnCfgChanTableEntry 22 }

        isgVGIsdnCfgFirstDialRetryIntrvl OBJECT-TYPE
            SYNTAX INTEGER
            ACCESS read-write
            STATUS mandatory
            DESCRIPTION
                "The Dial Retry Timer defines the time (1 second 
                 interval) between ISDN dial attempts. The range 
                 is 0, 15-3600. The timer will be disabled by a 
                 configuration of 0."
        ::= { isgVGIsdnCfgChanTableEntry 23 }

        isgVGIsdnCfgFirstNumCallRetries OBJECT-TYPE
            SYNTAX INTEGER (0..255)
            ACCESS read-write
            STATUS mandatory
            DESCRIPTION
                "The Dial Retry Counter specifies the number of times
                 the ISDN will attempt calling at the Call Retry Interval.
                 The value of 0 will allow unlimited number of attempts."
        ::= { isgVGIsdnCfgChanTableEntry 24 }

        isgVGIsdnCfgSecondChanPort OBJECT-TYPE
            SYNTAX INTEGER (0..3)
            ACCESS read-write
            STATUS mandatory
            DESCRIPTION
                "0   : No call or TEI activity for the following objects
                       prefixed by `isgVGIsdnCfgSecond'
                 1-3 : The associated port whose traffic will be on the
                       ISDN B-channel which has the call and TEI objects
                       prefixed by `isgVGIsdnCfgSecond'."
        ::= { isgVGIsdnCfgChanTableEntry 25 }

        isgVGIsdnCfgSecondAccType OBJECT-TYPE
            SYNTAX INTEGER {
                    perm (1),
                    cmd  (2),
                    pmd  (3),
                    cvl  (4),
                    dov  (5)
                    }
            ACCESS read-write
            STATUS mandatory
            DESCRIPTION
                "perm : Dedicated (nailed-down) B-channel service.
                 cmd  : Dialed B-channel service: Circuit Mode.
                 pmd  : Dialed B-channel service: Packet Mode.
                 cvl  : Dialed B-channel service: Circuit Mode 
                        (Virtual Leased Line).
                 dov  : dialed B-channel service: Circuit Mode 
                        (Data over voice)."
        ::= { isgVGIsdnCfgChanTableEntry 26 }

        isgVGIsdnCfgSecondCallDisablSTm OBJECT-TYPE
            SYNTAX DisplayString (SIZE(0..5))
            ACCESS read-only
            STATUS mandatory
            DESCRIPTION
                "The Call Disable Start Time indicates whether ISDN 
                 calls will/will-not be blocked. This field is blank 
                 or displayed in the format `HHMM'.
                 blank : ISDN calls will not be blocked.
                 HHMM  : ISDN calls will be blocked starting at 
                         HH hour MM minutes."
        ::= { isgVGIsdnCfgChanTableEntry 27 }

        isgVGIsdnCfgSecondCallEnablSTm OBJECT-TYPE
            SYNTAX DisplayString (SIZE(0..5))
            ACCESS read-only
            STATUS mandatory
            DESCRIPTION
                "The Call Enable Start Time indicates whether ISDN 
                 calls will/will-not be blocked. This field is blank 
                 or displayed in the format `HHMM'.
                 blank : ISDN calls will not be blocked.
                 HHMM  : ISDN calls will be blocked starting at 
                         HH hour MM minutes."
        ::= { isgVGIsdnCfgChanTableEntry 28 }

        isgVGIsdnCfgSecondSPBU OBJECT-TYPE
            SYNTAX INTEGER {
                    disable (1),
                    enable  (2)
                    }
            ACCESS read-write
            STATUS mandatory
            DESCRIPTION
                "This port is configured to carry Same Port Backup 
                 (SPBU) feature. This feature requires the corresponding 
                 Port's Connection Type be SIMP."
        ::= { isgVGIsdnCfgChanTableEntry 29 }

        isgVGIsdnCfgSecondSPBUOpt OBJECT-TYPE
            SYNTAX DisplayString (SIZE(3..18))
            ACCESS read-write
            STATUS mandatory
            DESCRIPTION
                "Same Port Backup (SPBU) feature options
                 This defines the switch back criteria for the backup 
                 ISDN line.
                 NONE    : No SPBU feature options.
                 TIMEOUT : Based on a pre-configured timeout period.
                 CALL    : Based on the status of the Backup ISDN call.
                 Any combination of the above can be specified by 
                 summing (e.g. TIMEOUT+CALL)."
        ::= { isgVGIsdnCfgChanTableEntry 30 }

        isgVGIsdnCfgSecondSPBUTmOut OBJECT-TYPE
            SYNTAX INTEGER (1..240)
            ACCESS read-write
            STATUS mandatory
            DESCRIPTION
                "Same Port Backup (SPBU) Timeout Counter.
                 This defines the ISDN call duration time before a return
                 to the leased line is attempted. This parameter is valid 
                 when TIMEOUT option is selected.The timeout period is a 1
                 minute interval."
        ::= { isgVGIsdnCfgChanTableEntry 31 }

        isgVGIsdnCfgSecondRate OBJECT-TYPE
            SYNTAX INTEGER {
                    rate64k  (1),
                    rate56k  (3)
                    }
            ACCESS read-write
            STATUS mandatory
            DESCRIPTION
                "This parameter specifies the line speed for this channel.
                 rate64k  : No Adaptation
                 rate56k  : Rate Adapted to 64K."
        ::= { isgVGIsdnCfgChanTableEntry 32 }

        isgVGIsdnCfgSecondTEI OBJECT-TYPE
            SYNTAX INTEGER
            ACCESS read-write
            STATUS mandatory
            DESCRIPTION
                "The value for the TEI (Terminal Endpoint Identifier).
                 is provided by the service provider. The range is 
                 0..63, 127, 255. Select 127 for automatic TEI 
                 negotiation and 255 to use TEI selected for B1."
        ::= { isgVGIsdnCfgChanTableEntry 33 }

        isgVGIsdnCfgSecondSPID OBJECT-TYPE
            SYNTAX DisplayString (SIZE(0..21))
            ACCESS read-write
            STATUS mandatory
            DESCRIPTION
                "The Service Profile ID identifies the service profile 
                 and is provided by the ISDN service provider."
        ::= { isgVGIsdnCfgChanTableEntry 34 }
        
        isgVGIsdnCfgSecondDN OBJECT-TYPE
            SYNTAX DisplayString (SIZE(0..17))
            ACCESS read-write
            STATUS mandatory
            DESCRIPTION
                "Local Subscriber Directory Number (DN)
                 DN is provided by the ISDN service provider."
        ::= { isgVGIsdnCfgChanTableEntry 35 }

        isgVGIsdnCfgSecondSubAddr OBJECT-TYPE
            SYNTAX DisplayString (SIZE(0..21))
            ACCESS read-write
            STATUS mandatory
            DESCRIPTION
                "Outgoing call : This subaddress will be sent in the call
                                 setup message.
                 Incoming call : This subaddress will be used for call
                                 verification if provided."
        ::= { isgVGIsdnCfgChanTableEntry 36 }

        isgVGIsdnCfgSecondOutDialNum1 OBJECT-TYPE
            SYNTAX DisplayString (SIZE(0..17))
            ACCESS read-write
            STATUS mandatory
            DESCRIPTION
               "The phone number to dial when establishing an 
                ISDN outbound call."
        ::= { isgVGIsdnCfgChanTableEntry 37 }

        isgVGIsdnCfgSecondOutDialNum2 OBJECT-TYPE
            SYNTAX DisplayString (SIZE(0..17))
            ACCESS read-write
            STATUS mandatory
            DESCRIPTION
                "The phone number to dial if B1 Outbound Dial Number #1
                 is not available. Alternate attempts will be made between
                 Number#1 and Number#2."
        ::= { isgVGIsdnCfgChanTableEntry 38 }

        isgVGIsdnCfgSecondDialRetryIntrvl OBJECT-TYPE
            SYNTAX INTEGER
            ACCESS read-write
            STATUS mandatory
            DESCRIPTION
                "The Dial Retry Timer defines the time (1 second interval) 
                 between ISDN dial attempts. The range is 0, 15-3600. The
                 timer will be disabled by a configuration of 0."
        ::= { isgVGIsdnCfgChanTableEntry 39 }

        isgVGIsdnCfgSecondNumCallRetries OBJECT-TYPE
            SYNTAX INTEGER (0..255)
            ACCESS read-write
            STATUS mandatory
            DESCRIPTION
                "The Dial Retry Counter specifies the number of times
                 the ISDN will attempt calling at the Call Retry Interval.
                 The value of 0 will allow unlimited number of attempts."
        ::= { isgVGIsdnCfgChanTableEntry 40 }

        isgVGIsdnCfgFirstPlainOldTelSet OBJECT-TYPE
            SYNTAX DisplayString 
            ACCESS read-write
            STATUS mandatory
            DESCRIPTION
                "none:   No Telephone support required
		 pots1:  Plain Old Telephone Set 1 connected"
        ::= { isgVGIsdnCfgChanTableEntry 41 }

        isgVGIsdnCfgFirstCallPerm  OBJECT-TYPE
            SYNTAX DisplayString 
            ACCESS read-write
            STATUS mandatory
            DESCRIPTION
                "out - Initiates Call only, does not accept call
		 inc - Accepts Call only, does not send call to network"
        ::= { isgVGIsdnCfgChanTableEntry 42 }

        isgVGIsdnCfgFirstChSelect OBJECT-TYPE
            SYNTAX INTEGER {
		 preferred  (1),
		 exclusive  (3)
		}
            ACCESS read-write
            STATUS mandatory
            DESCRIPTION
                "exclusive - implies channel requested will be fixed with
		             the configured selection
		 preferred - it will be up to the network to grant a channel
				for connection"
        ::= { isgVGIsdnCfgChanTableEntry 43 }

        isgVGIsdnCfgSecondPlainOldTelSet OBJECT-TYPE
            SYNTAX DisplayString 
            ACCESS read-write
            STATUS mandatory
            DESCRIPTION
                "none:   No Telephone support required
		 pots1:  Plain Old Telephone Set 1 connected
		 pots2:  Plain Old Telephone Set 2 connected"
        ::= { isgVGIsdnCfgChanTableEntry 44 }

        isgVGIsdnCfgSecondCallPerm OBJECT-TYPE
            SYNTAX DisplayString 
            ACCESS read-write
            STATUS mandatory
            DESCRIPTION
                "out - Initiates Call only, does not accept call
		 inc - Accepts Call only, does not send call to network"
        ::= { isgVGIsdnCfgChanTableEntry 45 }

        isgVGIsdnCfgSecondChSelect OBJECT-TYPE
            SYNTAX INTEGER {
                 preferred  (1),
                 exclusive  (3)
                }
            ACCESS read-write
            STATUS mandatory
            DESCRIPTION
                "exclusive - implies channel requested will be fixed with
		             the configured selection
		 preferred - it will be up to the network to grant a channel
				for connection"
        ::= { isgVGIsdnCfgChanTableEntry 46 }

        -- ISDN Statistics
        -- Current Call Statistics

        isgVGIsdnStats OBJECT IDENTIFIER ::= { isgIsdnStatsGroup 1 }

        isgVGIsdnCCStatsTbl OBJECT-TYPE
            SYNTAX SEQUENCE OF IsgVGIsdnCCStatsTblEntry
            ACCESS not-accessible
            STATUS mandatory
            DESCRIPTION
                "ISDN DSL Current Call Statistics Table."
        ::= { isgVGIsdnStats 1 }
     
        isgVGIsdnCCStatsTblEntry OBJECT-TYPE
            SYNTAX IsgVGIsdnCCStatsTblEntry
            ACCESS not-accessible
            STATUS mandatory
            DESCRIPTION
                "Current Call Statistics Table Entries."
            INDEX { isgVGIsdnCCStatsDSLNum, 
                    isgVGIsdnCCStatsChType }
        ::= { isgVGIsdnCCStatsTbl  1 }
    
        IsgVGIsdnCCStatsTblEntry  ::=
            SEQUENCE {
                isgVGIsdnCCStatsDSLNum
                    INTEGER,
                isgVGIsdnCCStatsChType
                    INTEGER,
                isgVGIsdnCCStatsSwtchType
                    INTEGER,
                isgVGIsdnCCStatsL1State
                    INTEGER,
                isgVGIsdnCCStatsTEI
                    INTEGER,
                isgVGIsdnCCStatsCallgAddr
                    DisplayString,
                isgVGIsdnCCStatsCalldAddr
                    DisplayString,
                isgVGIsdnCCStatsSubaddr
                    DisplayString,
                isgVGIsdnCCStatsDirection
                    INTEGER,
                isgVGIsdnCCStatsCallStatus
                    INTEGER,
                isgVGIsdnCCStatsAccType
                    INTEGER,
                isgVGIsdnCCStatsLineSpeed
                    INTEGER,
                isgVGIsdnCCStatsPortConn
                    INTEGER,
                isgVGIsdnCCStatsCauseCode
                    INTEGER,
                isgVGIsdnCCStatsCallStarted
                    DisplayString,
                isgVGIsdnCCStatsDChanStatus
                    INTEGER,
                isgVGIsdnCCStatsTrmStatus
                    INTEGER,
                isgVGIsdnCCStatsTrmTei
                    INTEGER
                }

       isgVGIsdnCCStatsDSLNum OBJECT-TYPE
           SYNTAX INTEGER
           ACCESS read-only
           STATUS mandatory
           DESCRIPTION
               "Digital Service Loop Number."
       ::= { isgVGIsdnCCStatsTblEntry  1 }

       isgVGIsdnCCStatsChType OBJECT-TYPE
           SYNTAX INTEGER {
                   dChannel  (1),
                   b1Channel (2),
                   b2Channel (3)
                   }
           ACCESS read-only
           STATUS mandatory
           DESCRIPTION
               "ISDN Channel Type."
       ::= { isgVGIsdnCCStatsTblEntry  2 }

       isgVGIsdnCCStatsSwtchType OBJECT-TYPE
           SYNTAX INTEGER {
                   bri1tr6Stype   (2),
                   bri5essStype   (3),
                   briDms100Stype (6),
                   briKddStype    (8),
                   briEtsiStype   (9),
                   briNi1Stype    (11),
                   briNttStype    (13),
                   briTs013Stype  (14),
                   briVnStype     (15),
                   unsupported    (16)
                   }
           ACCESS read-only
           STATUS mandatory
           DESCRIPTION
               "Switch Type.
                bri1tr6Stype    : German National ISDN.
                bri5essStype    : AT&T switch
                briDms100Stype  : DMS 100.
                briKddStype     : Japanese International Access ISDN.
                briEtsiStype    : Euro ISDB BRI (NET3).
                briNi1Stype     : National ISDN version 1.
                briNttStype     : Japanese National ISDN.
                briTs013Stype   : Australian National ISDN.
                briVnStype      : France National ISDN.
                unsupported       : Unsupported Switch Type."
       ::= { isgVGIsdnCCStatsTblEntry  3 }

       isgVGIsdnCCStatsL1State OBJECT-TYPE
           SYNTAX INTEGER {
                   l1Setup     (1),
                   l1Active    (2),
                   l1Deactive  (3),
                   l1B1Loop    (4),
                   l1B2Loop    (5),
                   l1B1B2Loop  (6),
                   l12BDLoop   (7),
                   unknown     (8)
                   }
           ACCESS read-only
           STATUS mandatory
           DESCRIPTION
               "Level1 State.
                l1Setup     : Setup State.
                l1Active    : Active State.
                l1Deactive  : Inactive State.
                l1B1Loop    : Loop Test State.
                l1B2Loop    : Loop Test State.
                l1B1B2Loop  : Loop Test State.
                l12BDLoop   : Loop Test State.
                unknown     : Loop Test State."
       ::= { isgVGIsdnCCStatsTblEntry  4 }

       isgVGIsdnCCStatsTEI OBJECT-TYPE
           SYNTAX INTEGER
           ACCESS read-only
           STATUS mandatory
           DESCRIPTION
               "Terminal Endpoint Identifier."
       ::= { isgVGIsdnCCStatsTblEntry  5 }

       isgVGIsdnCCStatsCallgAddr OBJECT-TYPE
           SYNTAX DisplayString (SIZE(0..21))
           ACCESS read-only
           STATUS mandatory
           DESCRIPTION
               "Current Call Statistics : Calling Address."
       ::= { isgVGIsdnCCStatsTblEntry  6 }
       
       isgVGIsdnCCStatsCalldAddr OBJECT-TYPE
           SYNTAX DisplayString (SIZE(0..21))
           ACCESS read-only
           STATUS mandatory
           DESCRIPTION
               "Current Call Statistics : Called Address."
       ::= { isgVGIsdnCCStatsTblEntry  7 }

       isgVGIsdnCCStatsSubaddr OBJECT-TYPE
           SYNTAX DisplayString (SIZE(0..21))
           ACCESS read-only
           STATUS mandatory
           DESCRIPTION
               "Current Call Statistics : Call Subaddress."
       ::= { isgVGIsdnCCStatsTblEntry  8 }

       isgVGIsdnCCStatsDirection OBJECT-TYPE
           SYNTAX INTEGER {
                   noCall    (1),
                   outgoing  (2),
                   incoming  (3),
                   collision (4)
                   }
           ACCESS read-only
           STATUS mandatory
           DESCRIPTION
               "Current Call Statistics : Call Direction.
                noCall    : Channel is idle.
                outgoing  : Call is coming from Vanguard 
                            into the ISDN network.
                incoming  : Call is coming into Vanguard 
                            from the ISDN Network.
                collision : A Call collision is detected."
       ::= { isgVGIsdnCCStatsTblEntry  9 }

       isgVGIsdnCCStatsAccType OBJECT-TYPE
           SYNTAX INTEGER {
                   permanent      (1),
                   cktMode        (2),
                   pktMode        (3),
                   cvl            (4),
                   notApplicable  (5)
                   }
           ACCESS read-only
           STATUS mandatory
           DESCRIPTION
               "Current Call Statistics : Channel Access Type.
                permanent      : Permanent B is selected.
                cktMode        : Dialed B-channel service: Circuit Mode.
                pktMode        : Dialed B-channel service: Packet Mode.
                cvl            : Dialed B-channel service: Circuit Mode
                                 (Virtual Leased Line)."
       ::= { isgVGIsdnCCStatsTblEntry  10 }

       isgVGIsdnCCStatsCallStatus OBJECT-TYPE
           SYNTAX INTEGER {
                   waitInit      (1),
                   initFail      (2),
                   termIdle      (3),
                   callInit      (4),
                   discSent      (5),
                   hostProc      (6),
                   callConn      (7),
                   notApplicable (8)
                   }
           ACCESS read-only
           STATUS mandatory
           DESCRIPTION
               "Current Call Statistics : Call Status.
                waitInit      : FIT waiting for SPID registration.
                initFail      : FIT's SPID registration has failed.
                termIdle      : Terminal is currently idle 
                                (ready for calls).
                callInit      : An outbound call setup is sent.
                discSent      : A disconnect request is sent.
                hostProc      : In Call Proc./Alert State.
                callConn      : An outbound/inbound call is connected.
                notApplicable : Not applicable to this channel.
                This object is only applicable to B1/B2 Channels."
       ::= { isgVGIsdnCCStatsTblEntry  11 }

       isgVGIsdnCCStatsLineSpeed OBJECT-TYPE
           SYNTAX INTEGER {
                   rate64k  (1),
                   rate56k  (2),
                   rate0k   (3)
                   }
           ACCESS read-only
           STATUS mandatory
           DESCRIPTION
                "Current Call Statistics : Line Speed.
                 rate64k  : No Adaptation
                 rate128k : Bonded, no adaptation
                 rate56k  : Rate Adapted to 64K
                 rate112k : Rate Adapted to 12D8K."
       ::= { isgVGIsdnCCStatsTblEntry  12 }

       isgVGIsdnCCStatsPortConn OBJECT-TYPE
           SYNTAX INTEGER
           ACCESS read-only
           STATUS mandatory
           DESCRIPTION
               "Current Call Statistics : Port number to carry this call."
       ::= { isgVGIsdnCCStatsTblEntry  13 }

       isgVGIsdnCCStatsCauseCode OBJECT-TYPE
           SYNTAX INTEGER
           ACCESS read-only
           STATUS mandatory
           DESCRIPTION
               "Current Call Statistics : Cause Code sent/received in the 
                                           Q.931 message."
       ::= { isgVGIsdnCCStatsTblEntry  14 }

       isgVGIsdnCCStatsCallStarted OBJECT-TYPE
           SYNTAX DisplayString (SIZE(0..18))
           ACCESS read-only
           STATUS mandatory
           DESCRIPTION
               "Current Call Statistics : Call Start Time."
       ::= { isgVGIsdnCCStatsTblEntry  15 }

       isgVGIsdnCCStatsDChanStatus OBJECT-TYPE
           SYNTAX INTEGER {
                   enabled  (1),
                   disabled (2)
                   }
           ACCESS read-only
           STATUS mandatory
           DESCRIPTION
               "enabled  : D channel is enabled.
                disabled : D channel is disabled."
       ::= { isgVGIsdnCCStatsTblEntry  16 }

       isgVGIsdnCCStatsTrmStatus OBJECT-TYPE
           SYNTAX INTEGER {
                   fitWaitInit    (1),
                   fitFailed      (2),
                   fitTimeout     (3),
                   networkTimeout (4),
                   spiDerror      (5),
                   online         (6)
                   }
           ACCESS read-only
           STATUS mandatory
           DESCRIPTION
               "fitWaitInit    : Fully Initializing Terminal (FIT)
                                 is waiting for SPID registration.
                fitFailed      : FIT registration failed, check alarm
                                 for cause.
                fitTimeout     : SPID registration has timed out,
                                 waiting for retry.
                networkTimeout : Network is not responding to SPID
                                 registration sent.
                spidError      : Network rejected SPID registration
                                 due to error in the ID.
                online         : Terminal is ready for ISDN
                                 communication."
       ::= { isgVGIsdnCCStatsTblEntry  17 }

       isgVGIsdnCCStatsTrmTei OBJECT-TYPE
           SYNTAX INTEGER
           ACCESS read-only
           STATUS mandatory
           DESCRIPTION
               "Terminal (B1/B2) TEI."
       ::= { isgVGIsdnCCStatsTblEntry  18 }

       -- Call History Table

       isgVGIsdnCHStatsTbl OBJECT-TYPE
           SYNTAX SEQUENCE OF IsgVGIsdnCHStatsTblEntry
           ACCESS not-accessible
           STATUS mandatory
           DESCRIPTION
               "ISDN DSL Call History Table."
        ::= { isgVGIsdnStats 2 }
     
        isgVGIsdnCHStatsTblEntry OBJECT-TYPE
            SYNTAX IsgVGIsdnCHStatsTblEntry
            ACCESS not-accessible
            STATUS mandatory
            DESCRIPTION
                "ISDN DSL Call History Table Entries."
            INDEX { isgVGIsdnCHStatsDSLNum, 
                    isgVGIsdnCHStatsChType,
                    isgVGIsdnCHStatsSession }
        ::= { isgVGIsdnCHStatsTbl 1 }
    
        IsgVGIsdnCHStatsTblEntry ::=
            SEQUENCE {
                isgVGIsdnCHStatsDSLNum
                    INTEGER,
                isgVGIsdnCHStatsChType
                    INTEGER,
                isgVGIsdnCHStatsSession
                    INTEGER,
                isgVGIsdnCHStatsNumCalld
                    DisplayString,
                isgVGIsdnCHStatsDirection
                    INTEGER,
                isgVGIsdnCHStatsCauseCode
                    INTEGER,
                isgVGIsdnCHStatsLineSpeed
                    INTEGER,
                isgVGIsdnCHStatsAsscPort
                    INTEGER,
                isgVGIsdnCHStatsStrtTm
                    DisplayString,
                isgVGIsdnCHStatsEndTm
                    DisplayString
                }

        isgVGIsdnCHStatsDSLNum OBJECT-TYPE
            SYNTAX INTEGER
            ACCESS read-only
            STATUS mandatory
            DESCRIPTION
                "Digital Service Loop Number."
        ::= { isgVGIsdnCHStatsTblEntry 1 }

        isgVGIsdnCHStatsChType OBJECT-TYPE
            SYNTAX INTEGER{
                    b1Channel (1),
                    b2Channel (2)
                    }
            ACCESS read-only
            STATUS mandatory
            DESCRIPTION
                "ISDN Channel Type."
        ::= { isgVGIsdnCHStatsTblEntry 2 }

        isgVGIsdnCHStatsSession OBJECT-TYPE
            SYNTAX INTEGER (0..2)
            ACCESS read-only
            STATUS mandatory
            DESCRIPTION
                "Call Session Number tracked.
                 0 : Most Recent call.
                 1 : Previous call.
                 2 : Oldest call."
        ::= { isgVGIsdnCHStatsTblEntry 3 }

        isgVGIsdnCHStatsNumCalld OBJECT-TYPE
            SYNTAX DisplayString (SIZE(0..31))
            ACCESS read-only
            STATUS mandatory
            DESCRIPTION
                "If the call is outgoing, this is the phone number that
                 has been called.
                 If the call is incoming, this is the number that is calling
                 (provided the line has subscribed to Caller ID Display."
        ::= { isgVGIsdnCHStatsTblEntry 4 }

        isgVGIsdnCHStatsDirection OBJECT-TYPE
            SYNTAX INTEGER {
                    noCall    (1),
                    outgoing  (2),
                    incoming  (3),
                    collision (4)
                    }
            ACCESS read-only
            STATUS mandatory
            DESCRIPTION
                "Direction of the call.
                 noCall    : Channel is idle.
                 outgoing  : Call is coming from Vanguard 
                             into the ISDN network.
                 incoming  : Call is coming into Vanguard 
                             from the ISDN Network.
                 collision : A Call collision is detected."
        ::= { isgVGIsdnCHStatsTblEntry 5 }

        isgVGIsdnCHStatsCauseCode OBJECT-TYPE
            SYNTAX INTEGER
            ACCESS read-only
            STATUS mandatory
            DESCRIPTION
                "Cause Code sent/received in the Q.931 message."
        ::= { isgVGIsdnCHStatsTblEntry 6 }

        isgVGIsdnCHStatsLineSpeed OBJECT-TYPE
            SYNTAX INTEGER {
                    rate64k  (1),
                    rate56k  (2),
                    rate0k   (3)
                    }
            ACCESS read-only
            STATUS mandatory
            DESCRIPTION
                "Line Speed for the call.
                 rate64k  : No Adaptation
                 rate56k  : Rate Adapted to 64K
                 rate0k   : Rate Adapted to 0K."
        ::= { isgVGIsdnCHStatsTblEntry  7 }

        isgVGIsdnCHStatsAsscPort OBJECT-TYPE
            SYNTAX INTEGER
            ACCESS read-only
            STATUS mandatory
            DESCRIPTION
                "Associated Port number to carry this call."
        ::= { isgVGIsdnCHStatsTblEntry  8 }

        isgVGIsdnCHStatsStrtTm OBJECT-TYPE
            SYNTAX DisplayString (SIZE(0..18))
            ACCESS read-only
            STATUS mandatory
            DESCRIPTION
                "Call Start Time."
        ::= { isgVGIsdnCHStatsTblEntry 9 }

        isgVGIsdnCHStatsEndTm OBJECT-TYPE
            SYNTAX DisplayString (SIZE(0..13))
            ACCESS read-only
            STATUS mandatory
            DESCRIPTION
                "Call End Time."
        ::= { isgVGIsdnCHStatsTblEntry 10 }

        -- ISDN PRI Stats

        isgVGIsdnPRICCStatsTbl OBJECT-TYPE
            SYNTAX SEQUENCE OF IsgVGIsdnPRICCStatsTblEntry
            ACCESS not-accessible
            STATUS mandatory
            DESCRIPTION
                "ISDN PRI DSL Current Call Statistics Table."
        ::= { isgVGIsdnStats 3 }

        isgVGIsdnPRICCStatsTblEntry OBJECT-TYPE
            SYNTAX IsgVGIsdnPRICCStatsTblEntry
            ACCESS not-accessible
            STATUS mandatory
            DESCRIPTION
                "PRI Current Call Statistics Table Entries."
            INDEX { isgVGIsdnPRICCStatsDSLNum }
        ::= { isgVGIsdnPRICCStatsTbl  1 }

        IsgVGIsdnPRICCStatsTblEntry  ::=
            SEQUENCE {
                isgVGIsdnPRICCStatsDSLNum
                    INTEGER,
                isgVGIsdnPRICCStatsSwtchType
                    INTEGER,
                isgVGIsdnPRICCStatsDChannelState
                    INTEGER
                }

       isgVGIsdnPRICCStatsDSLNum OBJECT-TYPE
           SYNTAX INTEGER
           ACCESS read-only
           STATUS mandatory
           DESCRIPTION
               "Digital Service Loop Number."
       ::= { isgVGIsdnPRICCStatsTblEntry  1 }

       isgVGIsdnPRICCStatsSwtchType OBJECT-TYPE
           SYNTAX INTEGER {
                   priUnspecifiedStype  (1),
                   priNi2Stype          (2),
                   pri5essStype         (3),
                   priDms100Stype       (4),
                   priNttStype          (5),
                   priTs014Stype        (6),
                   priEtsiStype         (7),
                   priQsigMStype        (8),
                   priQsigSStype        (9),
                   priT1QsigMStype      (10),
                   priT1QsigSStype      (11),
                   unsupported          (12)
                   }
           ACCESS read-only
           STATUS mandatory
           DESCRIPTION
               "Switch Type.
                bri1tr6Stype    : German National ISDN.
                priNi2Stype     : National ISDN version 2.
                pri5essStype    : AT&T switch
                priDms100Stype  : DMS 100.
                priNttStype     : Japanese National ISDN.
                priTs014Stype   : Australian National ISDN.
                priEtsiStype    : Euro ISDB BRI (NET3).
                priQsigMStype   : Master Side QSIG PBX.
                priQsigSStype   : Slave Side QSIG PBX.
                priT1QsigMStype : T1 Master Side QSIG PBX.
                priT1QsigSStype : T1 Slave Side QSIG PBX.
                unsupported     : Unsupported Switch Type."
       ::= { isgVGIsdnPRICCStatsTblEntry  2 }

       isgVGIsdnPRICCStatsDChannelState OBJECT-TYPE
           SYNTAX INTEGER {
                   dChannelUp     (1),
                   dChannelDown   (2),
                   unknown        (3)
                   }
           ACCESS read-only
           STATUS mandatory
           DESCRIPTION
               "D Channel Status.
                dChannelUp      : D Channel Up.
                dChannelDown    : D Channel Down.
                unknown         : Loop Test State."
       ::= { isgVGIsdnPRICCStatsTblEntry  3 }

        -- ISDN Controls

        isgVGIsdnBootChannel OBJECT-TYPE
            SYNTAX INTEGER {
                    boot    (1),
                    noBoot  (2)
                    }
            ACCESS write-only
            STATUS mandatory
            DESCRIPTION
                "Boot the ISDN channels."
        ::= { isgIsdnCtrlGroup 1 }

        END
