-- ============================================================================
-- Copyright (C) 2003 by  HUAWEI-3COM TECHNOLOGIES. All rights reserved.
--
-- Description: this mib will maintain the products mib oid and management
--              properties root node for Huawei-3Com products
--
-- Reference:  original from huawei-oid-mib and huawei-datacomm-oid-mib
-- Version:     V1.73
-- History:
--      V1.00 2003/12/23 created by xiejianping
--      V1.01 2004/6/11 add 'ar18-36' and 'ar18-37'
--      V1.02 2004/6/11 add 'h3cVoiceVlan'
--      V1.03 2004/6/18 add 'h3cL4Redirect'
--      V1.04 2004/6/21 add 'router' and 'dlsw' from original huawei MIB baseline
--      V1.05 2004/6/23 add vdg10-40 vdg10-41 e026
--                      e026-SI e050 from original huawei-oid-mib
--      V1.06 2004/6/25 add 's8508'
--      V1.07 2004/6/29 add 'secpath100N','secpath100V','secpath100S'
--      V1.10 2004/6/30 add all properties root node in h3c-mib-baseline library
--      V1.11 2004/7/1  change node 's3552F-EI' to 's3552F-HI'
--                      & add sr8805,sr8808,sr8812 sysoid
--      V1.12 2004/7/2  add 's5624P','s5624P-PWR','s5648P','s5648P-PWR'
--            2004/7/5  modify node name 's2008C','s2016C','s2403I'
--                      to 's2008-EI','s2016-EI','s2403H-EI'
--            2004/7/7  add 's2008C','s2016C','s2024C','ar18-13V','ar18-18v'
--            2004/7/13 add 'isPath1000'
--      V1.13 2004/7/14 synchronization with huawei-datacomm-oid.mib
--                      add follow nodes:
--                      hwEntityExtentMIB,hwQoS,hwMultilinkPPP,hwTCPMib,hwBGPMib
--      V1.14 2004/7/19 add 'ar18-20S'
--      V1.15 2004/7/27 add 'h3cIpPBX'
--      V1.16 2004/7/28 add 'h3cUser', 'h3cRadius'
--      V1.17 2004/7/28 add 'h3cPowerEthernetExt'
--      V1.18 2004/8/4  add 'h3cEntityRelation'
--      V1.19 2004/8/17 add 'wellhope' node & add 14 sysoids under wellhope for OEM
--      V1.20 2004/8/24 add 'h3cProtocolVlan'
--      V1.21 2004/8/24 add 'h3cQosProfile'
--      V1.22 2004/8/25 modify node name 'ar18-36','ar18-37' to 'ar18-33E','ar18-34E'
--      V1.23 2004/8/31 add 'xe200', 'xe2000'
--      V1.24 2004/9/9  change some nodes root from 'products' to 'lanSw',
--                      nodes list: s3552F-SI,s3552F-EI,e026,e026-SI,e050
--      V1.25 2004/10/10 add 'h3cNat'
--      V1.26 2004/10/10 modify node ID of 'hwCluster' from 6 to 7
--      V1.27 2004/10/11 add 'h3cPos'
--      V1.28 2004/10/14 add subnode 20 under h3cCommon,
--                       modify node 'hwLswVlan'(under huaweiDatacomm)
--                       to 'hwVlan' resolve name conflict.
--      V1.29 2004/10/15 add 'e026T','e008-FE','e017-FE','e026-FE';
--                       modify node name 's3026E_FM','s3026E_FS','s3526E_FM','s3526E_FS'
--                       to 's3026E-FM','s3026E-FS','s3526E-FM','s3526E-FS'.
--      V1.30 2004/10/29 add 'ar28-12','ar28-13','ar28-14';
--      V1.31 2004/11/8  add 'h3cAAL5' and 'h3cSSH';
--      V1.33 2004/11/10 add 'h3cRSA';
--      V1.34 2004/11/10 add 'ar18-10','ar18-21','ar18-21A','ar18-21B',
--                       'ar18-21C','ar18-22','ar18-22-8','ar18-22-24',
--                       'ar18-23-1','ar18-30E','ar18-31E','ar18-32E',
--                       'ar18-35E','ar18-36E','ar18-37E','ar18-52';
--            2004/11/23 add 's6502';
--      V1.35 2004/11/27 add 'h3cVrrpExt';
--      V1.36 2004/12/2  add 'S5124P-EI','S5126C-EI','S5148P-EI','S5150C-EI',
--                       'S5116P-SI','S5124P-SI','S5148P-SI',
--                       'h3cIpa','h3cPortSecurity';
--      V1.37 2004/12/6  add 'ar4620E','ar4640E','ar4680E','h3cVpls';
--      V1.38 2004/12/10 add 'h3cE1','h3cT1';
--      V1.39 2004/12/13 add 'h3cIkeMonitor';
--      V1.40 2004/12/15 add 'h3cIfExt';
--      V1.41 2004/12/16 add 'h3cWebSwitch','h3cAutoDetect';
--      V1.42 2004/12/16 add 'h3cIpBroadcast' and 'h3cIpx';
--      V1.43 2004/12/20 modife node name 'secpath100S' to 'secpath100F' by xiedong
--      V1.44 2004/12/21 add 'secpath1000F' and 'h3cCfCard';
--      V1.45 2004/12/24 add 'ar18-22s-8' and 'ar18-23s-1';
--      V1.46 2004/12/24 add 'h3cIPS';
--              V1.47 2004/12/29 add 'secEngineP500','h3cEpon','h3cDldp' by xiejianping;
--      V1.48 2005/1/6 add 's2108-SI','s2116-SI','s2126-SI','s2108-EI',
--                     's2116-EI','s2126-EI','s5624F' by xiejianping;
--      V1.49 2005/1/13 add 'h3cDhcpSnoop' by gaolong;
--      V1.50 2005/1/17 add 's3224P','s3226T','s3226P',
--                      's3250T','s3250P' by xiejianping;
--      V1.51 2005/1/31 add 'h3cProtocolPriority' by gaolong;
--      V1.52 2005/2/5 add 'S3108T', 'S3116T', 'S3126T', 'S3108C', 'S3116C',
--                      'S3126C' by gaolong;
--                     add 'h3cTrap' by gaolong;
--              V1.53 2005/2/5 add 'h3cUnicast' by xiejianping
--              V1.54 2005/3/3 add 'h3cRrpp' by xiejianping
--              V1.55 2005/3/10 modify 'h3cIkeMonitor' to 'h3cIKEMonitor' by gaolong
--              V1.56 2005/3/25 add 'ar28-12B' by xiejianping
--      V1.57 2005/3/26 modify product id name for S5624F by gaolong
--                      add 'secBladeIDS', 'secBladeIPS' by gaolong
--                      add 'h3cDomain', 'h3cIds' by gaolong
--                      modify initial character of some products
--                      modify object name for IPSec monitor
--      V1.58 2005/4/1 add 'secEngineD500' by xiejianping
--      V1.59 2005/4/14 add 's3928TP-V6','s3928P-V6','s3952P-V6',
--                      's3928F-V6','s5524P','s5524F' by xiejianping
--      V1.60 2005/4/15 add 'h3cRcr', 'xE7000', 'vg10-40', 'vg10-41',
--                      'vg20-16', 'vg20-32', 'vg20-08L', 'vg80-20',
--                      'vg80-20T' by gaolong
--      V1.61 2005/4/21 add 'h3cAtmDxi' by xiejianping
--      V1.62 2005/5/3 add 'h3cVoice' by gaolong
--      V1.63 2005/5/13 add 's2008CT','s2008CP' by xiejianping
--      V1.64 2005/5/20 add 'secBladeFW','secBladeVPN' by xiejianping
--      V1.65 2005/5/25 add 'secpath500F', 'h3cMulticast' and 'h3cMpm' by gaolong
--                      change name of subnode 20 under h3cCommon to 'h3cNS'
--      V1.66 2005/6/12 add 'secpath10F', 'h3cOadp', 'h3cTunnel', 'h3cGre' by gaolong
--      V1.67 2005/6/20 add 'secEngineD200' by gaolong
--      V1.68 2005/6/25 add 'intransa' and its subidentifier 'ix5000',
--                      add 'h3cStorage', 'h3cObjectInfo', 'h3cDvpn',
--                      'h3cDhcpRelay' by gaolong
--      V1.69 2005/7/9 add 'h3cIsis' by gaolong
--      V1.70 2005/8/2 add 'h3cRpr' by gaolong
--                     add 'sJW59', 'vg21-08', 'ar19-61', 'ar19-62', 'ar29-01', 'ar29-21',
--                         'ar29-41', 'ar29-61', 'ar49-45', 'ar49-65' by gaolong
--      V1.71 2005/9/2 add 'h3cSubnetVlan' by gaolong
--                     add 's5112P-EI', 's5113C-EI' by gaolong
--      V1.72 2005/9/20 add 'h3cDlswExt', 'h3cSyslog' by gaolong
--                     add 's5228C', 's5252C', 's5228C-PWR', 's5252C-PWR' and by gaolong
--      V1.73 2005/10/29 add 's2008-HI', 's2016-HI', 's2403H-HI' by longyin
--                       add 'secpath100FS', 'secpath100FE' by longyin
-- ============================================================================
HUAWEI-3COM-OID-MIB DEFINITIONS ::= BEGIN
IMPORTS
enterprises
        FROM RFC1155-SMI;

-- level 1 under .enterprises
        huawei OBJECT IDENTIFIER ::= { enterprises 2011 }

-- level 2 under .huawei
        hwLocal OBJECT IDENTIFIER ::= { huawei 1 }
        products OBJECT IDENTIFIER ::= { huawei 2 }
        huaweiMgmt OBJECT IDENTIFIER ::= { huawei 5 }
        huaweiUtility OBJECT IDENTIFIER ::= { huawei 6 }
        h3c     OBJECT IDENTIFIER ::= { huawei 10 }            -- July  09,2003,lcl added
        huaweiTCMIB OBJECT IDENTIFIER ::= { huawei 20021210 }  -- Reference: huawei-TC.mib

-- level 3
        quidway OBJECT IDENTIFIER ::= { hwLocal 1 }
        hwInternetProtocol OBJECT IDENTIFIER ::= { hwLocal 3 }
        router  OBJECT IDENTIFIER ::= { products 2 }    -- Reference: huawei-mlsr.mib
        lanSw   OBJECT IDENTIFIER ::= { products 23 }
        mlsr    OBJECT IDENTIFIER ::= { products 33 }
        dlsw    OBJECT IDENTIFIER ::= { products 34 }   -- Reference: huawei-dlsw.mib
        hwDhcp OBJECT IDENTIFIER ::= { huaweiMgmt 7 }
        hwMpls OBJECT IDENTIFIER ::= { huaweiMgmt 12 }
        hwpaeExtMib OBJECT IDENTIFIER ::= { huaweiMgmt 22 }   -- Reference: huawei-8021x-ext.mib
        huaweiDatacomm OBJECT IDENTIFIER ::= { huaweiMgmt 25 }
        hwDevice OBJECT IDENTIFIER ::= { huaweiUtility 1 }    -- Reference: huawei-splat-devm.mib
        hwCluster OBJECT IDENTIFIER ::= { huaweiUtility 7 }   -- Reference: huawei-hgmp.mib

-- under .huawei.h3c
        h3cProductId    OBJECT IDENTIFIER ::= { h3c 1 }         -- 2003/12/23, xiejianping added
        h3cCommon   OBJECT IDENTIFIER ::= { h3c 2 }             -- 2004/1/12, xiejianping changed
        h3cEntityVendorTypeOID OBJECT IDENTIFIER ::= { h3c 3 }  -- 2004/5/18, xiejianping added
        h3cNM OBJECT IDENTIFIER ::= { h3c 4 }                   -- 2004/5/18, xiejianping added
        hwSystem    OBJECT IDENTIFIER ::= { h3c 6 }             -- 2004/4/24, xiejianping changed

-- under .huawei.h3c.productId
        s2008-EI     OBJECT IDENTIFIER ::= { h3cProductId 1 }   -- 2003/12/29, xiejianping added
                                                                -- 2004/07/05, xjp modify name s2008Z to s2008-EI
        s2016-EI     OBJECT IDENTIFIER ::= { h3cProductId 2 }   -- 2003/12/29, xiejianping added
                                                                -- 2004/07/05, xjp modify name s2016C to s2016-EI
        s2403H-EI    OBJECT IDENTIFIER ::= { h3cProductId 3 }   -- 2003/12/29, xiejianping added
                                                                -- 2004/07/05, xjp modify name s2403I to s2403H-EI
        s3026PWR     OBJECT IDENTIFIER ::= { h3cProductId 4 }   -- 2003/12/29, xiejianping added
        secpath1000  OBJECT IDENTIFIER ::= { h3cProductId 5 }   -- 2003/12/31, xiejianping added
        ar18-35      OBJECT IDENTIFIER ::= { h3cProductId 6 }   -- 2004/02/17, xiejianping added
        s3552F-HI    OBJECT IDENTIFIER ::= { h3cProductId 7 }   -- 2004/07/1, xiejianping changend
        secpath10    OBJECT IDENTIFIER ::= { h3cProductId 8 }   -- 2003/12/31, xiejianping added
        s3924-SI     OBJECT IDENTIFIER ::= { h3cProductId 9 }   -- 2004/06/1, xiejianping added
        s3928P-SI    OBJECT IDENTIFIER ::= { h3cProductId 10 }  -- 2004/06/1, xiejianping added
        s3952P-SI    OBJECT IDENTIFIER ::= { h3cProductId 11 }  -- 2004/06/1, xiejianping added
        s3928TP-SI   OBJECT IDENTIFIER ::= { h3cProductId 12 }  -- 2004/06/1, xiejianping added
        s3928P-EI    OBJECT IDENTIFIER ::= { h3cProductId 13 }  -- 2004/06/1, xiejianping added
        s3952P-EI    OBJECT IDENTIFIER ::= { h3cProductId 14 }  -- 2004/06/1, xiejianping added
        s3928P-PWR-EI   OBJECT IDENTIFIER ::= { h3cProductId 15 }       -- 2004/06/1, xiejianping added
        s3952P-PWR-EI   OBJECT IDENTIFIER ::= { h3cProductId 16 }       -- 2004/06/1, xiejianping added
        s3928F-EI       OBJECT IDENTIFIER ::= { h3cProductId 17 }       -- 2004/06/1, xiejianping added
        s5600M          OBJECT IDENTIFIER ::= { h3cProductId 18 }       -- 2004/06/1, xiejianping added
        ar18-50         OBJECT IDENTIFIER ::= { h3cProductId 19 }       -- 2004/06/2, xiejianping added
        ar18-33E        OBJECT IDENTIFIER ::= { h3cProductId 20 }       -- 2004/08/25, chenjianhui modify node name
        ar18-34E        OBJECT IDENTIFIER ::= { h3cProductId 21 }       -- 2004/08/25, chenjianhui modify node name
        s8508           OBJECT IDENTIFIER ::= { h3cProductId 22 }       -- 2004/06/25, xiejianping added
        secpath100N      OBJECT IDENTIFIER ::= { h3cProductId 23 }      -- 2004/06/29, xiejianping added
        secpath100V      OBJECT IDENTIFIER ::= { h3cProductId 24 }      -- 2004/06/29, xiejianping added
        secpath100F      OBJECT IDENTIFIER ::= { h3cProductId 25 }      -- 2004/06/29, xiejianping added
        secpath1000F     OBJECT IDENTIFIER ::= { h3cProductId 26 }      -- 2004/12/21, xiejianping added
        secpath500F  OBJECT IDENTIFIER ::= { h3cProductId 27 } -- 2005/5/25, gaolong added
        secpath10F   OBJECT IDENTIFIER ::= { h3cProductId 28 } -- 2005/6/12, gaolong added
        secpath100FS  OBJECT IDENTIFIER ::= { h3cProductId 29 } -- 2005/10/29, longyin added
        secpath100FE  OBJECT IDENTIFIER ::= { h3cProductId 30 } -- 2005/10/29, longyin added
        --  28-39 reserve for secpath
        --
        sr8805   OBJECT IDENTIFIER ::= { h3cProductId 40 }      -- 2004/07/1, xiejianping added
        sr8808   OBJECT IDENTIFIER ::= { h3cProductId 41 }      -- 2004/07/1, xiejianping added
        sr8812   OBJECT IDENTIFIER ::= { h3cProductId 42 }      -- 2004/07/1, xiejianping added
        s5624P      OBJECT IDENTIFIER ::= { h3cProductId 43 }   -- 2004/07/2, xiejianping added
        s5624P-PWR  OBJECT IDENTIFIER ::= { h3cProductId 44 }   -- 2004/07/2, xiejianping added
        s5648P      OBJECT IDENTIFIER ::= { h3cProductId 45 }   -- 2004/07/2, xiejianping added
        s5648P-PWR  OBJECT IDENTIFIER ::= { h3cProductId 46 }   -- 2004/07/2, xiejianping added
        s2008C  OBJECT IDENTIFIER ::= { h3cProductId 47 }       -- 2004/07/7, xiejianping added
        s2016C  OBJECT IDENTIFIER ::= { h3cProductId 48 }       -- 2004/07/7, xiejianping added
        s2024C  OBJECT IDENTIFIER ::= { h3cProductId 49 }       -- 2004/07/7, xiejianping added
        ar18-13V  OBJECT IDENTIFIER ::= { h3cProductId 50 }     -- 2004/07/7, xiejianping added
        ar18-18V  OBJECT IDENTIFIER ::= { h3cProductId 51 }     -- 2004/07/7, xiejianping added
        isPath1000 OBJECT IDENTIFIER ::= { h3cProductId 52 }    -- 2004/07/13, xiejianping added
        ar18-20S  OBJECT IDENTIFIER ::= { h3cProductId 53 }     -- 2004/07/19, xiejianping added

        -- for Wellhope OEM
        wellhope  OBJECT IDENTIFIER ::= { h3cProductId 54 }  -- 2004/08/16, xiejianping added
        tph12616  OBJECT IDENTIFIER ::= { wellhope 1 }          -- NE80
        tph10408  OBJECT IDENTIFIER ::= { wellhope 2 }          -- NE40-8
        tph10404  OBJECT IDENTIFIER ::= { wellhope 3 }          -- NE40-4
        tph10402  OBJECT IDENTIFIER ::= { wellhope 4 }          -- NE40-2
        trt7554  OBJECT IDENTIFIER ::= { wellhope 5 }           -- NE05
        tab3740  OBJECT IDENTIFIER ::= { wellhope 6 }           -- AR46-40
        tab3680  OBJECT IDENTIFIER ::= { wellhope 7 }           -- AR28-80
        tab2609  OBJECT IDENTIFIER ::= { wellhope 8 }           -- AR28-09
        tab2611  OBJECT IDENTIFIER ::= { wellhope 9 }           -- AR28-11
        tab2631  OBJECT IDENTIFIER ::= { wellhope 10 }          -- AR28-31
        ts6061r  OBJECT IDENTIFIER ::= { wellhope 11 }          -- S6506R
        ts3262  OBJECT IDENTIFIER ::= { wellhope 12 }           -- S3526C
        ts2502  OBJECT IDENTIFIER ::= { wellhope 13 }           -- S3050C
        ts2262  OBJECT IDENTIFIER ::= { wellhope 14 }           -- S3026C

        xe200  OBJECT IDENTIFIER ::= { h3cProductId 55 }        -- 2004/08/31, xiejianping added
        xe2000 OBJECT IDENTIFIER ::= { h3cProductId 56 }        -- 2004/08/31, xiejianping added
        e026T   OBJECT IDENTIFIER ::= { h3cProductId 57 }       -- 2004/10/15, xiejianping added
        e008-FE OBJECT IDENTIFIER ::= { h3cProductId 58 }       -- 2004/10/15, xiejianping added
        e017-FE OBJECT IDENTIFIER ::= { h3cProductId 59 }       -- 2004/10/15, xiejianping added
        e026-FE OBJECT IDENTIFIER ::= { h3cProductId 60 }       -- 2004/10/15, xiejianping added
        ar28-12 OBJECT IDENTIFIER ::= { h3cProductId 61 }       -- 2004/10/29, xiejianping added
        ar28-13 OBJECT IDENTIFIER ::= { h3cProductId 62 }       -- 2004/10/29, xiejianping added
        ar28-14 OBJECT IDENTIFIER ::= { h3cProductId 63 }       -- 2004/10/29, xiejianping added
        ar18-10 OBJECT IDENTIFIER ::= { h3cProductId 64 }       -- 2004/11/18, xiejianping added
        ar18-21 OBJECT IDENTIFIER ::= { h3cProductId 65 }       -- 2004/11/18, xiejianping added
        ar18-21A OBJECT IDENTIFIER ::= { h3cProductId 66 }      -- 2004/11/18, xiejianping added
        ar18-21B OBJECT IDENTIFIER ::= { h3cProductId 67 }      -- 2004/11/18, xiejianping added
        ar18-21C OBJECT IDENTIFIER ::= { h3cProductId 68 }      -- 2004/11/18, xiejianping added
        ar18-22 OBJECT IDENTIFIER ::= { h3cProductId 69 }       -- 2004/11/18, xiejianping added
        ar18-22-8 OBJECT IDENTIFIER ::= { h3cProductId 70 }     -- 2004/11/18, xiejianping added
        ar18-22-24 OBJECT IDENTIFIER ::= { h3cProductId 71 }    -- 2004/11/18, xiejianping added
        ar18-23-1 OBJECT IDENTIFIER ::= { h3cProductId 72 }     -- 2004/11/18, xiejianping added
        ar18-30E OBJECT IDENTIFIER ::= { h3cProductId 73 }      -- 2004/11/18, xiejianping added
        ar18-31E OBJECT IDENTIFIER ::= { h3cProductId 74 }      -- 2004/11/18, xiejianping added
        ar18-32E OBJECT IDENTIFIER ::= { h3cProductId 75 }      -- 2004/11/18, xiejianping added
        ar18-35E OBJECT IDENTIFIER ::= { h3cProductId 76 }      -- 2004/11/18, xiejianping added
        ar18-36E OBJECT IDENTIFIER ::= { h3cProductId 77 }      -- 2004/11/18, xiejianping added
        ar18-37E OBJECT IDENTIFIER ::= { h3cProductId 78 }      -- 2004/11/18, xiejianping added
        ar18-52 OBJECT IDENTIFIER ::= { h3cProductId 79 }       -- 2004/11/18, xiejianping added
        s6502 OBJECT IDENTIFIER ::= { h3cProductId 80 }         -- 2004/11/23, xiejianping added
        s5124P-EI OBJECT IDENTIFIER ::= { h3cProductId 81 }     -- 2004/12/2, xiejianping added
        s5126C-EI OBJECT IDENTIFIER ::= { h3cProductId 82 }     -- 2004/12/2, xiejianping added
        s5148P-EI OBJECT IDENTIFIER ::= { h3cProductId 83 }     -- 2004/12/2, xiejianping added
        s5150C-EI OBJECT IDENTIFIER ::= { h3cProductId 84 }     -- 2004/12/2, xiejianping added
        s5116P-SI OBJECT IDENTIFIER ::= { h3cProductId 85 }     -- 2004/12/2, xiejianping added
        s5124P-SI OBJECT IDENTIFIER ::= { h3cProductId 86 }     -- 2004/12/2, xiejianping added
        s5148P-SI OBJECT IDENTIFIER ::= { h3cProductId 87 }     -- 2004/12/2, xiejianping added
        ar4620E OBJECT IDENTIFIER ::= { h3cProductId 88 }       -- 2004/12/6, xiejianping added
        ar4640E OBJECT IDENTIFIER ::= { h3cProductId 89 }       -- 2004/12/6, xiejianping added
        ar4680E OBJECT IDENTIFIER ::= { h3cProductId 90 }       -- 2004/12/6, xiejianping added
        ar18-22s-8 OBJECT IDENTIFIER ::= { h3cProductId 91 }    -- 2004/12/24, xiejianping added
        ar18-23s-1 OBJECT IDENTIFIER ::= { h3cProductId 92 }    -- 2004/12/24, xiejianping added
        secEngineP500 OBJECT IDENTIFIER ::= { h3cProductId 93 } -- 2004/12/29, xiejianping added
        s2108-SI OBJECT IDENTIFIER ::= { h3cProductId 94 }      -- 2005/1/6, xiejianping added
        s2116-SI OBJECT IDENTIFIER ::= { h3cProductId 95 }      -- 2005/1/6, xiejianping added
        s2126-SI OBJECT IDENTIFIER ::= { h3cProductId 96 }      -- 2005/1/6, xiejianping added
        s2108-EI OBJECT IDENTIFIER ::= { h3cProductId 97 }      -- 2005/1/6, xiejianping added
        s2116-EI OBJECT IDENTIFIER ::= { h3cProductId 98 }      -- 2005/1/6, xiejianping added
        s2126-EI OBJECT IDENTIFIER ::= { h3cProductId 99 }      -- 2005/1/6, xiejianping added
        s5624F OBJECT IDENTIFIER ::= { h3cProductId 100 }       -- 2005/1/6, xiejianping added
        s3224P OBJECT IDENTIFIER ::= { h3cProductId 101 }       -- 2005/1/17, xiejianping added
        s3226T OBJECT IDENTIFIER ::= { h3cProductId 102 }       -- 2005/1/17, xiejianping added
        s3226P OBJECT IDENTIFIER ::= { h3cProductId 103 }       -- 2005/1/17, xiejianping added
        s3250T OBJECT IDENTIFIER ::= { h3cProductId 104 }       -- 2005/1/17, xiejianping added
        s3250P OBJECT IDENTIFIER ::= { h3cProductId 105 }       -- 2005/1/17, xiejianping added
        s3108T OBJECT IDENTIFIER ::= { h3cProductId 106 }       -- 2005/2/5, gaolong added
        s3116T OBJECT IDENTIFIER ::= { h3cProductId 107 }       -- 2005/2/5, gaolong added
        s3126T OBJECT IDENTIFIER ::= { h3cProductId 108 }       -- 2005/2/5, gaolong added
        s3108C OBJECT IDENTIFIER ::= { h3cProductId 109 }       -- 2005/2/5, gaolong added
        s3116C OBJECT IDENTIFIER ::= { h3cProductId 110 }       -- 2005/2/5, gaolong added
        s3126C OBJECT IDENTIFIER ::= { h3cProductId 111 }       -- 2005/2/5, gaolong added
        ar28-12B OBJECT IDENTIFIER ::= { h3cProductId 112 }     -- 2005/3/25, xiejianping added
        secBladeIDS OBJECT IDENTIFIER ::= { h3cProductId 113 }  -- 2005/3/25, gaolong added
        secBladeIPS OBJECT IDENTIFIER ::= { h3cProductId 114 }  -- 2005/3/25, gaolong added
        secEngineD500 OBJECT IDENTIFIER ::= { h3cProductId 115 }        -- 2005/4/1, xiejianping added
        s3928TP-V6 OBJECT IDENTIFIER ::= { h3cProductId 116 }   -- 2005/4/14, xiejianping added
        s3928P-V6 OBJECT IDENTIFIER ::= { h3cProductId 117 }    -- 2005/4/14, xiejianping added
        s3952P-V6 OBJECT IDENTIFIER ::= { h3cProductId 118 }    -- 2005/4/14, xiejianping added
        s3928F-V6 OBJECT IDENTIFIER ::= { h3cProductId 119 }    -- 2005/4/14, xiejianping added
        s5524P OBJECT IDENTIFIER ::= { h3cProductId 120 }       -- 2005/4/14, xiejianping added
        s5524F OBJECT IDENTIFIER ::= { h3cProductId 121 }       -- 2005/4/14, xiejianping added
        xE7000 OBJECT IDENTIFIER ::= { h3cProductId 122 }       -- 2005/4/15, gaolong added
        vg10-40 OBJECT IDENTIFIER ::= { h3cProductId 123 }      -- 2005/4/15, gaolong added
        vg10-41 OBJECT IDENTIFIER ::= { h3cProductId 124 }      -- 2005/4/15, gaolong added
        vg20-16 OBJECT IDENTIFIER ::= { h3cProductId 125 }      -- 2005/4/15, gaolong added
        vg20-32 OBJECT IDENTIFIER ::= { h3cProductId 126 }      -- 2005/4/15, gaolong added
        vg20-08L OBJECT IDENTIFIER ::= { h3cProductId 127 }     -- 2005/4/15, gaolong added
        vg80-20 OBJECT IDENTIFIER ::= { h3cProductId 128 }      -- 2005/4/15, gaolong added
        vg80-20T OBJECT IDENTIFIER ::= { h3cProductId 129 }     -- 2005/4/15, gaolong added
        s2008CT OBJECT IDENTIFIER ::= { h3cProductId 130 }      -- 2005/5/13, xiejianping added
        s2008CP OBJECT IDENTIFIER ::= { h3cProductId 131 }      -- 2005/5/13, xiejianping added
        secBladeFW OBJECT IDENTIFIER ::= { h3cProductId 132 }   -- 2005/5/20, xiejianping added
        secBladeVPN OBJECT IDENTIFIER ::= { h3cProductId 133 }  -- 2005/5/20, xiejianping added
        secEngineD200 OBJECT IDENTIFIER ::= { h3cProductId 134 }        -- 2005/6/20, gaolong added
--      subidentifier {h3cProductId 135} is reserved for OEM.
        sJW59 OBJECT IDENTIFIER ::= { h3cProductId 136 }        -- 2005/8/2, gaolong added
        vg21-08 OBJECT IDENTIFIER ::= { h3cProductId 137 }      -- 2005/8/2, gaolong added
        ar19-61 OBJECT IDENTIFIER ::= { h3cProductId 138 }      -- 2005/8/2, gaolong added
        ar19-62 OBJECT IDENTIFIER ::= { h3cProductId 139 }      -- 2005/8/2, gaolong added
        ar29-01 OBJECT IDENTIFIER ::= { h3cProductId 140}       -- 2005/8/2, gaolong added
        ar29-21 OBJECT IDENTIFIER ::= { h3cProductId 141 }      -- 2005/8/2, gaolong added
        ar29-41 OBJECT IDENTIFIER ::= { h3cProductId 142 }      -- 2005/8/2, gaolong added
        ar29-61 OBJECT IDENTIFIER ::= { h3cProductId 143 }      -- 2005/8/2, gaolong added
        ar49-45 OBJECT IDENTIFIER ::= { h3cProductId 144 }      -- 2005/8/2, gaolong added
        ar49-65 OBJECT IDENTIFIER ::= { h3cProductId 145 }      -- 2005/8/2, gaolong added
        s5112P-EI OBJECT IDENTIFIER ::= { h3cProductId 146 }    -- 2005/8/2, gaolong added
        s5113C-EI OBJECT IDENTIFIER ::= { h3cProductId 147 }    -- 2005/8/2, gaolong added
        s5228C OBJECT IDENTIFIER ::= { h3cProductId 148 }       -- 2005/9/20, gaolong added
        s5252C OBJECT IDENTIFIER ::= { h3cProductId 149 }       -- 2005/9/20, gaolong added
        s5228C-PWR OBJECT IDENTIFIER ::= { h3cProductId 150 }   -- 2005/9/20, gaolong added
        s5252C-PWR OBJECT IDENTIFIER ::= { h3cProductId 151 }   -- 2005/9/20, gaolong added
        s2008-HI OBJECT IDENTIFIER ::= { h3cProductId 152 }     -- 2005/10/29, longyin added
        s2016-HI OBJECT IDENTIFIER ::= { h3cProductId 153 }     -- 2005/10/29, longyin added
        s2403H-HI OBJECT IDENTIFIER ::= { h3cProductId 154 }    -- 2005/10/29, longyin added
    -- for Intransa OEM
        intransa  OBJECT IDENTIFIER ::= { h3cProductId 135 }  -- 2005/06/25, gaolong added
        ix5000  OBJECT IDENTIFIER ::= { intransa 1 }            -- 2005/06/25, gaolong added

-- under .huawei.hwLocal.quidway
        quidwayRouter OBJECT IDENTIFIER ::= { quidway 1 }
        hwRouter OBJECT IDENTIFIER ::= { quidwayRouter 1 }
        quidway1600 OBJECT IDENTIFIER ::= { quidwayRouter 1600 }
        quidway1602 OBJECT IDENTIFIER ::= { quidwayRouter 1602 }  -- May 07,2003,yubo added
        quidway1612 OBJECT IDENTIFIER ::= { quidwayRouter 1612 }  -- May 07,2003,yubo added
        quidway1613 OBJECT IDENTIFIER ::= { quidwayRouter 1613 }  -- May 07,2003,yubo added
        quidway1614 OBJECT IDENTIFIER ::= { quidwayRouter 1614 }  -- May 07,2003,yubo added
        quidway1615 OBJECT IDENTIFIER ::= { quidwayRouter 1615 }  -- May 07,2003,yubo added
        quidway1760 OBJECT IDENTIFIER ::= { quidwayRouter 1760 }  -- May 07,2003,yubo added
        quidway1760B OBJECT IDENTIFIER ::= { quidwayRouter 1761 }  -- April 21,2003,yubo added
        quidway2501 OBJECT IDENTIFIER ::= { quidwayRouter 2501 }
        quidway2509 OBJECT IDENTIFIER ::= { quidwayRouter 2509 }
        quidway2511 OBJECT IDENTIFIER ::= { quidwayRouter 2511 }   -- May 07,2003,yubo added
        quidway2501E OBJECT IDENTIFIER ::= { quidwayRouter 2601 }  -- May 07,2003,yubo added
        quidway4001E OBJECT IDENTIFIER ::= { quidwayRouter 2606 }  -- May 07,2003,yubo added
        quidway2509E OBJECT IDENTIFIER ::= { quidwayRouter 2608 }  -- May 07,2003,yubo added
        quidway2511E OBJECT IDENTIFIER ::= { quidwayRouter 2609 }  -- May 07,2003,yubo added
        quidway2610 OBJECT IDENTIFIER ::= { quidwayRouter 2610 }  -- May 07,2003,yubo added
        quidway2611 OBJECT IDENTIFIER ::= { quidwayRouter 2611 }  -- May 07,2003,yubo added
        quidway2620 OBJECT IDENTIFIER ::= { quidwayRouter 2620 }  -- May 07,2003,yubo added
        quidway2621 OBJECT IDENTIFIER ::= { quidwayRouter 2621 }  -- May 07,2003,yubo added
        quidway2630 OBJECT IDENTIFIER ::= { quidwayRouter 2630 }  -- May 07,2003,yubo added
        quidway2631 OBJECT IDENTIFIER ::= { quidwayRouter 2631 }  -- May 07,2003,yubo added
        quidway3640 OBJECT IDENTIFIER ::= { quidwayRouter 3640 }
        quidway3680 OBJECT IDENTIFIER ::= { quidwayRouter 3680 }  -- May 07,2003,yubo added
        quidway4001 OBJECT IDENTIFIER ::= { quidwayRouter 4001 }
        eudemon OBJECT IDENTIFIER ::= { quidwayRouter 100 }    -- May 07,2003,yubo added
        ar28-80 OBJECT IDENTIFIER ::= { quidwayRouter 12880 }  -- May 19,2003,yubo added，rename 3680E
        ar28-10 OBJECT IDENTIFIER ::= { quidwayRouter 12810 }  -- May 19,2003,yubo added，rename 2610
        ar28-11 OBJECT IDENTIFIER ::= { quidwayRouter 12811 }  -- May 19,2003,yubo added，rename 2611
        ar18-12 OBJECT IDENTIFIER ::= { quidwayRouter 11812 }  -- May 19,2003,yubo added，rename 1612
        ar18-13 OBJECT IDENTIFIER ::= { quidwayRouter 11813 }  -- May 19,2003,yubo added，rename 1613
        ar18-15 OBJECT IDENTIFIER ::= { quidwayRouter 11815 }  -- May 19,2003,yubo added，rename 1615
        ar18-16 OBJECT IDENTIFIER ::= { quidwayRouter 11816 }  -- May 19,2003,yubo added，rename 1616
        ar28-40 OBJECT IDENTIFIER ::= { quidwayRouter 12840 }  -- May 19,2003,yubo added，rename 3640E
        ar28-09 OBJECT IDENTIFIER ::= { quidwayRouter 12809 }  -- May 19,2003,yubo added，rename 1760
        ar28-30 OBJECT IDENTIFIER ::= { quidwayRouter 12830 }  -- May 19,2003,yubo added，rename 2630
        ar28-31 OBJECT IDENTIFIER ::= { quidwayRouter 12831 }  -- May 19,2003,yubo added，rename 2631

-- under .huawei.hwLocal.hwInternetProtocol
        rIp OBJECT IDENTIFIER ::= { hwInternetProtocol 1 }     -- Reference: huawei-ip.mib
        rIcmp OBJECT IDENTIFIER ::= { hwInternetProtocol 2 }   -- Reference: huawei-icmp.mib
        vrpProtocol OBJECT IDENTIFIER ::= { hwInternetProtocol 3 }
        rmonExtend OBJECT IDENTIFIER ::= { hwInternetProtocol 4 }  -- Reference: huawei-rmon-ext.mib
        huawei-qos OBJECT IDENTIFIER ::= { vrpProtocol 2 }     -- Reference: huawei-qos.mib
        huawei-vlan OBJECT IDENTIFIER ::= { vrpProtocol 3 }    -- Reference: huawei-vlan.mib

-- under .huawei.products
        ar46-20 OBJECT IDENTIFIER ::= { products 44 } -- June 16, 2003, yubo added
        ar46-40 OBJECT IDENTIFIER ::= { products 45 } -- June 16, 2003, yubo added
        ar46-80 OBJECT IDENTIFIER ::= { products 46 } -- June 16, 2003, yubo added
        vdg10-40 OBJECT IDENTIFIER ::= { products 52 } -- June 24, 2003, yubo added
        vdg10-41 OBJECT IDENTIFIER ::= { products 53 } -- June 24, 2003, yubo added
        ar18-18 OBJECT IDENTIFIER ::= { products 55 }  -- August 12,2003,yubo added
        ar18-20 OBJECT IDENTIFIER ::= { products 56 }  -- August 12,2003,yubo added
        ar18-30 OBJECT IDENTIFIER ::= { products 57 }  -- August 12,2003,yubo added
        ar18-31 OBJECT IDENTIFIER ::= { products 58 }  -- August 12,2003,yubo added
        ar18-32 OBJECT IDENTIFIER ::= { products 59 }  -- August 12,2003,yubo added
        ar18-33 OBJECT IDENTIFIER ::= { products 60 }  -- August 12,2003,yubo added
        ar18-34 OBJECT IDENTIFIER ::= { products 61 }  -- August 12,2003,yubo added
        ne5000 OBJECT IDENTIFIER ::= { products 62 }  -- August 29,2003,xiejianping added

-- under .huawei.products.lanSw
        lswCommon OBJECT IDENTIFIER ::= { lanSw 1 }
        s8016 OBJECT IDENTIFIER ::= { lanSw 11 }
        s8016Common OBJECT IDENTIFIER ::= { s8016 1 }
        s8016A OBJECT IDENTIFIER ::= { s8016 2 }
        s8016B OBJECT IDENTIFIER ::= { s8016 3 }
        s3526 OBJECT IDENTIFIER ::= { lanSw 12 }
        s3026 OBJECT IDENTIFIER ::= { lanSw 13 }
        s3026V OBJECT IDENTIFIER ::= { lanSw 14 }
        s2008 OBJECT IDENTIFIER ::= { lanSw 15 }
        s2016 OBJECT IDENTIFIER ::= { lanSw 16 }
        s3526F OBJECT IDENTIFIER ::= { lanSw 17 }  -- May 07,2003,yubo modify name
        s5516 OBJECT IDENTIFIER ::= { lanSw 18 }
        s6506 OBJECT IDENTIFIER ::= { lanSw 19 }
        s3026F OBJECT IDENTIFIER ::= { lanSw 20 }
        s3526E OBJECT IDENTIFIER ::= { lanSw 21 }
        s2026 OBJECT IDENTIFIER ::= { lanSw 22 }
        s2403H OBJECT IDENTIFIER ::= { lanSw 23 }
        s3026E OBJECT IDENTIFIER ::= { lanSw 24 }
        s3026E-FM OBJECT IDENTIFIER ::= { lanSw 25 }
        s3026E-FS OBJECT IDENTIFIER ::= { lanSw 26 }
        s3526E-FM OBJECT IDENTIFIER ::= { lanSw 27 }
        s3526E-FS OBJECT IDENTIFIER ::= { lanSw 28 }
        s3050C OBJECT IDENTIFIER ::= { lanSw 29 }       -- May 07,2003,yubo added
        s6503 OBJECT IDENTIFIER ::= { lanSw 30 }        -- May 07,2003,yubo added
        s8512 OBJECT IDENTIFIER ::= { lanSw 31 }        -- April 08,2003,yubo added
        s8505 OBJECT IDENTIFIER ::= { lanSw 32 }        -- May 07,2003,yubo added
        s6506R OBJECT IDENTIFIER ::= { lanSw 33 }       -- May 07,2003,yubo added
        s3026c OBJECT IDENTIFIER ::= { lanSw 34 }       -- May 14,2003,yubo added
        s3026g OBJECT IDENTIFIER ::= { lanSw 35 }       -- May 14,2003,yubo added
        s3026t OBJECT IDENTIFIER ::= { lanSw 36 }       -- May 14,2003,yubo added
        s3552G OBJECT IDENTIFIER ::= { lanSw 37 }       -- May 19,2003,yubo added
        s3552P OBJECT IDENTIFIER ::= { lanSw 38 }       -- May 19,2003,yubo added
        s3528G OBJECT IDENTIFIER ::= { lanSw 39 }       -- May 19,2003,yubo added
        s3528P OBJECT IDENTIFIER ::= { lanSw 40 }       -- May 19,2003,yubo added
        s3526c OBJECT IDENTIFIER ::= { lanSw 41 }       -- May 23,2003,yubo added
        s3026c-24-12fs OBJECT IDENTIFIER ::= { lanSw 42 }       -- May 23,2003,yubo added
        s3026c-24-12fm OBJECT IDENTIFIER ::= { lanSw 43 }       -- May 23,2003,yubo added
        s3526c-24-12fs OBJECT IDENTIFIER ::= { lanSw 44 }       -- May 23,2003,yubo added
        s3526c-24-12fm OBJECT IDENTIFIER ::= { lanSw 45 }       -- May 23,2003,yubo added
        s5012G  OBJECT IDENTIFIER ::= { lanSw 46 }       -- July 03,2003,yubo added
        s5012G-DC       OBJECT IDENTIFIER ::= { lanSw 47 }       -- July 03,2003,yubo added
        s5012T-12-10GBC         OBJECT IDENTIFIER ::= { lanSw 48 }       -- July 03,2003,yubo added
        s5012T-12-10GBC-DC      OBJECT IDENTIFIER ::= { lanSw 49 }       -- July 03,2003,yubo added
        s5024G-24-20TP  OBJECT IDENTIFIER ::= { lanSw 50 }       -- July 03,2003,yubo added
        s5024G-24-20TP-DC       OBJECT IDENTIFIER ::= { lanSw 51 }       -- July 03,2003,yubo added
        s2026Z          OBJECT IDENTIFIER ::= { lanSw 52 }      -- August 12,2003,yubo added
        s2026C          OBJECT IDENTIFIER ::= { lanSw 53 }      -- August 12,2003,yubo added
        s3026G-SI       OBJECT IDENTIFIER ::= { lanSw 54 }      -- August 12,2003,yubo added
        s3026C-SI       OBJECT IDENTIFIER ::= { lanSw 55 }      -- August 12,2003,yubo added
        s3026S-SI       OBJECT IDENTIFIER ::= { lanSw 56 }      -- August 12,2003,yubo added
        s8505e          OBJECT IDENTIFIER ::= { lanSw 57 }      -- 2003/12/23, xiejianping added
        s3552F-SI       OBJECT IDENTIFIER ::= { lanSw 67 }      -- 2004-9-9,xiejianping added
        s3552F-EI       OBJECT IDENTIFIER ::= { lanSw 68 }      -- 2004-9-9,xiejianping added
        e026            OBJECT IDENTIFIER ::= { lanSw 69 }      -- 2004-9-9,xiejianping added
        e026-SI         OBJECT IDENTIFIER ::= { lanSw 70 }      -- 2004-9-9,xiejianping added
        e050            OBJECT IDENTIFIER ::= { lanSw 71 }      -- 2004-9-9,xiejianping added

        hws6506qAclMib OBJECT IDENTIFIER ::= { s6506 6 }  -- Reference: huawei-s6506-qacl.mib

-- under .huawei.products.lanSw.lswCommon
        hwLswExtInterface OBJECT IDENTIFIER ::= { lswCommon 1 }    -- Reference: huawei-splat-inf.mib
        hwLswVlan OBJECT IDENTIFIER ::= { lswCommon 2 }        -- Reference: huawei-splat-inf.mib,huawei-splat-vlan.mib
        hwLswMacPort OBJECT IDENTIFIER ::= { lswCommon 3 }     -- Reference: huawei-splat-mam.mib
        hwLswArpMib OBJECT IDENTIFIER ::= { lswCommon 4 }      -- Reference: huawei-splat-arp.mib
        hwLswL2InfMib OBJECT IDENTIFIER ::= { lswCommon 5 }    -- Reference: huawei-splat-inf.mib
        hwLswRstpMib OBJECT IDENTIFIER ::= { lswCommon 6 }     -- Reference: huawei-splat-rstp.mib
        hwLswIgmpsnoopingMib OBJECT IDENTIFIER ::= { lswCommon 7 }  -- Reference: huawei-splat-igsp.mib
        hwLswDhcpMib OBJECT IDENTIFIER ::= { lswCommon 8 }     -- Reference: huawei-splat-dhcp.mib
        hwLswdevMMib OBJECT IDENTIFIER ::= { lswCommon 9 }     -- Reference: huawei-splat-devm.mib
        hwsLswTrapMib OBJECT IDENTIFIER ::= { lswCommon 12 }   -- Reference: huawei-splat-trap.mib
        hwdot1sMstp OBJECT IDENTIFIER ::= { lswCommon 14 }     -- Reference: huawei-splat-mstp.mib
        hwLswQosAclMib OBJECT IDENTIFIER ::= { lswCommon 16 }  -- Reference: huawei-splat-qos.mib
        hwLswMix OBJECT IDENTIFIER ::= { lswCommon 17 }        -- Reference: huawei-splat-mix.mib
        hwLswDeviceAdmin OBJECT IDENTIFIER ::= { lswCommon 18 }     -- Reference: huawei-device.mib

-- under .huawei.products.mlsr
        terminalServer OBJECT IDENTIFIER ::= { mlsr 1 }   -- Reference: huawei-terminal.mib
        huaweiNDEC OBJECT IDENTIFIER ::= { mlsr 2 }       -- Reference: huawei-ndec.mib
        redundancyPower OBJECT IDENTIFIER ::= { mlsr 4 }  -- Reference: huawei-power.mib
        redundancyFan OBJECT IDENTIFIER ::= { mlsr 5 }    -- Reference: huawei-power.mib
        hwmSystem OBJECT IDENTIFIER ::= { mlsr 6 }        -- Reference: huawei-mlsr.mib
        hw8040If OBJECT IDENTIFIER ::= { mlsr 7 }         -- Reference: huawei-8040if.mib
        pos OBJECT IDENTIFIER ::= { mlsr 8 }              -- Reference: huawei-pos.mib
        hwIsdnMib OBJECT IDENTIFIER ::= { mlsr 9 }        -- Reference: huawei-isdn.mib
        aR46-E200 OBJECT IDENTIFIER ::= { mlsr 20 }       -- Reference: huawei-srm.mib

-- under .huawei.huaweiMgmt.hwDhcp
        hwDHCPRelayMib OBJECT IDENTIFIER ::= { hwDhcp 1 }       -- Reference: huawei-dhcpr.mib
        hwDHCPServerMib OBJECT IDENTIFIER ::= { hwDhcp 2 }      -- Reference: huawei-dhcps.mib

-- under .huawei.huaweiMgmt.hwMpls
        hwMplsLsr OBJECT IDENTIFIER ::= { hwMpls 1 }      -- Reference: huawei-mpls-lsr.mib
        hwMplsLdp OBJECT IDENTIFIER ::= { hwMpls 2 }      -- Reference: huawei-mpls-ldp.mib
        hwMplsVpn OBJECT IDENTIFIER ::= { hwMpls 3 }      -- Reference: huawei-mpls-vpn.mib

-- under .huawei.huaweiMgmt.huaweiDatacomm

        voice                   OBJECT IDENTIFIER ::= { huaweiDatacomm 1 }
        -- name: guoxiaojun
        -- id: 29157
        -- product: R2600,R1700,R3600
        -- reason: new mib requirement for voice General ,voice interface , voice analog interface, voice digital interface, voice dial control, call active, call history, GK client, AAA client,H323 call sataict.

        hwIPX          OBJECT IDENTIFIER ::= { huaweiDatacomm 2 }
        hwFWTP         OBJECT IDENTIFIER ::= { huaweiDatacomm 3 }
        hwHIIP         OBJECT IDENTIFIER ::= { huaweiDatacomm 4 }
        hwHRP          OBJECT IDENTIFIER ::= { huaweiDatacomm 5 }
        -- name: xuqingwei
        -- id: 27902
        -- product:
        -- reason: new mib requirement for hwIPX,hwFWTP,hwHIIP,hwHRP.

        hwASPF          OBJECT IDENTIFIER ::= { huaweiDatacomm 6 }
        hwNAT           OBJECT IDENTIFIER ::= { huaweiDatacomm 7 }
        hwBLS           OBJECT IDENTIFIER ::= { huaweiDatacomm 8 }
        hwMACBIND       OBJECT IDENTIFIER ::= { huaweiDatacomm 9 }
        hwATK           OBJECT IDENTIFIER ::= { huaweiDatacomm 10 }
        hwSECSTAT       OBJECT IDENTIFIER ::= { huaweiDatacomm 11 }
        hwPFLT          OBJECT IDENTIFIER ::= { huaweiDatacomm 12 }
        hwTRNG          OBJECT IDENTIFIER ::= { huaweiDatacomm 13 }    -- Reference: huawei-trng.mib
        hwSMAP          OBJECT IDENTIFIER ::= { huaweiDatacomm 14 }
        hwSZONE         OBJECT IDENTIFIER ::= { huaweiDatacomm 15 }
        hwSLOG          OBJECT IDENTIFIER ::= { huaweiDatacomm 16 }
        -- name: xuqingwei
        -- id: 27902
        -- product:
        -- reason: new mib requirement for safety characteristic.

        hwSSHMIB               OBJECT IDENTIFIER ::= { huaweiDatacomm 17 }
        -- name: guoxiaojun
        -- id: 29157
        -- product: R2600,R1700,R3600
        -- reason: new mib requirement for SSH.
        -- Reference: huawei-ssh.mib

        hwUserLogMIB           OBJECT IDENTIFIER ::= { huaweiDatacomm 18 }
        -- name: libingshan
        -- id: 22055
        -- product: NE05/08/08E/16/16E
        -- reason: new mib requirement for user log.
        -- Reference: huawei-userlog.mib

        hwSystemMan    OBJECT IDENTIFIER ::= { huaweiDatacomm 19 }
        -- name: xuqingwei
        -- id: 27902
        -- product:
        -- reason: new mib requirement for system management

        hwTACACS    OBJECT IDENTIFIER ::= { huaweiDatacomm 20 }
        -- name: limeng
        -- id: 15814
        -- product:
        -- reason: new mib requirement for hwTACACS (to send Email)
        -- Reference: huawei-hwtacacs.mib

        hwNBPortalMIB          OBJECT IDENTIFIER ::= { huaweiDatacomm 21 }
        -- name: libingshan
        -- id: 22055
        -- product: NE05/08/08E/16/16E
        -- reason: new mib requirement for portal of router narrowband.

        hwNTP    OBJECT IDENTIFIER ::= { huaweiDatacomm 22 }
        -- name: xuqingwei
        -- id: 27902
        -- product: VRP
        -- reason: new mib requirement for NTP server,command over snmp
        -- Reference: huawei-ntp.mib

        hwCmdOverSnmpMib    OBJECT IDENTIFIER ::= { huaweiDatacomm 23 }


        hwISIS    OBJECT IDENTIFIER ::= { huaweiDatacomm 24 }
        -- name: zhangxianping
        -- id: 29813
        -- product: VRP
        -- reason: new mib requirement for ISIS

        hwLAG    OBJECT IDENTIFIER ::= { huaweiDatacomm 25 }
        -- name: xuqingwei
        -- id: 27902
        -- product: Lanswitch platform
        -- reason: new mib requirement for LACP
        -- Reference: huawei-lag.mib

        hwSmonExtend    OBJECT IDENTIFIER ::= { huaweiDatacomm 26 }
        -- name: fuzhenyu
        -- id: 30224
        -- product: Lanswitch platform
        -- reason: new mib requirement for smon vlan enable purpose
        -- Reference: huawei-splat-smonext.mib

        hwTask    OBJECT IDENTIFIER ::= { huaweiDatacomm 27 }
        -- name: zhangxianping
        -- id: 29813
        -- product: VRP
        -- reason: new mib requirement for Task mib

        hwDismanPing    OBJECT IDENTIFIER ::= { huaweiDatacomm 28 }
        -- name: lvzhenfeng
        -- id: 18230
        -- product: Quidview
        -- reason: new mib requirement for RFC DismanPing(MIB) extend
        -- Reference: huawei-ping.mib

        hwVlan    OBJECT IDENTIFIER ::= { huaweiDatacomm 29 }
        -- name: fuzhenyu
        -- id: 30224
        -- product: Lanswitch platform
        -- reason: move old mib tree(huawei.products.lanSw.lswCommon) to new location(huawei.huaweiMgmt.hwDatacomm)

        hwAddrMgmt    OBJECT IDENTIFIER ::= { huaweiDatacomm 30 }
        -- name: cuikemao
        -- id: 20339
        -- date: 2003-09-25
        -- product: Eudemon2000 Series(Eudemon 2100, Eudemon 2200)
        -- reason: new mib requirement for Eudemon2000 Series

        hwEntityExtentMIB OBJECT IDENTIFIER ::= { huaweiDatacomm 31 }
        -- name: cuikemao
        -- id: 20339
        -- date: 2003-11-06
        -- product: 8070 8011 8060
        -- reason: new mib requirement for hwEntityExtentMIB

        hwQoS    OBJECT IDENTIFIER ::= { huaweiDatacomm 32 }
        -- name: cuikemao
        -- id: 20339
        -- date: 2004-05-18
        -- product: VRP
        -- reason: new mib requirement for HUAWEI-CBQOS-MIB

        hwMultilinkPPP    OBJECT IDENTIFIER ::= { huaweiDatacomm 33 }
        -- name: cuikemao
        -- id: 20339
        -- date: 2004-05-26
        -- product: VRP
        -- reason: new mib requirement for HUAWEI-MP-MIB

        hwTCPMib    OBJECT IDENTIFIER ::= { huaweiDatacomm 34 }
        -- name: cuikemao
        -- id: 20339
        -- date: 2004-06-29
        -- product: VRP
        -- reason: new mib requirement for HUAWEI-TCP-MIB

        hwBGPMib    OBJECT IDENTIFIER ::= { huaweiDatacomm 35 }
        -- name: cuikemao
        -- id: 20339
        -- date: 2004-06-29
        -- product: VRP
        -- reason: new mib requirement for HUAWEI-BGP-MIB

-- under .huawei.huaweiMgmt.huaweiDatacomm.voice

        -- name: guoxiaojun
        -- id: 29157
        -- product: R2600,R1700,R3600
        -- reason: new mib requirement for voice

        hwVoiceGeneralMIB              OBJECT IDENTIFIER ::= { voice 1 }   -- Reference: huawei-vogeneral.mib
        hwVoiceIfMIB                   OBJECT IDENTIFIER ::= { voice 2 }   -- Reference: huawei-voif.mib
        hwVoiceAnalogInterfaceMIB      OBJECT IDENTIFIER ::= { voice 3 }   -- Reference: huawei-voanalogif.mib
        hwVoiceDigitalInterfaceMIB     OBJECT IDENTIFIER ::= { voice 4 }   -- Reference: huawei-vodigitalif.mib
        hwVoiceDialControlMIB          OBJECT IDENTIFIER ::= { voice 5 }   -- Reference: huawei-vodialcontrol.mib
        hwVoiceCallActiveMIB           OBJECT IDENTIFIER ::= { voice 6 }   -- Reference: huawei-vocallactive.mib
        hwVoiceCallHistoryMIB          OBJECT IDENTIFIER ::= { voice 7 }   -- Reference: huawei-vocallhistory.mib
        hwVoiceGKClientMIB             OBJECT IDENTIFIER ::= { voice 8 }   -- Reference: huawei-vogkclient.mib
        hwVoiceAAAClientMIB            OBJECT IDENTIFIER ::= { voice 9 }   -- Reference: huawei-voaaaclient.mib
        hwVoiceH323CallStatMIB         OBJECT IDENTIFIER ::= { voice 11 }  -- Reference: huawei-voh323statistic.mib
        hwSIPMIB                       OBJECT IDENTIFIER ::= { voice 12 }  -- Reference: huawei-sip.mib

-- under huawei.h3c.h3cCommon

        h3cFtm    OBJECT IDENTIFIER ::= { h3cCommon 1 }
        -- name: xiejianping
        -- id: 00312
        -- date: 2004-01-12
        -- product: VRP Comware
        -- reason: new mib requirement for VRP Comware
        -- Reference: h3c-ftm.mib

        h3cUIMgt    OBJECT IDENTIFIER ::= { h3cCommon 2 }
        -- name: xiejianping
        -- id: 00312
        -- date: 2004-03-18
        -- product: all products
        -- reason: new mib requirement for VRP Comware:
        --   User-interface management such CONSOLE/AUX/TTY/VTY etc.

        h3cSystemMan    OBJECT IDENTIFIER ::= { h3cCommon 3 }
        -- name: xiejianping, gaolong
        -- id: 00312
        -- date: 2004-04-24
        -- product: VRP Comware
        -- reason: relocate from "huawei.huaweiMgmt.huaweiDatacomm.hwSystemMan" for VRP Comware:
        -- Reference: h3c-sys-man.mib

        h3cConfig    OBJECT IDENTIFIER ::= { h3cCommon 4 }
        -- name: xiejianping, gaolong
        -- id: 00312
        -- date: 2004-04-24
        -- product: all products
        -- reason: relocate from "huawei.huaweiUtility.hwConfig"
        -- Reference: h3c-config-man.mib

        h3cFlash    OBJECT IDENTIFIER ::= { h3cCommon 5 }
        -- name: xiejianping
        -- id: 00312
        -- date: 2004-04-24
        -- product: all products
        -- reason: relocate from "huawei.huaweiUtility.hwFlash"
        -- Reference: h3c-flash-man.mib

        h3cEntityExtend    OBJECT IDENTIFIER ::= { h3cCommon 6 }
        -- name: xiejianping
        -- id: 00312
        -- date: 2004-05-18
        -- product: all products
        -- reason: for Entity MIB extend.
        -- Reference: h3c-entity-ext.mib

        h3cIPSecMonitor    OBJECT IDENTIFIER ::= { h3cCommon 7 }
        -- name: xiejianping
        -- id: 00312
        -- date: 2004-06-1
        -- product: all products
        -- reason: for IPSEC VPN.

        h3cAcl    OBJECT IDENTIFIER ::= { h3cCommon 8 }
        -- name: xiejianping
        -- id: 00312
        -- date: 2004-06-1
        -- product: all products
        -- reason: for new ACL mib.
        -- Reference: h3c-acl.mib

        h3cVoiceVlan    OBJECT IDENTIFIER ::= { h3cCommon 9 }
        -- name: xiejianping
        -- id: 00312
        -- date: 2004-06-11
        -- product: all products
        -- reason: for voice vlan.
        -- Reference: h3c-voice-vlan.mib

        h3cL4Redirect   OBJECT IDENTIFIER ::= { h3cCommon 10 }
        -- name: xiejianping
        -- id: 00312
        -- date: 2004-06-11
        -- product: all products
        -- reason: for Layer 4 Redirection.
        -- Reference: h3c-l4rdt.mib

        h3cIpPBX        OBJECT IDENTIFIER ::= { h3cCommon 11 }
        -- name: xiejianping
        -- id: 00312
        -- date: 2004-07-27
        -- product: all products
        -- reason: for GateKeeper MIB.
        -- Reference: h3c-IP-PBX.mib

        h3cUser        OBJECT IDENTIFIER ::= { h3cCommon 12 }
        -- name: xiejianping
        -- id: 00312
        -- date: 2004-07-28
        -- product: all products
        -- Reference: h3c-user.mib

        h3cRadius        OBJECT IDENTIFIER ::= { h3cCommon 13 }
        -- name: xiejianping
        -- id: 00312
        -- date: 2004-07-28
        -- product: all products
        -- Reference: h3c-radius.mib

        h3cPowerEthernetExt        OBJECT IDENTIFIER ::= { h3cCommon 14 }
        -- name: xiejianping
        -- id: 00312
        -- date: 2004-07-29
        -- product: all products
        -- Reference: h3c-power-ethernet-ext.mib

        h3cEntityRelation        OBJECT IDENTIFIER ::= { h3cCommon 15 }
        -- name: xiejianping
        -- id: 00312
        -- date: 2004-08-04
        -- product: all products
        -- Reference: h3c-entity-relation.mib

        h3cProtocolVlan        OBJECT IDENTIFIER ::= { h3cCommon 16 }
        -- name: xiejianping
        -- id: 00312
        -- date: 2004-08-24
        -- product: all products
        -- Reference: h3c-protocol-vlan.mib

        h3cQosProfile        OBJECT IDENTIFIER ::= { h3cCommon 17 }
        -- name: xiejianping
        -- id: 00312
        -- date: 2004-08-24
        -- product: all products
        -- Reference: h3c-qos-profile.mib

        h3cNat        OBJECT IDENTIFIER ::= { h3cCommon 18 }
        -- name: xiejianping
        -- id: 00312
        -- date: 2004-10-10
        -- product: all products
        -- Reference: h3c-nat.mib

        h3cPos        OBJECT IDENTIFIER ::= { h3cCommon 19 }
        -- name: xiejianping
        -- id: 00312
        -- date: 2004-10-11
        -- product: all products
        -- Reference: h3c-pos.mib

        h3cNS          OBJECT IDENTIFIER ::= { h3cCommon 20 }
        -- name: xiejianping
        -- id: 00312
        -- date: 2004-10-14
        -- product: all products
        -- Reference: h3c-ns.mib

        h3cAAL5        OBJECT IDENTIFIER ::= { h3cCommon 21 }
        -- name: xiejianping
        -- id: 00312
        -- date: 2004-11-8
        -- product: all products
        -- Reference: h3c-AAL5.mib

        h3cSSH        OBJECT IDENTIFIER ::= { h3cCommon 22 }
        -- name: xiejianping
        -- id: 00312
        -- date: 2004-11-8
        -- product: all products
        -- Reference: h3c-ssh.mib

        h3cRSA        OBJECT IDENTIFIER ::= { h3cCommon 23 }
        -- name: xiejianping
        -- id: 00312
        -- date: 2004-11-10
        -- product: all products
        -- Reference: h3c-rsa.mib

        h3cVrrpExt        OBJECT IDENTIFIER ::= { h3cCommon 24 }
        -- name: xiejianping
        -- id: 00312
        -- date: 2004-11-27
        -- product: all products
        -- Reference: h3c-vrrp-ext.mib

        h3cIpa        OBJECT IDENTIFIER ::= { h3cCommon 25 }
        -- name: xiejianping
        -- id: 00312
        -- date: 2004-12-2
        -- product: all products
        -- Reference: h3c-ipa.mib

        h3cPortSecurity         OBJECT IDENTIFIER ::= { h3cCommon 26 }
        -- name: xiejianping
        -- id: 00312
        -- date: 2004-12-2
        -- product: all products
        -- Reference: h3c-port-security.mib

        h3cVpls         OBJECT IDENTIFIER ::= { h3cCommon 27 }
        -- name: xiejianping
        -- id: 00312
        -- date: 2004-12-6
        -- product: all products
        -- Reference: h3c-vpls.mib

        h3cE1         OBJECT IDENTIFIER ::= { h3cCommon 28 }
        -- name: xiejianping
        -- id: 00312
        -- date: 2004-12-10
        -- product: all products
        -- Reference: h3c-e1.mib

        h3cT1         OBJECT IDENTIFIER ::= { h3cCommon 29 }
        -- name: xiejianping
        -- id: 00312
        -- date: 2004-12-10
        -- product: all products
        -- Reference: h3c-t1.mib

        h3cIKEMonitor         OBJECT IDENTIFIER ::= { h3cCommon 30 }
        -- name: xiejianping
        -- id: 00312
        -- date: 2004-12-13
        -- product: all products
        -- Reference: h3c-ike-monitor.mib

        h3cWebSwitch         OBJECT IDENTIFIER ::= { h3cCommon 31 }
        -- name: xiejianping
        -- id: 00312
        -- date: 2004-12-16
        -- product: all products
        -- Reference: h3c-web-switch.mib

        h3cAutoDetect         OBJECT IDENTIFIER ::= { h3cCommon 32 }
        -- name: xiejianping
        -- id: 00312
        -- date: 2004-12-16
        -- product: all products
        -- Reference: h3c-auto-detect.mib

        h3cIpBroadcast         OBJECT IDENTIFIER ::= { h3cCommon 33 }
        -- name: gaolong
        -- id: 00803
        -- date: 2004-12-16
        -- product: all products
        -- Reference: h3c-ip-broadcast.mib

        h3cIpx         OBJECT IDENTIFIER ::= { h3cCommon 34 }
        -- name: gaolong
        -- id: 00803
        -- date: 2004-12-16
        -- product: all products
        -- Reference: h3c-ipx.mib

        h3cIPS         OBJECT IDENTIFIER ::= { h3cCommon 35 }
        -- name: gaolong
        -- id: 00803
        -- date: 2004-12-25
        -- product: all products
        -- Reference:

        h3cDhcpSnoop         OBJECT IDENTIFIER ::= { h3cCommon 36 }
        -- name: gaolong
        -- id: 00803
        -- date: 2005-01-13
        -- product: all products
        -- Reference:

        h3cProtocolPriority         OBJECT IDENTIFIER ::= { h3cCommon 37 }
        -- name: gaolong
        -- id: 00803
        -- date: 2005-01-31
        -- product:
        -- Reference:

        h3cTrap         OBJECT IDENTIFIER ::= { h3cCommon 38 }
        -- name: gaolong
        -- id: 00803
        -- date: 2005-02-05
        -- product: definiton of traps for all products
        -- Reference:

        h3cVoice        OBJECT IDENTIFIER ::= { h3cCommon 39 }
        -- name: gaolong
        -- id: 00803
        -- date: 2005-05-03
        -- product: voice products
        -- Reference:

        h3cIfExt         OBJECT IDENTIFIER ::= { h3cCommon 40 }
        -- name: gaolong
        -- id: 00803
        -- date: 2004-12-15
        -- product: all products
        -- Reference: h3c-if-ext.mib

        h3cCfCard         OBJECT IDENTIFIER ::= { h3cCommon 41 }
        -- name: xiejianping
        -- id: 00312
        -- date: 2004-12-21
        -- product: all products
        -- Reference: h3c-cf-card.mib

        h3cEpon         OBJECT IDENTIFIER ::= { h3cCommon 42 }
        -- name: xiejianping
        -- id: 00312
        -- date: 2004-12-29
        -- product: all products
        -- Reference:

        h3cDldp         OBJECT IDENTIFIER ::= { h3cCommon 43 }
        -- name: xiejianping
        -- id: 00312
        -- date: 2004-12-29
        -- product: all products
        -- Reference: h3c-dldp.mib

        h3cUnicast         OBJECT IDENTIFIER ::= { h3cCommon 44 }
        -- name: xiejianping
        -- id: 00312
        -- date: 2005-2-5
        -- product: all products
        -- Reference: h3c-unicast.mib

        h3cRrpp         OBJECT IDENTIFIER ::= { h3cCommon 45 }
        -- name: xiejianping
        -- id: 00312
        -- date: 2005-2-5
        -- product: lanswitch products
        -- Reference: h3c-rrpp.mib
        -- RRPP(Rapid Ring Protection Protocol)

        h3cDomain       OBJECT IDENTIFIER ::= { h3cCommon 46 }
        -- name: gaolong
        -- id: 00803
        -- date: 2005-03-26
        -- product: lanswitch products
        -- Reference:

        h3cIds          OBJECT IDENTIFIER ::= { h3cCommon 47 }
        -- name: gaolong
        -- id: 00803
        -- date: 2005-03-26
        -- product: lanswitch products
        -- Reference:

        h3cRcr          OBJECT IDENTIFIER ::= { h3cCommon 48 }
        -- name: gaolong
        -- id: 00803
        -- date: 2005-04-15
        -- product:
        -- Reference:

        h3cAtmDxi        OBJECT IDENTIFIER ::= { h3cCommon 49 }
        -- name: xiejianping
        -- id: 00312
        -- date: 2005-04-21
        -- product: router products
        -- Reference: h3c-atm-dxi.mib

        h3cMulticast     OBJECT IDENTIFIER ::= { h3cCommon 50 }
        -- name: gaolong
        -- id: 00803
        -- date: 2005-05-25
        -- product:
        -- Reference:

        h3cMpm           OBJECT IDENTIFIER ::= { h3cCommon 51 }
        -- name: gaolong
        -- id: 00803
        -- date: 2005-05-25
        -- product:
        -- Reference: layer 2 multicast port management

        h3cOadp           OBJECT IDENTIFIER ::= { h3cCommon 52 }
        -- name: gaolong
        -- id: 00803
        -- date: 2005-06-12
        -- product:
        -- Reference:

        h3cTunnel           OBJECT IDENTIFIER ::= { h3cCommon 53 }
        -- name: gaolong
        -- id: 00803
        -- date: 2005-06-12
        -- product:
        -- Reference:

        h3cGre           OBJECT IDENTIFIER ::= { h3cCommon 54 }
        -- name: gaolong
        -- id: 00803
        -- date: 2005-06-12
        -- product:
        -- Reference:

    h3cObjectInfo     OBJECT IDENTIFIER ::= { h3cCommon 55 }
        -- name: gaolong
        -- id: 00803
        -- date: 2005-06-25
        -- product:
        -- Reference:

    h3cStorage     OBJECT IDENTIFIER ::= { h3cCommon 56 }
        -- name: gaolong
        -- id: 00803
        -- date: 2005-06-25
        -- product: ix5000
        -- Reference:

    h3cDvpn     OBJECT IDENTIFIER ::= { h3cCommon 57 }
        -- name: gaolong
        -- id: 00803
        -- date: 2005-06-25
        -- product:
        -- Reference:

    h3cDhcpRelay     OBJECT IDENTIFIER ::= { h3cCommon 58 }
        -- name: gaolong
        -- id: 00803
        -- date: 2005-06-25
        -- product:
        -- Reference:

    h3cIsis     OBJECT IDENTIFIER ::= { h3cCommon 59 }
        -- name: gaolong
        -- id: 00803
        -- date: 2005-07-09
        -- product:
        -- Reference:

    h3cRpr     OBJECT IDENTIFIER ::= { h3cCommon 60 }
        -- name: gaolong
        -- id: 00803
        -- date: 2005-08-02
        -- product:
        -- Reference:

    h3cSubnetVlan     OBJECT IDENTIFIER ::= { h3cCommon 61 }
        -- name: gaolong
        -- id: 00803
        -- date: 2005-09-02
        -- product:
        -- Reference:

    h3cDlswExt     OBJECT IDENTIFIER ::= { h3cCommon 62 }
        -- name: gaolong
        -- id: 00803
        -- date: 2005-09-20
        -- product:
        -- Reference:

    h3cSyslog     OBJECT IDENTIFIER ::= { h3cCommon 63 }
        -- name: gaolong
        -- id: 00803
        -- date: 2005-09-20
        -- product:
        -- Reference:

END
