--==========================================================
--
-- MIB      : G700 Media Gateway               Avaya, Inc.
--
-- Version  : 0.1                            31 October 2001
-- Version  : 0.2                            21 January 2002
-- Version  : 0.3                            12 February 2002
-- Version  : 0.4                            07 March 2002
-- Version  : 1.1                            07 May 2002
-- Version  : 1.2                            24 May 2002
-- Version  : 1.3                            18 Jul 2002
-- Version  : 1.4                            29 Oct 2002
-- Version  : 1.5                            01 Mer 2003
-- Version  : 1.6                            2  Apr 2003
-- Version  : 1.7                            10 Apr 2003      
-- Version  : 1.8                            27 Apr 2003
-- Version  : 1.9                            03 May 2003     
-- Version  : 1.10                           04 Nov 2003
-- Version  : 1.11                           04 Nov 2003
-- Version  : 1.12                           05 Nov 2003
-- Version  : 1.13                           01 Dec 2003 
-- Version  : 1.14                           01 Feb 2004
-- Version  : 1.15                           01 Apr 2004
-- Version  : 1.16                           07 Apr 2004
-- Version  : 1.17                           15 May 2004
-- Version  : 1.18                           17 July 2004 
-- Version  : 1.19                           5 Oct 2004 
-- Version  : 1.20                           21 Jan 2005
-- Version  : 1.21                           5 Feb 2005
-- Version  : 1.22                           7 Jun 2005
-- Version  : 1.23                           21 June 2005
-- Version	: 1.24							 18 Jul 2005 
-- Version	: 1.25							 16 Oct 2005
-- Version	: 1.26							 26 Jan 2006 
-- Version	: 1.27							 26-Feb-2006
-- Version	: 1.28							 24-Mar-2006
-- Version	: 1.29							 2 -May-2006
-- Version	: 1.30							 20-Jul-2006
-- Version	: 1.31							 31-Jul-2006
-- Version	: 1.32							 17-Oct-2006
-- Version	: 1.33							 01-Nov-2006  
-- Version	: 1.34							 25-Dec-2006
-- Version	: 1.35							 01-Jan-2007
-- Version	: 1.36							 06-Feb-2007   
-- Version	: 1.37							 20-Feb-2007
-- Version	: 1.38							 28-May-2007
-- Version	: 1.39							 08-July-2007
-- Version	: 1.40							 11-Sep-2007
-- Version	: 1.41							 17-Sep-2007
-- Version	: 1.42							 02-Oct-2007  
-- Version	: 1.43							 03-Oct-2007  
-- Version	: 1.44							 07-Oct-2007  
-- Version	: 1.45							 17-Oct-2007  
-- Version	: 1.46							 15-Dec-2007  
-- Version	: 1.47							 21-Jan-2008
-- Version	: 1.48							 03-Feb-2008
-- Version	: 1.49							 04-Mar-2008
-- Version	: 1.50							 06-Mar-2008
-- Version	: 1.51							 28-Mar-2008
-- Version	: 1.52							 06-Apr-2008
-- Version	: 1.53							 08-May-2008
-- Version	: 1.54							 23-July-2008
-- Version	: 1.55							 16-Sep-2008
-- Version	: 1.56							 05-Nov-2008
-- Version	: 1.57							 19-Nov-2008   
-- Version	: 1.58							 22-Jan-2009
-- Version	: 1.59							 04-Mar-2009
--==========================================================
--
-- Copyright 2001-2008 Avaya, Inc.  All Rights Reserved.
--
-- THIS IS UNPUBLISHED PROPRIETARY SOURCE CODE OF Avaya Inc.
-- The copyright notice above does not evidence any
-- actual or intended publication of such source code.
--
--==========================================================
--                       
-- ========================================================
-- Source Safe data:
-- $Revision: 60 $
-- Check In: $Date: 19/04/09 5:59p $
-- $Author: Sbiton $
-- $Archive: /MIBs/Version 1.0/Source/Avaya/G700-MG-MIB.MY $
-- ========================================================
--
-- Compilation note: This MIB module includes items from (lucent) LOAD-MIB.
--    Both modules have groups named 'products' and 'mibs'. This fact causes 
--    problems for some SNMP MIB compilers. A bypass is to temporally rename
--    both groups in LOAD-MIB to 'lucentProduct' and 'lucentMibs' before 
--    compiling this module.                                            
--     
--  Changes in 1.59 -  04-Mar-2009 - Shlomi Biton
--  1.)  Update cmgPrimarySearchTime range to (1..59) instead of (1..60).
--		 Update cmgTotalSearchTime range to (2..60) instead of (1..60)
--
--  Changes in 1.58 -  22-Jan-2009 - Shlomi Biton
--  1.) Update cmgModuleType to include g430Mainboard(51).
--         
--  Changes in 1.57 -  19-Nov-2008 - Shlomi Biton
--  1.) Change Distributed Office to Communication Manager Branch Edition names.   
--  2.) Change i40-14A to i40-A14 and G250-14A to G250-A14.
--
--  Changes in 1.56 -  05-Nov-2008 - Shlomi Biton
--  1.) Update cmgVoipSlot description. 
--
--  Changes in 1.55 -  16-Sep-2008 - Shlomi Biton
--  1.) Add new enumerations for G430 H.248.
--      a. cmgHWType - avayaG430(41).
--		b. cmgModuleType - g430Mainboard(51)
--
--  Changes in 1.54 -  23-July-2008 - Shlomi Biton
--  1.) Add new enumeration to cmgVoipFaultMask - bit 8 - Unsupported DSP module. 
--
--  Changes in 1.53 -  08-May-2008 - Mark Rajcok
--  1.) Remove cmgRemotePrimaryClockSource, cmgRemoteSecondaryClockSource, 
--		cmgRemoteClockSwitching
--
--	Changes in 1.52 -  06-Apr-2008 - Shlomi Biton 
--  1.) Update Venus and Jupiter Product names to be G430 and G450.
--
--	Changes in 1.51 -  28-Mar-2008 - Imad Benbrahim
--  1.) Added trap cmgTimeslotOccupancyFault to indicate that timeslot occupancy
--      exceeded a threshold. New trap cmgTimeslotOccupancyClear clears that
--      condition.
--  2.) Added trap cmgTimeslotAvailabilityFault to indicate timeslot exhaustion.
--      New trap cmgTimeslotAvailabilityClear clears that condition.
--  3.) Added new attributes for timselot monitoring: cmgTimeslotMonitoring,
--      cmgTimeslotUpperThreshold and cmgTimeslotLowerThreshold.
--
--	Changes in 1.50 -  06-Mar-2008 - Shlomi Biton 
--  1.) Update cmgHardwareFaultMask:   
--  07      0/7   0x01   Power On Status Test failure
--  19      2/3   0x10   TDM Test Expansion Box 1 Failure
--  20      2/4   0x08   TDM Test Expansion Box 2 Failure
--  21      2/5   0x04   PoE Power Supply Base Box Failure
--  22      2/6   0x02   PoE Power Supply Expansion Box 1 Failure
--  23      2/7   0x01   PoE Power Supply Expansion Box 2 Failure
--
--	Changes in 1.49 -  03-Feb-2008 - Shlomi Biton 
--  1.) Add new varbind to cmgFirmwareDownloadBegun.
--
--	Changes in 1.48 -  03-Feb-2008 - Shlomi Biton 
--  1.) Add enumerations for Venus and Jupiter to cmgHWType
--		a. avayaDistributedOfficeJupiter(35)
-- 		b. avayaDistributedOfficeVenus(37) 
--	2.) Add enumeration for Jupiter Mainboard in cmgModuleType. 
--		a. jupiterMainboard(50)
--	3.) Add poe8(26) enumeration for MM118 in CmgModuleList and cmgModuleType.
--
--	Changes in 1.47 -  21-Jan-2008 - Mark Rajcok
--  1.) Add new cmgExpansionUnits table to cmgChassis group for venus and mercury
--
--	Changes in 1.46 -  15-Dec-2007 - Shlomi Biton according to Imad Benbrahim request
--  1.) Update the ranges of: cmgAnalogReceiveGain and cmgAnalogTransmitGain to be: 
--      (-600..300).
--
--	Changes in 1.45 -  17-Oct-2007 - Imad Benbrahim
--  1.) Add Echo Canceller attributes to the cmgVoip group.
--  2.) Add table cmgAnalogPorts to the cmgChasssis group. This new table
--      contains Echo canceller attributes and analog ports correction
--      attributes for the balance, receive gain and transmit gain.
--
--	Changes in 1.44 -  07-Oct-2007 - Shlomi Biton
--	1.) Fix the order of the bits in cmgVoipFaultMask as follows:
--    Cajun  Octet Octet
--    bit#   bit#  value	Meaning
--    0      0/0   0x80	Occupancy above threshold, based on a snapshot of
--			cmgVoipChannelsInUse divided by cmgVoipTotalChannels.
--    1      0/1   0x40	Occupancy above threshold, based on cmgVoipAverageOccupancy.
--    2      0/2   0x20	VoIP engine automatic reset.
--    3      0/3   0x10	VoIP hardware fault.
--    4      0/4   0x08	VoIP IP configuration fault.
--    5      0/5  0x04    VoIP DSP Failure
--    6      0/6   0x02    VoIP DSP CORE Failure 
--    7      0/7   0x01    VoIP DSP FPGA Failure
--    8-15   1/8-15 Unused
--
--	Changes in 1.43 -  03-Oct-2007 - Shlomi Biton
--	1.) Add explanation on new bits in cmgVoipFaultMask 
--    8      1/0   0x01    VoIP DSP FPGA Failure
--    9      1/1   0x02    VoIP DSP CORE Failure
--    10     1/2   0x04    VoIP DSP Failure
--    11-15  1/3-7 Unused
--
--	Changes in 1.42 -  02-Oct-2007 - Shlomi Biton
--	1.) Change g450SupervisorBlade(40) to g450Mainboard(40) in cmgModuleType.
--  
--	Changes in 1.41 -  17-Sep-2007 - Shlomi Biton
--	1.) Add avayaG250-14A(8) to cmgHWType. 
--  2.) Add g250-int-analog-6L8T(29) to cmgModuleList and cmgModuleType.
--
--	Changes in 1.40 -  11-Sep-2007 - Mark Rajcok
--	1.) Add cmgRemotePrimaryClockSource,  cmgRemoteSecondaryClockSource,
--      cmgRemoteClockSwitching, cmgClockSourceControl 
--      for G450 (SRAD 124033)
--
--	Changes in 1.39 -  28-May-2007 - Shlomi Biton
--	1.) Add avayaDistributedOfficei40-14A(34) to cmgHWType. 
--  2.) add i40-14A-int-analog-6L8T(49) to cmgModuleList and cmgModuleType.
--
--	Changes in 1.38 -  28-May-2007 - Shlomi Biton
--	1.) Add avayaTRM480(33)to cmgHWType. 
--
--	Changes in 1.37 -  20-Feb-2007 - John Madden/Shlomi Biton
--	1.) Increase length of cmgModuleList to account for 10 slots in G450
--  2.) Use shorter enumerations in cmgModuleList and cmgModuleType:
--      i120-intana(44) - i120 Integrated analog module
--	    i40-int-analog-2L4T(45) - avayaDistributedOfficei40 Integrated analog 2 Lines + 4 Trunks module
--		i40-int-analog-2L1T(46)- avayaDistributedOfficei40 Integrated analog 2 Lines + 1 Trunk module
--		i40-int-BRI(47) - avayaDistributedOfficei40 Integrated BRI Trunk module 
--		i40-int-DS1(48) - avayaDistributedOfficei40 Integrated DS1 Trunk module
--
--	Changes in 1.36 -  06-Feb-2007 - Shlomi Biton
--	1.) Add new enumerations to cmgModuleList and cmgModuleType
--      avayaDistributedOfficei120-intana(44) - i120 Integrated analog module
--	    avayaDistributedOfficei40-int-analog-2L4T(45) - avayaDistributedOfficei40 Integrated analog 2 Lines + 4 Trunks module
--		avayaDistributedOfficei40-int-analog-2L1T(46)- avayaDistributedOfficei40 Integrated analog 2 Lines + 1 Trunk module
--		avayaDistributedOfficei40-int-BRI(47) - avayaDistributedOfficei40 Integrated BRI Trunk module 
--		avayaDistributedOfficei40-int-DS1(48) - avayaDistributedOfficei40 Integrated DS1 Trunk module
--
--	Changes in 1.35 -  01-Jan-2007 - Shlomi Biton
--	1.) Rename Liverpool Project hardware names to fit Avaya Distributed Office Name
--      convention. In particular change cmgHWType values:
--		avayaG350L(28) to avayaDistributedOfficei120(28).
--		avayaG250L(29) to avayaDistributedOfficei40-Analog(29).
--      avayaG250L-BRI(30) to avayaDistributedOfficei40-BRI(30). 
--      avayaG250L-DS1(31) to avayaDistributedOfficei40-DS1(31).
--      avayaG250L-DCP(32) to avayaDistributedOfficei40-DCP(32). 
--      and cmgModuleList and cmgModuleType values:
--		server-blade(34) to avayaAM110ApplicationModule(34).
--
--	Changes in 1.34 -  25-Dec-2006 - M. Deutsch/John Madden
--	1.) Add enum (3):camp-on to cmgVoipAdminState
--      
-- 	Changes in 1.33 -  01-Nov-2006 - Shlomi Biton
--	1.) Add the values:  avayaG450(7),	avayaG350L(28), avayaG250L(29), avayaG250L-BRI(30), 
--      avayaG250L-DS1(31), avayaG250L-DCP(32) to cmgHWType.
--
-- 	Changes in 1.32 -  17-Oct-2006 - Shlomi Biton
--	1.) Add the values:  41 (TIM508), 42(TIM516) and 43(TIM518) to cmgModuleType.
--
-- 	Changes in 1.31 -  31-Jul-2006 - Shlomi Biton
--	1.) Change cmgStatic802Vlan and cmgCurrent802Vlan to support Vlan range of 1-4090(inclusive)
--      instead of 1-3071.
--
-- 	Changes in 1.30 -  20-Jul-2006 - John Madden
--	1.) Change cmgVoipDSPCoreTable so that there is no row creation
--	2.) Add dsp not responding test enumeraton
--
-- 	Changes in 1.29 -  2-May-2006 - Pesah Spector, Meir Duetsch, John Madden
--	1.) Change cmgVoipDSPCoreTable index
--	2.) Make cmgPrimaryClockSource, cmgSecondaryClockSource, cmgActiveClockSource read/write
--	3.) Add new element cmgClockSwitching
--
-- 	Changes in 1.28 - 24-Mar-2006 - Pesah Spector, John Madden
--	1.) Add cmgVoipDSPCoreTable for G450
--  2.) Add g450SupervisorBlade(40) enumeration for cmgModuleType and cmgModuleList
--  3.) Update range for cmgVoipSlot and cmgEtrModule for G450
--  4.) Add server-blade for G250L and G350L
--
-- 	Changes in 1.27 - 26-Feb-2006 - Meir Deutsch
--  1.) Add cmgPrimarySearchTime , cmgTotalSearchTime and cmgTransitionPoint
--  2.) Re use of cmgHardwareFanLowSpeedLevel. 
--
--  Changes in 1.26 - 26-Jan-2006 - Meir Deutsch
--  1.) Add TGM550/TIM514/TIM510/TIM521 support (cmgHwType and cmgModuleType).
--
--   
--  Changes in 1.25 - 16-Oct-2005 - Shlomi Biton
--	1.) Remove "Fan speed Low" MIB item. 
--
--  Changes in 1.24 - 18-Jul-2005 - John Madden
--	1.) Mark cmgDsu mib elements as obsolete
--  2.) Mark Dsu related traps as obsolete
--
--  Changes in 1.23 - 21-June-2005 - Shlomi Biton
--  1.) Add cmgHardwareFanLowSpeedLevel to control the speed of the fans. 
--  2.) Update cmgModuleNumberOfPorts from 0..32 to 0..64 for MM316 (40 ports +1 Gig copper).
--  3.) Fixing cmgModuleList and cmgModuleType to be
--      fxs24(18),	     MM716 24 FXS analog ports module	
--	4.) Update cmgTrapModule to be with range (0..32) instead of (0..10).
--  5.) Add new MM enumeration for MM314CR for cmgModuleList and cmgModuleType.
--      poe24cr(25), 		HDMM314 24 power over Ethernet plus 1 GBIC port 
--
--  Changes in 1.22 - 7-Jun-2005 - John M. Madden
--  1.) update cmgModuleSlot from 1..7 to 1..9
--  2.) update cmgModuleNumberOfPorts from 0..8 to 0..32
--  3.) Add bounds for cmgCcModule, cmgCcPort, cmgCcRelay, cmgETRModule, cmgETRNumberOfPorts
--  4.) Change cmgDynCacRBBL from INTEGER to Integer32                
--
--  Changes in 1.21 - 5-Feb-2005 - Meir Deutsch
--  1.) Add G250-DCP and G250-DS1 support (cmgHwType and cmgModuleType). change object names for G250/G250-BRI
--
--Changes in 1.20 - 31-Jan-2005 - Shlomi Biton
--  1.) Fixing compilation problems.
--  2.) Adding new enumarations to CmgModuleList and cmgModuleType of poe(40).
--  3.) Adding to cmgMgpFaultMask - bit 16 - Configuration download failure. 
--  4.) Adding 3 new trap for download configuration as follows:
--      a. cmgConfigDownloadFault - An attempt to download a configuration file has failed.
--      b. cmgConfigDownloadBegun - The media gateway has begun download of a configuration file.
--      c. cmgConfigDownloadSuccess	- The media gateway has completed successful download 
--         of a configuration file.
--
--Changes in 1.19 - 5-Oct-2004 - Meir Deutsch
--  1.) Add G250-BRI support (cmgHwType AND cmgModuleType) 
--
-- Changes in 1.18 - 17-Jul-2004 - Pesah Spector
--  1.) Add new trap that signals on non critical problems in firmware 
--      download process - cmgFirmwareDownloadWarning
--
-- Changes in 1.17 - 15-May-2004 - Dan Gluskin
--  1.) Add 'invalid(253)' cmgModuleType (required by G250 to send a cmgInsertFault trap
--      When a module in inserted in the wrong slot
--
-- Changes in 1.16 - 07-Apr-2004 - Shlomi Biton
--   1.) Changing dcp16 to dcp24 in cmgModuleList and cmgModuleType. 
--	     G350 HDMM312 is now dcp24hd(13) instead of dcp24(13).                            
--	     dcp24(17) for MM717 instead of dcp16(17). 
--	 2.) Adding g250intana(19) for G250 Integrated analog module in addition to g350intana(16)
--
-- Changes in 1.15 - 19-Feb-2004 - Shlomi Biton
--   1.) Add dcp16(17) and fxo4fxs12(18) to cmgModuleType.
--
-- Changes in 1.14
--   1.) Add cmgHWtype enumeraton for G250
--          
-- Changes in 1.13
--   1.) Add cmgHWtype enumeraton for G350
--   2.) cmgModuleName access changed to read-only
--
-- Changes in 1.12 
--  Move the traps OID under the new cmgTrapV3separator	Identifier
--  Rational: RFC 2576 says: 'If the SNMPv1 generic-trap parameter is 'enterpriseSpecific(6)', 
--       the SNMPv2 snmpTrapOID parameter SHALL be the concatentation of  the SNMPv1
--       enterprise parameter and two additional sub- identifiers, '0', 
--       and the SNMPv1 specific-trap parameter.'
--
--   in SNMPv1 G350 is sending for cmg traps:
--   generic trap: 		enterpriseSpecific(6)
--   enterprise: 		cmgTrapTypes(1.3.6.1.4.1.6889.2.9.1.5.2.2)
--   specific trap:		x (cmg trap number)
--
--   Consequently, for SNMPv3, G350 should send 1.3.6.1.4.1.6889.2.9.1.5.2.2.0.x 
--   and so the traps OIDs were moved under this identifier" 
--
--
-- Changes in Version 1.11
-- 1.)  Add cmgDynamicCAC group
--
-- Changes in Version 1.10
-- 1.)  Add G350 R1 new cmgModuleTypes
--
-- Changes in Version 1.9
-- 1.) Add the common traps variables (cmgTrapSubsystem, cmgTrapOnBoard, cmgTrapLocation) to 
--            cmgUnsupportedMmEnrolement and cmgDataModuleAwohConflict
-- 2.) Add range to cmgCcPulseDuration
--
-- Changes in Version 1.8
-- 1.) cmgDataModuleAwohConflict ADDED
-- 2.) CmgIccVlan removed (redundant with cmgStatic802Vlan
-- 3.) cmgEtrStatus, cmgEtrAdminState enumeration changed
-- Changes in Version 1.7
-- 1.) cmgCcOperatingTime renamed  to cmgCcPulseDuration 
--
-- Changes in Version 1.6
--  1.) ETR and Contact-Closure tables revised
--  2.) unsupportedMmEnrolement Trap added
--  3.) cmgModuleSlot range changed to 1..7 (for G350)
--  4.) cmgModuleFaultMask changed
--  5.) new item: cmgIccVlan
--
-- Changes in Version 1.5
-- 1.) Added support for Boxster
-- 2.) cmgContactClosures section
-- 3.) cmgETR section                             
--
-- Changes in Version 1.4
-- 1.) Added traps #36 cmgSyncSignalExcess and trap #37 cmgSyncExcessClear.
--     [hw021513]
-- 2.) Added to cmgHardwareFaultMask Octet/Bit 2/2 for Clock Synchronization Signal Excessive Switching. [hw021513]
--
-- Changes in Version 1.3
-- 1.) Changed size of cmgPrimaryClockSource and 
--     cmgSecondaryClockSource to 21. [hw021163]
-- 2.) Added traps #34 cmgSyncSignalWarn and trap #35 cmgSyncWarnClear.
--     [hw021134]
-- 3.) Added to cmgHardwareFaultMask Octet/Bit 2/1 for Clock Synchronization Signal Warning. [hw021196]
--
-- Changes in Version 1.2
-- 1.) Changed avayaProducts to products
-- 2.) Changed avayaMibs to mibs
-- 3.) Added parsing tokens 001 and 002 to this file in the form of comments
--      to allow scripts to operate on that part only. The script will
--      change products to avayaProducts and mibs to avayaMibs to avoid 
--      name conflicts with other MIBs during execution of Emanate MIB 
--      compiler and code generation tools.
--
-- Changes in Version 1.1
-- 1.) Corrected the order of variables in cmgFirmwareDownFault trap
--     (MR#hw020863)
-- 2.) Added to cmgVoipFaultMask Octet/Bit 0/4 for VoIP IP configuration fault
--     (MR#hw020860)
-- 3.) Added traps #142 cmgVoipIPConfigFault and trap #143 cmgVoipIpConfigClear
--     (MR#hw020860)
--
-- Changes in Version 0.4
-- 1.) Changed cmgCurrent802Vlan range to 1..3071
-- 2.) Changed cmgVoipRemoteRtcpReportPeriod range to 5..30
-- 3.) Changed cmgVoipLocalRtcpReportPeriod range to 5..30
--
-- Changes in Version 0.3
-- 1.) Changed cmgVoipLocalRtcpReportPeriod range to 0..300
-- 2.) Changed cmgStatic802Vlan range to 1..3071
--
-- Changes in Version 0.2
-- 1.) Changed MG-MIB to G700-MG-MIB
-- 2.) Replaced C-HawkMediaGateway by g700MediaGateway in object names
-- 3.) Replaced IP2100 by G700 in descriptions
-- 4.) Changed LAST-UPDATED and CONTACT-INFO fields in MODULE-IDENTITY
-- 5.) Removed objects cmgCurrentSubnetMask, cmgCurrentDefaultGateway,
--	cmgStaticSubnetMask and cmgStaticDefaultGateway from
--	cmgProcessorConfig group. Their OIDs will remain unused.
--	The OIDs for the remaining objects remain same.
-- 6.) Changed LOAD to LOAD-MIB in the IMPORTS clause

G700-MG-MIB DEFINITIONS ::= BEGIN

IMPORTS
        MODULE-IDENTITY, NOTIFICATION-TYPE, OBJECT-TYPE, IpAddress, Integer32, enterprises
                FROM SNMPv2-SMI
        RowStatus
                FROM SNMPv2-TC
	DisplayString
		FROM RFC1213-MIB
	genAppFileId, genAppFileName, genAppFileVersionNumber,
	genOpLastFailureIndex,genOpLastWarningDisplay
		FROM LOAD-MIB
			TimeTicks
        FROM RFC1155-SMI;

--Warning! do not change the token below. Required for parsing.
--ChkTk001 Parsing token 001

avaya		OBJECT IDENTIFIER ::= { enterprises 6889 }
products	OBJECT IDENTIFIER ::= { avaya 1 }
mibs		OBJECT IDENTIFIER ::= { avaya 2 }

g700MediaGateway	OBJECT IDENTIFIER ::= { products 9 }
g700MediaGatewayMIB	OBJECT IDENTIFIER ::= { mibs 9 }

--Warning! do not change the token below. Required for parsing.
--ChkTk002 Parsing token 002

CmgItuPerceivedSeverity ::= TEXTUAL-CONVENTION
       		STATUS current
       		DESCRIPTION
            		"ITU perceived severity values"
       		REFERENCE
            "ITU Recommendation M.3100, 'Generic Network Information
               Model', 1995
               ITU Recommendation X.733, 'Information Technology - Open
               Systems Interconnection - System Management: Alarm
               Reporting Function', 1992"
       		SYNTAX         INTEGER
              	{
              	cleared (1),
              	indeterminate (2),
              	critical (3),
              	major (4),
              	minor (5),
              	warning (6)
              	}  


cmgmib MODULE-IDENTITY
       LAST-UPDATED    "200312011443Z"
       ORGANIZATION "Avaya, Inc."
       CONTACT-INFO
              "         Development Support

                Postal: M. V. Roman
                	Avaya, Inc.
                        1300 W. 120th Avenue
                        Westminster, CO  80234-2726
                   Tel: +1 303 538 1934
                E-mail: mvroman@avaya.com

		Postal: P. C. Patil
                	Avaya, Inc.
                        1300 W. 120th Avenue
                        Westminster, CO  80234-2726
		E-mail: paragp@avaya.com
		
                     Dan Gluskin
                     Avaya Inc.
                Tel: +972(3)6457561
              Email: dgluskin@avaya.com
             Postal: Atidim technology Park, Bldg. #3
                     Tel Aviv, Israel, 61131

		"
       DESCRIPTION
	       "A MIB to support the Avaya G700 Media Gateway."
       ::= { g700MediaGatewayMIB 1 }

-- Textual Conventions

	CmgModuleSlot ::= TEXTUAL-CONVENTION
		STATUS current
		DESCRIPTION
			"gateway module slot number"
		SYNTAX INTEGER (1..9)

-- Groups in the mediaGateway

cmgChassis	OBJECT IDENTIFIER ::= { cmgmib 1 } -- Chassis group
cmgProcessor	OBJECT IDENTIFIER ::= { cmgmib 2 } -- MG processor group
cmgControllers	OBJECT IDENTIFIER ::= { cmgmib 3 } -- MG call controller group
cmgVoip		OBJECT IDENTIFIER ::= { cmgmib 4 } -- VoIP group
cmgTraps	OBJECT IDENTIFIER ::= { cmgmib 5 } -- Traps group
cmgContactClosures OBJECT IDENTIFIER ::= { cmgmib 6 }
cmgETR OBJECT IDENTIFIER ::= { cmgmib 7 }
cmgDynamicCAC OBJECT IDENTIFIER ::= { cmgmib 8 }

--
--	CHASSIS GROUP
--

cmgHWType OBJECT-TYPE
	SYNTAX      INTEGER { media-gateway(1),
	                      g350(2),
	                      avayaG250(3),
	                      avayaG250-BRI(4),
	                      avayaG250-DS1(5),
	                      avayaG250-DCP(6),
	                      avayaG450(7),
	                      avayaG250-A14(8),
	                      avayaTGM550(10),
	                      avayaCommunicationManagerBranchEditioni120(28),
	                      avayaCommunicationManagerBranchEditioni40-Analog(29),
	                      avayaCommunicationManagerBranchEditioni40-BRI(30),
	                      avayaCommunicationManagerBranchEditioni40-DS1(31),
	                      avayaCommunicationManagerBranchEditioni40-DCP(32),  
	                      avayaTRM480(33),
	                      avayaCommunicationManagerBranchEditioni40-A14(34),
						  avayaCommunicationManagerBranchEditionG450(35),
                          avayaCommunicationManagerBranchEditionG430(37),
                          avayaG430(41)                      
	                      }
        MAX-ACCESS  read-only
        STATUS      current
        DESCRIPTION "Indicates the type of component. Where 'media-gateway' refers to G700"
	::= { cmgChassis 1 }

cmgModelNumber OBJECT-TYPE
	SYNTAX      DisplayString (SIZE (0..16))
        MAX-ACCESS  read-only
        STATUS      current
        DESCRIPTION "Model number of this component."
	::= { cmgChassis 2 }

cmgDescription OBJECT-TYPE
	SYNTAX      DisplayString (SIZE (0..32))
        MAX-ACCESS  read-only
        STATUS      current
        DESCRIPTION "Description of this component: G700 Media Gateway."
	::= { cmgChassis 3 }

cmgSerialNumber OBJECT-TYPE
	SYNTAX      DisplayString (SIZE (0..16))
        MAX-ACCESS  read-only
        STATUS      current
        DESCRIPTION "Serial number of this gateway."
	::= { cmgChassis 4 }

cmgHWVintage OBJECT-TYPE
	SYNTAX      DisplayString (SIZE (0..8))
        MAX-ACCESS  read-only
        STATUS      current
        DESCRIPTION "Hardware version of this gateway."
	::= { cmgChassis 5 }

cmgHWSuffix OBJECT-TYPE
	SYNTAX      DisplayString (SIZE (0..2))
        MAX-ACCESS  read-only
        STATUS      current
        DESCRIPTION "Hardware vintage suffix of this gateway."
	::= { cmgChassis 6 }

cmgStackPosition OBJECT-TYPE
	SYNTAX      INTEGER (1..10)
        MAX-ACCESS  read-only
        STATUS      current
        DESCRIPTION "Position of this media gateway in the Cajun stack,
	counting from the bottom of the stack."
	::= { cmgChassis 7 }

cmgModuleList OBJECT-TYPE
	SYNTAX      OCTET STRING (SIZE (14))
        MAX-ACCESS  read-only
        STATUS      current
        DESCRIPTION
	"List of the physical media modules installed in this gateway.
	Meaning of each octet is as follows.
	1	Number of slots; in the G700 Media Gateway this is
		always 4.
	2	Type of slot identifier; in the G700 Media Gateway
		this is always integer(2).
	3-4	Length of each field in the following sequence; in the
		G700 Media Gateway this is always 1.
	5-14 Module type ids in slot order, 1 - 10.  Values are
		defined below for cmgModuleType, or none(0) if no
		module is installed.

		none(0),		-- no module installed
		t1e1-voip(1),	-- T1/E1 with integrated CSU/DSU & VoIP DSP
		bri(2),			-- BRI trunk module
		dcp(3),			-- DCP station module
		analog(4),		-- combination analog line and trunk
		t1e1(5),		-- T1/E1 with integrated CSU/DSU
		voip(6),		-- dedicated VoIP media module
		icc(7),			-- internal call controller
		fxo4fxs4(9),  	-- MM714 4 FXS + 4FXO analog ports module
		bri2(10),  		-- MM722 2 BRI trunk ports module
		ds1wan(11), 	-- MM340 1 DS1 (E1/T1) WAN data port module
		uspwan(12),		-- MM342 1 USP WAN data port module
		dcp24hd(13),	-- HDMM312 24 DCP station ports G350 high-density form-factor module
		poe24(14), 		-- HDMM314 24 power over Ethernet plus 1 GBIC port 
		g350intana(16), -- G350 Integrated analog module
	    dcp24(17),		-- MM717 24 DCP station ports module	        		
		fxs24(18),	    -- MM716 24 FXS analog ports module	
		g250-int-analog-2L4T(19), -- G250 Integrated analog 2 Lines + 4 Trunks module
		g250-int-analog-2L1T(20), -- G250 Integrated analog 2 Lines + 1 Trunk module
		g250-int-BRI(21), -- G250 Integrated BRI Trunk module 
		g250-int-DS1(24), -- G250 Integrated DS1 Trunk module
		g250-int-12pDCP(23), -- G250 Integrated 12 Port DCP lines module
		poe40(22), 		-- HDMM316 40 power over Ethernet plus 1 Giga bit copper  
		poe24cr(25),	-- HDMM314 24 power over Ethernet plus 1 GBIC port (Cost Reduction)
		poe8(26),  -- MM118 - 8 10/100 power over Ethernet ports module
		tgm550-int-analog-2L2T(30), -- TGM550 Integrated analog 2 Lines + 2 Trunks module
		tim514(31),		-- TIM514 4 FXS + 4 FXO analog ports module
		tim510(32),		-- TIM510 1 DS1 (E1/T1) module
		tim521(33),		-- TIM521 4 BRI trunk ports module
		avayaAM110ApplicationModule(34),	-- Avaya Communication Manager Branch Edition Application Module for i40 and i120.
		g450Mainboard(40),	-- G450 mainboard
		tim508(41),     -- TIM508 8 FXS analog ports module
		tim516(42),     -- TIM516 16 FXS analog ports module
		tim518(43),     -- TIM518 8 FXS + 8 FXO analog ports module     		
		i120-intana(44), -- i120 Integrated analog module
	    i40-int-analog-2L4T(45), -- avayaCommunicationManagerBranchEditioni40 Integrated analog 2 Lines + 4 Trunks module
		i40-int-analog-2L1T(46), -- avayaCommunicationManagerBranchEditioni40 Integrated analog 2 Lines + 1 Trunk module
		i40-int-BRI(47), -- avayaCommunicationManagerBranchEditioni40 Integrated BRI Trunk module 
		i40-int-DS1(48), -- avayaCommunicationManagerBranchEditioni40 Integrated DS1 Trunk module
		i40-A14-int-analog-6L8T(49), -- avayaCommunicationManagerBranchEditioni40 Integrated analog 6 Lines + 8 Trunks module				
		avayaCommunicationManagerBranchEditionG450Mainboard(50), --  Mainboard
		g430Mainboard(51),
		unknown(255)	-- type cannot be determined
	"
	::= { cmgChassis 8 }

cmgReset OBJECT-TYPE
	SYNTAX      INTEGER { on(1), off(2) }
        MAX-ACCESS  read-write
        STATUS      current
        DESCRIPTION
	"Setting the value of this attribute to ON is interpreted as
	a reset command for the whole chassis.  It initiates a complete
	reinitialisation of the chassis and of all the devices
	incorporated inside the chassis."
	::= { cmgChassis 9 }



--
--	Hardware Subgroup
--

cmgHardware	OBJECT IDENTIFIER ::= { cmgChassis 10 }

cmgCpuTemp OBJECT-TYPE
	SYNTAX      Integer32
	MAX-ACCESS  read-only
	STATUS      current
	DESCRIPTION
	"Reading of the internal temperature sensor at the CPU,
	expressed in degrees Celsius."
	::= { cmgHardware 1 }

cmgCpuTempWarningThresh OBJECT-TYPE
	SYNTAX      Integer32
	MAX-ACCESS  read-only
	STATUS      current
	DESCRIPTION
	"Internal enclosure temperature warning threshold, expressed in degrees
	Celsius.  When the temperature at the CPU sensor exceeds the threshold,
	a trap is sent to the management console.  If both CPU and DSP sensors
	exceed their thresholds, only one trap is sent."
	::= { cmgHardware 2 }

cmgCpuTempShutdownThresh OBJECT-TYPE
	SYNTAX      Integer32
	MAX-ACCESS  read-only
	STATUS      current
	DESCRIPTION
	"Internal enclosure temperature shutdown threshold, expressed in degrees
	Celsius.  When the temperature at the CPU sensor exceeds the threshold,
	a trap is sent to the management console and the media gateway begins
	a controlled shutdown."
	::= { cmgHardware 3 }

cmgDspTemp OBJECT-TYPE
	SYNTAX      Integer32
	MAX-ACCESS  read-only
	STATUS      current
	DESCRIPTION
	"Reading of the internal temperature sensor at the DSPs,
	expressed in degrees Celsius."
	::= { cmgHardware 4 }

cmgDspTempWarningThresh OBJECT-TYPE
	SYNTAX      Integer32
	MAX-ACCESS  read-only
	STATUS      current
	DESCRIPTION
	"Internal enclosure temperature warning threshold, expressed in degrees
	Celsius.  When the temperature at the DSP sensor exceeds the threshold,
	a trap is sent to the management console.  If both CPU and DSP sensors
	exceed their thresholds, only one trap is sent."
	::= { cmgHardware 5 }

cmgDspTempShutdownThresh OBJECT-TYPE
	SYNTAX      Integer32
	MAX-ACCESS  read-only
	STATUS      current
	DESCRIPTION
	"Internal enclosure temperature shutdown threshold, expressed in degrees
	Celsius.  When the temperature at the DSP sensor exceeds the threshold,
	a trap is sent to the management console and the media gateway begins
	a controlled shutdown."
	::= { cmgHardware 6 }

cmgPowerMgProcessor OBJECT-TYPE
	SYNTAX      Integer32
	MAX-ACCESS  read-only
	STATUS      current
	DESCRIPTION
	"Voltage reading in millivolts at the power supply serving the Media
	Gateway main processor.  Nominal value is +5100 mV.  If the reading
	falls outside the range 4950 to 5250 mV, a trap is sent to the
	management console and the corresponding bit in the fault mask
	is turned on."
	::= { cmgHardware 7 }

cmgPowerMediaModules OBJECT-TYPE
	SYNTAX      Integer32
	MAX-ACCESS  read-only
	STATUS      current
	DESCRIPTION
	"Voltage reading in millivolts at the power supply serving the Media
	Modules.  Nominal value is -48000 mV.  If the reading falls outside
	the range -43000 to -53000 mV, a trap is sent to the management
	console and the corresponding bit in the fault mask is turned on."
	::= { cmgHardware 8 }

cmgPowerVoipComplex OBJECT-TYPE
	SYNTAX      Integer32
	MAX-ACCESS  read-only
	STATUS      current
	DESCRIPTION
	"Voltage reading in millivolts at the power supply serving the VoIP
	complexes.  Nominal value is +3400 mV.  If the reading falls outside
	the range 3200 to 3600 mV, a trap is sent to the management console
	and the corresponding bit in the fault mask is turned on."
	::= { cmgHardware 9 }

cmgPowerDsp OBJECT-TYPE
	SYNTAX      Integer32
	MAX-ACCESS  read-only
	STATUS      current
	DESCRIPTION
	"Voltage reading in millivolts at the power supply serving the DSP
	units, derived from VoIP complex power.  Nominal value is +1580 mV.
	If the reading falls outside the range 1530 to 1620 mV, a trap is
	sent to the management console and the corresponding bit in the
	fault mask is turned on."
	::= { cmgHardware 10 }

cmgPower8260 OBJECT-TYPE
	SYNTAX      Integer32
	MAX-ACCESS  read-only
	STATUS      current
	DESCRIPTION
	"Voltage reading in millivolts at the power supply serving the 8260
	processor, derived from VoIP complex power.  Nominal value is +2500
	mV.  If the reading falls outside the range 2430 to 2580 mV, a
	trap is sent to the management console and the corresponding
	bit in the fault mask is turned on."
	::= { cmgHardware 11 }

cmgHardwareFaultMask OBJECT-TYPE
	SYNTAX      OCTET STRING (SIZE (0..3))
	MAX-ACCESS  read-only
	STATUS      current
	DESCRIPTION
	"Each bit of this value set to '1' indicates a specific fault
	in the module.

	Octets are numbered in the order in which they appear in the PDU.
	Bits are numbered from the most-significant leftmost bit in the
	octet (bit 0) to the least-significant rightmost bit (bit 7).

	Cajun numbering continues across octets, so that octet 1 bit 0 is
	called bit 8 in the Cajun scheme.  That number is also shown below,
	with the octet value for each single bit set.

	Octet 0 high-order 4 bits show fan status.
	Octet 0 low-order 4 bits show temperature status.
	Octet 1 shows power supply status.
	Octet 2 shows other alarms.

    Cajun  Octet Octet
    bit#   /bit# value	Meaning
    -----  ----- -----	-------
    0      0/0   0x80	Multiple fan warning: at least two fans have been operating
			at less than 90% of their nominal speed for 5 minutes or
			more.  This may be an early warning of overheating.

    1      0/1   0x40	PSU fan brief failure warning: the power supply fan has been
			operating at less than 90% of its nominal speed for 10 minutes
			or more, but less than 15 minutes.  This may be an early
			warning of overheating.

    2      0/2   0x20	PSU fan prolonged failure warning: the power supply fan has
			been operating at less than 90% of its nominal speed for 15
			minutes or more.  This may be an early warning of overheating.

    3      0/3       	Unused.

    4      0/4   0x08	Temperature warning: cmgCpuTemp has exceeded its warning
			threshold.

    5      0/5   0x04	Temperature warning: cmgDspTemp has exceeded its warning
			threshold.

    6     0/6	Unused.
    
    7     0/7   Power On Status Test failure -NCE, QUICC test failures on power up

    8      1/0   0x80	The +5.1 v power supply to the MG processor is out of range.
    9      1/1   0x40	The -48 v power supply to the media modules is out of range.
   10      1/2   0x20	The +3.3 v power supply to the VoIP complexes is out of range.
   11      1/3   0x10	The +1.58 v power supply to the DSP units is out of range.
   12      1/4   0x08	The +2.5 v power supply to the 8260 processor is out of range.
   13      1/5   0x04	The -48 v auxiliary power supply to the endpoints is out of
			range.
   14      1/6   0x02	The +12 v power supply to the fans is out of range.
   15      1/7		Unused.

   16      2/0   0x80	Clock synchronization signal is lost.
   17      2/1   0x40	Clock synchronization signal warning. Only one clock
                        syncronization signal source remains.
   18      2/2   0x20   Clock synchronization signal excessive switching.
   19      2/3   0x10   TDM Test Expansion Box 1 Failure
   20      2/4   0x08   TDM Test Expansion Box 2 Failure
   21      2/5   0x04   PoE Power Supply Base Box Failure
   22      2/6   0x02   PoE Power Supply Expansion Box 1 Failure
   23      2/7   0x01   PoE Power Supply Expansion Box 2 Failure
	"
	::= { cmgHardware 12 }

cmgHardwareStatusMask OBJECT-TYPE
	SYNTAX      OCTET STRING (SIZE (0..6))
	MAX-ACCESS  read-only
	STATUS      current
	DESCRIPTION
	"Each bit of this value set to '1' indicates a specific status
	condition in the module.

	Octets are numbered in the order in which they appear in the PDU.
	Bits are numbered from the most-significant leftmost bit in the
	octet (bit 0) to the least-significant rightmost bit (bit 7).

	Cajun numbering continues across octets, so that octet 1 bit 0 is
	called bit 8 in the Cajun scheme.  That number is also shown below,
	with the octet value for each single bit set.

	Octet 0 high-order 4 bits show LED status.
	Octet 0 low-order 4 bits show ICC status.
	Octets 1 - 5 show power-on self test (POST) results.

    Cajun  Octet Octet
    bit#   bit#  value	Meaning
    -----  ----- -----	-------
    0      0/0   0x80	Media gateway red LED is on.
    1      0/1   0x40	The red LED is on in one or more of the media modules.
    2-3    0/2-3	Unused.
    4      0/4   0x08	Integrated Communications Controller hardware watchdog
			alert is on.
    5-7    0/5-7	Unused.

    8      1/0	 0x80	POST HDLC local loopback failed.
    9      1/1	 0x40	POST Ethernet local loopback failed.
    10     1/2	 0x20	POST Ethernet physical local loopback failed.
    11     1/3	 0x10	POST Port I/O read-write test failed.
    12-15  1/4-7	Unused.

    16     2/0   0x80	POST NCE0 reset failed.
    17     2/1   0x40	POST NCE0 internal RAM test failed.
    18     2/2   0x20	POST NCE0 FIFO loop-around failed.
    19     2/3   0x10	POST NCE0 internal channel loopback failed.
    20     2/4   0x08	POST NCE0 internal TDM loopback failed.
    21     2/5   0x04	POST NCE0 external channel loopback failed.
    22-23  2/6-7	Unused.

    24     3/0   0x80	POST NCE1 reset failed.
    25     3/1   0x40	POST NCE1 internal RAM test failed.
    26     3/2   0x20	POST NCE1 FIFO loop-around failed.
    27     3/3   0x10	POST NCE1 internal channel loopback failed.
    28     3/4   0x08	POST NCE1 internal TDM loopback failed.
    29     3/5   0x04	POST NCE1 external channel loopback failed.
    30-31  3/6-7	Unused.

    32     4/0   0x80	POST DSP reset failed.
    33     4/1   0x40	POST POST SPI internal loopback failed.
    34     4/2   0x20	POST Spitfire FIFO test failed.
    35     4/3   0x10	POST ADC test failed.
    36     4/4   0x08	POST CPLD access test failed.
    37-39  4/5-7	Unused.

    40-47  5/0-7	Unused.
	"
	::= { cmgHardware 13 }

cmgHardwareFanLowSpeedLevel OBJECT-TYPE 
	SYNTAX      INTEGER {
		enable(1),
		disable(2)	
		}                                                        
	MAX-ACCESS  read-write
	STATUS      current
	DESCRIPTION "The fan speed level mode. Disable(2) is used for normal operation of two fan speeds.
	Enable(1) is used to activate additional lower speed level.
	Default is disable(2)."
	::= { cmgHardware 14 }



--
--  Modules Subgroup - physical media modules installed in the gateway
--

cmgModules	OBJECT IDENTIFIER		::= { cmgChassis 11 }


cmgModuleTable OBJECT-TYPE
	SYNTAX      SEQUENCE OF CmgModuleEntry
	MAX-ACCESS  not-accessible
	STATUS      current
	DESCRIPTION "Table of physical media modules in this media gateway."
	::= { cmgModules 1 } 

cmgModuleEntry OBJECT-TYPE
	SYNTAX      CmgModuleEntry
	MAX-ACCESS  not-accessible
	STATUS      current
	DESCRIPTION "An entry in the table, representing a single media module."
        INDEX  { cmgModuleSlot }
	::= { cmgModuleTable 1 }

CmgModuleEntry  ::=
	SEQUENCE  {
	cmgModuleSlot		INTEGER,
	cmgModuleType		INTEGER,
	cmgModuleDescription	DisplayString,
	cmgModuleName		DisplayString,
	cmgModuleSerialNumber	DisplayString,
	cmgModuleHWVintage	DisplayString,
	cmgModuleHWSuffix	DisplayString,
	cmgModuleFWVersion	DisplayString,
	cmgModuleNumberOfPorts	INTEGER,
	cmgModuleFaultMask	OCTET STRING,
	cmgModuleStatusMask	OCTET STRING,
	cmgModuleReset		INTEGER,
	cmgModuleNumberOfChannels	INTEGER
	}


cmgModuleSlot OBJECT-TYPE
	SYNTAX      INTEGER (1..9)
	MAX-ACCESS  read-only
	STATUS      current
	DESCRIPTION "Slot number of this module."
	::= { cmgModuleEntry 1 }

cmgModuleType OBJECT-TYPE
	SYNTAX      INTEGER {
		t1e1-voip(1),	-- T1/E1 with integrated CSU/DSU & VoIP DSP
		bri(2),			-- BRI trunk module
		dcp(3),			-- DCP station module
		analog(4),		-- combination analog line and trunk
		t1e1(5),		-- T1/E1 with integrated CSU/DSU
		voip(6),		-- dedicated VoIP media module
		icc(7),			-- internal call controller
    	fxo4fxs4(9),  	-- MM714 4 FXS + 4FXO analog ports module
		bri2(10),  		-- MM722 2 BRI trunk ports module
		ds1wan(11), 	-- MM340 1 DS1 (E1/T1) WAN data port module
		uspwan(12),		-- MM342 1 USP WAN data port module
		dcp24hd(13),	-- HDMM312 24 DCP station ports G350 high-density form-factor module
		poe24(14), 		-- HDMM314 24 power over Ethernet plus 1 GBIC port 
		g350intana(16), -- G350 Integrated analog module
	    dcp24(17),		-- MM717 24 DCP station ports module	        		
		fxs24(18),	    -- MM716 24 FXS analog ports module	 
		g250-int-analog-2L4T(19), -- G250 Integrated analog 2 Lines + 4 Trunks module
		g250-int-analog-2L1T(20), -- G250 Integrated analog 2 Lines + 1 Trunk module
		g250-int-BRI(21), -- G250 Integrated BRI Trunk module 
		g250-int-DS1(24), -- G250 Integrated DS1 Trunk module
		g250-int-12pDCP(23), -- G250 Integrated 12 Port DCP lines module
		poe40(22),      -- HDMM316 40 power over Ethernet plus 1 Giga bit copper  
		poe24cr(25), 	-- HDMM314 24 power over Ethernet plus 1 GBIC port
		poe8(26),       -- MM118 - 8 10/100 power over Ethernet ports module
		g250-int-analog-6L8T(29), -- G250-A14 Integrated analog 6 Lines + 8 Trunks module
		tgm550-int-analog-2L2T(30), -- TGM550 Integrated analog 2 Lines + 2 Trunks module
        tim514(31),		-- TIM514 4 FXS + 4 FXO analog ports module
        tim510(32),		-- TIM510 1 DS1 (E1/T1) module
        tim521(33),		-- TIM521 4 BRI trunk ports module
		avayaAM110ApplicationModule(34),	-- Avaya Communication Manager Branch Edition Application Module for i40 and i120.
		g450Mainboard(40),	-- G450 Mainboard 
		tim508(41),
		tim516(42),
		tim518(43),     
		i120-intana(44), -- i120 Integrated analog module
	    i40-int-analog-2L4T(45), -- avayaCommunicationManagerBranchEditioni40 Integrated analog 2 Lines + 4 Trunks module
		i40-int-analog-2L1T(46), -- avayaCommunicationManagerBranchEditioni40 Integrated analog 2 Lines + 1 Trunk module
		i40-int-BRI(47), -- avayaCommunicationManagerBranchEditioni40 Integrated BRI Trunk module 
		i40-int-DS1(48), -- avayaCommunicationManagerBranchEditioni40 Integrated DS1 Trunk module
		i40-A14-int-analog-6L8T(49), -- avayaCommunicationManagerBranchEditioni40 Integrated analog 6 Lines + 8 Trunks module
		avayaCommunicationManagerBranchEditionG450Mainboard(50), 
		g430Mainboard(51),
		invalid(253),   -- Bad module or a module in a slot that cannot support it.
		unknown(255)	-- type cannot be determined
		}                                                        
	MAX-ACCESS  read-only
	STATUS      current
	DESCRIPTION "Type of this module."
	::= { cmgModuleEntry 2 }

cmgModuleDescription OBJECT-TYPE
	SYNTAX      DisplayString (SIZE (0..32))
        MAX-ACCESS  read-only
        STATUS      current
        DESCRIPTION
	"Description of this media module, e.g. 'Avaya E1/T1 media module
	with integrated CSU/DSU'"
	::= { cmgModuleEntry 3 }

cmgModuleName OBJECT-TYPE
	SYNTAX      DisplayString (SIZE (0..32))
        MAX-ACCESS  read-only
        STATUS      current
        DESCRIPTION "User-assigned name of this media module."
	::= { cmgModuleEntry 4 }

cmgModuleSerialNumber OBJECT-TYPE
	SYNTAX      DisplayString (SIZE (0..16))
        MAX-ACCESS  read-only
        STATUS      current
        DESCRIPTION
	"Serial number of this module.  The first 12 characters are meaningful.
	Form is yyLLmmnnnnnn, where
	yy = last 2 digits of the year of manufacture
	LL = manufacturing facility, e.g. DR for Denver, Colorado
	mm = month of manufacture, 01 - 12
	nnnnnn = a six-digit sequence number
	"
	::= { cmgModuleEntry 5 }

cmgModuleHWVintage OBJECT-TYPE
	SYNTAX      DisplayString (SIZE (0..8))
        MAX-ACCESS  read-only
        STATUS      current
        DESCRIPTION "Hardware vintage of this module."
	::= { cmgModuleEntry 6 }

cmgModuleHWSuffix OBJECT-TYPE
	SYNTAX      DisplayString (SIZE (0..2))
        MAX-ACCESS  read-only
        STATUS      current
        DESCRIPTION "Hardware vintage suffix of this module."
	::= { cmgModuleEntry 7 }

cmgModuleFWVersion OBJECT-TYPE
	SYNTAX      DisplayString (SIZE (0..64))
        MAX-ACCESS  read-only
        STATUS      current
        DESCRIPTION
	"Firmware version of this module. This duplicates information available
	in the Load MIB.  It shows the media module run image version, plus
	the VoIP engine version if applicable."
	::= { cmgModuleEntry 8 }

cmgModuleNumberOfPorts OBJECT-TYPE
	SYNTAX      INTEGER (0..64)
	MAX-ACCESS  read-only
	STATUS      current
	DESCRIPTION "Number of physical connectors on this module."
	::= { cmgModuleEntry 9 }

cmgModuleFaultMask OBJECT-TYPE
	SYNTAX      OCTET STRING (SIZE (0..2))
	MAX-ACCESS  read-only
	STATUS      current
	DESCRIPTION
	"Each bit of this value set to '1' indicates a specific fault
	in the module.

	Octets are numbered in the order in which they appear in the PDU.
	Bits are numbered from the most-significant leftmost bit in the
	octet (bit 0) to the least-significant rightmost bit (bit 7).

	Cajun numbering continues across octets, so that octet 1 bit 0 is
	called bit 8 in the Cajun scheme.  That number is also shown below,
	with the octet value for each single bit set.

    Cajun  Octet Octet
    bit#   bit#  value	Meaning
    -----  ----- -----	-------
    0      0/0   0x80	Media module is in administrative busy-out.
    1      0/1   0x40	One or more ports on this media module is in administrative
			busy-out.
    2      0/2   0x20	Insertion sequence failed.
    3      0/3       	AWOH data module conflict.
    4      0/4   0x08	Media module automatic reset occurred.
    5      0/5   0x04	One or more power-on startup tests failed.
    6      0/6   0x02	Media module parameter exchange failed.
    7      0/7       	Unsupported module enrolment.
    8-15   1/0-7	Unused.
	"
	::= { cmgModuleEntry 10 }

cmgModuleStatusMask OBJECT-TYPE
	SYNTAX      OCTET STRING (SIZE (0..2))
	MAX-ACCESS  read-only
	STATUS      current
	DESCRIPTION
	"Each bit of this value set to '1' indicates a specific status
	condition in the module.

	Octets are numbered in the order in which they appear in the PDU.
	Bits are numbered from the most-significant leftmost bit in the
	octet (bit 0) to the least-significant rightmost bit (bit 7).

	Cajun numbering continues across octets, so that octet 1 bit 0 is
	called bit 8 in the Cajun scheme.  That number is also shown below,
	with the octet value for each single bit set.

    Cajun  Octet Octet
    bit#   bit#  value	Meaning
    -----  ----- -----	-------
    0      0/0   0x80	Red LED is on.
    1      0/1   0x40	Module controlled by ACP on communications controller.
    2-7    0/2-7	Unused.
    8-15   1/0-7	Unused.
	"
	::= { cmgModuleEntry 11 }

cmgModuleReset OBJECT-TYPE
	SYNTAX      INTEGER { on(1), off(2) }
        MAX-ACCESS  read-write
        STATUS      current
        DESCRIPTION
	"Setting the value of this attribute to ON is interpreted as a reset
	command for the module.  It initiates a complete reinitialization of
	the module and of all the devices incorporated inside the module."
	::= { cmgModuleEntry 12 }

cmgModuleNumberOfChannels OBJECT-TYPE
	SYNTAX      INTEGER (0..64)
	MAX-ACCESS  read-only
	STATUS      current
	DESCRIPTION
	"Number of communications channels or spans on this module.  Earlier
	Avaya products have referred to T1E1 channels as ports.  This media
	gateway calls them channels."
	::= { cmgModuleEntry 13 }


--
--	Analog table
--
cmgAnalogPorts  OBJECT IDENTIFIER  ::= { cmgChassis 12 }

cmgAnalogPortTable OBJECT-TYPE
       SYNTAX      SEQUENCE OF CmgAnalogPortEntry
    MAX-ACCESS  not-accessible
    STATUS      current
    DESCRIPTION
       "Table of analog ports in this media gateway."
    ::= { cmgAnalogPorts 1 }

cmgAnalogPortEntry OBJECT-TYPE
    SYNTAX      CmgAnalogPortEntry
    MAX-ACCESS  not-accessible
    STATUS      current
    DESCRIPTION
       "An entry in the table, representing a single analog port."
       INDEX { cmgAnalogSlot, cmgAnalogPort }
    ::= { cmgAnalogPortTable 1 }

CmgAnalogPortEntry ::= SEQUENCE {
    cmgAnalogSlot            INTEGER,
    cmgAnalogPort            INTEGER,
    cmgAnalogEchoCancellerControl  INTEGER,
    cmgAnalogEchoCancellerConfig1  INTEGER,
    cmgAnalogEchoCancellerConfig2  INTEGER,
    cmgAnalogBalance               INTEGER,
    cmgAnalogReceiveGain           INTEGER,
    cmgAnalogTransmitGain          INTEGER
    }

cmgAnalogSlot OBJECT-TYPE
    SYNTAX      INTEGER (1..9)
    MAX-ACCESS  read-only
    STATUS      current
    DESCRIPTION "Slot number of this analog port."
    ::= { cmgAnalogPortEntry 1 }

cmgAnalogPort OBJECT-TYPE
    SYNTAX      INTEGER (1..24)
    MAX-ACCESS  read-only
    STATUS      current
    DESCRIPTION "Port number of this analog port."
    ::= { cmgAnalogPortEntry 2 }

cmgAnalogEchoCancellerControl  OBJECT-TYPE
    SYNTAX      INTEGER { auto(0), on(1), off(2), 
                            fixedOn(3), notSupported(4) }
    MAX-ACCESS  read-write
    STATUS      current
    DESCRIPTION
       "The echo canceller control setting for this analog port.
          auto means that the system will enable or disable the echo
          canceller as appropriate for each call.
          fixedOn indicates that the analog firmware always enables
          the echo canceller (this value cannot be changed).
          Similarly, notSupported indicates that the analog HW
          does not contain echo cancellers (this value cannot be changed)."
    ::= { cmgAnalogPortEntry 3 }

cmgAnalogEchoCancellerConfig1   OBJECT-TYPE
    SYNTAX      INTEGER (0..255)
    MAX-ACCESS  read-write
    STATUS      current
    DESCRIPTION
       "Echo canceller configuration setting for this analog port (byte 1 of 2).
        This value is not writeable if cmgAnalogEchoCancellerControl
        is fixedOn(3) or notSupported(4)."
    ::= { cmgAnalogPortEntry 4 }

cmgAnalogEchoCancellerConfig2   OBJECT-TYPE
    SYNTAX      INTEGER (0..255)
    MAX-ACCESS  read-write
    STATUS      current
    DESCRIPTION
       "Echo canceller configuration setting for this analog port (byte 2 of 2).
        This value is not writeable if cmgAnalogEchoCancellerControl
        is fixedOn(3) or notSupported(4)."
    ::= { cmgAnalogPortEntry 5 }

cmgAnalogBalance OBJECT-TYPE
    SYNTAX      INTEGER (0..15)
    MAX-ACCESS  read-write 
    STATUS      current
    DESCRIPTION "Balance index."
    ::= { cmgAnalogPortEntry 6 }

cmgAnalogReceiveGain OBJECT-TYPE
    SYNTAX      INTEGER (-600..300)
    MAX-ACCESS  read-write 
    STATUS      current
    DESCRIPTION "The receive gain multiplied by 100, for instance -123 indicates -1.23dB."
    ::= { cmgAnalogPortEntry 7 }

cmgAnalogTransmitGain OBJECT-TYPE
    SYNTAX      INTEGER (-600..300)
    MAX-ACCESS  read-write 
    STATUS      current
    DESCRIPTION "The transmit gain multiplied by 100, for instance +287 indicates 2.87dB."
    ::= { cmgAnalogPortEntry 8 }

--
--	Expansion Units table
--
cmgExpansionUnits  OBJECT IDENTIFIER  ::= { cmgChassis 13 }

cmgExpansionUnitsTable OBJECT-TYPE
    SYNTAX      SEQUENCE OF CmgExpansions
    MAX-ACCESS  not-accessible
    STATUS      current
    DESCRIPTION
       "Table of Expansion Units connected to this media gateway."
    ::= { cmgExpansionUnits 1 }

cmgExpansions OBJECT-TYPE
    SYNTAX      CmgExpansions
    MAX-ACCESS  not-accessible
    STATUS      current
    DESCRIPTION
       "An entry in the table, representing a single Expansion Unit."
       INDEX { cmgExpansionSlot }
    ::= { cmgExpansionUnitsTable 1 }

CmgExpansions ::= SEQUENCE {
    cmgExpansionSlot             INTEGER,
    cmgExpansionModelNumber      DisplayString,
    cmgExpansionDescription      DisplayString,
    cmgExpansionSerialNumber     DisplayString,
    cmgExpansionHWVintage        DisplayString,
    cmgExpansionHWSuffix         DisplayString,
    cmgExpansionDemandTest       INTEGER,
    cmgExpansionDemandTestResult INTEGER
    }

cmgExpansionSlot OBJECT-TYPE
    SYNTAX      INTEGER (1..2)
    MAX-ACCESS  read-only
    STATUS      current
    DESCRIPTION "Expansion Unit Slot."
    ::= { cmgExpansions 1 }

cmgExpansionModelNumber OBJECT-TYPE
	SYNTAX      DisplayString (SIZE (0..16))
        MAX-ACCESS  read-only
        STATUS      current
        DESCRIPTION "Expansion Unit model."
    ::= { cmgExpansions 2 }

cmgExpansionDescription OBJECT-TYPE
	SYNTAX      DisplayString (SIZE (0..32))
        MAX-ACCESS  read-only
        STATUS      current
        DESCRIPTION "Expansion Unit description."
    ::= { cmgExpansions 3 }

cmgExpansionSerialNumber OBJECT-TYPE
	SYNTAX      DisplayString (SIZE (0..16))
        MAX-ACCESS  read-only
        STATUS      current
        DESCRIPTION "Expansion Unit serial number."
    ::= { cmgExpansions 4 }

cmgExpansionHWVintage OBJECT-TYPE
	SYNTAX      DisplayString (SIZE (0..8))
        MAX-ACCESS  read-only
        STATUS      current
        DESCRIPTION "Expansion Unit HW vintage."
    ::= { cmgExpansions 5 }

cmgExpansionHWSuffix OBJECT-TYPE
	SYNTAX      DisplayString (SIZE (0..2))
        MAX-ACCESS  read-only
        STATUS      current
        DESCRIPTION "Expansion Unit HW suffix."
    ::= { cmgExpansions 6 }

cmgExpansionDemandTest OBJECT-TYPE
    SYNTAX      INTEGER { on(1), off(2) }
    MAX-ACCESS  read-write
    STATUS      current
    DESCRIPTION "When set to on(1), activates on demand test for the Expansion Unit."
    ::= { cmgExpansions 7 }
    
cmgExpansionDemandTestResult OBJECT-TYPE
    SYNTAX      INTEGER { fail(1), pass(255) }
    MAX-ACCESS  read-only
    STATUS      current
    DESCRIPTION 
       "Result of the on demand test for the Expansion Unit. 
        Failure(1) may be the result of a disconnected or bad cable."
    ::= { cmgExpansions 8 }

--
--  Timeslot usage monitoring
--

cmgTimeslotMonitoring OBJECT-TYPE
	SYNTAX      INTEGER { on(1), off(2) }
        MAX-ACCESS  read-write
        STATUS      current
        DESCRIPTION
	"Timeslot Monitoring flag. When on, timeslot usage is monitored and
	traps are sent when thresholds are crossed. Those traps are
	cmgTimeslotOccupancyFault, cmgTimeslotOccupancyClear, 
	cmgTimeslotAvailabilityFault and cmgTimeslotAvailabilityClear."
	::= { cmgChassis 14 }

cmgTimeslotUpperThreshold OBJECT-TYPE
    SYNTAX      INTEGER (1..100)
        MAX-ACCESS  read-write
        STATUS      current
        DESCRIPTION
	"Timeslot Upper threshold. The gateway will send trap cmgTimeslotOccupancyFault
	as soon as the timeslot usage goes above this threshold.
	This threshold must be set greater than the lower threshold; for example,
	cmgTimeslotLowerThreshold=85, cmgTimeslotUpperThreshold=90. Default is 90.
	cmgTimeslotMonitoring must be set to on(1) for traps to be sent."
	::= { cmgChassis 15 }

cmgTimeslotLowerThreshold OBJECT-TYPE
    SYNTAX      INTEGER (0..99)
        MAX-ACCESS  read-write
        STATUS      current
        DESCRIPTION
	"Timeslot Lower threshold. After the gateway has sent a cmgTimeslotOccupancyFault
	trap, it will send a cmgTimeslotOccupancyClear as soon as the timeslot usage goes
	below this threshold. Also after the gateway has sent a cmgTimeslotAvailabilityFault
	trap, it will send cmgTimeslotAvailabilityClear as soon as the timeslot usage goes
	below this threshold.
	This lower threshold must be less than the upper threshold; for example
	cmgTimeslotLowerThreshold=85, cmgTimeslotUpperThreshold=90. Default is 85.
	cmgTimeslotMonitoring must be set to on(1) for traps to be sent."
	::= { cmgChassis 16 }

--
--	T1/E1 DSU tables
--

cmgDsu				OBJECT IDENTIFIER ::= { cmgModules 2 }

--
--	T1/E1 DSU Configuration table
--
--	The index includes port number, even though in R1 there is only one
--	port and its index is always one.  This is to accomodate possible
--	future expansion to more than one port on a T1/E1 module.
--

cmgDsuConfigTable OBJECT-TYPE
	SYNTAX      SEQUENCE OF CmgDsuConfigEntry
	MAX-ACCESS  not-accessible
	STATUS      obsolete
	DESCRIPTION "Configuration of E1/T1 DSUs in this media gateway."
	::= { cmgDsu 1 } 

cmgDsuConfigEntry OBJECT-TYPE
	SYNTAX      CmgDsuConfigEntry
	MAX-ACCESS  not-accessible
	STATUS      obsolete
	DESCRIPTION
	"An entry in the table, representing the configuration of one DSU
	on a T1/E1 media module."
        INDEX  { cmgDsuSlot, cmgDsuPort }
	::= { cmgDsuConfigTable 1 }

CmgDsuConfigEntry  ::=
	SEQUENCE  {
	cmgDsuSlot			INTEGER,
	cmgDsuPort			INTEGER,
	cmgDsuPortEnable		INTEGER,
	cmgDsuDataFormat		INTEGER,
	cmgDsuFlowControl		INTEGER,
	cmgDsuYellowAlarmAction		INTEGER,
	cmgDsuReceiveClock		INTEGER,
	cmgDsuInvertTxC			INTEGER,
	cmgDsuInvertRxC			INTEGER,
	cmgDsuInvertTxD			INTEGER,
	cmgDsuInvertRxD			INTEGER,
	cmgDsuPortInitiatedLoopback	INTEGER,
	cmgDsuNetworkInitiatedLoopback	INTEGER,
	cmgDsuChannelAssignments	OCTET STRING,
	cmgDsuDataRate			INTEGER
	}


cmgDsuSlot OBJECT-TYPE
	SYNTAX      INTEGER (1..4)
	MAX-ACCESS  read-only
	STATUS      obsolete
	DESCRIPTION "Slot number of this DSU."
	::= { cmgDsuConfigEntry 1 }

cmgDsuPort OBJECT-TYPE
	SYNTAX      INTEGER (1..1)
	MAX-ACCESS  read-only
	STATUS      obsolete
	DESCRIPTION "Port number of this DSU."
	::= { cmgDsuConfigEntry 2 }

cmgDsuPortEnable OBJECT-TYPE
	SYNTAX      INTEGER {
		enabled(1),
		disabled(2)
		}
	MAX-ACCESS  read-write
	STATUS      obsolete
	DESCRIPTION
	"This object allows a user to take the E1/T1 port out of service for
	administration.  During administration, it may be in an inconsistent
	state.  When administration is complete, the port may be enabled
	again.  If the port is not yet correctly administered, the change to
	the enabled state will fail with an INCONSISTENT_VALUE error."
	::= { cmgDsuConfigEntry 3 }

cmgDsuDataFormat OBJECT-TYPE
	SYNTAX      INTEGER { rate56Kbps(1), rate64KbpsClear(2) }
	MAX-ACCESS  read-write
	STATUS      obsolete
	DESCRIPTION "Data format (channel rate) of this DSU."
	::= { cmgDsuConfigEntry 4 }

cmgDsuFlowControl OBJECT-TYPE
	SYNTAX      INTEGER {
		dtr-rts(1),
		dtr(2),
		rts(3),
		disable(4)
		}
	MAX-ACCESS  read-write
	STATUS      obsolete
	DESCRIPTION
	"Specifies the conditions under which this DSU will send all ones to
	indicate data port not ready.

	dtr-rts(1) Monitor both DTR and RTS as described below.  If either
		is interrupted, send all ones.

	dtr(2)	Monitor the DTE Ready interchange circuit CD (CCITT 108/1/2).
		If DTR is interrupted, send all ones.

	rts(3)	Monitor the Request-to-Send interchange circuit CD (CCITT 105).
		If RTS is interrupted, send all ones.

	disable(4) Do not monitor interchange circuits from the DTE."
	::= { cmgDsuConfigEntry 5 }

cmgDsuYellowAlarmAction OBJECT-TYPE
	SYNTAX      INTEGER {
		noAction(1),
		halt(2)
		}
	MAX-ACCESS  read-write
	STATUS      obsolete
	DESCRIPTION
	"Specifies the action to take when a yellow alarm is received on
	the network interface.

	noAction(1) Ignore yellow alarms.

	halt(2)	Stop transmission and disable the data port.  Send all ones
		on the Received Data interchange circuit BB (CCITT 104) and
		interrupt the Clear-to-Send interchange circuit (CCITT 106)."
	::= { cmgDsuConfigEntry 6 }

cmgDsuReceiveClock OBJECT-TYPE
	SYNTAX      INTEGER {
		internal(1),
		external(2)
		}
	MAX-ACCESS  read-write
	STATUS      obsolete
	DESCRIPTION
	"Specifies whether data received from the data port is clocked using
	the DSU internal clock or by an external clock provided by the DTE
	connected to the port.  When an external clock is used, it must be
	synchronized to the same clock source as the DSU.

	The DSU Receive Clock is equivalent to the Data Port Transmit Clock.

	internal(1) The clock is provided internally by the DSU/CSU on the
		TXC interchange circuit DB (CCITT 114).

	external(2) The clock is provided externally by the DTE on the XTXC
		interchange circuit DA (CCITT 113).
	"
	::= { cmgDsuConfigEntry 7 }

cmgDsuInvertTxC OBJECT-TYPE
	SYNTAX      INTEGER {
		enabled(1),
		disabled(2)
		}
	MAX-ACCESS  read-write
	STATUS      obsolete
	DESCRIPTION
	"Specifies whether the clock supplied by the DSU/CSU on the TXC
	interchange circuit DB (CCITT 114) is phase inverted with respect
	to the Transmitted Data interchange ciucuit BA (CCITT 103).  This
	option is useful when long cable lengths between the DSU/CSU and
	the DTE are causing data errors."
	::= { cmgDsuConfigEntry 8 }

cmgDsuInvertRxC OBJECT-TYPE
	SYNTAX      INTEGER {
		enabled(1),
		disabled(2)
		}
	MAX-ACCESS  read-write
	STATUS      obsolete
	DESCRIPTION
	"Specifies whether the receive clock supplied by the DSU/CSU or
	DTE is phase inverted."
	::= { cmgDsuConfigEntry 9 }

cmgDsuInvertTxD OBJECT-TYPE
	SYNTAX      INTEGER {
		enabled(1),
		disabled(2)
		}
	MAX-ACCESS  read-write
	STATUS      obsolete
	DESCRIPTION
	"Specifies whether the transmitted data stream is logically inverted
	before being transmitted.  This option is useful for applications
	where HDLC data is being transported.  Inverting the data ensures
	that the density requirements for the network interface are met."
	::= { cmgDsuConfigEntry 10 }

cmgDsuInvertRxD OBJECT-TYPE
	SYNTAX      INTEGER {
		enabled(1),
		disabled(2)
		}
	MAX-ACCESS  read-write
	STATUS      obsolete
	DESCRIPTION
	"Specifies whether the received data stream is logically inverted.
	This option is useful for applications where HDLC data is being
	transported.  Inverting the data ensures that the density
	requirements for the network interface are met."
	::= { cmgDsuConfigEntry 11 }

cmgDsuPortInitiatedLoopback OBJECT-TYPE
	SYNTAX      INTEGER {
		allow(1),
		disallow(2)
		}
	MAX-ACCESS  read-write
	STATUS      obsolete
	DESCRIPTION
	"Specifies whether the DSU should accept loopback requests from
	the DTE port.  The local DTE can send an LL or RL signal to the
	T1/E1 media module in the EIA-530A interface.  The LL signal causes
	the module to activate a local DTE loopback.  An RL signal causes
	the module to send an in-band code to signal the far end to go
	into loopback."
	::= { cmgDsuConfigEntry 12 }

cmgDsuNetworkInitiatedLoopback OBJECT-TYPE
	SYNTAX      INTEGER {
		allow(1),
		disallow(2)
		}
	MAX-ACCESS  read-write
	STATUS      obsolete
	DESCRIPTION
	"Specifies whether the DSU should accept in-band loopback requests
	from the far end, that is, a DSU across the network."
	::= { cmgDsuConfigEntry 13 }

cmgDsuChannelAssignments OBJECT-TYPE
	SYNTAX      OCTET STRING (SIZE (4))
	MAX-ACCESS  read-write
	STATUS      obsolete
	DESCRIPTION
	"Specifies which channels are assigned to Voice and which to the DSU.
	Each bit represents one channel.  If the bit is set to 1, the channel
	is assigned to the DSU; otherwise it is assigned to Voice.  The
	channel number of a bit is determined by the formula (8*n + b + 1),
	where n is the octet number and b is the bit number.  So the 3rd bit
	in octet 2 represents channel (8*2 + 3 + 1) = 20."
	::= { cmgDsuConfigEntry 14 }

cmgDsuDataRate OBJECT-TYPE
	SYNTAX      INTEGER (0..2048)
	MAX-ACCESS  read-only
	STATUS      obsolete
	DESCRIPTION
	"Data format (channel rate) of this DSU times the number of channels
	of type ds0-dsu-channel(5).  See cmgChType in cmgChannelTable."
	::= { cmgDsuConfigEntry 15 }



--
--	T1/E1 DSU Port Status table
--
--	Much of this table could be represented in masks.  We have
--	decided to break status out into separate objects because it's
--	likely to be presented that way in the device manager, rather
--	than in the drop-down lists that show faults.
--
--	The index includes port number, even though in R1 there is only one
--	port and its index is always one.  This is to accomodate possible
--	future expansion to more than one port on a T1/E1 module.
--

cmgDsuPortStatusTable OBJECT-TYPE
	SYNTAX      SEQUENCE OF CmgDsuPortStatusEntry
	MAX-ACCESS  not-accessible
	STATUS      obsolete
	DESCRIPTION "Status of E1/T1 DSUs in this media gateway."
	::= { cmgDsu 2 } 

cmgDsuPortStatusEntry OBJECT-TYPE
	SYNTAX      CmgDsuPortStatusEntry
	MAX-ACCESS  not-accessible
	STATUS      obsolete
	DESCRIPTION
	"An entry in the table, representing the configuration of one DSU
	on a T1/E1 media module."
        INDEX  { cmgDsuSlot, cmgDsuPort }
	::= { cmgDsuPortStatusTable 1 }

CmgDsuPortStatusEntry  ::=
	SEQUENCE  {
	cmgDsuRTS		INTEGER,
	cmgDsuDTR		INTEGER,
	cmgDsuLL		INTEGER,
	cmgDsuRL		INTEGER,
	cmgDsuRLSD		INTEGER,
	cmgDsuCTS		INTEGER,
	cmgDsuDSR		INTEGER,
	cmgDsuRing		INTEGER,
	cmgDsuTestMode		INTEGER,
	cmgDsuTxD		INTEGER,
	cmgDsuRxD		INTEGER,
	cmgDsuFaultMask		OCTET STRING,
	cmgDsuStatusMask	OCTET STRING
	}


--
--  DTE output signals
--
cmgDsuRTS OBJECT-TYPE
	SYNTAX      INTEGER {
		on(1),
		off(2)
		}
	MAX-ACCESS  read-only
	STATUS      obsolete
	DESCRIPTION "State of request-to-send signal from the DTE to the DSU."
	::= { cmgDsuPortStatusEntry 1 }

cmgDsuDTR OBJECT-TYPE
	SYNTAX      INTEGER {
		on(1),
		off(2)
		}
	MAX-ACCESS  read-only
	STATUS      obsolete
	DESCRIPTION
	"State of data-terminal-ready signal from the DTE to the DSU."
	::= { cmgDsuPortStatusEntry 2 }

cmgDsuLL OBJECT-TYPE
	SYNTAX      INTEGER {
		on(1),
		off(2)
		}
	MAX-ACCESS  read-only
	STATUS      obsolete
	DESCRIPTION
	"Is there a DTE local loopback active between the DTE and the DSU?"
	::= { cmgDsuPortStatusEntry 3 }

cmgDsuRL OBJECT-TYPE
	SYNTAX      INTEGER {
		on(1),
		off(2)
		}
	MAX-ACCESS  read-only
	STATUS      obsolete
	DESCRIPTION
	"Is there a remote loopback active in the FPGA?"
	::= { cmgDsuPortStatusEntry 4 }


--
--  DTE input signals
--
cmgDsuRLSD OBJECT-TYPE
	SYNTAX      INTEGER {
		on(1),
		off(2)
		}
	MAX-ACCESS  read-only
	STATUS      obsolete
	DESCRIPTION
	"State of the Receive Line Signal Detect from the DSU to the DTE."
	::= { cmgDsuPortStatusEntry 5 }

cmgDsuCTS OBJECT-TYPE
	SYNTAX      INTEGER {
		on(1),
		off(2)
		}
	MAX-ACCESS  read-only
	STATUS      obsolete
	DESCRIPTION "State of clear-to-send signal from the DSU to the DTE."
	::= { cmgDsuPortStatusEntry 6 }

cmgDsuDSR OBJECT-TYPE
	SYNTAX      INTEGER {
		on(1),
		off(2)
		}
	MAX-ACCESS  read-only
	STATUS      obsolete
	DESCRIPTION "State of data-set-ready signal from the DCE to the DTE."
	::= { cmgDsuPortStatusEntry 7 }

cmgDsuRing OBJECT-TYPE
	SYNTAX      INTEGER {
		on(1),
		off(2)
		}
	MAX-ACCESS  read-only
	STATUS      obsolete
	DESCRIPTION "State of the DCE ring indicator signal to the DTE."
	::= { cmgDsuPortStatusEntry 8 }

cmgDsuTestMode OBJECT-TYPE
	SYNTAX      INTEGER {
		on(1),
		off(2)
		}
	MAX-ACCESS  read-only
	STATUS      obsolete
	DESCRIPTION "Indicates whether tests are currently in progress."
	::= { cmgDsuPortStatusEntry 9 }

cmgDsuTxD OBJECT-TYPE
	SYNTAX      INTEGER {
		mark(1),
		space(2),
		cycling(3)
		}
	MAX-ACCESS  read-only
	STATUS      obsolete
	DESCRIPTION
	"State of data transmission from the synchronous DTE to the
	data port on the DSU."
	::= { cmgDsuPortStatusEntry 10 }

cmgDsuRxD OBJECT-TYPE
	SYNTAX      INTEGER {
		mark(1),
		space(2),
		cycling(3)
		}
	MAX-ACCESS  read-only
	STATUS      obsolete
	DESCRIPTION
	"State of data reception at the synchronous DTE from the
	data port on the DSU/CSU."
	::= { cmgDsuPortStatusEntry 11 }

cmgDsuFaultMask OBJECT-TYPE
	SYNTAX      OCTET STRING (SIZE (0..2))
	MAX-ACCESS  read-only
	STATUS      obsolete
	DESCRIPTION
	"Each bit of this value set to '1' indicates a specific fault
	in this DSU.

	Octets are numbered in the order in which they appear in the PDU.
	Bits are numbered from the most-significant leftmost bit in the
	octet (bit 0) to the least-significant rightmost bit (bit 7).

	Cajun numbering continues across octets, so that octet 1 bit 0 is
	called bit 8 in the Cajun scheme.  That number is also shown below,
	with the octet value for each single bit set.

    Cajun  Octet Octet
    bit#   bit#  value	Meaning
    -----  ----- -----	-------
    0      0/0   0x80	DSU FPGA configuration failure.
    1      0/1   0x40	DSU automatic reset.
    2-3    0/2-3	Unused.
    4      0/4   0x08	DSU DTE DTR off - DTE is disconnected or not functioning.
    5      0/5   0x04	DSU DTE RTS off - DTE is not sending data.
    6      0/6   0x02	DSU TxD failure - data received from DTE is all zeroes or
			all ones.
    7      0/7   0x01	DSU RxD failure - data received from far end is all zeroes or
			all ones.
    8-15   1/0-7	Unused.
	"
	::= { cmgDsuPortStatusEntry 12 }

cmgDsuStatusMask OBJECT-TYPE
	SYNTAX      OCTET STRING (SIZE (0..4))
	MAX-ACCESS  read-only
	STATUS      obsolete
	DESCRIPTION
	"Each bit of this value set to '1' indicates a specific status
	condition in this DSU, or a fault or status condition in its
	associated CSU.

	Octets are numbered in the order in which they appear in the PDU.
	Bits are numbered from the most-significant leftmost bit in the
	octet (bit 0) to the least-significant rightmost bit (bit 7).

	Cajun numbering continues across octets, so that octet 1 bit 0 is
	called bit 8 in the Cajun scheme.  That number is also shown below,
	with the octet value for each single bit set.

	If the CSU is reporting a Blue Alarm (AIS), multiple other alarms
	may be hidden by the Blue Alarm.

--  The four octets of the T1E1 status mask are taken from three different
--  maintenance APIs and assembled by the SNMP agent.

	Octets 0-1 show CSU fault status.
--  From t1e1csu_status.mask, built by the macro T1E1CSU_STATUS_MKMASK.
--  This is defined in CAPIStructures.h:851 and used in T1E1Csu.C:194.

	Octet 2 shows CSU loopbacks active.
--  From t1e1csu_lpbkstatus.mask, built by the macro T1E1CSU_LPBKSTATUS_MKMASK.
--  This is defined in CAPIStructures.h:803 and used in T1E1Csu.C:173.

	Octet 3 shows DSU loopbacks active.
--  From t1e1dsu_tstmgmt.mask, built by the macro T1E1DSU_TSTMGMT_MKMASK
--  This is defined in CAPIStructures.h:1115 and used in T1E1Dsu.C:1574.
--  Note this just copies t1e1dsu_tstmgmt.status_lpbk into the mask field.
--  Don't confuse t1e1dsu_tstmgmt.lpbk and t1e1dsu_tstmgmt.status_lpbk.  The
--  first is what a CLI user requested; the second is what the board reports.
--
--  The bit assignments are chosen to facilitate retrieval from the board.

    Cajun  Octet Octet
    bit#   bit#  value	Meaning
    -----  ----- -----	-------
    0-5    0/0-5	Unused.
    6      0/6   0x02	CSU CRC multiframe lost (LCM) - E1 only
    7      0/7   0x01	CSU remote multiframe alignment lost (RMA) - E1 only

    8      1/0   0x80	CSU local multiframe alignment lost (LMA) - E1 only
    9      1/1   0x40	CSU polar density violations (PDV) - in the T1 configuration
			using AMI line coding, this is equivalent to bipolar
			violations (BPV).
    10     1/2   0x20	CSU alarm indication signal (AIS, Blue Alarm).
    11     1/3   0x10	CSU remote alarm indication signal (RAI, Yellow Alarm).
    12     1/4   0x08	CSU loss of frame (LOF, Red Alarm) - unable to synchronize
    13     1/5   0x04	CSU excessive error rate (EER) - applies to ESF framing only.
			on DS1 signal.
    14     1/6   0x02	CSU out of frame (OOF) - 2 of 4 frame synchronization bits
			in error.
    15     1/7   0x01	CSU loss of signal (LOS) - 175 consecutive zeroes received.

    16-20  2/0-4       	Unused.
    21     2/5   0x04	CSU Digital diagnostic loopback active (towards DTE).  This is
			the equivalent of either equipment (DTE) or repeater loopback
			in the Paradyne 3160.
    22     2/6   0x02	CSU Line loopback active (towards network).
    23     2/7   0x01	CSU Payload loopback active (towards network).

    24-26  3/0-2	Unused.
    27     3/3   0x10	DSU Far-end Data Channel loopback active.
    28     3/4   0x08	DSU Data Terminal loopback active.
    29     3/5   0x04	DSU Remote loopback active.
    30     3/6   0x02	DSU Near-end Data Channel loopback active.
    31     3/7   0x01	DSU Local DTE loopback active.
	"
	::= { cmgDsuPortStatusEntry 13 }



--
--	T1/E1 DSU Test table
--
--	The index includes port number, even though in R1 there is only one
--	port and its index is always one.  This is to accomodate possible
--	future expansion to more than one port on a T1/E1 module.
--

cmgDsuTestTable OBJECT-TYPE
	SYNTAX      SEQUENCE OF CmgDsuTestEntry
	MAX-ACCESS  not-accessible
	STATUS      obsolete
	DESCRIPTION "Loopback tests in effect on DSUs in this media gateway."
	::= { cmgDsu 3 } 

cmgDsuTestEntry OBJECT-TYPE
	SYNTAX      CmgDsuTestEntry
	MAX-ACCESS  not-accessible
	STATUS      obsolete
	DESCRIPTION
	"An entry in the table, representing the configuration of one DSU
	on a T1/E1 media module."
        INDEX  { cmgDsuSlot, cmgDsuPort }
	::= { cmgDsuTestTable 1 }

CmgDsuTestEntry  ::=
	SEQUENCE  {
	cmgDsuLoopbackPattern			INTEGER,
	cmgDsuLocalDteLoopback			INTEGER,
	cmgDsuNearEndDataChannelLoopback	INTEGER,
	cmgDsuFarEndDataChannelLoopback		INTEGER,
	cmgDsuRemoteLoopback			INTEGER,
	cmgDsuDataTerminalLoopback		INTEGER,
	cmgDsuReset				INTEGER
	}

cmgDsuLoopbackPattern OBJECT-TYPE
	SYNTAX      INTEGER {
		allZeroes(1),
		allOnes(2),
		oneZeroOne(3),
		oneIn5(4),
		oneIn8(5),
		threeIn24(6),
		qrs(7),
		qrs511(8),
		qrs2047(9),
		none(255)
		}
	MAX-ACCESS  read-only
	STATUS      obsolete
	DESCRIPTION
	"Specifies the pattern to be sent during a loopback test.
	allZeroes(1) is most often used to verify B8ZS line encoding.
	allOnes(2) is most often used to measure signal power.
	oneZeroOne(3) alternates ones and zeroes.  It is most often used
		to test bridge taps.
	oneIn5(4) is the pattern '00001', to send a remote loopback request.
	oneIn8(5) is the pattern '00000001', used to test repeater timing
		recovery.
	threeIn24(6) is 21 zeroes followed by 3 ones, used to test the ones
		density tolerance in AMI coded lines.
	qrs(7) is a quasi-random signal approximating live data.  It is
		also available in repeating patterns of 511 or 2047 bits.
	none means no pattern; used for response.
	"
	::= { cmgDsuTestEntry 1 }

cmgDsuLocalDteLoopback OBJECT-TYPE
	SYNTAX      INTEGER {
		active(1),
		inactive(2)
		}
	MAX-ACCESS  read-only
	STATUS      obsolete
	DESCRIPTION
	"Indicates whether a Local DTE loopback is active, in which
	a signal received from the DTE is looped back after passing
	through the transceivers, but before passing through the FIFOs.
	This loopback can be activated by this DSU or by the local DTE."
	::= { cmgDsuTestEntry 2 }

cmgDsuNearEndDataChannelLoopback OBJECT-TYPE
	SYNTAX      INTEGER {
		active(1),
		inactive(2)
		}
	MAX-ACCESS  read-only
	STATUS      obsolete
	DESCRIPTION
	"Indicates whether a Near-end Data Channel loopback is active,
	in which a signal received from the CSU is looped back after
	passing through the FIFOs but before entering the transceivers.
	This loopback was activated by the near end, that is, this DSU."
	::= { cmgDsuTestEntry 3 }

cmgDsuFarEndDataChannelLoopback OBJECT-TYPE
	SYNTAX      INTEGER {
		active(1),
		inactive(2)
		}
	MAX-ACCESS  read-only
	STATUS      obsolete
	DESCRIPTION
	"Indicates whether a Far-end Data Channel loopback is active.
	This is functionally equivalent to the Near-end Data Channel
	loopback, except that this loopback was activated by the far
	end, that is, a DSU across the network."
	::= { cmgDsuTestEntry 4 }

cmgDsuRemoteLoopback OBJECT-TYPE
	SYNTAX      INTEGER {
		active(1),
		inactive(2)
		}
	MAX-ACCESS  read-only
	STATUS      obsolete
	DESCRIPTION
	"Indicates whether a Remote loopback is active, in which a
	signal received from the CSU is looped back before entering
	the FIFOs.  This loopback may have been activated by either
	the near end (this DSU) or the far end (a DSU across the
	network)."
	::= { cmgDsuTestEntry 5 }

cmgDsuDataTerminalLoopback OBJECT-TYPE
	SYNTAX      INTEGER {
		active(1),
		inactive(2)
		}
	MAX-ACCESS  read-only
	STATUS      obsolete
	DESCRIPTION
	"Indicates whether a Data Terminal loopback is active, in which
	a signal received from the DTE is looped back after passing
	through the FIFOs.  This loopback can only be activated by the
	near end, that is, this DSU."
	::= { cmgDsuTestEntry 6 }


cmgDsuReset OBJECT-TYPE
	SYNTAX      INTEGER {
		on(1),
		off(2)
		}
	MAX-ACCESS  read-write
	STATUS      obsolete
	DESCRIPTION "Set to on(1) to request reinitialization of the DSU."
	::= { cmgDsuTestEntry 7 }





--
--	MG PROCESSOR GROUP
--

cmgProcessorConfig		OBJECT IDENTIFIER ::= { cmgProcessor 1 }

cmgProcessorQos			OBJECT IDENTIFIER ::= { cmgProcessor 2 }

cmgProcessorClock		OBJECT IDENTIFIER ::= { cmgProcessor 3 }

--
-- MGP Configuration and Status group
--
cmgGatewayNumber OBJECT-TYPE
	SYNTAX      DisplayString (SIZE (0..3))
	MAX-ACCESS  read-only
	STATUS      current
	DESCRIPTION
	"Media gateway number by which the Call Controller
	knows this media module."
	::= { cmgProcessorConfig 1 }

cmgMACAddress OBJECT-TYPE
	SYNTAX      OCTET STRING (SIZE (0..6))
        MAX-ACCESS  read-only
        STATUS      current
        DESCRIPTION "MAC address of this processor."
	::= { cmgProcessorConfig 2 }

cmgFWVersion OBJECT-TYPE
	SYNTAX      OCTET STRING (SIZE (0..9))
        MAX-ACCESS  read-only
        STATUS      current
        DESCRIPTION "Firmware version of this gateway."
	::= { cmgProcessorConfig 3 }

cmgCurrentIpAddress OBJECT-TYPE
	SYNTAX      IpAddress
	MAX-ACCESS  read-only
	STATUS      current
        DESCRIPTION
	"Current IP address of this processor.  If cmgUseDhcpForIpAddress
	was on(1) at the time of last startup, this was received from the
	DHCP server.  Otherwise it is the value of cmgStaticIpAddress
	at the last startup.  If cmgUseDhcpForIpAddress was on(1) and
	the DHCP request failed, this value will be '0.0.0.0'."
	::= { cmgProcessorConfig 4 }

cmgUseDhcpForIpAddress OBJECT-TYPE
	SYNTAX      INTEGER {
		on(1),
		off(2)
		}
	MAX-ACCESS  read-write
	STATUS      current
        DESCRIPTION
	"Specifies whether the gateway should get its IP address, default
	gateway, and subnet mask from the DHCP server, or use the locally
	administered static IP address, default gateway, and subnet mask."
	::= { cmgProcessorConfig 7 }

cmgUseDhcpForVlan OBJECT-TYPE
	SYNTAX      INTEGER {
		on(1),
		off(2)
		}
	MAX-ACCESS  read-write
	STATUS      current
        DESCRIPTION
	"Specifies whether the gateway should get its VLAN ID from the
	DHCP server, or use the locally administered static VLAN ID
	cmgStatic802Vlan."
	::= { cmgProcessorConfig 8 }

cmgDhcpSson OBJECT-TYPE
	SYNTAX      INTEGER (128..254)
	MAX-ACCESS  read-write
	STATUS      current
        DESCRIPTION
	"Specifies the DHCP Site-Specific Option Number to use with a
	DHCP request.  This gives the DHCP server information about the
	client's capabilities and properties."
	::= { cmgProcessorConfig 9 }

cmgStaticIpAddress OBJECT-TYPE
	SYNTAX      IpAddress
	MAX-ACCESS  read-write
	STATUS      current
        DESCRIPTION
	"Locally administered static IP address of this processor.  If
	cmgUseDhcpForIpAddress is on(1), this object is ignored."
	::= { cmgProcessorConfig 10 }

cmgDnsServerList OBJECT-TYPE
	SYNTAX      DisplayString (SIZE (0..255))
	MAX-ACCESS  read-write
	STATUS      current
        DESCRIPTION
	"Comma-separated list of DNS server IP addresses this processor
	may use."
	::= { cmgProcessorConfig 13 }

cmgDnsHostname OBJECT-TYPE
	SYNTAX      DisplayString (SIZE (0..32))
	MAX-ACCESS  read-only
	STATUS      current
        DESCRIPTION "DNS Hostname of this processor."
	::= { cmgProcessorConfig 14 }

cmgMgpFaultMask OBJECT-TYPE
	SYNTAX      OCTET STRING (SIZE (0..3))
	MAX-ACCESS  read-only
	STATUS      current
	DESCRIPTION
	"Each bit of this value set to '1' indicates a specific fault
	in the Media Gateway processor.

	Octets are numbered in the order in which they appear in the PDU.
	Bits are numbered from the most-significant leftmost bit in the
	octet (bit 0) to the least-significant rightmost bit (bit 7).

	Cajun numbering continues across octets, so that octet 1 bit 0 is
	called bit 8 in the Cajun scheme.  That number is also shown below,
	with the octet value for each single bit set.

    Cajun  Octet Octet
    bit#   bit#  value	Meaning
    -----  ----- -----	-------
    0      0/0   0x80	Memory failure.
    1      0/1   0x40	DHCP request failure.
    2      0/2   0x20	Firmware download failure.
    3      0/3   0x10	Software watchdog alert - MG processes restarting.
    4      0/4   0x08	Internal Communications Controller expected but not present.
    5      0/5   0x04	Internal Communications Controller automatic reset.
    6      0/6   0x02	Media Gateway busy-out.
    7      0/7   0x01	Configuration upload failure.

    8      1/0   0x80	Primary controller not found.
    9      1/1   0x40	No controller found.
    10     1/2   0x20	Registration failure.
    11     1/3   0x10	H.248 control link down.
    12-13  1/4-5	Unused.
    14     1/6   0x02	Maintenance test failure.
    15     1/7   0x01	Maintenance test failure over threshold.
    16     2/0   0x80   Configuration download failure.

    17-23  2/0-7	Unused.
	"
	::= { cmgProcessorConfig 15 }



--
-- MGP Quality of Service group
--
cmgQosControl OBJECT-TYPE
	SYNTAX      INTEGER {
		local(1),
		remote(2)
		}
	MAX-ACCESS  read-only
	STATUS      current
        DESCRIPTION
	"Specifies whether this processor should use the locally administered
	Quality of Service parameters, or whether it should use the parameters
	downloaded from the controller.  This affects both signaling and
	voice traffic."
	::= { cmgProcessorQos 1 }

cmgRemoteSigDscp OBJECT-TYPE
	SYNTAX      INTEGER (0..63)
	MAX-ACCESS  read-only
	STATUS      current
	DESCRIPTION
	"DiffServ Code Point for signaling traffic on the H.248 link,
	received from the controller.  If cmgQosControl is local(1),
	this value is ignored."
	::= { cmgProcessorQos 2 }

cmgRemoteSig802Priority OBJECT-TYPE
	SYNTAX      INTEGER (0..7)
	MAX-ACCESS  read-only
	STATUS      current
	DESCRIPTION
	"802.1 Priority for signaling traffic on the H.248 link,
	received from the controller.  If cmgQosControl is local(1),
	this value is ignored."
	::= { cmgProcessorQos 3 }

cmgLocalSigDscp OBJECT-TYPE
	SYNTAX      INTEGER (0..63)
	MAX-ACCESS  read-write
	STATUS      current
	DESCRIPTION
	"DiffServ Code Point for signaling traffic on the H.248 link,
	locally administered.  If cmgQosControl is remote(2),
	this value is ignored."
	::= { cmgProcessorQos 4 }

cmgLocalSig802Priority OBJECT-TYPE
	SYNTAX      INTEGER (0..7)
	MAX-ACCESS  read-write
	STATUS      current
	DESCRIPTION
	"802.1 Priority for signaling traffic on the H.248 link,
	locally administered.  If cmgQosControl is remote(2),
	this value is ignored."
	::= { cmgProcessorQos 5 }

cmgStatic802Vlan OBJECT-TYPE
	SYNTAX      INTEGER (1..4090)
	MAX-ACCESS  read-write
	STATUS      current
	DESCRIPTION
	"802.1 VLAN ID for this processor, locally administered.
	If cmgUseDhcpForVlan is on(1), this value is ignored."
	::= { cmgProcessorQos 6 }

cmgCurrent802Vlan OBJECT-TYPE
	SYNTAX      INTEGER (1..4090)
	MAX-ACCESS  read-only
	STATUS      current
	DESCRIPTION
	"802.1 VLAN ID currently in use for this processor.  If
	cmgUseDhcpForVlan was on(1) at the last startup, this came
	from the DHCP server.  Otherwise it is equal to cmgStatic802Vlan
	at the time of the last startup."
	::= { cmgProcessorQos 7 }


--
-- MGP Clock group
--

cmgPrimaryClockSource OBJECT-TYPE
	SYNTAX      DisplayString (SIZE (0..21))
	MAX-ACCESS  read-write
	STATUS      current
	DESCRIPTION
	"Primary clock source configured for this processor.  If a T1
	or BRI module is providing the clock, it reads 'Vs' or 'Vs(pp,pp,...)',
	where s is slot number and pp are the port numbers.  If the
	VoIP module is providing the clock, it reads 'voip'.
	It reads 'None' if no primary clock source is configured.
	If cmgClockSourceControl is remote(2), access is read-only.	
	If cmgClockSourceControl is local(1), access is read-write."
	::= { cmgProcessorClock 1 }

cmgSecondaryClockSource OBJECT-TYPE
	SYNTAX      DisplayString (SIZE (0..21))
	MAX-ACCESS  read-write
	STATUS      current
	DESCRIPTION
	"Secondary clock source configured for this processor.  If a T1
	or BRI module is providing the clock, it reads 'Vs' or 'Vs(pp,pp,...)',
	where s is slot number and pp are the port numbers.  If the
	VoIP module is providing the clock, it reads 'voip'.
	It reads 'None' if no secondary clock source is configured.
 	If cmgClockSourceControl is remote(2), access is read-only.	
	If cmgClockSourceControl is local(1), access is read-write."
	::= { cmgProcessorClock 2 }

cmgActiveClockSource OBJECT-TYPE
	SYNTAX      INTEGER {
		primary(1),
		secondary(2),
		local(3)
		}
	MAX-ACCESS  read-write
	STATUS      current
	DESCRIPTION "Identifies the clock source in use at this processor.
 	If cmgClockSourceControl is remote(2), access is read-only.	
	If cmgClockSourceControl is local(1), access is read-write."
	::= { cmgProcessorClock 3 }

cmgClockSwitching OBJECT-TYPE
	SYNTAX      INTEGER {enabled(1), disabled(2) }
	MAX-ACCESS  read-write
	STATUS      current
	DESCRIPTION
	"A flag to enable/disable sync switching.
	If cmgClockSourceControl is remote(2), access is read-only.	
	If cmgClockSourceControl is local(1), access is read-write."
	::= { cmgProcessorClock 4 }

cmgClockSourceControl OBJECT-TYPE
	SYNTAX      INTEGER {local(1), remote(2) }
	MAX-ACCESS  read-only
	STATUS      current
	DESCRIPTION
	"Specifies whether this processor sync administration parameters
	are controlled locally or remotely."
	::= { cmgProcessorClock 5 }

--
--	CALL CONTROLLER	 GROUP
--

cmgRegistrationState OBJECT-TYPE
	SYNTAX      INTEGER { registered(1), notRegistered(2) }
	MAX-ACCESS  read-only
	STATUS      current
	DESCRIPTION
	"Shows whether this media gateway is currently registered with any
	call controller."
	::= { cmgControllers 1 }

cmgActiveControllerAddress OBJECT-TYPE
	SYNTAX      IpAddress
	MAX-ACCESS  read-only
	STATUS      current
	DESCRIPTION
	"IP Address of the call controller now serving this media gateway.
	If cmgRegistrationState is notRegistered(2), this will be '0.0.0.0'.
	Otherwise it will be taken from one of the two address lists at
	registration time."
	::= { cmgControllers 2 }

cmgH248LinkStatus OBJECT-TYPE
	SYNTAX      INTEGER { up(1),down(2) }
	MAX-ACCESS  read-only
	STATUS      current
	DESCRIPTION
	"Status of the H.248 link connecting this media gateway
	to its active call controller."
	::= { cmgControllers 3 }

cmgH248LinkErrorCode OBJECT-TYPE
	SYNTAX      Integer32
	MAX-ACCESS  read-only
	STATUS      current
	DESCRIPTION
	"Most recently received H.248 error code affecting the link
	between this media gateway and its active call controller.
	If cmgH248LinkStatus is up(1), this value will be zero.
	  0	No error
	400	Syntax error in message
	403	Syntax error in TransactionRequest
	406	Version not supported
	410	Incorrect identifier
	411	The transaction refers to an unknown ContextId
	412	No ContextIDs available
	421	Unknown action or illegal combination of actions
	422	Syntax error in action
	430	Unknown TerminationID
	431	No TerminationID matched a wildcard
	432	Out of TerminationIDs or No TerminationID available
	433	TerminationID is already in a Context
	434	Max number of Terminations in a Context exceeded
	440	Unsupported or unknown package
	441	Missing remote or local descriptor
	442	Syntax error in command
	443	Unknown command
	444	Unsupported or unknown descriptor
	445	Unsupported property
	446	Unsupported or unknown parameter
	447	Descriptor not legal in this command
	448	Descriptor appears twice in a command
	450	No such property in this package
	451	No such event in this package
	452	No such signal in this package
	453	No such statistic in this package
	454	No such parameter value in this package
	455	Parameter illegal in this descriptor
	456	Parameter or property appears twice in this descriptor
	457	Missing parameter in signal or event
	471	Implied add for multiplex failure
	500	Internal software failure in the media gateway
	501	Not implemented
	502	Not ready
	503	Service unavailable
	504	Command received from unauthorized entity
	505	Transaction Request received before ServiceChange Reply received
	510	Insufficient resources
	512	Gateway unequipped to detect requested event
	513	Gateway unequipped to generate requested signal
	514	Gateway cannot send the specified announcement
	515	Unsupported media type
	517	Unsupported or invalid mode
	518	Event buffer full
	519	Out of space to store digit map
	520	Digit map undefined in MG
	521	Termination is 'Service Changing'
	526	Insufficient bandwidth
	529	Internal hardware failure in MG
	530	Temporary network failure
	531	Permanent network failure
	581	Does not exist
	"
	::= { cmgControllers 4 }

cmgUseDhcpForMgcList OBJECT-TYPE
	SYNTAX      INTEGER { on(1), off(2) }
	MAX-ACCESS  read-write
	STATUS      current
	DESCRIPTION
	"Should this gateway get its controller IP address from the DHCP
	server, or should it use the locally administered controller list?
	If this value is on(1), the gateway will try the DHCP-provided
	addresses first, and if they fail it will try the static addresses.
	If the value is off(2), the gateway will try only static addresses.
	Changes to this object take effect when the gateway is restarted."
	::= { cmgControllers 5 }

cmgStaticControllerHosts OBJECT-TYPE
	SYNTAX      DisplayString (SIZE (0..64))
	MAX-ACCESS  read-write
	STATUS      current
	DESCRIPTION
	"Comma-separated list of up to four administered static IP addresses
	for primary and backup call controllers.  IP addresses should be in
	the form '123.124.125.126', with no port numbers.  (The Media Gateway
	always uses the default H.248 port number 2945.) An IP address may
	appear more than once in the list.  If cmgUseDhcpForMgcList is equal
	to off(2), these are the only addresses the gateway will try.  In that
	case this list must contain at least one active entry.  Changes to the
	list take effect when the gateway is restarted."
	::= { cmgControllers 6 }

cmgDhcpControllerHosts OBJECT-TYPE
	SYNTAX      DisplayString (SIZE (0..64))
	MAX-ACCESS  read-only
	STATUS      current
	DESCRIPTION
	"List of IP addresses for up to four primary and backup call
	controllers, received from the DHCP server.  An IP address may
	appear more than once in the list.  If cmgUseDhcpForMgcList is
	equal to on(2), the gateway will try these addresses first,
	and if none succeed, it will try the addresses in
	cmgStaticControllerHosts."
	::= { cmgControllers 7 }
  
cmgPrimarySearchTime OBJECT-TYPE
	SYNTAX      INTEGER (1..59)
	MAX-ACCESS  read-write
	STATUS      current
	DESCRIPTION
	"Number of minutes for the Primary Search Timer."
	::= { cmgControllers 8 }
   
   cmgTotalSearchTime OBJECT-TYPE
	SYNTAX      INTEGER (2..60)
	MAX-ACCESS  read-write
	STATUS      current
	DESCRIPTION
	"Number of minutes for the Total Search Timer."
	::= { cmgControllers 9 }

cmgTransitionPoint  OBJECT-TYPE
	SYNTAX      INTEGER (1..4)
	MAX-ACCESS  read-write
	STATUS      current
	DESCRIPTION
	"Value of the Transition Point."
	::= { cmgControllers 10 }

 
--
--	VoIP GROUP
--

cmgVoipEngineUseDhcp OBJECT-TYPE
	SYNTAX      INTEGER { on(1), off(2) }
	MAX-ACCESS  read-write
	STATUS      current
	DESCRIPTION
	"Determines whether VoIP engines use their statically administered
	IP addresses or whether they get their addresses from the DHCP server."
	::= { cmgVoip 1 }

cmgVoipQosControl OBJECT-TYPE
	SYNTAX      INTEGER { local(1), remote(2) }
	MAX-ACCESS  read-only
	STATUS      current
	DESCRIPTION
	"This is the same as cmgQosControl in the MG Processor group.  That
	parameter determines whether the gateway uses voice and signaling
	QoS parameters administered locally or whether it gets the parameters
	from its call controller.  It is reproduced here for convenience."
	::= { cmgVoip 2 }


cmgVoipRemoteParameters		OBJECT IDENTIFIER ::= { cmgVoip 3 }

cmgVoipRemoteQosParameters	OBJECT IDENTIFIER ::= { cmgVoipRemoteParameters 1 }
cmgVoipRemoteRtcpParameters	OBJECT IDENTIFIER ::= { cmgVoipRemoteParameters 2 }
cmgVoipRemoteRsvpParameters	OBJECT IDENTIFIER ::= { cmgVoipRemoteParameters 3 }


cmgVoipLocalParameters		OBJECT IDENTIFIER ::= { cmgVoip 4 }

cmgVoipLocalQosParameters	OBJECT IDENTIFIER ::= { cmgVoipLocalParameters 1 }
cmgVoipLocalRtcpParameters	OBJECT IDENTIFIER ::= { cmgVoipLocalParameters 2 }
cmgVoipLocalRsvpParameters	OBJECT IDENTIFIER ::= { cmgVoipLocalParameters 3 }


--
--	Remote (controller-provided) QoS parameters
--
cmgVoipRemoteBbeDscp OBJECT-TYPE
	SYNTAX      INTEGER (0..63)
	MAX-ACCESS  read-only
	STATUS      current
	DESCRIPTION
	"The Better-than-Best-Effort DiffServ code point received from the
	controller.  This is a value to be assigned to the code point part
	of the Differentiated Services field in the IP header of each voice
	packet.  See RFC2475 for a full description of Differentiated Services."
	::= { cmgVoipRemoteQosParameters 1 }

cmgVoipRemoteEfDscp OBJECT-TYPE
	SYNTAX      INTEGER (0..63)
	MAX-ACCESS  read-only
	STATUS      current
	DESCRIPTION
	"The Expedited-Forwarding DiffServ code point received from the
	controller.  This is a value to be assigned to the code point part
	of the Differentiated Services field in the IP header of each voice
	packet.  See RFC2475 for a full description of Differentiated Services."
	::= { cmgVoipRemoteQosParameters 2 }

cmgVoipRemote802Priority OBJECT-TYPE
	SYNTAX      INTEGER (0..7)
	MAX-ACCESS  read-only
	STATUS      current
	DESCRIPTION
	"The 802.1 priority received from the call controller.  This is
	a priority value to be assigned to the tag header for priority-tagged
	voice frames.  See IEEE standard 802.1Q-1998 for a full description."
	::= { cmgVoipRemoteQosParameters 3 }

cmgVoipRemoteMinRtpPort OBJECT-TYPE
	SYNTAX      INTEGER (1..65533)
	MAX-ACCESS  read-only
	STATUS      current
	DESCRIPTION
	"The lower end of the range of UDP ports assigned to voice traffic,
	received from the call controller.  Must be less than or equal
	to cmgVoipRemoteMaxRtpPort."
	::= { cmgVoipRemoteQosParameters 4 }

cmgVoipRemoteMaxRtpPort OBJECT-TYPE
	SYNTAX      INTEGER (3..65535)
	MAX-ACCESS  read-only
	STATUS      current
	DESCRIPTION
	"The upper end of the range of UDP ports assigned to voice traffic,
	received from the call controller.  Must be greater than or equal
	to cmgVoipRemoteMinRtpPort."
	::= { cmgVoipRemoteQosParameters 5 }


--
--	Remote (controller-provided) RTCP parameters
--
cmgVoipRemoteRtcpEnabled OBJECT-TYPE
	SYNTAX      INTEGER {enabled(1), disabled(2) }
	MAX-ACCESS  read-only
	STATUS      current
	DESCRIPTION
	"A flag that determines whether the Media Gateway will collect and
	report RTCP statistics.  See RFC 1889 for a full description of RTCP.
	If this value is disabled(2), the rest of this group will be ignored."
	::= { cmgVoipRemoteRtcpParameters 1 }

cmgVoipRemoteRtcpMonitorIpAddress OBJECT-TYPE
	SYNTAX      IpAddress
	MAX-ACCESS  read-only
	STATUS      current
	DESCRIPTION
	"The address of an RTCP monitor to which the Media Gateway should
	report its RTCP statistics."
	::= { cmgVoipRemoteRtcpParameters 2 }

cmgVoipRemoteRtcpMonitorPort OBJECT-TYPE
	SYNTAX      INTEGER (1..65535)
	MAX-ACCESS  read-only
	STATUS      current
	DESCRIPTION
	"The port on the RTCP monitor to which the Media Gateway should
	report its RTCP statistics."
	::= { cmgVoipRemoteRtcpParameters 3 }

cmgVoipRemoteRtcpReportPeriod OBJECT-TYPE
	SYNTAX      INTEGER (5..30)
	MAX-ACCESS  read-only
	STATUS      current
	DESCRIPTION
	"The RTCP reporting interval in seconds."
	::= { cmgVoipRemoteRtcpParameters 4 }


--
--	Remote (controller-provided) RSVP parameters
--
cmgVoipRemoteRsvpEnabled OBJECT-TYPE
	SYNTAX      INTEGER {enabled(1), disabled(2) }
	MAX-ACCESS  read-only
	STATUS      current
	DESCRIPTION
	"A flag that determines whether the VoIP engines should use RSVP to
	control call admission.  See RFC 2205 for a full description of RSVP.
	If this value is disabled(2), the rest of this group will be ignored."
	::= { cmgVoipRemoteRsvpParameters 1 }

cmgVoipRemoteRetryOnFailure OBJECT-TYPE
	SYNTAX      INTEGER {enabled(1), disabled(2) }
	MAX-ACCESS  read-only
	STATUS      current
	DESCRIPTION
	"A flag that determines whether the VoIP engines should retry a
	reservation request after the first one fails.  If this value is
	disabled(2), the next object will be ignored."
	::= { cmgVoipRemoteRsvpParameters 2 }

cmgVoipRemoteRetryDelay OBJECT-TYPE
	SYNTAX      INTEGER (1..99)	-- Is there a defined range?
	MAX-ACCESS  read-only
	STATUS      current
	DESCRIPTION
	"The interval in seconds between a reservation request failure and the
	subsequent retry.  If cmgVoipRemoteRetryOnFailure is disabled(2), this
	object will be ignored."
	::= { cmgVoipRemoteRsvpParameters 3 }

cmgVoipRemoteRsvpProfile OBJECT-TYPE
	SYNTAX      INTEGER {guaranteedService(1), controlledLoadService(2) }
	MAX-ACCESS  read-only
	STATUS      current
	DESCRIPTION
	"The RSVP service model to request."
	::= { cmgVoipRemoteRsvpParameters 4 }


--
--	Locally administered QoS parameters
--
cmgVoipLocalBbeDscp OBJECT-TYPE
	SYNTAX      INTEGER (0..63)
	MAX-ACCESS  read-write
	STATUS      current
	DESCRIPTION
	"The Better-than-Best-Effort DiffServ code point received from the
	controller.  This is a value to be assigned to the code point part
	of the Differentiated Services field in the IP header of each voice
	packet.  See RFC2475 for a full description of Differentiated Services."
	::= { cmgVoipLocalQosParameters 1 }

cmgVoipLocalEfDscp OBJECT-TYPE
	SYNTAX      INTEGER (0..63)
	MAX-ACCESS  read-write
	STATUS      current
	DESCRIPTION
	"The Expedited-Forwarding DiffServ code point received from the
	controller.  This is a value to be assigned to the code point part
	of the Differentiated Services field in the IP header of each voice
	packet.  See RFC2475 for a full description of Differentiated Services."
	::= { cmgVoipLocalQosParameters 2 }

cmgVoipLocal802Priority OBJECT-TYPE
	SYNTAX      INTEGER (0..7)
	MAX-ACCESS  read-write
	STATUS      current
	DESCRIPTION
	"The 802.1 priority received from the call controller.  This is
	a priority value to be assigned to the tag header for priority-tagged
	voice frames.  See IEEE standard 802.1Q-1998 for a full description."
	::= { cmgVoipLocalQosParameters 3 }

cmgVoipLocalMinRtpPort OBJECT-TYPE
	SYNTAX      INTEGER (1..65533)
	MAX-ACCESS  read-write
	STATUS      current
	DESCRIPTION
	"The lower end of the range of UDP ports assigned to voice traffic,
	received from the call controller.  Must be less than or equal
	to cmgVoipLocalMaxRtpPort."
	::= { cmgVoipLocalQosParameters 4 }

cmgVoipLocalMaxRtpPort OBJECT-TYPE
	SYNTAX      INTEGER (3..65535)
	MAX-ACCESS  read-write
	STATUS      current
	DESCRIPTION
	"The upper end of the range of UDP ports assigned to voice traffic,
	received from the call controller.  Must be greater than or equal
	to cmgVoipLocalMinRtpPort."
	::= { cmgVoipLocalQosParameters 5 }


--
--	Locally administered RTCP parameters
--
cmgVoipLocalRtcpEnabled OBJECT-TYPE
	SYNTAX      INTEGER {enabled(1), disabled(2) }
	MAX-ACCESS  read-write
	STATUS      current
	DESCRIPTION
	"A flag that determines whether the Media Gateway will collect and
	report RTCP statistics.  See RFC 1889 for a full description of RTCP.
	If this value is disabled(2), the rest of this group will be ignored."
	::= { cmgVoipLocalRtcpParameters 1 }

cmgVoipLocalRtcpMonitorIpAddress OBJECT-TYPE
	SYNTAX      IpAddress
	MAX-ACCESS  read-write
	STATUS      current
	DESCRIPTION
	"The address of an RTCP monitor to which the Media Gateway should
	report its RTCP statistics."
	::= { cmgVoipLocalRtcpParameters 2 }

cmgVoipLocalRtcpMonitorPort OBJECT-TYPE
	SYNTAX      INTEGER (1..65535)
	MAX-ACCESS  read-write
	STATUS      current
	DESCRIPTION
	"The port on the RTCP monitor to which the Media Gateway should
	report its RTCP statistics."
	::= { cmgVoipLocalRtcpParameters 3 }

cmgVoipLocalRtcpReportPeriod OBJECT-TYPE
	SYNTAX      INTEGER (5..30)
	MAX-ACCESS  read-write
	STATUS      current
	DESCRIPTION
	"The RTCP reporting interval in seconds."
	::= { cmgVoipLocalRtcpParameters 4 }


--
--	Locally administered RSVP parameters
--
cmgVoipLocalRsvpEnabled OBJECT-TYPE
	SYNTAX      INTEGER {enabled(1), disabled(2) }
	MAX-ACCESS  read-write
	STATUS      current
	DESCRIPTION
	"A flag that determines whether the VoIP engines should use RSVP to
	control call admission.  See RFC 2205 for a full description of RSVP.
	If this value is disabled(2), the rest of this group will be ignored."
	::= { cmgVoipLocalRsvpParameters 1 }

cmgVoipLocalRetryOnFailure OBJECT-TYPE
	SYNTAX      INTEGER {enabled(1), disabled(2) }
	MAX-ACCESS  read-write
	STATUS      current
	DESCRIPTION
	"A flag that determines whether the VoIP engines should retry a
	reservation request after the first one fails.  If this value is
	disabled(2), the next object will be ignored."
	::= { cmgVoipLocalRsvpParameters 2 }

cmgVoipLocalRetryDelay OBJECT-TYPE
	SYNTAX      INTEGER (1..99)	-- Is there a defined range?
	MAX-ACCESS  read-write
	STATUS      current
	DESCRIPTION
	"The interval in seconds between a reservation request failure and the
	subsequent retry.  If cmgVoipLocalRetryOnFailure is disabled(2), this
	object will be ignored."
	::= { cmgVoipLocalRsvpParameters 3 }

cmgVoipLocalRsvpProfile OBJECT-TYPE
	SYNTAX      INTEGER {guaranteedService(1), controlledLoadService(2) }
	MAX-ACCESS  read-write
	STATUS      current
	DESCRIPTION "The RSVP service model to request."
	::= { cmgVoipLocalRsvpParameters 4 }



--
--	VoIP Engine Table
--
cmgVoipEngineTable OBJECT-TYPE
	SYNTAX      SEQUENCE OF VoipEngineEntry
	MAX-ACCESS  not-accessible
	STATUS      current
	DESCRIPTION "Table of VoIP engines in the media gateway."
	::= { cmgVoip 5 }

cmgVoipEngineEntry OBJECT-TYPE
	SYNTAX      VoipEngineEntry
	MAX-ACCESS  not-accessible
	STATUS      current
	DESCRIPTION "An entry in the table representing one VoIP engine."
	INDEX  { cmgVoipSlot }
	::= { cmgVoipEngineTable 1 }

VoipEngineEntry  ::=
	SEQUENCE  {
	cmgVoipSlot		INTEGER,
	cmgVoipMACAddress	OCTET STRING,
	cmgVoipStaticIpAddress	IpAddress,
	cmgVoipCurrentIpAddress	IpAddress,
	cmgVoipJitterBufferSize	Integer32,
	cmgVoipTotalChannels	Integer32,
	cmgVoipChannelsInUse	Integer32,
	cmgVoipAverageOccupancy	INTEGER,
	cmgVoipHyperactivity	INTEGER,
	cmgVoipAdminState	INTEGER,
	cmgVoipDspFWVersion	DisplayString,
	cmgVoipDspStatus	INTEGER,
	cmgVoipEngineReset	INTEGER,
	cmgVoipFaultMask	OCTET STRING
	}

cmgVoipSlot OBJECT-TYPE
	SYNTAX      INTEGER (1..104)
	MAX-ACCESS  read-only
	STATUS      current
	DESCRIPTION
	"Location of this VoIP engine, either a media module slot (1-4 for G700) or
	the motherboard (100 for G700, 10 for G350, G250).
	For G450/G430 the index arrangement is as follows:
	 * For V1 - V10 the rule is cmgVoIPSlot = Slot# * 10 + SoDIMM#. Note that MM760 is not supported 
	 in G430/G450, nor other MM which support VoIP engine. Thus, only V10 is relevant. 
	 	* For G450 motherboard is 101-104. 
	 	* For G430 motherboard is 101-102 (101 is the on board DSP and 102 is the replaceable VoIP 
	 	SoDIMM module. 
	"
	::= { cmgVoipEngineEntry 1 }

cmgVoipMACAddress OBJECT-TYPE
	SYNTAX      OCTET STRING (SIZE (0..6))
        MAX-ACCESS  read-only
        STATUS      current
        DESCRIPTION "MAC address of the component hosting this VoIP engine."
	::= { cmgVoipEngineEntry 2 }

cmgVoipStaticIpAddress OBJECT-TYPE
	SYNTAX      IpAddress
	MAX-ACCESS  read-write
	STATUS      current
	DESCRIPTION
	"Administered static IP Address of this VoIP engine.  If
	cmgVoipEngineUseDhcp was off(2) at startup time, this value
	determined the current IP address of the engine."
	::= { cmgVoipEngineEntry 3 }

cmgVoipCurrentIpAddress OBJECT-TYPE
	SYNTAX      IpAddress
	MAX-ACCESS  read-only
	STATUS      current
	DESCRIPTION
	"IP Address currently in use at this VoIP engine.  If
	cmgVoipEngineUseDhcp was on(2) at startup time, this value
	was received from the DHCP server.  Otherwise it is equal to
	cmgVoipStaticIpAddress at startup time."
	::= { cmgVoipEngineEntry 4 }

cmgVoipJitterBufferSize OBJECT-TYPE
	SYNTAX      Integer32
	MAX-ACCESS  read-only
	STATUS      current
	DESCRIPTION
	"Size in bytes of the dynamic jitter buffer at this VoIP engine."
	::= { cmgVoipEngineEntry 5 }

cmgVoipTotalChannels OBJECT-TYPE
	SYNTAX      Integer32
	MAX-ACCESS  read-only
	STATUS      current
	DESCRIPTION "Total channels available to this VoIP engine."
	::= { cmgVoipEngineEntry 6 }

cmgVoipChannelsInUse OBJECT-TYPE
	SYNTAX      Integer32
	MAX-ACCESS  read-only
	STATUS      current
	DESCRIPTION "Number of channels in use at this VoIP engine."
	::= { cmgVoipEngineEntry 7 }

		--
		-- Can we say more about the algorithms
		-- for occupancy and hyperactivity?
		--
cmgVoipAverageOccupancy OBJECT-TYPE
	SYNTAX      INTEGER (0..100)
	MAX-ACCESS  read-only
	STATUS      current
	DESCRIPTION "5-minute average occupancy of this VoIP engine."
	::= { cmgVoipEngineEntry 8 }

cmgVoipHyperactivity OBJECT-TYPE
	SYNTAX      INTEGER { normal(1), hyperactive(2), unknown(255) }
	MAX-ACCESS  read-only
	STATUS      current
	DESCRIPTION
	"Indicates whether hyperactivity has been detected by this VoIP engine."
	::= { cmgVoipEngineEntry 9 }

cmgVoipAdminState OBJECT-TYPE
	SYNTAX      INTEGER { busy-out(1), release(2), camp-on(3), unknown(255) }
	MAX-ACCESS  read-only
	STATUS      current
	DESCRIPTION "Maintenance busy-out state of this VoIP engine."
	::= { cmgVoipEngineEntry 10 }

cmgVoipDspFWVersion OBJECT-TYPE
	SYNTAX      DisplayString (SIZE (0..9))
	MAX-ACCESS  read-only
	STATUS      current
	DESCRIPTION
	"Firmware version of the DSP complex on this VoIP engine.  This is
	also available in the Load MIB."
	::= { cmgVoipEngineEntry 11 }

cmgVoipDspStatus OBJECT-TYPE
	SYNTAX      INTEGER { idle(1), inUse(2), fault(3) }
	MAX-ACCESS  read-only
	STATUS      current
	DESCRIPTION "Status of the DSP complex on this VoIP engine."
	::= { cmgVoipEngineEntry 12 }

cmgVoipEngineReset OBJECT-TYPE
	SYNTAX      INTEGER { on(1), off(2) }
        MAX-ACCESS  read-write
        STATUS      current
        DESCRIPTION
	"Setting the value of this attribute to ON is interpreted as
	a reset command for the VoIP engine.  It initiates a complete
	reinitialisation of the VoIP engine."
	::= { cmgVoipEngineEntry 13 }

cmgVoipFaultMask OBJECT-TYPE
	SYNTAX      OCTET STRING (SIZE (0..2))
	MAX-ACCESS  read-only
	STATUS      current
	DESCRIPTION
	"Each bit of this value set to '1' indicates a specific fault
	in the VoIP engine.

	Octets are numbered in the order in which they appear in the PDU.
	Bits are numbered from the most-significant leftmost bit in the
	octet (bit 0) to the least-significant rightmost bit (bit 7).

	Cajun numbering continues across octets, so that octet 1 bit 0 is
	called bit 8 in the Cajun scheme.  That number is also shown below,
	with the octet value for each single bit set.

    Cajun  Octet Octet
    bit#   bit#  value	Meaning
    -----  ----- -----	-------
    0      0/0   0x80	Occupancy above threshold, based on a snapshot of
			cmgVoipChannelsInUse divided by cmgVoipTotalChannels.
    1      0/1   0x40	Occupancy above threshold, based on cmgVoipAverageOccupancy.
    2      0/2   0x20	VoIP engine automatic reset.
    3      0/3   0x10	VoIP hardware fault.
    4      0/4   0x08	VoIP IP configuration fault.
    5      0/5  0x04    VoIP DSP Failure
    6      0/6   0x02   VoIP DSP CORE Failure 
    7      0/7   0x01   VoIP DSP FPGA Failure
    8      1/0   0x80   Unsupported DSP module. 
    9--15  1/1-7 Unused
	"
	::= { cmgVoipEngineEntry 14 }

cmgVoipDSPCoreTable OBJECT-TYPE
	SYNTAX      SEQUENCE OF CmgVoipDSPCoreEntry
	MAX-ACCESS  not-accessible
	STATUS      current
	DESCRIPTION "Table representing the DSP cores in VoIP engine of the media gateway."
	::= { cmgVoip 6 }   
	
cmgVoipDSPCoreEntry OBJECT-TYPE
	SYNTAX      CmgVoipDSPCoreEntry
	MAX-ACCESS  not-accessible
	STATUS      current
	DESCRIPTION "An entry in the table representing one DSP Core of a VoIP engine.
				This table uses an external index from cmgVoIPEngineTable 
				which selects a DSP SoDIMM/engine module and secondary index 
				cmgDSPVoIPCoreID that selects a core on SoDIMM module"
	INDEX  { cmgVoipSlot, cmgDSPCoreCoreId }
	::= { cmgVoipDSPCoreTable 1 }  
	
CmgVoipDSPCoreEntry  ::=
	SEQUENCE  {
	cmgDSPCoreCoreId			INTEGER,
	cmgDSPCoreTotalChannels		INTEGER,
	cmgDSPCoreChannelsInUse		INTEGER,
	cmgDSPCoreAdminState		INTEGER,
	cmgDSPCoreStatus			INTEGER,
	cmgDSPCoreDemandTest		INTEGER,
    cmgDSPCoreDemandTestResult	INTEGER
	}

cmgDSPCoreCoreId OBJECT-TYPE
	SYNTAX      INTEGER (1..4)
	MAX-ACCESS  read-only
	STATUS      current
	DESCRIPTION
	"The DSP core ID within the specific DSP VoIP engine."
	::= { cmgVoipDSPCoreEntry 1 }

cmgDSPCoreTotalChannels OBJECT-TYPE
	SYNTAX      INTEGER (1..20)
	MAX-ACCESS  read-only
	STATUS      current
	DESCRIPTION "Total channels available to this DSP core."
	::= { cmgVoipDSPCoreEntry 2 }

cmgDSPCoreChannelsInUse OBJECT-TYPE
	SYNTAX      INTEGER (1..20)
	MAX-ACCESS  read-only
	STATUS      current
	DESCRIPTION "Number of channels in use at this DSP core."
	::= { cmgVoipDSPCoreEntry 3 }

cmgDSPCoreAdminState OBJECT-TYPE
	SYNTAX      INTEGER { busy-out(1), release(2), camp-on(3), unknown(255) }
	MAX-ACCESS  read-write
	STATUS      current
	DESCRIPTION "Maintenance busy-out state of this DSP core."
	::= { cmgVoipDSPCoreEntry 4 }

cmgDSPCoreStatus OBJECT-TYPE
	SYNTAX      INTEGER { idle(1), inUse(2), fault(3) }
	MAX-ACCESS  read-only
	STATUS      current
	DESCRIPTION "Status of the DSP Core."
	::= { cmgVoipDSPCoreEntry 5 }

cmgDSPCoreDemandTest OBJECT-TYPE
	SYNTAX      INTEGER { on(1), off(2) }
	MAX-ACCESS  read-write
	STATUS      current
	DESCRIPTION "Activates on demand test for the DSP Core."
	::= { cmgVoipDSPCoreEntry 6 }

cmgDSPCoreDemandTestResult OBJECT-TYPE
	SYNTAX      INTEGER { errorCode1 (1), errorCode2 (2),
						  errorCode3 (3), errorCode4 (4),
						  errorCode5 (5), errorCode6 (6),
						  notResponding (7), pass (255) 
						 }
	MAX-ACCESS  read-only
	STATUS      current
	DESCRIPTION "Result of the on demand test for the DSP Core."
	::= { cmgVoipDSPCoreEntry 7 }


--
--	Voip Echo Canceller
--

cmgVoipEchoCancellerControl OBJECT-TYPE
    SYNTAX      INTEGER { auto(0), on(1), off(2), fixedOn(3) }
    MAX-ACCESS  read-write
    STATUS      current
    DESCRIPTION
       "The echo canceller control setting for all VoIP engines.
          auto means that the system will enable or disable the echo
          cancellers as appropriate for each call.
          fixedOn indicates that the VoIP firmware always enables
          the echo cancellers (this value cannot be changed)."
    ::= { cmgVoip 7 }

cmgVoipEchoCancellerConfig1 OBJECT-TYPE
    SYNTAX      INTEGER (0..255)
    MAX-ACCESS  read-write
    STATUS      current
    DESCRIPTION
       "Echo canceller configuration setting for all VoIP engines (byte 1 of 2).
       This value may not be writable if the VoIP firmware is old."
    ::= { cmgVoip 8 }

cmgVoipEchoCancellerConfig2 OBJECT-TYPE
    SYNTAX      INTEGER (0..255)
    MAX-ACCESS  read-write
    STATUS      current
    DESCRIPTION
       "Echo canceller configuration setting for all VoIP engines (byte 2 of 2).
       This value may not be writable if the VoIP firmware is old."
    ::= { cmgVoip 9 }


--
--	TRAPS GROUP
--

cmgTrapManagerTable OBJECT-TYPE
	SYNTAX      SEQUENCE OF CmgTrapManagerEntry
	MAX-ACCESS  not-accessible
	STATUS      current
	DESCRIPTION "Table of trap receivers in this media gateway."
	::= { cmgTraps 1 } 

cmgTrapManagerEntry OBJECT-TYPE
	SYNTAX      CmgTrapManagerEntry
	MAX-ACCESS  not-accessible
	STATUS      current
	DESCRIPTION "An entry in the table, representing a single trap receiver."
        INDEX  { cmgTrapManagerAddress }
	::= { cmgTrapManagerTable 1 }

CmgTrapManagerEntry  ::=
	SEQUENCE  {
	cmgTrapManagerAddress	IpAddress,
	cmgTrapManagerControl	INTEGER,
	cmgTrapManagerMask	Integer32,
	cmgTrapManagerRowStatus	RowStatus
	}


cmgTrapManagerAddress OBJECT-TYPE
	SYNTAX      IpAddress
	MAX-ACCESS  read-create
	STATUS      current
	DESCRIPTION "IP address of this trap receiver."
	::= { cmgTrapManagerEntry 1 }

--
--  { cmgTrapManagerEntry 2 } is reserved for a later release, when we
--  may support fully-qualified DNS domain names to identify trap managers.
--

cmgTrapManagerControl OBJECT-TYPE
	SYNTAX      INTEGER {
		active(1),
		inactive(2)
	}
	MAX-ACCESS  read-create
	STATUS      current
	DESCRIPTION
	"Specifies whether this trap receiver is currently receiving traps."
	::= { cmgTrapManagerEntry 3 }

cmgTrapManagerMask OBJECT-TYPE
	SYNTAX      Integer32
	MAX-ACCESS  read-create
	STATUS      current
	DESCRIPTION
	"A bit mask indicating the trap categories of interest
	to this trap receiver.
	Bit	Category
	0	Power warnings
	1	Fan and temperature warnings
	2	Application faults
	3	Module insert or remove
	4	Configuration traps: port enable or disable, administrative
		busy-out and release for ports and media modules
	5-7	Not supported
	8	Voice faults: Quality of service problems, voice hardware
		faults
	9	Normal operations: successful registration with the gateway
		controller, successful firmware download.
	10-31	Not supported
	"
	::= { cmgTrapManagerEntry 4 }

cmgTrapManagerRowStatus OBJECT-TYPE
	SYNTAX      RowStatus
	MAX-ACCESS  read-create
	STATUS      current
	DESCRIPTION
        "The status of this entry in the table.  Available states:
	active(1),	-- Trap receiver is administered, though not
			-- necessarily active.
	createAndGo(4),	-- Used to add a new receiver to the table.
	destroy(6)	-- Used to delete a receiver from the table.
 
        The cmgTrapManagerAddress of a new entry must be different from all other
        entries, or the create request will return INCONSISTENT-VALUE-ERROR.
	"
	::= { cmgTrapManagerEntry 5 }


--
--	Trap definitions and the trap variables to support them
--

cmgTrapDefinitions	OBJECT IDENTIFIER ::= { cmgTraps 2 }

cmgTrapVariables	OBJECT IDENTIFIER ::= { cmgTrapDefinitions 1 }
cmgTrapTypes		OBJECT IDENTIFIER ::= { cmgTrapDefinitions 2 }

cmgTrapLocation OBJECT-TYPE
	SYNTAX      DisplayString (SIZE (0..8))
	MAX-ACCESS  accessible-for-notify
	STATUS      current
	DESCRIPTION
	"Location of the problem in the form gggVspp, where
	ggg	Media gateway number, or zero if the gateway is not
		currently registered with any controller.
	V	The letter V; a field separator.
	s	Slot number, if applicable.  If the fault occurred on
		the media gateway processor, this will be omitted.
	pp	Port number, if applicable.  If the fault occurred on
		the media gateway processor or on a media module as a
		whole, this will be omitted.
	"
	::= { cmgTrapVariables 1 }

cmgTrapOnBoard OBJECT-TYPE
	SYNTAX      DisplayString (SIZE (0..4))
	MAX-ACCESS  accessible-for-notify
	STATUS      current
	DESCRIPTION
	"Expected values are 'no' and 'yes'.  If a problem is on-board,
	replacing the media module is likely to resolve the problem."
	::= { cmgTrapVariables 2 }

cmgTrapSubsystem OBJECT-TYPE
	SYNTAX      DisplayString (SIZE (0..4))
	MAX-ACCESS  accessible-for-notify
	STATUS      current
	DESCRIPTION "The high-level subsystem that generated the trap.
	Expected values are 'HW', 'SW', and 'Net'."
	::= { cmgTrapVariables 3 }

cmgTrapOnIccMissing	OBJECT-TYPE
	SYNTAX      INTEGER { no(1), yes(2) }
	MAX-ACCESS  read-write
	STATUS      current
	DESCRIPTION
	"Should the media gateway send a trap on startup if there is no
	integrated communications controller in slot 1?"
	::= { cmgTrapVariables 4 }

cmgTrapModule	OBJECT-TYPE
	SYNTAX      DisplayString (SIZE (0..32))
	MAX-ACCESS  accessible-for-notify
	STATUS      current
	DESCRIPTION
	"A display string to identify the module type in module
	insert and remove traps."
	::= { cmgTrapVariables 5 }   
	
cmgTrapSeverity OBJECT-TYPE            
   	SYNTAX   CmgItuPerceivedSeverity
   	MAX-ACCESS accessible-for-notify
   	STATUS current            
   	DESCRIPTION
  	"The severity of the notification."
   	::= { cmgTrapVariables 6}    
   	
cmgProductId OBJECT-TYPE            
    SYNTAX   DisplayString (SIZE (0..10))
    MAX-ACCESS accessible-for-notify
    STATUS current            
    DESCRIPTION
    "The Product Id of Avaya Device - 10 characters."
    ::= { cmgTrapVariables 7} 


cmgTrapAvailableTimeslots OBJECT-TYPE
	SYNTAX      Integer32
	MAX-ACCESS  accessible-for-notify
	STATUS      current
	DESCRIPTION "Number of Timeslots available on this gateway."
	::= { cmgTrapVariables 8 }
 
cmgTrapInUseTimeslots OBJECT-TYPE
	SYNTAX      Integer32
	MAX-ACCESS  accessible-for-notify
	STATUS      current
	DESCRIPTION "Number of Timeslots in use on this gateway."
	::= { cmgTrapVariables 9 }

--
cmgTrapV3separator		OBJECT IDENTIFIER ::= { cmgTrapTypes 0 }

-- "RFC 2576 says: 'If the SNMPv1 generic-trap parameter is 'enterpriseSpecific(6)', 
--       the SNMPv2 snmpTrapOID parameter SHALL be the concatentation of  the SNMPv1
--       enterprise parameter and two additional sub- identifiers, '0', 
--       and the SNMPv1 specific-trap parameter.'
--
--   in SNMPv1 G350 is sending for cmg traps:
--   generic trap: 		enterpriseSpecific(6)
--   enterprise: 		cmgTrapTypes(1.3.6.1.4.1.6889.2.9.1.5.2.2)
--   specific trap:		x (cmg trap number)
--
--   Consequently, for SNMPv3, G350 should send 1.3.6.1.4.1.6889.2.9.1.5.2.2.0.x 
--   and so the traps OIDs were moved under this identifier" 
  
--
--  Hardware traps
--

cmgMultipleFanFault	NOTIFICATION-TYPE
	OBJECTS   { cmgTrapSubsystem, cmgTrapOnBoard, cmgTrapLocation, cmgHardwareFaultMask }
	STATUS      current
	DESCRIPTION
	"At least two fans have been operating at less than 90% of their
	nominal speed for five minutes or more.  This may be an early
	warning of overheating."
	::= { cmgTrapV3separator 2 }

cmgMultipleFanClear	NOTIFICATION-TYPE
	OBJECTS   { cmgTrapSubsystem, cmgTrapOnBoard, cmgTrapLocation, cmgHardwareFaultMask }
	STATUS      current
	DESCRIPTION
	"At least three fans are operating normally.  The system should
	be operable indefinitely without overheating."
	::= { cmgTrapV3separator 3 }

cmgPsuFanBriefFault	NOTIFICATION-TYPE
	OBJECTS   { cmgTrapSubsystem, cmgTrapOnBoard, cmgTrapLocation, cmgHardwareFaultMask }
	STATUS      current
	DESCRIPTION
	"The power supply fan has been operating at less than 90% of its
	optimal speed for 10 minutes or more, but less than 15 minutes.
	This may be an early warning of overheating."
	::= { cmgTrapV3separator 4 }

cmgPsuFanBriefClear	NOTIFICATION-TYPE
	OBJECTS   { cmgTrapSubsystem, cmgTrapOnBoard, cmgTrapLocation, cmgHardwareFaultMask }
	STATUS      current
	DESCRIPTION "The power supply fan is operating normally."
	::= { cmgTrapV3separator 5 }

cmgPsuFanProlongedFault	NOTIFICATION-TYPE
	OBJECTS   { cmgTrapSubsystem, cmgTrapOnBoard, cmgTrapLocation, cmgHardwareFaultMask }
	STATUS      current
	DESCRIPTION
	"The power supply fan has been operating at less than 90% of its
	optimal speed for 15 minutes or more.  This may be an early
	warning of overheating."
	::= { cmgTrapV3separator 6 }

cmgPsuFanProlongedClear		NOTIFICATION-TYPE
	OBJECTS   { cmgTrapSubsystem, cmgTrapOnBoard, cmgTrapLocation, cmgHardwareFaultMask }
	STATUS      current
	DESCRIPTION "The power supply fan is operating normally."
	::= { cmgTrapV3separator 7 }

-- Trap types 8 and 9 are unused.

cmgCpuTempWarningFault	NOTIFICATION-TYPE
	OBJECTS   { cmgTrapSubsystem, cmgTrapOnBoard, cmgTrapLocation, cmgHardwareFaultMask, cmgCpuTemp, cmgCpuTempWarningThresh, cmgCpuTempShutdownThresh }
	STATUS      current
	DESCRIPTION
	"The temperature sensor at the CPU has exceeded its warning threshold."
	::= { cmgTrapV3separator 10 }

cmgCpuTempWarningClear	NOTIFICATION-TYPE
	OBJECTS   { cmgTrapSubsystem, cmgTrapOnBoard, cmgTrapLocation, cmgHardwareFaultMask, cmgCpuTemp, cmgCpuTempWarningThresh, cmgCpuTempShutdownThresh }
	STATUS      current
	DESCRIPTION
	"The temperature sensor at the CPU has dropped below its warning
	threshold."
	::= { cmgTrapV3separator 11 }

cmgDspTempWarningFault	NOTIFICATION-TYPE
	OBJECTS   { cmgTrapSubsystem, cmgTrapOnBoard, cmgTrapLocation, cmgHardwareFaultMask, cmgDspTemp, cmgDspTempWarningThresh, cmgDspTempShutdownThresh }
	STATUS      current
	DESCRIPTION
	"The temperature sensor at the DSP complex has exceeded its
	warning threshold."
	::= { cmgTrapV3separator 12 }

cmgDspTempWarningClear	NOTIFICATION-TYPE
	OBJECTS   { cmgTrapSubsystem, cmgTrapOnBoard, cmgTrapLocation, cmgHardwareFaultMask, cmgDspTemp, cmgDspTempWarningThresh, cmgDspTempShutdownThresh }
	STATUS      current
	DESCRIPTION
	"The temperature sensor at the DSP complex has dropped below its
	warning threshold."
	::= { cmgTrapV3separator 13 }

cmgTempShutdownFault	NOTIFICATION-TYPE
	OBJECTS   { cmgTrapSubsystem, cmgTrapOnBoard, cmgTrapLocation, cmgHardwareFaultMask, cmgCpuTemp, cmgCpuTempShutdownThresh, cmgDspTemp, cmgDspTempShutdownThresh }
	STATUS      current
	DESCRIPTION
	"The CPU temperature sensor has exceeded its shutdown threshold.
	The system is about to begin controlled shutdown."
	::= { cmgTrapV3separator 14 }

--	There is no Clear trap for Temp Shutdown.  Trap Type 15 is reserved.

cmgMgpPowerFault	NOTIFICATION-TYPE
	OBJECTS   { cmgTrapSubsystem, cmgTrapOnBoard, cmgTrapLocation, cmgHardwareFaultMask, cmgPowerMgProcessor }
	STATUS      current
	DESCRIPTION
	"The voltage reading at the +5.1v power source serving the MG
	Processor is out of tolerance."
	::= { cmgTrapV3separator 16 }

cmgMgpPowerClear	NOTIFICATION-TYPE
	OBJECTS   { cmgTrapSubsystem, cmgTrapOnBoard, cmgTrapLocation, cmgHardwareFaultMask, cmgPowerMgProcessor }
	STATUS      current
	DESCRIPTION
	"The voltage reading at the +5.1v power source serving the MG
	Processor is back within its tolerance range."
	::= { cmgTrapV3separator 17 }

cmgMediaModulePowerFault	NOTIFICATION-TYPE
	OBJECTS   { cmgTrapSubsystem, cmgTrapOnBoard, cmgTrapLocation, cmgHardwareFaultMask, cmgPowerMediaModules }
	STATUS      current
	DESCRIPTION
	"The voltage reading at the -48v power source serving the media modules
	is out of tolerance."
	::= { cmgTrapV3separator 18 }

cmgMediaModulePowerClear	NOTIFICATION-TYPE
	OBJECTS   { cmgTrapSubsystem, cmgTrapOnBoard, cmgTrapLocation, cmgHardwareFaultMask, cmgPowerMediaModules }
	STATUS      current
	DESCRIPTION
	"The voltage reading at the -48v power source serving the media modules
	is back within its tolerance range."
	::= { cmgTrapV3separator 19 }

cmgVoipPowerFault	NOTIFICATION-TYPE
	OBJECTS   { cmgTrapSubsystem, cmgTrapOnBoard, cmgTrapLocation, cmgHardwareFaultMask, cmgPowerVoipComplex }
	STATUS      current
	DESCRIPTION
	"The voltage reading at the +3.4v power source serving the VoIP
	complexes is out of tolerance."
	::= { cmgTrapV3separator 20 }

cmgVoipPowerClear	NOTIFICATION-TYPE
	OBJECTS   { cmgTrapSubsystem, cmgTrapOnBoard, cmgTrapLocation, cmgHardwareFaultMask, cmgPowerVoipComplex }
	STATUS      current
	DESCRIPTION
	"The voltage reading at the +3.4v power source serving the VoIP
	complexes is back within its tolerance range."
	::= { cmgTrapV3separator 21 }

cmgDspPowerFault	NOTIFICATION-TYPE
	OBJECTS   { cmgTrapSubsystem, cmgTrapOnBoard, cmgTrapLocation, cmgHardwareFaultMask, cmgPowerDsp }
	STATUS      current
	DESCRIPTION
	"The voltage reading at the +1.58v power source serving the DSP units
	is out of tolerance."
	::= { cmgTrapV3separator 22 }

cmgDspPowerClear	NOTIFICATION-TYPE
	OBJECTS   { cmgTrapSubsystem, cmgTrapOnBoard, cmgTrapLocation, cmgHardwareFaultMask, cmgPowerDsp }
	STATUS      current
	DESCRIPTION
	"The voltage reading at the +1.58v power source serving the DSP units
	is back within its tolerance range."
	::= { cmgTrapV3separator 23 }

cmg8260PowerFault		NOTIFICATION-TYPE
	OBJECTS   { cmgTrapSubsystem, cmgTrapOnBoard, cmgTrapLocation, cmgHardwareFaultMask, cmgPower8260 }
	STATUS      current
	DESCRIPTION
	"The voltage reading at the +2.5v power source serving the 8260
	processor is out of tolerance."
	::= { cmgTrapV3separator 24 }

cmg8260PowerClear		NOTIFICATION-TYPE
	OBJECTS   { cmgTrapSubsystem, cmgTrapOnBoard, cmgTrapLocation, cmgHardwareFaultMask, cmgPower8260 }
	STATUS      current
	DESCRIPTION
	"The voltage reading at the +2.5v power source serving the 8260
	processor is back within its tolerance range."
	::= { cmgTrapV3separator 25 }

cmgAuxPowerFault		NOTIFICATION-TYPE
	OBJECTS   { cmgTrapSubsystem, cmgTrapOnBoard, cmgTrapLocation, cmgHardwareFaultMask }
	STATUS      current
	DESCRIPTION
	"The voltage reading at the -48v auxiliary power source serving the
	end points is out of tolerance."
	::= { cmgTrapV3separator 26 }

cmgAuxPowerClear		NOTIFICATION-TYPE
	OBJECTS   { cmgTrapSubsystem, cmgTrapOnBoard, cmgTrapLocation, cmgHardwareFaultMask }
	STATUS      current
	DESCRIPTION
	"The voltage reading at the -48v auxiliary power source serving the
	end points is back within its tolerance range."
	::= { cmgTrapV3separator 27 }

cmgFanPowerFault		NOTIFICATION-TYPE
	OBJECTS   { cmgTrapSubsystem, cmgTrapOnBoard, cmgTrapLocation, cmgHardwareFaultMask }
	STATUS      current
	DESCRIPTION
	"The voltage at the +12 auxiliary power source serving the fans is
	out of tolerance."
	::= { cmgTrapV3separator 28 }

cmgFanPowerClear		NOTIFICATION-TYPE
	OBJECTS   { cmgTrapSubsystem, cmgTrapOnBoard, cmgTrapLocation, cmgHardwareFaultMask }
	STATUS      current
	DESCRIPTION
	"The voltage at the +12 auxiliary power source serving the fans is
	back within its tolerance range."
	::= { cmgTrapV3separator 29 }

cmgSyncSignalFault	NOTIFICATION-TYPE
	OBJECTS   { cmgTrapSubsystem, cmgTrapOnBoard, cmgTrapLocation, cmgHardwareFaultMask, cmgPrimaryClockSource, cmgSecondaryClockSource, cmgActiveClockSource }
	STATUS      current
	DESCRIPTION "Synchronization signal lost."
	::= { cmgTrapV3separator 30 }

cmgSyncSignalClear		NOTIFICATION-TYPE
	OBJECTS   { cmgTrapSubsystem, cmgTrapOnBoard, cmgTrapLocation, cmgHardwareFaultMask, cmgPrimaryClockSource, cmgSecondaryClockSource, cmgActiveClockSource }
	STATUS      current
	DESCRIPTION "Synchronization signal normal."
	::= { cmgTrapV3separator 31 }

cmgVoipHardwareFault	NOTIFICATION-TYPE
	OBJECTS   { cmgTrapSubsystem, cmgTrapOnBoard, cmgTrapLocation, cmgVoipFaultMask }
	STATUS      current
	DESCRIPTION
	"One or more of the DSP complexes serving VoIP engines has failed."
	::= { cmgTrapV3separator 32 }

cmgVoipHardwareClear	NOTIFICATION-TYPE
	OBJECTS   { cmgTrapSubsystem, cmgTrapOnBoard, cmgTrapLocation, cmgVoipFaultMask }
	STATUS      current
	DESCRIPTION
	"All the DSP complexes serving VoIP engines are back in service."
	::= { cmgTrapV3separator 33 }

cmgSyncSignalWarn	NOTIFICATION-TYPE
	OBJECTS   { cmgTrapSubsystem, cmgTrapOnBoard, cmgTrapLocation, cmgHardwareFaultMask, cmgPrimaryClockSource, cmgSecondaryClockSource, cmgActiveClockSource }
	STATUS      current
	DESCRIPTION "Synchronization signal lost."
	::= { cmgTrapV3separator 34 }

cmgSyncWarnClear		NOTIFICATION-TYPE
	OBJECTS   { cmgTrapSubsystem, cmgTrapOnBoard, cmgTrapLocation, cmgHardwareFaultMask, cmgPrimaryClockSource, cmgSecondaryClockSource, cmgActiveClockSource }
	STATUS      current
	DESCRIPTION "Synchronization signal normal."
	::= { cmgTrapV3separator 35 }

cmgSyncSignalExcess	NOTIFICATION-TYPE
	OBJECTS   { cmgTrapSubsystem, cmgTrapOnBoard, cmgTrapLocation, cmgHardwareFaultMask, cmgPrimaryClockSource, cmgSecondaryClockSource, cmgActiveClockSource }
	STATUS      current
	DESCRIPTION "The synchronization signal source (primary or secondary) is experiencing excessive failures in a short period of time causing excessive switching to an alternate source."
	::= { cmgTrapV3separator 36 }

cmgSyncExcessClear		NOTIFICATION-TYPE
	OBJECTS   { cmgTrapSubsystem, cmgTrapOnBoard, cmgTrapLocation, cmgHardwareFaultMask, cmgPrimaryClockSource, cmgSecondaryClockSource, cmgActiveClockSource }
	STATUS      current
	DESCRIPTION "Synchronization signal source which was causing excessive switching due to excessive failures is now normal."
	::= { cmgTrapV3separator 37 }


--
--  Configuration Change traps
--

cmgModuleRemove		NOTIFICATION-TYPE
	OBJECTS   { cmgTrapSubsystem, cmgTrapOnBoard, cmgTrapLocation, cmgTrapModule }
	STATUS      current
	DESCRIPTION "A media module has been removed."
	::= { cmgTrapV3separator 50 }

--	There is no Clear trap for Module Remove.  Trap Type 51 is reserved.

cmgModuleInsertFault		NOTIFICATION-TYPE
	OBJECTS   { cmgTrapSubsystem, cmgTrapOnBoard, cmgTrapLocation, cmgModuleFaultMask, cmgTrapModule }
	STATUS      current
	DESCRIPTION "Media module insertion sequence has failed."
	::= { cmgTrapV3separator 52 }

cmgModuleInsertSuccess		NOTIFICATION-TYPE
	OBJECTS   { cmgTrapSubsystem, cmgTrapOnBoard, cmgTrapLocation, cmgTrapModule }
	STATUS      current
	DESCRIPTION "A media module has been inserted."
	::= { cmgTrapV3separator 53 }

cmgMgBusyout		NOTIFICATION-TYPE
	OBJECTS   { cmgTrapSubsystem, cmgTrapOnBoard, cmgTrapLocation }
	STATUS      current
	DESCRIPTION
	"An administrator has moved a media module or port to
	the busy-out state."
	::= { cmgTrapV3separator 54 }

cmgMgRelease		NOTIFICATION-TYPE
	OBJECTS   { cmgTrapSubsystem, cmgTrapOnBoard, cmgTrapLocation }
	STATUS      current
	DESCRIPTION
	"An administrator has moved a media module or port from the
	busy-out state back into service."
	::= { cmgTrapV3separator 55 }

cmgUnsupportedMmEnrolement		NOTIFICATION-TYPE
	OBJECTS   { cmgTrapSubsystem, cmgTrapOnBoard, cmgTrapLocation, cmgModuleSlot, cmgModuleType, cmgModuleName}
	STATUS      current
	DESCRIPTION
	"The event is sent when a module is inserted to a slot where it can be identified 
	but not supported due to hardware limitations."
	::= { cmgTrapV3separator 56 }

cmgDataModuleAwohConflict		NOTIFICATION-TYPE
	OBJECTS   { cmgTrapSubsystem, cmgTrapOnBoard, cmgTrapLocation, cmgModuleSlot, cmgModuleType, cmgModuleName}
	STATUS      current
	DESCRIPTION
	"This event is generated when a data module is found in a slot that was Administered
	without hardware as a voice module in the call controller."
	::= { cmgTrapV3separator 57 }

--
--  Normal Operations traps
--

cmgFirmwareDownloadBegun	NOTIFICATION-TYPE
	OBJECTS   { cmgTrapSubsystem, cmgTrapOnBoard, cmgTrapLocation, genAppFileId, genAppFileName, genAppFileVersionNumber, cmgProductId, cmgTrapSeverity } 
	STATUS      current
	DESCRIPTION
	"The media gateway has begun download of a software module."
	::= { cmgTrapV3separator 70 }

cmgFirmwareDownloadSuccess	NOTIFICATION-TYPE
	OBJECTS   { cmgTrapSubsystem, cmgTrapOnBoard, cmgTrapLocation, genAppFileId, genAppFileName, genAppFileVersionNumber } 
	STATUS      current
	DESCRIPTION
	"The media gateway has completed successful download of a software module."
	::= { cmgTrapV3separator 71 }

--	The Registration Fault trap is among the Application Fault traps.
--	Trap Type 72 is reserved.

cmgRegistrationSuccess		NOTIFICATION-TYPE
	OBJECTS   { cmgTrapSubsystem, cmgTrapOnBoard, cmgTrapLocation, cmgActiveControllerAddress }
	STATUS      current
	DESCRIPTION
	"The media gateway has successfully registered with a controller."
	::= { cmgTrapV3separator 73 }

cmgMgManualReset		NOTIFICATION-TYPE
	OBJECTS   { cmgTrapSubsystem, cmgTrapOnBoard, cmgTrapLocation }
	STATUS      current
	DESCRIPTION
	"The media gateway is beginning a user-requested reset operation."
	::= { cmgTrapV3separator 74 }

cmgModuleManualReset		NOTIFICATION-TYPE
	OBJECTS   { cmgTrapSubsystem, cmgTrapOnBoard, cmgTrapLocation }
	STATUS      current
	DESCRIPTION
	"A media module is beginning a user-requested reset operation."
	::= { cmgTrapV3separator 75 }

cmgVoipManualReset		NOTIFICATION-TYPE
	OBJECTS   { cmgTrapSubsystem, cmgTrapOnBoard, cmgTrapLocation }
	STATUS      current
	DESCRIPTION
	"A VoIP engine is beginning a user-requested reset operation."
	::= { cmgTrapV3separator 76 }

cmgDsuManualReset		NOTIFICATION-TYPE
	OBJECTS   { cmgTrapSubsystem, cmgTrapOnBoard, cmgTrapLocation }
	STATUS      obsolete
	DESCRIPTION
	"An E1/T1 DSU is beginning a user-requested reset operation."
	::= { cmgTrapV3separator 77 }

cmgConfigUploadBegun	NOTIFICATION-TYPE
	OBJECTS   { cmgTrapSubsystem, cmgTrapOnBoard, cmgTrapLocation } 
	STATUS      current
	DESCRIPTION
	"The media gateway has begun upload of a configuration file."
	::= { cmgTrapV3separator 78 }

cmgConfigUploadSuccess	NOTIFICATION-TYPE
	OBJECTS   { cmgTrapSubsystem, cmgTrapOnBoard, cmgTrapLocation } 
	STATUS      current
	DESCRIPTION
	"The media gateway has completed successful upload of a configuration file."
	::= { cmgTrapV3separator 79 }


--
--  Application Fault traps
--

cmgMemoryFault		NOTIFICATION-TYPE
	OBJECTS   { cmgTrapSubsystem, cmgTrapOnBoard, cmgTrapLocation, cmgMgpFaultMask }
	STATUS      current
	DESCRIPTION "Main processor memory has issued a failure warning."
	::= { cmgTrapV3separator 90 }

cmgMemoryClear		NOTIFICATION-TYPE
	OBJECTS   { cmgTrapSubsystem, cmgTrapOnBoard, cmgTrapLocation, cmgMgpFaultMask }
	STATUS      current
	DESCRIPTION "Main processor memory is back in normal service."
	::= { cmgTrapV3separator 91 }

cmgDhcpRequestFault		NOTIFICATION-TYPE
	OBJECTS   { cmgTrapSubsystem, cmgTrapOnBoard, cmgTrapLocation, cmgMgpFaultMask }
	STATUS      current
	DESCRIPTION
	"The media gateway cannot contact its DHCP server, or the server
	failed to respond to a request."
	::= { cmgTrapV3separator 92 }

cmgDhcpRequestClear		NOTIFICATION-TYPE
	OBJECTS   { cmgTrapSubsystem, cmgTrapOnBoard, cmgTrapLocation, cmgMgpFaultMask }
	STATUS      current
	DESCRIPTION
	"The media gateway has received a successful response to a DHCP request."
	::= { cmgTrapV3separator 93 }

cmgFirmwareDownloadFault	NOTIFICATION-TYPE
	OBJECTS   { cmgTrapSubsystem, cmgTrapOnBoard, cmgTrapLocation, cmgMgpFaultMask, genAppFileId, genAppFileName, genAppFileVersionNumber, genOpLastFailureIndex }
	STATUS      current
	DESCRIPTION
	"An attempt to download a software module has failed."
	::= { cmgTrapV3separator 94 }

cmgFirmwareDownloadWarning	NOTIFICATION-TYPE  
        OBJECTS   { cmgTrapSubsystem, cmgTrapOnBoard, cmgTrapLocation,genAppFileId, genAppFileName, genAppFileVersionNumber, genOpLastWarningDisplay}	
        STATUS      current	
        DESCRIPTION	
        "Non critical event occur during attempt to download a software module."	
        ::= { cmgTrapTypes 95 }

cmgProcessRestart		NOTIFICATION-TYPE
	OBJECTS   { cmgTrapSubsystem, cmgTrapOnBoard, cmgTrapLocation, cmgMgpFaultMask }
	STATUS      current
	DESCRIPTION
	"One or more media gateway software processes have terminated and
	been restarted by the software task manager."
	::= { cmgTrapV3separator 96 }

cmgProcessRestartClear		NOTIFICATION-TYPE
	OBJECTS   { cmgTrapSubsystem, cmgTrapOnBoard, cmgTrapLocation, cmgMgpFaultMask }
	STATUS      current
	DESCRIPTION
	"Media gateway software processes are running normally."
	::= { cmgTrapV3separator 97 }

cmgIccMissingFault		NOTIFICATION-TYPE
	OBJECTS   { cmgTrapSubsystem, cmgTrapOnBoard, cmgTrapLocation, cmgMgpFaultMask }
	STATUS      current
	DESCRIPTION
	"An Internal Communications Controller expected in slot 1 is missing."
	::= { cmgTrapV3separator 98 }

cmgIccMissingClear		NOTIFICATION-TYPE
	OBJECTS   { cmgTrapSubsystem, cmgTrapOnBoard, cmgTrapLocation, cmgMgpFaultMask }
	STATUS      current
	DESCRIPTION
	"The Internal Communications Controller expected in slot 1 is present."
	::= { cmgTrapV3separator 99 }

cmgIccAutoReset		NOTIFICATION-TYPE
	OBJECTS   { cmgTrapSubsystem, cmgTrapOnBoard, cmgTrapLocation, cmgMgpFaultMask }
	STATUS      current
	DESCRIPTION
	"The Media gateway has automatically reset the Internal
	Communications Controller."
	::= { cmgTrapV3separator 100 }

cmgIccAutoResetClear		NOTIFICATION-TYPE
	OBJECTS   { cmgTrapSubsystem, cmgTrapOnBoard, cmgTrapLocation, cmgMgpFaultMask }
	STATUS      current
	DESCRIPTION
	"The Internal Communications Controller is running normally."
	::= { cmgTrapV3separator 101 }

cmgPrimaryControllerFault	NOTIFICATION-TYPE
	OBJECTS   { cmgTrapSubsystem, cmgTrapOnBoard, cmgTrapLocation, cmgMgpFaultMask, cmgUseDhcpForMgcList }
	STATUS      current
	DESCRIPTION
	"The media gateway cannot contact the first controller
	in its controller list."
	::= { cmgTrapV3separator 102 }

cmgPrimaryControllerClear	NOTIFICATION-TYPE
	OBJECTS   { cmgTrapSubsystem, cmgTrapOnBoard, cmgTrapLocation, cmgMgpFaultMask, cmgUseDhcpForMgcList }
	STATUS      current
	DESCRIPTION
	"The media gateway has successfully contacted the first controller
	in its controller list."
	::= { cmgTrapV3separator 103 }

cmgNoControllerFault		NOTIFICATION-TYPE
	OBJECTS   { cmgTrapSubsystem, cmgTrapOnBoard, cmgTrapLocation, cmgMgpFaultMask, cmgUseDhcpForMgcList }
	STATUS      current
	DESCRIPTION
	"The media gateway cannot contact any controller in its controller lists."
	::= { cmgTrapV3separator 104 }

cmgNoControllerClear		NOTIFICATION-TYPE
	OBJECTS   { cmgTrapSubsystem, cmgTrapOnBoard, cmgTrapLocation, cmgMgpFaultMask, cmgUseDhcpForMgcList }
	STATUS      current
	DESCRIPTION
	"The media gateway has successfully contacted one of the controllers
	in its controller lists."
	::= { cmgTrapV3separator 105 }

cmgRegistrationFault		NOTIFICATION-TYPE
	OBJECTS   { cmgTrapSubsystem, cmgTrapOnBoard, cmgTrapLocation, cmgMgpFaultMask, cmgActiveControllerAddress }
	STATUS      current
	DESCRIPTION
	"The media gateway cannot register with any controller
	in its controller list."
	::= { cmgTrapV3separator 106 }

--	The Clear trap for Registration Fault is Registration Success,
--	among the Normal Operations Traps.  Trap Type 107 is reserved.

cmgH248LinkDown			NOTIFICATION-TYPE
	OBJECTS   { cmgTrapSubsystem, cmgTrapOnBoard, cmgTrapLocation, cmgMgpFaultMask }
	STATUS      current
	DESCRIPTION
	"The H.248 link between the media gateway and its controller is down."
	::= { cmgTrapV3separator 108 }

cmgH248LinkUp			NOTIFICATION-TYPE
	OBJECTS   { cmgTrapSubsystem, cmgTrapOnBoard, cmgTrapLocation, cmgMgpFaultMask }
	STATUS      current
	DESCRIPTION
	"The H.248 link between the media gateway and its controller
	is back in service."
	::= { cmgTrapV3separator 109 }

cmgTestFault			NOTIFICATION-TYPE
	OBJECTS   { cmgTrapSubsystem, cmgTrapOnBoard, cmgTrapLocation, cmgMgpFaultMask }
	STATUS      current
	DESCRIPTION "A maintenance test has failed."
	::= { cmgTrapV3separator 110 }

cmgTestClear			NOTIFICATION-TYPE
	OBJECTS   { cmgTrapSubsystem, cmgTrapOnBoard, cmgTrapLocation, cmgMgpFaultMask }
	STATUS      current
	DESCRIPTION "Failed maintenance tests have succeeded."
	::= { cmgTrapV3separator 111 }

cmgTestThresholdFault			NOTIFICATION-TYPE
	OBJECTS   { cmgTrapSubsystem, cmgTrapOnBoard, cmgTrapLocation, cmgMgpFaultMask }
	STATUS      current
	DESCRIPTION "Maintenance test failure count has exceeded its
	reporting threshold."
	::= { cmgTrapV3separator 112 }

cmgTestThresholdClear			NOTIFICATION-TYPE
	OBJECTS   { cmgTrapSubsystem, cmgTrapOnBoard, cmgTrapLocation, cmgMgpFaultMask }
	STATUS      current
	DESCRIPTION "Maintenance test failure count has dropped below
	its reporting threshold."
	::= { cmgTrapV3separator 113 }

cmgMgAutoReset			NOTIFICATION-TYPE
	OBJECTS   { cmgTrapSubsystem, cmgTrapOnBoard, cmgTrapLocation, cmgMgpFaultMask }
	STATUS      current
	DESCRIPTION
	"The media gateway is beginning automatic reinitialization."
	::= { cmgTrapV3separator 114 }

--	There is no Clear trap for MG Auto Reset.  Trap Type 115 is reserved.

cmgModuleAutoReset		NOTIFICATION-TYPE
	OBJECTS   { cmgTrapSubsystem, cmgTrapOnBoard, cmgTrapLocation, cmgModuleFaultMask }
	STATUS      current
	DESCRIPTION
	"One of the media modules is beginning automatic reinitialization."
	::= { cmgTrapV3separator 116 }

cmgModuleAutoResetClear		NOTIFICATION-TYPE
	OBJECTS   { cmgTrapSubsystem, cmgTrapOnBoard, cmgTrapLocation, cmgModuleFaultMask }
	STATUS      current
	DESCRIPTION
	"The reset media module is running normally."
	::= { cmgTrapV3separator 117 }

cmgModulePostFault		NOTIFICATION-TYPE
	OBJECTS   { cmgTrapSubsystem, cmgTrapOnBoard, cmgTrapLocation, cmgModuleFaultMask }
	STATUS      current
	DESCRIPTION
	"A media module has failed its power-on startup test."
	::= { cmgTrapV3separator 118 }

cmgModulePostClear		NOTIFICATION-TYPE
	OBJECTS   { cmgTrapSubsystem, cmgTrapOnBoard, cmgTrapLocation, cmgModuleFaultMask }
	STATUS      current
	DESCRIPTION
	"Media module power-on startup test successful."
	::= { cmgTrapV3separator 119 }

cmgModuleParameterFault		NOTIFICATION-TYPE
	OBJECTS   { cmgTrapSubsystem, cmgTrapOnBoard, cmgTrapLocation, cmgModuleFaultMask }
	STATUS      current
	DESCRIPTION
	"A media module has failed its parameter exchange."
	::= { cmgTrapV3separator 120 }

cmgModuleParameterClear		NOTIFICATION-TYPE
	OBJECTS   { cmgTrapSubsystem, cmgTrapOnBoard, cmgTrapLocation, cmgModuleFaultMask }
	STATUS      current
	DESCRIPTION
	"Media module parameter exchange successful."
	::= { cmgTrapV3separator 121 }

cmgConfigUploadFault	NOTIFICATION-TYPE
	OBJECTS   { cmgTrapSubsystem, cmgTrapOnBoard, cmgTrapLocation, cmgMgpFaultMask, genOpLastFailureIndex }
	STATUS      current
	DESCRIPTION
	"An attempt to upload a configuration file has failed."
	::= { cmgTrapV3separator 122 }

--	The Clear trap for Configuration Upload Fault is Configuration Upload
--	Success, among the Normal Operations Traps.  Trap Type 123 is reserved.


cmgVoipOccFault		NOTIFICATION-TYPE
	OBJECTS   { cmgTrapSubsystem, cmgTrapOnBoard, cmgTrapLocation, cmgVoipFaultMask, cmgVoipChannelsInUse, cmgVoipTotalChannels }
	STATUS      current
	DESCRIPTION
	"One or more of the VoIP engines in the media gateway is over
	its occupancy threshold, as measured by a snapshot:
	(Channels In Use)/(Total Channels)."
	::= { cmgTrapV3separator 124 }

cmgVoipOccClear		NOTIFICATION-TYPE
	OBJECTS   { cmgTrapSubsystem, cmgTrapOnBoard, cmgTrapLocation, cmgVoipFaultMask, cmgVoipChannelsInUse, cmgVoipTotalChannels }
	STATUS      current
	DESCRIPTION
	"All the VoIP engines in the media gateway are operating below
	occupancy threshold, as measured by a snapshot:
	(Channels In Use)/(Total Channels)."
	::= { cmgTrapV3separator 125 }

cmgVoipAvgOccFault	NOTIFICATION-TYPE
	OBJECTS   { cmgTrapSubsystem, cmgTrapOnBoard, cmgTrapLocation, cmgVoipFaultMask, cmgVoipAverageOccupancy }
	STATUS      current
	DESCRIPTION
	"One or more of the VoIP engines in the media gateway is over
	its average occupancy threshold."
	::= { cmgTrapV3separator 126 }

cmgVoipAvgOccClear	NOTIFICATION-TYPE
	OBJECTS   { cmgTrapSubsystem, cmgTrapOnBoard, cmgTrapLocation, cmgVoipFaultMask, cmgVoipAverageOccupancy }
	STATUS      current
	DESCRIPTION
	"All the VoIP engines in the media gateway are operating below
	occupancy threshold, as measured by a snapshot:
	(Channels In Use)/(Total Channels)."
	::= { cmgTrapV3separator 127 }


cmgVoipAutoReset	NOTIFICATION-TYPE
	OBJECTS   { cmgTrapSubsystem, cmgTrapOnBoard, cmgTrapLocation, cmgVoipFaultMask }
	STATUS      current
	DESCRIPTION "A VoIP engine has begun automatic reset."
	::= { cmgTrapV3separator 128 }

cmgVoipAutoResetClear	NOTIFICATION-TYPE
	OBJECTS   { cmgTrapSubsystem, cmgTrapOnBoard, cmgTrapLocation, cmgVoipFaultMask }
	STATUS      current
	DESCRIPTION
	"A VoIP engine has completed automatic reset, and is running normally."
	::= { cmgTrapV3separator 129 }

cmgDsuFpgaConfigureFault	NOTIFICATION-TYPE
	OBJECTS   { cmgTrapSubsystem, cmgTrapOnBoard, cmgTrapLocation }
	STATUS      obsolete
	DESCRIPTION
	"The DSU in one of the E1/T1 media modules failed to
	configure its Field Programmable Gateway Array."
	::= { cmgTrapV3separator 130 }

cmgDsuFpgaConfigureClear	NOTIFICATION-TYPE
	OBJECTS   { cmgTrapSubsystem, cmgTrapOnBoard, cmgTrapLocation }
	STATUS      obsolete
	DESCRIPTION
	"The DSU in one of the E1/T1 media modules has successfully
	configured its Field Programmable Gateway Array."
	::= { cmgTrapV3separator 131 }

cmgDsuAutoReset	NOTIFICATION-TYPE
	OBJECTS   { cmgTrapSubsystem, cmgTrapOnBoard, cmgTrapLocation }
	STATUS      obsolete
	DESCRIPTION
	"A DSU in one of the E1/T1 media modules has begun automatic reset."
	::= { cmgTrapV3separator 132 }

cmgDsuAutoResetClear	NOTIFICATION-TYPE
	OBJECTS   { cmgTrapSubsystem, cmgTrapOnBoard, cmgTrapLocation }
	STATUS      obsolete
	DESCRIPTION
	"A DSU in one of the E1/T1 media modules has completed automatic
	reset, and is running normally."
	::= { cmgTrapV3separator 133 }

cmgDsuDteDtrFault	NOTIFICATION-TYPE
	OBJECTS   { cmgTrapSubsystem, cmgTrapOnBoard, cmgTrapLocation }
	STATUS      obsolete
	DESCRIPTION
	"One of the E1/T1 media modules has detected that the DTR signal from
	its DTE is off.  This indicates that the DTE is not connected or not
	functioning."
	::= { cmgTrapV3separator 134 }

cmgDsuDteDtrClear	NOTIFICATION-TYPE
	OBJECTS   { cmgTrapSubsystem, cmgTrapOnBoard, cmgTrapLocation }
	STATUS      obsolete
	DESCRIPTION
	"One of the E1/T1 media modules has detected that the DTR signal from
	its DTE is back to normal."
	::= { cmgTrapV3separator 135 }

cmgDsuDteRtsFault		NOTIFICATION-TYPE
	OBJECTS   { cmgTrapSubsystem, cmgTrapOnBoard, cmgTrapLocation }
	STATUS      obsolete
	DESCRIPTION
	"An E1/T1 media module has detected that the RTS signal from its
	DTE is not on whenever the DTE requests to send data and during
	data transfer.  This indicates that the DTE is not functioning."
	::= { cmgTrapV3separator 136 }

cmgDsuDteRtsClear		NOTIFICATION-TYPE
	OBJECTS   { cmgTrapSubsystem, cmgTrapOnBoard, cmgTrapLocation }
	STATUS      obsolete
	DESCRIPTION
	"An E1/T1 media module has detected that the RTS signal from its
	DTE is back to normal."
	::= { cmgTrapV3separator 137 }

cmgDsuTxDFault		NOTIFICATION-TYPE
	OBJECTS   { cmgTrapSubsystem, cmgTrapOnBoard, cmgTrapLocation }
	STATUS      obsolete
	DESCRIPTION
	"An E1/T1 media module has detected that the data received from the
	local DTE to be sent to the far end is either all ones or all zeroes."
	::= { cmgTrapV3separator 138 }

cmgDsuTxDClear			NOTIFICATION-TYPE
	OBJECTS   { cmgTrapSubsystem, cmgTrapOnBoard, cmgTrapLocation }
	STATUS      obsolete
	DESCRIPTION
	"The E1/T1 media module is receiving normal data from the local
	DTE to be sent to the far end."
	::= { cmgTrapV3separator 139 }

cmgDsuRxDFailure		NOTIFICATION-TYPE
	OBJECTS   { cmgTrapSubsystem, cmgTrapOnBoard, cmgTrapLocation }
	STATUS      obsolete
	DESCRIPTION
	"An E1/T1 media module has detected that the data received from the
	far end to be sent to the local DTE is either all ones or all zeroes."
	::= { cmgTrapV3separator 140 }

cmgDsuRxDClear			NOTIFICATION-TYPE
	OBJECTS   { cmgTrapSubsystem, cmgTrapOnBoard, cmgTrapLocation }
	STATUS      obsolete
	DESCRIPTION
	"The E1/T1 media module is receiving normal data from the far end
	to be sent to the local DTE."
	::= { cmgTrapV3separator 141 }

cmgVoipIpConfigFault		NOTIFICATION-TYPE
	OBJECTS   { cmgTrapSubsystem, cmgTrapOnBoard, cmgTrapLocation, cmgVoipFaultMask, cmgVoipCurrentIpAddress }
	STATUS      current
	DESCRIPTION
	"There is an IP configuration failure in the VoIP Engine.
	No static IP address has been supplied or the firmware is getting 
	indications that this is a duplicate IP address."
	::= { cmgTrapV3separator 142 }

cmgVoipIpConfigClear		NOTIFICATION-TYPE
	OBJECTS   { cmgTrapSubsystem, cmgTrapOnBoard, cmgTrapLocation, cmgVoipFaultMask, cmgVoipCurrentIpAddress }
	STATUS      current
	DESCRIPTION
	"The IP configuration of the VoIP Engine is successful."
	::= { cmgTrapV3separator 143 }
                                            
cmgConfigDownloadFault	NOTIFICATION-TYPE
	OBJECTS   { cmgTrapSubsystem, cmgTrapOnBoard, cmgTrapLocation, cmgMgpFaultMask, genOpLastFailureIndex }
	STATUS      current
	DESCRIPTION
	"An attempt to download a configuration file has failed."
	::= { cmgTrapV3separator 144 }

--	The Clear trap for Configuration Download Fault is Configuration Download
--  Success, among the Normal Operations Traps.
                                                   
cmgConfigDownloadBegun	NOTIFICATION-TYPE
	OBJECTS   { cmgTrapSubsystem, cmgTrapOnBoard, cmgTrapLocation } 
	STATUS      current
	DESCRIPTION
	"The media gateway has begun download of a configuration file."
	::= { cmgTrapV3separator 145 }

cmgConfigDownloadSuccess	NOTIFICATION-TYPE
	OBJECTS   { cmgTrapSubsystem, cmgTrapOnBoard, cmgTrapLocation } 
	STATUS      current
	DESCRIPTION
	"The media gateway has completed successful download of a configuration file."
	::= { cmgTrapV3separator 146 }
                                                   
cmgTimeslotOccupancyFault        NOTIFICATION-TYPE
       OBJECTS   { cmgTrapSubsystem, cmgTrapOnBoard, cmgTrapLocation, cmgTrapAvailableTimeslots, cmgTrapInUseTimeslots }
       STATUS      current
       DESCRIPTION
       "Timeslot usage is over the occupancy threshold,
       as measured by a snapshot:
       (Timeslots In Use)/(Total Timeslots)."
       ::= { cmgTrapV3separator 147 }
 
cmgTimeslotOccupancyClear        NOTIFICATION-TYPE
       OBJECTS   { cmgTrapSubsystem, cmgTrapOnBoard, cmgTrapLocation, cmgTrapAvailableTimeslots, cmgTrapInUseTimeslots}
       STATUS      current
       DESCRIPTION
       "Timeslot usage is below the occupancy threshold,
       as measured by a snapshot:
       (Timeslots In Use)/(Total Timeslots)."
       ::= { cmgTrapV3separator 148 }
 
cmgTimeslotAvailabilityFault             NOTIFICATION-TYPE
       OBJECTS   { cmgTrapSubsystem, cmgTrapOnBoard, cmgTrapLocation, cmgTrapAvailableTimeslots, cmgTrapInUseTimeslots }
       STATUS      current
       DESCRIPTION
       "No more Timeslot are available on this gateway."
       ::= { cmgTrapV3separator 149 }
 
cmgTimeslotAvailabilityClear             NOTIFICATION-TYPE
       OBJECTS   { cmgTrapSubsystem, cmgTrapOnBoard, cmgTrapLocation, cmgTrapAvailableTimeslots, cmgTrapInUseTimeslots}
       STATUS      current
       DESCRIPTION
       "Timeslots are again available on this gateway,
       usage is below the occupancy threshold,
       as measured by a snapshot:
       (Timeslots In Use)/(Total Timeslots)."
       ::= { cmgTrapV3separator 150 }
                                                   
                                                   
-- ************************************************************************* --

		-- 1.3.6.1.4.1.6889.1.2.9.1.6.1
		cmgContactClosuresTable OBJECT-TYPE
			SYNTAX SEQUENCE OF CmgContactClosuresEntry
			MAX-ACCESS not-accessible
			STATUS current   
			DESCRIPTION
			"
			This table is used for managing contact closure adjunct port. 
			The adjunct box contains two relays.			
			"
			::= { cmgContactClosures 1 }
		
		-- 1.3.6.1.4.1.6889.1.2.9.1.6.1.1
		cmgContactClosuresEntry OBJECT-TYPE
			SYNTAX CmgContactClosuresEntry
			MAX-ACCESS not-accessible
			STATUS current 
			DESCRIPTION ""
			INDEX { cmgCcModule, cmgCcPort, cmgCcRelay }
			::= { cmgContactClosuresTable 1 }
		
		CmgContactClosuresEntry ::=
			SEQUENCE { 
				cmgCcModule		INTEGER,
				cmgCcPort		INTEGER,
				cmgCcRelay		INTEGER,
				cmgCcAdminState	INTEGER,
				cmgCcPulseDuration	INTEGER,
				cmgCcStatus		INTEGER
			 }

		-- 1.3.6.1.4.1.6889.1.2.9.1.6.1.1.1
		cmgCcModule OBJECT-TYPE
			SYNTAX INTEGER   (10)
			MAX-ACCESS read-only
			STATUS current
			DESCRIPTION ""
			::= { cmgContactClosuresEntry 1 }

		-- 1.3.6.1.4.1.6889.1.2.9.1.6.1.1.2
		cmgCcPort OBJECT-TYPE 
			SYNTAX INTEGER  (1)
			MAX-ACCESS read-only
			STATUS current
			DESCRIPTION ""
			::= { cmgContactClosuresEntry 2 }

		-- 1.3.6.1.4.1.6889.1.2.9.1.6.1.1.3
		cmgCcRelay OBJECT-TYPE
			SYNTAX INTEGER  (1..2)
			MAX-ACCESS read-only
			STATUS current
			DESCRIPTION "Each contact closure port can control two relays on the adjunct"
			::= { cmgContactClosuresEntry 3 }
		
		-- 1.3.6.1.4.1.6889.1.2.9.1.6.1.1.4
		cmgCcAdminState OBJECT-TYPE
			SYNTAX INTEGER {
 			auto(1),
			manualTrigger(2),
			manualOff(3)
			}
			MAX-ACCESS read-write
			STATUS current
			DESCRIPTION
			"
			The admin state of the contact-closure where:
			Auto(1): The Contact Closure is controlled by the call
                     Controller.
			Trigger(2): The contact closure relay is triggered.
			Off(3): The contact closure relay is off (not triggered). 
			"         
			DEFVAL { auto }
			::= { cmgContactClosuresEntry 4 }
		
		-- 1.3.6.1.4.1.6889.1.2.9.1.6.1.1.5
		cmgCcPulseDuration OBJECT-TYPE
			SYNTAX INTEGER (1..100)
			MAX-ACCESS read-write
			STATUS current
			DESCRIPTION "
			The number of second the relay is triggred after each pulse activation
			signal is received from the call-controller. 			
			"
			DEFVAL { 3 }
			::= { cmgContactClosuresEntry 5 }
		
		-- 1.3.6.1.4.1.6889.1.2.9.1.6.1.1.6
		cmgCcStatus OBJECT-TYPE
			SYNTAX INTEGER
				{
				triggered(1),
				off(2)
				}
			MAX-ACCESS read-only
			STATUS current
			DESCRIPTION "
			The actual contact closure relay state
			"
			::= { cmgContactClosuresEntry 6 }
		
		
		-- 1.3.6.1.4.1.6889.1.2.9.1.7.1
		cmgETRTable OBJECT-TYPE
			SYNTAX SEQUENCE OF CmgETREntry
			MAX-ACCESS not-accessible
			STATUS current
			DESCRIPTION 
                  "Emergency Transfer Function Table (short circuit             
                   Line and Trunk ports in case of call-controller connectivity
                   problems)"
			::= { cmgETR 1 }
		
		-- 1.3.6.1.4.1.6889.1.2.9.1.7.1.1
		cmgETREntry OBJECT-TYPE
			SYNTAX CmgETREntry
			MAX-ACCESS not-accessible
			STATUS current   
			DESCRIPTION ""
			INDEX { cmgEtrModule }
			::= { cmgETRTable 1 }
		
		CmgETREntry ::=	SEQUENCE { 
				cmgEtrModule	INTEGER,
				cmgEtrAdminState	INTEGER,
				cmgEtrNumberOfPairs		INTEGER,
				cmgEtrStatus			INTEGER,
				cmgEtrCurrentLoopDetect		OCTET STRING	
			 }

		-- 1.3.6.1.4.1.6889.1.2.9.1.7.1.1.1
		cmgEtrModule OBJECT-TYPE
			SYNTAX INTEGER (1..10)
			MAX-ACCESS read-only
			STATUS current     
			DESCRIPTION "Module number - 10 on G450"
			::= { cmgETREntry 1 }
		
		-- 1.3.6.1.4.1.6889.1.2.9.1.7.1.1.2
		cmgEtrAdminState OBJECT-TYPE
			SYNTAX INTEGER
				{
				auto(1),
				on(2),   
				off(3)
				}			
			MAX-ACCESS read-write			
			STATUS current 			
			DESCRIPTION 
			"Module's ETR administration state where:
			   off(1): ETR is turned off without checking if there
			      is an active call among trunk-line port pairs
			   
			   auto(2): ETR is turned off as soon as the module is
			      operational (controlled  by a call controller) 

                           on(3): ETR is never turned off"        
			DEFVAL { auto }
			::= { cmgETREntry 2 }
		
		-- 1.3.6.1.4.1.6889.1.2.9.1.7.1.1.3			
			cmgEtrNumberOfPairs  OBJECT-TYPE
			SYNTAX INTEGER (1..2)
			MAX-ACCESS read-only
			STATUS current 			
			DESCRIPTION 
			"The number of ETR TRUNK-LINE pairs"        
			DEFVAL { 1 }
			::= { cmgETREntry 3 }
			
		
		-- 1.3.6.1.4.1.6889.1.2.9.1.7.1.1.4
		cmgEtrStatus OBJECT-TYPE
			SYNTAX INTEGER
				{
				on(1),
				off(2)
				}			

			MAX-ACCESS read-only
			STATUS current
			DESCRIPTION 
			"The current status of the ETR function"
			::= { cmgETREntry 4 }
		
		-- 1.3.6.1.4.1.6889.1.2.9.1.7.1.1.5
		cmgEtrCurrentLoopDetect OBJECT-TYPE			
			SYNTAX      OCTET STRING (SIZE (1))
			MAX-ACCESS read-write
			STATUS current
			DESCRIPTION 
			"Each bit in the bit-mask represents a current-loop-detector of one
			 trunk-line ETR pairs. The bit is set when current is detected"
			::= { cmgETREntry 5 }
--
--  cmgDynamicCAC
--
		-- 1.3.6.1.4.1.6889.1.2.9.1.8.1
		cmgDynCacStatus OBJECT-TYPE
			SYNTAX INTEGER
				{
				active(1),
				notConfigured(2),
				notArmed(3),
				armedNotConfigured(4),
				notSupported(255)				
				}			
			MAX-ACCESS read-only			
			STATUS current 			
			DESCRIPTION 
			"Dynamic CAC status"
			::= { cmgDynamicCAC 1 }
			
          -- 1.3.6.1.4.1.6889.1.2.9.1.8.2  
            cmgDynCacRBBL OBJECT-TYPE
			SYNTAX Integer32
			MAX-ACCESS read-only
			STATUS current 			
			DESCRIPTION 
			"The last Reported BBL value sent to the MGC"        
			::= { cmgDynamicCAC 2 }      
			
	      -- 1.3.6.1.4.1.6889.1.2.9.1.8.3  		
		  cmgDynCacLastUpdate OBJECT-TYPE
			SYNTAX TimeTicks
			MAX-ACCESS read-only
			STATUS current 			
			DESCRIPTION 
			"The last time (sysUpTime) a 'dynamic CAC' event was sent to the MGC"        
			::= { cmgDynamicCAC 3 }      
            
END
