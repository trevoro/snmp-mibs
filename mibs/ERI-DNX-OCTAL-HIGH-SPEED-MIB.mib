ERI-DNX-OCTAL-HIGH-SPEED-MIB DEFINITIONS ::= BEGIN

IMPORTS
	MODULE-IDENTITY, OBJECT-IDENTITY, OBJECT-TYPE, Integer32,
	IpAddress, NOTIFICATION-TYPE
		FROM SNMPv2-SMI
    DisplayString
        FROM SNMPv2-TC
    eriMibs
        FROM ERI-ROOT-SMI
    devices, PortStatus, ConnectionSpeed, FunctionSwitch, 
    LinkPortAddress, LinkCmdStatus, trapSequence, DecisionType
        FROM ERI-DNX-SMC-MIB;

eriDNXOctalHSMIB MODULE-IDENTITY 
      LAST-UPDATED    "200302050000Z"
      ORGANIZATION    "Eastern Research, Inc."
      CONTACT-INFO
                      "Customer Service
                Postal: Eastern Research, Inc.
                        225 Executive Drive
                        Moorestown, NJ 08057
                Phone:  +1-800-337-4374
                Email:  support@erinc.com"
      DESCRIPTION
              "The ERI Enterprise MIB Module for the DNX High Speed ports."

      REVISION        "200302050000Z"
      DESCRIPTION
              "Nevio Poljak - Software Release 15.1
              Added new configurable field for Clock Edge Error control.
              Converted history comments to MODULE-IDENTITY REVISION format."

      REVISION        "200205130000Z"
      DESCRIPTION
              "Nevio Poljak - Software Release 15.0
              Moved IMPORT for eriMibs to ERI-ROOT-SMI and corrected
              description for oHSCfgDsr object."

      REVISION        "200203110000Z"
      DESCRIPTION
              "Nevio Poljak - Software Release 15.0
              Converted to SMIv2 format."

      REVISION        "200108010000Z"
      DESCRIPTION
              "Nevio Poljak - Software Release 12.4
              Added new InService-OOS commands for all links."

      REVISION        "200106250000Z"
      DESCRIPTION
              "Nevio Poljak - Software Release 12.0
              OHS Speed Configuration Object was obsoleted."
              
      REVISION        "200103010000Z"
      DESCRIPTION
              "Initial Release of this MIB. - Nevio Poljak"

  	::= { eriMibs 6 }

-- *************************************************************************
-- The enterprise OID will be { iso(1) org(3) dod(6) internet(1) private(4)
--                              enterprises(1) virent(644) eri(2) dnx (4) 
--                              devices(2), dnxOHS(5) }

-- *************************************************************************
-- The Octal High Speed card is currently controlled via the Config or Diag groups.
-- The Configuration branch is used to perform all High Speed Port Configuration 
-- functions and the Diagnostic branch is used to run Port tests and view 
-- associated Port Statistics. 
-- *************************************************************************

dnxOHS      OBJECT IDENTIFIER   ::= { devices 5}
ohsConfig   OBJECT IDENTIFIER 	::= { dnxOHS 1 }
ohsDiag     OBJECT IDENTIFIER 	::= { dnxOHS 2 }

-- *************************************************************************
-- This table is the Octal High Speed configuration table
-- *************************************************************************

oHSConfigTable OBJECT-TYPE
        SYNTAX SEQUENCE OF OHSConfigEntry
        MAX-ACCESS not-accessible
        STATUS current
        DESCRIPTION
            "This is the Octal High Speed Configuration table which consists
            of an entry for each of the Octal High Speed card's 8 links(ports).
            The total number of entries depends on the number of Octal High Speed 
            cards in the nest. Changes to the Port Configuration must be made
            on a record or row by row basis.  This means that any use of the 
            Set command on writable fields must include the oHSCfgCmdStatus
            field with a value of 'update' as the last variable in the SET PDU."
        ::= { ohsConfig 1 }

oHSConfigEntry OBJECT-TYPE
        SYNTAX OHSConfigEntry
        MAX-ACCESS not-accessible
        STATUS current
        DESCRIPTION
            "The conceptual row of the Octal High Speed Configuration table. 
            A row in this table cannot be added or deleted, only modified
            using the oHSCfgCmdStatus field with a value of 'update' as 
            the last variable in the SET PDU. The oHSCfgCmdStatus field must
            be included as the last variable in a SET PDU for the action to 
            take effect. If the oHSCfgCmdStatus is missing from the SET PDU, 
            the GET RESPONSE will contain the SNMP error status of 'genErr' for 
            and an error index equal to the last variable."
        INDEX { oHSCfgPortAddr }
        ::= { oHSConfigTable 1 }

OHSConfigEntry ::=
        SEQUENCE {
                oHSCfgPortAddr       LinkPortAddress,   -- RO
                oHSCfgResource       Integer32,         -- RO
                oHSCfgPortName       DisplayString,
                oHSCfgStatus         PortStatus,
                oHSCfgMode           INTEGER,
                oHSCfgSpeed          ConnectionSpeed,
                oHSCfgType           INTEGER,
                oHSCfgData           INTEGER,
                oHSCfgClock          INTEGER,
                oHSCfgNetLoop        FunctionSwitch,
                oHSCfgTiming         INTEGER,
                oHSCfgDcd            INTEGER,
                oHSCfgDsr            INTEGER,
                oHSCfgCtsIndication  INTEGER,
                oHSCfgDTELoop        FunctionSwitch,
                oHSCfgCmdStatus      LinkCmdStatus,
                oHSCfgClockEdgeErrs  DecisionType
                }

oHSCfgPortAddr OBJECT-TYPE
        SYNTAX LinkPortAddress
        MAX-ACCESS read-only
        STATUS current
        DESCRIPTION
           "This number uniquely identifies an Octal High Speed Port resource. 
           This number will be used throughout the system to identify 
           a unique port. The format is represented using an IP address 
           syntax (4 byte string). Note that the maximum valid port 
           number will vary depending on the specified device. 
            
               The 1st byte represents the Nest Number (0-7)
               The 2nd byte represents the Slot Number (1-11)            
               The 3rd byte represents the Port Number (1-32)
               The 4th byte is reserved for future use           
           "
        ::= { oHSConfigEntry 1 }

oHSCfgResource OBJECT-TYPE
        SYNTAX Integer32
        MAX-ACCESS read-only
        STATUS current
        DESCRIPTION
                "Uniquely identifies an Octal High Speed port in the system.
                 This number is provided as key to allow the manager to 
                 map this entry to a corresponding Resource Table entry."
        ::= { oHSConfigEntry 2 }

oHSCfgPortName OBJECT-TYPE
        SYNTAX DisplayString (SIZE(0..20))
        MAX-ACCESS read-write
        STATUS current
        DESCRIPTION
        	"This is the user friendly text name to identify the port."
        ::= { oHSConfigEntry 3 }

oHSCfgStatus OBJECT-TYPE
        SYNTAX PortStatus
        MAX-ACCESS read-write
        STATUS current
        DESCRIPTION
           "Dictates the current status of the port, in-service or 
           out-of-service."
        ::= { oHSConfigEntry 4 }

oHSCfgMode OBJECT-TYPE
        SYNTAX INTEGER {
            nxDs0(0),
            ds0-A(1),
            nxDs0-Special(2),
            ds0-A-Special(3)
            }
        MAX-ACCESS read-write
        STATUS current
        DESCRIPTION
           "The port's configured transfer mode.
              nxDs0	         (0)  Transfer rate is Kbps per channel multiplied 
                                  by Ds0s in configured Connection 
              ds0-A		     (1)  9.6 K mode
              nxDs0-Special  (2)  Special Control signals mode not valid 
                                  with X.21
              ds0-A-Special  (3)  9.6 K mode plus Special Control signals mode" 
        ::= { oHSConfigEntry 5 }

-- *************************************************************************
-- The OHS Cfg Speed is no longer applicable for Connections and is not
-- supported by the Agent as of Release 12.0
-- *************************************************************************
oHSCfgSpeed OBJECT-TYPE
        SYNTAX ConnectionSpeed
        MAX-ACCESS read-only
        STATUS obsolete
        DESCRIPTION
           "Displays the configured Speed based on configured Connection."
        ::= { oHSConfigEntry 6 }

oHSCfgType OBJECT-TYPE
        SYNTAX INTEGER {
        	eia232(2),
        	eia422(4),
        	eia530(13),
        	ituV-35(14),
        	eia530A(15),
        	ituX-21(16)
        	}
        MAX-ACCESS read-write
        STATUS current
        DESCRIPTION
           "Determines the type of Interface for the High Speed port.
            
              eia232 (2) - EIA/TIA-232
                Common physical layer interface standard, developed by EIA and TIA, 
                that supports unbalanced circuits at signal speeds of up to 64 kbps. 
                Formerly called as RS-232. 
              eia422 (4) - EIA/TIA-422 (RS-422)
                Common physical layer interface standard that supports balanced 
                electrical implementation of EIA/TIA-449 for high-speed data 
                transmission. 
              eia530 (13) - EIA-530
                Refers to two electrical implementations of EIA/TIA-449: 
                RS-422 (for balanced transmission) and RS-423 (for unbalanced 
                transmission). Now referred to collectively as EIA-530. 
              ituV-35 (14) - ITU V.35
                ITU-T standard describing a synchronous, physical layer protocol 
                used for communications between a network access device and a 
                packet network. V.35 is most commonly used in the United States 
                and in Europe, and is recommended for speeds up to 48 Kbps.
              eia530A (15) - EIA-530A
                Common physical layer interface standard, developed by EIA and TIA, 
                that supports unbalanced circuits at signal speeds of up to 64 kbps. 
                Formerly called as RS-232.                  
              ituX-21 (16) - ITU X.21
                ITU-T standard for serial communications over synchronous digital 
                lines. The X.21 protocol is used primarily in Europe and Japan.
           "                    
        ::= { oHSConfigEntry 7 }

oHSCfgData OBJECT-TYPE
        SYNTAX INTEGER {
            normal(0),
            invert(1)
            }
        MAX-ACCESS read-write
        STATUS current
        DESCRIPTION
           "Determines the data polarity of the port."
        ::= { oHSConfigEntry 8 }

oHSCfgClock OBJECT-TYPE
        SYNTAX INTEGER {
            normal(0),
            invert(1)
            }
        MAX-ACCESS read-write
        STATUS current
        DESCRIPTION
           "Determines the polarity of the port's clock."
        ::= { oHSConfigEntry 9 }

oHSCfgNetLoop OBJECT-TYPE
        SYNTAX FunctionSwitch
        MAX-ACCESS read-write
        STATUS current
        DESCRIPTION
           "Determines whether or not the port should respond to 
           V.54 loop diagnostic codes received from the network 
           supplier. Select 'enable' unless the commands are to be 
           passed to another High Speed device."
        ::= { oHSConfigEntry 10 }

oHSCfgTiming OBJECT-TYPE
        SYNTAX INTEGER {
            internal(0),
            int-ext(1),
            external(2)
            }
        MAX-ACCESS read-write
        STATUS current
        DESCRIPTION
           "Source of the port's bit rate clock. 
              internal      (0) Both the transmit and receive clocks
                                are internal.
              int-ext       (1) The transmit clock is internal and the 
                                receive clock is external.
              external      (2) Both the transmit and receive clocks 
                                are provided external."
        ::= { oHSConfigEntry 11 }

oHSCfgDcd OBJECT-TYPE
        SYNTAX INTEGER {
            forced-off(0),
            forced-on(1),
            track-RTS(2),
            drop-carrier(4)
            }
        MAX-ACCESS read-write
        STATUS current
        DESCRIPTION
           "The Data Carrier Detect configuration method used on this port.
           DCD does not apply to X.21 Port Types.
              forced-off	(0)  DCD is off
              forced-on		(1)  DCD is on
              track-RTS		(2)  asserts Request to Send (RTS) each time data 
                                 needs to be transmitted and drops RTS at some 
                                 point after data transmission begins.
              drop-carrier  (4)  drops DCD in response to a Carrier link fault."
        ::= { oHSConfigEntry 12 }

oHSCfgDsr OBJECT-TYPE
        SYNTAX INTEGER  {
            forced-off(0),
            forced-on(1),
            track-DTR(2)
            }
        MAX-ACCESS read-write
        STATUS current
        DESCRIPTION
           "The Data Set Ready configuration method used on this port.
           DSR does not apply to X.21 Port Types.
              forced-off	(0)  DSR signaling is off
              forced-on		(1)  DSR signaling is on
              track-DTR		(2)  tracks Data Terminal Ready (DTR) signal 
                                 before transmitting data to the DTE."
        ::= { oHSConfigEntry 13 }

oHSCfgCtsIndication OBJECT-TYPE
        SYNTAX INTEGER {
            forced-off(0),
            forced-on(1),
            track-RTS(2)
            }
        MAX-ACCESS read-write
        STATUS current
        DESCRIPTION
           "A Control Signal configuration used on this port.
           When the Port type is X.21, this field represents the X.21 
           Control Signals.  In all other cases, this is the Clear to Send
           method.
              forced-off	(0)  method is off
              forced-on		(1)  method is on
              track-RTS		(2)  asserts Request to Send (RTS) each time data 
                                 needs to be transmitted and drops RTS at some 
                                 point after data transmission begins."
        ::= { oHSConfigEntry 14 }

oHSCfgDTELoop OBJECT-TYPE
        SYNTAX FunctionSwitch
        MAX-ACCESS read-write
        STATUS current
        DESCRIPTION
           "Enables or disables bi-directional DTE Local Loop & Remote Loop.
           This option only applies when port is configured for nxDs0-Special(3) 
           or ds0-A-Special(4) modes."
        ::= { oHSConfigEntry 15 }

oHSCfgCmdStatus OBJECT-TYPE
        SYNTAX LinkCmdStatus
        MAX-ACCESS read-write
        STATUS current
        DESCRIPTION
           "The command status for this port configuration row/record.
           The value used in a SET will be replaced by a response
           value in the GET RESPONSE indicating success or failure.
           		
            Default Response State used in GET RESPONSE Command
                ready-for-command (0)
                    initial default status for a row           
                    
            High Speed Port Commands used in SET Command (1..99)            
                update-link-config(1)
                    Change existing Port Configuration
                inServiceAll (7)
                    Change Link Status to in-service for all 8 ports.
                copyToAll (9)
                    Copy HS Port configuration to all other ports 
                    within the same device
                outOfServiceAll (12)
                    Change Link Status to out-of-service for all 8 ports.
               		              		               		
            Response States used in GET RESPONSE Command (100..199)
                update-successful (101)
                    Port data has been successfully changed
                insvc-successful (107)
                    All Ports have been successfully placed In Service
                copy-successful (109)
                    HS Port data has been successfully copied to other ports
                oos-successful (112)
                    All Ports have been successfully placed Out of Service
               		
            High Speed Port Config Error Codes used in GET RESPONSE Command (200..699)
                err-general-link-config-error (400)
                    Unknown HS port configuration error occurred                
                err-invalid-link-status (401)
                    Unrecognized HS port status setting
                err-invalid-link-command (403)
                    Unrecognized HS port command-action
                err-invalid-link-op-mode (407)
                	Unrecognized HS port Mode
                err-invalid-link-rem-loop (408)
                    Unrecognized or not applicable DTE Loop
                err-invalid-network-loop (410)
                    Unrecognized network loop setting
                err-invalid-interface (419)
                    Unrecognized or not applicable HS Type
                err-invalid-polarity (420)
                    Unrecognized polarity setting
                err-invalid-clock-timing (421)
                    Unrecognized clock setting
                err-invalid-control-signal (422)
                    Unrecognized Control setting
                err-dcd-dsr-not-applicable (423)
                    DCD/DSR not configurable with X.21 
                err-requires-special-mode (424)
                    Field not configurable in non-Special Mode
                err-cts-not-applicable (425)
                    CTS not configurable in Special Mode
                err-data-locked-by-another-user (450)
                    Another administrative user is making changes to this
                    part of the system via a terminal session. Check Event
                    Log for user name
                err-snmp-parse-failed (500)
                    Agent could not parse variable
                err-invalid-snmp-type (501)
                    Variable ASN type does not match Agent defined type 
                err-invalid-snmp-var-size (502)
                    Variable size is too big"                 		
         ::= { oHSConfigEntry 16 }

oHSCfgClockEdgeErrs OBJECT-TYPE
        SYNTAX DecisionType
        MAX-ACCESS read-write
        STATUS current
        DESCRIPTION
           "Determines whether or not the port should monitor Clock 
           Edge errors."
        ::= { oHSConfigEntry 17 }

-- *************************************************************************
--   This is the Trap Definitions section for the OCTAL-HS MIB. 
-- *************************************************************************

dnxOHSEnterprise OBJECT-IDENTITY
      STATUS current
      DESCRIPTION "ERI DNX High Speed Enterprise for Alarms/Events"
    ::= { dnxOHS 0 }

oHSConfigTrap NOTIFICATION-TYPE
        OBJECTS {
            trapSequence,
            oHSCfgPortAddr,
            oHSCfgCmdStatus
            }
        STATUS current
        DESCRIPTION
              	"This trap is used to notify a NMS that a user has updated 
              	the Port configuration for a given High Speed Port entry."
        ::= { dnxOHSEnterprise 1 }
                              
END

-- *************************************************************************
--
--  MIB:    ERI-DNX-STM1-OC3-MIB
--
--  Purpose:
--          This will be the MIB for the DNX STM1 and OC3 Interface 
--          Modules. This will provide for Configuration for any STM1 
--          or OC3 card in the Node.
--
--  Contact: Eastern Research Inc. 1-800-337-4374  Email: support@erinc.com
--
-- *************************************************************************
