--  (C) COPYRIGHT HEWLETT-PACKARD COMPANY 2008.
--
--  LaserJet 6015 Printer Model Specific MIB.
--
--  Generated on Apr. 09, 2008.
--
--  Company names and product names mentioned herein may be 
--  trademarks, and/or registered trademarks of their respective
--  companies.
--
--  For internal and external use.
--
--  This MIB describes all the printer model specific
--  objects supported by the LaserJet 6015 printer
--  when networked connected using a JetDirect print
--  server.
--
--  The following MIBs also contain objects supported
--  by a JetDirect connected LaserJet 6015 printer:
--
--  rfc 1514 Host Resources MIB
--  rfc 1759 Printer MIB
--  rfc 1213 MIB II
--
--  This MIB complies with the following RFCs:
--
--  rfc 1157 Simple Network Management Protocol
--  rfc 1155 Structure of Management Information
--
--  Notes:
--
--  1) Objects containing a string which are defined in this MIB use the
--     first two bytes to hold the symbol set used to encode the string.
--     The Roman-8 symbol set has a hex encoding of 0x0115.  Other 
--     symbol sets are listed in the PCL 5 Comparison Guide in table
--     C-1 Symbol Set Values.
--
--  2) Some of the objects included are only supported if an accessory 
--     is installed.  These accessories include:
--       MIO based accessories
--       SIMM based accessories
--       AT hard disk
--       Paper handling accessories
--       Adobe PostScript accessory
LJ6015-MIB DEFINITIONS ::= BEGIN

IMPORTS OBJECT-TYPE FROM SNMPv2-SMI;

hp OBJECT IDENTIFIER ::= { iso(1) org(3) dod(6) internet(1) private(4) enterprises(1) 11}
dm OBJECT IDENTIFIER ::= { hp nm(2) hpsystem(3) net-peripheral(9) netdm(4) 2}

DisplayString ::= OCTET STRING

device                                 OBJECT IDENTIFIER ::=  { dm 1 } 
device-system                          OBJECT IDENTIFIER ::=  { device 1 } 
status-system                          OBJECT IDENTIFIER ::=  { device-system 2 } 
test                                   OBJECT IDENTIFIER ::=  { device-system 5 } 
job                                    OBJECT IDENTIFIER ::=  { device-system 6 } 
job-info                               OBJECT IDENTIFIER ::=  { job 5 } 
job-info-accounting                    OBJECT IDENTIFIER ::=  { job-info 28 } 
processing-subsystem                   OBJECT IDENTIFIER ::=  { device 3 } 
pml                                    OBJECT IDENTIFIER ::=  { processing-subsystem 4 } 
control-panel-display                  OBJECT IDENTIFIER ::=  { status-system 65 } 
settings-system                        OBJECT IDENTIFIER ::=  { device-system 1 } 
interface                              OBJECT IDENTIFIER ::=  { device-system 4 } 
simm                                   OBJECT IDENTIFIER ::=  { interface 1 } 
simm1                                  OBJECT IDENTIFIER ::=  { simm 1 } 
simm1-bank                             OBJECT IDENTIFIER ::=  { simm1 6 } 
simm1-bank1                            OBJECT IDENTIFIER ::=  { simm1-bank 1 } 
simm1-bank2                            OBJECT IDENTIFIER ::=  { simm1-bank 2 } 
simm2                                  OBJECT IDENTIFIER ::=  { simm 2 } 
simm2-bank                             OBJECT IDENTIFIER ::=  { simm2 6 } 
simm2-bank1                            OBJECT IDENTIFIER ::=  { simm2-bank 1 } 
simm2-bank2                            OBJECT IDENTIFIER ::=  { simm2-bank 2 } 
simm3                                  OBJECT IDENTIFIER ::=  { simm 3 } 
simm3-bank                             OBJECT IDENTIFIER ::=  { simm3 6 } 
simm3-bank1                            OBJECT IDENTIFIER ::=  { simm3-bank 1 } 
simm3-bank2                            OBJECT IDENTIFIER ::=  { simm3-bank 2 } 
simm4                                  OBJECT IDENTIFIER ::=  { simm 4 } 
simm4-bank                             OBJECT IDENTIFIER ::=  { simm4 6 } 
simm4-bank1                            OBJECT IDENTIFIER ::=  { simm4-bank 1 } 
simm4-bank2                            OBJECT IDENTIFIER ::=  { simm4-bank 2 } 
simm5                                  OBJECT IDENTIFIER ::=  { simm 5 } 
simm5-bank                             OBJECT IDENTIFIER ::=  { simm5 6 } 
simm5-bank1                            OBJECT IDENTIFIER ::=  { simm5-bank 1 } 
simm5-bank2                            OBJECT IDENTIFIER ::=  { simm5-bank 2 } 
settings-job                           OBJECT IDENTIFIER ::=  { job 1 } 
operating-system                       OBJECT IDENTIFIER ::=  { device-system 19 } 
pdl                                    OBJECT IDENTIFIER ::=  { processing-subsystem 3 } 
settings-pdl                           OBJECT IDENTIFIER ::=  { pdl 1 } 
status-pdl                             OBJECT IDENTIFIER ::=  { pdl 2 } 
background-message                     OBJECT IDENTIFIER ::=  { status-system 37 } 
background-message1                    OBJECT IDENTIFIER ::=  { background-message 1 } 
background-message2                    OBJECT IDENTIFIER ::=  { background-message 2 } 
destination-subsystem                  OBJECT IDENTIFIER ::=  { device 4 } 
print-engine                           OBJECT IDENTIFIER ::=  { destination-subsystem 1 } 
menus                                  OBJECT IDENTIFIER ::=  { print-engine 13 } 
errorlog                               OBJECT IDENTIFIER ::=  { device-system 11 } 
error1                                 OBJECT IDENTIFIER ::=  { errorlog 1 } 
error2                                 OBJECT IDENTIFIER ::=  { errorlog 2 } 
error3                                 OBJECT IDENTIFIER ::=  { errorlog 3 } 
error4                                 OBJECT IDENTIFIER ::=  { errorlog 4 } 
error5                                 OBJECT IDENTIFIER ::=  { errorlog 5 } 
error6                                 OBJECT IDENTIFIER ::=  { errorlog 6 } 
error7                                 OBJECT IDENTIFIER ::=  { errorlog 7 } 
error8                                 OBJECT IDENTIFIER ::=  { errorlog 8 } 
error9                                 OBJECT IDENTIFIER ::=  { errorlog 9 } 
error10                                OBJECT IDENTIFIER ::=  { errorlog 10 } 
error11                                OBJECT IDENTIFIER ::=  { errorlog 11 } 
error12                                OBJECT IDENTIFIER ::=  { errorlog 12 } 
error13                                OBJECT IDENTIFIER ::=  { errorlog 13 } 
error14                                OBJECT IDENTIFIER ::=  { errorlog 14 } 
error15                                OBJECT IDENTIFIER ::=  { errorlog 15 } 
error16                                OBJECT IDENTIFIER ::=  { errorlog 16 } 
error17                                OBJECT IDENTIFIER ::=  { errorlog 17 } 
error18                                OBJECT IDENTIFIER ::=  { errorlog 18 } 
error19                                OBJECT IDENTIFIER ::=  { errorlog 19 } 
error20                                OBJECT IDENTIFIER ::=  { errorlog 20 } 
error21                                OBJECT IDENTIFIER ::=  { errorlog 21 } 
error22                                OBJECT IDENTIFIER ::=  { errorlog 22 } 
error23                                OBJECT IDENTIFIER ::=  { errorlog 23 } 
error24                                OBJECT IDENTIFIER ::=  { errorlog 24 } 
error25                                OBJECT IDENTIFIER ::=  { errorlog 25 } 
error26                                OBJECT IDENTIFIER ::=  { errorlog 26 } 
error27                                OBJECT IDENTIFIER ::=  { errorlog 27 } 
error28                                OBJECT IDENTIFIER ::=  { errorlog 28 } 
error29                                OBJECT IDENTIFIER ::=  { errorlog 29 } 
error30                                OBJECT IDENTIFIER ::=  { errorlog 30 } 
error31                                OBJECT IDENTIFIER ::=  { errorlog 31 } 
error32                                OBJECT IDENTIFIER ::=  { errorlog 32 } 
error33                                OBJECT IDENTIFIER ::=  { errorlog 33 } 
error34                                OBJECT IDENTIFIER ::=  { errorlog 34 } 
error35                                OBJECT IDENTIFIER ::=  { errorlog 35 } 
error36                                OBJECT IDENTIFIER ::=  { errorlog 36 } 
error37                                OBJECT IDENTIFIER ::=  { errorlog 37 } 
error38                                OBJECT IDENTIFIER ::=  { errorlog 38 } 
error39                                OBJECT IDENTIFIER ::=  { errorlog 39 } 
error40                                OBJECT IDENTIFIER ::=  { errorlog 40 } 
error41                                OBJECT IDENTIFIER ::=  { errorlog 41 } 
error42                                OBJECT IDENTIFIER ::=  { errorlog 42 } 
error43                                OBJECT IDENTIFIER ::=  { errorlog 43 } 
error44                                OBJECT IDENTIFIER ::=  { errorlog 44 } 
error45                                OBJECT IDENTIFIER ::=  { errorlog 45 } 
error46                                OBJECT IDENTIFIER ::=  { errorlog 46 } 
error47                                OBJECT IDENTIFIER ::=  { errorlog 47 } 
error48                                OBJECT IDENTIFIER ::=  { errorlog 48 } 
error49                                OBJECT IDENTIFIER ::=  { errorlog 49 } 
error50                                OBJECT IDENTIFIER ::=  { errorlog 50 } 
channel                                OBJECT IDENTIFIER ::=  { device 6 } 
display                                OBJECT IDENTIFIER ::=  { status-system 20 } 
display-status                         OBJECT IDENTIFIER ::=  { display 1 } 
id                                     OBJECT IDENTIFIER ::=  { device-system 3 } 
web-server                             OBJECT IDENTIFIER ::=  { interface 6 } 
settings-web-server                    OBJECT IDENTIFIER ::=  { web-server 1 } 
settings-prt-eng                       OBJECT IDENTIFIER ::=  { print-engine 1 } 
intray                                 OBJECT IDENTIFIER ::=  { print-engine 3 } 
settings-intray                        OBJECT IDENTIFIER ::=  { intray 1 } 
ph                                     OBJECT IDENTIFIER ::=  { print-engine 7 } 
settings-ph                            OBJECT IDENTIFIER ::=  { ph 1 } 
pdl-pcl                                OBJECT IDENTIFIER ::=  { pdl 3 } 
pdl-postscript                         OBJECT IDENTIFIER ::=  { pdl 4 } 
pdl-pdf                                OBJECT IDENTIFIER ::=  { pdl 15 } 
active-print-jobs                      OBJECT IDENTIFIER ::=  { job 2 } 
job-being-parsed                       OBJECT IDENTIFIER ::=  { active-print-jobs 1 } 
job-info-attribute                     OBJECT IDENTIFIER ::=  { job-info 23 } 
held-job                               OBJECT IDENTIFIER ::=  { job 7 } 
held-job-info                          OBJECT IDENTIFIER ::=  { held-job 1 } 
held-job-control                       OBJECT IDENTIFIER ::=  { held-job 2 } 
source-subsystem                       OBJECT IDENTIFIER ::=  { device 2 } 
spooler                                OBJECT IDENTIFIER ::=  { source-subsystem 4 } 
settings-spooler                       OBJECT IDENTIFIER ::=  { spooler 1 } 
pjl                                    OBJECT IDENTIFIER ::=  { processing-subsystem 5 } 
mio                                    OBJECT IDENTIFIER ::=  { interface 3 } 
mio1                                   OBJECT IDENTIFIER ::=  { mio 1 } 
mio4                                   OBJECT IDENTIFIER ::=  { mio 4 } 
usb-interface                          OBJECT IDENTIFIER ::=  { interface 9 } 
usb                                    OBJECT IDENTIFIER ::=  { usb-interface 2 } 
io                                     OBJECT IDENTIFIER ::=  { source-subsystem 1 } 
settings-io                            OBJECT IDENTIFIER ::=  { io 1 } 
ports                                  OBJECT IDENTIFIER ::=  { io 3 } 
port1                                  OBJECT IDENTIFIER ::=  { ports 1 } 
tables                                 OBJECT IDENTIFIER ::=  { device 7 } 
remote-procedure-call                  OBJECT IDENTIFIER ::=  { device-system 13 } 
settings-rpc                           OBJECT IDENTIFIER ::=  { remote-procedure-call 1 } 
status-rpc                             OBJECT IDENTIFIER ::=  { remote-procedure-call 2 } 
file-system                            OBJECT IDENTIFIER ::=  { device-system 10 } 
settings-file-system                   OBJECT IDENTIFIER ::=  { file-system 1 } 
file-systems                           OBJECT IDENTIFIER ::=  { file-system 3 } 
file-system2                           OBJECT IDENTIFIER ::=  { file-systems 2 } 
file-system3                           OBJECT IDENTIFIER ::=  { file-systems 3 } 
file-system4                           OBJECT IDENTIFIER ::=  { file-systems 4 } 
resource-manager                       OBJECT IDENTIFIER ::=  { device-system 12 } 
mass-storage-resources                 OBJECT IDENTIFIER ::=  { resource-manager 3 } 
mass-storage-block-driver              OBJECT IDENTIFIER ::=  { device-system 15 } 
settings-mass-storage-bd               OBJECT IDENTIFIER ::=  { mass-storage-block-driver 1 } 
status-mass-storage-bd                 OBJECT IDENTIFIER ::=  { mass-storage-block-driver 2 } 
device-configure                       OBJECT IDENTIFIER ::=  { settings-system 32 } 
phd                                    OBJECT IDENTIFIER ::=  { interface 5 } 
phd1                                   OBJECT IDENTIFIER ::=  { phd 1 } 
phd2                                   OBJECT IDENTIFIER ::=  { phd 2 } 
marking-agent-density                  OBJECT IDENTIFIER ::=  { settings-prt-eng 9 } 
status-prt-eng                         OBJECT IDENTIFIER ::=  { print-engine 2 } 
printer-calibration-dhalf              OBJECT IDENTIFIER ::=  { status-prt-eng 37 } 
printer-cal-dhalf-data                 OBJECT IDENTIFIER ::=  { printer-calibration-dhalf 3 } 
printer-cal-grayaxis                   OBJECT IDENTIFIER ::=  { printer-calibration-dhalf 6 } 
printer-cal-grayaxis-data              OBJECT IDENTIFIER ::=  { printer-calibration-dhalf 7 } 
printer-calibration-cpr                OBJECT IDENTIFIER ::=  { status-prt-eng 38 } 
intrays                                OBJECT IDENTIFIER ::=  { intray 3 } 
intray1                                OBJECT IDENTIFIER ::=  { intrays 1 } 
intray2                                OBJECT IDENTIFIER ::=  { intrays 2 } 
intray3                                OBJECT IDENTIFIER ::=  { intrays 3 } 
intray5                                OBJECT IDENTIFIER ::=  { intrays 5 } 
intray6                                OBJECT IDENTIFIER ::=  { intrays 6 } 
outbin                                 OBJECT IDENTIFIER ::=  { print-engine 4 } 
settings-outbin                        OBJECT IDENTIFIER ::=  { outbin 1 } 
outbins                                OBJECT IDENTIFIER ::=  { outbin 3 } 
outbin1                                OBJECT IDENTIFIER ::=  { outbins 1 } 
outbin2                                OBJECT IDENTIFIER ::=  { outbins 2 } 
outbin3                                OBJECT IDENTIFIER ::=  { outbins 3 } 
outbin4                                OBJECT IDENTIFIER ::=  { outbins 4 } 
marking-agent                          OBJECT IDENTIFIER ::=  { print-engine 5 } 
settings-marking-agent                 OBJECT IDENTIFIER ::=  { marking-agent 1 } 
print-media                            OBJECT IDENTIFIER ::=  { print-engine 8 } 
settings-print-media                   OBJECT IDENTIFIER ::=  { print-media 1 } 
media-info                             OBJECT IDENTIFIER ::=  { print-media 3 } 
media1                                 OBJECT IDENTIFIER ::=  { media-info 1 } 
media2                                 OBJECT IDENTIFIER ::=  { media-info 2 } 
media3                                 OBJECT IDENTIFIER ::=  { media-info 3 } 
media4                                 OBJECT IDENTIFIER ::=  { media-info 4 } 
media5                                 OBJECT IDENTIFIER ::=  { media-info 5 } 
media6                                 OBJECT IDENTIFIER ::=  { media-info 6 } 
media7                                 OBJECT IDENTIFIER ::=  { media-info 7 } 
media8                                 OBJECT IDENTIFIER ::=  { media-info 8 } 
media9                                 OBJECT IDENTIFIER ::=  { media-info 9 } 
media10                                OBJECT IDENTIFIER ::=  { media-info 10 } 
media11                                OBJECT IDENTIFIER ::=  { media-info 11 } 
media12                                OBJECT IDENTIFIER ::=  { media-info 12 } 
media13                                OBJECT IDENTIFIER ::=  { media-info 13 } 
media14                                OBJECT IDENTIFIER ::=  { media-info 14 } 
media15                                OBJECT IDENTIFIER ::=  { media-info 15 } 
media16                                OBJECT IDENTIFIER ::=  { media-info 16 } 
media17                                OBJECT IDENTIFIER ::=  { media-info 17 } 
media18                                OBJECT IDENTIFIER ::=  { media-info 18 } 
media19                                OBJECT IDENTIFIER ::=  { media-info 19 } 
media20                                OBJECT IDENTIFIER ::=  { media-info 20 } 
media21                                OBJECT IDENTIFIER ::=  { media-info 21 } 
media22                                OBJECT IDENTIFIER ::=  { media-info 22 } 
media23                                OBJECT IDENTIFIER ::=  { media-info 23 } 
media24                                OBJECT IDENTIFIER ::=  { media-info 24 } 
media25                                OBJECT IDENTIFIER ::=  { media-info 25 } 
media26                                OBJECT IDENTIFIER ::=  { media-info 26 } 
media27                                OBJECT IDENTIFIER ::=  { media-info 27 } 
media28                                OBJECT IDENTIFIER ::=  { media-info 28 } 
media29                                OBJECT IDENTIFIER ::=  { media-info 29 } 
media30                                OBJECT IDENTIFIER ::=  { media-info 30 } 
media31                                OBJECT IDENTIFIER ::=  { media-info 31 } 
media32                                OBJECT IDENTIFIER ::=  { media-info 32 } 
media33                                OBJECT IDENTIFIER ::=  { media-info 33 } 
media34                                OBJECT IDENTIFIER ::=  { media-info 34 } 
media35                                OBJECT IDENTIFIER ::=  { media-info 35 } 
media36                                OBJECT IDENTIFIER ::=  { media-info 36 } 
media37                                OBJECT IDENTIFIER ::=  { media-info 37 } 
media38                                OBJECT IDENTIFIER ::=  { media-info 38 } 
media39                                OBJECT IDENTIFIER ::=  { media-info 39 } 
media-modes                            OBJECT IDENTIFIER ::=  { print-media 4 } 
media-types                            OBJECT IDENTIFIER ::=  { print-media 8 } 
media-counts                           OBJECT IDENTIFIER ::=  { print-media 7 } 
media-size                             OBJECT IDENTIFIER ::=  { print-media 5 } 
consumables                            OBJECT IDENTIFIER ::=  { print-engine 10 } 
consumables-1                          OBJECT IDENTIFIER ::=  { consumables 1 } 
consumable-status                      OBJECT IDENTIFIER ::=  { consumables-1 1 } 
consumable-string                      OBJECT IDENTIFIER ::=  { consumables 8 } 
consumables-status                     OBJECT IDENTIFIER ::=  { consumables 5 } 
consumables-life                       OBJECT IDENTIFIER ::=  { consumables-status 1 } 
print-meter                            OBJECT IDENTIFIER ::=  { print-engine 11 } 
printer-average                        OBJECT IDENTIFIER ::=  { print-meter 1 } 
webserver-proc-sub                     OBJECT IDENTIFIER ::=  { processing-subsystem 9 } 
settings-webserver                     OBJECT IDENTIFIER ::=  { webserver-proc-sub 1 } 
firmware-download                      OBJECT IDENTIFIER ::=  { device-system 18 } 
upgradable-devices                     OBJECT IDENTIFIER ::=  { device-system 20 } 


perm-store-init-occurred OBJECT-TYPE
   SYNTAX      OCTET STRING
   ACCESS      read-only
   STATUS      optional
   DESCRIPTION "This object will set the cAllPermDevices bit when a full perm		
                storage initialization occurs (as would be the case for a brand		
                new system or as a result of a powerup key sequence or		
                PE-TEST-POWERUP-KEY-SEQUENCE object request). If only one		
                device was initialized (as would be the case if a disk were		
                added to an existing system or a formatter were swapped out),		
                then only the appropriate collection bits will be returned. If		
                there are no collection bits set then this indicates that no		
                initialization took place."
::= { status-system 10 }
               
               
self-test OBJECT-TYPE
   SYNTAX      INTEGER {
		   eNotInASelfTest(1),
		   eNonDestructiveSelfTest(4)
		   }
   ACCESS      read-write
   STATUS      optional
   DESCRIPTION "Writing this object allows a device self test to be started.		
                Reading this object provides an indication what self-test is		
                currently executing, if any. Actual self-test operation is		
                device specific. A self test may not be allowed at any		
                arbitrary time. If the device supports the requested self test,		
                but can not start the execution of the self test when		
                requested, the device will respond with		
                <genErr>. If a non-destructive self		
                test is being started, the device will generate a response		
                before the self test is completed. RECOMMENDATION: If the		
                device is ready (i.e. the NOT-READY-PRINTER object does not		
                contain any items, except maybe being off-line) and is idle		
                (i.e. the NOT-IDLE object does not contain any items), this		
                request should always succeed. This provides a mechanism for		
                driver writers to always determine if the action will succeed		
                or not.
                Additional information:
                The eNonDestructiveSelfTest performs limited
                testing on the printer and its attached paper handling
                devices. After the self-test is complete a
                configuration page is printed. The recommended
                way to cause a configuration page to be printed is to
                use the PRINT-INTERNAL-PAGE object.  
                
                Setting this object to eNonDestructiveSelfTest results in a status of <noError>
                and a value of eNonDestructiveSelfTest being returned.
                If the printer is not idle (whether printing an external job or printing
                an internal page), this action will be delayed until the next job boundary.
                
                See the PRINT-INTERNAL-PAGE object for more details."
::= { test 1 }
               
               
print-internal-page OBJECT-TYPE
   SYNTAX      INTEGER {
		   eNotPrintingAnInternalPage(1),
		   ePrintingAnUnknownInternalPage(2),
		   eDeviceDemoPage1ConfigurationPage(3),
		   eDeviceDemoPage2(4),
		   eDeviceDemoPage5ErrorLog(7),
		   eDeviceDemoPage6FileSystemDirectoryListing(8),
		   eDeviceDemoPage7MenuMap(9),
		   ePrintUsagePage(100),
		   eSuppliesPage(101),
		   eDeviceAutoCleaningPage(252),
		   eDeviceCleaningPage(253),
		   eDevicePaperPathTest(254),
		   eDevicePageRegistrationPage(255),
		   ePrintQualityPages(256),
		   eHighVoltageTestPage(257),
		   eColorPaletteRGBPage(258),
		   eColorPaletteCMYKPage(259),
		   eDevicePageDiagnosticsPage(260),
		   ePCLFontList1(350),
		   ePSFontList(450),
		   eDeviceShowMeHowPageHelpGuide(1406)
		   }
   ACCESS      read-write
   STATUS      optional
   DESCRIPTION "Writing this object to a value other than		
                eNotPrintingAnInternalPage causes the device to attempt to		
                print an internally generated page. Reading this object		
                provides an indication what internally generated page is		
                currently being printed, if any. The actual page is device		
                specific. Some devices may support continuously printing an		
                internally generated page. Setting this object to		
                eNotPrintingAnInternalPage terminates continuously printing		
                internally generated pages. An internally generated page may		
                not be allowed to be printed at any arbitrary time; under what		
                conditions it will succeed or fail is device specific. If the		
                device supports the requested page, but can not start printing		
                the page when requested, the device will respond with		
                <genErr>. RECOMMENDATION: If the		
                device is ready (i.e. the NOT-READY-PRINTER object does not		
                contain any items, except maybe being off-line) and is idle		
                (i.e. the NOT-IDLE object does not contain any items), this		
                request should always succeed. This provides a mechanism for		
                driver writers to always determine if the action will succeed		
                or not.
                Additional information:
                Previous products used 
                ePCLDemoPage1ConfigurationPage(300) for the
                Configuration or Self Test page.  This product uses
                eDeviceDemoPage1ConfigurationPage(3).  
                
                $product_str does not support continuously printing a demo page.  
                
                When this object is set to a valid value, the status returned is <noError>
                and the value returned is ePrintingAnUnknownInternalPage.  If the printer
                is idle, the page will be printed immediately.  If the printer is
                currently printing another job, the internal page requested will not print
                until that job is finished.  
                
                Setting this object to a valid value causes the
                desired page to be formatted and put in the printer's
                print queue.  While the page is being formatted a get on this object will
                return the value ePrintingAnUnknownInternalPage.  Once the page (or pages)
                is finished being formatted, this object returns a value of
                eNotPrintingAnInternalPage, even though the page may not have finished
                being printed.  
                
                Setting this object multiple times will queue up the requests, but only
                a limited number will be queued.  Once the queue is full, additional
                requests will be ignored."
::= { test 2 }
               
               
job-info-accounting-color-usage-log OBJECT-TYPE
   SYNTAX      INTEGER {
		   eClear(1),
		   ePrint(2)
		   }
   ACCESS      write-only
   STATUS      optional
   DESCRIPTION "Provides applications with the ability to clear or print the		
                Color Usage Log. eClear - clear the log. ePrint - print the		
                log. Either action will complete before any subsequent action		
                is performed.
                Additional information:
                Provides applications with the ability to clear or print the		
                Color Usage Log. eClear - clear the log. ePrint - print the		
                log. Either action will complete before any subsequent action		
                is performed."
::= { job-info-accounting 32 }
               
               
localization-languages-supported OBJECT-TYPE
   SYNTAX      OCTET STRING
   ACCESS      read-only
   STATUS      optional
   DESCRIPTION "The list of languages supported by the device. The languages		
                are primarily, but not limited to, two character codes from ISO		
                639, each separated by a comma character.
                Additional information:
                This string will always be in the Roman-8 character
                set.  See prtLocalizationLanguage for details about each language value."
::= { status-system 52 }
               
               
localization-countries-supported OBJECT-TYPE
   SYNTAX      OCTET STRING
   ACCESS      read-only
   STATUS      optional
   DESCRIPTION "The list of countries supported by the device. The countries		
                are primarily, but not limited to, two character codes from ISO		
                3166, each separated by a comma character.
                Additional information:
                This string will always be in the Roman-8 character
                set.  See prtLocalizationCountry for details about each country value."
::= { status-system 53 }
               
               
control-panel-button-press OBJECT-TYPE
   SYNTAX      INTEGER {
		   eMenuPlusButton(2),
		   eMenuMinusButton(3),
		   eItemPlusButton(4),
		   eItemMinusButton(5),
		   eValuePlusButton(6),
		   eValueMinusButton(7),
		   eSelectButton(8),
		   eCancelJobButton(9),
		   ePauseResumeButton(10),
		   eUpArrowButton(11),
		   eDownArrowButton(12),
		   eBackButton(13),
		   eQuestionMarkButton(14),
		   eClearButton(15),
		   eNumericButton0(16),
		   eNumericButton1(17),
		   eNumericButton2(18),
		   eNumericButton3(19),
		   eNumericButton4(20),
		   eNumericButton5(21),
		   eNumericButton6(22),
		   eNumericButton7(23),
		   eNumericButton8(24),
		   eNumericButton9(25),
		   eRotateButton(26),
		   eInfoButton(27),
		   eMenuButton(28),
		   eStopButton(29)
		   }
   ACCESS      read-write
   STATUS      optional
   DESCRIPTION "Writing this object simulates pressing a button on the control		
                panel. Reading it will return the last key pressed either on		
                the control panel or via PML. The device POS will specify which		
                keys are supported.
                Additional information:
                Writing this object simulates pressing a button on the control
                panel. Reading it will return the last key pressed either on
                the control panel or via PML. The device POS will specify which
                keys are supported.
                NOTE:eGoButton(1) has been removed from the enum list. 
                Go button is not supported as this is changed to Menu."
::= { status-system 60 }
               
               
control-panel-display-contents-change-counter OBJECT-TYPE
   SYNTAX      INTEGER
   ACCESS      read-only
   STATUS      optional
   DESCRIPTION "A counter which increments whenever the contents of the front		
                panel display changes. This object is implemented as a 32-bit		
                signed integer which rolls over to zero when it reaches a		
                maximum value."
::= { status-system 63 }
               
               
control-panel-display-contents-crc OBJECT-TYPE
   SYNTAX      INTEGER
   ACCESS      read-only
   STATUS      optional
   DESCRIPTION "Reading this object returns a 32-bit Cyclical Redundancy Check		
                (CRC) which represents the current contents of the display.
                Additional information:
                This object has been implimented as an 8-bit CRC for
                this product."
::= { status-system 64 }
               
               
control-panel-display-graphical-contents OBJECT-TYPE
   SYNTAX      OCTET STRING
   ACCESS      read-only
   STATUS      optional
   DESCRIPTION "Reading this object returns a graphical file format image		
                representing the current pixel content of the display. The		
                device POS will specify the expected screen resolution, color		
                depth of the display and graphics file format for a given		
                product (eg. 160x64x1 GIF format OR 640x240x4 JPEG format). If		
                the image is large enough that it needs to be returned in		
                multiple objects then each array object will contain a portion		
                of the image. The image will then need to be reconstructed by a		
                host application. An application that needs to determine if		
                their is an additional object to be retreived will need to		
                perform a GETNEXT operation until there are no more objects in		
                the sub-tree.
                Additional information:
                This object returns a GIF image that represents the
                current contents of the 160x64x1 control panel display.  Most
                display images require more than one instance of this object
                in order to retreive the complete GIF image."
::= { control-panel-display 1 }
               
               
energy-star OBJECT-TYPE
   SYNTAX      INTEGER
   ACCESS      read-write
   STATUS      optional
   DESCRIPTION "Returns or changes the Energy Star sleep value. If the value		
                is greater than zero, then the device will go into energy		
                saving sleep mode after the print engine has been idle for the		
                number of seconds specified by this object. A value of zero		
                means Energy Star is disabled and the device will not go to		
                sleep based on print engine idle time. The value must be		
                non-negative.
                Additional information:
                Returns or changes the Energy Star sleep value.
                The device will go into energy saving sleep
                mode after the print engine has been idle for
                the number of seconds specified by this
                object.  
                
                Laserjet 4700 MFP supports values of 0, 60, 900, 1800,
                2700, 3600, 5400, 7200, 14400  seconds.  A value of 0 means
                never enter sleep mode based on the print engine
                idle time.  Setting to an unsupported value causes
                the printer to substitute a value (listed
                below) and to return <noError>
                status.  Setting this value when the printer is in
                sleep mode will not cause it to wakeup unless it is
                set to 0.  
                
                The values are as follow:  
                <=0                 snap to 0  
                >=1    and <= 1349  snap to 900   (15 minutes)  
                >=1350 and <= 2249  snap to 1800  (30 minutes)  
                >=2250 and <= 3149  snap to 2700  (45 minutes)  
                >=3150 and <= 4499  snap to 3600  (1 hour)  
                >=4500 and <= 6299  snap to 5400  (90 minutes)  
                >=6300 and <= 10799 snap to 7200  (2 hours)  
                >=10800             snap to 14400 (4 hours)."
::= { settings-system 1 }
               
               
sleep-mode OBJECT-TYPE
   SYNTAX      INTEGER {
		   eFalse(1),
		   eTrue(2)
		   }
   ACCESS      read-write
   STATUS      optional
   DESCRIPTION "Returns eTrue if the device is in energy saving sleep mode,		
                otherwise returns eFalse. Setting SLEEP-MODE to eFalse causes		
                the device to wake up, if it is in sleep mode. Setting		
                SLEEP-MODE to eTrue causes the device to go into sleep mode.
                Additional information:
                This object returns eTrue if the device is in
                energy saving sleep mode, otherwise it returns eFalse.  
                Setting this object to eTrue while the printer
                is awake will not change the printer's current state
                and will return <genErr>
                status. NOTE: This object should behave this way
                when the printer does not have an instant-on fuser.  
                Setting this object to eTrue while printer is already
                in Sleep Mode will not change the printer's
                current state and will return <noError> status.  
                Setting this object to eFalse while printer is already
                awake will not change the printer's current state and
                will return <noError> status.  
                Setting this object to eFalse while the printer is
                asleep causes the device to wake up.   "
::= { settings-system 2 }
               
               
on-off-line OBJECT-TYPE
   SYNTAX      INTEGER {
		   eOnline(1),
		   eOffline(2),
		   eOfflineAtEndOfJob(3)
		   }
   ACCESS      read-write
   STATUS      optional
   DESCRIPTION "To bring the PDL processing sub-system on or off line. If the		
                device is a printer, then the printer does not process print		
                job data when the printer is off line. PML communication		
                persists.
                Additional information:
                When the printer is in the Offline state,
                printing will stop as soon as possible (no more sheets
                of media are pulled from input trays).  The I/O
                is taken offline also.  
                
                Setting to eOnline has the following affect:
                Printer will immediately go to or remain in the Online
                state; <noError> status is returned.  
                If the printer's current state
                is Offline with a pending error condition that
                prevents the printer from going to the Online
                state, the printer will remain in the Offline state;
                <genErr> status is returned
                (see the Control Panel ERS for a list of error
                conditions).  
                
                Setting to eOffline has the following affect:
                Printer will immediately go to or remain in the
                Offline state; <noError> status is returned.
                If pages are being printed, those pages will complete
                with the printer in the Offline state.  
                
                Setting to eOfflineAtEndOfJob has the following
                affect:  
                If not in a job or already in the Offline state, the
                printer will immediately go to or remain in the
                Offline state; <noError> status is returned.  
                If in a job and the current state is Online, the
                printer will remain in the Online state, with the
                value of this object as eOfflineAtEndOfJob, until the
                end of the job; <noError> status is returned. At the end of
                the job, the printer goes to the Offline state and the
                value of this object becomes eOffline.  
                Setting this object to eOffline or eOnline before the
                end of the job causes the action for that value to be
                taken immediately."
::= { status-system 5 }
               
               
continue OBJECT-TYPE
   SYNTAX      INTEGER {
		   eInitiateAction(1),
		   eRetry(2),
		   eRetryAndCheck(3),
		   eUseLoadedMedia(4),
		   eEjectAndWait(5),
		   eSelectMediaSize(6)
		   }
   ACCESS      write-only
   STATUS      optional
   DESCRIPTION "A device can support a class of errors called continuable		
                errors. When a continuable error is encountered, the device		
                requires a continue event to occur before the device will		
                continue operation. One continue event is setting the CONTINUE		
                object to eInitiateAction. Devices can support other continue		
                events, like auto-continue. A continue event causes the		
                continuable error to be acknowledged, thus allowing the device		
                to continue. Each device needs to list the continuable errors.		
                If the device doesn't currently have an unacknowledged		
                continuable error, the response will contain		
                <genErr>.
                Additional information:
                See the CLEARABLE-WARNING and AUTO-CONTINUE objects for the
                errors that this object will clear."
::= { status-system 6 }
               
               
auto-continue OBJECT-TYPE
   SYNTAX      INTEGER {
		   eOff(1),
		   eOn(2)
		   }
   ACCESS      read-write
   STATUS      optional
   DESCRIPTION "Indicates if the device will automatically continue after		
                encountering a continuable error. If AUTO-CONTINUE is set to		
                eOn, the device will automatically generate continue event to		
                acknowledge continuable errors. If AUTO-CONTINUE is set to		
                eOff, then some other continue event will have to acknowledge		
                the continuable error.
                Additional information:
                If this is set to eOn the device displays an
                error message and goes offline for ten seconds. After ten seconds the
                printer automatically returns to the online state.  
                
                If this is set to eOff then the device displays an error message and
                goes offline. It remains offline until the operator presses the GO key or
                until the CONTINUE object is set.  
                
                If the printer is not idle, the new value may not take effect
                until a job boundary is reached. If a get is done on this object before
                the job boundary is reached, the value last set will be returned."
::= { status-system 7 }
               
               
simm1-type OBJECT-TYPE
   SYNTAX      INTEGER {
		   eEmpty(1),
		   eUnknown(2),
		   eUnSupported(3),
		   eReadOnlyMemory(4),
		   eVolatileRandomAccessMemory(5),
		   eFlashMemory(7),
		   eRamRom(9)
		   }
   ACCESS      read-only
   STATUS      optional
   DESCRIPTION "Returns an indication of the type of option installed in SIMM		
                slot 1.    	
                    eEmpty means the device did not detect any option installed		
                        in the interface slot.    	
                    eUnknown means the device doesn't recognize the installed		
                        option.    	
                    eUnSupported means the device recognizes the installed		
                        option, but does not support the option.    	
                    eReadOnlyMemory means the installed option contains ROM		
                        Ics.    	
                    eVolatileRandomAccessMemory means the installed option		
                        contains RAM ICs that loose data when the power is		
                        turned off.    	
                    eNonVolatileRandomAccessMemory means that the installed		
                        option contains RAM ICs that do not loose data when the		
                        power is turned off.    	
                    eFlashMemory means that the installed option contains a		
                        type of non-volatile RAM that needs to be erased before		
                        it can be written.    	
                    eDiskDrive means the installed option contains a disk		
                        drive.    	
                    eRamRom means the installed option contains both volatile		
                        random access memory and read only memory.    	
                    eInputPHD means the installed option is an input paper		
                        handling device.    	
                    eOutputPHD means the installed option is an output paper		
                        handling device. eIOCard means the installed option is		
                        an I/O card.    	
                    eVolatileRAMOnBoardMemory means the installed option		
                        contains on board RAM ICs that loose data when the		
                        power is turned off.  
                Additional information:
                This object is used for describing DIMMs instead
                of SIMMs on $product_str. eRamRom is used to denote $product_str's combo simm."
::= { simm1 4 }
               
               
simm1-capacity OBJECT-TYPE
   SYNTAX      INTEGER
   ACCESS      read-only
   STATUS      optional
   DESCRIPTION "Returns an indication of the capacity of the SIMM installed in		
                SIMM slot 1. The capacity is dependent on the type of option,		
                as indicated by the SIMM1-TYPE object. This object has no		
                meaning if the installed option type is eUnknown or		
                eReadOnlyMemory. This object contains the size, in bytes, if		
                the installed option type is eVolatileRandomAccessMemory,		
                eNonVolatileRandomAccessMemory, eFlashMemory, or eDiskDrive. If		
                the type of the installed option is eRamRom, this object		
                contains the size, in bytes, of the random access memory. If		
                the type of the installed option is eInputPHD, the capacity		
                indicates the number of input trays supported by the installed		
                option. If the type of the installed option is eOutputPHD, the		
                capacity indicates the number of output bins supported by the		
                installed option. If the type of the installed option is		
                eIOCard, the capacity indicates the number of logical I/O ports		
                supported by the I/O card.
                Additional information:
                Returns an indication of the capacity of the 
                installed option in bytes.  This object is not 
                supported unless the SIMM1-TYPE type is 
                eVolatileRandomAccessMemory, eRamRom, or eFlashMemory.
                For eRamRom only the size of the Ram portion of the SIMM
                is returned."
::= { simm1 5 }
               
               
simm1-bank1-type OBJECT-TYPE
   SYNTAX      INTEGER {
		   eEmpty(1),
		   eUnknown(2),
		   eUnSupported(3),
		   eReadOnlyMemory(4),
		   eVolatileRandomAccessMemory(5),
		   eFlashMemory(7),
		   eRamRom(9)
		   }
   ACCESS      read-only
   STATUS      optional
   DESCRIPTION "Returns an indication of the type of option installed in Bank 1		
                of SIMM slot 1. See SIMM1-TYPE for a description.
                Additional information:
                This object is used for describing the type
                of DIMM banks.  Each physical DIMM slot has up to 2 banks."
::= { simm1-bank1 1 }
               
               
simm1-bank1-capacity OBJECT-TYPE
   SYNTAX      INTEGER
   ACCESS      read-only
   STATUS      optional
   DESCRIPTION "Returns an indication of the capacity of Bank 1 of the SIMM		
                installed in SIMM slot 1. See SIMM1-CAPACITY for a		
                description.
                Additional information:
                Returns an indication of the capacity of the
                installed bank option in bytes.  This object is not
                supported unless the SIMM1-BANK1-TYPE type is
                eReadOnlyMemory, eFlashMemory, eEDORandomAccessMemory,
                eSDRandomAccessMemory, eSRandomAccessMemory,
                or eFPMRandomAccessMemory."
::= { simm1-bank1 2 }
               
               
simm1-bank2-type OBJECT-TYPE
   SYNTAX      INTEGER {
		   eEmpty(1),
		   eUnknown(2),
		   eUnSupported(3),
		   eReadOnlyMemory(4),
		   eVolatileRandomAccessMemory(5),
		   eFlashMemory(7),
		   eRamRom(9)
		   }
   ACCESS      read-only
   STATUS      optional
   DESCRIPTION "Returns an indication of the type of option installed in Bank 2		
                of SIMM slot 1. See SIMM1-TYPE for a description.
                Additional information:
                This object is used for describing the type
                of DIMM banks.  Each physical DIMM slot has up to 2 banks."
::= { simm1-bank2 1 }
               
               
simm1-bank2-capacity OBJECT-TYPE
   SYNTAX      INTEGER
   ACCESS      read-only
   STATUS      optional
   DESCRIPTION "Returns an indication of the capacity of Bank 2 of the SIMM		
                installed in SIMM slot 1. See SIMM1-CAPACITY for a		
                description.
                Additional information:
                Returns an indication of the capacity of the
                installed bank option in bytes.  This object is not
                supported unless the SIMM1-BANK2-TYPE type is
                eReadOnlyMemory, eFlashMemory, eEDORandomAccessMemory,
                eSDRandomAccessMemory, eSRandomAccessMemory,
                or eFPMRandomAccessMemory."
::= { simm1-bank2 2 }
               
               
simm2-type OBJECT-TYPE
   SYNTAX      INTEGER {
		   eEmpty(1),
		   eUnknown(2),
		   eUnSupported(3),
		   eReadOnlyMemory(4),
		   eVolatileRandomAccessMemory(5),
		   eFlashMemory(7),
		   eRamRom(9)
		   }
   ACCESS      read-only
   STATUS      optional
   DESCRIPTION "Returns an indication of the type of option installed in SIMM		
                slot 2. See SIMM1-TYPE for a description.
                Additional information:
                This object is used for describing DIMMs instead
                of SIMMs on $product_str. eRamRom is used to denote $product_str's combo simm."
::= { simm2 4 }
               
               
simm2-capacity OBJECT-TYPE
   SYNTAX      INTEGER
   ACCESS      read-only
   STATUS      optional
   DESCRIPTION "Returns an indication of the capacity of the SIMM installed in		
                SIMM slot 2. See SIMM1-CAPACITY for a description.
                Additional information:
                This object is used for describing DIMMs instead
                of SIMMs on $product_str. Returns an indication of the capacity of the
                installed option in bytes.  This object is not
                supported unless the SIMM2-TYPE type is
                eVolatileRandomAccessMemory, eRamRom, or eFlashMemory.
                For eRamRom only the size of the Ram portion of the
                SIMM is returned."
::= { simm2 5 }
               
               
simm2-bank1-type OBJECT-TYPE
   SYNTAX      INTEGER {
		   eEmpty(1),
		   eUnknown(2),
		   eUnSupported(3),
		   eReadOnlyMemory(4),
		   eVolatileRandomAccessMemory(5),
		   eFlashMemory(7),
		   eRamRom(9)
		   }
   ACCESS      read-only
   STATUS      optional
   DESCRIPTION "Returns an indication of the type of option installed in Bank 1		
                of SIMM slot 2. See SIMM1-TYPE for a description.
                Additional information:
                This object is used for describing the type
                of DIMM banks.  Each physical DIMM slot has up to 2 banks."
::= { simm2-bank1 1 }
               
               
simm2-bank1-capacity OBJECT-TYPE
   SYNTAX      INTEGER
   ACCESS      read-only
   STATUS      optional
   DESCRIPTION "Returns an indication of the capacity of Bank 1 of the SIMM		
                installed in SIMM slot 2. See SIMM1-CAPACITY for a		
                description.
                Additional information:
                Returns an indication of the capacity of the
                installed bank option in bytes.  This object is not
                supported unless the SIMM2-BANK1-TYPE type is
                eReadOnlyMemory, eFlashMemory, eEDORandomAccessMemory,
                eSDRandomAccessMemory, eSRandomAccessMemory,
                or eFPMRandomAccessMemory."
::= { simm2-bank1 2 }
               
               
simm2-bank2-type OBJECT-TYPE
   SYNTAX      INTEGER {
		   eEmpty(1),
		   eUnknown(2),
		   eUnSupported(3),
		   eReadOnlyMemory(4),
		   eVolatileRandomAccessMemory(5),
		   eFlashMemory(7),
		   eRamRom(9)
		   }
   ACCESS      read-only
   STATUS      optional
   DESCRIPTION "Returns an indication of the type of option installed in Bank 2		
                of SIMM slot 2. See SIMM1-TYPE for a description.
                Additional information:
                This object is used for describing the type
                of DIMM banks.  Each physical DIMM slot has up to 2 banks."
::= { simm2-bank2 1 }
               
               
simm2-bank2-capacity OBJECT-TYPE
   SYNTAX      INTEGER
   ACCESS      read-only
   STATUS      optional
   DESCRIPTION "Returns an indication of the capacity of Bank 2 of the SIMM		
                installed in SIMM slot 2. See SIMM1-CAPACITY for a		
                description.
                Additional information:
                Returns an indication of the capacity of the
                installed bank option in bytes.  This object is not
                supported unless the SIMM2-BANK2-TYPE type is
                eReadOnlyMemory, eFlashMemory, eEDORandomAccessMemory,
                eSDRandomAccessMemory, eSRandomAccessMemory,
                or eFPMRandomAccessMemory."
::= { simm2-bank2 2 }
               
               
simm3-type OBJECT-TYPE
   SYNTAX      INTEGER {
		   eEmpty(1),
		   eUnknown(2),
		   eUnSupported(3),
		   eReadOnlyMemory(4),
		   eVolatileRandomAccessMemory(5),
		   eFlashMemory(7),
		   eRamRom(9)
		   }
   ACCESS      read-only
   STATUS      optional
   DESCRIPTION "Returns an indication of the type of option installed in SIMM		
                slot 3. See SIMM1-TYPE for a description."
::= { simm3 4 }
               
               
simm3-capacity OBJECT-TYPE
   SYNTAX      INTEGER
   ACCESS      read-only
   STATUS      optional
   DESCRIPTION "Returns an indication of the capacity of the SIMM installed in		
                SIMM slot 3. See SIMM1-CAPACITY for a description.
                Additional information:
                This object is used for describing DIMMs instead
                of SIMMs on $product_str. Returns an indication of the capacity of the
                installed option in bytes.  This object is not
                supported unless the SIMM3-TYPE type is
                eVolatileRandomAccessMemory, eRamRom, or eFlashMemory.
                For eRamRom only the size of the Ram portion of the
                simm is returned."
::= { simm3 5 }
               
               
simm3-bank1-type OBJECT-TYPE
   SYNTAX      INTEGER {
		   eEmpty(1),
		   eUnknown(2),
		   eUnSupported(3),
		   eReadOnlyMemory(4),
		   eVolatileRandomAccessMemory(5),
		   eFlashMemory(7),
		   eRamRom(9)
		   }
   ACCESS      read-only
   STATUS      optional
   DESCRIPTION "Returns an indication of the type of option installed in Bank 1		
                of SIMM slot 3. See SIMM1-TYPE for a description.
                Additional information:
                This object is used for describing the type
                of DIMM banks.  Each physical DIMM slot has up to 2 banks."
::= { simm3-bank1 1 }
               
               
simm3-bank1-capacity OBJECT-TYPE
   SYNTAX      INTEGER
   ACCESS      read-only
   STATUS      optional
   DESCRIPTION "Returns an indication of the capacity of Bank 1 of the SIMM		
                installed in SIMM slot 3. See SIMM1-CAPACITY for a		
                description.
                Additional information:
                Returns an indication of the capacity of the
                installed bank option in bytes.  This object is not
                supported unless the SIMM3-BANK1-TYPE type is
                eReadOnlyMemory, eFlashMemory, eEDORandomAccessMemory,
                eSDRandomAccessMemory, eSRandomAccessMemory,
                or eFPMRandomAccessMemory."
::= { simm3-bank1 2 }
               
               
simm3-bank2-type OBJECT-TYPE
   SYNTAX      INTEGER {
		   eEmpty(1),
		   eUnknown(2),
		   eUnSupported(3),
		   eReadOnlyMemory(4),
		   eVolatileRandomAccessMemory(5),
		   eFlashMemory(7),
		   eRamRom(9)
		   }
   ACCESS      read-only
   STATUS      optional
   DESCRIPTION "Returns an indication of the type of option installed in Bank 2		
                of SIMM slot 3. See SIMM1-TYPE for a description.
                Additional information:
                This object is used for describing the type
                of DIMM banks.  Each physical DIMM slot has up to 2 banks."
::= { simm3-bank2 1 }
               
               
simm3-bank2-capacity OBJECT-TYPE
   SYNTAX      INTEGER
   ACCESS      read-only
   STATUS      optional
   DESCRIPTION "Returns an indication of the capacity of Bank 2 of the SIMM		
                installed in SIMM slot 3. See SIMM1-CAPACITY for a		
                description.
                Additional information:
                Returns an indication of the capacity of the
                installed bank option in bytes.  This object is not
                supported unless the SIMM3-BANK2-TYPE type is
                eReadOnlyMemory, eFlashMemory, eEDORandomAccessMemory,
                eSDRandomAccessMemory, eSRandomAccessMemory,
                or eFPMRandomAccessMemory."
::= { simm3-bank2 2 }
               
               
simm4-type OBJECT-TYPE
   SYNTAX      INTEGER {
		   eEmpty(1),
		   eUnknown(2),
		   eUnSupported(3),
		   eReadOnlyMemory(4),
		   eVolatileRandomAccessMemory(5),
		   eFlashMemory(7),
		   eRamRom(9)
		   }
   ACCESS      read-only
   STATUS      optional
   DESCRIPTION "Returns an indication of the type of option installed in SIMM		
                slot 4. See SIMM1-TYPE for a description."
::= { simm4 4 }
               
               
simm4-capacity OBJECT-TYPE
   SYNTAX      INTEGER
   ACCESS      read-only
   STATUS      optional
   DESCRIPTION "Returns an indication of the capacity of the SIMM installed in		
                SIMM slot 4. See SIMM1-CAPACITY for a description.
                Additional information:
                This object is used for describing DIMMs instead
                of SIMMs on $product_str. Returns an indication of the capacity of the
                installed option in bytes.  This object is not
                supported unless the SIMM4-TYPE type is
                eVolatileRandomAccessMemory, eRamRom, or eFlashMemory.
                For eRamRom only the size of the Ram portion of the
                simm is returned."
::= { simm4 5 }
               
               
simm4-bank1-type OBJECT-TYPE
   SYNTAX      INTEGER {
		   eEmpty(1),
		   eUnknown(2),
		   eUnSupported(3),
		   eReadOnlyMemory(4),
		   eVolatileRandomAccessMemory(5),
		   eFlashMemory(7),
		   eRamRom(9)
		   }
   ACCESS      read-only
   STATUS      optional
   DESCRIPTION "Returns an indication of the type of option installed in Bank 1		
                of SIMM slot 4. See SIMM1-TYPE for a description.
                Additional information:
                This object is used for describing the type
                of DIMM banks.  Each physical DIMM slot has up to 2 banks."
::= { simm4-bank1 1 }
               
               
simm4-bank1-capacity OBJECT-TYPE
   SYNTAX      INTEGER
   ACCESS      read-only
   STATUS      optional
   DESCRIPTION "Returns an indication of the capacity of Bank 1 of the SIMM		
                installed in SIMM slot 4. See SIMM1-CAPACITY for a		
                description.
                Additional information:
                Returns an indication of the capacity of the
                installed bank option in bytes.  This object is not
                supported unless the SIMM4-BANK1-TYPE type is
                eReadOnlyMemory, eFlashMemory, eEDORandomAccessMemory,
                eSDRandomAccessMemory, eSRandomAccessMemory,
                or eFPMRandomAccessMemory."
::= { simm4-bank1 2 }
               
               
simm4-bank2-type OBJECT-TYPE
   SYNTAX      INTEGER {
		   eEmpty(1),
		   eUnknown(2),
		   eUnSupported(3),
		   eReadOnlyMemory(4),
		   eVolatileRandomAccessMemory(5),
		   eFlashMemory(7),
		   eRamRom(9)
		   }
   ACCESS      read-only
   STATUS      optional
   DESCRIPTION "Returns an indication of the type of option installed in Bank 2		
                of SIMM slot 4. See SIMM1-TYPE for a description.
                Additional information:
                This object is used for describing the type
                of DIMM banks.  Each physical DIMM slot has up to 2 banks."
::= { simm4-bank2 1 }
               
               
simm4-bank2-capacity OBJECT-TYPE
   SYNTAX      INTEGER
   ACCESS      read-only
   STATUS      optional
   DESCRIPTION "Returns an indication of the capacity of Bank 2 of the SIMM		
                installed in SIMM slot 4. See SIMM1-CAPACITY for a		
                description.
                Additional information:
                Returns an indication of the capacity of the
                installed bank option in bytes.  This object is not
                supported unless the SIMM4-BANK2-TYPE type is
                eReadOnlyMemory, eFlashMemory, eEDORandomAccessMemory,
                eSDRandomAccessMemory, eSRandomAccessMemory,
                or eFPMRandomAccessMemory."
::= { simm4-bank2 2 }
               
               
simm5-type OBJECT-TYPE
   SYNTAX      INTEGER {
		   eEmpty(1),
		   eUnknown(2),
		   eUnSupported(3),
		   eReadOnlyMemory(4),
		   eVolatileRandomAccessMemory(5),
		   eFlashMemory(7),
		   eRamRom(9)
		   }
   ACCESS      read-only
   STATUS      optional
   DESCRIPTION "Returns an indication of the type of option installed in SIMM		
                slot 5. See SIMM1-TYPE for a description."
::= { simm5 4 }
               
               
simm5-capacity OBJECT-TYPE
   SYNTAX      INTEGER
   ACCESS      read-only
   STATUS      optional
   DESCRIPTION "Returns an indication of the capacity of the SIMM installed in		
                SIMM slot 5. See SIMM1-CAPACITY for a description.
                Additional information:
                This object is used for describing DIMMs instead
                of SIMMs on $product_str. Returns an indication of the capacity of the
                installed option in bytes.  This object is not
                supported unless the SIMM5-TYPE type is
                eVolatileRandomAccessMemory, eRamRom, or eFlashMemory.
                For eRamRom only the size of the Ram portion of the
                simm is returned."
::= { simm5 5 }
               
               
simm5-bank1-type OBJECT-TYPE
   SYNTAX      INTEGER {
		   eEmpty(1),
		   eUnknown(2),
		   eUnSupported(3),
		   eReadOnlyMemory(4),
		   eVolatileRandomAccessMemory(5),
		   eFlashMemory(7),
		   eRamRom(9)
		   }
   ACCESS      read-only
   STATUS      optional
   DESCRIPTION "Returns an indication of the type of option installed in Bank 1		
                of SIMM slot 5. See SIMM1-TYPE for a description.
                Additional information:
                This object is used for describing the type
                of DIMM banks.  Each physical DIMM slot has up to 2 banks."
::= { simm5-bank1 1 }
               
               
simm5-bank1-capacity OBJECT-TYPE
   SYNTAX      INTEGER
   ACCESS      read-only
   STATUS      optional
   DESCRIPTION "Returns an indication of the capacity of Bank 1 of the SIMM		
                installed in SIMM slot 5. See SIMM1-CAPACITY for a		
                description.
                Additional information:
                Returns an indication of the capacity of the
                installed bank option in bytes.  This object is not
                supported unless the SIMM5-BANK1-TYPE type is
                eReadOnlyMemory, eFlashMemory, eEDORandomAccessMemory,
                eSDRandomAccessMemory, eSRandomAccessMemory,
                or eFPMRandomAccessMemory."
::= { simm5-bank1 2 }
               
               
simm5-bank2-type OBJECT-TYPE
   SYNTAX      INTEGER {
		   eEmpty(1),
		   eUnknown(2),
		   eUnSupported(3),
		   eReadOnlyMemory(4),
		   eVolatileRandomAccessMemory(5),
		   eFlashMemory(7),
		   eRamRom(9)
		   }
   ACCESS      read-only
   STATUS      optional
   DESCRIPTION "Returns an indication of the type of option installed in Bank 2		
                of SIMM slot 5. See SIMM1-TYPE for a description.
                Additional information:
                This object is used for describing the type
                of DIMM banks.  Each physical DIMM slot has up to 2 banks."
::= { simm5-bank2 1 }
               
               
simm5-bank2-capacity OBJECT-TYPE
   SYNTAX      INTEGER
   ACCESS      read-only
   STATUS      optional
   DESCRIPTION "Returns an indication of the capacity of Bank 2 of the SIMM		
                installed in SIMM slot 5. See SIMM1-CAPACITY for a		
                description.
                Additional information:
                Returns an indication of the capacity of the
                installed bank option in bytes.  This object is not
                supported unless the SIMM5-BANK2-TYPE type is
                eReadOnlyMemory, eFlashMemory, eEDORandomAccessMemory,
                eSDRandomAccessMemory, eSRandomAccessMemory,
                or eFPMRandomAccessMemory."
::= { simm5-bank2 2 }
               
               
cancel-job OBJECT-TYPE
   SYNTAX      INTEGER(-1..32767)
   ACCESS      write-only
   STATUS      optional
   DESCRIPTION "Cancels the print job whose ID matches the value written to the		
                CANCEL-JOB object. The host first learns the job ID using the		
                CURRENT-JOB-PARSING-ID command. If the printer has completely		
                processed the job, the printer responds with		
                <badValue>. If the value of the		
                CURRENT-JOB-PARSING-ID is smaller than the value written to the		
                CANCEL-JOB object, then the printer responds with		
                <badValue>. When read, returns the value		
                of the last job ID what was canceled, or -1 to indicate no job		
                has been canceled.
                Additional information:
                If the value written matches the ID of a job that is
                currently being canceled (for any reason),
                the printer responds with <noError>.  
                It uses job ID's in the range of -1..32767.
                Because the ID number can wrap to zero,
                CURRENT-JOB-PARSING-ID may be smaller than the value
                written to this object; when this occurs, no error
                will result as long as the ID is for a currently
                processing job. This object is write only, so the
                comment in the general description stating the
                job ID will be returned on a read does not
                apply. A -1 represents the current job"
::= { settings-job 2 }
               
               
os-execute-file OBJECT-TYPE
   SYNTAX      OCTET STRING
   ACCESS      write-only
   STATUS      optional
   DESCRIPTION "This object's input is a null-terminated string representing a		
                fully-qualified path name for an executable file. This object		
                causes the file to be executed by the OS.
                Additional information:
                This object's input is a null-terminated string of two or
                more whitespace-separated tokens.  The first token is a path
                to a directory to make the current working directory.  The
                second token is a path to an executable file to be executed.
                Any remaining whitespace-separated tokens are optional and
                will be passed as parameters to the executable.  The paths 
                to the directory and executable can be either PJL style 
                (e.g., 1:\app\example) or UNIX-style (e.g., 
                /hpmnt/dsk_ide1a/app/example).  The executable is run in
                a separate process."
::= { operating-system 1 }
               
               
form-feed OBJECT-TYPE
   SYNTAX      INTEGER {
		   eInitiateAction(1)
		   }
   ACCESS      write-only
   STATUS      optional
   DESCRIPTION "Instructs the PDL processing sub-system to finishing processing		
                the current page of the current job. Form feed is also known as		
                close page or eject page. If the PDL processing sub-system is		
                in a FORM-FEED-NEEDED state, this causes the device to flush or		
                finish processing the current page of the current job. If the		
                device is not in the FORM-FEED-NEEDED state, an		
                <genErr> will occur."
::= { settings-pdl 5 }
               
               
form-feed-needed OBJECT-TYPE
   SYNTAX      INTEGER {
		   eFalse(1),
		   eTrue(2)
		   }
   ACCESS      read-only
   STATUS      optional
   DESCRIPTION "Indicates if the PDL processing sub-system has made marks on		
                the current page and the source subsystem has been idle for a		
                device specific amount of time.
                Additional information:
                $product_str will set this object to eTrue when it
                has made marks on the current page, the IO-TIMEOUT has
                expired while PCL was running in `backward-compatibility
                mode' (which is caused by jobs consisting purely of PCL
                data with no prepended PJL commands), and no data is pending
                on another I/O. Once it is set to eTrue, more data on the
                same I/O will cause this object to be set to eFalse, until
                the above conditions are met again."
::= { status-pdl 2 }
               
               
background-status-msg-line1-part1 OBJECT-TYPE
   SYNTAX      OCTET STRING (SIZE(0..16))
   ACCESS      read-write
   STATUS      optional
   DESCRIPTION "The string displayed on the device's front panel in place of		
                the printer's built-in background status string. An example		
                built-in background status string is '00 READY'.
                Additional information:
                The display size for the $product_str printers is 2 X 16.
                The value of this object and the current value of
                BACKGROUND-STATUS-MSG-LINE2-PART1 are displayed
                together on the 2-line display, but they must 
                be set independently.  If line 2 has been set, and the
                next message to be displayed only requires line 1,
                BACKGROUND-STATUS-MSG-LINE2-PART1 must be set to the 
                null string to clear it.  
                This object allows a message to be displayed when
                it is the highest priority message. Setting this
                object does not guarantee the message will be
                displayed; and reading it returns the value last
                written, not the currently displayed message (use
                prtConsoleDisplayBufferText to read the
                display).  
                The priority assigned for displaying this message
                is one lower than the READY message.  In other words,
                the only message that can be replaced by these
                objects is the READY message.  
                To clear the message, write a null string to both
                this object and BACKGROUND-STATUS-MSG-LINE2-PART1."
::= { background-message1 1 }
               
               
background-status-msg-line2-part1 OBJECT-TYPE
   SYNTAX      OCTET STRING (SIZE(0..16))
   ACCESS      read-write
   STATUS      optional
   DESCRIPTION "The string displayed on the device's front panel in place of		
                the printer's built-in background status string. An example		
                built-in background status string is '00 READY'.
                Additional information:
                See BACKGROUND-STATUS-MSG-LINE1-PART1"
::= { background-message2 1 }
               
               
error-log-clear OBJECT-TYPE
   SYNTAX      INTEGER {
		   eClearErrorLog(1)
		   }
   ACCESS      write-only
   STATUS      optional
   DESCRIPTION "Setting this object clears all the entries in the error log		
                sub-tree.
                Additional information:
                Setting this object removes all errors that have been
                stored in the printer's non-volatile memory."
::= { status-system 38 }
               
               
clearable-warning OBJECT-TYPE
   SYNTAX      INTEGER {
		   eOn(2),
		   eJob(3)
		   }
   ACCESS      read-write
   STATUS      optional
   DESCRIPTION "Returns or controls how the device will track clearable		
                warnings. A clearable warning indicates a transient event in		
                the device. The device will continue after the transient event		
                occurs. If CLEARABLE-WARNING is eOff, the device does not track		
                clearable warnings. If CLEARABLE-WARNING is eOn, all clearable		
                warnings will be tracked until cleared (acknowledged). If		
                CLEARABLE-WARNING is eJob, a clearable warning generated due to		
                an event that occurs because of the print job being processed		
                will be automatically cleared when the device has finished		
                processing the job. Example clearable warning events include		
                the device altering resolution or page protection due to memory		
                constraints. The POS will document what transient events are		
                treated as clearable warnings.
                Additional information:
                If set to eOn, the warning is displayed until the GO key
                is pressed or the CONTINUE object is set.  
                
                If set to eJob, the warning is displayed until the end of the job in which
                it was generated."
::= { settings-job 1 }
               
               
error1-time-stamp OBJECT-TYPE
   SYNTAX      INTEGER
   ACCESS      read-only
   STATUS      optional
   DESCRIPTION "Contains some sort of time stamp indicating when error 1		
                occurred. Example time stamps include the actual time the error		
                occurred (in seconds since Jan. 1, 1970), and the total engine		
                page count. The device POS documents the meaning of the time		
                stamp.
                Additional information:
                This item contains the engine
                page count when the error occurred.  
                
                If there is currently no error entry for this object, a '0' will be returned.
                Note that '0' may also be returned when there is a valid error, but a current
                page count was unavailable. If ERROR1-CODE object also returns '0', then
                an error has not yet been logged for this object.
                
                See ERROR1-CODE for an explanation of the order used for storing errors."
::= { error1 1 }
               
               
error1-code OBJECT-TYPE
   SYNTAX      INTEGER
   ACCESS      read-only
   STATUS      optional
   DESCRIPTION "Contains a device specific error code. Each device POS should		
                list what errors are logged to the error log and the meaning of		
                each supported error code value.
                Additional information:
                Returns a device specific error code.
                If the error code returned is '0', then the printer has not yet logged an
                error for this object.
                When the maximum number of errors is reached (30 on LaserJet printers), and
                a new error occurs, the error in ERROR1-CODE will be replaced by the
                one in ERROR2-CODE, and so on until the last error object will be given
                the value of the new error.  
                
                The error number is returned in the upper 16 bits.
                If it is 68, 69, 79, or 80, then the sub code is returned in the lower
                16 bits (eg. 68 001C, where the subcode is already a hexadecimal value).
                If the error number is any other number, then the 1st sub code (XX)
                will be in bits 15-8 and the 2nd sub code (YY) will be in bits 7-0 (eg.
                55.04.02) where XX=04 and YY=02).  
                
                See the Control Panel ERS for specific information about the meaning of
                each code.  
                
                Example: If the error is 68 001A, then the value returned will be 4456474.  
                To break it down: 4456474 = 0x0044001A  
                The upper 16 bits: 0x0044 = 68  
                The lower 16 bits: 0x001A = 001A
                Which is the error: 68 001A  
                
                Example: If the error is 55.04.241, then the error code will be 3605745.  
                To break it down: 3605745 = 0x003704F1  
                The upper 16 bits: 0x0037 = 55  
                The upper byte of the lower 16 bits: 0x04 = 04  
                The lower byte of the lower 16 bits: 0xF1 = 241  
                Which is the error: 55.04.241"
::= { error1 2 }
               
               
error1-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                This item contains the date and 
                the time when the error occurred.  
                
                It returns the date and the time at which the error occured in hexadecimal.
                For instance, if  date is 2004-Jul-13 and time is 03:15 am 
                when the error was logged, then we get 04 07 0d 03 0f where,
                04 (hex) - corresponds to the year 2004.
                07 (hex) - corresponds to month 07
                0d(hex) - corresponds to date 13
                03(hex) - corresponds to hour- 03
                0f(hex) - corresponds to min- 15.  
                
                If there is currently no error entry , '00 00 00 00 00' will be returned.
                See ERROR1-CODE for an explanation of the order used for storing errors."
::= { error1 3 }
               
               
error2-time-stamp OBJECT-TYPE
   SYNTAX      INTEGER
   ACCESS      read-only
   STATUS      optional
   DESCRIPTION "Contains some sort of time stamp indicating when error 2		
                occurred. Example time stamps include the actual time the error		
                occurred (in seconds since Jan. 1, 1970), and the total engine		
                page count. The device POS documents the meaning of the time		
                stamp.
                Additional information:
                See ERROR1-TIME-STAMP."
::= { error2 1 }
               
               
error2-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error2 2 }
               
               
error2-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error2 3 }
               
               
error3-time-stamp OBJECT-TYPE
   SYNTAX      INTEGER
   ACCESS      read-only
   STATUS      optional
   DESCRIPTION "Contains some sort of time stamp indicating when error 3		
                occurred. Example time stamps include the actual time the error		
                occurred (in seconds since Jan. 1, 1970), and the total engine		
                page count. The device POS documents the meaning of the time		
                stamp.
                Additional information:
                See ERROR1-TIME-STAMP."
::= { error3 1 }
               
               
error3-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error3 2 }
               
               
error3-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error3 3 }
               
               
error4-time-stamp OBJECT-TYPE
   SYNTAX      INTEGER
   ACCESS      read-only
   STATUS      optional
   DESCRIPTION "Contains some sort of time stamp indicating when error 4		
                occurred. Example time stamps include the actual time the error		
                occurred (in seconds since Jan. 1, 1970), and the total engine		
                page count. The device POS documents the meaning of the time		
                stamp.
                Additional information:
                See ERROR1-TIME-STAMP."
::= { error4 1 }
               
               
error4-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error4 2 }
               
               
error4-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error4 3 }
               
               
error5-time-stamp OBJECT-TYPE
   SYNTAX      INTEGER
   ACCESS      read-only
   STATUS      optional
   DESCRIPTION "Contains some sort of time stamp indicating when error 5		
                occurred. Example time stamps include the actual time the error		
                occurred (in seconds since Jan. 1, 1970), and the total engine		
                page count. The device POS documents the meaning of the time		
                stamp.
                Additional information:
                See ERROR1-TIME-STAMP."
::= { error5 1 }
               
               
error5-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error5 2 }
               
               
error5-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error5 3 }
               
               
error6-time-stamp OBJECT-TYPE
   SYNTAX      INTEGER
   ACCESS      read-only
   STATUS      optional
   DESCRIPTION "Contains some sort of time stamp indicating when error 6		
                occurred. Example time stamps include the actual time the error		
                occurred (in seconds since Jan. 1, 1970), and the total engine		
                page count. The device POS documents the meaning of the time		
                stamp.
                Additional information:
                See ERROR1-TIME-STAMP."
::= { error6 1 }
               
               
error6-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error6 2 }
               
               
error6-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error6 3 }
               
               
error7-time-stamp OBJECT-TYPE
   SYNTAX      INTEGER
   ACCESS      read-only
   STATUS      optional
   DESCRIPTION "Contains some sort of time stamp indicating when error 7		
                occurred. Example time stamps include the actual time the error		
                occurred (in seconds since Jan. 1, 1970), and the total engine		
                page count. The device POS documents the meaning of the time		
                stamp.
                Additional information:
                See ERROR1-TIME-STAMP."
::= { error7 1 }
               
               
error7-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error7 2 }
               
               
error7-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error7 3 }
               
               
error8-time-stamp OBJECT-TYPE
   SYNTAX      INTEGER
   ACCESS      read-only
   STATUS      optional
   DESCRIPTION "Contains some sort of time stamp indicating when error 8		
                occurred. Example time stamps include the actual time the error		
                occurred (in seconds since Jan. 1, 1970), and the total engine		
                page count. The device POS documents the meaning of the time		
                stamp.
                Additional information:
                See ERROR1-TIME-STAMP."
::= { error8 1 }
               
               
error8-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error8 2 }
               
               
error8-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error8 3 }
               
               
error9-time-stamp OBJECT-TYPE
   SYNTAX      INTEGER
   ACCESS      read-only
   STATUS      optional
   DESCRIPTION "Contains some sort of time stamp indicating when error 9		
                occurred. Example time stamps include the actual time the error		
                occurred (in seconds since Jan. 1, 1970), and the total engine		
                page count. The device POS documents the meaning of the time		
                stamp.
                Additional information:
                See ERROR1-TIME-STAMP."
::= { error9 1 }
               
               
error9-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error9 2 }
               
               
error9-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error9 3 }
               
               
error10-time-stamp OBJECT-TYPE
   SYNTAX      INTEGER
   ACCESS      read-only
   STATUS      optional
   DESCRIPTION "Contains some sort of time stamp indicating when error 10		
                occurred. Example time stamps include the actual time the error		
                occurred (in seconds since Jan. 1, 1970), and the total engine		
                page count. The device POS documents the meaning of the time		
                stamp.
                Additional information:
                See ERROR1-TIME-STAMP."
::= { error10 1 }
               
               
error10-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error10 2 }
               
               
error10-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error10 3 }
               
               
error11-time-stamp OBJECT-TYPE
   SYNTAX      INTEGER
   ACCESS      read-only
   STATUS      optional
   DESCRIPTION "Contains some sort of time stamp indicating when error 11		
                occurred. Example time stamps include the actual time the error		
                occurred (in seconds since Jan. 1, 1970), and the total engine		
                page count. The device POS documents the meaning of the time		
                stamp.
                Additional information:
                See ERROR1-TIME-STAMP."
::= { error11 1 }
               
               
error11-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error11 2 }
               
               
error11-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error11 3 }
               
               
error12-time-stamp OBJECT-TYPE
   SYNTAX      INTEGER
   ACCESS      read-only
   STATUS      optional
   DESCRIPTION "Contains some sort of time stamp indicating when error 12		
                occurred. Example time stamps include the actual time the error		
                occurred (in seconds since Jan. 1, 1970), and the total engine		
                page count. The device POS documents the meaning of the time		
                stamp.
                Additional information:
                See ERROR1-TIME-STAMP."
::= { error12 1 }
               
               
error12-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error12 2 }
               
               
error12-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error12 3 }
               
               
error13-time-stamp OBJECT-TYPE
   SYNTAX      INTEGER
   ACCESS      read-only
   STATUS      optional
   DESCRIPTION "Contains some sort of time stamp indicating when error 13		
                occurred. Example time stamps include the actual time the error		
                occurred (in seconds since Jan. 1, 1970), and the total engine		
                page count. The device POS documents the meaning of the time		
                stamp.
                Additional information:
                See ERROR1-TIME-STAMP."
::= { error13 1 }
               
               
error13-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error13 2 }
               
               
error13-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error13 3 }
               
               
error14-time-stamp OBJECT-TYPE
   SYNTAX      INTEGER
   ACCESS      read-only
   STATUS      optional
   DESCRIPTION "Contains some sort of time stamp indicating when error 14		
                occurred. Example time stamps include the actual time the error		
                occurred (in seconds since Jan. 1, 1970), and the total engine		
                page count. The device POS documents the meaning of the time		
                stamp.
                Additional information:
                See ERROR1-TIME-STAMP."
::= { error14 1 }
               
               
error14-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error14 2 }
               
               
error14-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error14 3 }
               
               
error15-time-stamp OBJECT-TYPE
   SYNTAX      INTEGER
   ACCESS      read-only
   STATUS      optional
   DESCRIPTION "Contains some sort of time stamp indicating when error 15		
                occurred. Example time stamps include the actual time the error		
                occurred (in seconds since Jan. 1, 1970), and the total engine		
                page count. The device POS documents the meaning of the time		
                stamp.
                Additional information:
                See ERROR1-TIME-STAMP."
::= { error15 1 }
               
               
error15-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error15 2 }
               
               
error15-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error15 3 }
               
               
error16-time-stamp OBJECT-TYPE
   SYNTAX      INTEGER
   ACCESS      read-only
   STATUS      optional
   DESCRIPTION "Contains some sort of time stamp indicating when error 16		
                occurred. Example time stamps include the actual time the error		
                occurred (in seconds since Jan. 1, 1970), and the total engine		
                page count. The device POS documents the meaning of the time		
                stamp.
                Additional information:
                See ERROR1-TIME-STAMP."
::= { error16 1 }
               
               
error16-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error16 2 }
               
               
error16-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error16 3 }
               
               
error17-time-stamp OBJECT-TYPE
   SYNTAX      INTEGER
   ACCESS      read-only
   STATUS      optional
   DESCRIPTION "Contains some sort of time stamp indicating when error 17		
                occurred. Example time stamps include the actual time the error		
                occurred (in seconds since Jan. 1, 1970), and the total engine		
                page count. The device POS documents the meaning of the time		
                stamp.
                Additional information:
                See ERROR1-TIME-STAMP."
::= { error17 1 }
               
               
error17-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error17 2 }
               
               
error17-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error17 3 }
               
               
error18-time-stamp OBJECT-TYPE
   SYNTAX      INTEGER
   ACCESS      read-only
   STATUS      optional
   DESCRIPTION "Contains some sort of time stamp indicating when error 18		
                occurred. Example time stamps include the actual time the error		
                occurred (in seconds since Jan. 1, 1970), and the total engine		
                page count. The device POS documents the meaning of the time		
                stamp.
                Additional information:
                See ERROR1-TIME-STAMP."
::= { error18 1 }
               
               
error18-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error18 2 }
               
               
error18-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error18 3 }
               
               
error19-time-stamp OBJECT-TYPE
   SYNTAX      INTEGER
   ACCESS      read-only
   STATUS      optional
   DESCRIPTION "Contains some sort of time stamp indicating when error 19		
                occurred. Example time stamps include the actual time the error		
                occurred (in seconds since Jan. 1, 1970), and the total engine		
                page count. The device POS documents the meaning of the time		
                stamp.
                Additional information:
                See ERROR1-TIME-STAMP."
::= { error19 1 }
               
               
error19-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error19 2 }
               
               
error19-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error19 3 }
               
               
error20-time-stamp OBJECT-TYPE
   SYNTAX      INTEGER
   ACCESS      read-only
   STATUS      optional
   DESCRIPTION "Contains some sort of time stamp indicating when error 20		
                occurred. Example time stamps include the actual time the error		
                occurred (in seconds since Jan. 1, 1970), and the total engine		
                page count. The device POS documents the meaning of the time		
                stamp.
                Additional information:
                See ERROR1-TIME-STAMP."
::= { error20 1 }
               
               
error20-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error20 2 }
               
               
error20-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error20 3 }
               
               
error21-time-stamp OBJECT-TYPE
   SYNTAX      INTEGER
   ACCESS      read-only
   STATUS      optional
   DESCRIPTION "Contains some sort of time stamp indicating when error 21		
                occurred. Example time stamps include the actual time the error		
                occurred (in seconds since Jan. 1, 1970), and the total engine		
                page count. The device POS documents the meaning of the time		
                stamp.
                Additional information:
                See ERROR1-TIME-STAMP."
::= { error21 1 }
               
               
error21-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error21 2 }
               
               
error21-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error21 3 }
               
               
error22-time-stamp OBJECT-TYPE
   SYNTAX      INTEGER
   ACCESS      read-only
   STATUS      optional
   DESCRIPTION "Contains some sort of time stamp indicating when error 22		
                occurred. Example time stamps include the actual time the error		
                occurred (in seconds since Jan. 1, 1970), and the total engine		
                page count. The device POS documents the meaning of the time		
                stamp.
                Additional information:
                See ERROR1-TIME-STAMP."
::= { error22 1 }
               
               
error22-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error22 2 }
               
               
error22-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error22 3 }
               
               
error23-time-stamp OBJECT-TYPE
   SYNTAX      INTEGER
   ACCESS      read-only
   STATUS      optional
   DESCRIPTION "Contains some sort of time stamp indicating when error 23		
                occurred. Example time stamps include the actual time the error		
                occurred (in seconds since Jan. 1, 1970), and the total engine		
                page count. The device POS documents the meaning of the time		
                stamp.
                Additional information:
                See ERROR1-TIME-STAMP."
::= { error23 1 }
               
               
error23-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error23 2 }
               
               
error23-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error23 3 }
               
               
error24-time-stamp OBJECT-TYPE
   SYNTAX      INTEGER
   ACCESS      read-only
   STATUS      optional
   DESCRIPTION "Contains some sort of time stamp indicating when error 24		
                occurred. Example time stamps include the actual time the error		
                occurred (in seconds since Jan. 1, 1970), and the total engine		
                page count. The device POS documents the meaning of the time		
                stamp.
                Additional information:
                See ERROR1-TIME-STAMP."
::= { error24 1 }
               
               
error24-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error24 2 }
               
               
error24-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error24 3 }
               
               
error25-time-stamp OBJECT-TYPE
   SYNTAX      INTEGER
   ACCESS      read-only
   STATUS      optional
   DESCRIPTION "Contains some sort of time stamp indicating when error 25		
                occurred. Example time stamps include the actual time the error		
                occurred (in seconds since Jan. 1, 1970), and the total engine		
                page count. The device POS documents the meaning of the time		
                stamp.
                Additional information:
                See ERROR1-TIME-STAMP."
::= { error25 1 }
               
               
error25-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error25 2 }
               
               
error25-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error25 3 }
               
               
error26-time-stamp OBJECT-TYPE
   SYNTAX      INTEGER
   ACCESS      read-only
   STATUS      optional
   DESCRIPTION "Contains some sort of time stamp indicating when error 26		
                occurred. Example time stamps include the actual time the error		
                occurred (in seconds since Jan. 1, 1970), and the total engine		
                page count. The device POS documents the meaning of the time		
                stamp.
                Additional information:
                See ERROR1-TIME-STAMP."
::= { error26 1 }
               
               
error26-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error26 2 }
               
               
error26-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error26 3 }
               
               
error27-time-stamp OBJECT-TYPE
   SYNTAX      INTEGER
   ACCESS      read-only
   STATUS      optional
   DESCRIPTION "Contains some sort of time stamp indicating when error 27		
                occurred. Example time stamps include the actual time the error		
                occurred (in seconds since Jan. 1, 1970), and the total engine		
                page count. The device POS documents the meaning of the time		
                stamp.
                Additional information:
                See ERROR1-TIME-STAMP."
::= { error27 1 }
               
               
error27-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error27 2 }
               
               
error27-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error27 3 }
               
               
error28-time-stamp OBJECT-TYPE
   SYNTAX      INTEGER
   ACCESS      read-only
   STATUS      optional
   DESCRIPTION "Contains some sort of time stamp indicating when error 28		
                occurred. Example time stamps include the actual time the error		
                occurred (in seconds since Jan. 1, 1970), and the total engine		
                page count. The device POS documents the meaning of the time		
                stamp.
                Additional information:
                See ERROR1-TIME-STAMP."
::= { error28 1 }
               
               
error28-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error28 2 }
               
               
error28-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error28 3 }
               
               
error29-time-stamp OBJECT-TYPE
   SYNTAX      INTEGER
   ACCESS      read-only
   STATUS      optional
   DESCRIPTION "Contains some sort of time stamp indicating when error 29		
                occurred. Example time stamps include the actual time the error		
                occurred (in seconds since Jan. 1, 1970), and the total engine		
                page count. The device POS documents the meaning of the time		
                stamp.
                Additional information:
                See ERROR1-TIME-STAMP."
::= { error29 1 }
               
               
error29-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error29 2 }
               
               
error29-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error29 3 }
               
               
error30-time-stamp OBJECT-TYPE
   SYNTAX      INTEGER
   ACCESS      read-only
   STATUS      optional
   DESCRIPTION "Contains some sort of time stamp indicating when error 30		
                occurred. Example time stamps include the actual time the error		
                occurred (in seconds since Jan. 1, 1970), and the total engine		
                page count. The device POS documents the meaning of the time		
                stamp.
                Additional information:
                See ERROR1-TIME-STAMP."
::= { error30 1 }
               
               
error30-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error30 2 }
               
               
error30-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error30 3 }
               
               
error31-time-stamp OBJECT-TYPE
   SYNTAX      INTEGER
   ACCESS      read-only
   STATUS      optional
   DESCRIPTION "Contains some sort of time stamp indicating when error 31		
                occurred. Example time stamps include the actual time the error		
                occurred (in seconds since Jan. 1, 1970), and the total engine		
                page count. The device POS documents the meaning of the time		
                stamp.
                Additional information:
                See ERROR1-TIME-STAMP."
::= { error31 1 }
               
               
error31-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error31 2 }
               
               
error31-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error31 3 }
               
               
error32-time-stamp OBJECT-TYPE
   SYNTAX      INTEGER
   ACCESS      read-only
   STATUS      optional
   DESCRIPTION "Contains some sort of time stamp indicating when error 32		
                occurred. Example time stamps include the actual time the error		
                occurred (in seconds since Jan. 1, 1970), and the total engine		
                page count. The device POS documents the meaning of the time		
                stamp.
                Additional information:
                See ERROR1-TIME-STAMP."
::= { error32 1 }
               
               
error32-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error32 2 }
               
               
error32-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error32 3 }
               
               
error33-time-stamp OBJECT-TYPE
   SYNTAX      INTEGER
   ACCESS      read-only
   STATUS      optional
   DESCRIPTION "Contains some sort of time stamp indicating when error 33		
                occurred. Example time stamps include the actual time the error		
                occurred (in seconds since Jan. 1, 1970), and the total engine		
                page count. The device POS documents the meaning of the time		
                stamp.
                Additional information:
                See ERROR1-TIME-STAMP."
::= { error33 1 }
               
               
error33-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error33 2 }
               
               
error33-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error33 3 }
               
               
error34-time-stamp OBJECT-TYPE
   SYNTAX      INTEGER
   ACCESS      read-only
   STATUS      optional
   DESCRIPTION "Contains some sort of time stamp indicating when error 34		
                occurred. Example time stamps include the actual time the error		
                occurred (in seconds since Jan. 1, 1970), and the total engine		
                page count. The device POS documents the meaning of the time		
                stamp.
                Additional information:
                See ERROR1-TIME-STAMP."
::= { error34 1 }
               
               
error34-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error34 2 }
               
               
error34-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error34 3 }
               
               
error35-time-stamp OBJECT-TYPE
   SYNTAX      INTEGER
   ACCESS      read-only
   STATUS      optional
   DESCRIPTION "Contains some sort of time stamp indicating when error 35		
                occurred. Example time stamps include the actual time the error		
                occurred (in seconds since Jan. 1, 1970), and the total engine		
                page count. The device POS documents the meaning of the time		
                stamp.
                Additional information:
                See ERROR1-TIME-STAMP."
::= { error35 1 }
               
               
error35-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error35 2 }
               
               
error35-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error35 3 }
               
               
error36-time-stamp OBJECT-TYPE
   SYNTAX      INTEGER
   ACCESS      read-only
   STATUS      optional
   DESCRIPTION "Contains some sort of time stamp indicating when error 36		
                occurred. Example time stamps include the actual time the error		
                occurred (in seconds since Jan. 1, 1970), and the total engine		
                page count. The device POS documents the meaning of the time		
                stamp.
                Additional information:
                See ERROR1-TIME-STAMP."
::= { error36 1 }
               
               
error36-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error36 2 }
               
               
error36-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error36 3 }
               
               
error37-time-stamp OBJECT-TYPE
   SYNTAX      INTEGER
   ACCESS      read-only
   STATUS      optional
   DESCRIPTION "Contains some sort of time stamp indicating when error 37		
                occurred. Example time stamps include the actual time the error		
                occurred (in seconds since Jan. 1, 1970), and the total engine		
                page count. The device POS documents the meaning of the time		
                stamp.
                Additional information:
                See ERROR1-TIME-STAMP."
::= { error37 1 }
               
               
error37-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error37 2 }
               
               
error37-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error37 3 }
               
               
error38-time-stamp OBJECT-TYPE
   SYNTAX      INTEGER
   ACCESS      read-only
   STATUS      optional
   DESCRIPTION "Contains some sort of time stamp indicating when error 38		
                occurred. Example time stamps include the actual time the error		
                occurred (in seconds since Jan. 1, 1970), and the total engine		
                page count. The device POS documents the meaning of the time		
                stamp.
                Additional information:
                See ERROR1-TIME-STAMP."
::= { error38 1 }
               
               
error38-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error38 2 }
               
               
error38-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error38 3 }
               
               
error39-time-stamp OBJECT-TYPE
   SYNTAX      INTEGER
   ACCESS      read-only
   STATUS      optional
   DESCRIPTION "Contains some sort of time stamp indicating when error 39		
                occurred. Example time stamps include the actual time the error		
                occurred (in seconds since Jan. 1, 1970), and the total engine		
                page count. The device POS documents the meaning of the time		
                stamp.
                Additional information:
                See ERROR1-TIME-STAMP."
::= { error39 1 }
               
               
error39-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error39 2 }
               
               
error39-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error39 3 }
               
               
error40-time-stamp OBJECT-TYPE
   SYNTAX      INTEGER
   ACCESS      read-only
   STATUS      optional
   DESCRIPTION "Contains some sort of time stamp indicating when error 40		
                occurred. Example time stamps include the actual time the error		
                occurred (in seconds since Jan. 1, 1970), and the total engine		
                page count. The device POS documents the meaning of the time		
                stamp.
                Additional information:
                See ERROR1-TIME-STAMP."
::= { error40 1 }
               
               
error40-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error40 2 }
               
               
error40-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error40 3 }
               
               
error41-time-stamp OBJECT-TYPE
   SYNTAX      INTEGER
   ACCESS      read-only
   STATUS      optional
   DESCRIPTION "Contains some sort of time stamp indicating when error 41		
                occurred. Example time stamps include the actual time the error		
                occurred (in seconds since Jan. 1, 1970), and the total engine		
                page count. The device POS documents the meaning of the time		
                stamp.
                Additional information:
                See ERROR1-TIME-STAMP."
::= { error41 1 }
               
               
error41-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error41 2 }
               
               
error41-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error41 3 }
               
               
error42-time-stamp OBJECT-TYPE
   SYNTAX      INTEGER
   ACCESS      read-only
   STATUS      optional
   DESCRIPTION "Contains some sort of time stamp indicating when error 42		
                occurred. Example time stamps include the actual time the error		
                occurred (in seconds since Jan. 1, 1970), and the total engine		
                page count. The device POS documents the meaning of the time		
                stamp.
                Additional information:
                See ERROR1-TIME-STAMP."
::= { error42 1 }
               
               
error42-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error42 2 }
               
               
error42-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error42 3 }
               
               
error43-time-stamp OBJECT-TYPE
   SYNTAX      INTEGER
   ACCESS      read-only
   STATUS      optional
   DESCRIPTION "Contains some sort of time stamp indicating when error 43		
                occurred. Example time stamps include the actual time the error		
                occurred (in seconds since Jan. 1, 1970), and the total engine		
                page count. The device POS documents the meaning of the time		
                stamp.
                Additional information:
                See ERROR1-TIME-STAMP."
::= { error43 1 }
               
               
error43-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error43 2 }
               
               
error43-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error43 3 }
               
               
error44-time-stamp OBJECT-TYPE
   SYNTAX      INTEGER
   ACCESS      read-only
   STATUS      optional
   DESCRIPTION "Contains some sort of time stamp indicating when error 44		
                occurred. Example time stamps include the actual time the error		
                occurred (in seconds since Jan. 1, 1970), and the total engine		
                page count. The device POS documents the meaning of the time		
                stamp.
                Additional information:
                See ERROR1-TIME-STAMP."
::= { error44 1 }
               
               
error44-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error44 2 }
               
               
error44-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error44 3 }
               
               
error45-time-stamp OBJECT-TYPE
   SYNTAX      INTEGER
   ACCESS      read-only
   STATUS      optional
   DESCRIPTION "Contains some sort of time stamp indicating when error 45		
                occurred. Example time stamps include the actual time the error		
                occurred (in seconds since Jan. 1, 1970), and the total engine		
                page count. The device POS documents the meaning of the time		
                stamp.
                Additional information:
                See ERROR1-TIME-STAMP."
::= { error45 1 }
               
               
error45-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error45 2 }
               
               
error45-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error45 3 }
               
               
error46-time-stamp OBJECT-TYPE
   SYNTAX      INTEGER
   ACCESS      read-only
   STATUS      optional
   DESCRIPTION "Contains some sort of time stamp indicating when error 46		
                occurred. Example time stamps include the actual time the error		
                occurred (in seconds since Jan. 1, 1970), and the total engine		
                page count. The device POS documents the meaning of the time		
                stamp.
                Additional information:
                See ERROR1-TIME-STAMP."
::= { error46 1 }
               
               
error46-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error46 2 }
               
               
error46-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error46 3 }
               
               
error47-time-stamp OBJECT-TYPE
   SYNTAX      INTEGER
   ACCESS      read-only
   STATUS      optional
   DESCRIPTION "Contains some sort of time stamp indicating when error 47		
                occurred. Example time stamps include the actual time the error		
                occurred (in seconds since Jan. 1, 1970), and the total engine		
                page count. The device POS documents the meaning of the time		
                stamp.
                Additional information:
                See ERROR1-TIME-STAMP."
::= { error47 1 }
               
               
error47-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error47 2 }
               
               
error47-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error47 3 }
               
               
error48-time-stamp OBJECT-TYPE
   SYNTAX      INTEGER
   ACCESS      read-only
   STATUS      optional
   DESCRIPTION "Contains some sort of time stamp indicating when error 48		
                occurred. Example time stamps include the actual time the error		
                occurred (in seconds since Jan. 1, 1970), and the total engine		
                page count. The device POS documents the meaning of the time		
                stamp.
                Additional information:
                See ERROR1-TIME-STAMP."
::= { error48 1 }
               
               
error48-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error48 2 }
               
               
error48-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error48 3 }
               
               
error49-time-stamp OBJECT-TYPE
   SYNTAX      INTEGER
   ACCESS      read-only
   STATUS      optional
   DESCRIPTION "Contains some sort of time stamp indicating when error 49		
                occurred. Example time stamps include the actual time the error		
                occurred (in seconds since Jan. 1, 1970), and the total engine		
                page count. The device POS documents the meaning of the time		
                stamp.
                Additional information:
                See ERROR1-TIME-STAMP."
::= { error49 1 }
               
               
error49-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error49 2 }
               
               
error49-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error49 3 }
               
               
error50-time-stamp OBJECT-TYPE
   SYNTAX      INTEGER
   ACCESS      read-only
   STATUS      optional
   DESCRIPTION "Contains some sort of time stamp indicating when error 50		
                occurred. Example time stamps include the actual time the error		
                occurred (in seconds since Jan. 1, 1970), and the total engine		
                page count. The device POS documents the meaning of the time		
                stamp.
                Additional information:
                See ERROR1-TIME-STAMP."
::= { error50 1 }
               
               
error50-code OBJECT-TYPE
   SYNTAX      INTEGER
   ACCESS      read-only
   STATUS      optional
   DESCRIPTION "Contains a device specific error code. Each device POS should		
                list what errors are logged to the error log and the meaning of		
                each supported error code value.
                Additional information:
                See ERROR1-CODE."
::= { error50 2 }
               
               
error50-date-time OBJECT-TYPE
   SYNTAX      OCTET STRING
   ACCESS      read-only
   STATUS      optional
   DESCRIPTION "This item contains the date and the time at which an error		
                occurred. The values returned will be in hexadecimal. If the		
                date is 2004-Jul-13 and the time is 03:15 a.m., we get 04 07 0d		
                03 0f where,    	
                    04 (hex) - corresponds to the year 2004.    	
                    07 (hex) - corresponds to month, 07    	
                    0d (hex) - corresponds to date, 13    	
                    03 (hex) - corresponds to hour, 3 a.m.    	
                    0f (hex) - corresponds to min, 15.   
                Additional information:
                See ERROR1-DATE-TIME."
::= { error50 3 }
               
               
channelprinteralert OBJECT-TYPE
   SYNTAX      OCTET STRING
   ACCESS      read-only
   STATUS      optional
   DESCRIPTION "Identifies the values of prtAlertIndex, prtAlertSeverityLevel,		
                prtAlertGroup, prtAlertGroupIndex, prtAlertLocation, and		
                prtAlertCode for the latest critical evnet in the		
                prtAlertTable. The binary string is defined as following:    	
                    <table>
                    -----------------------------------------------------
                    Field  | Filed  | Description 
                    Offset | Length | 
                    -----------------------------------------------------
                      0    |    4   | the value of prtAlertIndex
                      4    |    4   | the value of prtAlertSeverityLevel
                      8    |    4   | the value of prtAlertGroup
                     12    |    4   | the value of prtAlertGroupIndex
                     16    |    4   | the value of prtAlertLocation
                     20    |    4   | the value of prtAlertCode
                    ------------------------------------------------------
                    </table> 
                       	
                Each field is in Big Endian style.
                Additional information:
                This object is used to pass alert information from the
                peripheral to the IIO card.  The standard printer MIB
                contains the following description:  
                
                printerAlert TRAP-TYPE  
                ENTERPRISE printerV1Alert  
                VARIABLES { prtAlertIndex, prtAlertSeverityLevel, prtAlertGroup,
                prtAlertGroupIndex, prtAlertLocation, prtAlertCode }  
                DESCRIPTION  
                'This trap is sent whenever a critical event is added to the
                prtAlertTable.'  
                
                In order to provide this information in the trap packet, the
                IIO card enables traps on channelPrinterAlert.  When a critical
                alert is generated the peripheral fills the appropriate value
                into this object and sends it to the card.
                This object is a structure which contains 24 bytes of data.
                The structure is:  
                
                struct structAlertInfo {  
                sint32 prtAlertIndex;  
                sint32 prtAlertSeverityLevel;  
                sint32 prtAlertGroup;  
                sint32 prtAlertGroupIndex;  
                sint32 prtAlertLocation;  
                sint32 prtAlertCode;  
                } thisAlertData;"
::= { channel 2 }
               
               
pages-remaining OBJECT-TYPE
   SYNTAX      INTEGER {
		   eOff(1),
		   eOn(2)
		   }
   ACCESS      read-write
   STATUS      optional
   DESCRIPTION "Used to enable/disable the number of pages remaining with the		
                supply that is shown on control panel messages and supplies		
                status menu.
                Additional information:
                The PAGES-REMAINING would allow the user to turn off/on
                'PAGES REMAINING' part of the 'ORDER <COLOR> CARTRIDGE
                LESS THAN X PAGES REMAINING ' messages"
::= { settings-system 70 }
               
               
order-cartridge OBJECT-TYPE
   SYNTAX      INTEGER {
		   eOff(1),
		   eOn(2)
		   }
   ACCESS      read-write
   STATUS      optional
   DESCRIPTION "Used to enable/disable the supplies status message that is		
                shown when the supply reaches low.
                Additional information:
                This will allow the user to turn off/on 'ORDER <COLOR>
                CARTRIDGE LESS THAN X PAGES REMAINING ' messages"
::= { settings-system 71 }
               
               
level-display OBJECT-TYPE
   SYNTAX      INTEGER {
		   eOff(1),
		   eOn(2)
		   }
   ACCESS      read-write
   STATUS      optional
   DESCRIPTION "Used to enable/disable the supplies level indicators that is		
                displayed on the control panel.
                Additional information:
                This will allow the user to turn off/on
                BAR GRAPHS on the control panel"
::= { settings-system 72 }
               
               
install-date OBJECT-TYPE
   SYNTAX      OCTET STRING (SIZE(13))
   ACCESS      read-write
   STATUS      optional
   DESCRIPTION "Identifies the date that the device was installed. The format		
                of the string is 'YYYYMMDDHHmmZ'. Where:    	
                    YYYY is the year.    	
                    MM is the month (1-12).    	
                    DD is the day (1-31).    	
                    HH is the hour of the day (0-23).    	
                    mm are the minutes (0-59).    	
                    'Z' designates Greenwich Mean Time; if 'Z' not specified,		
                        value is local time.    	
                Device POS must specify the conditions for setting this		
                object.
                Additional information:
                Setting the SERVICE-<<hidden>> object will
                enable setting this object."
::= { status-system 8 }
               
               
service-id OBJECT-TYPE
   SYNTAX      OCTET STRING (SIZE(5))
   ACCESS      read-write
   STATUS      optional
   DESCRIPTION "A read of this object will return the current SERVICE ID value		
                in the printer. The format is 'YYDDD' where:    	
                    YY = calendar year - 1990    	
                    DDD = (calendar month - 1) * 30 + (calendar day of the		
                        month or 30, if > 30)    	
                A write of this object will only succeed if the		
                MANUFACTURING-CONTROL PML object has been set with the correct		
                <<hidden>>. If the write operation is not allowed, this object		
                will return an <genErr> status.
                Additional information:
                Setting the SERVICE-<<hidden>> object will
                enable setting this object."
::= { status-system 19 }
               
               
show-address OBJECT-TYPE
   SYNTAX      INTEGER {
		   eOff(1),
		   eAuto(3)
		   }
   ACCESS      read-write
   STATUS      optional
   DESCRIPTION "If this object is set to eAuto, and the device has an IP		
                address, the IP address of the device will be shown with the		
                READY message. If this object is set to eOff, the IP address		
                will not be shown."
::= { display-status 3 }
               
               
serial-number OBJECT-TYPE
   SYNTAX      OCTET STRING (SIZE(0..10))
   ACCESS      read-only
   STATUS      optional
   DESCRIPTION "Identifies the serial number for the device. If the		
                SERIAL-NUMBER object is set by the user, then setting the		
                object does not need to be protected. If the SERIAL-NUMBER		
                object is set at the factory, then the <<hidden>> object		
                must be set correctly before the SERIAL-NUMBER object is		
                writable. If this is a writable object, the POS should indicate		
                the maximum supported string length. If possible, encode the		
                serial number in a symbol set (like Roman-8) that matches the		
                ASCII character set and limit the characters used to ASCII		
                characters.
                Additional information:
                This value IS AFFECTED BY NVRAM resets, it is set to the 
                default value of XXXXXXXXXX, when a NVRAM init is done."
::= { id 3 }
               
               
fw-rom-datecode OBJECT-TYPE
   SYNTAX      OCTET STRING
   ACCESS      read-only
   STATUS      optional
   DESCRIPTION "Identifies the base system firmware date code. The date code		
                will be encoded in the yyyymmdd format. There may be several		
                versions of the base system firmware. The date code associated		
                with the version of the base system firmware that is being used		
                is reported. There may be other date code objects for other		
                specific modules such as fonts, localization modules, etc.;		
                these other datecode objects are device specific."
::= { id 5 }
               
               
fw-rom-revision OBJECT-TYPE
   SYNTAX      OCTET STRING
   ACCESS      read-only
   STATUS      optional
   DESCRIPTION "This identifies the system code firmware ROM revision code. The		
                format for a revision is major_revision.minor_revision. There		
                may be other ROM revision code objects for other specific ROMs		
                such as font ROMs, localization ROMs, etc; these other ROM		
                revision code objects are device specific."
::= { id 6 }
               
               
device-name OBJECT-TYPE
   SYNTAX      OCTET STRING (SIZE(0..32))
   ACCESS      read-write
   STATUS      optional
   DESCRIPTION "User defined device name. The POS should indicate the maximum		
                supported string length. If the user entered string is too		
                long, the device will store as much as possible and will return		
                the <OKNearestLegal ValueSubstituted>.Additional information:
                The maximum supported string length is 32  
                characters.  If the user entered string is too long, 
                the device will store the first 32 characters and will 
                return the <noError> status."
::= { id 10 }
               
               
device-location OBJECT-TYPE
   SYNTAX      OCTET STRING
   ACCESS      read-write
   STATUS      optional
   DESCRIPTION "User defined device location. The POS should indicate the		
                maximum supported string length. If the user entered string is		
                too long, the device will store as much as possible and will		
                return the <OKNearestLegal ValueSubstituted>.Additional information:
                The maximum supported string length is 16 
                characters.  If the user entered string is too long, 
                the device will store the first 16 characters and will 
                return the <noError> status."
::= { id 11 }
               
               
asset-number OBJECT-TYPE
   SYNTAX      OCTET STRING
   ACCESS      read-write
   STATUS      optional
   DESCRIPTION "User defined asset number. The POS should indicate the maximum		
                supported string length. If the user entered string is too		
                long, the device will store as much as possible and will return		
                the <OKNearestLegal ValueSubstituted>.Additional information:
                The maximum supported string length is 8 
                characters.  If the user entered string is too long, 
                the device will store the first 8 characters and will  
                return the <noError> status."
::= { id 12 }
               
               
ews-request-control-panel-supplies-status OBJECT-TYPE
   SYNTAX      INTEGER {
		   eFalse(1),
		   eTrue(2)
		   }
   ACCESS      read-write
   STATUS      optional
   DESCRIPTION "System variable EWS_REQUEST_CONTROL_PANEL_SUPPPLIES_STATUS		
                requires a PML interface so that WJA can directly access it		
                without needing EWS support for that.
                Additional information:
                If this object is set to eTrue, the Supplies Status messages will
                not be shown on the CP."
::= { settings-web-server 5 }
               
               
default-copies OBJECT-TYPE
   SYNTAX      INTEGER
   ACCESS      read-write
   STATUS      optional
   DESCRIPTION "Returns or changes default copies. Default copies is the		
                default values used by the PDL to control the number of copies		
                of each page in the print job that are printed. The print job		
                can override this value. The list of supported values should be		
                documented in the device POS.
                Additional information:
                 The supported values are 1 through 32000.  
                	  Setting to an unsupported value causes the printer to substitute in a snap
                	  value and to return <noError> status.   
                	  The snaps are as follows:  
                		  <1 snaps to 1  
                		  >999 snaps to 32000"
::= { settings-pdl 4 }
               
               
default-lines-per-page OBJECT-TYPE
   SYNTAX      INTEGER
   ACCESS      read-write
   STATUS      optional
   DESCRIPTION "Returns or changes the default number of lines per page. The		
                POS indicates the supported values. An unsupported value causes		
                the printer to use the closest supported value, causing the		
                printer to return the <noError>.
                Additional information:
                The supported values in $product_str are 5 to 128. 
                Setting to an unsupported value causes the  
                the printer to substitute in a snap value and to return 
                <noError> 
                status.   
                The snap values are as follow:   
                <5 snaps to 5   
                >128 snaps to 128"
::= { settings-pdl 11 }
               
               
default-vmi OBJECT-TYPE
   SYNTAX      INTEGER
   ACCESS      read-write
   STATUS      optional
   DESCRIPTION "Returns or changes the default vertical motion index. The unit		
                of measure for VMI is centipoints per line. The POS indicates		
                the supported values. An unsupported value causes the printer		
                to use the closest supported value, causing the printer to		
                return <noError>."
::= { settings-pdl 12 }
               
               
default-media-size OBJECT-TYPE
   SYNTAX      INTEGER {
		   eUSExecutive(1),
		   eUSLetter(2),
		   eUSLegal(3),
		   eFoolscap(10),
		   eLedger(11),
		   eStatement(15),
		   eROC16K(17),
		   eROC8K(19),
		   eISOandJISA6(24),
		   eISOandJISA5(25),
		   eISOandJISA4(26),
		   eISOandJISA3(27),
		   ePRC8K270X390(33),
		   ePRC16K195X270(34),
		   ePRC8K260X368(35),
		   eISOSRA3(38),
		   eISORA3(39),
		   eJISB6(44),
		   eJISB5(45),
		   eJISB4(46),
		   eJapansePostcardSingle(71),
		   eJapanesePostcardDouble(72),
		   eIndexCard4x6(74),
		   eIndexCard5x8(75),
		   eMonarch(80),
		   eCommercial10(81),
		   ePRC16K184X260(89),
		   eInternationalDL(90),
		   eInternationalC5(91),
		   eEnvelopeC6(92),
		   eInternationalB5(100),
		   eCustom(101),
		   eEnvelope9(102),
		   eTabloidExtra(120),
		   eISOandJISA4R(282),
		   eUSLetterR(258),
		   eUnknownMediaSize(32767)
		   }
   ACCESS      read-write
   STATUS      optional
   DESCRIPTION "This indicates the default media size. A write of an		
                unsupported value causes an <ErrorInvalidOrUnsupported Value>.		Complete list of supported media sizes along with their		
                dimensions are listed in the ''Media Size Table'' near the end		
                of this document. (for a full list of media size enums see the		
                end of this file) "
::= { settings-pdl 13 }
               
               
cold-reset-media-size OBJECT-TYPE
   SYNTAX      INTEGER {
		   eUSLetter(2),
		   eISOandJISA4(26)
		   }
   ACCESS      read-write
   STATUS      optional
   DESCRIPTION "Returns or sets the media size that is used as the		
                DEFAULT-MEDIA-SIZE when a cold reset occurs."
::= { settings-pdl 19 }
               
               
reprint OBJECT-TYPE
   SYNTAX      INTEGER {
		   eOff(1),
		   eOn(2),
		   eAuto(3)
		   }
   ACCESS      read-write
   STATUS      optional
   DESCRIPTION "Returns or changes the reprint (jam recovery) setting. If eOn,		
                then the device will reprint pages jammed pages. If eOff, the		
                device will not attempt to reprint jammed pages. If eAuto, a		
                device dependent algorithm (which should be documented in the		
                POS) will be used to determine if the page gets reprinted. This		
                object controls all PDLs, unless a specific PDL supports its		
                own reprint control mechanism. To date, only PostScript has a		
                PDL reprint control mechanism."
::= { settings-pdl 36 }
               
               
duplex-blank-pages OBJECT-TYPE
   SYNTAX      INTEGER {
		   eDuplexBlankPagesAuto(1),
		   eDuplexBlankPagesYes(2)
		   }
   ACCESS      read-write
   STATUS      optional
   DESCRIPTION "When the value of the system variable is set to		
                eDuplexBlankPagesAuto, it means to Smart Duplex in any of the		
                specified conditions. This selection is logically equivalent to		
                'NO, do not duplex blank pages if not duplexing them obtains a		
                performance enhancement'. When the value of the system variable		
                is set to eDuplexBlankPagesYes, it means to disable Smart		
                Duplexing.
                Additional information:
                When the value of the system variable is set to
                eDuplexBlankPagesAuto, it means to Smart Duplex in any of the
                specified conditions. This selection is logically equivalent to
                'NO, do not duplex blank pages if not duplexing them obtains a
                performance enhancement'. When the value of the system variable
                is set to eDuplexBlankPagesYes, it means to disable Smart
                Duplexing."
::= { settings-prt-eng 28 }
               
               
tray-prompt OBJECT-TYPE
   SYNTAX      INTEGER {
		   eDoNotDisplay(1),
		   eDisplay(2)
		   }
   ACCESS      read-write
   STATUS      optional
   DESCRIPTION "If this object is set to eDisplay, whenever a paper tray is		
                opened, refilled, and closed in a printer, the end user is		
                prompted with a message 'To change size or type press check' on		
                the control panel. If this object is set to eDoNotDisplay, then		
                the end user will not be prompted with this message whenever a		
                paper tray is opened, refilled, and closed in a printer.
                Additional information:
                Whenever a paper tray is opened and closed, the user is
                provided with two options Display and Do Not Display, through
                the menu item Size/Type Prompt.On selecting Display he chooses
                to get prompted with the message to change the size or type of
                paper. Whereas he is not prompted with this message in case he
                chooses Do Not Display."
::= { settings-intray 19 }
               
               
tray-disable-use-instead OBJECT-TYPE
   SYNTAX      INTEGER {
		   eDisabled(1),
		   eEnabled(2)
		   }
   ACCESS      read-write
   STATUS      optional
   DESCRIPTION "If this object is set to eEnabled, the paper mount message that		
                is normally posted('To use another tray....') is turned off		
                thereby disallowing the user to specify another tray from which		
                paper can be taken for printing. However, on setting this		
                object to eDisabled the paper mount message is posted allowing		
                the user to specify another tray for paper feed.
                Additional information:
                The feature provides a menu item under TRAY BEHAVIOUR, i.e
                USE ANOTHER TRAY which has two options ENABLED and DISABLED.
                Whenever the menu item is set to ENABLED, it provides the user
                with the ability to select another tray from which paper could
                be provided for the job. However on selecting DISABLED forces
                the user to provide paper through the same tray, after the paper
                mount message is posted, in either cases."
::= { settings-ph 1 }

               
               
pcl-total-page-count OBJECT-TYPE
   SYNTAX      INTEGER
   ACCESS      read-only
   STATUS      optional
   DESCRIPTION "Total number of PCL pages printed by the device.
                Additional information:
                In $product_str the PCL page count is kept in
                NVRAM, and the NVRAM value is updated at least every
                10 pages.  NOTE: The value returned by this object will
                be incremented every page but if power is lost between
                NVRAM updates, up to 9 pages of the page count may be
                lost.  The page count counter will be reset to zero
                after 16,777,215 (2^24-1) pages.  
                The page count is incremented when a sheet of media is pulled from an input
                tray. A duplex printed sheet will cause this counter to be incremented by
                two."
::= { pdl-pcl 5 }
               
               
pcl-default-font-height OBJECT-TYPE
   SYNTAX      INTEGER
   ACCESS      read-write
   STATUS      optional
   DESCRIPTION "Returns or changes the default PCL height. Height is an		
                approximate measure of the body of the type in centipoints. A		
                centipoint is 1/7200 inch. Height applies only to proportional		
                fonts. Point size, in points, can be converted to font height,		
                in centipoints, by multiplying the point size by 100. The POS		
                indicates the supported values. An unsupported value causes the		
                printer to use the closest supported value, causing the printer		
                to return <noError>. ''Closest'' means		
                the smallest absolute difference.
                Additional information:
                Supported values range from 400 to 99975, in
                increments of 25 units.
                Setting to an unsupported value causes the 
                printer to substitute in a snap value and to 
                return <noError> status.   
                The snap values are as follow:   
                <=400 snaps to 400   
                >=99975 snaps to 99975   
                Unsupported values in the range 400 to 99975 snap
                DOWN to the previous supported value 
                (i.e 25293 snaps to 25275 or 75038 snaps to 75025)."
::= { pdl-pcl 13 }
               
               
pcl-default-font-source OBJECT-TYPE
   SYNTAX      INTEGER {
		   eInternal(1),
		   ePermanentSoft(2),
		   eRomSimm2(11),
		   eRomSimm3(12),
		   eRomSimm4(13),
		   eRomSimm5(14)
		   }
   ACCESS      read-write
   STATUS      optional
   DESCRIPTION "Returns or changes the value of the default font source		
                variable in NVRAM."
::= { pdl-pcl 14 }
               
               
pcl-default-font-number OBJECT-TYPE
   SYNTAX      INTEGER(0..255)
   ACCESS      read-write
   STATUS      optional
   DESCRIPTION "Returns or changes the value of the default font number		
                variable in NVRAM. Writing an unsupported value causes the		
                printer to generate an <badValue>.
                Additional information:
                Valid numbers or 0 - 255, but only font numbers that are 
                included in the PCL FONT LIST are selectable."
::= { pdl-pcl 15 }
               
               
pcl-default-font-width OBJECT-TYPE
   SYNTAX      INTEGER
   ACCESS      read-write
   STATUS      optional
   DESCRIPTION "Returns or changes the default PCL font width. Width is		
                expressed as the width of a character in centipoints. A		
                centipoint is 1/7200 inch. Width applies only to fixed space		
                fonts. Pitch, in character per inch, can be converted to font		
                width, in centipoints, by dividing 7200 by the pitch. The POS		
                indicates the supported values. An unsupported value causes the		
                printer to use the closest supported value, causing the printer		
                to return <noError>. ''Closest'' means		
                the smallest absolute difference.
                Additional information:
                Setting to an unsupported value causes the 
                printer to substitue in a snap value (listed below)
                and return <noError> status.   
                The snap values for pitch are as follow:   
                <=44 snaps to 44   
                >=9999 snaps to 9999"
::= { pdl-pcl 16 }
               
               
postscript-total-page-count OBJECT-TYPE
   SYNTAX      INTEGER
   ACCESS      read-only
   STATUS      optional
   DESCRIPTION "Total number of PostScript pages printed by the device.
                Additional information:
                This object is only supported if the PostScript
                option is installed.  
                In $product_str the count is kept in NVRAM, and the
                NVRAM value is updated at least every 10
                sheets.  NOTE: The value returned by this object will
                be incremented every sheet but if power is lost between
                NVRAM updates up to 9 sheets of the count may be
                lost.  The counter will be reset to zero
                after 16,777,215 (2^24-1) pages. "
::= { pdl-postscript 5 }
               
               
postscript-print-errors OBJECT-TYPE
   SYNTAX      INTEGER {
		   eOff(1),
		   eOn(2)
		   }
   ACCESS      read-write
   STATUS      optional
   DESCRIPTION "Returns or changes the value of the print PostScript errors		
                setting. If eOn, PostScript prints an error page showing the		
                error encountered and the stack at the time of the error.
                Additional information:
                This object is only supported if the PostScript
                option is installed."
::= { pdl-postscript 11 }
               
               
pdf-print-errors OBJECT-TYPE
   SYNTAX      INTEGER {
		   eOff(1),
		   eOn(2)
		   }
   ACCESS      read-write
   STATUS      optional
   DESCRIPTION "Returns or changes the value of the print PDF errors setting.		
                If eOn, PDF prints an error page showing the error encountered		
                and the stack at the time of the error.
                Additional information:
                This object is only supported if the PDF
                option is installed."
::= { pdl-pdf 4 }
               
               
collated-originals-support OBJECT-TYPE
   SYNTAX      OCTET STRING
   ACCESS      read-only
   STATUS      optional
   DESCRIPTION "Indicates that the printer can create multiple, collated		
                'originals' of a job and shows the level of support for this		
                capability.    	
                    cCollatedOriginals - The printer can create multiple		
                        collated originals, or 'mopies'. This is the base		
                        functionality required by the other collection items.		
                           	
                    cProofAndHold - The printer saves a copy of the job while		
                        printing the first mopy. Later, this held job can be		
                        released and the rest of the mopies will print.    	
                    cSecurityPrint - The printer spools the job and holds the		
                        job until the user releases the job by entering a		
                        <<hidden>> at the printer's control panel.    	
                    cAutoHighlight - The printer prints the job a number of		
                        times with a mail distribution list prepended to each		
                        job. A different mailing address is highlighted on each		
                        mopy.    	
                    cCollatedAtSpeed - The printer can create multiple collated		
                        copies where all copies after the original are printed		
                        at engine speed.   
                Additional information:
                Indicates that the printer can create multiple, collated   
                originals of a job and shows the level of support for this  
                capability.    
                cCollatedOriginals - The printer can create multiple collated  
                originals, or mopies.  
                
                This is the base functionality required by the other   
                collection items.    
                Without disk, this object will not exist. This will be set at   
                boot-up initialization. If the disk fails, in any way, then   
                the disk error functionality will handle the situation.
                
                A color printer (LaserJet 4550) that only has a RAMDISK installed is 
                treated like there is no disk and therefore this object will 
                not exist.  
                
                The value of this object will be:
                !cCollatedOriginals - Only FLASH installed
                cCollatedOriginals  - IDE is installed combined
                with/without FLASH
                cCollatedOriginals  - RAMDISK is On combined with/without FLASH"
::= { status-system 42 }
               
               
host-application-available-memory OBJECT-TYPE
   SYNTAX      INTEGER
   ACCESS      read-only
   STATUS      optional
   DESCRIPTION "Returns the amount of memory, in bytes, that the device has		
                available for job-related processing or resources. Also known		
                as driver work space (DWS) memory."
::= { status-system 59 }
               
               
job-info-change-id OBJECT-TYPE
   SYNTAX      OCTET STRING (SIZE(16))
   ACCESS      read-only
   STATUS      optional
   DESCRIPTION "Returns the current value of an object in the job-info sub-tree		
                whose value has changed. Define the object identifier for the		
                object whose value has changed as		
                job-info.required-field.optional-field.job-id. job-info		
                represents the OID prefix of all objects in the job-info		
                sub-tree. Required-field represents the OID field value that		
                follows the job-info prefix. Since some objects in the job-info		
                sub-tree have two OID fields between the job-info prefix and		
                the job-id, the optional-field represents the OID field between		
                the required-field and the job-id field, if present. Using this		
                definition, the format for the JOB-INFO-CHANGE-ID binary value		
                can be described as follows:    	
                    Bytes 0-3 : required-field    	
                    Bytes 4-7 : optional-field, or all zeros if there    	
                    is no optional field    	
                    Bytes 8-11: Job ID.    	
                    Bytes 12-n : The value of the object job-info.		
                        required-field.optional-field.job-id.    	
                All multi-byte values stored in Motorola (big-endian) format,		
                where the most significant byte occurs first.
                Additional information:
                $product_str will use this object to report
                changes to the job-info-pages-printed and job-info-state
                objects.  The required-field (bytes 0 through 3) will 
                designate whether the change to be reported involves the 
                pages printed (13) or job state (15).  The optional-field 
                (bytes 4 through 7) will always be zeroes.  The value-field
                (bytes 12 through 15) will contain the new value for pages
                printed or job state cast to a 32-bit integer.
                
                Note:  It is possible that traps generated by this object
                have the same value.  This is caused by the architecture of
                $product_str.  In the $product_str System, it is highly probable that
                the object value will change so rapidly that when the trap is
                processed, PML will read the same value twice.  This is timing
                related and will generally be seen at the end of a job."
::= { settings-job 3 }
               
               
hold-job-timeout OBJECT-TYPE
   SYNTAX      INTEGER
   ACCESS      read-write
   STATUS      optional
   DESCRIPTION "The time, in minutes, that the printer will wait before		
                automatically deleting a held job. This allows the printer to		
                automatically clean up jobs that have been forgotten (held but		
                never released).
                Additional information:
                This only applies to temporary held jobs, i.e., HOLD=ON or
                PROOF.  This is a global timer that only affects the jobs
                that are sent after it is set.
                		A value of 0 means never delete the jobs.
                		Setting it to an unsupported value causes
                		the printer to substitute a value (listed
                		below) and to return <noError>
                		status.  
                		LaserJet 4600 supports values of 0, 60, 240, 1440, and 10080   
                		The values are as follows:  
                <=0 snap to 0   (disabled)  
                >=1 and <=150 snap to 60 (60 minutes)  
                >=151 and <=840 snap to 240 (4 hours)  
                >=841 and <=2880 snap to 1440 (1 day)  
                >=2881 snap to 10080  (1 week)"
::= { settings-job 10 }
               
               
current-job-parsing-id OBJECT-TYPE
   SYNTAX      INTEGER(-1..2147483647)
   ACCESS      read-only
   STATUS      optional
   DESCRIPTION "Contains the printer assigned job identification for the job		
                currently being processed by the processing PDL sub-system. The		
                job ID is a monotonically increasing number. The job ID may be		
                reset to zero at power-up and may roll over to zero after		
                reaching some maximum value.
                Additional information:
                A value of -1 is returned when the printer
                is not parsing a job.  
                
                When data for a new job is detected, this object is
                updated (the job may or may not turn out to be a Null
                Job); however, the trap does not occur until the printer
                determines that it is not a Null Job.  (A job is considered
                to be a 'null job' if it has no name or job attribute, 
                causes no pages to be printed, and consumes MIN_JOB_SIZE
                (9) or fewer bytes.)  A trapped value will differ from 
                the previous value by one or more.  See the Job Boundary 
                ERS for details on what constitutes a job boundary.  
                
                Some job-info- objects are created when the first data
                bytes are received.  If the printer determines that the
                job is a Null Job, the job-info- objects related to the
                Null Job are deleted.  $product_str retains the job-info-
                objects for the MAX_JOBS_IN_LIST (32) most recent jobs 
                that are not Null Jobs.  
                
                The first job received after power-up will have job ID 1,
                and the job ID will increment to 2,147,483,647 before 
                rolling to zero.  To distinguish whether a power cycle or a 
                rollover causes a reduction in the job ID value, the 
                object prtGeneralConfigChanges can be watched and if it 
                increments at the same time as the drop is observed in
                the value of CURRENT-JOB-PARSING-ID, then a power cycle
                is the most likely cause."
::= { job-being-parsed 1 }
               
               
job-info-name1 OBJECT-TYPE
   SYNTAX      OCTET STRING
   ACCESS      read-only
   STATUS      optional
   DESCRIPTION "Contains the first part of this print job's name. The last OID		
                field for this dynamic object contains the job ID.
                Additional information:
                The job name is the string specified by the
                NAME= parameter of the @PJL JOB command which allows a
                maximum of 80 characters.  The first 40 characters are
                in this object and the second 40 are in job-info-name2.
                The symbol set is Roman-8.  
                
                When jobs are nested, the value assigned to this object
                is the name provided by the most recent @PJL JOB NAME=
                command.  If no name is provided, a null string is
                returned."
::= { job-info 1 }
               
               
job-info-name2 OBJECT-TYPE
   SYNTAX      OCTET STRING
   ACCESS      read-only
   STATUS      optional
   DESCRIPTION "Contains the second part of this print job's name. The last OID		
                field for this dynamic object contains the job ID.
                Additional information:
                See job-info-name1."
::= { job-info 2 }
               
               
job-info-stage OBJECT-TYPE
   SYNTAX      OCTET STRING
   ACCESS      read-only
   STATUS      optional
   DESCRIPTION "Indicates what printer sub-systems are currently processing		
                this print job. The last OID field for this dynamic object		
                contains the job ID. cSourceSubsystem - some of the job is in		
                the printer I/O subsystem. cProcessingSubsystem - some of the		
                job is in the printer imaging processing subsystem.		
                cDestinationSubsystem - some of the job is being printed.
                Additional information:
                For $product_str, cSourceSubsystem and
                cProcessingSubsystem will always be set and cleared
                together.  They are set when the beginning of the
                job is detected, and they are cleared when the end
                of the job is parsed.  
                
                A non-printing job will never set
                cDestinationSubsystem.  
                
                When a page is ready to be printed (the intermediate has
                been built and the page is `closed' by the personality), 
                cDestinationSubsystem will be set even if a page of a 
                previous job is currently being printed.
                cDestinationSubsystem remains set until the last page of
                the job has finished printing.  
                
                If a page requires extensive processing and allows all
                the previous pages of a job to complete printing,
                cDestinationSubsystem will remain set until the last
                page of the job has finished printing."
::= { job-info 10 }
               
               
job-info-io-source OBJECT-TYPE
   SYNTAX      INTEGER
   ACCESS      read-only
   STATUS      optional
   DESCRIPTION "Indicates which I/O source, the print job was received over.		
                The value maps to port numbering scheme supported in the		
                DEVICE/SOURCE-SUBSYSTEM/IO/PORTS sub-tree."
::= { job-info 11 }
               
               
job-info-pages-processed OBJECT-TYPE
   SYNTAX      INTEGER
   ACCESS      read-only
   STATUS      optional
   DESCRIPTION "Indicates the number of pages processed by the processing		
                subsystem. If neither the cSourceSubsystem or the		
                cProcessingSubsystem items are in the associated JOB-INFO-STAGE		
                object, then this object contains the total number of pages		
                processed for this job. The last OID field for this dynamic		
                object contains the job ID.
                Additional information:
                This object is incremented by one when a
                page is processed (`closed' by the personality), regardless 
                of the number of pages that are printed as a result of the 
                single page processed.  In other words, it does not matter 
                how many identical copies of a page are printed or no pages
                may be printed if operating in silent run mode, this count
                is incremented exactly once.  
                
                A page is considered processed when all of the input
                data has been processed for a page (that is, when the 
                intermediate has been produced, and the personality has 
                `closed' the page.  At this time, the image of the page is 
                not necessarily completely formed.)"
::= { job-info 12 }
               
               
job-info-pages-printed OBJECT-TYPE
   SYNTAX      INTEGER
   ACCESS      read-only
   STATUS      optional
   DESCRIPTION "Indicates the number of pages printed by the destination		
                subsystem. If none of the cSourceSubsystem,		
                cProcessingSubsystem or cDestinationSubsystem items are in the		
                associated JOB-INFO-STAGE object, then this object contains the		
                total number of pages printed for this job. This value may		
                increase by two each time for duplex jobs. The last OID field		
                for this dynamic object contains the job ID.
                Additional information:
                If multiple copies of a page are printed,
                each copy is counted individually."
::= { job-info 13 }
               
               
job-info-size OBJECT-TYPE
   SYNTAX      INTEGER
   ACCESS      read-only
   STATUS      optional
   DESCRIPTION "Indicates the number of bytes of data processed by the		
                processing subsystem. If neither of the cSourceSubsystem or		
                cProcessingSubsystem items are in the associated JOB-INFO-STAGE		
                object, then this object contains the size of this job, in		
                bytes. The last OID field for this dynamic object contains the		
                job ID.
                Additional information:
                This count may be incremented by values
                other than one as blocks of data are processed; blocks
                of data (which may be as large as 2K bytes) will be
                processed in a varying amount of time.  
                
                During the processing of a job and even when a job completes, 
                an exact count of the number of I/O bytes processed by the
                job is not necessarily to be expected."
::= { job-info 14 }
               
               
job-info-state OBJECT-TYPE
   SYNTAX      INTEGER {
		   eAborted(3),
		   eWaitingForResources(4),
		   ePrinted(5),
		   eTerminating(7),
		   eCancelled(10),
		   eProcessing(11),
		   eScanning(12),
		   eSending(13)
		   }
   ACCESS      read-only
   STATUS      optional
   DESCRIPTION "Indicates the state of the job. The last OID field for this		
                dynamic object contains the job ID.    	
                    eAborted - the print job was aborted.    	
                    eWaitingForResources - the print job requires resources		
                        that are not currently available. Example resources		
                        that can cause the job to wait include the print engine		
                        or PDL processor being unavailable. The print engine		
                        could be unavailable due to paper out, paper jam,		
                        staple out, stapler jam, marking agent low, output bin		
                        full, etc. The PDL processor could be unavailable due		
                        to an off-line condition. Each printer specific object		
                        specification should state which conditions cause a job		
                        to be waiting for resources and also state which		
                        objects can be retrieved by an application to determine		
                        the exact cause of a resource being unavailable.    	
                    ePrinted - the job has printed. The related JOB-INFO-		
                        OUTCOME object indicates if any problems were		
                        encountered while the job was processed.    	
                    eRetained - the job can be reprinted.    	
                    eTerminating - the job was aborted or cancelled and is		
                        currently is terminating.    	
                    eInterrupted - the job has been interrupted. The job can be		
                        continued.    	
                    ePaused - the job has been paused. The job can be		
                        continuted.    	
                    eCancelled - the job has been cancelled.    	
                    eProcessing - the job is currently being printed normally.		
                          "
::= { job-info 15 }
               
               
job-info-outcome OBJECT-TYPE
   SYNTAX      INTEGER {
		   eOk(3)
		   }
   ACCESS      read-only
   STATUS      optional
   DESCRIPTION "Indicates if any warning or error conditions were encountered		
                while processing the assoicated job. The last OID field for		
                this dynamic object contains the job ID.
                Additional information:
                In $product_str, warnings and errors are not recorded
                in this object.  Although no meaningful information can be
                obtained from this object, it is kept around for the
                compatibility needs of existing software."
::= { job-info 19 }
               
               
job-info-outbins-used OBJECT-TYPE
   SYNTAX      OCTET STRING
   ACCESS      read-only
   STATUS      optional
   DESCRIPTION "Indicates which output bins this job has delivered printed		
                pages to. The last OID field for this dynamic object contains		
                the job ID.
                Additional information:
                The bins designated by this collection include
                the printer's own output bins as well as the `logical output
                bins' associated with any attached external paper handling
                devices.  (The mapping of the physical output bins of an
                external paper handling device to its `logical output bins'
                depends on the usage mode of the device.  For instance, in
                `mailbox mode', there is one-to-one correspondence of
                `logical output bins' to physical bins, whereas in `stacker
                mode', one `logical output bin' may map to several physical
                bins.)  
                
                Although LaserJet 4100 and LaserJet 4550 both come with two output
                bins -- a face-down bin on the top of the device and a
                face-up bin at the back of the device -- firmware will not
                provide a means of selecting between the two, nor will it
                report which of the two gets used.  For this reason, bit 0
                (cOutbin1) of this collection is being used to designate
                both of these bins together."
::= { job-info 20 }
               
               
job-info-physical-outbins-used OBJECT-TYPE
   SYNTAX      OCTET STRING
   ACCESS      read-only
   STATUS      optional
   DESCRIPTION "Indicates which physical output bins this job has delivered		
                printed pages to. The last OID field for this dynamic object		
                contains the job ID.
                Additional information:
                The output bins designated by the bits of
                this collection include the standard output bin(s) plus the
                physical bins of attached external paper handling devices.
                The configuration (if any) of external paper handling devices
                will determine the mapping of individual bits in this
                collection to the physical bins of the devices.
                For LaserJet 4100 and LaserJet 4550, the cOutbin1 is used for Face Down
                bin, cOutbin2 is used for Face Up bin, and 3-15 are used for
                the 13 optional output bins (12 plus an extension to the Face
                Up bin) for backwards compatibility with LaserJet 8000/LaserJet 8100 and
                forwards compatibility with LaserJet 8150.  However, since they
                cannot distinguish output going to the Face Up or Face Down
                bin in the firmware because the diverter can only be moved
                manually, bit 0 (cOutbin1) is being used to designate
                both of these bits together.  If an external paper handling
                output device is connected, then bit 2 (cOutbin3) will
                represent the device's first output bin (and so on)."
::= { job-info 22 }
               
               
job-info-attr-1 OBJECT-TYPE
   SYNTAX      OCTET STRING (SIZE(1..80))
   ACCESS      read-only
   STATUS      optional
   DESCRIPTION "Returns the value that was set in PJL via the SET JOBATTR=		
                command. Attribute objects are saved sequentially, starting		
                with 1, after the start of a job. If more attributes are set		
                than there are objects to store them, the excess JOBATTR values		
                are ignored. If the corresponding SET JOBATTR= command has not		
                been received when a get is done for this object, a status of		
                <noSuchName> will be returned."
::= { job-info-attribute 1 }
               
               
job-info-attr-2 OBJECT-TYPE
   SYNTAX      OCTET STRING (SIZE(1..80))
   ACCESS      read-only
   STATUS      optional
   DESCRIPTION "Returns the value that was set in PJL via the SET JOBATTR=		
                command. See JOB-INFO-ATTR-1 for details."
::= { job-info-attribute 2 }
               
               
job-info-attr-3 OBJECT-TYPE
   SYNTAX      OCTET STRING (SIZE(1..80))
   ACCESS      read-only
   STATUS      optional
   DESCRIPTION "Returns the value that was set in PJL via the SET JOBATTR=		
                command. See JOB-INFO-ATTR-1 for details."
::= { job-info-attribute 3 }
               
               
job-info-attr-4 OBJECT-TYPE
   SYNTAX      OCTET STRING (SIZE(1..80))
   ACCESS      read-only
   STATUS      optional
   DESCRIPTION "Returns the value that was set in PJL via the SET JOBATTR=		
                command. See JOB-INFO-ATTR-1 for details."
::= { job-info-attribute 4 }
               
               
job-info-attr-5 OBJECT-TYPE
   SYNTAX      OCTET STRING (SIZE(1..80))
   ACCESS      read-only
   STATUS      optional
   DESCRIPTION "Returns the value that was set in PJL via the SET JOBATTR=		
                command. See JOB-INFO-ATTR-1 for details."
::= { job-info-attribute 5 }
               
               
job-info-attr-6 OBJECT-TYPE
   SYNTAX      OCTET STRING (SIZE(1..80))
   ACCESS      read-only
   STATUS      optional
   DESCRIPTION "Returns the value that was set in PJL via the SET JOBATTR=		
                command. See JOB-INFO-ATTR-1 for details."
::= { job-info-attribute 6 }
               
               
job-info-attr-7 OBJECT-TYPE
   SYNTAX      OCTET STRING (SIZE(1..80))
   ACCESS      read-only
   STATUS      optional
   DESCRIPTION "Returns the value that was set in PJL via the SET JOBATTR=		
                command. See JOB-INFO-ATTR-1 for details."
::= { job-info-attribute 7 }
               
               
job-info-attr-8 OBJECT-TYPE
   SYNTAX      OCTET STRING (SIZE(1..80))
   ACCESS      read-only
   STATUS      optional
   DESCRIPTION "Returns the value that was set in PJL via the SET JOBATTR=		
                command. See JOB-INFO-ATTR-1 for details."
::= { job-info-attribute 8 }
               
               
job-info-attr-9 OBJECT-TYPE
   SYNTAX      OCTET STRING (SIZE(1..80))
   ACCESS      read-only
   STATUS      optional
   DESCRIPTION "Returns the value that was set in PJL via the SET JOBATTR=		
                command. See JOB-INFO-ATTR-1 for details."
::= { job-info-attribute 9 }
               
               
job-info-attr-10 OBJECT-TYPE
   SYNTAX      OCTET STRING (SIZE(1..80))
   ACCESS      read-only
   STATUS      optional
   DESCRIPTION "Returns the value that was set in PJL via the SET JOBATTR=		
                command. See JOB-INFO-ATTR-1 for details."
::= { job-info-attribute 10 }
               
               
job-info-attr-11 OBJECT-TYPE
   SYNTAX      OCTET STRING (SIZE(1..80))
   ACCESS      read-only
   STATUS      optional
   DESCRIPTION "Returns the value that was set in PJL via the SET JOBATTR=		
                command. See JOB-INFO-ATTR-1 for details."
::= { job-info-attribute 11 }
               
               
job-info-attr-12 OBJECT-TYPE
   SYNTAX      OCTET STRING (SIZE(1..80))
   ACCESS      read-only
   STATUS      optional
   DESCRIPTION "Returns the value that was set in PJL via the SET JOBATTR=		
                command. See JOB-INFO-ATTR-1 for details."
::= { job-info-attribute 12 }
               
               
job-info-attr-13 OBJECT-TYPE
   SYNTAX      OCTET STRING (SIZE(1..80))
   ACCESS      read-only
   STATUS      optional
   DESCRIPTION "Returns the value that was set in PJL via the SET JOBATTR=		
                command. See JOB-INFO-ATTR-1 for details."
::= { job-info-attribute 13 }
               
               
job-info-attr-14 OBJECT-TYPE
   SYNTAX      OCTET STRING (SIZE(1..80))
   ACCESS      read-only
   STATUS      optional
   DESCRIPTION "Returns the value that was set in PJL via the SET JOBATTR=		
                command. See JOB-INFO-ATTR-1 for details."
::= { job-info-attribute 14 }
               
               
job-info-attr-15 OBJECT-TYPE
   SYNTAX      OCTET STRING (SIZE(1..80))
   ACCESS      read-only
   STATUS      optional
   DESCRIPTION "Returns the value that was set in PJL via the SET JOBATTR=		
                command. See JOB-INFO-ATTR-1 for details."
::= { job-info-attribute 15 }
               
               
job-info-attr-16 OBJECT-TYPE
   SYNTAX      OCTET STRING (SIZE(1..80))
   ACCESS      read-only
   STATUS      optional
   DESCRIPTION "Returns the value that was set in PJL via the SET JOBATTR=		
                command. See JOB-INFO-ATTR-1 for details."
::= { job-info-attribute 16 }
               
               
job-info-requested-originals OBJECT-TYPE
   SYNTAX      INTEGER
   ACCESS      read-only
   STATUS      optional
   DESCRIPTION "The number of requested collated copies. The value was supplied		
                with the job via PJL QTY variable, the PostScript Collate and		
                NumCopies entries in the page device dictionary, or via some		
                other mechansim."
::= { job-info 24 }
               
               
job-info-page-count-current-original OBJECT-TYPE
   SYNTAX      INTEGER
   ACCESS      read-only
   STATUS      optional
   DESCRIPTION "The page number being printed within the current copy of a		
                collated multi-copy job. This value changes when the		
                job-info-pages-printed changes. The job-info-pages-printed		
                indicates the total number of pages printed in the job, while		
                this object indicates the number of pages printed for this copy		
                of a collated multi-copy job.
                Additional information:
                The number of pages in the current copy of a collated
                multi-copy job which have been completely printed and
                safely delivered to the output bin."
::= { job-info 25 }
               
               
job-info-pages-in-original OBJECT-TYPE
   SYNTAX      INTEGER
   ACCESS      read-only
   STATUS      optional
   DESCRIPTION "Number of pages in a single copy of a collated multi-copy job."
::= { job-info 26 }
               
               
job-info-printed-originals OBJECT-TYPE
   SYNTAX      INTEGER
   ACCESS      read-only
   STATUS      optional
   DESCRIPTION "Number of collated copies completely printed and delivered to		
                the output bin at time of query."
::= { job-info 27 }
               
               
job-info-accounting-media-size OBJECT-TYPE
   SYNTAX      INTEGER {
		   eUSExecutive(1),
		   eUSLetter(2),
		   eUSLegal(3),
		   eLedger(11),
		   eROC16K(17),
		   eJISExecutive(18),
		   eROC8K(19),
		   eISOandJISA5(25),
		   eISOandJISA4(26),
		   eISOandJISA3(27),
		   eJISB5(45),
		   eJISB4(46),
		   eISOB5(65),
		   eJapansePostcardDouble(72),
		   eMonarch(80),
		   eCommercial10(81),
		   eInternationalDL(90),
		   eInternationalC5(91),
		   eInternationalB5(100),
		   eCustom(101),
		   eUSLetterR(258),
		   eISOandJISA4R(282),
		   eUnknownMediaSize(32767)
		   }
   ACCESS      read-only
   STATUS      optional
   DESCRIPTION "Contains the media size of the printed job. The media size of		
                the first page will decide the media size of the entire job.		
                The return value of this object will only be valid when the		
                printer finishes printing the entire job."
::= { job-info-accounting 1 }
               
               
job-info-accounting-media-type OBJECT-TYPE
   SYNTAX      INTEGER {
		   eUnknownMedia(1),
		   eStandardType(2),
		   ePreprinted(3),
		   eLetterhead(4),
		   eTransparency(5),
		   ePrepunched(6),
		   eLabels(7),
		   eBond(8),
		   eRecycled(9),
		   eColored(10),
		   eCardStock(11),
		   eLight(12),
		   eIntermediate(13),
		   eHeavy(14),
		   eExtraHeavy(15),
		   eRough(16),
		   eGloss(17),
		   eHeavyGloss(18),
		   eEnvelope(19),
		   eGlossFilm(20),
		   eExtraHeavyGloss(21),
		   eCardGlossy(22),
		   eMidWeight(23),
		   eHpMatte90(24),
		   eHpMatte105(25),
		   eHpMatte120(26),
		   eHpSoftGloss120(27),
		   eHpGlossy120(28),
		   eHpMatte160(29),
		   eHpGlossy160(30),
		   eHpMatte200(31),
		   eHpMatte220(32),
		   eHpGlossy220(33),
		   eHpTough(34),
		   eUserType1(35),
		   eUserType2(36),
		   eUserType3(37),
		   eUserType4(38),
		   eUserType5(39)
		   }
   ACCESS      read-only
   STATUS      optional
   DESCRIPTION "Contains the media type of the printed job. The media type of		
                the first page will decide the media type of the entire job.		
                The return value of this object will only be valid when the		
                printer finishes printing the entire job."
::= { job-info-accounting 2 }
               
               
job-info-accounting-finishing-options OBJECT-TYPE
   SYNTAX      INTEGER {
		   eNoFinish(1),
		   eOffset(2),
		   ePunch(3),
		   eStapler(4),
		   eFinisher(5)
		   }
   ACCESS      read-only
   STATUS      optional
   DESCRIPTION "Contains the finishing option used on the printed job. The		
                finishing option specified for the first page will decide the		
                finishing option of the entire job. The return value of this		
                object will only be valid when the printer finishes printing		
                the entire job."
::= { job-info-accounting 3 }
               
               
job-info-accounting-media-simplex-count OBJECT-TYPE
   SYNTAX      INTEGER
   ACCESS      read-only
   STATUS      optional
   DESCRIPTION "Contains the total number of simplex pages printed in a		
                particular job."
::= { job-info-accounting 4 }
               
               
job-info-accounting-media-duplex-count OBJECT-TYPE
   SYNTAX      INTEGER
   ACCESS      read-only
   STATUS      optional
   DESCRIPTION "Contains the total number of duplex pages printed in a		
                particular job."
::= { job-info-accounting 5 }
               
               
job-info-accounting-grayscale-impression-count OBJECT-TYPE
   SYNTAX      INTEGER
   ACCESS      read-only
   STATUS      optional
   DESCRIPTION "Contains the total number of monochrome pages printed in a		
                particular job."
::= { job-info-accounting 6 }
               
               
job-info-accounting-color-impression-count OBJECT-TYPE
   SYNTAX      INTEGER
   ACCESS      read-only
   STATUS      optional
   DESCRIPTION "Contains the total number of color pages printed in a		
                particular job."
::= { job-info-accounting 7 }
               
               
job-info-accounting-black-dots OBJECT-TYPE
   SYNTAX      INTEGER
   ACCESS      read-only
   STATUS      optional
   DESCRIPTION "Contains the total number of black pixels used in a particular		
                job.
                Additional information:
                This object reports kilodots.  (A kilodot
                is 1000 dots.)"
::= { job-info-accounting 8 }
               
               
job-info-accounting-yellow-dots OBJECT-TYPE
   SYNTAX      INTEGER
   ACCESS      read-only
   STATUS      optional
   DESCRIPTION "Contains the total number of yellow pixels used in a particular		
                job.
                Additional information:
                This object reports kilodots.  (A kilodot
                is 1000 dots.)"
::= { job-info-accounting 9 }
               
               
job-info-accounting-cyan-dots OBJECT-TYPE
   SYNTAX      INTEGER
   ACCESS      read-only
   STATUS      optional
   DESCRIPTION "Contains the total number of cyan pixels used in a particular		
                job.
                Additional information:
                This object reports kilodots.  (A kilodot
                is 1000 dots.)"
::= { job-info-accounting 10 }
               
               
job-info-accounting-magenta-dots OBJECT-TYPE
   SYNTAX      INTEGER
   ACCESS      read-only
   STATUS      optional
   DESCRIPTION "Contains the total number of magenta pixels used in a		
                particular job.
                Additional information:
                This object reports kilodots.  (A kilodot
                is 1000 dots.)"
::= { job-info-accounting 11 }
               
               
job-info-accounting-job-type OBJECT-TYPE
   SYNTAX      INTEGER {
		   ePrintJob(1),
		   eIPPJob(2),
		   eCopyJob(3),
		   eCopyInterruptJob(4),
		   eJetSendJob(5),
		   eInternalPage(6),
		   eCleaningPage(7),
		   eAutoCleaningPage(8),
		   eDigitalSendJob(9),
		   eWebPrintJob(10),
		   eFaxPrintJob(11),
		   eRetrievedJob(12),
		   ePhotoCardPrintJob(13),
		   eUnknownJob(1000)
		   }
   ACCESS      read-only
   STATUS      optional
   DESCRIPTION "Keeps track of what type of job is processed. "
::= { job-info-accounting 14 }
               
               
held-job-user-name OBJECT-TYPE
   SYNTAX      OCTET STRING (SIZE(0..40))
   ACCESS      read-only
   STATUS      optional
   DESCRIPTION "User name that is obtained by the driver through some internal		
                method or from user input.
                Additional information:
                The following is a general description for all the JOB-MANAGEMENT
                objects described below.  These object describe the attributes of the
                dynamic list containing all the stored jobs on the disk available for
                printing or deleting via the job-management feature.  The jobs on this
                list are not deleted from the disk unless explicitly specified by the
                user.  A print job may be specified for retention by PJL commands in the
                data stream.
                
                Following is a list of the PJL commands (i.e. these comments describe 
                the PJL implementation and in some cases do not reflect the PML 
                implementation.):
                
                @PJL SET HOLD=OFF|ON|PROOF|STORE|PRINT
                
                GENERAL DESCRIPTION: 
                
                This variable specifies the retention classification of the job.  The
                values indicate whether the job is printed immediately and/or stored.
                
                OFF:  The job is printed but not retained on disk after printing.  This
                is the default value.
                
                ON:  This setting may be thought of as free proof-and-hold.  The
                requested number of copies will be printed and the job will be
                temporarily stored on disk.  The job will then be available for printing
                additional copies through the control panel and through PML.  There will
                be a limit to the number of these temporary jobs that may be stored, and
                when the limit is exceeded the oldest job will be removed from the disk.
                
                PROOF:  One copy of the job is printed and remaining copies are stored
                on disk.  The job is then available to select for printing via the
                control panel menus or PML.  The job will be deleted from the disk when
                the disk space is needed for another proof and hold job but only after
                the additional copies have been printed.  It will also be deleted when
                the user sends down another proof and hold job with the same job name,
                or the user explicitly deletes the job.
                
                STORE:  The job is not printed immediately but is retained on disk.  The
                job is available to select for printing via the control panel
                
                DEFAULT VALUE: OFF
                
                The value will be stored in RAM only, not in NVRAM.
                The legal PJL commands are SET and INQUIRE.  DEFAULT is not allowed.
                The variable will appear in the PJL INFO VARIABLES list.
                
                @PJL SET USERNAME=<80 bytes>
                
                GENERAL DESCRIPTION: 
                
                Eighty-character user name that is obtained by the driver through some
                internal method or from user input.  If the job stream does not contain
                a USERNAME the default value will be NO USER NAME.  The driver is
                responsible for determining the size of the printers control panel and
                sending a string of appropriate length.
                
                DEFAULT VALUE: NO USER NAME
                
                The value will be stored in RAM only, not in NVRAM.
                The legal PJL commands are SET and, INQUIRE. DEFAULT is not allowed.
                The variable will appear in the PJL INFO VARIABLES list.
                
                @PJL SET JOBNAME=<80 bytes>
                
                GENERAL DESCRIPTION:
                
                Eighty-character job name that may be generated by the driver or
                obtained from user input.  This value may be used in conjunction with
                the USERNAME to select a job from the front panel.  If the job stream
                does not contain a JOBNAME, the printer will assume no job name; each
                subsequent job that is sent down by the same user would replace the
                users last job on disk.  The driver is responsible for determining the
                size of the printers control panel and sending a string of appropriate
                length.
                
                NOTE:  The limit of 80 bytes is a PJL limit.  The limit for PML will
                be 40 bytes.
                
                DEFAULT VALUE: NULL STRING
                
                The value will be stored in RAM only, not in NVRAM.
                The legal PJL commands are SET and INQUIRE. DEFAULT is not allowed.
                The variable will appear in the PJL INFO VARIABLES list.
                
                @PJL SET HOLDTYPE=PUBLIC|PRIVATE
                
                GENERAL DESCRIPTION:
                
                This variable specifies the privacy level of the job.
                
                PUBLIC:  The job does not require a PIN in order to be released for
                printing.  This is the default value.
                
                PRIVATE:  The job requires a PIN in order to be released for printing.
                The PIN is specified by the HOLDKEY variable.  If the
                
                HOLDTYPE is set to PRIVATE, a HOLDKEY value must be specified.  If no
                HOLDKEY is specified, the job will be considered PUBLIC.
                
                DEFAULT VALUE: PUBLIC
                
                The value will be stored in RAM only, not in NVRAM.
                The legal PJL commands are SET and INQUIRE. DEFAULT is not allowed.
                The variable will appear in the PJL INFO VARIABLES list.
                
                @PJL SET HOLDKEY=4 digits, 0000...9999
                
                GENERAL DESCRIPTION:
                
                A 4-digit string, each digit 0-9, that is specified in the job stream
                and then required to be entered in order to release the job for
                printing.  If a HOLDTYPE is PRIVATE, a HOLDKEY value must be specified.
                If no HOLDKEY value is specified, a job will be considered PUBLIC.
                
                DEFAULT VALUE: NULL STRING
                
                The value will be stored in RAM only, not in NVRAM.
                The legal PJL commands are SET and INQUIRE. DEFAULT is not allowed.
                The variable will appear in the PJL INFO VARIABLES list.
                
                
                The format for the OID is as follows:
                
                3.4.1.6.x.y
                <-----> | |
                |    |  \
                /     |  job-id in the system
                /       \   
                PML_JOB_MGNT_ROOT_OID  \
                job attribute 1..6
                
                x values are 1..6:
                
                1) user-name:  user name that is obtained by the driver through some
                internal method or from user input.
                
                2) job-name:  job name may be generated by the driver or obtained from
                user input.
                
                3) hold:  indicates the retention classification of the job.  The values
                indicate whether the job is printed immediately and/or stored.  There
                are 4 options:
                OFF:    The job is printed but not retained on the disk.
                ON:     The job is printed and stored temporarily on the disk.
                STORE:  The job is not printed but stored on the disk.
                PROOF:  One copy of the job is printed and the remaining copies are
                stored on the disk.
                
                4) holdtype:  The variable specifies the security level of the job.
                PUBLIC:  The job does not require a PIN in order to release the job for
                printing.
                PRIVATE:  The job requires a PIN in order to be released for printing.
                
                5) quantity:  number of copies to print.  Valid values are 0..999.
                
                6) pin:  A 4 digit string, each digit is 0-9, that is specified in the
                job stream and then required to be entered in order to release the job
                for printing.
                
                y :  an unsigned 32-bit number which uniquely identifies the job.  The job
                id for the job remains the same for the job until it is deleted from the
                held jobs list.
                
                
                For example, the OID below is asking for the user name of the
                job whose id is 3.  The application would issue:
                
                OID    
                get 3.4.1.6.1.3
                
                For example, the <getnext> OID values sequence is as follows:
                
                OID                returned OID
                getnext 3.4.1.6         3.4.1.6.1.1
                getnext 3.4.1.6.1.1     3.4.1.6.1.2
                getnext 3.4.1.6.2.1     3.4.1.6.2.2
                ***
                getnext 3.4.1.6.1.6     3.4.1.6.1.7
                getnext 3.4.1.6.2.1     3.4.1.6.2.2
                getnext 3.4.1.6.5.2828  3.4.1.6.6.1 
                
                NOTE: for example above, job id 2828 is the last job in the list of
                held jobs.
                ***
                
                Also supported is <getnext> on the job attributes:
                OID                returned OID
                getnext 3.4.1.6.1       3.4.1.6.1.1
                getnext 3.4.1.6.6       3.4.1.6.6.1"
::= { held-job-info 1 }
               
               
held-job-job-name OBJECT-TYPE
   SYNTAX      OCTET STRING (SIZE(0..40))
   ACCESS      read-only
   STATUS      optional
   DESCRIPTION "The job name may be generated by the driver or obtained from		
                user input."
::= { held-job-info 2 }
               
               
held-job-retention OBJECT-TYPE
   SYNTAX      INTEGER {
		   eHoldOff(1),
		   eHoldOn(2),
		   eHoldStore(3),
		   eHoldProof(4)
		   }
   ACCESS      read-only
   STATUS      optional
   DESCRIPTION "Indicates the retention classification of the job. The values		
                indicate whether the job is printed immediately or stored.		
                There are 4 options:    	
                    eHoldOff: The job is printed but not retained on the disk.		
                           	
                    eHoldOn: The job is printed and stored temporarily on the		
                        disk.    	
                    eHoldStore: The job is not printed but stored on the disk.		
                           	
                    eHoldProof: One copy of the job is printed and the		
                        remaining copies are stored on the disk.   "
::= { held-job-info 3 }
               
               
held-job-security OBJECT-TYPE
   SYNTAX      INTEGER {
		   eHoldTypePublic(1),
		   eHoldTypePrivate(2)
		   }
   ACCESS      read-only
   STATUS      optional
   DESCRIPTION "The variable specifies the security level of the job.    	
                    eHoldTypePublic: The job does not require a PIN in order to		
                        release the job for printing.    	
                    eHoldTypePrivate: The job requires a PIN in order to be		
                        released for printing.   "
::= { held-job-info 4 }
               
               
held-job-quantity OBJECT-TYPE
   SYNTAX      INTEGER(1..999)
   ACCESS      read-only
   STATUS      optional
   DESCRIPTION "Number of copies to print."
::= { held-job-info 5 }
               
               
held-job-pin OBJECT-TYPE
   SYNTAX      OCTET STRING (SIZE(0..4))
   ACCESS      read-only
   STATUS      optional
   DESCRIPTION "A string that is specified in the job stream and then required		
                to be entered in order to release the job for printing. PIN		
                stands for Personal Identification Number.
                Additional information:
                Must be a 4 digit string, each digit must be 0..9 or a null string
                if there is no pin.
                		For security purposes, you can no longer get the value of the PIN."
::= { held-job-info 6 }
               
               
held-job-print OBJECT-TYPE
   SYNTAX      OCTET STRING (SIZE(12))
   ACCESS      write-only
   STATUS      optional
   DESCRIPTION "Instructs the printer to schedule the specified held job for		
                printing with the specified number of copies. The job-id is		
                used to identify which job to print. A held job can also be		
                printed from the control panel.
                Additional information:
                Bytes 0-3 is the job id of the job to print.
                Bytes 4-7 is the number of copies to print.
                Bytes 8-11 (optional) contain the PIN for
                a Private job. "
::= { held-job-control 1 }
               
               
held-job-delete OBJECT-TYPE
   SYNTAX      INTEGER
   ACCESS      write-only
   STATUS      optional
   DESCRIPTION "Instructs the printer to delete the specified held job from the		
                list. The job-id is used to identify which job to delete. A		
                held job can also be deleted from the control panel.
                Additional information:
                Setting this to a value that is not a Held Job on the
                system or is a Private Held Job returns <ErrUnsupValue>.
                To delete a private Held Job, you must use the PML object
                HELD-JOB-PRINT with a quantity of 0 and supply the correct
                HELD-JOB-PIN with the request. (See HELD-JOB-PRINT)"
::= { held-job-control 2 }
               
               
held-job-set-queue-size OBJECT-TYPE
   SYNTAX      INTEGER(0..100)
   ACCESS      read-write
   STATUS      optional
   DESCRIPTION "Sets the maximum number of jobs which can be stored in the held		
                job list.
                Additional information:
                Sets the size of the temporary job lists queue."
::= { held-job-control 3 }
               
               
held-job-enable OBJECT-TYPE
   SYNTAX      INTEGER {
		   eDisabled(1),
		   eEnabled(2)
		   }
   ACCESS      read-write
   STATUS      optional
   DESCRIPTION "Enables or disables Job Retention (Job Hold). The valid values		
                are eDisabled and eEnabled. (Specifying an invalid mode causes		
                an <badValue> error to be returned.) When		
                eDisabled is specified all Job Retention (Hold, Proof, Store,		
                PIN Printing) is disabled. When eEnabled is specified, the Job		
                Retention characteristics of a given job are defined by the PJL		
                variable SET HOLD.
                Additional information:
                When disabled, held jobs are not removed,
                but must be explicitly removed through the Control Panel
                or the PML object HELD-JOB-DELETE."
::= { held-job-control 4 }
               
               
mopy-mode OBJECT-TYPE
   SYNTAX      INTEGER {
		   eOff(1),
		   eStandard(4),
		   eEnhanced(5)
		   }
   ACCESS      read-write
   STATUS      optional
   DESCRIPTION "Controls or reports how mopies are generated. eOff turns off		
                the mopy feature. eAuto allows the device to determine the best		
                method for generating mopies based on the device configuration.		
                eStandard spools the I/O data and replays the I/O data multiple		
                times to generate the mopies. eEnhanced spools the rasterized		
                page images and replays the rasterized data to generate the		
                mopies. Typically, the rasterized data will be larger and will		
                allow all but the first mopy to print at speed. If the job		
                being mopied is not extremely complex, then the first mopy will		
                print at speed also."
::= { settings-spooler 1 }

               
               
date-display OBJECT-TYPE
   SYNTAX      INTEGER {
		   eDateDisplayMMM-DD-YYYY(4),
		   eDateDisplayDD-MMM-YYYY(5),
		   eDateDisplayYYYY-MMM-DD(6)
		   }
   ACCESS      read-write
   STATUS      optional
   DESCRIPTION "Controls front-panel date display format.
                Additional information:
                Controls front-panel date display format."
::= { settings-system 22 }
               
               
date-and-time OBJECT-TYPE
   SYNTAX      OCTET STRING
   ACCESS      read-write
   STATUS      optional
   DESCRIPTION "A C structure containing the following fields:    typedef		
                struct {    	
                    ubyte yr; /* year: 0 to 99 */    	
                    ubyte mon; /* month: 1 to 12 */    	
                    ubyte day; /* day: 1 to 31 */    	
                    ubyte wday; /* Day of week: 1 to 07 */    	
                    ubyte hr; /* hour: 0 to 23 */    	
                    ubyte min; /* minute: 0 to 59 */    	
                    ubyte sec; /* second: 0 to 59 */    	
                    } date_t;    	
                where ubyte is an unsigned byte (0-255).
                Additional information:
                A C structure containing the following fields:    typedef
                struct {   
                ubyte yr;   /* year: 3 to 99 */   
                ubyte mon;  /* month: 1 to 12 */   
                ubyte day;  /* day: 1 to 31 */   
                ubyte wday; /* Day of week: 1 to 07 */   
                ubyte hr;   /* hour: 0 to 23 */   
                ubyte min;  /* minute: 0 to 59 */   
                ubyte sec;  /* second: 0 to 59 */   
                } date_t;   
                where ubyte is an unsigned byte (0-255)."
::= { status-system 17 }
               
               
time-display OBJECT-TYPE
   SYNTAX      INTEGER {
		   eTimeDisplayTwelveHour(1),
		   eTimeDisplayTwentyFourHour(2)
		   }
   ACCESS      read-write
   STATUS      optional
   DESCRIPTION "Controls front-panel time display format. Set to		
                eTimeDisplayTwelveHour for AM/PM display. Set to		
                eTimeDisplayTwentyFourHour for military-type display.
                Additional information:
                Controls front-panel time display format. Set to
                eTimeDisplayTwelveHour for AM/PM display. Set to
                eTimeDisplayTwentyFourHour for military-type display."
::= { status-system 28 }
               
               
direct-connect-ports-enable OBJECT-TYPE
   SYNTAX      INTEGER {
		   eFalse(1),
		   eTrue(2),
		   eUnSupported(3)
		   }
   ACCESS      read-write
   STATUS      optional
   DESCRIPTION "This object specifies whether all direct connect ports		
                (parallel and USB) are available or ignored. JetDirect,		
                embedded network connectivity, and third party add-on cards		
                (such as Firewire) will be unaffected by setting this object."
::= { settings-system 43 }
               
               
mio1-model-name OBJECT-TYPE
   SYNTAX      OCTET STRING
   ACCESS      read-only
   STATUS      optional
   DESCRIPTION "Returns product information identifying the I/O card. Example:		
                XXXX."
::= { mio1 2 }
               
               
mio1-manufacturing-info OBJECT-TYPE
   SYNTAX      OCTET STRING
   ACCESS      read-only
   STATUS      optional
   DESCRIPTION "Returns information describing the manufacture of the I/O card		
                installed in MIO/EIO slot 1. May include serial number and		
                firmware revision.
                Additional information:
                The format of the string returned is determined by
                the manufacturer of the EIO device. There is no standard for 
                content of the string."
::= { mio1 3 }
               
               
mio1-type OBJECT-TYPE
   SYNTAX      INTEGER {
		   eEmpty(1),
		   eUnknown(2),
		   eDiskDrive(8),
		   eIOCard(12)
		   }
   ACCESS      read-only
   STATUS      optional
   DESCRIPTION "Returns an indication of the type of option installed in		
                MIO/EIO slot 1. See SIMM1-TYPE for an explanation of the		
                enumerations."
::= { mio1 4 }
               
               
mio1-ip-address OBJECT-TYPE
   SYNTAX      OCTET STRING
   ACCESS      read-only
   STATUS      optional
   DESCRIPTION "This object will return the IP Address of the I/O cards present		
                in the available slots of a printer. Laserjet 4700 MFP supports 2 slots		
                and a Embedded Jet Direct Card. Slot 4 corresponds to the		
                Embedded Jet Direct Card. If there is no I/O card in a		
                particular slot, then a NULL value will be returned."
::= { mio1 6 }
               
               
mio4-model-name OBJECT-TYPE
   SYNTAX      OCTET STRING
   ACCESS      read-only
   STATUS      optional
   DESCRIPTION "Returns product information identifying the I/O card. Example:		
                XXXX.
                Additional information:
                Returns a string describing the firmware version of
                the embedded JDI LAN card."
::= { mio4 2 }
               
               
mio4-manufacturing-info OBJECT-TYPE
   SYNTAX      OCTET STRING
   ACCESS      read-only
   STATUS      optional
   DESCRIPTION "Returns information describing the manufacture of the I/O card		
                installed in MIO/EIO interface 4. May include serial number and		
                firmware revision.
                Additional information:
                Returns a string describing the embedded JDI LAN card."
::= { mio4 3 }
               
               
mio4-type OBJECT-TYPE
   SYNTAX      INTEGER {
		   eEmpty(1),
		   eIOCard(12)
		   }
   ACCESS      read-only
   STATUS      optional
   DESCRIPTION "Returns an indication of the type of option installed in		
                MIO/EIO interface 4. See SIMM1-TYPE for an explanation of the		
                enumerations.
                Additional information:
                Returns eEmpty if the embedded JDI LAN
                card is disabled.  Returns eIOCard if the embedded
                JDI LAN card is enabled."
::= { mio4 4 }
               
               
mio4-ip-address OBJECT-TYPE
   SYNTAX      OCTET STRING
   ACCESS      read-only
   STATUS      optional
   DESCRIPTION "This object will return the IP Address of the I/O cards present		
                in the available slots of a printer. Laserjet 4700 MFP supports 2 slots		
                and a Embedded Jet Direct Card. Slot 4 corresponds to the		
                Embedded Jet Direct Card. If there is no I/O card in a		
                particular slot, then a NULL value will be returned."
::= { mio4 6 }
               
               
usb-host-supported OBJECT-TYPE
   SYNTAX      INTEGER {
		   eFalse(1),
		   eTrue(2)
		   }
   ACCESS      read-only
   STATUS      optional
   DESCRIPTION "The USB Host protocol is supported by the device when the value		
                returned is eTrue. The USB Host protocol is not supported when		
                the value returned is eFalse."
::= { usb-interface 1 }
               
               
usb-serial-number OBJECT-TYPE
   SYNTAX      OCTET STRING
   ACCESS      read-only
   STATUS      optional
   DESCRIPTION "Returns the serial number of a connected USB device as defined		
                in the Standard Device Descriptor of the Universal Serial Bus		
                Specification Version 2.0."
::= { usb 1 }
               
               
usb-manufacturer-name OBJECT-TYPE
   SYNTAX      OCTET STRING
   ACCESS      read-only
   STATUS      optional
   DESCRIPTION "Returns the description of the manufacturer of a connected USB		
                device as defined in the Standard Device Descriptor of the		
                Universal Serial Bus Specification Version 2.0."
::= { usb 2 }
               
               
usb-product-description OBJECT-TYPE
   SYNTAX      OCTET STRING
   ACCESS      read-only
   STATUS      optional
   DESCRIPTION "Returns the product description of a connected USB device as		
                defined in the Standard Device Descriptor of the Universal		
                Serial Bus Specification Version 2.0."
::= { usb 3 }
               
               
usb-vendor-id OBJECT-TYPE
   SYNTAX      INTEGER
   ACCESS      read-only
   STATUS      optional
   DESCRIPTION "Returns the Vendor ID of a connected USB device as defined in		
                the Standard Device Descriptor of the Universal Serial Bus		
                Specification Version 2.0. The value will be in the range		
                0..65535."
::= { usb 4 }
               
               
usb-product-id OBJECT-TYPE
   SYNTAX      INTEGER
   ACCESS      read-only
   STATUS      optional
   DESCRIPTION "Returns the Product ID of a connected USB device as defined in		
                the Standard Device Descriptor of the Universal Serial Bus		
                Specification Version 2.0. The value will be in the range		
                0..65535."
::= { usb 5 }
               
               
usb-device-kind OBJECT-TYPE
   SYNTAX      INTEGER {
		   eUSBStorageDevice(1),
		   eUSBNonStorageDevice(2),
		   eUSBCompositeDevice(3),
		   eUSBUnsupportedDevice(4)
		   }
   ACCESS      read-only
   STATUS      optional
   DESCRIPTION "The USB-DEVICE-KIND object classifies a USB device into one of		
                four broad categories: \ 	
                    eUSBStorageDevice(1): The USB device is strictly a device		
                        for storing data. \ 	
                    eUSBNonStorageDevice(2): The USB device has no storage		
                        capability (e.g., a card reader). \ 	
                    eUSBCompositeDevice(3): The USB device has storage		
                        capability and additional functionality normally not		
                        associated with a storage device. \ 	
                eUSBUnsupportedDevice(4): The USB device was detected, but no		
                driver exists for the device or the device draws more current		
                than allowed. \"
::= { usb 6 }
               
               
usb-driver-name OBJECT-TYPE
   SYNTAX      OCTET STRING
   ACCESS      read-only
   STATUS      optional
   DESCRIPTION "Returns the name of the low-level USB driver supporting this		
                device."
::= { usb 7 }
               
               
io-timeout OBJECT-TYPE
   SYNTAX      INTEGER(5..300)
   ACCESS      read-write
   STATUS      optional
   DESCRIPTION "The amount of time, in seconds, to wait for more print job data		
                to be received before an I/O timeout occurs. The I/O channel		
                being timed is the I/O channel that received the data		
                associated with the current print job. If an I/O timeout		
                occurs, the PDL processing sub-system assumes all the data		
                associated with the current print job has been received, and		
                processes the end of job in a PDL specific manner. The POS		
                specifies the supported values.
                Additional information:
                If an I/O timeout occurs,the PDL processing
                sub-system will consider it an end of job condition only
                if there is data from another I/O subsystem waiting to be
                processed.    
                The supported values are 5 to 300 seconds. 
                Setting to a value outside the supported range returns 
                <noError> status and the
                value will be snapped to the nearest supported value."
::= { settings-io 1 }
               
               
io-switch OBJECT-TYPE
   SYNTAX      INTEGER {
		   eYes(1)
		   }
   ACCESS      read-only
   STATUS      optional
   DESCRIPTION "Indicates if the device will switch between I/O channels when a		
                job boundary is encountered and print job data is available on		
                another I/O channel."
::= { settings-io 2 }
               
               
port1-parallel-speed OBJECT-TYPE
   SYNTAX      INTEGER {
		   eSlow(1),
		   eFast(2)
		   }
   ACCESS      read-write
   STATUS      optional
   DESCRIPTION "Returns or changes the maximum parallel I/O port speed, for		
                port 1. This object is only supported if this port is a		
                parallel port. An eSlow setting causes a 10 us busy pulse per		
                received byte of data. An eFast setting causes a 1.5 us busy		
                pulse per received byte of data. In rare cases, setting this		
                value to eFast can cause the parallel port to no longer		
                transfer data reliably.
                Additional information:
                When the value of this object is changed, it takes 
                effect immediately. It is recommended that the printer
                be offline and not in a job when this object is changed."
::= { port1 4 }
               
               
port1-parallel-bidirectionality OBJECT-TYPE
   SYNTAX      INTEGER {
		   eUnidirectional(1),
		   eBidirectional(2)
		   }
   ACCESS      read-write
   STATUS      optional
   DESCRIPTION "Returns or changes whether the parallel I/O port supports		
                bidirectional communication for port 1. This object is only		
                supported if this port is a parallel port.
                Additional information:
                A get on this object returns the current mode 
                for the parallel port. Setting this object specifies whether 
                or not bidirectional communications will be allowed."
::= { port1 5 }
               
               
channelnumberofchannels OBJECT-TYPE
   SYNTAX      INTEGER
   ACCESS      write-only
   STATUS      optional
   DESCRIPTION "An indication of how many print data channels the I/O card		
                supports.
                Additional information:
                This object is used by the IIO card to tell the peripheral
                firmware how many logical channels will be used by the card.
                This object can only be set once per physical channel.  If
                an attempt is made to set it a subsequent time it is ignored
                and an return code of <ErrorActionCanNotBePerformedNow.is returned.  
                
                If new firmware is dynamically downloaded to the Blazers Plus
                card, and if that firmware uses more logical channels, it is
                necessary to reset the printer."
::= { channel 1 }
               
               
ChannelEntry   ::= SEQUENCE {
    channelindex             INTEGER,
    channeltype              INTEGER,
    channelprotocolversion   OCTET STRING,
    channelstate             INTEGER,
    channelifindex           INTEGER,
    channelstatus            INTEGER,
    channelinformation       OCTET STRING
}




DeviceChannelEntry   ::= SEQUENCE {
    channel-index              INTEGER,
    channel-bytes-sent         INTEGER,
    channel-bytes-received     INTEGER,
    channel-io-errors          INTEGER,
    channel-jobs-received      INTEGER,
    channel-mio                INTEGER
}

               
               
rpc-bind-protocol-address OBJECT-TYPE
   SYNTAX      OCTET STRING
   ACCESS      read-only
   STATUS      optional
   DESCRIPTION "Array of Berkeley sockets style protocol addresses used to bind		
                RPC to a communications protocol family. Setting an instance of		
                this array object to a zero length binary value disables the		
                transport protocol indicated by that instance. All multi-bytes		
                fields are in network (or big-endian) order. Bytes 1 and 2		
                indicate the transport protocol. Some of the transport protocol		
                mapping information can be found in RFC 1010 Assigned Numbers.		
                A list of interesting transport protocol number mappings		
                include:    	
                    <table>
                    Protocol | Number
                    ---------+-------
                     UDP/IP  |  17 
                      IPX    |  1000 
                      MLC    |  4660
                    </table>
                    Bytes 3 and 4 indicate the address family. The address		
                        family uses the same mapping as the BSD sockets address		
                        family. A list of interesting address family mappings		
                        include:    	
                    <table>
                    Address Family | Number
                    ---------------+-------
                        Internet   |   2
                        NetWare    |   6
                        MLC        | 22136 
                    </table>
                The format the fifth and following bytes is dependent on the		
                address family. For the Internet address family, bytes 5 and 6		
                contain the port number, bytes 7 through 10 contain the IP		
                address, and the following eight bytes are unused. For NetWare,		
                bytes 5 through 8 are the network number, bytes 9 through 14		
                are the node number, and bytes 15 and 16 are the socket		
                number.
                Additional information:
                The length of the binary value is zero
                if the instance of an object in the rpc-bind-protocol-address
                array is not in use.
                Returns <noSuchName>
                status if attempting to access this object and there
                is no storage device is installed."
::= { settings-rpc 2 }
               
               
rpc-bound-protocol-address OBJECT-TYPE
   SYNTAX      OCTET STRING
   ACCESS      read-only
   STATUS      optional
   DESCRIPTION "An array of Berkeley sockets style protocol addresses that the		
                NFS service has been bound to successful. The format is that		
                same as the array of RPC-BIND-PROTOCOL-ADDRESS of objects.
                Additional information:
                Returns <noSuchName>
                status if attempting to access this object and there
                is no storage device is installed."
::= { status-rpc 3 }
               
               
file-system-max-open-files OBJECT-TYPE
   SYNTAX      INTEGER
   ACCESS      read-only
   STATUS      optional
   DESCRIPTION "The number of open files allowed at one time. Opening a file		
                when the maximum number of files are currently open will fail.
                Additional information:
                Indicates the number of open files a
                personality (e.g. PCL or PostScript) is guaranteed to be
                able to open before the file system runs out of file handles.
                		   This object is between 1 and 500.
                Returns <noSuchName>
                status if attempting to access this object and there
                is no storage device is installed."
::= { settings-file-system 2 }
               
               
file-system-set-system-partition-writeable OBJECT-TYPE
   SYNTAX      OCTET STRING
   ACCESS      write-only
   STATUS      optional
   DESCRIPTION "This object allows the system partition to be written to. It		
                consists of a C structure containing the following fields:    	
                    typedef struct {    	
                    ubyte <<hidden>>[8];    	
                    ubyte volumenumber;    	
                    } fs_writeable_system_partition_t;    	
                    which is described below:    	
                    Bytes 0 - 7: contain the <<hidden>>    	
                    Byte 8 : is the volume number    	
                Access to this command is controlled by the <<hidden>>. If the		
                <<hidden>> supplied is incorrect the command will fail. The		
                volumenumber is a volume number of an existing system		
                partition.
                Additional information:
                Returns <noSuchName>
                status if attempting to access this object and there
                is no storage device is installed.
                Returns <badValue> if the <<hidden>> is incorrect or if
                		   the volume requested is not present."
::= { settings-file-system 6 }
               
               
file-system-set-system-partition-readonly OBJECT-TYPE
   SYNTAX      INTEGER
   ACCESS      write-only
   STATUS      optional
   DESCRIPTION "Changes a system partition to be READ-ONLY. The value is the		
                volume number to change. If the volume number specified is NOT		
                a system partition an error is returned.
                Additional information:
                Returns <noSuchName>
                status if attempting to access this object and there
                is no storage device is installed.
                Returns <badValue> if the volume requested
                		   is not present."
::= { settings-file-system 7 }
               
               
file-system-delete-files OBJECT-TYPE
   SYNTAX      OCTET STRING
   ACCESS      write-only
   STATUS      optional
   DESCRIPTION "Setting this object causes the specified filename to be		
                deleted, after first validating that the authentication data is		
                correct for the specified user ID.    	
                    The format for this object is a C structure:   	
                    typedef struct {    	
                    sint32 UserId;    	
                    uint16 AuthenticationDataLen    	
                    ubyte AuthenticationData[]    	
                    char Filename[];    	
                    } fs_delete_files_t;    	
                    which is described below:   	
                    Bytes 0 - 3: contains a user id represented as a multi-byte		
                        value that is stored in big-endian format, where the		
                        most significant byte occurs first.    	
                    Bytes 4 - 5 : Length of the Athentication data that follows		
                        starting at offset 6. Stored as a multi-byte value that		
                        is stored in big-endian format, where the most		
                        significant byte occurs first.    	
                    Bytes 6 - 6+AuthenticationDataLen : a ubyte array		
                        containing the Authentication data used to verify		
                        access for this operation.   	
                    Bytes starting at offset (6+AuthenticationDataLen+1): A		
                        null terminated character array representing the ASCII		
                        file name to be deleted. The length of the string will		
                        be limited by the remaining space in the object.    	
                This string represents a fully-qualified path name which may		
                specify a filename or a regular expression that may match		
                multiple files (e.g <path>/*.exe). Access to this command is		
                controlled by the UserId and the authentication data. If the		
                UserID or authentication data supplied is incorrect the command		
                will fail. The device POS will specify any limitations to the		
                length of the filename string, what constitutes a correct user		
                ID, what constitutes correct authentication data, and the		
                significance of any return values.
                Additional information:
                Setting this object causes the specified filename
                to be deleted, after first validating that the
                authentication data is correct for the specified
                user ID.  This object is always present.
                
                The format for this object is a C structure:
                
                typedef struct {        
                sint32 UserId;        
                uint16 AuthenticationDataLen 
                ubyte  AuthenticationData[]  
                char   Filename[];     
                } fs_delete_files_t;   
                
                Bytes 0 - 3: contains a user id represented
                as a multi-byte value that is stored in big-endian
                format, where the most significant byte occurs first.
                
                Bytes 4 - 5 : Length of the authentication data that
                follows starting at offset 6. Stored as a multi-byte
                value that is stored in big-endian format, where the
                most significant byte occurs first. 
                
                Bytes 6 - 6+AuthenticationDataLen : a ubyte array
                containing the authentication data used to verify
                access for this operation.
                
                Bytes starting at offset (6+AuthenticationDataLen+1):
                A null terminated character array representing the
                ASCII file name to be deleted. The length of the
                string will be limited by the remaining space in the
                object.  This string represents a fully-qualified path 
                name which may specify a filename or a file-type regular 
                expression that may match multiple files (e.g.,
                <path>/*.exe). 
                
                Access to this command is controlled by the UserId
                and the authentication data.  If the UserID or 
                authentication data supplied is incorrect the 
                command will fail.
                
                The device POS will specify any limitations to the
                length of the filename string, what constitutes a
                correct user ID, what constitutes correct
                authentication data, and the significance of any
                return values."
::= { settings-file-system 8 }
               
               
file-system-external-access-capabilities OBJECT-TYPE
   SYNTAX      OCTET STRING
   ACCESS      read-write
   STATUS      optional
   DESCRIPTION "This object is used to control access to the file system of the		
                device. It is always readable. It is writable when		
                <<hidden>> is not the empty string,		
                and a successful write to that object with the current <<hidden>>		
                has preceded the write to this object. In other words, the		
                <<hidden>> must be in the		
                'authenticated state' for a write on		
                FILE-SYSTEM-EXTERNAL-ACCESS-CAPABILITIES to succeed. After the		
                object has successfully been written to, it becomes read-only,		
                and the <<hidden>> object exits the		
                authenticated state. <<hidden>> must		
                then be written to again with the current <<hidden>> in order to		
                make another write operation on		
                FILE-SYSTEM-EXTERNAL-ACCESS-CAPABILITIES possible.    	
                    cDisablePJLFileSystemAccess - All file system access		
                        through PJL will be disabled.    	
                    cDisablePMLFileSystemWrite - All file-systems-related PML		
                        objects such as FILE-SYSTEM-DELETE-FILES or		
                        hrPartitionLabel become read-only. For objects that are		
                        normally write-only this means that no successful		
                        operations can now be performed on them.    	
                    cDisableNFSFileSystemAccess - All NFS file system access		
                        will be disabled.    	
                    cDisablePSFileSystemAccess - All file system access through		
                        PostScript will be disabled.    	
                    cDisableEWSFileSystemAccess - All access to the file system		
                        by the Embedded Web Server will be disabled.   "
::= { settings-file-system 10 }
               
               
file-system-erase-mode OBJECT-TYPE
   SYNTAX      OCTET STRING
   ACCESS      read-write
   STATUS      optional
   DESCRIPTION "This object is used to control how file data is handled when		
                files are deleted. It is always readable. It is writable when		
                <<hidden>> is the empty string or		
                when a write to <<hidden>> with the		
                current <<hidden>> has preceeded the write to the object. When		
                <<hidden>> is not the empty string		
                then this object becomes read-only after a successful write to		
                it. <<hidden>> must then be written		
                to again with the current <<hidden>> in order to make another		
                write operation on the object possible. If the		
                <<hidden>> is incorrectly set, this		
                object becomes read-only until the <<hidden>> is correctly set.		
                The logical settings for this object are:    	
                    NonSecureFastErase - When a file is deleted, only the		
                        reference to it in the file system tables is removed.		
                        No file data is overwritten. This is the default		
                        setting. This is the setting when both bits in the		
                        collection are set to 0.   	
                    SecureFastErase - File information is overwritten with		
                        identical, random character pattern when it is deleted.		
                        This is the setting when cEraseMode0 is set to 1 and		
                        cEraseMode1 is set to 0.   	
                    SecureSanitizeErase - Secure, repetitive algorithm used to		
                        overwrite all deleted file information and remove any		
                        residual data persistence. A random character is		
                        written to all bytes of deleted sectors. Then the		
                        complement of that character and finally, another		
                        random character is written. This is the setting when		
                        cEraseMode0 is set to 0 and cEraseMode1 is set to 1.   	
                Note that an error will be returned for an attempt to set both		
                bits of the collection to 1.
                Additional information:
                This object is used to control how file data is handled when
                files are deleted. It is always readable. It is writable when
                <<hidden>> is the empty string or
                when a write to <<hidden>> with the
                current <<hidden>> has preceeded the write to the object. When
                <<hidden>> is not the empty string
                then this object becomes read-only after a successful write to
                it. <<hidden>> must then be written
                to again with the current <<hidden>> in order to make another
                write operation on the object possible. If the
                <<hidden>> is incorrectly set, this
                object becomes read-only until the <<hidden>> is correctly set.
                The logical settings for this object are:   
                NonSecureFastErase - When a file is deleted, only the
                reference to it in the file system tables is removed.
                No file data is overwritten. This is the default
                setting. This is the setting when all the bits in the
                collection are set to 0.  
                SecureFastErase - File information is overwritten with
                identical, random character pattern when it is deleted.
                This is the setting when cEraseMode0 is set to 1 and
                cEraseMode1 is set to 0. Also cEraseMode2 set to 0  
                SecureSanitizeErase - Secure, repetitive algorithm used to
                overwrite all deleted file information and remove any
                residual data persistence. A random character is
                written to all bytes of deleted sectors. Then the
                complement of that character and finally, another
                random character is written. This is the setting when
                cEraseMode0 is set to 0 and cEraseMode1 is set to 1.
                cEraseMode2 is set to 0  
                SevenPass -Erase with 7 different patterns.(Dod 5220.22-M specification.)
                This is the setting when
                cEraseMode0 is set to 1 and cEraseMode1 is set to 1.
                cEraseMode2 is set to 0  
                
                ThirtFivePass -Erase with 35 passes. (Gutmann algorithm)
                This is the setting when
                cEraseMode0 is set to 0 and cEraseMode1 is set to 0.
                cEraseMode2 is set to 1  
                Note that an error will be returned for an attempt to set both
                bits of the collection to 1."
::= { settings-file-system 11 }
               
               
file-system-wipe-disk OBJECT-TYPE
   SYNTAX      INTEGER
   ACCESS      read-write
   STATUS      optional
   DESCRIPTION "This object is a non-leaf node which will have one leaf node		
                under it for each file system in the printer. The leaf nodes		
                will be in a 1-to-1 correspondence with the hrDeviceIndex		
                objects. This object specifies for each leaf node whether the		
                file system on the device is going to be erased according to		
                the setting of the FILE-SYSTEM-ERASE-MODE referenced by the		
                corresponding hrDeviceIndex. A file system will be overwritten		
                on system reboot if this object is set to 1. It will be		
                unchanged if this object is set to 0. If this object's value is		
                -1 then the file system cannot be wiped. If the file system		
                contains the permstore, the permstore will be saved off and		
                restored after the file-system wipe is completed. This object		
                is always readable. It is writable when		
                <<hidden>> is the empty string or		
                when a write to <<hidden>> with the		
                current <<hidden>> has preceeded the write to the object. When		
                <<hidden>> is not the empty string		
                then this object becomes read-only after a successful write to		
                it. <<hidden>> must then be written		
                to again with the current <<hidden>> in order to make another		
                write operation on the object possible. If the		
                <<hidden>> is incorrectly set, this		
                object becomes read-only until the <<hidden>> is correctly set.
                Additional information:
                This object is a non-leaf node which will have one leaf node
                under it for each file system in the printer. The leaf nodes
                will be in a 1-to-1 correspondence with the hrDeviceIndex
                objects. This object specifies for each leaf node whether the
                file system on the device is going to be erased according to
                the setting of the FILE-SYSTEM-ERASE-MODE referenced by the
                corresponding hrDeviceIndex. A file system will be overwritten
                on system reboot if this object is set to 1. It will be
                unchanged if this object is set to 0. If this object's value is
                -1 then the file system cannot be wiped. If the file system
                contains the permstore, the permstore will be saved off and
                restored after the file-system wipe is completed. This object
                is always readable. It is writable when
                <<hidden>> is the empty string or
                when a write to <<hidden>> with the
                current <<hidden>> has preceeded the write to the object. When
                <<hidden>> is not the empty string
                then this object becomes read-only after a successful write to
                it. <<hidden>> must then be written
                to again with the current <<hidden>> in order to make another
                write operation on the object possible. If the
                <<hidden>> is incorrectly set, this
                object becomes read-only until the <<hidden>> is correctly set.
                This object can also be used to set the following erase modes
                Erase mode can be set to any of the modes using this object irrespective 
                of the FILE-SYSTEM-ERASE-MODE .In this no need to use FILE-SYSTEM-ERASE-MODE 
                to set the erase mode.
                SecureSanitizeErase - Secure, repetitive algorithm used to
                overwrite all deleted file information and remove any
                residual data persistence. A random character is
                written to all bytes of deleted sectors. Then the
                complement of that character and finally, another
                random character is written.The value to set this mode is 2.
                SevenPass -Erase with 7 different patterns.(Dod 5220.22-M specification.)
                The value used for this is 3.
                ThirtFivePass -Erase with 35 passes. (Gutmann algorithm)
                The value used to set this is 4."
::= { settings-file-system 12 }
               
               
file-system-wipe-disk-status OBJECT-TYPE
   SYNTAX      INTEGER
   ACCESS      read-only
   STATUS      optional
   DESCRIPTION "This object is a non-leaf node which will have one leaf node		
                under it for each file system in the printer. The leaf nodes		
                will be in a 1-to-1 correspondence with the hrDeviceIndex		
                objects. This object specifies for each leaf node the status of		
                a disk wipe in progress. A return value of -1 indicates that no		
                disk wipe is in progress. A return value in the range of 0 to		
                100 indicates the percent done for a disk wipe in progress. All		
                other values are illegal."
::= { settings-file-system 13 }
               
               
file-system2-initialize-volume OBJECT-TYPE
   SYNTAX      INTEGER {
		   eInitializing(2)
		   }
   ACCESS      write-only
   STATUS      optional
   DESCRIPTION "Setting this object to eInitializing causes file system 2 to be		
                initialized. Reading this object indicates if the file system		
                is currently being initialized.
                Additional information:
                The hrDeviceIndex value for the mass storage
                device is the same value that is used to index into the
                FILE-SYSTEM sub-tree.  Since this product supports
                up to 3 physical mass storage device, and since the hrDeviceIndex
                for the mass storage devices will start at 2 if the mass
                	       storage device is installed, the FILE-SYSTEM2-INITIALIZE-VOLUME
                	       object will be the object that allows the mass storage device to be 
                initialized that is the 1st device."
::= { file-system2 6 }
               
               
file-system3-initialize-volume OBJECT-TYPE
   SYNTAX      INTEGER {
		   eInitializing(2)
		   }
   ACCESS      write-only
   STATUS      optional
   DESCRIPTION "Setting this object to eInitializing causes file system 3 to be		
                initialized. Reading this object indicates if the file system		
                is currently being initialized.
                Additional information:
                The hrDeviceIndex value for the mass storage
                device is the same value that is used to index into the
                FILE-SYSTEM sub-tree.  Since this product supports
                up to 3 physical mass storage device, and since the hrDeviceIndex
                for the mass storage devices will start at 2 if the mass
                	       storage device is installed, the FILE-SYSTEM3-INITIALIZE-VOLUME
                	       object will be the object that allows the mass storage device to be 
                initialized that is the 2nd device."
::= { file-system3 6 }
               
               
file-system4-initialize-volume OBJECT-TYPE
   SYNTAX      INTEGER {
		   eInitializing(2)
		   }
   ACCESS      write-only
   STATUS      optional
   DESCRIPTION "Setting this object to eInitializing causes file system 4 to be		
                initialized. Reading this object indicates if the file system		
                is currently being initialized.
                Additional information:
                The hrDeviceIndex value for the mass storage
                device is the same value that is used to index into the
                FILE-SYSTEM sub-tree.  Since this product supports
                up to 3 physical mass storage devices, and since the hrDeviceIndex
                for the mass storage devices will start at 2 if the mass
                	       storage device is installed, the FILE-SYSTEM4-INITIALIZE-VOLUME
                	       object will be the object that allows the mass storage device to be 
                initialized that is the 3rd device."
::= { file-system4 6 }
               
               
mass-storage-resource-change-counter OBJECT-TYPE
   SYNTAX      INTEGER
   ACCESS      read-only
   STATUS      optional
   DESCRIPTION "A counter which changes when a mass storage based resource has		
                been added or deleted.
                Additional information:
                The value of this counter changes 
                each time the MASS-STORAGE-RESOURCE-CHANGED object
                is set to eTrue.  The value also changes when the 
                mass storage device is initialized.  However, the value does not
                change when a mass storage device is removed and a different
                mass storage device is installed.  Initializing all volumes sets 
                this object back to the factory default value.  A reboot sets
                	   this object back to the factory devalut value.
                Returns <noSuchName>
                status if attempting to access this object and there
                is no storage device is installed."
::= { mass-storage-resources 1 }
               
               
mass-storage-resource-changed OBJECT-TYPE
   SYNTAX      INTEGER {
		   eTrue(2)
		   }
   ACCESS      write-only
   STATUS      optional
   DESCRIPTION "Setting to eTrue causes MASS-STORAGE-RESOURCE-CHANGE-COUNTER to		
                be incremented.
                Additional information:
                Returns <noSuchName>
                status if attempting to access this object and there
                is no storage device is installed."
::= { mass-storage-resources 2 }
               
               
ram-disk-mode OBJECT-TYPE
   SYNTAX      INTEGER {
		   eOff(1),
		   eAuto(3)
		   }
   ACCESS      read-write
   STATUS      optional
   DESCRIPTION "Returns or controls RAM disk support. eOFF turns off the RAM		
                disk functionality. eOn turns on the RAM disk functionality and		
                creates a RAM disk whose size is controlled by the		
                RAM-DISK-SIZE object. eAuto turns on the RAM disk functionality		
                and creates a RAM disk size determined by the printer based on		
                installed options and other memory related settings.
                Additional information:
                Returns or controls RAM disk support.  eOFF turns off
                the RAM disk functionality. eAuto turns on
                the RAM disk functionality and creates a RAM disk size
                determined by the printer based on the amount of installed
                memory."
::= { settings-mass-storage-bd 1 }
               
               
ram-disk-size OBJECT-TYPE
   SYNTAX      INTEGER
   ACCESS      read-only
   STATUS      optional
   DESCRIPTION "Returns or controls the size of the RAM disk. The device POS		
                specifies the minimum memory requirements. The object		
                MAXIMUM-RAM-DISK-MEMORY specifies the maximum memory available		
                for the RAM disk.
                Additional information:
                Returns the size of the RAM disk."
::= { settings-mass-storage-bd 2 }
               
               
maximum-ram-disk-memory OBJECT-TYPE
   SYNTAX      INTEGER
   ACCESS      read-only
   STATUS      optional
   DESCRIPTION "This object's name is misleading. This object does not return		
                the maximum configurable RAM disk size. Instead, it returns the		
                maximum amount of memory, in bytes, that can used to increase		
                the size of the RAM disk.
                Additional information:
                This object returns the maximum amount of additional 
                memory that is available for increasing the size of the RAM 
                disk."
::= { status-mass-storage-bd 1 }
               
               
mono-color-switching-mode OBJECT-TYPE
   SYNTAX      INTEGER {
		   eAutoSwitch(1),
		   eMostlyColor(2),
		   eMostlyMono(3)
		   }
   ACCESS      read-write
   STATUS      optional
   DESCRIPTION "This object allows the user to view/change the color/mono		
                switching mode for a device.
                Additional information:
                This object allows the user to view/change the
                color/mono switching mode for a device.  The behavior of 
                each setting may vary depending on the device. The value will
                be stored in NVRAM"
::= { settings-system 31 }
               
               
device-configure-printer-parameters OBJECT-TYPE
   SYNTAX      OCTET STRING (SIZE(1..256))
   ACCESS      read-write
   STATUS      optional
   DESCRIPTION "Allow the printer to be configured as a duplex or simplex		
                printer. There will be a <<hidden>> encoded in this string and		
                decoded by the printer firmware. If the <<hidden>> check passes		
                the printer will be configured accordingly.
                Additional information:
                Used to configure engines for duplex enabled or not.
                Encoded configuration string is passed in, which is decoded
                by firmware.  Firmware verifies config. string is valid, and
                retrieves device Configuration data.
                Expandable to accommodate future products configuration needs."
::= { device-configure 12 }
               
               
speed-energy-usage OBJECT-TYPE
   SYNTAX      INTEGER {
		   eFasterFirstPage(1),
		   eSaveEnergy(2)
		   }
   ACCESS      read-write
   STATUS      optional
   DESCRIPTION "Option to keep the fuser in a pre-warmed state to speed up		
                first page out.
                Additional information:
                Option to keep the fuser in a pre-warmed state to speed up
                
                first page out."
::= { settings-system 50 }
               
               
job-input-auto-continue-timeout OBJECT-TYPE
   SYNTAX      INTEGER(-1..3600)
   ACCESS      read-write
   STATUS      optional
   DESCRIPTION "The number of seconds the device waits after a job related		
                continuable error occurs before automatically continuing. An		
                example job related continuable error is the job requesting a		
                media size that is not available. After the timeout expires,		
                the device will continue processing the job as if a continue		
                event occurred, such as the front panel continue key being		
                pressed. If the value is -1, the device does not automatically		
                continue after a job related continuable error occurs. If the		
                value is 0, the device immediately continues. If the value is		
                greater than 0, the value represents the timeout value in		
                seconds.
                Additional information:
                The number of seconds the device waits after a job
                related continuable error occurs before automatically
                continuing.  An example job related continuable error is
                the job requesting a media size that is not available.
                After the timeout expires, the device will continue
                processing the job accourding to the action defined by
                JOB-INPUT-AUTO-CONTINUE-MODE. 
                If the value is -1, the device does not automatically continue
                after a job related continuable error occurs.  If the
                value is 0, the device immediately continues.  If the
                value is greater than 0, the value represents the
                timeout value in seconds.
                The data for this object is stored in NVRAM."
::= { status-system 35 }
               
               
job-input-auto-continue-mode OBJECT-TYPE
   SYNTAX      OCTET STRING
   ACCESS      read-write
   STATUS      optional
   DESCRIPTION "Returns or sets the device behavior when the desired media is		
                not currently available.    	
                    cCancelJob - The device cancels the job. The device POS		
                        should explain what happens if this item is not the		
                        only item in the collection.    	
                    cAutoMediaSizeOverride - The device is allowed to		
                        substitute a different size media.    	
                    cAutoMediaNameOverride - The device is allowed to		
                        substitute a different media name.    	
                    cUSMediaSizeOverride - The device is allowed to substitute		
                        US media sizes (letter, etc.) for ISO media sizes (A4,		
                        etc.).    	
                    cISOMediaSizeOverride - The device is allowed to substitute		
                        ISO media sizes (A4, etc.) for US media sizes (letter,		
                        etc.).   
                Additional information:
                Returns or sets the device behavior when the desired
                media is not currently available.
                cCancelJob - The device cancels the job regardless of other
                item settings.  
                cAutoMediaSizeOverride - The device is allowed to substitute 
                a different size media.
                cAutoMediaNameOverride - The device is allowed to substitute 
                a different media name.
                --                 cUSMediaSizeOverride - The device is allowed to substitute
                --                              US media sizes (letter, etc.) for ISO media sizes
                --                              (A4, etc.).
                --                 cISOMediaSizeOverride - The device is allowed to substitute
                --                              ISO media sizes (A4, etc.) for US media sizes
                --                              (letter, etc.).
                At least one bit of the collection must be set; setting
                this object to zero will cause a status of
                <badValue> to be returned.
                This object describes the action that is performed when the
                JOB-INPUT-AUTO-CONTINUE-TIMEOUT expires. "
::= { status-system 36 }
               
               
job-output-auto-continue-timeout OBJECT-TYPE
   SYNTAX      INTEGER(-1..3600)
   ACCESS      read-write
   STATUS      optional
   DESCRIPTION "Returns or sets the time that the printer will wait after an		
                output bin becomes full and the printer is trying to deliver a		
                sheet of media to that output bin. When the timeout expires,		
                the job is processed according to the OUTBINn-OVERRIDE-MODE. A		
                value of -1 indicates that the printer will wait for a continue		
                event. A non-negative value is the number of seconds to wait.
                Additional information:
                Returns or sets the time that the printer will wait
                after an output bin becomes full and the printer is
                trying to deliver a sheet of media to that output bin.
                When the timeout expires, the job is processed according
                to the OUTBINn-OVERRIDE-MODE.  A value of -1 indicates
                that the printer will wait for a continue event.  A non-
                negative value is the number of seconds to wait."
::= { status-system 40 }
               
               
dfa-data-in-nvram OBJECT-TYPE
   SYNTAX      INTEGER(0..65535)
   ACCESS      read-write
   STATUS      optional
   DESCRIPTION "This object will act as a Read/Write area for HP print		
                application to facilitate the new Design for Attach Data and		
                Product Warranty Extension efforts. This object will access a		
                special area of protected NVRAM. The value will be in the range		
                0..65535.
                Additional information:
                This object will act as a Read/Write area for HP print
                application to facilitate the new Design for Attach Data and
                Product Warranty Extension efforts. This object will access a
                special area of protected NVRAM. The value will be in the range
                0..65535."
::= { status-system 116 }
               
               
model-number OBJECT-TYPE
   SYNTAX      OCTET STRING
   ACCESS      read-only
   STATUS      optional
   DESCRIPTION "Identifies the device model number as listed in the HP		
                corporate price list (e.g. C2121A for DeskJet 500C). The string		
                is as specific as possible. Products should note in POS if the		
                model number on the CPL changes but the device reports the		
                previous model number. If the model number changes based on the		
                installed options, the POS should indicate if only the base		
                model number is returned, or if the device senses the installed		
                options and returns the correct model number. If possible,		
                encode the model number in a symbol set (like Roman-8) that		
                matches the ASCII character set and limit the characters used		
                to ASCII characters.
                Additional information:
                Identifies the device model number as listed in the HP
                corporate price list (e.g.  C2121A for DeskJet 500C).
                The string is as specific as possible.
                The value of this object does not change based on 
                the installed options. The default of this object is the
                same on all $product_str printers."
::= { id 1 }
               
               
model-name OBJECT-TYPE
   SYNTAX      OCTET STRING (SIZE(1..32))
   ACCESS      read-only
   STATUS      optional
   DESCRIPTION "Identifies the device model name (e.g. ''DeskJet 1200C''). The		
                string is as specific as possible. Capitalization and spacing		
                should match family naming conventions. Products should note in		
                POS if the model name on the HP corporate price list changes		
                but the device reports the previous device name. If the model		
                name changes based on the installed options, the POS should		
                indicate if only the base model name is returned, or if the		
                device senses the installed options and returns the correct		
                model name. If possible, encode the model name in a symbol set		
                (like Roman-8) that matches the ASCII character set and limit		
                the characters used to ASCII characters.
                Additional information:
                Since the value of this object is frequently used in 
                displaying a list of printers, it is kept relatively short in
                case systems have limited width for their display area. The
                model name does not change based on sensing of installed options."
::= { id 2 }
               
               
formatter-serial-number OBJECT-TYPE
   SYNTAX      OCTET STRING
   ACCESS      read-only
   STATUS      optional
   DESCRIPTION "This object returns the formatter serial number for the device.		
                The value returned from this object is the FORMATTERNUMBER		
                system variable. If possible, encode the serial number in a		
                symbol set (like Roman-8) that matches the ASCII character set		
                and limit the characters used to ASCII characters.
                Additional information:
                Returns the formatter serial number, prefixed with
                the PML_UNICODE_PREFIX.."
::= { id 20 }
               
               
phd1-diagnostics-nvram-data OBJECT-TYPE
   SYNTAX      OCTET STRING
   ACCESS      read-only
   STATUS      optional
   DESCRIPTION "The NVRAM Diagnostics information consist of e-serial number,		
                born-on date, manufacturing date, page counter, finisher		
                counter, jam rate history, event log, and any other		
                device-specific information that the PHD1 stores in NVRAM. This		
                information will be returned as a string with XML format within		
                XML tags.
                Additional information:
                The NVRAM Diagnostics information consist of e-serial number,
                born-on date, manufacturing date, page counter, finisher
                counter, jam rate history, event log, and any other
                device-specific information that the PHD1 stores in NVRAM. This
                information will be returned as a string with XML format within
                XML tags."
::= { phd1 9 }
               
               
phd2-model OBJECT-TYPE
   SYNTAX      OCTET STRING
   ACCESS      read-only
   STATUS      optional
   DESCRIPTION "Returns product information identifying PHD device 2. Example:		
                XXXX.
                Additional information:
                Returns product information identifying the first paper 
                handling device in the device chaing, PHD device 2.
                If PDH device 2 does not exist, ERROR-UNKNOWN-OBJECT-IDENTIFIER
                will be returned."
::= { phd2 1 }
               
               
phd2-manufacturing-info OBJECT-TYPE
   SYNTAX      OCTET STRING
   ACCESS      read-only
   STATUS      optional
   DESCRIPTION "Returns information describing the manufacture of PHD 2. May		
                include serial number and firmware revision.
                Additional information:
                Returns information describing the manufacture of PHD 2.
                If PHD 2 does not exist, ERROR-UNKNOWN-OBJECT-IDENTIFIER
                will be returned."
::= { phd2 2 }
               
               
phd2-type OBJECT-TYPE
   SYNTAX      INTEGER {
		   eUnknown(2),
		   eInputPHD(10),
		   eOutputPHD(11),
		   eBindingPHD(13)
		   }
   ACCESS      read-only
   STATUS      optional
   DESCRIPTION "Returns an indication of the type of option installed in PHD		
                interface 2. See SIMM1-TYPE for an explanation of the		
                enumerations.
                Additional information:
                Returns an indication of the type of option installed in
                PHD interface 2.
                If PHD 2 does not exist, ERROR-UNKNOWN-OBJECT-IDENTIFIER
                will be returned."
::= { phd2 3 }
               
               
phd2-capacity OBJECT-TYPE
   SYNTAX      INTEGER
   ACCESS      read-only
   STATUS      optional
   DESCRIPTION "Returns an indication of the capacity of the installed option.		
                See SIMM1-CAPACITY for an explanation of the meaning of the		
                value of this object.
                Additional information:
                Returns an indication of the capacity of the installed
                option.  For eInputPHD or eOutputPHD, or eBindingPHD the number
                of input trays or output bins is returned.
                If PHD 2 does not exist, ERROR-UNKNOWN-OBJECT-IDENTIFIER
                will be returned."
::= { phd2 4 }
               
               
engine-self-diagnostic OBJECT-TYPE
   SYNTAX      OCTET STRING
   ACCESS      read-only
   STATUS      optional
   DESCRIPTION "The ENGINE-SELF-DIAGNOSTIC object reveals current engine		
                failures; it returns a binary string of two-byte motor, clutch,		
                solenoid, and sensor failure codes.
                Additional information:
                The ENGINE-SELF-DIAGNOSTIC object reveals current
                Engine Failures; it returns a BINARY string of two-byte
                Motor, Clutch, Solenoid and Sensor failure codes."
::= { test 7 }
               
               
engine-parameter OBJECT-TYPE
   SYNTAX      OCTET STRING
   ACCESS      read-only
   STATUS      optional
   DESCRIPTION "The ENGINE-PARAMETER object returns a device specific set of		
                engine parameters as a binary string of byte values. It will be		
                necessary to have a decoder for each engine to interpret the		
                data.
                Additional information:
                The ENGINE-PARAMETER object returns a device specific
                set of engine parameters as a BINARY string of byte
                values. It will be necessary to have a decoder for each
                engine to interpret the data."
::= { test 8 }
               
               
default-media-name OBJECT-TYPE
   SYNTAX      OCTET STRING
   ACCESS      read-write
   STATUS      optional
   DESCRIPTION "Returns or sets the media name that is used until the media		
                name is changed by a print job command.
                Additional information:
                Returns or sets the media name that is used until the
                media name is changed by a print job command.
                This string must be one of the MEDIAn-NAME 
                objects. 
                This object is localized if the corresponding MEDIAn-NAME 
                object is localized.
                The data for this object is stored in NVRAM."
::= { settings-pdl 22 }
               
               
override-media-name OBJECT-TYPE
   SYNTAX      OCTET STRING
   ACCESS      read-write
   STATUS      optional
   DESCRIPTION "Sets a string identifying the media name that is to be used in		
                place of the currently requested media. The substitution will		
                continue until another media is selected. If set to a named		
                media that is not currently available the requested media is		
                not overridden.
                Additional information:
                When a request is received to print on a size and
                type of media that is not currently available, this
                object contains the desired media name as set by the
                print job. This object should be set to a media name
                that is currently available in the printer.  If a
                paper mount request is not pending, attempting to get
                or set this object will cause
                <noSuchName> to be returned.
                Setting this object to a string other than one of the
                MEDIAn-NAME objects (MEDIA-NAMES-AVAILABLE is applied)
                will cause a status of <badValue>
                to be returned."
::= { settings-prt-eng 2 }
               
               
override-media-size OBJECT-TYPE
   SYNTAX      INTEGER {
		   eUSExecutive(1),
		   eUSLetter(2),
		   eUSLegal(3),
		   eFoolscap(10),
		   eLedger(11),
		   eStatement(15),
		   eROC16K(17),
		   eJISExecutive(18),
		   eROC8K(19),
		   eISOandJISA6(24),
		   eISOandJISA5(25),
		   eISOandJISA4(26),
		   eISOandJISA3(27),
		   ePRC8K270X390(33),
		   ePRC16K195X270(34),
		   ePRC8K260X368(35),
		   eISOSRA3(38),
		   eISORA3(39),
		   eJISB6(44),
		   eJISB5(45),
		   eJISB4(46),
		   eISOB6(64),
		   eJapanesePostcardDouble(72),
		   eIndexCard4x6(74),
		   eIndexCard5x8(75),
		   eMonarch(80),
		   eCommercial10(81),
		   ePRC16K184X260(89),
		   eInternationalDL(90),
		   eInternationalC5(91),
		   eInternationalC6(92),
		   eInternationalB5(100),
		   eEnvelope9(102),
		   eTabloidExtra(120),
		   eCustom(101),
		   eUSLetterR(258),
		   eISOandJISA4R(282),
		   eUnknownMediaSize(32767)
		   }
   ACCESS      read-write
   STATUS      optional
   DESCRIPTION "Sets the media size that is to be used in place of the		
                currently requested media size.
                Additional information:
                When a request is received to print on a size and
                type of media that is not currently available, this object
                contains the desired size as set by the print job. This object
                should be set to a media size that is currently available to the
                printer. If a paper mount request is not pending, attempting to
                get or set this object will cause <noSuchName>
                to be returned."
::= { settings-prt-eng 3 }
               
               
marking-agent-highlights-density-setting OBJECT-TYPE
   SYNTAX      INTEGER
   ACCESS      read-write
   STATUS      optional
   DESCRIPTION "Returns or sets the marking agent highlights density setting		
                for each of the marking agents installed. The value of this		
                object is in the range of -5..+5. The Marking Agent (aka Print)		
                density is the instantaneous amount of marking agent applied to		
                the media while printing. A value of -5 has the lowest print		
                density, yeilding a lighter pageA value of +5 the highest print		
                density, yielding a darker page.
                Additional information:
                Returns or sets the marking agent highlights density setting for each 
                of the marking agents installed. The value of this object is in the 
                range of -5..+5. The Marking Agent (aka Print) density is the instantaneous 
                amount of marking agent applied to the media while printing. A value of -5 
                has the lowest print density, yielding a lighter page. A value of +5 has the 
                highest print density, yielding a darker page."
::= { marking-agent-density 2 }
               
               
marking-agent-midtones-density-setting OBJECT-TYPE
   SYNTAX      INTEGER
   ACCESS      read-write
   STATUS      optional
   DESCRIPTION "Returns or sets the marking agent midtones density setting for		
                each of the marking agents installed. The value of this object		
                is in the range of -5..+5. See		
                MARKING-AGENT-HIGHLIGHTS-DENSITY-SETTING for a more specific		
                description.
                Additional information:
                Returns or sets the marking agent midtones density setting for each 
                of the marking agents installed. The value of this object is in the 
                range of -5..+5. See MARKING-AGENT-HIGHLIGHTS-DENSITY-SETTING 
                for a more specific description."
::= { marking-agent-density 3 }
               
               
marking-agent-shadows-density-setting OBJECT-TYPE
   SYNTAX      INTEGER
   ACCESS      read-write
   STATUS      optional
   DESCRIPTION "Returns or sets the marking agent shadows density setting for		
                each of the marking agents installed. The value of this object		
                is in the range of -5..+5. See		
                MARKING-AGENT-HIGHLIGHTS-DENSITY-SETTING for a more specific		
                description.
                Additional information:
                Returns or sets the marking agent shadows density setting for each 
                of the marking agents installed. The value of this object is in the 
                range of -5..+5. See MARKING-AGENT-HIGHLIGHTS-DENSITY-SETTING 
                for a more specific description."
::= { marking-agent-density 4 }
               
               
finisher-image-rotation OBJECT-TYPE
   SYNTAX      OCTET STRING
   ACCESS      read-write
   STATUS      optional
   DESCRIPTION "This PML object will provide the additional image rotation that		
                is applied to a printed job depending on the presence or		
                absence of a finisher device or the value of the		
                SVM_ALWAYS_MATCH_OUTPUT_ORIENTATION variable.
                Additional information:
                This PML object will provide the additional image
                rotation that is applied to a printed job depending
                on the presence or absence of a finisher device 
                and/or the state of the IMAGE ROTATION menu element."
::= { settings-prt-eng 31 }
               
               
itb-tensioning-status OBJECT-TYPE
   SYNTAX      INTEGER {
		   eITBDetensioned(1),
		   eITBTensioned(2),
		   eITBUnknownTensioning(3)
		   }
   ACCESS      read-only
   STATUS      optional
   DESCRIPTION "This object is uses to determine the Current status of the ITB.		
                It will either be De-Tensioned or Tenstioned and it will return		
                an enumeration accordingly. If the state can not be determined		
                at this point it will return UnknownTensioning.
                Additional information:
                This object is used to determine the current status of the
                ITB.  It will either be De-Tensioned or Tensione and it will
                return the proper enumeration accordingly.  If the state can
                not be determined at this point it will return UnknownTenstioning"
::= { settings-prt-eng 34 }
               
               
media-sensor-calibration OBJECT-TYPE
   SYNTAX      INTEGER {
		   eStartMediaSensorCalibration(3)
		   }
   ACCESS      write-only
   STATUS      optional
   DESCRIPTION "This object is used to start the media sensor calibration. If		
                you do a get on this object it will simply return the media		
                sensor state. If you set this object to the value 3 then it		
                will start a media sensor calibration.
                Additional information:
                This object is useded to start the media sensor calibration.  
                If you set this object to the value 3 then it will set the
                proper NVRAM bytes in the engine to zero thus signaling the
                DCC to start a media sensor calibration."
::= { settings-prt-eng 35 }
               
               
total-color-page-count OBJECT-TYPE
   SYNTAX      INTEGER
   ACCESS      read-only
   STATUS      optional
   DESCRIPTION "Total number of color pages printed by the device.
                Additional information:
                Total number of color pages printed by the device.
                The valid range of this object is 0 to 2^24-1. When the number of
                color pages printed exceeds the maximum color page count, the
                value will roll to zero.
                A duplexed sheet of media will cause the counter to be
                incremented by two."
::= { status-prt-eng 7 }
               
               
printer-cal-dlsr-present OBJECT-TYPE
   SYNTAX      INTEGER {
		   eNotSupported(1),
		   eSupported(2)
		   }
   ACCESS      read-only
   STATUS      optional
   DESCRIPTION "Indicates whether any download stay resident color tables		
                present in the printer.
                Additional information:
                Indicates whether any download stay resident color tables
                present in the printer."
::= { status-prt-eng 51 }
               
               
printer-cal-customiq-factory-default OBJECT-TYPE
   SYNTAX      INTEGER {
		   eFactoryDefaultTrue(2),
		   eFactoryDefaultFalse(1)
		   }
   ACCESS      read-only
   STATUS      optional
   DESCRIPTION "Provides the status of the customIQ color table, indicating		
                whether the table is the factory default or whether the table		
                has been updated via RFU. eFactoryDefaultTrue(2) means the		
                table is the factory default; eFactorDefaultFalse(1) means an		
                RFU download has occurred, and the table is not the factory		
                default. Note, an RFU for the factory default is available, and		
                if in place, eFactoryDefaultTrue will be reported.
                Additional information:
                Provides the status of the customIQ color table, indicating
                whether the table is the factory default or whether the table
                has been updated via RFU. eFactoryDefaultTrue(2) means the
                table is the factory default; eFactorDefaultFalse(1) means an
                RFU download has occurred, and the table is not the factory
                default. Note, an RFU for the factory default is available, and
                if in place, eFactoryDefaultTrue will be reported."
::= { status-prt-eng 52 }
               
               
duplex-page-count OBJECT-TYPE
   SYNTAX      INTEGER
   ACCESS      read-only
   STATUS      optional
   DESCRIPTION "Total number of sheets of media that have been duplex printed.		
                A sheet is counted if it travels through the duplex page path,		
                regardless of whether or not marks are made on the page. The		
                POS will indicate if the value is kept in NVRAM.
                Additional information:
                Total number of sheets of media that have been duplex
                printed.  A sheet is counted if it travels through the
                duplex page path, regardless of whether or not marks are
                made on the page.  
                This value is kept in NVRAM however the NVRAM value is only 
                updated every 10 sheets. NOTE: The value returned by this object 
                will be incremented every sheet but if power is lost between
                NVRAM updates up to 9 sheets of the count may be lost. The counter 
                will be reset to zero after 16,777,215 (2^24-1) pages. "
::= { status-prt-eng 22 }
               
               
print-engine-revision OBJECT-TYPE
   SYNTAX      OCTET STRING (SIZE(1..16))
   ACCESS      read-only
   STATUS      optional
   DESCRIPTION "Print engine revision string.
                Additional information:
                Print engine revision string.  The symbol set for this string is 
                Roman-8. "
::= { status-prt-eng 26 }
               
               
printer-cal-dhalf-page-count OBJECT-TYPE
   SYNTAX      INTEGER
   ACCESS      read-only
   STATUS      optional
   DESCRIPTION "Provides the page count when the last DHALF calibration		
                occurred. A '-1' indicates that a calibration of this kind has		
                not taken place yet. This object exists (and is meaningful)		
                only in color printers.
                Additional information:
                Provides the page count when last DHALF calibration
                occurred. A -1 indicates that a calibration of this
                kind has not taken place yet. This object exists
                (and is meaningful) only in color printers."
::= { printer-calibration-dhalf 1 }
               
               
printer-cal-dhalf-utc OBJECT-TYPE
   SYNTAX      INTEGER
   ACCESS      read-only
   STATUS      optional
   DESCRIPTION "Provides the time (in UTC - Universal Time Code format) when		
                the last DHALF calibration occurred. This value could be zero		
                if no calibration has taken place or if the printer lacked		
                real-time. This object exists (and is meaningful) only in color		
                printers.
                Additional information:
                Provides the time (in UTC - Universal Time Code format)
                when last DHALF calibration occurred. This value could
                be zero if no calibration has taken place and / or if
                the printer lacked real-time. This object exists (and
                is meaningful) only in color printers."
::= { printer-calibration-dhalf 2 }
               
               
printer-cal-dhalf-data1 OBJECT-TYPE
   SYNTAX      OCTET STRING
   ACCESS      read-only
   STATUS      optional
   DESCRIPTION "Provides a device specific set of DHalf calibration data as a		
                binary string of byte values. It will be necessary to have a		
                decoder for each engine to interpret the data.
                Additional information:
                Provides a device specific set of Dhalf calibration data as a
                binary string of byte values. It will be necessary to have a
                decoder for each engine to interpret the data."
::= { printer-cal-dhalf-data 1 }
               
               
printer-cal-dhalf-data2 OBJECT-TYPE
   SYNTAX      OCTET STRING
   ACCESS      read-only
   STATUS      optional
   DESCRIPTION "Provides a device specific set of DHalf calibration data as a		
                binary string of byte values. It will be necessary to have a		
                decoder for each engine to interpret the data.
                Additional information:
                Provides a device specific set of Dhalf calibration data as a
                binary string of byte values. It will be necessary to
                	       have a decoder for each engine to interpret the data."
::= { printer-cal-dhalf-data 2 }
               
               
printer-cal-grayaxis-count OBJECT-TYPE
   SYNTAX      INTEGER
   ACCESS      read-only
   STATUS      optional
   DESCRIPTION "Provides the page count when last GRAY AXIS CONTROL calibration		
                occurred. A '-1' indicates that a calibration of this kind has		
                not taken place yet. This object exists (and is meaningful)		
                only in color printers.
                Additional information:
                Provides the page count when last GRAY AXIS CONTROL 
                calibration occurred. A -1 indicates that a calibration 
                of this kind has not taken place yet. This object exists 
                (and is meaningful) only in color printers."
::= { printer-calibration-dhalf 4 }
               
               
printer-cal-grayaxis-utc OBJECT-TYPE
   SYNTAX      INTEGER
   ACCESS      read-only
   STATUS      optional
   DESCRIPTION "Provides the time (in UTC - Universal Time Code form) when the		
                last GRAY AXIS CONTROL calibration occurred. This value could		
                be zero if no calibration has taken place and / or if the		
                printer lacked real-time. This object exists (and is		
                meaningful) only in color printers.
                Additional information:
                Provides the time (in UTC - Universal Time Code form) 
                when the last GRAY AXIS CONTROL calibration occurred. 
                	       This value could be zero if no calibration has taken 
                	       place and / or if the printer lacked real-time. This 
                object exists (and is meaningful) only in color 
                printers."
::= { printer-calibration-dhalf 5 }
               
               
printer-cal-grayaxis-tray OBJECT-TYPE
   SYNTAX      INTEGER
   ACCESS      read-write
   STATUS      optional
   DESCRIPTION "Defines the tray from which a GRAY AXIS CALIBRATION will be		
                performed when executed by the PRINTER-MARKER-CALIBRATION		
                command. This object exists (and is meaningful) only in color		
                printers.
                Additional information:
                Defines the tray from which a GRAY AXIS CALIBRATION will 
                be performed when executed by the 
                PRINTER-MARKER-CALIBRATION command. This object exists 
                (and is meaningful) only in color printers."
::= { printer-cal-grayaxis 1 }
               
               
printer-cal-grayaxis-media OBJECT-TYPE
   SYNTAX      OCTET STRING (SIZE(1..24))
   ACCESS      read-write
   STATUS      optional
   DESCRIPTION "Defines the media type for a GRAY AXIS CONTROL calibration		
                which is executed by the PRINTER-MARKER-CALIBRATION command.		
                The symbol set for this string is Roman-8. This object exists		
                (and is meaningful) only in color printers.
                Additional information:
                Defines the media type for a GRAY AXIS CONTROL 
                calibration which is executed by the 
                PRINTER-MARKER-CALIBRATION command. The symbol set for 
                this string is Roman-8. This object exists (and is 
                meaningful) only in color printers."
::= { printer-cal-grayaxis 2 }
               
               
printer-cal-grayaxis-xsize OBJECT-TYPE
   SYNTAX      INTEGER
   ACCESS      read-write
   STATUS      optional
   DESCRIPTION "Defines the width of the media to be used for a GRAY AXIS		
                CONTROL calibration when executed by		
                PRINTER-MARKER-CALIBRATION. This object exists (and is		
                meaningful) only in color printers.
                Additional information:
                Defines the width of the media to be used for a GRAY 
                AXIS CONTROL calibration when executed by 
                PRINTER-MARKER-CALIBRATION. This object exists (and is 
                meaningful) only in color printers."
::= { printer-cal-grayaxis 3 }
               
               
printer-cal-grayaxis-ysize OBJECT-TYPE
   SYNTAX      INTEGER
   ACCESS      read-write
   STATUS      optional
   DESCRIPTION "Defines the length of the media to be used for a GRAY AXIS		
                CONTROL calibration when executed by		
                PRINTER-MARKER-CALIBRATION. This object exists (and is		
                meaningful) only in color printers.
                Additional information:
                Defines the length of the media to be used for a GRAY 
                AXIS CONTROL calibration when executed by 
                PRINTER-MARKER-CALIBRATION. This object exists (and is 
                meaningful) only in color printers."
::= { printer-cal-grayaxis 4 }
               
               
printer-cal-grayaxis-data1 OBJECT-TYPE
   SYNTAX      OCTET STRING
   ACCESS      read-only
   STATUS      optional
   DESCRIPTION "Provides a device specific set of GRAY AXIS CONTROL calibration		
                data as a binary string of byte values. It will be necessary to		
                have a decoder for each engine to interpret the data. This		
                object exists (and is meaningful) only in color printers.
                Additional information:
                Provides a device specific set of GRAY AXIS CONTROL 
                calibration data as a binary string of byte values. It 
                	       will be necessary to have a decoder for each engine to 
                	       interpret the data. This object exists (and is 
                	       meaningful) only in color printers."
::= { printer-cal-grayaxis-data 1 }
               
               
printer-cal-grayaxis-data2 OBJECT-TYPE
   SYNTAX      OCTET STRING
   ACCESS      read-only
   STATUS      optional
   DESCRIPTION "Provides a device specific set of GRAY AXIS CONTROL calibration		
                data as a binary string of byte values. It will be necessary to		
                have a decoder for each engine to interpret the data. This		
                object exists (and is meaningful) only in color printers.
                Additional information:
                Provides a device specific set of GRAY AXIS CONTROL 
                	       calibration data as a binary string of byte values. It 
                	       will be necessary to have a decoder for each engine to 
                	       interpret the data. This object exists (and is 
                meaningful) only in color printers."
::= { printer-cal-grayaxis-data 2 }
               
               
printer-cal-cpr-page-count OBJECT-TYPE
   SYNTAX      INTEGER
   ACCESS      read-only
   STATUS      optional
   DESCRIPTION "Provides the page count when last CPR calibration occurred. A		
                '-1' indicates that a calibration of this kind has not taken		
                place yet. This object exists (and is meaningful) only in color		
                printers.
                Additional information:
                Provides the page count when last CPR calibration
                occurred. A -1 indicates that a calibration of this
                kind has not taken place yet. This object exists
                (and is meaningful) only in color printers."
::= { printer-calibration-cpr 1 }
               
               
printer-cal-cpr-utc OBJECT-TYPE
   SYNTAX      INTEGER
   ACCESS      read-only
   STATUS      optional
   DESCRIPTION "Provides the time (in UTC - Universal Time Code format) when		
                the last CPR calibration occurred. This value could be zero if		
                no calibration has taken place or if the printer lacked		
                real-time. This object exists (and is meaningful) only in color		
                printers.
                Additional information:
                Provides the time (in UTC - Universal Time Code format)
                when last CPR calibration occurred. This value could
                be zero if no calibration has taken place and / or if
                the printer lacked real-time. This object exists (and
                is meaningful) only in color printers."
::= { printer-calibration-cpr 2 }
               
               
printer-cal-cpr-data OBJECT-TYPE
   SYNTAX      OCTET STRING
   ACCESS      read-only
   STATUS      optional
   DESCRIPTION "Provides a device specific set of CPR calibration data as a		
                binary string of byte values. It will be necessary to have a		
                decoder for each engine to interpret the data.
                Additional information:
                Provides a device specific set of CPR calibration data as a
                binary string of byte values. It will be necessary to have a
                decoder for each engine to interpret the data."
::= { printer-calibration-cpr 3 }
               
               
input-tray-auto-select OBJECT-TYPE
   SYNTAX      INTEGER {
		   eOff(1),
		   eOn(2)
		   }
   ACCESS      read-write
   STATUS      optional
   DESCRIPTION "Indicates if the device will automatically try to load media		
                from the next input media tray in the auto-select sequence		
                (defined by each device) when it cannot load media from the		
                current tray. Locked trays will not be permitted in the		
                auto-select sequence. This object has no meaning if there is		
                only one unlocked input media tray.
                Additional information:
                Indicates if the device will automatically try to load
                media from the next input media tray in the auto-select
                sequence (defined by each device) when it cannot load
                media from the current tray.  Locked trays will not be
                permitted in the auto-select sequence.  This object has
                no meaning if there is only one unlocked input media
                tray."
::= { settings-intray 2 }
               
               
custom-paper-feed-dim OBJECT-TYPE
   SYNTAX      INTEGER
   ACCESS      read-write
   STATUS      optional
   DESCRIPTION "Sets the printer's custom paper dimension in the feed direction		
                (direction parallel to the direction of paper feeding). The		
                value for this object is specified in micrometers or		
                tenthousandths of an inch, depending upon the value of		
                CUSTOM-PAPER-DIM-UNIT. The valid range is engine-dependent and		
                should be documented in the POS for each product.
                Additional information:
                Get/Set custom paper dimension (height).
                The return/set value is either in micrometers or 
                10,000ths of inches.  A tray has to be in
                custom switch or without media size sensor to be
                able to set the custom dimension. 
                If it is successfully setting the dimension value,
                the size of a tray is set to CUSTOM."
::= { settings-intray 8 }
               
               
custom-paper-xfeed-dim OBJECT-TYPE
   SYNTAX      INTEGER
   ACCESS      read-write
   STATUS      optional
   DESCRIPTION "Sets the printer's custom paper dimension in the cross-feed		
                direction (direction ninety degrees relative to the direction		
                of paper feeding). The value for this object is specified in		
                micrometers or tenthousandths of an inch, depending upon the		
                value of CUSTOM-PAPER-DIM-UNIT. The valid range is		
                engine-dependent and should be documented in the POS for each		
                product.
                Additional information:
                Get/Set custom paper dimension (width).
                The return/set value is either in micrometers or 
                10,000ths of inches.  A tray has to be in
                custom switch or without media size sensor to be
                able to set the custom dimension. 
                If it is successfully setting the dimension value,
                the size of a tray is set to CUSTOM."
::= { settings-intray 9 }
               
               
default-custom-paper-dim-unit OBJECT-TYPE
   SYNTAX      INTEGER {
		   eTenThousandthsOfInches(3),
		   eMicrometers(4)
		   }
   ACCESS      read-write
   STATUS      optional
   DESCRIPTION "The units of measure used to specify the width and height of		
                the printer's default custom paper size. The unit of measure of		
                eTenThousandthsOfInches is 0.0001 inches.
                Additional information:
                The units of measure used to specify the width and 
                height of the printer's default custom paper size.
                The unit of measure of eTenThousandthsOfInches is
                0.0001 inches."
::= { settings-intray 10 }
               
               
default-custom-paper-feed-dim OBJECT-TYPE
   SYNTAX      INTEGER
   ACCESS      read-write
   STATUS      optional
   DESCRIPTION "Sets the printer's default custom paper size dimension in the		
                feed direction (direction parallel to the direction of paper		
                feeding). The value for this object is specified in micrometers		
                or tenthousandths of an inch, depending upon the value of		
                DEFAULT-CUSTOM-PAPER-DIM-UNIT. The valid range is		
                engine-dependent and should be documented in the POS for each		
                product.
                Additional information:
                Sets the printer's default custom paper size dimension 
                in the feed direction (direction parallel to the direction
                of paper feeding). The value for this object is specified
                in micrometers or tenthousandths of an inch, depending upon
                the value of DEFAULT-CUSTOM-PAPER-DIM-UNIT. The valid
                range is engine-dependent and should be documented in the
                POS for each product."
::= { settings-intray 11 }
               
               
default-custom-paper-xfeed-dim OBJECT-TYPE
   SYNTAX      INTEGER
   ACCESS      read-write
   STATUS      optional
   DESCRIPTION "Sets the printer's default custom paper size dimension in the		
                cross-feed direction (direction ninety degrees relative to the		
                direction of paper feeding). The value for this object is		
                specified in micrometers or tenthousandths of an inch,		
                depending upon the value of DEFAULT-CUSTOM-PAPER-DIM-UNIT. The		
                valid range is engine-dependent and should be documented in the		
                POS for each product.
                Additional information:
                Sets the printer's default custom paper size dimension 
                in the cross-feed direction (direction ninety degrees
                relative to the direction of paper feeding). The value
                for this object is specified in micrometers or
                tenthousandths of an inch, depending upon the value of
                DEFAULT-CUSTOM-PAPER-DIM-UNIT. The valid range is
                engine-dependent and should be documented in the POS
                for each product."
::= { settings-intray 12 }
               
               
input-tray-max-media-feed-dim OBJECT-TYPE
   SYNTAX      INTEGER
   ACCESS      read-only
   STATUS      optional
   DESCRIPTION "The maximum physical media size in the feed direction of this		
                input device expressed in units of measure specified by INPUT-		
                TRAY-MIN-MAX-DIM-UNIT. A value of (-1) implies 'unlimited', a		
                value of (-2) implies 'unknown'.
                Additional information:
                The maximum physical media size in the feed direction of this 
                input device expressed in units of measure specified by
                PrtInputDimUnit. A value of (-1) implies 'unlimited',
                a value of (-2) implies 'unknown'.
                Refer to Printer Management Standards web page,
                http://bldlabs.boi.hp.com/BLDPrinterLab/Project/PrinterManagement, for more details in the original format
                of the Standard Printer MIB."
::= { settings-intray 14 }
               
               
input-tray-max-media-xfeed-dim OBJECT-TYPE
   SYNTAX      INTEGER
   ACCESS      read-only
   STATUS      optional
   DESCRIPTION "The maximum physical media size across the feed direction of a		
                particular input device expressed in units of measure specified		
                by INPUT-TRAY-MIN-MAX-DIM-UNIT. A value of (-1) implies		
                'unlimited', a value of (-2) implies 'unknown'.
                Additional information:
                The maximum physical media size across the feed direction of this 
                input device expressed in units of measure specified by
                PrtInputDimUnit. A value of (-1) implies 'unlimited',
                a value of (-2) implies 'unknown'.
                Refer to Printer Management Standards web page,
                http://bldlabs.boi.hp.com/BLDPrinterLab/Project/PrinterManagement, f
                or more details in the original format
                of the Standard Printer MIB."
::= { settings-intray 15 }
               
               
input-tray-min-media-feed-dim OBJECT-TYPE
   SYNTAX      INTEGER
   ACCESS      read-only
   STATUS      optional
   DESCRIPTION "The minimum physical media size in the feed direction of a		
                particular input device expressed in units of measure specified		
                by PrtInputMinMaxDimUnit. A value of (-1) implies 'unlimited',		
                a value of (-2) implies 'unknown'.
                Additional information:
                The minimum physical media size in the feed direction of this 
                input device expressed in units of measure specified by
                PrtInputDimUnit. A value of (-1) implies 'unlimited',
                a value of (-2) implies 'unknown'.
                Refer to Printer Management Standards web page,
                http://bldlabs.boi.hp.com/BLDPrinterLab/Project/PrinterManagement,
                for more details in the original format
                of the Standard Printer MIB."
::= { settings-intray 16 }
               
               
input-tray-min-media-xfeed-dim OBJECT-TYPE
   SYNTAX      INTEGER
   ACCESS      read-only
   STATUS      optional
   DESCRIPTION "The minimum physical media size across the feed direction of a		
                particular input device expressed in units of measure specified		
                by PrtInputMinMaxDimUnit. A value of (-1) implies 'unlimited',		
                a value of (-2) implies 'unknown'.
                Additional information:
                The minimum physical media size across the feed direction of this 
                input device expressed in units of measure specified by
                PrtInputDimUnit. A value of (-1) implies 'unlimited',
                a value of (-2) implies 'unknown'.
                Refer to Printer Management Standards web page,
                http://bldlabs.boi.hp.com/BLDPrinterLab/Project/PrinterManagement,
                for more details in the original format
                of the Standard Printer MIB."
::= { settings-intray 17 }
               
               
tray1-media-size-loaded OBJECT-TYPE
   SYNTAX      INTEGER {
		   eUSExecutive(1),
		   eUSLetter(2),
		   eUSLegal(3),
		   eFoolscap(10),
		   eLedger(11),
		   eStatement(15),
		   eROC16K(17),
		   eROC8K(19),
		   eISOandJISA6(24),
		   eISOandJISA5(25),
		   eISOandJISA4(26),
		   eISOandJISA3(27),
		   ePRC8K270X390(33),
		   ePRC16K195X270(34),
		   ePRC8K260X368(35),
		   eISOSRA3(38),
		   eISORA3(39),
		   eJISB6(44),
		   eJISB5(45),
		   eJISB4(46),
		   eJapansePostcardDouble(72),
		   eIndexCard4x6(74),
		   eIndexCard5x8(75),
		   eMonarch(80),
		   eCommercial10(81),
		   ePRC16K184X260(89),
		   eInternationalDL(90),
		   eInternationalC5(91),
		   eInternationalC6(92),
		   eInternationalB5(100),
		   eCustom(101),
		   eEnvelope9(102),
		   eTabloidExtra(120),
		   eUSLetterR(258),
		   eISOandJISA4R(282),
		   eAnyCustomSize(32764),
		   eAnySize(32765)
		   }
   ACCESS      read-write
   STATUS      optional
   DESCRIPTION "Returns the media size that is currently configuredconfigured		
                in tray #1. This object can be set to indicate the media size		
                currently loaded, if the printer supports input trays that can		
                not sense the media size. Complete list of supported media		
                sizes along with their dimensions are listed in the ''Media		
                Size Table'' near the end of this document.
                Additional information:
                Returns the media size that is currently 
                configuredconfigured in tray #1. This object can be set
                to indicate the media size currently loaded, if the
                printer supports input trays that can not sense the
                media size. Complete list of supported media sizes
                along with their dimensions are listed in the ''Media
                Size Table'' near the end of this document."
::= { intray1 1 }
               
               
tray1-phd OBJECT-TYPE
   SYNTAX      INTEGER
   ACCESS      read-only
   STATUS      optional
   DESCRIPTION "Provides the number of the Paper Handling Device that contains		
                this input tray.
                Additional information:
                Provides the number of the Paper Handling Device that
                contains this input tray."
::= { intray1 12 }
               
               
tray2-media-size-loaded OBJECT-TYPE
   SYNTAX      INTEGER {
		   eUSExecutive(1),
		   eUSLetter(2),
		   eUSLegal(3),
		   eFoolscap(10),
		   eLedger(11),
		   eROC16K(17),
		   eROC8K(19),
		   eISOandJISA5(25),
		   eISOandJISA4(26),
		   eISOandJISA3(27),
		   ePRC8K270X390(33),
		   ePRC16K195X270(34),
		   ePRC8K260X368(35),
		   eJISB5(45),
		   eJISB4(46),
		   ePRC16K184X260(89),
		   eCustom(101),
		   eUSLetterR(258),
		   eISOandJISA4R(282)
		   }
   ACCESS      read-write
   STATUS      optional
   DESCRIPTION "Returns the media size that is currently configured in tray #2.		
                Complete list of supported media sizes along with their		
                dimensions are listed in the ''Media Size Table'' near the end		
                of this document.
                Additional information:
                Returns the media size that is currently configured in
                tray #2."
::= { intray2 1 }
               
               
tray2-phd OBJECT-TYPE
   SYNTAX      INTEGER
   ACCESS      read-only
   STATUS      optional
   DESCRIPTION "Provides the number of the Paper Handling Device that contains		
                this input tray.
                Additional information:
                Provides the number of the Paper Handling Device that 
                contains this input tray."
::= { intray2 12 }
               
               
tray3-media-size-loaded OBJECT-TYPE
   SYNTAX      INTEGER {
		   eUSExecutive(1),
		   eUSLetter(2),
		   eUSLegal(3),
		   eFoolscap(10),
		   eLedger(11),
		   eROC16K(17),
		   eROC8K(19),
		   eISOandJISA5(25),
		   eISOandJISA4(26),
		   eISOandJISA3(27),
		   ePRC8K270X390(33),
		   ePRC16K195X270(34),
		   ePRC8K260X368(35),
		   eISOSRA3(38),
		   eISORA3(39),
		   eJISB5(45),
		   eJISB4(46),
		   ePRC16K184X260(89),
		   eCustom(101),
		   eTabloidExtra(120),
		   eUSLetterR(258),
		   eISOandJISA4R(282),
		   eAnyCustomSize(32764)
		   }
   ACCESS      read-write
   STATUS      optional
   DESCRIPTION "Returns the media size that is currently configured in tray #3.		
                Complete list of supported media sizes along with their		
                dimensions are listed in the ''Media Size Table'' near the end		
                of this document.
                Additional information:
                Returns the media size that is currently configured in
                tray #3."
::= { intray3 1 }
               
               
tray3-phd OBJECT-TYPE
   SYNTAX      INTEGER
   ACCESS      read-only
   STATUS      optional
   DESCRIPTION "Provides the number of the Paper Handling Device that contains		
                this input tray.
                Additional information:
                Provides the number of the Paper Handling Device that 
                contains this input tray."
::= { intray3 12 }
               
               
tray5-media-size-loaded OBJECT-TYPE
   SYNTAX      INTEGER {
		   eUSExecutive(1),
		   eUSLetter(2),
		   eUSLegal(3),
		   eFoolscap(10),
		   eLedger(11),
		   eROC16K(17),
		   eROC8K(19),
		   eISOandJISA5(25),
		   eISOandJISA4(26),
		   eISOandJISA3(27),
		   ePRC8K270X390(33),
		   ePRC16K195X270(34),
		   ePRC8K260X368(35),
		   eISOSRA3(38),
		   eISORA3(39),
		   eJISB5(45),
		   eJISB4(46),
		   ePRC16K184X260(89),
		   eCustom(101),
		   eTabloidExtra(120),
		   eUSLetterR(258),
		   eISOandJISA4R(282),
		   eAnyCustomSize(32764)
		   }
   ACCESS      read-write
   STATUS      optional
   DESCRIPTION "Returns the media size that is currently configured in tray #5.		
                Complete list of supported media sizes along with their		
                dimensions are listed in the ''Media Size Table'' near the end		
                of this document.
                Additional information:
                Returns the media size that is currently configured in
                tray #5."
::= { intray5 1 }
               
               
tray5-phd OBJECT-TYPE
   SYNTAX      INTEGER
   ACCESS      read-only
   STATUS      optional
   DESCRIPTION "Provides the number of the Paper Handling Device that contains		
                this input tray.
                Additional information:
                Provides the number of the Paper Handling Device that
                contains this input tray."
::= { intray5 12 }
               
               
tray6-media-size-loaded OBJECT-TYPE
   SYNTAX      INTEGER {
		   eUSExecutive(1),
		   eUSLetter(2),
		   eUSLegal(3),
		   eFoolscap(10),
		   eLedger(11),
		   eROC16K(17),
		   eROC8K(19),
		   eISOandJISA5(25),
		   eISOandJISA4(26),
		   eISOandJISA3(27),
		   ePRC8K270X390(33),
		   ePRC16K195X270(34),
		   ePRC8K260X368(35),
		   eISOSRA3(38),
		   eISORA3(39),
		   eJISB5(45),
		   eJISB4(46),
		   ePRC16K184X260(89),
		   eCustom(101),
		   eTabloidExtra(120),
		   eUSLetterR(258),
		   eISOandJISA4R(282),
		   eAnyCustomSize(32764)
		   }
   ACCESS      read-write
   STATUS      optional
   DESCRIPTION "Returns the media size that is currently configured in tray #5.		
                Complete list of supported media sizes along with their		
                dimensions are listed in the ''Media Size Table'' near the end		
                of this document.
                Additional information:
                Returns the media size that is currently configured in
                tray #6."
::= { intray6 1 }
               
               
tray6-phd OBJECT-TYPE
   SYNTAX      INTEGER
   ACCESS      read-only
   STATUS      optional
   DESCRIPTION "Provides the number of the Paper Handling Device that contains		
                this input tray.
                Additional information:
                Provides the number of the Paper Handling Device that 
                contains this input tray."
::= { intray6 12 }
               
               
overflow-bin OBJECT-TYPE
   SYNTAX      INTEGER
   ACCESS      read-write
   STATUS      optional
   DESCRIPTION "Returns or sets the bin that will be used for additional sheets		
                of media when the current bin is full and printing is allowed		
                to continue.
                Additional information:
                Returns or sets the bin that will be used for additional
                sheets of media when the current bin is full and
                printing is allowed to continue. 
                The data for this object is stored in NVRAM."
::= { settings-outbin 4 }
               
               
outbin1-override-mode OBJECT-TYPE
   SYNTAX      OCTET STRING
   ACCESS      read-write
   STATUS      optional
   DESCRIPTION "Returns or sets the device behavior when this output bin		
                condition causes printing to stop.    	
                    cCancelJob - The device cancels the job.    	
                    cOutbinFullOverride - The device sends subsequent media to		
                        the overflow bin.    	
                    cOutbinAttentionOverride - The device ignores the attention		
                        condition and continues printing.    	
                    cBinderAttentionOverride - The device ignores the binder		
                        attention condition and continues printing.  
                Additional information:
                Returns or sets the device behavior when this output bin
                condition causes printing to stop.
                cCancelJob - The device cancels the job, regardless of other
                bit settings.
                cOutbinFullOverride - The device sends subsequent
                media to the overflow bin.  If this bin is the
                overflow bin, this bit is ignored.
                cOutbinAttentionOverride - The device ignores the
                attention condition and continues printing.
                cBinderAttentionOverride - The device ignores the
                binder attention condition and continues printing.
                
                This object describes the action that is performed when the
                JOB-OUTPUT-AUTO-CONTINUE-TIMEOUT expires. If no bits
                are set, no override action is taken (the printer
                will continue to wait)."
::= { outbin1 9 }
               
               
outbin2-override-mode OBJECT-TYPE
   SYNTAX      OCTET STRING
   ACCESS      read-write
   STATUS      optional
   DESCRIPTION "Returns or sets the device behavior when this output bin		
                condition causes printing to stop.    	
                    cCancelJob - The device cancels the job.    	
                    cOutbinFullOverride - The device sends subsequent media to		
                        the overflow bin.    	
                    cOutbinAttentionOverride - The device ignores the attention		
                        condition and continues printing.    	
                    cBinderAttentionOverride - The device ignores the binder		
                        attention condition and continues printing.   
                Additional information:
                Returns or sets the device behavior when this output bin
                condition causes printing to stop.
                cCancelJob - The device cancels the job, regardless of other
                bit settings.
                cOutbinFullOverride - The device sends subsequent
                media to the overflow bin.  If this bin is the
                overflow bin, this bit is ignored.
                cOutbinAttentionOverride - The device ignores the
                attention condition and continues printing.
                cBinderAttentionOverride - The device ignores the
                binder attention condition and continues printing.
                
                This object describes the action that is performed when the
                JOB-OUTPUT-AUTO-CONTINUE-TIMEOUT expires. If no bits
                are set, no override action is taken (the printer
                will continue to wait)."
::= { outbin2 9 }
               
               
outbin2-maximum-binding OBJECT-TYPE
   SYNTAX      INTEGER
   ACCESS      read-only
   STATUS      optional
   DESCRIPTION "The maximum number of sheets of 20 pound paper that can be		
                bound by the binding device that serves this output bin. If a		
                job exceeds this number and the job has requested binding,		
                cBindingError will be set in NOT-		
                READY-DESTINATION-PRINT-ENGINE.
                Additional information:
                The maximum number of sheets of 20 pound paper that can
                be bound by the binding device that serves this output
                bin. If a job exceeds this number and the job has
                requested binding, cBindingError will be set in NOT-
                READY-DESTINATION-PRINT-ENGINE."
::= { outbin2 10 }
               
               
outbin2-phd OBJECT-TYPE
   SYNTAX      INTEGER
   ACCESS      read-only
   STATUS      optional
   DESCRIPTION "Provides the number of the Paper Handling Device that contains		
                this output bin.
                Additional information:
                Provides the number of the Paper Handling Device that
                contains this output bin."
::= { outbin2 11 }
               
               
outbin2-error-info OBJECT-TYPE
   SYNTAX      OCTET STRING
   ACCESS      read-only
   STATUS      optional
   DESCRIPTION "A device specific description of the last error encountered for		
                output bin 2. Each POS should document the meaning of all		
                supported error information.
                Additional information:
                This is a description of the current error state of a
                finishing device. (ie stapler). If the bin does not
                support any finishing capabilities then the object
                will return <badValue>.
                The possible return values are as follows:
                Byte1, Byte2, and Byte3 should be 0x00. as they are
                reserved for future use.
                Byte4 is a bit field that can be interpreted as
                follows:
                bit 0 - unused
                bit 1 - eBinderOut Out of staples
                bit 2 - eBinderLimit Too many pages to finish
                bit 3 - eBinderJam Staple jammed in stapler
                bit 4 - eBinderAlign Pages aren't aligned correctly to finish.
                bit 5 - unused
                bit 6 - unused
                bit 7 - unused
                NOTE: Because HP is marketing a device with a max of
                16 bins the OUTBIN-MAXIMUM-BINDING objects are 3-18 but
                the external device specification requires support of
                up to 315 output bins. Therefore if these bins exist
                above 16, then the coresponding objects will also exist
                OUTBIN19-MAXIMUM-BINDING ... OUTBIN317-MAXIMUM-BINDING"
::= { outbin2 12 }
               
               
outbin3-override-mode OBJECT-TYPE
   SYNTAX      OCTET STRING
   ACCESS      read-write
   STATUS      optional
   DESCRIPTION "Returns or sets the device behavior when this output bin		
                condition causes printing to stop.    	
                    cCancelJob - The device cancels the job.    	
                    cOutbinFullOverride - The device sends subsequent media to		
                        the overflow bin.    	
                    cOutbinAttentionOverride - The device ignores the attention		
                        condition and continues printing.    	
                    cBinderAttentionOverride - The device ignores the binder		
                        attention condition and continues printing.   
                Additional information:
                Returns or sets the device behavior when this output bin
                condition causes printing to stop.
                cCancelJob - The device cancels the job, regardless of other
                bit settings.
                cOutbinFullOverride - The device sends subsequent
                media to the overflow bin.  If this bin is the
                overflow bin, this bit is ignored.
                cOutbinAttentionOverride - The device ignores the
                attention condition and continues printing.
                cBinderAttentionOverride - The device ignores the
                binder attention condition and continues printing.
                
                This object describes the action that is performed when the
                JOB-OUTPUT-AUTO-CONTINUE-TIMEOUT expires. If no bits
                are set, no override action is taken (the printer
                will continue to wait)."
::= { outbin3 9 }
               
               
outbin3-maximum-binding OBJECT-TYPE
   SYNTAX      INTEGER
   ACCESS      read-only
   STATUS      optional
   DESCRIPTION "The maximum number of sheets of 20 pound paper that can be		
                bound by the binding device that serves this output bin. If a		
                job exceeds this number and the job has requested binding,		
                cBindingError will be set in NOT-		
                READY-DESTINATION-PRINT-ENGINE.
                Additional information:
                The maximum number of sheets of 20 pound paper that can
                be bound by the binding device that serves this output
                bin. If a job exceeds this number and the job has
                requested binding, cBindingError will be set in NOT-
                READY-DESTINATION-PRINT-ENGINE."
::= { outbin3 10 }
               
               
outbin3-phd OBJECT-TYPE
   SYNTAX      INTEGER
   ACCESS      read-only
   STATUS      optional
   DESCRIPTION "Provides the number of the Paper Handling Device that contains		
                this output bin.
                Additional information:
                Provides the number of the Paper Handling Device that
                contains this output bin."
::= { outbin3 11 }
               
               
outbin3-error-info OBJECT-TYPE
   SYNTAX      OCTET STRING
   ACCESS      read-only
   STATUS      optional
   DESCRIPTION "A device specific description of the last error encountered for		
                output bin 3. Each POS should document the meaning of all		
                supported error information.
                Additional information:
                This is a description of the current error state of a
                finishing device. (ie stapler). If the bin does not
                support any finishing capabilities then the object
                will return <badValue>.
                The possible return values are as follows:
                Byte1, Byte2, and Byte3 should be 0x00. as they are
                reserved for future use.
                Byte4 is a bit field that can be interpreted as
                follows:
                bit 0 - unused
                bit 1 - eBinderOut Out of staples
                bit 2 - eBinderLimit Too many pages to finish
                bit 3 - eBinderJam Staple jammed in stapler
                bit 4 - eBinderAlign Pages aren't aligned correctly to finish.
                bit 5 - unused
                bit 6 - unused
                bit 7 - unused
                NOTE: Because HP is marketing a device with a max of
                16 bins the OUTBIN-MAXIMUM-BINDING objects are 3-18 but
                the external device specification requires support of
                up to 315 output bins. Therefore if these bins exist
                above 16, then the coresponding objects will also exist
                OUTBIN19-MAXIMUM-BINDING ... OUTBIN317-MAXIMUM-BINDING"
::= { outbin3 12 }
               
               
outbin4-override-mode OBJECT-TYPE
   SYNTAX      OCTET STRING
   ACCESS      read-write
   STATUS      optional
   DESCRIPTION "Returns or sets the device behavior when this output bin		
                condition causes printing to stop.    	
                    cCancelJob - The device cancels the job.    	
                    cOutbinFullOverride - The device sends subsequent media to		
                        the overflow bin.    	
                    cOutbinAttentionOverride - The device ignores the attention		
                        condition and continues printing.    	
                    cBinderAttentionOverride - The device ignores the binder		
                        attention condition and continues printing.   
                Additional information:
                Returns or sets the device behavior when this output bin
                condition causes printing to stop.
                cCancelJob - The device cancels the job, regardless of other
                bit settings.
                cOutbinFullOverride - The device sends subsequent
                media to the overflow bin.  If this bin is the
                overflow bin, this bit is ignored.
                cOutbinAttentionOverride - The device ignores the
                attention condition and continues printing.
                cBinderAttentionOverride - The device ignores the
                binder attention condition and continues printing.
                
                This object describes the action that is performed when the
                JOB-OUTPUT-AUTO-CONTINUE-TIMEOUT expires. If no bits
                are set, no override action is taken (the printer
                will continue to wait)."
::= { outbin4 9 }
               
               
outbin4-maximum-binding OBJECT-TYPE
   SYNTAX      INTEGER
   ACCESS      read-only
   STATUS      optional
   DESCRIPTION "The maximum number of sheets of 20 pound paper that can be		
                bound by the binding device that serves this output bin. If a		
                job exceeds this number and the job has requested binding,		
                cBindingError will be set in NOT-		
                READY-DESTINATION-PRINT-ENGINE.
                Additional information:
                The maximum number of sheets of 20 pound paper that can
                be bound by the binding device that serves this output
                bin. If a job exceeds this number and the job has
                requested binding, cBindingError will be set in NOT-
                READY-DESTINATION-PRINT-ENGINE."
::= { outbin4 10 }
               
               
outbin4-phd OBJECT-TYPE
   SYNTAX      INTEGER
   ACCESS      read-only
   STATUS      optional
   DESCRIPTION "Provides the number of the Paper Handling Device that contains		
                this output bin.
                Additional information:
                Provides the number of the Paper Handling Device that
                contains this output bin."
::= { outbin4 11 }
               
               
outbin4-error-info OBJECT-TYPE
   SYNTAX      OCTET STRING
   ACCESS      read-only
   STATUS      optional
   DESCRIPTION "A device specific description of the last error encountered for		
                output bin 4. Each POS should document the meaning of all		
                supported error information.
                Additional information:
                This is a description of the current error state of a
                finishing device. (ie stapler). If the bin does not
                support any finishing capabilities then the object
                will return <badValue>.
                The possible return values are as follows:
                Byte1, Byte2, and Byte3 should be 0x00. as they are
                reserved for future use.
                Byte4 is a bit field that can be interpreted as
                follows:
                bit 0 - unused
                bit 1 - eBinderOut Out of staples
                bit 2 - eBinderLimit Too many pages to finish
                bit 3 - eBinderJam Staple jammed in stapler
                bit 4 - eBinderAlign Pages aren't aligned correctly to finish.
                bit 5 - unused
                bit 6 - unused
                bit 7 - unused
                NOTE: Because HP is marketing a device with a max of
                16 bins the OUTBIN-MAXIMUM-BINDING objects are 3-18 but
                the external device specification requires support of
                up to 315 output bins. Therefore if these bins exist
                above 16, then the coresponding objects will also exist
                OUTBIN19-MAXIMUM-BINDING ... OUTBIN317-MAXIMUM-BINDING"
::= { outbin4 12 }
               
               
marker-density-calibration OBJECT-TYPE
   SYNTAX      INTEGER {
		   eNotCalibrating(1),
		   eCalibrateALL(2),
		   eCalibrateColor(3),
		   eCalibrateHalftone(4),
		   eCalibrateColorPlaneRegistration(5),
		   eCalibrateDrumPhaseAdjustment(6),
		   eCalibrateGrayAxisControl(7)
		   }
   ACCESS      read-write
   STATUS      optional
   DESCRIPTION "Returns the calibration status or triggers a calibration cycle.		
                All calibration procedures are used if set to eCalibrateALL. If		
                set to eCalibrateColor then a full density engine calibration		
                is triggered. If set to eCalibrateHalftone, then a Halftone		
                calibration is triggered. If set to		
                eCalibrateColorPlaneRegistration, then a Color Plane		
                Registration calibration is triggered. If set to		
                eCalibrateDrumPhaseAdjustment, then a Drum Phase Adjustment		
                calibration is triggered.If set to eCalibrateLowSpeedColor,		
                then a Low Speed Color calibration is triggered.If set to		
                eCalibrateDrumSpeedAdjustment, then a Drum Speed Adjustment		
                calibration is triggered.If set to eCalibrateNeutrals, then a		
                Gray Axis Control calibration is triggered.
                Additional information:
                Returns the calibration status or triggers a calibration 
                cycle. All calibration procedures are used if set to
                eCalibrateALL. If set to eCalibrateColor then a full
                density engine calibration is triggered. If set to
                eCalibrateHalftone, then a Halftone calibration is triggered.
                If set to eCalibrateColorPlaneRegistration, then a Color
                Plane Registration calibration is triggered. If set to
                eCalibrateDrumPhaseAdjustment, then a Drum Phase Adjustment
                calibration is triggered. If set to eCalibrateGrayAxisControl, 
                then a Gray Axis Control calibration is triggered."
::= { settings-marking-agent 11 }
               
               
media-names-available OBJECT-TYPE
   SYNTAX      OCTET STRING
   ACCESS      read-write
   STATUS      optional
   DESCRIPTION "The value of this object controls which of the MEDIAx-NAME		
                objects are supported. If a bit is set to zero, then attempting		
                to get or set the corresponding MEDIAx-NAME objects will return		
                <noSuchName>.
                Additional information:
                Setting a bit to one will cause the corresponding
                MEDIAn- objects to be available (attempting to access
                an unavailable object will return <noSuchName>).
                MEDIA1- objects are always present, as this is the default
                media. If this object is set to a value that does not include
                cMediaName2Available, that bit will be set and a status of
                <noError> will be returned.
                PLEASE NOTE:  This object is bound to 32 bits and in some 
                products we now will support more than 32 at any given time.
                If that is the case there is a new Binary object that is now
                used called MEDIA-NAMES-ENABLED that can be used to enable 
                and disable these 32 media types as well as any beyond 
                the 32 bit boundary. So the MEDIA-NAMES-ENABLED object should
                be used in this case.  Please see the description of this
                object for further use.  Also note that disabling media type
                9 (for example) here in this collect will also disable it
                in MEDIA-NAMES-ENABLED object as they both point to the same
                values in NVRAM.  The same is true for enabling a media type.
                The only difference is that MEDIA-NAMES-ENABLED goes beyond 
                the 32 bit boundary.  This object was kept for backwards 
                compatibility.  The one issue is that the 5 user defined objects
                for some products(Like $product_str 6015) may be pushed beyond the
                32 bit boundary and this object this can not be used to enable
                or disable those media types.  This was an agreement between 
                Web Jet Admin, Testing, and firmware."
::= { settings-print-media 1 }
               
               
north-edge-offset OBJECT-TYPE
   SYNTAX      INTEGER
   ACCESS      read-write
   STATUS      optional
   DESCRIPTION "Returns or sets the number of 300 dpi dots by which the image		
                is shifted. Shift is relative to the leading edge of the medium		
                as the medium flows through the marking engine with the side to		
                be imaged facing the observer. The leading edge is the North		
                edge and the other edges are defined by the normal compass		
                layout of directions with the compass facing the observer. The		
                adjustment is for all pages printed. A positive value moves the		
                image away from the leading edge of the medium. A negative		
                value moves the image closer to the leading edge of the medium.		
                The value 0 will return the image to its factory default		
                position.
                Additional information:
                Returns or sets the number of 300 dpi dots by which the image is
                shifted.  Shift is relative to the leading edge of the medium as the
                medium flows through the marking engine with the side to be imaged
                facing the observer. The leading edge is the North edge and the
                other edges are defined by the normal compass layout of directions
                with the compass facing the ob server. The adjustment is for all
                pages printed. A positive value moves the image away from the leading
                edge of the medium. A negative value moves the image closer to the
                leading edge of the medium.  The value 0 will return the image to
                its factory default position.
                The value of this object is stored in NVRAM."
::= { settings-print-media 2 }
               
               
media-names-enabled OBJECT-TYPE
   SYNTAX      OCTET STRING (SIZE(0..63))
   ACCESS      read-write
   STATUS      optional
   DESCRIPTION "The value of this object controls whish of the MEDIAx-NAME		
                objects are supported. Of a bit is set to zero then the attempt		
                to get or set the corresponding MEDIAx-NAME objects will return		
                <noSuchName>
                Additional information:
                Setting a bit to one will cause the corresponding
                MEDIAn- objects to be available (attempting to access
                an unavailable object will return <noSuchName>).
                MEDIA1- objects are always present, as this is the default
                media. If this object is set to a value that does not include
                the 2nd bit , that bit will be set and a status of
                <noError> will be returned.
                Each bit represents a supported media type just like
                the MEDIA-NAMES-AVAILABLE object but we are now not
                limited to 32 bits. In order to understand which media type
                is associated with which bit then you must do a get on the 
                MEDIAn-NAME object for the bit number that is turned on after
                doing a get on this object.
                There is a master list of media types in the firmware and 
                each product only supports a subset of those media types.  This
                object refers to only the supported media types in that master list.
                It is important to know the master list  of supported media types 
                for your product.  In order to enable all of the supported media 
                types for $product_str 6015 GO you must send the following binary bytes of 
                data: FF FF FF FF 7F"
::= { settings-print-media 3 }
               
               
media1-name OBJECT-TYPE
   SYNTAX      OCTET STRING (SIZE(1..24))
   ACCESS      read-only
   STATUS      optional
   DESCRIPTION "Media 1 name.
                Additional information:
                The order of these objects is determined by the order of 
                SysOD_MediaTypeEnum.  The symbol set for this string is Roman-8.  "
::= { media1 1 }
               
               
media1-short-name OBJECT-TYPE
   SYNTAX      OCTET STRING (SIZE(1..9))
   ACCESS      read-only
   STATUS      optional
   DESCRIPTION "Length restricted version of the media name 1. The length		
                restriction is required to allow the media name to be displayed		
                on the device's control panel. The device POS must state the		
                maximum number of characters allowed. If the device also has a		
                limitation on what characters in a character set can be used		
                (e.g. only uppercase characters allowed), the POS should also		
                state character restrictions.
                Additional information:
                The order of these objects is determined by the order of 
                SysOD_MediaTypeEnum.  Length restricted version of the media 
                name 1.  The length restriction is required to allow the media 
                name to be displayed on the device's control panel.  
                The maximum supported string length is 9 characters. If 
                the user entered string is too long, the device will store
                the first 9 characters and will return the
                <noError> status.
                The characters must be in the range 20H to 7FH except 5C
                cannot be used. The default symbol set is Roman-8 for
                English; additional legal symbol sets are ISOLatin5,
                ISOLatin2 and Windows31J. Setting this object with characters
                outside of the range or of an illegal symbol set will cause an
                error status of <badValue> to be returned.
                This string is localized according to prtConsoleLocalization.
                If this object represents a standard type, and the user
                attempts to set the object, 'OK Nearest Legal Value Substituted'
                will be returned, and the standard value is retained.
                If this object represents a user defined type, and the user
                attempts to set the object, then the set will be successfull."
::= { media1 2 }
               
               
media1-page-count OBJECT-TYPE
   SYNTAX      INTEGER
   ACCESS      read-only
   STATUS      optional
   DESCRIPTION "Number of sheets of media 1 that have been printed. The device		
                POS should state whether this value is lost across a power		
                cycle or kept in NVRAM.
                Additional information:
                Number of sheets of media 1 that have been printed.
                This page count is saved in NVRAM after every 10 
                pages. The maximum value is 4,294,967,295 which will never be
                reached in normal operation.
                The page count is incremented when a sheet of media is pulled 
                from an input tray. A duplex printed sheet will cause this 
                counter to be incremented by one."
::= { media1 3 }
               
               
media1-engine-media-mode OBJECT-TYPE
   SYNTAX      INTEGER
   ACCESS      read-write
   STATUS      optional
   DESCRIPTION "The engine processing characteristics that are to be applied to		
                this media. The processing characteristics are device		
                specific.
                Additional information:
                Displays the engine processing characterstics that are applied
                to this media type."
::= { media1 4 }
               
               
media2-name OBJECT-TYPE
   SYNTAX      OCTET STRING (SIZE(1..24))
   ACCESS      read-only
   STATUS      optional
   DESCRIPTION "Media 2 name.
                Additional information:
                See MEDIA1-NAME."
::= { media2 1 }
               
               
media2-short-name OBJECT-TYPE
   SYNTAX      OCTET STRING (SIZE(1..9))
   ACCESS      read-only
   STATUS      optional
   DESCRIPTION "Length restricted version of the media name 2. See		
                MEDIA1-SHORT-NAME for details.
                Additional information:
                See MEDIA1-SHORT-NAME."
::= { media2 2 }
               
               
media2-page-count OBJECT-TYPE
   SYNTAX      INTEGER
   ACCESS      read-only
   STATUS      optional
   DESCRIPTION "Number of sheets of media 2 that have been printed. See		
                MEDIA1-PAGE-COUNT for details.
                Additional information:
                See MEDIA1-PAGE-COUNT."
::= { media2 3 }
               
               
media2-engine-media-mode OBJECT-TYPE
   SYNTAX      INTEGER
   ACCESS      read-write
   STATUS      optional
   DESCRIPTION "The engine processing characteristics that are to be applied to		
                this media. The processing characteristics are device		
                specific.
                Additional information:
                See the description for MEDIA1-ENGINE-MEDIA-MODE."
::= { media2 4 }
               
               
media3-name OBJECT-TYPE
   SYNTAX      OCTET STRING (SIZE(1..24))
   ACCESS      read-only
   STATUS      optional
   DESCRIPTION "Media 3 name.
                Additional information:
                See MEDIA1-NAME."
::= { media3 1 }
               
               
media3-short-name OBJECT-TYPE
   SYNTAX      OCTET STRING (SIZE(1..9))
   ACCESS      read-only
   STATUS      optional
   DESCRIPTION "Length restricted version of the media name 3. See		
                MEDIA1-SHORT-NAME for details.
                Additional information:
                See MEDIA1-SHORT-NAME."
::= { media3 2 }
               
               
media3-page-count OBJECT-TYPE
   SYNTAX      INTEGER
   ACCESS      read-only
   STATUS      optional
   DESCRIPTION "Number of sheets of media 3 that have been printed. See		
                MEDIA1-PAGE-COUNT for details.
                Additional information:
                See MEDIA1-PAGE-COUNT."
::= { media3 3 }
               
               
media3-engine-media-mode OBJECT-TYPE
   SYNTAX      INTEGER
   ACCESS      read-write
   STATUS      optional
   DESCRIPTION "The engine processing characteristics that are to be applied to		
                this media. The processing characteristics are device		
                specific.
                Additional information:
                See the description for MEDIA1-ENGINE-MEDIA-MODE."
::= { media3 4 }
               
               
media4-name OBJECT-TYPE
   SYNTAX      OCTET STRING (SIZE(1..24))
   ACCESS      read-only
   STATUS      optional
   DESCRIPTION "Media 4 name.
                Additional information:
                See MEDIA1-NAME."
::= { media4 1 }
               
               
media4-short-name OBJECT-TYPE
   SYNTAX      OCTET STRING (SIZE(1..9))
   ACCESS      read-only
   STATUS      optional
   DESCRIPTION "Length restricted version of the media name 4. See		
                MEDIA1-SHORT-NAME for details.
                Additional information:
                See MEDIA1-SHORT-NAME."
::= { media4 2 }
               
               
media4-page-count OBJECT-TYPE
   SYNTAX      INTEGER
   ACCESS      read-only
   STATUS      optional
   DESCRIPTION "Number of sheets of media 4 that have been printed. See		
                MEDIA1-PAGE-COUNT for details.
                Additional information:
                See MEDIA1-PAGE-COUNT."
::= { media4 3 }
               
               
media4-engine-media-mode OBJECT-TYPE
   SYNTAX      INTEGER
   ACCESS      read-write
   STATUS      optional
   DESCRIPTION "The engine processing characteristics that are to be applied to		
                this media. The processing characteristics are device		
                specific.
                Additional information:
                See the description for MEDIA1-ENGINE-MEDIA-MODE."
::= { media4 4 }
               
               
media5-name OBJECT-TYPE
   SYNTAX      OCTET STRING (SIZE(1..24))
   ACCESS      read-only
   STATUS      optional
   DESCRIPTION "Media 5 name.
                Additional information:
                See MEDIA1-NAME."
::= { media5 1 }
               
               
media5-short-name OBJECT-TYPE
   SYNTAX      OCTET STRING (SIZE(1..9))
   ACCESS      read-only
   STATUS      optional
   DESCRIPTION "Length restricted version of the media name 5. See		
                MEDIA1-SHORT-NAME for details.
                Additional information:
                See MEDIA1-SHORT-NAME."
::= { media5 2 }
               
               
media5-page-count OBJECT-TYPE
   SYNTAX      INTEGER
   ACCESS      read-only
   STATUS      optional
   DESCRIPTION "Number of sheets of media 5 that have been printed. See		
                MEDIA1-PAGE-COUNT for details.
                Additional information:
                See MEDIA1-PAGE-COUNT."
::= { media5 3 }
               
               
media5-engine-media-mode OBJECT-TYPE
   SYNTAX      INTEGER
   ACCESS      read-write
   STATUS      optional
   DESCRIPTION "The engine processing characteristics that are to be applied to		
                this media. The processing characteristics are device		
                specific.
                Additional information:
                See the description for MEDIA1-ENGINE-MEDIA-MODE."
::= { media5 4 }
               
               
media6-name OBJECT-TYPE
   SYNTAX      OCTET STRING (SIZE(1..24))
   ACCESS      read-only
   STATUS      optional
   DESCRIPTION "Media 6 name.
                Additional information:
                See MEDIA1-NAME."
::= { media6 1 }
               
               
media6-short-name OBJECT-TYPE
   SYNTAX      OCTET STRING (SIZE(1..9))
   ACCESS      read-only
   STATUS      optional
   DESCRIPTION "Length restricted version of the media name 6. See		
                MEDIA1-SHORT-NAME for details.
                Additional information:
                See MEDIA1-SHORT-NAME."
::= { media6 2 }
               
               
media6-page-count OBJECT-TYPE
   SYNTAX      INTEGER
   ACCESS      read-only
   STATUS      optional
   DESCRIPTION "Number of sheets of media 6 that have been printed. See		
                MEDIA1-PAGE-COUNT for details.
                Additional information:
                See MEDIA1-PAGE-COUNT."
::= { media6 3 }
               
               
media6-engine-media-mode OBJECT-TYPE
   SYNTAX      INTEGER
   ACCESS      read-write
   STATUS      optional
   DESCRIPTION "The engine processing characteristics that are to be applied to		
                this media. The processing characteristics are device		
                specific.
                Additional information:
                See the description for MEDIA1-ENGINE-MEDIA-MODE."
::= { media6 4 }
               
               
media7-name OBJECT-TYPE
   SYNTAX      OCTET STRING (SIZE(1..24))
   ACCESS      read-only
   STATUS      optional
   DESCRIPTION "Media 7 name.
                Additional information:
                See MEDIA1-NAME."
::= { media7 1 }
               
               
media7-short-name OBJECT-TYPE
   SYNTAX      OCTET STRING (SIZE(1..9))
   ACCESS      read-only
   STATUS      optional
   DESCRIPTION "Length restricted version of the media name 7. See		
                MEDIA1-SHORT-NAME for details.
                Additional information:
                See MEDIA1-SHORT-NAME."
::= { media7 2 }
               
               
media7-page-count OBJECT-TYPE
   SYNTAX      INTEGER
   ACCESS      read-only
   STATUS      optional
   DESCRIPTION "Number of sheets of media 7 that have been printed. See		
                MEDIA1-PAGE-COUNT for details.
                Additional information:
                See MEDIA1-PAGE-COUNT."
::= { media7 3 }
               
               
media7-engine-media-mode OBJECT-TYPE
   SYNTAX      INTEGER
   ACCESS      read-write
   STATUS      optional
   DESCRIPTION "The engine processing characteristics that are to be applied to		
                this media. The processing characteristics are device		
                specific.
                Additional information:
                See the description for MEDIA1-ENGINE-MEDIA-MODE."
::= { media7 4 }
               
               
media8-name OBJECT-TYPE
   SYNTAX      OCTET STRING (SIZE(1..24))
   ACCESS      read-only
   STATUS      optional
   DESCRIPTION "Media 8 name.
                Additional information:
                See MEDIA1-NAME."
::= { media8 1 }
               
               
media8-short-name OBJECT-TYPE
   SYNTAX      OCTET STRING (SIZE(1..9))
   ACCESS      read-only
   STATUS      optional
   DESCRIPTION "Length restricted version of the media name 8. See		
                MEDIA1-SHORT-NAME for details.
                Additional information:
                See MEDIA1-SHORT-NAME."
::= { media8 2 }
               
               
media8-page-count OBJECT-TYPE
   SYNTAX      INTEGER
   ACCESS      read-only
   STATUS      optional
   DESCRIPTION "Number of sheets of media 8 that have been printed. See		
                MEDIA1-PAGE-COUNT for details.
                Additional information:
                See MEDIA1-PAGE-COUNT."
::= { media8 3 }
               
               
media8-engine-media-mode OBJECT-TYPE
   SYNTAX      INTEGER
   ACCESS      read-write
   STATUS      optional
   DESCRIPTION "The engine processing characteristics that are to be applied to		
                this media. The processing characteristics are device		
                specific.
                Additional information:
                See the description for MEDIA1-ENGINE-MEDIA-MODE."
::= { media8 4 }
               
               
media9-name OBJECT-TYPE
   SYNTAX      OCTET STRING (SIZE(1..24))
   ACCESS      read-only
   STATUS      optional
   DESCRIPTION "Media 9 name.
                Additional information:
                See MEDIA1-NAME."
::= { media9 1 }
               
               
media9-short-name OBJECT-TYPE
   SYNTAX      OCTET STRING (SIZE(1..9))
   ACCESS      read-only
   STATUS      optional
   DESCRIPTION "Length restricted version of the media name 9. See		
                MEDIA1-SHORT-NAME for details.
                Additional information:
                See MEDIA1-SHORT-NAME."
::= { media9 2 }
               
               
media9-page-count OBJECT-TYPE
   SYNTAX      INTEGER
   ACCESS      read-only
   STATUS      optional
   DESCRIPTION "Number of sheets of media 9 that have been printed. See		
                MEDIA1-PAGE-COUNT for details.
                Additional information:
                See MEDIA1-PAGE-COUNT."
::= { media9 3 }
               
               
media9-engine-media-mode OBJECT-TYPE
   SYNTAX      INTEGER
   ACCESS      read-only
   STATUS      optional
   DESCRIPTION "The engine processing characteristics that are to be applied to		
                this media. The processing characteristics are device		
                specific.
                Additional information:
                See the description for MEDIA1-ENGINE-MEDIA-MODE."
::= { media9 4 }
               
               
media10-name OBJECT-TYPE
   SYNTAX      OCTET STRING (SIZE(1..24))
   ACCESS      read-only
   STATUS      optional
   DESCRIPTION "Media 10 name.
                Additional information:
                See MEDIA1-NAME."
::= { media10 1 }
               
               
media10-short-name OBJECT-TYPE
   SYNTAX      OCTET STRING (SIZE(1..9))
   ACCESS      read-only
   STATUS      optional
   DESCRIPTION "Length restricted version of the media name 10. See		
                MEDIA1-SHORT-NAME for details.
                Additional information:
                See MEDIA1-SHORT-NAME."
::= { media10 2 }
               
               
media10-page-count OBJECT-TYPE
   SYNTAX      INTEGER
   ACCESS      read-only
   STATUS      optional
   DESCRIPTION "Number of sheets of media 10 that have been printed. See		
                MEDIA1-PAGE-COUNT for details.
                Additional information:
                See MEDIA1-PAGE-COUNT."
::= { media10 3 }
               
               
media10-engine-media-mode OBJECT-TYPE
   SYNTAX      INTEGER
   ACCESS      read-write
   STATUS      optional
   DESCRIPTION "The engine processing characteristics that are to be applied to		
                this media. The processing characteristics are device		
                specific.
                Additional information:
                See the description for MEDIA1-ENGINE-MEDIA-MODE."
::= { media10 4 }
               
               
media11-name OBJECT-TYPE
   SYNTAX      OCTET STRING (SIZE(1..24))
   ACCESS      read-only
   STATUS      optional
   DESCRIPTION "Media 11 name.
                Additional information:
                See MEDIA1-NAME."
::= { media11 1 }
               
               
media11-short-name OBJECT-TYPE
   SYNTAX      OCTET STRING (SIZE(1..9))
   ACCESS      read-only
   STATUS      optional
   DESCRIPTION "Length restricted version of the media name 11. See		
                MEDIA1-SHORT-NAME for details.
                Additional information:
                See MEDIA1-SHORT-NAME."
::= { media11 2 }
               
               
media11-page-count OBJECT-TYPE
   SYNTAX      INTEGER
   ACCESS      read-only
   STATUS      optional
   DESCRIPTION "Number of sheets of media 11 that have been printed. See		
                MEDIA1-PAGE-COUNT for details.
                Additional information:
                See MEDIA1-PAGE-COUNT."
::= { media11 3 }
               
               
media11-engine-media-mode OBJECT-TYPE
   SYNTAX      INTEGER
   ACCESS      read-write
   STATUS      optional
   DESCRIPTION "The engine processing characteristics that are to be applied to		
                this media. The processing characteristics are device		
                specific.
                Additional information:
                See the description for MEDIA1-ENGINE-MEDIA-MODE."
::= { media11 4 }
               
               
media12-name OBJECT-TYPE
   SYNTAX      OCTET STRING (SIZE(1..24))
   ACCESS      read-only
   STATUS      optional
   DESCRIPTION "Media 12 name.
                Additional information:
                See MEDIA1-NAME."
::= { media12 1 }
               
               
media12-short-name OBJECT-TYPE
   SYNTAX      OCTET STRING (SIZE(1..9))
   ACCESS      read-only
   STATUS      optional
   DESCRIPTION "Length restricted version of the media name 12. See		
                MEDIA1-SHORT-NAME for details.
                Additional information:
                See MEDIA1-SHORT-NAME."
::= { media12 2 }
               
               
media12-page-count OBJECT-TYPE
   SYNTAX      INTEGER
   ACCESS      read-only
   STATUS      optional
   DESCRIPTION "Number of sheets of media 12 that have been printed. See		
                MEDIA1-PAGE-COUNT for details.
                Additional information:
                See MEDIA1-PAGE-COUNT."
::= { media12 3 }
               
               
media12-engine-media-mode OBJECT-TYPE
   SYNTAX      INTEGER
   ACCESS      read-write
   STATUS      optional
   DESCRIPTION "The engine processing characteristics that are to be applied to		
                this media. The processing characteristics are device		
                specific.
                Additional information:
                See the description for MEDIA1-ENGINE-MEDIA-MODE."
::= { media12 4 }
               
               
media13-name OBJECT-TYPE
   SYNTAX      OCTET STRING (SIZE(1..24))
   ACCESS      read-only
   STATUS      optional
   DESCRIPTION "Media 13 name.
                Additional information:
                See MEDIA1-NAME."
::= { media13 1 }
               
               
media13-short-name OBJECT-TYPE
   SYNTAX      OCTET STRING (SIZE(1..9))
   ACCESS      read-only
   STATUS      optional
   DESCRIPTION "Length restricted version of the media name 13. See		
                MEDIA1-SHORT-NAME for details.
                Additional information:
                See MEDIA1-SHORT-NAME."
::= { media13 2 }
               
               
media13-page-count OBJECT-TYPE
   SYNTAX      INTEGER
   ACCESS      read-only
   STATUS      optional
   DESCRIPTION "Number of sheets of media 13 that have been printed. See		
                MEDIA1-PAGE-COUNT for details.
                Additional information:
                See MEDIA1-PAGE-COUNT."
::= { media13 3 }
               
               
media13-engine-media-mode OBJECT-TYPE
   SYNTAX      INTEGER
   ACCESS      read-write
   STATUS      optional
   DESCRIPTION "The engine processing characteristics that are to be applied to		
                this media. The processing characteristics are device		
                specific.
                Additional information:
                See the description for MEDIA1-ENGINE-MEDIA-MODE."
::= { media13 4 }
               
               
media14-name OBJECT-TYPE
   SYNTAX      OCTET STRING (SIZE(1..24))
   ACCESS      read-only
   STATUS      optional
   DESCRIPTION "Media 14 name.
                Additional information:
                See MEDIA1-NAME."
::= { media14 1 }
               
               
media14-short-name OBJECT-TYPE
   SYNTAX      OCTET STRING (SIZE(1..9))
   ACCESS      read-only
   STATUS      optional
   DESCRIPTION "Length restricted version of the media name 14. See		
                MEDIA1-SHORT-NAME for details.
                Additional information:
                See MEDIA1-SHORT-NAME."
::= { media14 2 }
               
               
media14-page-count OBJECT-TYPE
   SYNTAX      INTEGER
   ACCESS      read-only
   STATUS      optional
   DESCRIPTION "Number of sheets of media 14 that have been printed. See		
                MEDIA1-PAGE-COUNT for details.
                Additional information:
                See MEDIA1-PAGE-COUNT."
::= { media14 3 }
               
               
media14-engine-media-mode OBJECT-TYPE
   SYNTAX      INTEGER
   ACCESS      read-write
   STATUS      optional
   DESCRIPTION "The engine processing characteristics that are to be applied to		
                this media. The processing characteristics are device		
                specific.
                Additional information:
                See the description for MEDIA1-ENGINE-MEDIA-MODE."
::= { media14 4 }
               
               
media15-name OBJECT-TYPE
   SYNTAX      OCTET STRING (SIZE(1..24))
   ACCESS      read-only
   STATUS      optional
   DESCRIPTION "Media 15 name.
                Additional information:
                See MEDIA1-NAME."
::= { media15 1 }
               
               
media15-short-name OBJECT-TYPE
   SYNTAX      OCTET STRING (SIZE(1..9))
   ACCESS      read-only
   STATUS      optional
   DESCRIPTION "Length restricted version of the media name 15. See		
                MEDIA1-SHORT-NAME for details.
                Additional information:
                See MEDIA1-SHORT-NAME."
::= { media15 2 }
               
               
media15-page-count OBJECT-TYPE
   SYNTAX      INTEGER
   ACCESS      read-only
   STATUS      optional
   DESCRIPTION "Number of sheets of media 15 that have been printed. See		
                MEDIA1-PAGE-COUNT for details.
                Additional information:
                See MEDIA1-PAGE-COUNT."
::= { media15 3 }
               
               
media15-engine-media-mode OBJECT-TYPE
   SYNTAX      INTEGER
   ACCESS      read-write
   STATUS      optional
   DESCRIPTION "The engine processing characteristics that are to be applied to		
                this media. The processing characteristics are device		
                specific.
                Additional information:
                See the description for MEDIA1-ENGINE-MEDIA-MODE."
::= { media15 4 }
               
               
media16-name OBJECT-TYPE
   SYNTAX      OCTET STRING (SIZE(1..24))
   ACCESS      read-only
   STATUS      optional
   DESCRIPTION "Media 16 name.
                Additional information:
                See MEDIA1-NAME."
::= { media16 1 }
               
               
media16-short-name OBJECT-TYPE
   SYNTAX      OCTET STRING (SIZE(1..9))
   ACCESS      read-only
   STATUS      optional
   DESCRIPTION "Length restricted version of the media name 16. See		
                MEDIA1-SHORT-NAME for details.
                Additional information:
                See MEDIA1-SHORT-NAME."
::= { media16 2 }
               
               
media16-page-count OBJECT-TYPE
   SYNTAX      INTEGER
   ACCESS      read-only
   STATUS      optional
   DESCRIPTION "Number of sheets of media 16 that have been printed. See		
                MEDIA1-PAGE-COUNT for details.
                Additional information:
                See MEDIA1-PAGE-COUNT."
::= { media16 3 }
               
               
media16-engine-media-mode OBJECT-TYPE
   SYNTAX      INTEGER
   ACCESS      read-write
   STATUS      optional
   DESCRIPTION "The engine processing characteristics that are to be applied to		
                this media. The processing characteristics are device		
                specific.
                Additional information:
                See the description for MEDIA1-ENGINE-MEDIA-MODE."
::= { media16 4 }
               
               
media17-name OBJECT-TYPE
   SYNTAX      OCTET STRING (SIZE(1..24))
   ACCESS      read-only
   STATUS      optional
   DESCRIPTION "Media 17 name.
                Additional information:
                See MEDIA1-NAME."
::= { media17 1 }
               
               
media17-short-name OBJECT-TYPE
   SYNTAX      OCTET STRING (SIZE(1..9))
   ACCESS      read-only
   STATUS      optional
   DESCRIPTION "Length restricted version of the media name 17. See		
                MEDIA1-SHORT-NAME for details.
                Additional information:
                See MEDIA1-SHORT-NAME."
::= { media17 2 }
               
               
media17-page-count OBJECT-TYPE
   SYNTAX      INTEGER
   ACCESS      read-only
   STATUS      optional
   DESCRIPTION "Number of sheets of media 17 that have been printed. See		
                MEDIA1-PAGE-COUNT for details.
                Additional information:
                See MEDIA1-PAGE-COUNT."
::= { media17 3 }
               
               
media17-engine-media-mode OBJECT-TYPE
   SYNTAX      INTEGER
   ACCESS      read-write
   STATUS      optional
   DESCRIPTION "The engine processing characteristics that are to be applied to		
                this media. The processing characteristics are device		
                specific.
                Additional information:
                See the description for MEDIA1-ENGINE-MEDIA-MODE."
::= { media17 4 }
               
               
media18-name OBJECT-TYPE
   SYNTAX      OCTET STRING (SIZE(1..24))
   ACCESS      read-only
   STATUS      optional
   DESCRIPTION "Media 18 name.
                Additional information:
                See MEDIA1-NAME."
::= { media18 1 }
               
               
media18-short-name OBJECT-TYPE
   SYNTAX      OCTET STRING (SIZE(1..9))
   ACCESS      read-only
   STATUS      optional
   DESCRIPTION "Length restricted version of the media name 18. See		
                MEDIA1-SHORT-NAME for details.
                Additional information:
                See MEDIA1-SHORT-NAME."
::= { media18 2 }
               
               
media18-page-count OBJECT-TYPE
   SYNTAX      INTEGER
   ACCESS      read-only
   STATUS      optional
   DESCRIPTION "Number of sheets of media 18 that have been printed. See		
                MEDIA1-PAGE-COUNT for details.
                Additional information:
                See MEDIA1-PAGE-COUNT."
::= { media18 3 }
               
               
media18-engine-media-mode OBJECT-TYPE
   SYNTAX      INTEGER
   ACCESS      read-write
   STATUS      optional
   DESCRIPTION "The engine processing characteristics that are to be applied to		
                this media. The processing characteristics are device		
                specific.
                Additional information:
                See the description for MEDIA1-ENGINE-MEDIA-MODE."
::= { media18 4 }
               
               
media19-name OBJECT-TYPE
   SYNTAX      OCTET STRING (SIZE(1..24))
   ACCESS      read-only
   STATUS      optional
   DESCRIPTION "Media 19 name.
                Additional information:
                See MEDIA1-NAME."
::= { media19 1 }
               
               
media19-short-name OBJECT-TYPE
   SYNTAX      OCTET STRING (SIZE(1..9))
   ACCESS      read-only
   STATUS      optional
   DESCRIPTION "Length restricted version of the media name 19. See		
                MEDIA1-SHORT-NAME for details.
                Additional information:
                See MEDIA1-SHORT-NAME."
::= { media19 2 }
               
               
media19-page-count OBJECT-TYPE
   SYNTAX      INTEGER
   ACCESS      read-only
   STATUS      optional
   DESCRIPTION "Number of sheets of media 19 that have been printed. See		
                MEDIA1-PAGE-COUNT for details.
                Additional information:
                See MEDIA1-PAGE-COUNT."
::= { media19 3 }
               
               
media19-engine-media-mode OBJECT-TYPE
   SYNTAX      INTEGER
   ACCESS      read-write
   STATUS      optional
   DESCRIPTION "The engine processing characteristics that are to be applied to		
                this media. The processing characteristics are device		
                specific.
                Additional information:
                See the description for MEDIA1-ENGINE-MEDIA-MODE."
::= { media19 4 }
               
               
media20-name OBJECT-TYPE
   SYNTAX      OCTET STRING (SIZE(1..24))
   ACCESS      read-only
   STATUS      optional
   DESCRIPTION "Media 20 name.
                Additional information:
                See MEDIA1-NAME."
::= { media20 1 }
               
               
media20-short-name OBJECT-TYPE
   SYNTAX      OCTET STRING (SIZE(1..9))
   ACCESS      read-only
   STATUS      optional
   DESCRIPTION "Length restricted version of the media name 20. See		
                MEDIA1-SHORT-NAME for details.
                Additional information:
                See MEDIA1-SHORT-NAME."
::= { media20 2 }
               
               
media20-page-count OBJECT-TYPE
   SYNTAX      INTEGER
   ACCESS      read-only
   STATUS      optional
   DESCRIPTION "Number of sheets of media 20 that have been printed. See		
                MEDIA1-PAGE-COUNT for details.
                Additional information:
                See MEDIA1-PAGE-COUNT."
::= { media20 3 }
               
               
media20-engine-media-mode OBJECT-TYPE
   SYNTAX      INTEGER
   ACCESS      read-write
   STATUS      optional
   DESCRIPTION "The engine processing characteristics that are to be applied to		
                this media. The processing characteristics are device		
                specific.
                Additional information:
                See the description for MEDIA1-ENGINE-MEDIA-MODE."
::= { media20 4 }
               
               
media21-name OBJECT-TYPE
   SYNTAX      OCTET STRING (SIZE(1..24))
   ACCESS      read-only
   STATUS      optional
   DESCRIPTION "Media 21 name.
                Additional information:
                See MEDIA1-NAME."
::= { media21 1 }
               
               
media21-short-name OBJECT-TYPE
   SYNTAX      OCTET STRING (SIZE(1..9))
   ACCESS      read-only
   STATUS      optional
   DESCRIPTION "Length restricted version of the media name 21. See		
                MEDIA1-SHORT-NAME for details.
                Additional information:
                See MEDIA1-SHORT-NAME."
::= { media21 2 }
               
               
media21-page-count OBJECT-TYPE
   SYNTAX      INTEGER
   ACCESS      read-only
   STATUS      optional
   DESCRIPTION "Number of sheets of media 21 that have been printed. See		
                MEDIA1-PAGE-COUNT for details.
                Additional information:
                See MEDIA1-PAGE-COUNT."
::= { media21 3 }
               
               
media21-engine-media-mode OBJECT-TYPE
   SYNTAX      INTEGER
   ACCESS      read-write
   STATUS      optional
   DESCRIPTION "The engine processing characteristics that are to be applied to		
                this media. The processing characteristics are device		
                specific.
                Additional information:
                See the description for MEDIA1-ENGINE-MEDIA-MODE."
::= { media21 4 }
               
               
media22-name OBJECT-TYPE
   SYNTAX      OCTET STRING (SIZE(1..24))
   ACCESS      read-only
   STATUS      optional
   DESCRIPTION "Media 22 name.
                Additional information:
                See MEDIA1-NAME."
::= { media22 1 }
               
               
media22-short-name OBJECT-TYPE
   SYNTAX      OCTET STRING (SIZE(1..9))
   ACCESS      read-only
   STATUS      optional
   DESCRIPTION "Length restricted version of the media name 22. See		
                MEDIA1-SHORT-NAME for details.
                Additional information:
                See MEDIA1-SHORT-NAME."
::= { media22 2 }
               
               
media22-page-count OBJECT-TYPE
   SYNTAX      INTEGER
   ACCESS      read-only
   STATUS      optional
   DESCRIPTION "Number of sheets of media 22 that have been printed. See		
                MEDIA1-PAGE-COUNT for details.
                Additional information:
                See MEDIA1-PAGE-COUNT."
::= { media22 3 }
               
               
media22-engine-media-mode OBJECT-TYPE
   SYNTAX      INTEGER
   ACCESS      read-write
   STATUS      optional
   DESCRIPTION "The engine processing characteristics that are to be applied to		
                this media. The processing characteristics are device		
                specific.
                Additional information:
                See the description for MEDIA1-ENGINE-MEDIA-MODE."
::= { media22 4 }
               
               
media23-name OBJECT-TYPE
   SYNTAX      OCTET STRING (SIZE(1..24))
   ACCESS      read-only
   STATUS      optional
   DESCRIPTION "Media 23 name.
                Additional information:
                See MEDIA1-NAME."
::= { media23 1 }
               
               
media23-short-name OBJECT-TYPE
   SYNTAX      OCTET STRING (SIZE(1..9))
   ACCESS      read-only
   STATUS      optional
   DESCRIPTION "Length restricted version of the media name 23. See		
                MEDIA1-SHORT-NAME for details.
                Additional information:
                See MEDIA1-SHORT-NAME."
::= { media23 2 }
               
               
media23-page-count OBJECT-TYPE
   SYNTAX      INTEGER
   ACCESS      read-only
   STATUS      optional
   DESCRIPTION "Number of sheets of media 23 that have been printed. See		
                MEDIA1-PAGE-COUNT for details.
                Additional information:
                See MEDIA1-PAGE-COUNT."
::= { media23 3 }
               
               
media23-engine-media-mode OBJECT-TYPE
   SYNTAX      INTEGER
   ACCESS      read-write
   STATUS      optional
   DESCRIPTION "The engine processing characteristics that are to be applied to		
                this media. The processing characteristics are device		
                specific.
                Additional information:
                See the description for MEDIA1-ENGINE-MEDIA-MODE."
::= { media23 4 }
               
               
media24-name OBJECT-TYPE
   SYNTAX      OCTET STRING (SIZE(1..24))
   ACCESS      read-only
   STATUS      optional
   DESCRIPTION "Media 24 name.
                Additional information:
                See MEDIA1-NAME."
::= { media24 1 }
               
               
media24-short-name OBJECT-TYPE
   SYNTAX      OCTET STRING (SIZE(1..9))
   ACCESS      read-only
   STATUS      optional
   DESCRIPTION "Length restricted version of the media name 24. See		
                MEDIA1-SHORT-NAME for details.
                Additional information:
                See MEDIA1-SHORT-NAME."
::= { media24 2 }
               
               
media24-page-count OBJECT-TYPE
   SYNTAX      INTEGER
   ACCESS      read-only
   STATUS      optional
   DESCRIPTION "Number of sheets of media 24 that have been printed. See		
                MEDIA1-PAGE-COUNT for details.
                Additional information:
                See MEDIA1-PAGE-COUNT."
::= { media24 3 }
               
               
media24-engine-media-mode OBJECT-TYPE
   SYNTAX      INTEGER
   ACCESS      read-only
   STATUS      optional
   DESCRIPTION "The engine processing characteristics that are to be applied to		
                this media. The processing characteristics are device		
                specific.
                Additional information:
                See the description for MEDIA1-ENGINE-MEDIA-MODE."
::= { media24 4 }
               
               
media25-name OBJECT-TYPE
   SYNTAX      OCTET STRING (SIZE(1..24))
   ACCESS      read-only
   STATUS      optional
   DESCRIPTION "Media 25 name.
                Additional information:
                See MEDIA1-NAME."
::= { media25 1 }
               
               
media25-short-name OBJECT-TYPE
   SYNTAX      OCTET STRING (SIZE(1..9))
   ACCESS      read-only
   STATUS      optional
   DESCRIPTION "Length restricted version of the media name 25. See		
                MEDIA1-SHORT-NAME for details.
                Additional information:
                See MEDIA1-SHORT-NAME."
::= { media25 2 }
               
               
media25-page-count OBJECT-TYPE
   SYNTAX      INTEGER
   ACCESS      read-only
   STATUS      optional
   DESCRIPTION "Number of sheets of media 25 that have been printed. See		
                MEDIA1-PAGE-COUNT for details.
                Additional information:
                See MEDIA1-PAGE-COUNT."
::= { media25 3 }
               
               
media25-engine-media-mode OBJECT-TYPE
   SYNTAX      INTEGER
   ACCESS      read-only
   STATUS      optional
   DESCRIPTION "The engine processing characteristics that are to be applied to		
                this media. The processing characteristics are device		
                specific.
                Additional information:
                See the description for MEDIA1-ENGINE-MEDIA-MODE."
::= { media25 4 }
               
               
media26-name OBJECT-TYPE
   SYNTAX      OCTET STRING (SIZE(1..24))
   ACCESS      read-only
   STATUS      optional
   DESCRIPTION "Media 26 name.
                Additional information:
                See MEDIA1-NAME."
::= { media26 1 }
               
               
media26-short-name OBJECT-TYPE
   SYNTAX      OCTET STRING (SIZE(1..9))
   ACCESS      read-only
   STATUS      optional
   DESCRIPTION "Length restricted version of the media name 26. See		
                MEDIA1-SHORT-NAME for details.
                Additional information:
                See MEDIA1-SHORT-NAME."
::= { media26 2 }
               
               
media26-page-count OBJECT-TYPE
   SYNTAX      INTEGER
   ACCESS      read-only
   STATUS      optional
   DESCRIPTION "Number of sheets of media 26 that have been printed. See		
                MEDIA1-PAGE-COUNT for details.
                Additional information:
                See MEDIA1-PAGE-COUNT."
::= { media26 3 }
               
               
media26-engine-media-mode OBJECT-TYPE
   SYNTAX      INTEGER
   ACCESS      read-only
   STATUS      optional
   DESCRIPTION "The engine processing characteristics that are to be applied to		
                this media. The processing characteristics are device		
                specific.
                Additional information:
                See the description for MEDIA1-ENGINE-MEDIA-MODE."
::= { media26 4 }
               
               
media27-name OBJECT-TYPE
   SYNTAX      OCTET STRING (SIZE(1..24))
   ACCESS      read-only
   STATUS      optional
   DESCRIPTION "Media 27 name.
                Additional information:
                See MEDIA1-NAME."
::= { media27 1 }
               
               
media27-short-name OBJECT-TYPE
   SYNTAX      OCTET STRING (SIZE(1..9))
   ACCESS      read-only
   STATUS      optional
   DESCRIPTION "Length restricted version of the media name 27. See		
                MEDIA1-SHORT-NAME for details.
                Additional information:
                See MEDIA1-SHORT-NAME."
::= { media27 2 }
               
               
media27-page-count OBJECT-TYPE
   SYNTAX      INTEGER
   ACCESS      read-only
   STATUS      optional
   DESCRIPTION "Number of sheets of media 27 that have been printed. See		
                MEDIA1-PAGE-COUNT for details.
                Additional information:
                See MEDIA1-PAGE-COUNT."
::= { media27 3 }
               
               
media27-engine-media-mode OBJECT-TYPE
   SYNTAX      INTEGER
   ACCESS      read-only
   STATUS      optional
   DESCRIPTION "The engine processing characteristics that are to be applied to		
                this media. The processing characteristics are device		
                specific.
                Additional information:
                See the description for MEDIA1-ENGINE-MEDIA-MODE."
::= { media27 4 }
               
               
media28-name OBJECT-TYPE
   SYNTAX      OCTET STRING (SIZE(1..24))
   ACCESS      read-only
   STATUS      optional
   DESCRIPTION "Media 28 name.
                Additional information:
                See MEDIA1-NAME."
::= { media28 1 }
               
               
media28-short-name OBJECT-TYPE
   SYNTAX      OCTET STRING (SIZE(1..9))
   ACCESS      read-only
   STATUS      optional
   DESCRIPTION "Length restricted version of the media name 28. See		
                MEDIA1-SHORT-NAME for details.
                Additional information:
                See MEDIA1-SHORT-NAME."
::= { media28 2 }
               
               
media28-page-count OBJECT-TYPE
   SYNTAX      INTEGER
   ACCESS      read-only
   STATUS      optional
   DESCRIPTION "Number of sheets of media 28 that have been printed. See		
                MEDIA1-PAGE-COUNT for details.
                Additional information:
                See MEDIA1-PAGE-COUNT."
::= { media28 3 }
               
               
media28-engine-media-mode OBJECT-TYPE
   SYNTAX      INTEGER
   ACCESS      read-only
   STATUS      optional
   DESCRIPTION "The engine processing characteristics that are to be applied to		
                this media. The processing characteristics are device		
                specific.
                Additional information:
                See the description for MEDIA1-ENGINE-MEDIA-MODE."
::= { media28 4 }
               
               
media29-name OBJECT-TYPE
   SYNTAX      OCTET STRING (SIZE(1..24))
   ACCESS      read-only
   STATUS      optional
   DESCRIPTION "Media 29 name.
                Additional information:
                See MEDIA1-NAME."
::= { media29 1 }
               
               
media29-short-name OBJECT-TYPE
   SYNTAX      OCTET STRING (SIZE(1..9))
   ACCESS      read-only
   STATUS      optional
   DESCRIPTION "Length restricted version of the media name 29. See		
                MEDIA1-SHORT-NAME for details.
                Additional information:
                See MEDIA1-SHORT-NAME."
::= { media29 2 }
               
               
media29-page-count OBJECT-TYPE
   SYNTAX      INTEGER
   ACCESS      read-only
   STATUS      optional
   DESCRIPTION "Number of sheets of media 29 that have been printed. See		
                MEDIA1-PAGE-COUNT for details.
                Additional information:
                See MEDIA1-PAGE-COUNT."
::= { media29 3 }
               
               
media29-engine-media-mode OBJECT-TYPE
   SYNTAX      INTEGER
   ACCESS      read-only
   STATUS      optional
   DESCRIPTION "The engine processing characteristics that are to be applied to		
                this media. The processing characteristics are device		
                specific.
                Additional information:
                See the description for MEDIA1-ENGINE-MEDIA-MODE."
::= { media29 4 }
               
               
media30-name OBJECT-TYPE
   SYNTAX      OCTET STRING (SIZE(1..24))
   ACCESS      read-only
   STATUS      optional
   DESCRIPTION "Media 30 name.
                Additional information:
                See MEDIA1-NAME."
::= { media30 1 }
               
               
media30-short-name OBJECT-TYPE
   SYNTAX      OCTET STRING (SIZE(1..9))
   ACCESS      read-only
   STATUS      optional
   DESCRIPTION "Length restricted version of the media name 30. See		
                MEDIA1-SHORT-NAME for details.
                Additional information:
                See MEDIA1-SHORT-NAME."
::= { media30 2 }
               
               
media30-page-count OBJECT-TYPE
   SYNTAX      INTEGER
   ACCESS      read-only
   STATUS      optional
   DESCRIPTION "Number of sheets of media 30 that have been printed. See		
                MEDIA1-PAGE-COUNT for details.
                Additional information:
                See MEDIA1-PAGE-COUNT."
::= { media30 3 }
               
               
media30-engine-media-mode OBJECT-TYPE
   SYNTAX      INTEGER
   ACCESS      read-only
   STATUS      optional
   DESCRIPTION "The engine processing characteristics that are to be applied to		
                this media. The processing characteristics are device		
                specific.
                Additional information:
                See the description for MEDIA1-ENGINE-MEDIA-MODE."
::= { media30 4 }
               
               
media31-name OBJECT-TYPE
   SYNTAX      OCTET STRING (SIZE(1..24))
   ACCESS      read-only
   STATUS      optional
   DESCRIPTION "Media 31 name.
                Additional information:
                See MEDIA1-NAME."
::= { media31 1 }
               
               
media31-short-name OBJECT-TYPE
   SYNTAX      OCTET STRING (SIZE(1..9))
   ACCESS      read-only
   STATUS      optional
   DESCRIPTION "Length restricted version of the media name 31. See		
                MEDIA1-SHORT-NAME for details.
                Additional information:
                See MEDIA1-SHORT-NAME."
::= { media31 2 }
               
               
media31-page-count OBJECT-TYPE
   SYNTAX      INTEGER
   ACCESS      read-only
   STATUS      optional
   DESCRIPTION "Number of sheets of media 31 that have been printed. See		
                MEDIA1-PAGE-COUNT for details.
                Additional information:
                See MEDIA1-PAGE-COUNT."
::= { media31 3 }
               
               
media31-engine-media-mode OBJECT-TYPE
   SYNTAX      INTEGER
   ACCESS      read-only
   STATUS      optional
   DESCRIPTION "The engine processing characteristics that are to be applied to		
                this media. The processing characteristics are device		
                specific.
                Additional information:
                See the description for MEDIA1-ENGINE-MEDIA-MODE."
::= { media31 4 }
               
               
media32-name OBJECT-TYPE
   SYNTAX      OCTET STRING (SIZE(1..24))
   ACCESS      read-only
   STATUS      optional
   DESCRIPTION "Media 32 name.
                Additional information:
                See MEDIA1-NAME."
::= { media32 1 }
               
               
media32-short-name OBJECT-TYPE
   SYNTAX      OCTET STRING (SIZE(1..9))
   ACCESS      read-only
   STATUS      optional
   DESCRIPTION "Length restricted version of the media name 32. See		
                MEDIA1-SHORT-NAME for details.
                Additional information:
                See MEDIA1-SHORT-NAME."
::= { media32 2 }
               
               
media32-page-count OBJECT-TYPE
   SYNTAX      INTEGER
   ACCESS      read-only
   STATUS      optional
   DESCRIPTION "Number of sheets of media 32 that have been printed. See		
                MEDIA1-PAGE-COUNT for details.
                Additional information:
                See MEDIA1-PAGE-COUNT."
::= { media32 3 }
               
               
media32-engine-media-mode OBJECT-TYPE
   SYNTAX      INTEGER
   ACCESS      read-only
   STATUS      optional
   DESCRIPTION "The engine processing characteristics that are to be applied to		
                this media. The processing characteristics are device		
                specific.
                Additional information:
                See the description for MEDIA1-ENGINE-MEDIA-MODE."
::= { media32 4 }
               
               
media33-name OBJECT-TYPE
   SYNTAX      OCTET STRING (SIZE(1..24))
   ACCESS      read-only
   STATUS      optional
   DESCRIPTION "Media 3 name.
                Additional information:
                See MEDIA1-NAME."
::= { media33 1 }
               
               
media33-short-name OBJECT-TYPE
   SYNTAX      OCTET STRING (SIZE(1..9))
   ACCESS      read-only
   STATUS      optional
   DESCRIPTION "Length restricted version of the media name 3. See		
                MEDIA1-SHORT-NAME for details.
                Additional information:
                See MEDIA1-SHORT-NAME."
::= { media33 2 }
               
               
media33-page-count OBJECT-TYPE
   SYNTAX      INTEGER
   ACCESS      read-only
   STATUS      optional
   DESCRIPTION "Number of sheets of media 3 that have been printed. See		
                MEDIA1-PAGE-COUNT for details.
                Additional information:
                See MEDIA1-PAGE-COUNT."
::= { media33 3 }
               
               
media33-engine-media-mode OBJECT-TYPE
   SYNTAX      INTEGER
   ACCESS      read-write
   STATUS      optional
   DESCRIPTION "The engine processing characteristics that are to be applied to		
                this media. The processing characteristics are device		
                specific.
                Additional information:
                See the description for MEDIA1-ENGINE-MEDIA-MODE."
::= { media33 4 }
               
               
media34-name OBJECT-TYPE
   SYNTAX      OCTET STRING (SIZE(1..24))
   ACCESS      read-only
   STATUS      optional
   DESCRIPTION "Media 3 name.
                Additional information:
                See MEDIA1-NAME."
::= { media34 1 }
               
               
media34-short-name OBJECT-TYPE
   SYNTAX      OCTET STRING (SIZE(1..9))
   ACCESS      read-only
   STATUS      optional
   DESCRIPTION "Length restricted version of the media name 3. See		
                MEDIA1-SHORT-NAME for details.
                Additional information:
                See MEDIA1-SHORT-NAME."
::= { media34 2 }
               
               
media34-page-count OBJECT-TYPE
   SYNTAX      INTEGER
   ACCESS      read-only
   STATUS      optional
   DESCRIPTION "Number of sheets of media 3 that have been printed. See		
                MEDIA1-PAGE-COUNT for details.
                Additional information:
                See MEDIA1-PAGE-COUNT."
::= { media34 3 }
               
               
media34-engine-media-mode OBJECT-TYPE
   SYNTAX      INTEGER
   ACCESS      read-write
   STATUS      optional
   DESCRIPTION "The engine processing characteristics that are to be applied to		
                this media. The processing characteristics are device		
                specific.
                Additional information:
                See the description for MEDIA1-ENGINE-MEDIA-MODE."
::= { media34 4 }
               
               
media35-name OBJECT-TYPE
   SYNTAX      OCTET STRING (SIZE(1..54))
   ACCESS      read-write
   STATUS      optional
   DESCRIPTION "Media 3 name.
                Additional information:
                See MEDIA1-NAME."
::= { media35 1 }
               
               
media35-short-name OBJECT-TYPE
   SYNTAX      OCTET STRING (SIZE(1..36))
   ACCESS      read-write
   STATUS      optional
   DESCRIPTION "Length restricted version of the media name 3. See		
                MEDIA1-SHORT-NAME for details.
                Additional information:
                See MEDIA1-SHORT-NAME."
::= { media35 2 }
               
               
media35-page-count OBJECT-TYPE
   SYNTAX      INTEGER
   ACCESS      read-only
   STATUS      optional
   DESCRIPTION "Number of sheets of media 3 that have been printed. See		
                MEDIA1-PAGE-COUNT for details.
                Additional information:
                See MEDIA1-PAGE-COUNT."
::= { media35 3 }
               
               
media35-engine-media-mode OBJECT-TYPE
   SYNTAX      INTEGER
   ACCESS      read-write
   STATUS      optional
   DESCRIPTION "The engine processing characteristics that are to be applied to		
                this media. The processing characteristics are device		
                specific.
                Additional information:
                See the description for MEDIA1-ENGINE-MEDIA-MODE."
::= { media35 4 }
               
               
media36-name OBJECT-TYPE
   SYNTAX      OCTET STRING (SIZE(1..54))
   ACCESS      read-write
   STATUS      optional
   DESCRIPTION "Media 3 name.
                Additional information:
                See MEDIA1-NAME."
::= { media36 1 }
               
               
media36-short-name OBJECT-TYPE
   SYNTAX      OCTET STRING (SIZE(1..36))
   ACCESS      read-write
   STATUS      optional
   DESCRIPTION "Length restricted version of the media name 3. See		
                MEDIA1-SHORT-NAME for details.
                Additional information:
                See MEDIA1-SHORT-NAME."
::= { media36 2 }
               
               
media36-page-count OBJECT-TYPE
   SYNTAX      INTEGER
   ACCESS      read-only
   STATUS      optional
   DESCRIPTION "Number of sheets of media 3 that have been printed. See		
                MEDIA1-PAGE-COUNT for details.
                Additional information:
                See MEDIA1-PAGE-COUNT."
::= { media36 3 }
               
               
media36-engine-media-mode OBJECT-TYPE
   SYNTAX      INTEGER
   ACCESS      read-write
   STATUS      optional
   DESCRIPTION "The engine processing characteristics that are to be applied to		
                this media. The processing characteristics are device		
                specific.
                Additional information:
                See the description for MEDIA1-ENGINE-MEDIA-MODE."
::= { media36 4 }
               
               
media37-name OBJECT-TYPE
   SYNTAX      OCTET STRING (SIZE(1..54))
   ACCESS      read-write
   STATUS      optional
   DESCRIPTION "Media 3 name.
                Additional information:
                See MEDIA1-NAME."
::= { media37 1 }
               
               
media37-short-name OBJECT-TYPE
   SYNTAX      OCTET STRING (SIZE(1..36))
   ACCESS      read-write
   STATUS      optional
   DESCRIPTION "Length restricted version of the media name 3. See		
                MEDIA1-SHORT-NAME for details.
                Additional information:
                See MEDIA1-SHORT-NAME."
::= { media37 2 }
               
               
media37-page-count OBJECT-TYPE
   SYNTAX      INTEGER
   ACCESS      read-only
   STATUS      optional
   DESCRIPTION "Number of sheets of media 3 that have been printed. See		
                MEDIA1-PAGE-COUNT for details.
                Additional information:
                See MEDIA1-PAGE-COUNT."
::= { media37 3 }
               
               
media37-engine-media-mode OBJECT-TYPE
   SYNTAX      INTEGER
   ACCESS      read-write
   STATUS      optional
   DESCRIPTION "The engine processing characteristics that are to be applied to		
                this media. The processing characteristics are device		
                specific.
                Additional information:
                See the description for MEDIA1-ENGINE-MEDIA-MODE."
::= { media37 4 }
               
               
media38-name OBJECT-TYPE
   SYNTAX      OCTET STRING (SIZE(1..54))
   ACCESS      read-write
   STATUS      optional
   DESCRIPTION "Media 3 name.
                Additional information:
                See MEDIA1-NAME."
::= { media38 1 }
               
               
media38-short-name OBJECT-TYPE
   SYNTAX      OCTET STRING (SIZE(1..36))
   ACCESS      read-write
   STATUS      optional
   DESCRIPTION "Length restricted version of the media name 3. See		
                MEDIA1-SHORT-NAME for details.
                Additional information:
                See MEDIA1-SHORT-NAME."
::= { media38 2 }
               
               
media38-page-count OBJECT-TYPE
   SYNTAX      INTEGER
   ACCESS      read-only
   STATUS      optional
   DESCRIPTION "Number of sheets of media 3 that have been printed. See		
                MEDIA1-PAGE-COUNT for details.
                Additional information:
                See MEDIA1-PAGE-COUNT."
::= { media38 3 }
               
               
media38-engine-media-mode OBJECT-TYPE
   SYNTAX      INTEGER
   ACCESS      read-write
   STATUS      optional
   DESCRIPTION "The engine processing characteristics that are to be applied to		
                this media. The processing characteristics are device		
                specific.
                Additional information:
                See the description for MEDIA1-ENGINE-MEDIA-MODE."
::= { media38 4 }
               
               
media39-name OBJECT-TYPE
   SYNTAX      OCTET STRING (SIZE(1..54))
   ACCESS      read-write
   STATUS      optional
   DESCRIPTION "Media 3 name.
                Additional information:
                See MEDIA1-NAME."
::= { media39 1 }
               
               
media39-short-name OBJECT-TYPE
   SYNTAX      OCTET STRING (SIZE(1..36))
   ACCESS      read-write
   STATUS      optional
   DESCRIPTION "Length restricted version of the media name 3. See		
                MEDIA1-SHORT-NAME for details.
                Additional information:
                See MEDIA1-SHORT-NAME."
::= { media39 2 }
               
               
media39-page-count OBJECT-TYPE
   SYNTAX      INTEGER
   ACCESS      read-only
   STATUS      optional
   DESCRIPTION "Number of sheets of media 3 that have been printed. See		
                MEDIA1-PAGE-COUNT for details.
                Additional information:
                See MEDIA1-PAGE-COUNT."
::= { media39 3 }
               
               
media39-engine-media-mode OBJECT-TYPE
   SYNTAX      INTEGER
   ACCESS      read-write
   STATUS      optional
   DESCRIPTION "The engine processing characteristics that are to be applied to		
                this media. The processing characteristics are device		
                specific.
                Additional information:
                See the description for MEDIA1-ENGINE-MEDIA-MODE."
::= { media39 4 }
               
               
engine-media-modes-supported1 OBJECT-TYPE
   SYNTAX      OCTET STRING
   ACCESS      read-only
   STATUS      optional
   DESCRIPTION "The list of engine media modes supported by the device. The		
                modes are each separated by a comma character. An example		
                string would be: 'Normal,Rough,Low,Vellum'.
                Additional information:
                The list of engine media modes supported by the device. 
                The modes are each separated by a comma character. An
                example string would be: 'Normal,Rough,Low,Vellum'."
::= { media-modes 1 }
               
               
media-number-of-type-supported OBJECT-TYPE
   SYNTAX      INTEGER
   ACCESS      read-only
   STATUS      optional
   DESCRIPTION "Indicates the maximum number of supported media types.
                Additional information:
                Indicates the number of supported media type.
                This also indicates which bit in
                MEDIA-NAMES-AVAILABLE is significant"
::= { media-types 1 }
               
               
non-assured-oht-page-count OBJECT-TYPE
   SYNTAX      INTEGER
   ACCESS      read-only
   STATUS      optional
   DESCRIPTION "This is a count of the number of invalid (non-HP Laser Jet)		
                transparencies that have been printed on. This value is		
                incremented every time an invalid OHT is printed on It is reset		
                whenever the fuser count is set to 0.
                Additional information:
                This is a count of the number of invalid (non HP Laser Jet)
                transparencies that have been printed on. This value is
                incremented every time an invalid OHT is printed on. It is reset
                whenever the fuser count is set to 0."
::= { media-counts 1 }
               
               
media-size-west-edge-first-side-offset OBJECT-TYPE
   SYNTAX      INTEGER
   ACCESS      read-write
   STATUS      optional
   DESCRIPTION "Returns or sets the number of 300 dpi dots by which the image		
                is shifted relative to the west edge of the medium (see		
                NORTH-EDGE-OFFSET). The adjustment is for the first printed		
                side of the medium only. A positive value moves the image away		
                from the west edge of the medium. A negative value moves the		
                image closer to the west edge of the medium. The value 0 will		
                return the image to its factory default position.
                Additional information:
                Returns or sets the number of 300 dpi dots by which the
                image is shifted relative to the west edge of the medium
                (see NORTH-EDGE-OFFSET). The adjustment is for the
                first printed side of the medium only. A positive value
                moves the image away from the west edge of the medium.
                A negative value moves the image closer to the west edge
                of the medium. The value 0 will return the image to its
                factory default position.
                The values in the sub array index are from the media size table
                in the hpmib. This adjustment is done on a paper size by paper
                size basis. The standard PCL5 codes for paper size are used for
                the value used in the OID. Please see S_ARRAY_SUB1 for legal "
::= { media-size 2 }
               
               
media-size-west-edge-second-side-offset OBJECT-TYPE
   SYNTAX      INTEGER
   ACCESS      read-write
   STATUS      optional
   DESCRIPTION "Returns or sets the number of 300 dpi dots by which the image		
                is shifted relative to the west edge of the medium (see		
                NORTH-EDGE-OFFSET). The adjustment is for the second printed		
                side of the medium only. A positive value moves the image away		
                from the west edge of the medium. A negative value moves the		
                image closer to the west edge of the medium. The value 0 will		
                return the image to its factory default position.
                Additional information:
                Returns or sets the number of 300 dpi dots by which the
                image is shifted relative to the west edge of the medium
                (see NORTH-EDGE-OFFSET). The adjustment is for the
                second printed side of the medium only. A positive value
                moves the image away from the west edge of the medium.
                A negative value moves the image closer to the west edge
                of the medium. The value 0 will return the image to its
                factory default position. The values in the sub array index
                are from the media size table in the hpmib.
                This adjustment is done on a paper size by paper size basis.
                The standard PCL5 codes for paper size are used for the value
                used in the OID. Please see S_ARRAY_SUB1 for legal values.
                The data for this object is stored in NVRAM."
::= { media-size 3 }
               
               
media-size-west-edge-side-offset-by-tray OBJECT-TYPE
   SYNTAX      INTEGER
   ACCESS      read-write
   STATUS      optional
   DESCRIPTION "Returns or sets the number of 300 dpi dots by which the image		
                is shifted relative to the west edge of the medium (see		
                NORTH-EDGE-OFFSET). A positive value moves the image away from		
                the west edge of the medium. A negative value moves the image		
                closer to the west edge of the medium. The value 0 will return		
                the image to its factory default position. Each OID binding		
                corresponds to a valid tray number for this product. There can		
                be a maximum of 15 trays, a combination of internal and		
                external trays. Products that support other combinations of		
                trays will specify this information in the device pos. The data		
                for this object is stored in NVRAM.
                Additional information:
                Returns or sets the number of 300 dpi dots by which the
                image is shifted relative to the west edge of the medium
                (see NORTH-EDGE-OFFSET). A positive value moves the
                image away from the west edge of the medium. A negative
                value moves the image closer to the west edge of the medium.
                The value 0 will return the image to its factory default
                position.
                
                Each OID binding corresponds to a valid tray number
                for this product. There can be a maximum of 15 trays, a
                combination of internal and external trays. Products that
                support other combinations of trays will specify this
                information in the device pos. The data for this object
                is stored in NVRAM."
::= { media-size 4 }
               
               
color-supply-out-action OBJECT-TYPE
   SYNTAX      INTEGER {
		   eStop(1),
		   eAutoContinueBlack(2)
		   }
   ACCESS      read-write
   STATUS      optional
   DESCRIPTION "This PML object can be used to change the behavior of the		
                printer when a Color Cartridge reaches OUT. When this PML		
                Object is set to eStop, the printer will be offline when a		
                Color Cartridge reaches OUT. When this PML object is set to		
                eAutoContinueBlack, then the printer will continue printing in		
                Mono provided the Black cartridge has not reached OUT.
                Additional information:
                This corresponds to the menu setting 'Color Supply Out'.This
                object can be changed by the control panel or by the PJL
                variable. It can have any of the following enumerated values-
                eStop(1), eAutoContinueBlack(2). "
::= { settings-system 34 }
               
               
control-panel-supplies-status-message OBJECT-TYPE
   SYNTAX      INTEGER {
		   eShow(1),
		   eDontShow(2)
		   }
   ACCESS      read-write
   STATUS      optional
   DESCRIPTION "This PML object can be used to enable or disable supplies		
                status messages from being displayed on the control panel.    	
                    eShow - show the status messages on the control panel.    	
                    eDontShow - do not show the status messages on the control		
                        panel.   
                Additional information:
                . This PML Object can be used to enable or disable the supplies
                status messages from being displayed on the control panel.
                eShow      Show the status messages on the control panel.
                eDontShow  Do not show the status messages on the control panel."
::= { settings-system 44 }
               
               
configurable-low-threshold-setting OBJECT-TYPE
   SYNTAX      INTEGER(0..100)
   ACCESS      read-write
   STATUS      optional
   DESCRIPTION "This PML object can be used to configure the low threshold for		
                supplies.
                Additional information:
                This PML object can be used to configure the Low Threshold for Supplies."
::= { settings-prt-eng 24 }
               
               
supplies-replace-action-at-setting OBJECT-TYPE
   SYNTAX      INTEGER {
		   eStopAtLow(1),
		   eStopAtOut(2),
		   eOverrideAtOut(3),
		   eOverrideAtOut2(4)
		   }
   ACCESS      read-write
   STATUS      optional
   DESCRIPTION "This object can be used to change the setting of menu item		
                REPLACE SUPPLIES. The behavior of the printer when a supply		
                reaches low changes in accordance with the setting of this PML		
                Object. If the option eStopAtLow is selected printer will stop		
                when a supply reaches LOW. If the option eStopAtOut is selected		
                then printer will stop when a supply reaches OUT. If the		
                options eStopAtMaxLife (supported only on Mono products) is		
                selected, the printer will continue past supply OUT. If the		
                option eOverrideAtOut or eOverrideAtOut2 (supported only on		
                Color products) is selected then printer will continue past OUT		
                in override mode. This option is not writeable. That is using		
                this PML object the setting could be changed to any option		
                other than eOverrideAtOut and eOverrideAtOut2.
                Additional information:
                This PML object can be used to change the setting of the menu 
                item REPLACE SUPPLIES. The behavior of the printer when a supply
                		 hits low changes in accordance with the setting of this PML Object.
                		 1. eStopAtLow - Printer will stop when a supply reaches low.
                		 2. eStopAtOut - Printer will stop when a supply reaches out.
                		 3. eOverrideAtOut[Read-only, Color Products] - Printer will continue
                		    print past out in override level 1 mode.
                		 4. eOverrideAtOut2[Read-only, Color Products] - Printer will continue
                		    print past out in override level 2 mode."
::= { settings-prt-eng 25 }
               
               
supply-out-user-configured-override-limit OBJECT-TYPE
   SYNTAX      INTEGER(0..100000)
   ACCESS      read-only
   STATUS      optional
   DESCRIPTION "This PML object reports the user configured cartridge out		
                override page limit.
                Additional information:
                This PML object reports the user configured cartridge out override
                limit."
::= { settings-prt-eng 26 }
               
               
cartridge-out-override-control OBJECT-TYPE
   SYNTAX      INTEGER
   ACCESS      write-only
   STATUS      optional
   DESCRIPTION "This PML object is used to control Cartridge Out Override		
                feature.
                Additional information:
                This object is used for the following purposes:
                		1. Enable/disable cartridge out override through 
                	           SUPPLIES_REPLACE_ACTION_AT_PML Object.
                		2. Enable/disable Toner Out Limit: When toner out limit is disabled
                		   using this PML Object, engine will not be taken offline when a 
                		   cartridge reaches toner out. Engine will continue to print and will
                		   be in Override mode until other limits are reached.
                		3. Enable/disable CRG R&D Limit: When CRG R&D limit is disabled
                		   using this PML Object, engine will not be taken offline when CRG 
                		   R&D limit for printing in override is reached for any out cartridge. 
                		   Engine will continue to print and will be in Override mode until 
                		   other limits are reached."
::= { settings-prt-eng 27 }
               
               
supply-out-user-configured-override2-limit OBJECT-TYPE
   SYNTAX      INTEGER
   ACCESS      read-only
   STATUS      optional
   DESCRIPTION "This PML object reports the user configured consumable out		
                override level two page limit.
                Additional information:
                This PML object reports the user configured consumable out		
                override level two page limit."
::= { settings-prt-eng 33 }
               
               
supply-out-action-support OBJECT-TYPE
   SYNTAX      OCTET STRING
   ACCESS      read-only
   STATUS      optional
   DESCRIPTION "This object is used to determine if a particular capability		
                that allows printing to continue after one or more cartridge		
                has reached out is supported by the device. The collection bits		
                include: cSupplyOutOverride - indicates that continuing to		
                print with an out supply in use is supported.		
                cMonochromePrintingAfterColorCartridgeOut - indicates that		
                continuing to print in monochrome after a color cartridge is		
                out is supported. cPrintingToMaxLife - indicates that printing		
                until 'max life' is reached is supported [monochrome only].
                Additional information:
                This object is used to determine what capabilities are supported
                by the device for allowing printing to continue after one or more
                		 cartridges have reached out. The collection bits include:
                		 cSupplyOutOverride - indicates that continuing to print with
                		    an out supply in use is supported.
                		 cMonochromePrintingAfterColorCartridgeOut - indicates that 
                		    continuing to print with monochrome after a color cartridge is 
                		    out is supported."
::= { status-prt-eng 48 }
               
               
supply-out-device-state OBJECT-TYPE
   SYNTAX      INTEGER {
		   eNoSupplyOut(1),
		   eOffline(2),
		   eSupplyOutOverride(3),
		   eMonochromePrintingAfterColorCartridgeOut(4)
		   }
   ACCESS      read-only
   STATUS      optional
   DESCRIPTION "This PML object indicates the current behavior of the device if		
                one or more supplies have reached out. If no supply has reached		
                out, the value of this PML object is eNoSupplyOut. If one or		
                more supplies have reached out, the value of this PML object		
                will indicate if the printer is online and if so what mode is		
                being used to continue printing.
                Additional information:
                This object indicates the current behavior of the device if one
                or more supplies have reached out. The enums represent:
                		 eNoSupplyOut - No supplies have reached out.
                		 eOffline - Printer is offline since one or more supplies have 
                		    reached out.
                		 eSupplyOutOverride - The supply override out is active.
                		 eMonochromePrintingAfterColorCartridgeOut - Monochrome printing
                		    after a color cartridge out is active."
::= { status-prt-eng 49 }
               
               
supply-after-out-state OBJECT-TYPE
   SYNTAX      OCTET STRING
   ACCESS      read-only
   STATUS      optional
   DESCRIPTION "This object is used to read and write the various status flags		
                indicating whether the consumable was used after out. The		
                collection bits supported include:    	
                    cNotUsedAfterOut - indicates the consumable was not used in		
                        any capacity after out. If cUsedAfterOutInOverrideMode		
                        or cUsedAfterOutInMonoPrintingAfterColorOutMode is set,		
                        this flag will not be set.    	
                    cInstalledWhileInOverrideMode - indicates the consumable		
                        was installed while Supply Out Override was activated.		
                           	
                    cUsedAfterOutInOverrideMode - indicates the consumable was		
                        used after out while Supply Out Override was activated.		
                           	
                    cInstalledWhileInMonoPrintingAfterColorOutMode - indicates		
                        the consumable was installed while MPACCO was		
                        activated.    	
                    cUsedAfterOutInMonoPrintingAfterColorOutMode - indicates		
                        the consumable was used after out while MPACCO was		
                        activated.   
                Additional information:
                This object is used to read the various status flags indicating
                whether the consumable was used after out. The collection bits include:
                		 cNotUsedAfterOut - indicates the consumable is not used after out.
                		 cUsedAfterOutInOverrideMode - indicates the consumable was used 
                		    after out while supply out override was actiavted.
                		 cInstalledWhileInMonoPrintingAfterColorOutMode - indicates that 
                		    the consumable was installed while MPACCO was activated.
                		 cUsedAfterOutInMonoPrintingAfterColorOutMode - indicates that the
                		    consumable was after out while MPACCO was activated."
::= { status-prt-eng 50 }
               
               
consumable-status-page-count-a3-ledger OBJECT-TYPE
   SYNTAX      INTEGER(0..65535)
   ACCESS      read-only
   STATUS      optional
   DESCRIPTION "This object is used to report the number of pages that have		
                been printed by this consumable that are of the specified media		
                size - A3 or Ledger.
                Additional information:
                This object will only exist for Authentic HP consumables.
                If the cartridge is deemed to be NonHP, then this object
                will not exist."
::= { consumable-status 10 }
               
               
consumable-status-page-count-b5-executive OBJECT-TYPE
   SYNTAX      INTEGER(0..65535)
   ACCESS      read-only
   STATUS      optional
   DESCRIPTION "This object is used to report the number of pages that have		
                been printed by this consumable that are of the specified media		
                size - B5 or Executive.
                Additional information:
                This object will only exist for Authentic HP consumables.
                If the cartridge is deemed to be NonHP, then this object
                will not exist."
::= { consumable-status 13 }
               
               
consumable-status-page-count-envelope OBJECT-TYPE
   SYNTAX      INTEGER(0..65535)
   ACCESS      read-only
   STATUS      optional
   DESCRIPTION "This object is used to report the number of pages that have		
                been printed by this consumable that are of the specified media		
                size - Envelope.
                Additional information:
                This object will only exist for Authentic HP consumables.
                If the cartridge is deemed to be NonHP, then this object
                will not exist."
::= { consumable-status 14 }
               
               
consumable-status-web-service-access-data OBJECT-TYPE
   SYNTAX      INTEGER
   ACCESS      read-only
   STATUS      optional
   DESCRIPTION "This object is used to report Web Service Access Data.
                Additional information:
                This object is used to report Web Service Access Data."
::= { consumable-status 75 }
               
               
consumable-status-web-service-access-control OBJECT-TYPE
   SYNTAX      OCTET STRING
   ACCESS      read-only
   STATUS      optional
   DESCRIPTION "This object is used to report data that controls how web		
                service access is enabled.
                Additional information:
                This object is used to report data that controls how web service access is enabled."
::= { consumable-status 76 }
               
               
consumable-string-information OBJECT-TYPE
   SYNTAX      OCTET STRING (SIZE(0..287))
   ACCESS      read-write
   STATUS      optional
   DESCRIPTION "This object is used to read and write the string value that		
                describes the consumable information."
::= { consumable-string 1 }
               
               
consumable-string-information-reset OBJECT-TYPE
   SYNTAX      INTEGER {
		   ePresetToNVRAM(1)
		   }
   ACCESS      read-write
   STATUS      optional
   DESCRIPTION "This object is used to reset (set back to factory default) or		
                read the current status of the corresponding information		
                string. When Set to eResetToDefault, this object can be used to		
                reset the corresponding information object back to its factory		
                default value. Setting this object with an enumerated value of		
                eCustomized has no effect. When a Get operation is performed on		
                this object it will return a value eResetToDefault if still set		
                to its factory value. It will return eCustomized if the		
                corresponding information value has been set to a custom		
                value.
                Additional information:
                This object returns ePresetToNVRAM(1) if CONSUMABLE-STRING-INFORMATION is currently set to the default string. It will return eCustomized(2) otherwise. However, we can explicitly set this object only to ePresetToNVRAM(1) and not eCustomized(2)."
::= { consumable-string 2 }
               
               
consumable-reorder-url OBJECT-TYPE
   SYNTAX      OCTET STRING (SIZE(0..64))
   ACCESS      read-write
   STATUS      optional
   DESCRIPTION "This object is used to read and write the URL that can be used		
                to reorder consumables for this device. This URL is set at the		
                factory but can be updated by a reseller or third party.
                Additional information:
                The URL can be up to 64 characters long."
::= { consumables 2 }
               
               
consumable-current-state OBJECT-TYPE
   SYNTAX      OCTET STRING
   ACCESS      read-only
   STATUS      optional
   DESCRIPTION "This PML object returns the current state of the particular		
                consumable.    	
                    cAuthLevel1 - Consumable is at Authentication Level 1    	
                    cAuthLevel2 - Consumable is at Authentication Level 2    	
                    cAuthLevel3 - Consumable is at Authentication Level 3    	
                    cAuthLevel4 - Consumable is at Authentication Level 4    	
                    cAuthLevel5 - Consumable is at Authentication Level 5    	
                    cGenuineHPUnsupported - Cartridge is GenuineHP intended for		
                        another product    	
                    cDefectiveMemory - Cartridge has a defective memory tag    	
                    cMissingMemory - Memory tag is missing from the cartridge		
                           	
                    cLowCondition - Consumable has reached the engine low		
                        threshold    	
                    cOutCondition - Consumable has reached its out threshold   	                         
                    cIncorrect - Cartridge inserted is not the correct one    	
                    cMissing - Consumable is missing from the printer    	
                    cConfigurableLow - Consumable has reached the configurable		
                        low threshold value    	
                    cStatusArevalid - The status reported on other bits are		
                        valid only if the bit is set to 1. If it is 0, the		
                        values are invalid.    	
                    cExpired - Is the cartridge expired, which is determined   	                         
                    by the formatter.   	
                    cFailure - Cartridge has failed determined by the engine.		
                           	
                    cLeak - Cartridge has a leak as determined by the engine.		
                           	
                    cUnknownManufacturer - the brand of the cartridge is    	
                    unknown as determined by the engine.    	
                    cUnsupported --- Cartridge is not supported as determined		
                           	
                    by the engine.    	
                These are the possible states and whenever the consumable is in		
                any of these states, the appropriate bit will be set. The		
                cLowCondition will be set when the consumable reaches the		
                engine low threshold, and cConfigurableLow will be set when the		
                consumable reaches the Configurable Low threshold value. For		
                non-cartridge supplies only cLowCondition, cOutCondition, and		
                cMissing will be supported.
                Additional information:
                This object returns the current state of the particular consumable.
                cAuthLevel1 - Consumable is at Authentication Level 1
                cAuthLevel2 - Consumable is at Authentication Level 2
                cAuthLevel3 - Consumable is at Authentication Level 3
                cAuthLevel4 - Consumable is at Authentication Level 4
                cGenuineHPUnsupported - Cartridge is GenuineHP intended for another product
                cDefectiveMemory - Cartridge has a Defective Memory
                cMissingMemory - Memory is Missing from the Cartridge
                cLowCondition - Consumable has reached its low threshold
                cOutCondition - Consumable has reached its out threshold
                cIncorrect - Cartridge inserted is not the correct one
                cMissing - Consumable is Missing from the Printer
                cConfigurableLow - Consumable has reached the 
                configurable low threshold value
                cStatusAreValid - The Status reported on other bits are valid only if
                this bit is set to 1. If it is 0, the values are invalid.
                These are the possible states and whenever a Consumable is in any of these
                states, the appropriate bit will be set. For Non Cartridge Supplies only
                cLowCondition, cOutCondition and cMissing will be supported."
::= { consumables 7 }
               
               
consumable-notification-status OBJECT-TYPE
   SYNTAX      OCTET STRING
   ACCESS      read-write
   STATUS      optional
   DESCRIPTION "This object is used to read and write the various status flags		
                supported by this consumable. For Laserjet 4700 MFP the collection bits		
                supported include:    	
                    cClient1ReorderNotificationSent - indicates whether EWS		
                        (Embedded Web Server) has already sent the reorder		
                        notification e-mail for this consumable. This bit can		
                        be both read and written.    	
                    cClient2ReorderNotificationSent - indicates whether WJA		
                        (Web Jet Admin) has already sent the reorder		
                        notification e-mail for this consumable. This bit can		
                        be both read and written.    	
                    cClient3ReorderNotificationSent - for future implementation		
                           	
                    cClient4ReorderNotificationSent - for future implementation		
                           	
                    cClient5ReorderNotificationSent - for future implementation		
                           	
                    cClient1ReplaceNotificationSent - indicates whether EWS		
                        (Embedded Web Server) has already sent the replace		
                        notification e-mail for this consumable. This bit can		
                        be both read and written.    	
                    cClient2ReplaceNotificationSent - indicates whether WJA		
                        (Web Jet Admin) has already sent the replace		
                        notification e-mail for this consumable. This bit can		
                        be both read and written.    	
                    cClient3ReplaceNotificationSent - for future implementation		
                           	
                    cClient4ReplaceNotificationSent - for future implementation		
                           	
                    cClient5ReplaceNotificationSent - for future implementation		
                          
                Additional information:
                If the cartridge is deemed to be NonHP, then this object will not exist.
                This object will have 1 sub arrays for the consumable.
                The client1 and 2 currently are assingned to EWS and WJA the remaining client are
                reserved for the future third party pml tools. A client is requiered to set only his assigned
                bit for reorder or replace notification. A client using other client's bit for reorder replace 
                will result in the other client being not able to set the notification.
                Ex: For EWS ReOrderNotification it will send 0x00010000 and 
                For EWS ReplaceNotification it will send 0x00000001
                For WJA ReOrderNotification it will send 0x00020000 and
                For WJA ReplaceNotification it will send 0x00000002"
::= { consumables 10 }
               
               
consumable-pages-printed-with-supply OBJECT-TYPE
   SYNTAX      INTEGER
   ACCESS      read-only
   STATUS      optional
   DESCRIPTION "This PML object returns the number of pages printed with a		
                cartridge consumable. This PML object returns the value that		
                should be displayed under 'Pages Printed With This Supply' for		
                cartridges in color products.
                Additional information:
                This PML object returns the number of pages printed with a
                cartridge consumable. This PML object returns the value that
                should be displayed under 'Pages Printed With This Supply' for
                cartridges in color products."
::= { consumables 11 }
               
               
supply-override-activated-level OBJECT-TYPE
   SYNTAX      INTEGER {
		   eHasNotBeenActivated(1),
		   eLevel01(2),
		   eLevel02(3)
		   }
   ACCESS      read-only
   STATUS      optional
   DESCRIPTION "This PML object indicates the last override activation level		
                for a given supply.
                Additional information:
                This PML object indicates the last override activation level for a given supply."
::= { consumables 12 }
               
               
supply-override-activated-pagecount OBJECT-TYPE
   SYNTAX      INTEGER
   ACCESS      read-only
   STATUS      optional
   DESCRIPTION "This object reports the printer’s historical page count at		
                which the last override activation occurred for a given		
                supply.
                Additional information:
                This object reports the printers historical page count at which the last override
                activation occurred for a given supply."
::= { consumables 13 }
               
               
supply-override-activated-date OBJECT-TYPE
   SYNTAX      OCTET STRING
   ACCESS      read-only
   STATUS      optional
   DESCRIPTION "This object reports the date when the last override activation		
                occurred for a given supply.
                Additional information:
                This object reports the date when the last override activation occurred for a given supply."
::= { consumables 14 }
               
               
consumable-life-usage-units-remaining OBJECT-TYPE
   SYNTAX      INTEGER
   ACCESS      read-only
   STATUS      optional
   DESCRIPTION "This object reports the current estimate of the number of usage		
                units that remain before this supply is depleted. An installed		
                supply that cannot report such a number will return a value of		
                -2. It is the reponsibility of the host application to query		
                each supply in order to determine an overall device		
                USAGE-UNITS-REMAINING number - the lowest value returned. The		
                unit of measure for this life estimate is determined by reading		
                the corresponding CONSUMABLE-LIFE-USAGE-UNITS object.
                Additional information:
                This object will return the Pages or Estimated Pages remaining for 
                the speciffic supply requested by the leaf node of this object."
::= { consumables-life 1 }
               
               
consumable-life-usage-units OBJECT-TYPE
   SYNTAX      INTEGER {
		   ePagesRemaining(1),
		   eEstimatedPagesRemaining(2)
		   }
   ACCESS      read-only
   STATUS      optional
   DESCRIPTION "This object reports current usage units in use by the		
                corresponding CONSUMABLE-LIFE-USAGE-UNITS-REMAINING object.
                Additional information:
                This object returns the units that REMAINING
                is returned in.  Either ePagesRemaining(1) or eEstimatedPagesRemaining(2)."
::= { consumables-life 2 }
               
               
consumable-life-low-threshold OBJECT-TYPE
   SYNTAX      INTEGER
   ACCESS      read-only
   STATUS      optional
   DESCRIPTION "This object is used to report and modify a threshold value		
                indicating the point in the life of a consumable or supply at		
                which a transition to a LOW state will occur."
::= { consumables-life 3 }
               
               
printer-average-marking-agent-units-per-gram OBJECT-TYPE
   SYNTAX      OCTET STRING
   ACCESS      read-only
   STATUS      optional
   DESCRIPTION "This object is used to read the marking agent units of measure		
                per gram. This is typically a conversion factor for converting		
                pixels of toner to grams. This pixels-per-gram value is used to		
                calculate the estimated number of pages remaining for a given		
                marking agent."
::= { printer-average 4 }
               
               
printer-average-marking-agent-coverage-actual OBJECT-TYPE
   SYNTAX      OCTET STRING
   ACCESS      read-only
   STATUS      optional
   DESCRIPTION "This object is used to read the actual average marking agent		
                coverage for a given color plane. It is a real number that		
                represents percent coverage and will read from 0 to 100%. This		
                object will return the same value as		
                PRINTER-AVERAGE-MARKING-AGENT-COVERAGE except under certain		
                conditions which will be specified in the device POS."
::= { printer-average 5 }

               
               
default-vertical-black-resolution OBJECT-TYPE
   SYNTAX      INTEGER
   ACCESS      read-write
   STATUS      optional
   DESCRIPTION "Returns or changes the value of the default vertical black		
                resolution. The units are dots per inch.
                Additional information:
                In $product_str changing this OID also causes
                DEFAULT-HORIZONTAL-BLACK RESOLUTION to change.
                DEFAULT-HORIZONTAL-BLACK-RESOLUTION and
                DEFAULT-VERTICAL-BLACK-RESOLUTION must always be the
                same.  The supported values are:
                LaserJet 4100: 300, 600, 1200
                Color Products: 600
                LaserJet 9000: 300, 600   
                Setting to an unsupported value causes the printer
                to substitute in a snap value and
                to return <noError> status.  
                The snap values are as follow:  
                LaserJet 4100:  
                450 >= n < 900 snaps to 600  
                n >= 900 snaps to 1200   
                Color Products:  
                			  n <= 900 snaps to 600  
                			  n >  900 snaps to 1200   			  
                LaserJet 9000:  
                n < 450 snaps to 300  
                n >=450 snaps to 600  "
::= { settings-pdl 8 }
               
               
default-horizontal-black-resolution OBJECT-TYPE
   SYNTAX      INTEGER
   ACCESS      read-write
   STATUS      optional
   DESCRIPTION "Returns or changes the value of the default horizontal black		
                resolution. The units are dots per inch.
                Additional information:
                In $product_str changing this object also causes
                DEFAULT-VERTICAL-BLACK RESOLUTION to change.
                DEFAULT-HORIZONTAL-BLACK-RESOLUTION and
                DEFAULT-VERTICAL-BLACK-RESOLUTION must always be the
                same.  The supported values are:
                LaserJet 4100: 300, 600, 1200
                Color Products: 600
                LaserJet 9000: 300, 600   
                Setting to an unsupported value causes the printer
                to substitute in a snap value and to
                return <noError> status.  
                The snap values are as follow:  
                LaserJet 4100:  
                n < 450 snaps to 300  
                450 >= n < 900 snaps to 600  
                n >= 900 snaps to 1200   
                Color Products:  
                			  n <= 900 snaps to 600  
                			  n > 900  snaps to 1200   
                LaserJet 9000:  
                n < 450 snaps to 300  
                n >=450 snaps to 600  "
::= { settings-pdl 9 }
               
               
default-page-protect OBJECT-TYPE
   SYNTAX      INTEGER {
		   eOn(2)
		   }
   ACCESS      read-write
   STATUS      optional
   DESCRIPTION "Returns or changes the default page protection behavior. If		
                eOff, the device does not reserve memory for holding the entire		
                raster form of a processed page. If eOn, then memory is		
                reserved. If eAuto, the device determines the amount of memory		
                to reserve.
                Additional information:
                Setting to eOn causes MET to be more conservative, but
                it will not allocate memory to hold an entire
                rasterized page."
::= { settings-pdl 10 }
               
               
default-bits-per-pixel OBJECT-TYPE
   SYNTAX      INTEGER
   ACCESS      read-write
   STATUS      optional
   DESCRIPTION "Controls the number of levels used (per pixel) when printing		
                grayscale or color images."
::= { settings-pdl 39 }
               
               
web-server-security OBJECT-TYPE
   SYNTAX      OCTET STRING
   ACCESS      read-write
   STATUS      optional
   DESCRIPTION "Each collection bit represents a device or Embedded Web Server		
                feature that can be enabled or disabled via this object."
::= { settings-webserver 3 }
               
               
firmware-download-write-status-supported OBJECT-TYPE
   SYNTAX      INTEGER {
		   eFalse(1),
		   eTrue(2)
		   }
   ACCESS      read-only
   STATUS      optional
   DESCRIPTION "This object provides information on whether the printer has the		
                ability to communicate the write-status of the firmware		
                download while the download is taking place."
::= { firmware-download 1 }
               
               
firmware-download-write-time OBJECT-TYPE
   SYNTAX      INTEGER
   ACCESS      read-only
   STATUS      optional
   DESCRIPTION "If the design of the firmware-download implementation does not		
                allow PML interaction during the download process, this value		
                provides an estimation of the time where the printer will not		
                be able to engage in PML communication.
                Additional information:
                If the design of the firmware-download 
                			implementation does not allow PML interaction during 
                			the download process, this value provides an 
                			estimation of the time where the printer will not be 
                			able to engage in PML communication. The calculated
                			time is expected to be 140 secs. However, this time
                			may increase as high as 280 secs as the flash part 
                			nears the maximum flash count."
::= { firmware-download 2 }
               
               
firmware-download-current-state OBJECT-TYPE
   SYNTAX      INTEGER {
		   eIdle(1),
		   eReceivingImage(2),
		   eReceivedImageError(3),
		   eVerifyingImage(4),
		   eVerifiedImageError(5),
		   eWritingImage(6),
		   eWritingImageError(7),
		   eDownloadComplete(8),
		   eOKtoShutDown(9),
		   eCancelDownload(10),
		   eShuttingDown(11)
		   }
   ACCESS      read-only
   STATUS      optional
   DESCRIPTION "Provides the current or last reportable state of the firmware		
                download process. The current state may not necessarily be the		
                current state, but could be the post-mortem state."
::= { firmware-download 4 }
               
               
firmware-download-name OBJECT-TYPE
   SYNTAX      OCTET STRING
   ACCESS      read-only
   STATUS      mandatory
   DESCRIPTION "This returns the name of the printer. This should match the		
                name in the header of the upgrade image being sent to the flash		
                part. If the name does not match with the name returned then		
                the image that we are attempting to download does not upgrade		
                the printer firmware.
                Additional information:
                This object returns the HP name of the printer.  
                			     This should match what is in the PJL header of the RFU job
                			     Web Jet Admin uses this to ensure the printer is available
                		   	     to be upgraded."
::= { firmware-download 6 }
               
               
firmware-download-version OBJECT-TYPE
   SYNTAX      OCTET STRING
   ACCESS      read-only
   STATUS      mandatory
   DESCRIPTION "This object will return a string value representing the current		
                revision of firmware that the printer is operating with. This		
                is used to determine if code needs to be upgraded when an		
                firmware bundle comes in, in an upgrade job.
                Additional information:
                Web Jet Admin uses the version string that is returned to
                			     determine what peices of an RFU bundle need to be upgraded 
                			     when an RFU job is being built. This objects will return
                			     the version string of the printer."
::= { firmware-download 7 }
               
               
upgradable-devices-write-status-supported OBJECT-TYPE
   SYNTAX      INTEGER {
		   eFalse(1),
		   eTrue(2)
		   }
   ACCESS      read-only
   STATUS      optional
   DESCRIPTION "This object provides information on whether the upgradable		
                device has the ability to communicate the write-status of the		
                upgrade while the upgrade is taking place."
::= { upgradable-devices 1 }
               
               
upgradable-devices-write-time OBJECT-TYPE
   SYNTAX      INTEGER
   ACCESS      read-only
   STATUS      optional
   DESCRIPTION "If the design of the device upgrade implementation does not		
                allow PML interaction during the download process, this value		
                provides an estimation of the time where the device will not be		
                able to engage in PML communication. The time returned will		
                depend upon what device is attempting to be upgraded."
::= { upgradable-devices 2 }
               
               
upgradable-devices-current-state OBJECT-TYPE
   SYNTAX      INTEGER {
		   eIdle(1),
		   eReceivedImage(2),
		   eReceivedImageError(3),
		   eVerifiedImage(4),
		   eVerifiedImageError(5),
		   eWritingImage(6),
		   eWritingImageError(7),
		   eUpgradeComplete(8),
		   eUpgradeSkipped(9)
		   }
   ACCESS      read-only
   STATUS      optional
   DESCRIPTION "Provides the current or last reportable state of the device		
                upgrade process. The current state may not necessarily be the		
                current state, but could be the post-mortem state."
::= { upgradable-devices 4 }
               
               
upgradable-devices-name OBJECT-TYPE
   SYNTAX      OCTET STRING
   ACCESS      read-only
   STATUS      mandatory
   DESCRIPTION "This returns the name of the upgradable device. This should		
                match the name in the header of the upgrade image being sent to		
                the flash part. If the name does not match with any of the		
                names returned then the device that we are attempting to		
                upgrade is unavailable for upgrading.
                Additional information:
                This object returns the HP name of the printer and the upgradable
                			     devices. There is one Name object per upgradable device.  
                			     This should match what is in the PJL header of the RFU job
                			     Web Jet Admin uses this to ensure the printer or device  is
                			     available to be upgraded."
::= { upgradable-devices 6 }
               
               
upgradable-devices-version OBJECT-TYPE
   SYNTAX      OCTET STRING
   ACCESS      read-only
   STATUS      mandatory
   DESCRIPTION "This object will return a string value representing the current		
                revision of firmware that device X is operating with. This is		
                used to determine if code needs to be upgraded when a firmware		
                bundle comes in, in an upgrade job.
                Additional information:
                Web Jet Admin uses the version string that is returned to
                			     determine what peices of an RFU bundle need to be upgraded 
                			     when an RFU job is being built. This internal object will 
                			     return the current version string of the printer or device 
                			     that it corresponds to."
::= { upgradable-devices 7 }
               
               
remote-upgrade-enable OBJECT-TYPE
   SYNTAX      INTEGER {
		   eOff(1),
		   eOn(2)
		   }
   ACCESS      read-write
   STATUS      mandatory
   DESCRIPTION "Enables or disables the ability to upgrade the firmware		
                associated with any device that is available to be upgraded.		
                This will be set to on or off at the RFU level in that if this		
                mode is on any available device can be upgraded and if this		
                mode is off none of the devices can be upgraded. There is not		
                an individual mode for each device. Trying to set this to a		
                value other than eOn or eOff will cause an UnsupportedValue		
                error to occur."
::= { upgradable-devices 8 }
               
               
END
