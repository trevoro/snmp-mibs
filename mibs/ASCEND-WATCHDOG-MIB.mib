-- $Id: watchdog.mib,v 1.3.6.2 2000/05/25 03:46:28 asarma Exp $
--
-- The Watchdog Management Information Base
--
-- Copyright (c) 1999 Ascend Communications, Inc.
--		 All rights reserved.
-- 
-- The watchdog MIB supports any slot watchdog SNMP functionality.
-- The initial use for the watchdog MIB is to support thermal watchdogs
-- on the MAX 3000.
--
-- TAOS release 7.4, 8.0 and later will support the thermal watchdog MIB.
--
-- 26th February 1999	Initial creation
--   01 July     1999	Add watchdogID fan(3) in TAOS 8.0 for Stinger

ASCEND-WATCHDOG-MIB DEFINITIONS ::= BEGIN

    IMPORTS
	    slots		FROM ASCEND-MIB
	    TimeTicks		FROM RFC1155-SMI
	    DisplayString	FROM RFC1213-MIB
            OBJECT-TYPE		FROM RFC-1212;

    watchdog	OBJECT IDENTIFIER ::= { slots 7 }

    watchdogCount OBJECT-TYPE
	SYNTAX  INTEGER
	ACCESS  read-only
	STATUS  mandatory
	DESCRIPTION
	    "The number of entries in the watchdogTable"
	::= { watchdog 1 }

    watchdogTable OBJECT-TYPE
	SYNTAX  SEQUENCE OF WatchdogEntry
	ACCESS  not-accessible
	STATUS  mandatory
	DESCRIPTION
	    "The watchdog table"
	::= { watchdog 2 }

    watchdogTrapState OBJECT-TYPE
	SYNTAX  INTEGER { 
	    enabled(1),
	    disabled(2) }
        ACCESS  read-write
        STATUS  mandatory
	DESCRIPTION
           "This variable indicates whether the system
 	    produces the watchdogWarningTrap trap."
     	::= { watchdog 3 }

    watchdogEntry OBJECT-TYPE
	SYNTAX  WatchdogEntry
	ACCESS  not-accessible
	STATUS  mandatory
	DESCRIPTION
	    "An entry in the watchdog table"
	INDEX  { watchdogIndex }
	::= { watchdogTable 1 }

    WatchdogEntry ::=
	SEQUENCE {
	    watchdogIndex		INTEGER,
	    watchdogName		DisplayString,
	    watchdogID		 	INTEGER,
	    watchdogState		INTEGER,
	    watchdogReading		INTEGER,
	    watchdogLastViolation	TimeTicks,
	    watchdogLocation		DisplayString,
	    watchdogUnit		INTEGER,
	    watchdogReadingUnits	INTEGER,
	    watchdogThreshold		INTEGER
	}

    watchdogIndex OBJECT-TYPE
	SYNTAX  INTEGER
        ACCESS  read-only
        STATUS  mandatory
        DESCRIPTION
            "The index of the watchdog entry."
       ::= { watchdogEntry 1 }

    watchdogName OBJECT-TYPE
	SYNTAX	DisplayString
	ACCESS	read-only
	STATUS 	mandatory
	DESCRIPTION
	    "A descriptive name for the watchdog"
	::= { watchdogEntry 2 }

    watchdogID OBJECT-TYPE
	SYNTAX  INTEGER {
	    other(1),
	    thermal(2),
	    fan(3),
	    fantray(4)
	}
        ACCESS  read-only
        STATUS  mandatory
        DESCRIPTION
            "This defines what type of watchdog relates to this entry.
	     The possible values are: (1) 'other' for a sensor other than
	     the types listed, (2) 'thermal' for a temperature sensor,
	     (3) 'fan' for a fan speed sensor, (4) 'fantray' for a sensor
	     associated with a fantray assembly"
       ::= { watchdogEntry 3 }

    watchdogState OBJECT-TYPE
	SYNTAX  INTEGER {
	    other(1),
	    operational(2),
	    failed(3)
	}
        ACCESS  read-only
        STATUS  mandatory
        DESCRIPTION
	    "The state of the watchdog.  If the value is 'other' then the
	     watchdog does not support state information."
	::= { watchdogEntry 4 }

    watchdogReading OBJECT-TYPE
	SYNTAX  INTEGER
        ACCESS  read-only
        STATUS  mandatory
        DESCRIPTION
	    "A measurement reading of the watchdog.  The unit of measurment
	     is defined by watchdogReadingUnits.  A -1 value indicates a
	     reading of the watchdog is not supported."
	::= { watchdogEntry 5 }

    watchdogLastViolation OBJECT-TYPE
	SYNTAX	TimeTicks
	ACCESS	read-only
	STATUS	mandatory
	DESCRIPTION
	    "The value of sysUpTime at the time the last watchdog
	     violation occurred (last violation trap sent)."
	::= { watchdogEntry 6 }

    watchdogLocation OBJECT-TYPE
	SYNTAX	DisplayString
	ACCESS	read-only
	STATUS 	mandatory
	DESCRIPTION
	    "The location of the watchdog"
	::= { watchdogEntry 7 }

    watchdogUnit OBJECT-TYPE
	SYNTAX  INTEGER
        ACCESS  read-only
        STATUS  mandatory
        DESCRIPTION
            "The unit number of the watchdog entry.  This number is an
	     unique identifier assigned to each watchdog of a particular type."
       ::= { watchdogEntry 8 }

    watchdogReadingUnits OBJECT-TYPE
	SYNTAX  INTEGER {
	    other(1),
	    celsius(2),
	    rpm(3),
	    noReadingSupported(4)
	}
        ACCESS  read-only
        STATUS  mandatory
        DESCRIPTION
	    "The measurement units of a reading from the watchdog"
	::= { watchdogEntry 9 }

    watchdogThreshold OBJECT-TYPE
	SYNTAX  INTEGER
        ACCESS  read-only
        STATUS  mandatory
        DESCRIPTION
	    "The reading level for the watchdog that will trigger a trap"
	::= { watchdogEntry 10 }

END
