--
-- OPCD-CLUSTER-MIB-V2
-- Last Modified: Thu, Feb 18, 2010
--


OPCD-CLUSTER-MIB-V2 DEFINITIONS ::= BEGIN


--  OPCD-CLUSTER-MIB:
--    A private enterprise mib for Opencode Cluster application.


IMPORTS
	MODULE-IDENTITY, OBJECT-TYPE, NOTIFICATION-TYPE, enterprises  FROM SNMPv2-SMI
	DisplayString						      FROM SNMPv2-TC
	opencode-systems 					      FROM OPCD-SUPPORT-MIB-V2;




--  opencode cluster  branch: 30374.40
--  opencode cluster traps branch: 30374.40.1



  occluster   	  OBJECT IDENTIFIER ::= { opencode-systems 40 }
  occluster-traps OBJECT IDENTIFIER ::= { occluster 1 }

  definitions 	OBJECT IDENTIFIER ::= { occluster-traps 0 }
  vars 		OBJECT IDENTIFIER ::= { occluster-traps 1 }
--
--


mcr-Host OBJECT-TYPE
	SYNTAX DisplayString (SIZE (0..255))
	MAX-ACCESS accessible-for-notify
	STATUS current
	DESCRIPTION
		"String containing hostname of fault node."
	::= { vars 1 }


mcr-Severity OBJECT-TYPE
	SYNTAX INTEGER{
		critical(1),
		major(2),
		minor(3),
		normal(4),
		warning(5)
	}
	MAX-ACCESS accessible-for-notify
	STATUS mandatory
	DESCRIPTION
		"Alarm severity."
	::= { vars 2 }


mcr-Text OBJECT-TYPE
	SYNTAX DisplayString (SIZE (0..255))
	MAX-ACCESS accessible-for-notify
	STATUS current
	DESCRIPTION
		"String containing text of the alarm."
	::= { vars 3 }


--
-- Traps
--
-----------------------------------------------------------------------------------------------


------------------------------------------------------------------------------------------



-- 1.3.6......0.2
occluster-became-supervisor NOTIFICATION-TYPE
	OBJECTS	{ mcr-Host, mcr-Severity, mcr-Text}	
	STATUS  current
	DESCRIPTION  "The supervisor is elected.Possible reason:
                      1.Supervisor node/cluster application is down.
                      2.The cluster is started and the new supervisor is
		      elected"
	--#SUMMARY   "Alarm on host: $1 (cluster application) :  $3"
	--#CATEGORY  "Error Alarms"
        --#ARGUMENTS {}
        --#SEVERITY  Warning
	::= { definitions 2 }


-- 1.3.6......0.3
occluster-became-supervisor-Canceled NOTIFICATION-TYPE
	OBJECTS	{ mcr-Host, mcr-Severity, mcr-Text}	
	STATUS  current
	DESCRIPTION  "The event is canceled after timeout period."
	--#SUMMARY   "Alarm on host: $1 (cluster application) :  $3"
	--#CATEGORY  "Error Alarms"
        --#ARGUMENTS {}
        --#SEVERITY  NORMAL
	::= { definitions 3 }


-- 1.3.6......0.4
occluster-node-down NOTIFICATION-TYPE
        OBJECTS	{ mcr-Host, mcr-Severity, mcr-Text}	
	    STATUS  current
        DESCRIPTION  "Nodes are detected as down from the cluster
		     manager"
        --#SUMMARY   "Alarm on host: $1 (cluster application) :  $3"
        --#CATEGORY  "Error Alarms"
        --#ARGUMENTS {}
        --#SEVERITY  Major
        ::= { definitions 4 }

-- 1.3.6......0.5
occluster-node-down-Canceled NOTIFICATION-TYPE
        OBJECTS	{ mcr-Host, mcr-Severity, mcr-Text}	
	    STATUS  current
        DESCRIPTION  "Nodes are UP."
        --#SUMMARY   "Alarm on host: $1 (cluster application) :  $3"
        --#CATEGORY  "Error Alarms"
        --#ARGUMENTS {}
        --#SEVERITY  NORMAL
        ::= { definitions 5 }

-- 1.3.6......0.6
occluster-resourceagent-down NOTIFICATION-TYPE
        OBJECTS	{ mcr-Host, mcr-Severity, mcr-Text}	
	    STATUS  current
        DESCRIPTION  "Resource agent/s seems to be down."
        --#SUMMARY   "Alarm on host: $1 (cluster application) :  $3"
        --#CATEGORY  "Error Alarms"
        --#ARGUMENTS {}
        --#SEVERITY  Major
        ::= { definitions 6 }

-- 1.3.6......0.7
occluster-resourceagent-down-Canceled NOTIFICATION-TYPE
        OBJECTS	{ mcr-Host, mcr-Severity, mcr-Text}	
	    STATUS  current
        DESCRIPTION  "Resource agent/s are UP."
        --#SUMMARY   "Alarm on host: $1 (cluster application) :  $3"
        --#CATEGORY  "Error Alarms"
        --#ARGUMENTS {}
        --#SEVERITY  NORMAL
        ::= { definitions 7 }

-- 1.3.6......0.8
occluster-resource-down NOTIFICATION-TYPE
        OBJECTS	{ mcr-Host, mcr-Severity, mcr-Text}	
	    STATUS  current
        DESCRIPTION  "Some resources are detected as Down from the cluster
		     manager"
        --#SUMMARY   "Alarm on host: $1 (cluster application) :  $3"
        --#CATEGORY  "Error Alarms"
        --#ARGUMENTS {}
        --#SEVERITY  Critical
        ::= { definitions 8 }

-- 1.3.6......0.9
occluster-resource-down-Canceled NOTIFICATION-TYPE
        OBJECTS	{ mcr-Host, mcr-Severity, mcr-Text}	
	    STATUS  current
        DESCRIPTION  "Resources are UP."
        --#SUMMARY   "Alarm on host: $1 (cluster application) :  $3"
        --#CATEGORY  "Error Alarms"
        --#ARGUMENTS {}
        --#SEVERITY  NORMAL
        ::= { definitions 9 }

-- 1.3.6......0.10
occluster-service-down NOTIFICATION-TYPE
        OBJECTS	{ mcr-Host, mcr-Severity, mcr-Text}	
	    STATUS  current
        DESCRIPTION  "Some services are deteced as DOWN from the cluster
	             manager."
        --#SUMMARY   "Alarm on host: $1 (cluster application) :  $3"
        --#CATEGORY  "Error Alarms"
        --#ARGUMENTS {}
        --#SEVERITY  Critical
        ::= { definitions 10 }

-- 1.3.6......0.11
occluster-service-down-Canceled NOTIFICATION-TYPE
        OBJECTS	{ mcr-Host, mcr-Severity, mcr-Text}	
	    STATUS  current
        DESCRIPTION  "The services are UP."
        --#SUMMARY   "Alarm on host: $1 (cluster application) :  $3"
        --#CATEGORY  "Error Alarms"
        --#ARGUMENTS {}
        --#SEVERITY  NORMAL
        ::= { definitions 11 }

END


--
-- OPCD-CLUSTER-MIB-V2
--
