ATM-SOFT-PVC-TRAP-MIB DEFINITIONS ::= BEGIN


-- Copyright 1998 Bay Networks, Inc.
-- All rights reserved.
-- This Bay Networks SNMP Management Information Base Specification 
-- (Specification) embodies Bay Networks' confidential and
-- proprietary intellectual property. Bay Networks retains all
-- title and ownership in the Specification, including any
-- revisions. 
 
-- This Specification is supplied "AS IS," and Bay Networks makes
-- no warranty, either express or implied, as to the use,
-- operation, condition, or performance of the Specification.    


IMPORTS
	TRAP-TYPE				FROM RFC-1215
	atmSoftPvcTrapsPrefix,  
	atmSoftPvcCallFailures, 			
	atmSoftPvcCurrentlyFailingSoftPVccs,
	atmSoftPvcCurrentlyFailingSoftPVpcs	FROM ATM-SOFT-PVC-MIB;

atmSoftPvcCallFailuresTrap	TRAP-TYPE
	ENTERPRISE	atmSoftPvcTrapsPrefix
	VARIABLES	{ atmSoftPvcCallFailures, atmSoftPvcCurrentlyFailingSoftPVccs,
	atmSoftPvcCurrentlyFailingSoftPVpcs}
--	STATUS	mandatory
	DESCRIPTION
		"A notification indicating that one or more series of
		call attempts in trying to establish a Soft PVPC or
		Soft PVCC have failed since the last
		atmSoftPvcCallFailureTrap was sent. If this trap has
		not been sent for the last atmSoftPvcNotificationInterval,
		then it will be sent on the next increment of
		atmSoftPvcCallFailures."
	::= 1
END
-- SECTION 1: Top Level Definitions
