--			Ascend mibds1clkerr MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBDS1CLKERR-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibds1ClockErrorProfile  OBJECT IDENTIFIER ::= { configuration 164}

	-- The mibds1ClockErrorProfile table
	--
	-- This table contains parameters for the mibds1ClockErrorProfile profile
	--

    mibds1ClockErrorProfileTable	OBJECT-TYPE
	SYNTAX		SEQUENCE OF Mibds1ClockErrorProfileEntry
	ACCESS		not-accessible
	STATUS		mandatory
	DESCRIPTION	"A list of mibds1ClockErrorProfile profile entries."
	::= { mibds1ClockErrorProfile 1 }

    mibds1ClockErrorProfileEntry	OBJECT-TYPE
	SYNTAX		Mibds1ClockErrorProfileEntry
	ACCESS		not-accessible
	STATUS		mandatory
	DESCRIPTION	"A mibds1ClockErrorProfile entry containing objects that
			 maps to the parameters of mibds1ClockErrorProfile profile."
	INDEX		{ ds1ClockErrorProfile-Index-o }
	::= { mibds1ClockErrorProfileTable 1 }

    Mibds1ClockErrorProfileEntry ::=
	SEQUENCE {
	    ds1ClockErrorProfile-Index-o
		INTEGER,
	    ds1ClockErrorProfile-Enabled
		INTEGER,
	    ds1ClockErrorProfile-CrcThreshold
		INTEGER,
	    ds1ClockErrorProfile-FrameSlipsThreshold
		INTEGER,
	    ds1ClockErrorProfile-FerThreshold
		INTEGER,
	    ds1ClockErrorProfile-OofThreshold
		INTEGER,
	    ds1ClockErrorProfile-FebeThreshold
		INTEGER,
	    ds1ClockErrorProfile-LcvThreshold
		INTEGER,
	    ds1ClockErrorProfile-Action-o
		INTEGER
	}

    ds1ClockErrorProfile-Index-o	OBJECT-TYPE
	SYNTAX	INTEGER
	ACCESS	read-only
	STATUS	mandatory
	DESCRIPTION	""
	::= { mibds1ClockErrorProfileEntry 1 }

    ds1ClockErrorProfile-Enabled	OBJECT-TYPE
	SYNTAX	INTEGER {
		    no (1),
		    yes (2)
		}
	ACCESS	read-write
	STATUS	mandatory
	DESCRIPTION	"Enables or disables the feature of swapping the master clock source with the next priority source, if it is experiencing errors. The default value is 'no'."
	::= { mibds1ClockErrorProfileEntry 2 }

    ds1ClockErrorProfile-CrcThreshold	OBJECT-TYPE
	SYNTAX	INTEGER
	ACCESS	read-write
	STATUS	mandatory
	DESCRIPTION	"Threshold value of Cyclic Redundancy Check ( CRC ) Error per second. If set to 0, will not be considered in switching the Clock."
	::= { mibds1ClockErrorProfileEntry 3 }

    ds1ClockErrorProfile-FrameSlipsThreshold	OBJECT-TYPE
	SYNTAX	INTEGER
	ACCESS	read-write
	STATUS	mandatory
	DESCRIPTION	"Threshold value of Frame Slips Error per second. If set to 0, will not be considered in switching the Clock."
	::= { mibds1ClockErrorProfileEntry 4 }

    ds1ClockErrorProfile-FerThreshold	OBJECT-TYPE
	SYNTAX	INTEGER
	ACCESS	read-write
	STATUS	mandatory
	DESCRIPTION	"Threshold value of Framing Error ( FER ) per second. If set to 0, will not be considered in switching the Clock."
	::= { mibds1ClockErrorProfileEntry 5 }

    ds1ClockErrorProfile-OofThreshold	OBJECT-TYPE
	SYNTAX	INTEGER
	ACCESS	read-write
	STATUS	mandatory
	DESCRIPTION	"Threshold value of Out Of Frame (OOF) Error per second. If set to 0, will not be considered in switching the Clock."
	::= { mibds1ClockErrorProfileEntry 6 }

    ds1ClockErrorProfile-FebeThreshold	OBJECT-TYPE
	SYNTAX	INTEGER
	ACCESS	read-write
	STATUS	mandatory
	DESCRIPTION	"Threshold value of Far end block ( FEBE ) Error per second. If set to 0, will not be considered in switching the Clock."
	::= { mibds1ClockErrorProfileEntry 7 }

    ds1ClockErrorProfile-LcvThreshold	OBJECT-TYPE
	SYNTAX	INTEGER
	ACCESS	read-write
	STATUS	mandatory
	DESCRIPTION	"Threshold value of Line code violations ( LCV ) Error per second. If set to 0, will not be considered in switching the Clock."
	::= { mibds1ClockErrorProfileEntry 8 }

    ds1ClockErrorProfile-Action-o	OBJECT-TYPE
	SYNTAX	INTEGER {
		    noAction (1),
		    createProfile (2),
		    deleteProfile (3)
		}
	ACCESS	read-write
	STATUS	mandatory
	DESCRIPTION	""
	::= { mibds1ClockErrorProfileEntry 9 }

END
