--
-- CDM-570.my
-- MIB generated by MG-SOFT Visual MIB Builder Version 2.1 Build 199
-- Wednesday, June 28, 2006 at 15:05:10
--

	CDM-570 DEFINITIONS ::= BEGIN

		IMPORTS 
			comtechEFData			
				FROM ComtechEFData			
			OBJECT-GROUP, MODULE-COMPLIANCE, NOTIFICATION-GROUP			
				FROM SNMPv2-CONF			
			IpAddress, OBJECT-TYPE, MODULE-IDENTITY, NOTIFICATION-TYPE			
				FROM SNMPv2-SMI			
			DisplayString, MacAddress			
				FROM SNMPv2-TC;
	
	
		cdm570 MODULE-IDENTITY
			LAST-UPDATED "200602220000Z"
			ORGANIZATION
				"Comtech EF Data Corp."
			CONTACT-INFO
				"Comtech EF Data Crop.
				2114 W. 7th Street
				Tempe, AZ  85281 USA
				
				Tel: 480-333-2200
				Fax: 480-333-2540
				Web: http://www.comtechefdata.com
				"
			DESCRIPTION
				"Module Identity for both CDM-570 L-Band and 
				IF-Band Satellite Modems."
			REVISION "200602220000Z"
			DESCRIPTION
				"Updated for 1.5.3 Maint. Release"
			::= { comtechEFData 24 }
		
	
	
--
-- Node definitions
--
	
		cdm570Objects OBJECT IDENTIFIER ::= { cdm570 1 }
		
		cdm570System OBJECT IDENTIFIER ::= { cdm570Objects 1 }
		
		cdm570SystemInfo OBJECT IDENTIFIER ::= { cdm570System 1 }
		
		cdm570SerialNumber OBJECT-TYPE
			SYNTAX DisplayString (SIZE (9))
			MAX-ACCESS read-only
			STATUS current
			DESCRIPTION
				"Used to query the unit 9-digit serial number.  
				Unit returns its S/N in the form xxxxxxxxx."
			::= { cdm570SystemInfo 1 }
		
		cdm570Temperature OBJECT-TYPE
			SYNTAX INTEGER (-99..99)
			UNITS "degrees Celsius"
			MAX-ACCESS read-only
			STATUS current
			DESCRIPTION
				"Unit returns the value of the internal 
				temperature, in degrees Celsius."
			::= { cdm570SystemInfo 2 }
		
		cdm570SystemEquipmentID OBJECT IDENTIFIER ::= { cdm570System 2 }
		
		cdm570TurboOption OBJECT-TYPE
			SYNTAX INTEGER
				{
				none(0),
				turbo(1),
				tpcLdpc(2)
				}
			MAX-ACCESS read-only
			STATUS current
			DESCRIPTION
				"Turbo option, where:
				0 = None
				1 = Turbo
				2 = TPC/LDPC"
			::= { cdm570SystemEquipmentID 1 }
		
		cdm570ModelNumber OBJECT-TYPE
			SYNTAX INTEGER (0..999)
			MAX-ACCESS read-only
			STATUS current
			DESCRIPTION
				"Modem model number."
			::= { cdm570SystemEquipmentID 2 }
		
		cdm570DataRateOption OBJECT-TYPE
			SYNTAX INTEGER
				{
				base512kbps(0),
				upto2048kbps(1),
				upto5000kbps(2),
				upto9980kbps(3)
				}
			MAX-ACCESS read-only
			STATUS current
			DESCRIPTION
				"Data rate option, where:
				0 = Base (512 kbps)
				1 = Up to 2048 kbps
				2 = Up to 5000 kbps
				3 = Up to 9980 kbps"
			::= { cdm570SystemEquipmentID 3 }
		
		cdm570HigherOrderModulation OBJECT-TYPE
			SYNTAX INTEGER
				{
				none(0),
				modulation8PSK8QAM(1),
				modulation16QAM(2),
				modulation8PSK8QAM16QAM(3)
				}
			MAX-ACCESS read-only
			STATUS current
			DESCRIPTION
				"Higer order modulation, where:
				0 = None
				1 = 8-PSK/8-QAM
				2 = 16-QAM
				3 = 8-PSK/8-QAM and 16-QAM"
			::= { cdm570SystemEquipmentID 4 }
		
		cdm570IPOption OBJECT-TYPE
			SYNTAX INTEGER
				{
				none(0),
				installed(1)
				}
			MAX-ACCESS read-only
			STATUS current
			DESCRIPTION
				"IP Controller card, where:
				0 = None
				1 = Installed"
			::= { cdm570SystemEquipmentID 5 }
		
		cdm570RSCodecOption OBJECT-TYPE
			SYNTAX INTEGER
				{
				none(0),
				installed(1)
				}
			MAX-ACCESS read-only
			STATUS current
			DESCRIPTION
				"RS Codec Option, where:
				0 = None
				1 = Installed"
			::= { cdm570SystemEquipmentID 6 }
		
		cdm570SystemFirmware OBJECT IDENTIFIER ::= { cdm570System 3 }
		
		cdm570FirmwareRevision OBJECT-TYPE
			SYNTAX DisplayString (SIZE (34..37))
			MAX-ACCESS read-only
			STATUS current
			DESCRIPTION
				"Unit returns the value of the internal 
				software revision installed in the unit, 
				in the form of:
				Boot: XXXXXX Bulk1: YYYYYY Bulk2: ZZZZZZ, where:
				XXXXXX = software version of boot 
				YYYYYY = software version of bulk1
				ZZZZZZ = software version of bulk2"
			::= { cdm570SystemFirmware 1 }
		
		cdm570Config OBJECT IDENTIFIER ::= { cdm570Objects 2 }
		
		cdm570EthernetRemoteControl OBJECT IDENTIFIER ::= { cdm570Config 1 }
		
		cdm570IpAddress OBJECT-TYPE
			SYNTAX IpAddress
			MAX-ACCESS read-write
			STATUS current
			DESCRIPTION
				"The IP address for the 10/100 BaseTx Ethernet 
				management port."
			::= { cdm570EthernetRemoteControl 1 }
		
		cdm570IpSubnetMask OBJECT-TYPE
			SYNTAX INTEGER (0..31)
			UNITS "network prefix"
			MAX-ACCESS read-write
			STATUS current
			DESCRIPTION
				"The network prefix length for the 10/100 BaseTx 
				Ethernet management port."
			::= { cdm570EthernetRemoteControl 2 }
		
		cdm570DefaultGateway OBJECT-TYPE
			SYNTAX IpAddress
			MAX-ACCESS read-write
			STATUS current
			DESCRIPTION
				"The IP address of the default gateway."
			::= { cdm570EthernetRemoteControl 3 }
		
		cdm570MacAddress OBJECT-TYPE
			SYNTAX MacAddress
			MAX-ACCESS read-only
			STATUS current
			DESCRIPTION
				"The MAC address of the Ethernet interface."
			::= { cdm570EthernetRemoteControl 4 }
		
		cdm570AccessLists OBJECT IDENTIFIER ::= { cdm570EthernetRemoteControl 5 }
		
		cdm570AccessListEnforcement OBJECT-TYPE
			SYNTAX INTEGER
				{
				disabled(0),
				enabled(1)
				}
			MAX-ACCESS read-write
			STATUS current
			DESCRIPTION
				"Enable or disable enforcement of the the access 
				list.
				
				Note: Be sure that you have added the SNMP 
				browser's/manager's IP Address to the access 
				list before enabling access list filtering.
				Otherwise, the SNMP browser/manager will no 
				longer be able to gain access to the unit."
			::= { cdm570AccessLists 1 }
		
		cdm570AccessListTable OBJECT-TYPE
			SYNTAX SEQUENCE OF Cdm570AccessListEntry
			MAX-ACCESS not-accessible
			STATUS current
			DESCRIPTION
				"The table that holds the access list."
			::= { cdm570AccessLists 2 }
		
		cdm570AccessListEntry OBJECT-TYPE
			SYNTAX Cdm570AccessListEntry
			MAX-ACCESS not-accessible
			STATUS current
			DESCRIPTION
				"The entry for the access list table."
			INDEX { cdm570AccessListIndex }
			::= { cdm570AccessListTable 1 }
		
		Cdm570AccessListEntry ::=
			SEQUENCE { 
				cdm570AccessListIndex
					INTEGER,
				cdm570AccessIPAddress
					IpAddress,
				cdm570AccessSubnetMaskLength
					INTEGER
			 }

		cdm570AccessListIndex OBJECT-TYPE
			SYNTAX INTEGER (1..4)
			MAX-ACCESS read-only
			STATUS current
			DESCRIPTION
				"The index for the access list from 1..4."
			::= { cdm570AccessListEntry 1 }
		
		cdm570AccessIPAddress OBJECT-TYPE
			SYNTAX IpAddress
			MAX-ACCESS read-write
			STATUS current
			DESCRIPTION
				"The IP addresses that can access the unit.
				The value of 0.0.0.0 means not defined."
			::= { cdm570AccessListEntry 2 }
		
		cdm570AccessSubnetMaskLength OBJECT-TYPE
			SYNTAX INTEGER (0 | 8..32)
			MAX-ACCESS read-write
			STATUS current
			DESCRIPTION
				"The subnet mask length of the IP address 
				for the access list.  Subnet mask can be 
				from 8..32. The value of 0 means not defined."
			::= { cdm570AccessListEntry 3 }
		
		cdm570SNMP OBJECT IDENTIFIER ::= { cdm570EthernetRemoteControl 6 }
		
		cdm570SNMPTrapDestinationIpAddress1 OBJECT-TYPE
			SYNTAX IpAddress
			MAX-ACCESS read-write
			STATUS current
			DESCRIPTION
				"The IP address were SNMP notifications (traps)
				are to be sent.  This IP address should 
				correspond to a SNMP manager or browser."
			::= { cdm570SNMP 1 }
		
		cdm570SNMPTrapDestinationIpAddress2 OBJECT-TYPE
			SYNTAX IpAddress
			MAX-ACCESS read-write
			STATUS current
			DESCRIPTION
				"The IP address were SNMP notifications (traps)
				are to be sent.  This IP address should 
				correspond to a SNMP manager or browser."
			::= { cdm570SNMP 2 }
		
		cdm570SNMPTrapCommunity OBJECT-TYPE
			SYNTAX DisplayString
			MAX-ACCESS read-write
			STATUS current
			DESCRIPTION
				"The community that will be included in SNMP 
				notifications (traps) that are sent from unit."
			::= { cdm570SNMP 3 }
		
		cdm570SNMPTrapVersion OBJECT-TYPE
			SYNTAX INTEGER
				{
				snmpV1(1),
				snmpV2(2)
				}
			MAX-ACCESS read-write
			STATUS current
			DESCRIPTION
				"The SNMP version that will be used when sending 
				traps from the unit.  SNMPv1 will send V1 traps.
				SNMPv2 will send V2 notifications."
			::= { cdm570SNMP 4 }
		
		cdm570Tx OBJECT IDENTIFIER ::= { cdm570Config 2 }
		
		cdm570TxFrequency OBJECT-TYPE
			SYNTAX INTEGER (50000000..90000000 | 100000000..180000000 | 950000000..1950000000)
			UNITS "Hz"
			MAX-ACCESS read-write
			STATUS current
			DESCRIPTION
				"Transmit frequency for both CDM-570L (L-Band) modem and
				CDM-570 (IF-band) modems.
				  L-Band is 950 MHz to 1950 MHz.
				  IF-Band is 50 MHz to 90 MHz and 100 MHz to 180 MHz.
				Units = Hz.
				Resolution = 100 Hz."
			::= { cdm570Tx 1 }
		
		cdm570TxDataRate OBJECT-TYPE
			SYNTAX INTEGER (2400..9980000)
			UNITS "bps"
			MAX-ACCESS read-write
			STATUS current
			DESCRIPTION
				"Tx data rate in bps (Varies based on chart below.)
				Units = bps
				Resolution = 1 bps
				
				FEC Type   Modulation    Code Rate           Data Rate         High Rate
				--------   -----------   ----------   ---------------------    ---------
				None       BPSK          Uncoded      4.8 kbps to 3.0 Mbps    
				None       QPSK/OQPSK    Uncoded      9.6 kbps to 5.0 Mbps
				Viterbi    BPSK          Rate 1/2     2.4 kbps to 1.5 Mbps
				Viterbi    QPSK/OQPSK    Rate 1/2     4.8 kbps to 3.0 Mbps
				Viterbi    QPSK/OQPSK    Rate 3/4     7.2 kbps to 4.5 Mbps
				Viterbi    QPSK/OQPSK    Rate 7/8     8.4 kbps to 5.0 Mbps
				Vit + RS   BPSK          Rate 1/2     2.4 kbps to 1.363 Mbps   
				Vit + RS   QPSK/OQPSK    Rate 1/2     4.3 kbps to 2.727 Mbps
				Vit + RS   QPSK/OQPSK    Rate 3/4     6.5 kbps to 4.091 Mbps
				Vit + RS   QPSK/OQPSK    Rate 7/8     7.5 kbps to 4.666 Mbps
				Vit + RS   16-QAM        Rate 3/4     13.0 kbps to 4.0 Mbps
				Vit + RS   16-QAM        Rate 7/8     16.8 kbps to 4.666 Mbps
				TCM + RS   8-PSK         Rate 2/3     8.7 kbps to 4.4 Mbps
				Turbo      BPSK          Rate 5/16    2.4 kbps to 0.937 Mbps
				Turbo      BPSK          Rate 21/44   2.4 kbps to 1.430 Mbps
				Turbo      QPSK/OQPSK    Rate 21/44   4.8 kbps to 2.860 Mbps
				Turbo      QPSK/OQPSK    Rate 3/4     7.2 kbps to 4.5 Mbps      N/A
				Turbo      QPSK/OQPSK    Rate 7/8     8.4 kbps to 5.0 Mbps      5.25  Mbps
				Turbo      QPSK/OQPSK    Rate 0.95    9.1 kbps to 5.0 Mbps      5.667 Mbps
				Turbo      8-PSK/8-QAM   Rate 3/4     10.8 kbps to 5.0 Mbps     6.75  Mbps
				Turbo      8-PSK/Q-QAM   Rate 7/8     13.6 kbps to 5.0 Mbps     7.875 Mbps
				Turbo      8-PSK/Q-QAM   Rate 0.95    15.3 kbps to 5.0 Mbps     8.5   Mbps
				Turbo      16-QAM        Rate 3/4     14.4 kbps to 5.0 Mbps     9.0   Mbps
				Turbo      16-QAM        Rate 7/8     16.8 kbps to 5.0 Mbps     9.98  Mbps"
			::= { cdm570Tx 2 }
		
		cdm570TxFECCodeRate OBJECT-TYPE
			SYNTAX INTEGER
				{
				rate516(0),
				rate2144(1),
				rate12(2),
				rate23(3),
				rate34(4),
				rate78(5),
				rate095(6),
				uncoded(7)
				}
			MAX-ACCESS read-write
			STATUS current
			DESCRIPTION
				"Transmit code rate, where
				0 = Rate 5/16 (Turbo only)
				1 = Rate 22/44 (Turbo only)
				2 = Rate 1/2
				3 = Rate 2/3 (8-PSK TCM or 16-QAM only)
				4 = Rate 3/4
				5 = Rate 7/8
				6 = Rate 0.95 (Turbo only)
				7 = Rate 1/1 (Uncoded or No FEC)"
			::= { cdm570Tx 3 }
		
		cdm570TxModType OBJECT-TYPE
			SYNTAX INTEGER
				{
				modBPSK(0),
				modQPSK(1),
				modOQPSK(2),
				mod8PSK(3),
				mod16QAM(4),
				mod8QAM(5)
				}
			MAX-ACCESS read-write
			STATUS current
			DESCRIPTION
				"Transmit modulation type, where:
				0 = BPSK
				1 = QPSK
				2 = OQPSK
				3 = 8-PSK
				4 = 16-QAM (Turbo or Viterbi + RS only)
				5 = 8-QAM
				
				Depending on FEC type, not all of these 
				selections will be valid."
			::= { cdm570Tx 4 }
		
		cdm570TxFECType OBJECT-TYPE
			SYNTAX INTEGER
				{
				uncoded(0),
				viterbi(1),
				viterbiReedSolomon(2),
				tcmReedSolomon(5),
				turbo(6),
				tpcLdpc(7)
				}
			MAX-ACCESS read-write
			STATUS current
			DESCRIPTION
				"Transmit FEC type where:
				0 = Uncoded 
				1 = Viterbi
				2 = Viterbit + Reed-Solomon
				5 = TCM + Reed-Solomon (Code Rate = 2/3)
				6 = Turbo
				7 = TPC/LDPC
				
				Depending on hardware, not all of these 
				selections will be valid."
			::= { cdm570Tx 5 }
		
		cdm570TxSpectrumInvert OBJECT-TYPE
			SYNTAX INTEGER
				{
				normal(0),
				inverted(1)
				}
			MAX-ACCESS read-write
			STATUS current
			DESCRIPTION
				"Transmit spectrum invert selection, where:
				0 = Normal
				1 = Transmit spectrum inverted"
			::= { cdm570Tx 6 }
		
		cdm570TxDataInvert OBJECT-TYPE
			SYNTAX INTEGER
				{
				normal(0),
				inverted(1)
				}
			MAX-ACCESS read-write
			STATUS current
			DESCRIPTION
				"Invert transmit data, where:
				0 = Normal
				1 = Inverted"
			::= { cdm570Tx 7 }
		
		cdm570TxClockSource OBJECT-TYPE
			SYNTAX INTEGER
				{
				internal(0),
				txTerrestrial(1),
				loopTimed(2)
				}
			MAX-ACCESS read-write
			STATUS current
			DESCRIPTION
				"Transmit clock source, where:
				0 = Internal
				1 = Tx Terrestrial
				2 = Loop-Timed"
			::= { cdm570Tx 8 }
		
		cdm570TxScrambler OBJECT-TYPE
			SYNTAX INTEGER
				{
				off(0),
				onDefaul(1),
				onIESS315(2)
				}
			MAX-ACCESS read-write
			STATUS current
			DESCRIPTION
				"Transmit scrambler state, where:
				0 = Off
				1 = On (Default scrambler type)
				2 = On = IESS-315 (Turbo only)"
			::= { cdm570Tx 9 }
		
		cdm570TxPowerLevel OBJECT-TYPE
			SYNTAX INTEGER (-400..0)
			UNITS "0.1 dBm"
			MAX-ACCESS read-write
			STATUS current
			DESCRIPTION
				"Transmit output power level for both CDM-570L (L-Band) modem and
				CDM-570 (IF-band) modem.
				  CDM-570L power level is between -40 and 0 dBm.
				  CDM-570 power level is between -25 and 0 dBm.
				Units = 0.1 dBm"
			::= { cdm570Tx 10 }
		
		cdm570TxCarrierState OBJECT-TYPE
			SYNTAX INTEGER
				{
				off(0),
				on(1),
				rxTxInhibit(2),
				externalControlReadOnly(3),
				bucWarmUpDelayReadOnly(4),
				stdmaBurstReadOnly(5)
				}
			MAX-ACCESS read-write
			STATUS current
			DESCRIPTION
				"Transmit carrier state, where:
				0 = Off 
				1 = On
				2 = RTI (Receive/Transmit Inhibit)
				
				The following values are query only:
				3 = External Control (read only)
				4 = BUC warm-up delay (read only)
				5 = STDMA Burst (ready only)"
			::= { cdm570Tx 11 }
		
		cdm570TxSymbolRate OBJECT-TYPE
			SYNTAX INTEGER (4800..3000000)
			UNITS "sps"
			MAX-ACCESS read-only
			STATUS current
			DESCRIPTION
				"Tx symbol rate in symbols per second (sps)
				Units = symbols per second (sps)
				Resolution = 1 sps"
			::= { cdm570Tx 12 }
		
		cdm570Rx OBJECT IDENTIFIER ::= { cdm570Config 3 }
		
		cdm570RxFrequency OBJECT-TYPE
			SYNTAX INTEGER (50000000..90000000 | 100000000..180000000 | 950000000..1950000000)
			UNITS "Hz"
			MAX-ACCESS read-write
			STATUS current
			DESCRIPTION
				"Receive frequency for both CDM-570L (L-Band) modem and
				CDM-570 (IF-band) modems.
				  L-Band is 950 MHz to 1950 MHz.
				  IF-Band is 50 MHz to 90 MHz and 100 MHz to 180 MHz.
				Units = Hz.
				Resolution = 100 Hz."
			::= { cdm570Rx 1 }
		
		cdm570RxDataRate OBJECT-TYPE
			SYNTAX INTEGER (2400..9980000)
			UNITS "bps"
			MAX-ACCESS read-write
			STATUS current
			DESCRIPTION
				"Rx data rate in bps (Varies based on chart below.)
				Units = bps
				Resolution = 1 bps
				
				FEC Type   Modulation    Code Rate           Data Rate         High Rate
				--------   -----------   ----------   ---------------------    ---------
				None       BPSK          Uncoded      4.8 kbps to 3.0 Mbps    
				None       QPSK/OQPSK    Uncoded      9.6 kbps to 5.0 Mbps
				Viterbi    BPSK          Rate 1/2     2.4 kbps to 1.5 Mbps
				Viterbi    QPSK/OQPSK    Rate 1/2     4.8 kbps to 3.0 Mbps
				Viterbi    QPSK/OQPSK    Rate 3/4     7.2 kbps to 4.5 Mbps
				Viterbi    QPSK/OQPSK    Rate 7/8     8.4 kbps to 5.0 Mbps
				Vit + RS   BPSK          Rate 1/2     2.4 kbps to 1.363 Mbps   
				Vit + RS   QPSK/OQPSK    Rate 1/2     4.3 kbps to 2.727 Mbps
				Vit + RS   QPSK/OQPSK    Rate 3/4     6.5 kbps to 4.091 Mbps
				Vit + RS   QPSK/OQPSK    Rate 7/8     7.5 kbps to 4.666 Mbps
				Vit + RS   16-QAM        Rate 3/4     13.0 kbps to 4.0 Mbps
				Vit + RS   16-QAM        Rate 7/8     16.8 kbps to 4.666 Mbps
				TCM + RS   8-PSK         Rate 2/3     8.7 kbps to 4.4 Mbps
				Turbo      BPSK          Rate 5/16    2.4 kbps to 0.937 Mbps
				Turbo      BPSK          Rate 21/44   2.4 kbps to 1.430 Mbps
				Turbo      QPSK/OQPSK    Rate 21/44   4.8 kbps to 2.860 Mbps
				Turbo      QPSK/OQPSK    Rate 3/4     7.2 kbps to 4.5 Mbps      N/A
				Turbo      QPSK/OQPSK    Rate 7/8     8.4 kbps to 5.0 Mbps      5.25  Mbps
				Turbo      QPSK/OQPSK    Rate 0.95    9.1 kbps to 5.0 Mbps      5.667 Mbps
				Turbo      8-PSK/8-QAM   Rate 3/4     10.8 kbps to 5.0 Mbps     6.75  Mbps
				Turbo      8-PSK/Q-QAM   Rate 7/8     13.6 kbps to 5.0 Mbps     7.875 Mbps
				Turbo      8-PSK/Q-QAM   Rate 0.95    15.3 kbps to 5.0 Mbps     8.5   Mbps
				Turbo      16-QAM        Rate 3/4     14.4 kbps to 5.0 Mbps     9.0   Mbps
				Turbo      16-QAM        Rate 7/8     16.8 kbps to 5.0 Mbps     9.98  Mbps"
			::= { cdm570Rx 2 }
		
		cdm570RxFECCodeRate OBJECT-TYPE
			SYNTAX INTEGER
				{
				rate516(0),
				rate2144(1),
				rate12(2),
				rate23(3),
				rate34(4),
				rate78(5),
				rate095(6),
				uncoded(7)
				}
			MAX-ACCESS read-write
			STATUS current
			DESCRIPTION
				"Rx code rate, where
				0 = Rate 5/16 (Turbo only)
				1 = Rate 22/44 (Turbo only)
				2 = Rate 1/2
				3 = Rate 2/3 (8-PSK TCM or 16-QAM only)
				4 = Rate 3/4
				5 = Rate 7/8
				6 = Rate 0.95 (Turbo only)
				7 = Rate 1/1 (Uncoded or No FEC)"
			::= { cdm570Rx 3 }
		
		cdm570RxDemodType OBJECT-TYPE
			SYNTAX INTEGER
				{
				demodBPSK(0),
				demodQPSK(1),
				demodOQPSK(2),
				demod8PSK(3),
				demod16QAM(4),
				demod8QAM(5)
				}
			MAX-ACCESS read-write
			STATUS current
			DESCRIPTION
				"Rx demodulation type, where:
				0 = BPSK
				1 = QPSK
				2 = OQPSK
				3 = 8-PSK
				4 = 16-QAM (Turbo or Viterbi + RS only)
				5 = 8-QAM
				
				Depending on FEC type, not all of these 
				selections will be valid."
			::= { cdm570Rx 4 }
		
		cdm570RxFECType OBJECT-TYPE
			SYNTAX INTEGER
				{
				uncoded(0),
				viterbi(1),
				viterbiReedSolomon(2),
				tcmReedSolomon(5),
				turbo(6),
				tpcLdpc(7)
				}
			MAX-ACCESS read-write
			STATUS current
			DESCRIPTION
				"Rx FEC type where:
				0 = Uncoded
				1 = Viterbi
				2 = Viterbit + Reed-Solomon
				5 = TCM + Reed-Solomon (Code Rate = 2/3)
				6 = Turbo
				7 = TPC/LDPC
				
				Depending on hardware, not all of these 
				selections will be valid."
			::= { cdm570Rx 5 }
		
		cdm570RxEbNoAlarmPoint OBJECT-TYPE
			SYNTAX INTEGER (1..160)
			UNITS "0.1 dB"
			MAX-ACCESS read-write
			STATUS current
			DESCRIPTION
				"Rx Eb/No alarm point in 0.1 dB, with a 
				range between 0.1 dB and 16 dB.
				Units = 0.1 dB.
				Resolution = 0.1 dB."
			::= { cdm570Rx 6 }
		
		cdm570RxSpectrumInvert OBJECT-TYPE
			SYNTAX INTEGER
				{
				normal(0),
				inverted(1)
				}
			MAX-ACCESS read-write
			STATUS current
			DESCRIPTION
				"Rx spectrum inversion, where:
				0 = Normal
				1 = Rx spectrum inverted"
			::= { cdm570Rx 7 }
		
		cdm570RxDataInvert OBJECT-TYPE
			SYNTAX INTEGER
				{
				normal(0),
				inverted(1)
				}
			MAX-ACCESS read-write
			STATUS current
			DESCRIPTION
				"Invert receive data, where:
				0 = Normal
				1 = Inverted"
			::= { cdm570Rx 8 }
		
		cdm570RxBufferSize OBJECT-TYPE
			SYNTAX INTEGER
				{
				disabled(0),
				size1024bits(1),
				size2048bits(2),
				size4096bits(3),
				size8192bits(4),
				size16384bits(5),
				size32786bits(6),
				size128bits(7),
				size256bits(8),
				size512bits(9)
				}
			MAX-ACCESS read-write
			STATUS current
			DESCRIPTION
				"Rx buffer size, where:
				0 = Buffer disabled (Clock mode = Rx satellite)
				1 = +/- 1024 bits
				2 = +/- 2048 bits
				3 = +/- 4096 bits
				4 = +/- 8192 bits
				5 = +/- 16384 bits
				6 = +/- 32786 bits
				7 = +/- 128 bits
				8 = +/- 256 bits
				9 = +/- 512 bits"
			::= { cdm570Rx 9 }
		
		cdm570RxDescrambler OBJECT-TYPE
			SYNTAX INTEGER
				{
				off(0),
				onDefault(1),
				onIESS315(2)
				}
			MAX-ACCESS read-write
			STATUS current
			DESCRIPTION
				"Rx descrambler state, where:
				0 = Off
				1 = On (default descrambler type)
				2 = On - IESS-315 (Turbo only)"
			::= { cdm570Rx 10 }
		
		cdm570RxDemodAcqSweepWidth OBJECT-TYPE
			SYNTAX INTEGER (1..200)
			UNITS "KHz"
			MAX-ACCESS read-write
			STATUS current
			DESCRIPTION
				"Rx +/- acquisition sweep range of demodulator, 
				in KHz, ranging from:
				+/- 1 to +/- 32 KHz (rates < 625 ksym/second)
				or +/- 1 to 200 KHz (rates >= 625 ksym/second)."
			::= { cdm570Rx 11 }
		
		cdm570RxSymbolRate OBJECT-TYPE
			SYNTAX INTEGER (4800..3000000)
			UNITS "sps"
			MAX-ACCESS read-only
			STATUS current
			DESCRIPTION
				"Rx symbol rate in symbols per second (sps)
				Units = symbols per second (sps)
				Resolution = 1 sps"
			::= { cdm570Rx 12 }
		
		cdm570Frame OBJECT IDENTIFIER ::= { cdm570Config 4 }
		
		cdm570FramingMode OBJECT-TYPE
			SYNTAX INTEGER
				{
				unframed(0),
				framingEDMAC(1),
				framingEDMAC2(2)
				}
			MAX-ACCESS read-write
			STATUS current
			DESCRIPTION
				"Unit operating mode, where:
				0 = Unframed
				1 = EDMAC Framing
				2 = EDMAC-2 Framing"
			::= { cdm570Frame 1 }
		
		cdm570EDMAC OBJECT IDENTIFIER ::= { cdm570Frame 2 }
		
		cdm570EDMACMode OBJECT-TYPE
			SYNTAX INTEGER
				{
				idle(0),
				master(1),
				slave(2)
				}
			MAX-ACCESS read-write
			STATUS current
			DESCRIPTION
				"EDMAC mode, where:
				0 = EDMAC Idle
				1 = EDMAC Master
				2 = EDMAC Slave"
			::= { cdm570EDMAC 1 }
		
		cdm570EDMACAddress OBJECT-TYPE
			SYNTAX INTEGER (10..9990)
			MAX-ACCESS read-write
			STATUS current
			DESCRIPTION
				"For a Master, the EDMA Address is the range of 
				addresses of distant-end units (modems or 
				transceivers) which this unit, as the Master, 
				will forward messages for. Only values which 
				are integer multiples of ten are permitted. 
				(10, 20, 30, 40, etc....)
				
				For a Slave, the EDMAC address is the address 
				of the slave and is query only."
			::= { cdm570EDMAC 2 }
		
		cdm570AUPC OBJECT IDENTIFIER ::= { cdm570Frame 3 }
		
		cdm570AUPCEnable OBJECT-TYPE
			SYNTAX INTEGER
				{
				disable(0),
				enable(1)
				}
			MAX-ACCESS read-write
			STATUS current
			DESCRIPTION
				"AUPC mode enable/disable, where:
				0 = Disable
				1 = Enable
				Note: To enable AUPC, framing must 
				      FIRST be enabled."
			::= { cdm570AUPC 1 }
		
		cdm570AUPCRemoteDemodTargetEbNo OBJECT-TYPE
			SYNTAX INTEGER (0..149)
			UNITS "0.1 dB"
			MAX-ACCESS read-write
			STATUS current
			DESCRIPTION
				"Target Eb/No value for remote demod, 
				from 0.0 to 14.9 dB.
				Units = 0.1 dB."
			::= { cdm570AUPC 2 }
		
		cdm570AUPCTxPowerMaxIncrease OBJECT-TYPE
			SYNTAX INTEGER (0..9)
			UNITS "dB"
			MAX-ACCESS read-write
			STATUS current
			DESCRIPTION
				"Max increase in Tx Power permitted, 
				from 0 to 9 dB.
				Units = dB."
			::= { cdm570AUPC 3 }
		
		cdm570AUPCActionOnMaxPower OBJECT-TYPE
			SYNTAX INTEGER
				{
				noAction(0),
				generateTxAlarm(1)
				}
			MAX-ACCESS read-write
			STATUS current
			DESCRIPTION
				"Defines action on max. power condition, where:
				0 = No action
				1 = Generate Tx alarm"
			::= { cdm570AUPC 4 }
		
		cdm570AUPCActionOnRemoteDemodUnlock OBJECT-TYPE
			SYNTAX INTEGER
				{
				goToNominalPower(0),
				goToMaxPower(1)
				}
			MAX-ACCESS read-write
			STATUS current
			DESCRIPTION
				"Defines action on remote demod unlock, where:
				0 = Go to nominal power
				1 = Go to max power"
			::= { cdm570AUPC 5 }
		
		cdm570Interface OBJECT IDENTIFIER ::= { cdm570Config 5 }
		
		cdm570DataInterface OBJECT-TYPE
			SYNTAX INTEGER
				{
				interfaceEIA422(0),
				interfaceV35(1),
				interfaceEIA232(2),
				interfaceG703T1AMI(3),
				interfaceG703T1B8ZS(4),
				interfaceG703E1UnbalAMI(5),
				interfaceG703E1UnbalHDB3(6),
				interfaceG703E1BalAMI(7),
				interfaceG703E1BalHDB3(8),
				interfaceIP(9)
				}
			MAX-ACCESS read-write
			STATUS current
			DESCRIPTION
				"Terrestrial interface type, where:
				0 = EIA-422/EIA-530 DCE
				1 = V.35 DCE
				2 = EIA-232 (sync)
				3 = G.703 T1 AMI 
				    (forces Rx and Tx data rates to 1544 kbps)
				4 = G.703 T1 B8ZS 
				    (forces Rx and Tx data rates to 1544 kbps)
				5 = G.703 E1 Unbal AMI 
				    (forces Rx and Tx data rates to 2048 kbps)
				6 = G.703 E1 Unbal HDB3 
				    (forces Rx and Tx data rates to 2048 kbps)
				7 = G.703 E1 Bal AMI 
				    (forces Rx and Tx data rates to 2048 kbps)
				8 = G.703 E1 Bal HDB3 
				    (forces Rx and Tx data rates to 2048 kbps)
				9 = IP (Ethernet)"
			::= { cdm570Interface 1 }
		
		cdm570RTSCTSOper OBJECT IDENTIFIER ::= { cdm570Interface 2 }
		
		cdm570RTS OBJECT-TYPE
			SYNTAX INTEGER
				{
				loopRTSCTSNoAction(0),
				loopRTSControlsTx(1),
				ignoreRTSAssertCTS(2),
				ignoreRTSCTS(3)
				}
			MAX-ACCESS read-write
			STATUS current
			DESCRIPTION
				"Defines how RTS/CTS will operate at the main data 
				interface, where:
				0 = RTS/CTS Loop, No Action 
				    (RTS and CTS are looped, so that CTS echoes
				     the state of RTS, but RTS does not control
				     the ON/OFF state of the carrier)
				1 = Loop, RTS controls Tx Ouput 
				    (RTS and CTS are looped, so that CTS 
				     echoes the state of RTS and RTS 
				     controls the ON/OFF state of the 
				     carrier - the modem will not bring 
				     up its TX carrier until RTS is asserted.)
				2 = Ignore RTS, Assert CTS
				
				Query Only:
				3 = 1:N system in use, RTS/CTS ignored
				"
			::= { cdm570RTSCTSOper 1 }
		
		cdm570G703T1 OBJECT IDENTIFIER ::= { cdm570Interface 3 }
		
		cdm570T1LineBuildOut OBJECT-TYPE
			SYNTAX INTEGER
				{
				distance0To133feet(0),
				distance133To266feet(1),
				distance266To399feet(2),
				distance399To533feet(3),
				distance533To655feet(4)
				}
			MAX-ACCESS read-write
			STATUS current
			DESCRIPTION
				"Valid only for T1 interface, where:
				0 = 0 - 133 feet
				1 = 133 - 266 feet
				2 = 266 - 399 feet
				3 = 399 - 533 feet
				4 = 533 - 655 feet"
			::= { cdm570G703T1 1 }
		
		cdm570Reference OBJECT IDENTIFIER ::= { cdm570Config 6 }
		
		cdm570ReferenceFrequency OBJECT-TYPE
			SYNTAX INTEGER
				{
				int10MHz(0),
				ext1MHz(1),
				ext2MHz(2),
				ext5MHz(3),
				ext10MHz(4),
				ext20MHz(5)
				}
			MAX-ACCESS read-write
			STATUS current
			DESCRIPTION
				"External reference frequency, where:
				0 = Internal 10 MHz
				1 = External 1 MHz
				2 = External 2 MHz
				3 = External 5 MHz
				4 = External 10 MHz
				5 = External 20 MHz"
			::= { cdm570Reference 1 }
		
		cdm570AlarmMask OBJECT IDENTIFIER ::= { cdm570Config 7 }
		
		cdm570AlarmMaskTxFIFO OBJECT-TYPE
			SYNTAX INTEGER
				{
				unmasked(0),
				masked(1)
				}
			MAX-ACCESS read-write
			STATUS current
			DESCRIPTION
				"Tx FIFO alarm mask, where:
				0 = Unmasked
				1 = Masked"
			::= { cdm570AlarmMask 1 }
		
		cdm570AlarmMaskG703BPV OBJECT-TYPE
			SYNTAX INTEGER
				{
				unmasked(0),
				masked(1)
				}
			MAX-ACCESS read-write
			STATUS current
			DESCRIPTION
				"G.703 BPV alarm mask, where:
				0 = Unmasked
				1 = Masked"
			::= { cdm570AlarmMask 2 }
		
		cdm570AlarmMaskTxAIS OBJECT-TYPE
			SYNTAX INTEGER
				{
				unmasked(0),
				masked(1)
				}
			MAX-ACCESS read-write
			STATUS current
			DESCRIPTION
				"Tx-AIS alarm mask, where:
				0 = Unmasked
				1 = Masked"
			::= { cdm570AlarmMask 3 }
		
		cdm570AlarmMaskRxAGC OBJECT-TYPE
			SYNTAX INTEGER
				{
				unmasked(0),
				masked(1)
				}
			MAX-ACCESS read-write
			STATUS current
			DESCRIPTION
				"Rx AGC alarm mask, where:
				0 = Unmasked
				1 = Masked"
			::= { cdm570AlarmMask 4 }
		
		cdm570AlarmMaskEbNoAlarm OBJECT-TYPE
			SYNTAX INTEGER
				{
				unmasked(0),
				masked(1)
				}
			MAX-ACCESS read-write
			STATUS current
			DESCRIPTION
				"Eb/No alarm mask, where:
				0 = Unmasked
				1 = Masked"
			::= { cdm570AlarmMask 5 }
		
		cdm570AlarmMaskRxAIS OBJECT-TYPE
			SYNTAX INTEGER
				{
				unmasked(0),
				masked(1)
				}
			MAX-ACCESS read-write
			STATUS current
			DESCRIPTION
				"Rx-AIS alarm mask, where:
				0 = Unmasked
				1 = Masked"
			::= { cdm570AlarmMask 6 }
		
		cdm570AlarmMaskBufferSlip OBJECT-TYPE
			SYNTAX INTEGER
				{
				unmasked(0),
				masked(1)
				}
			MAX-ACCESS read-write
			STATUS current
			DESCRIPTION
				"Buffer slip alarm mask, where:
				0 = Unmasked
				1 = Masked"
			::= { cdm570AlarmMask 7 }
		
		cdm570AlarmMaskExtReference OBJECT-TYPE
			SYNTAX INTEGER
				{
				unmasked(0),
				masked(1)
				}
			MAX-ACCESS read-write
			STATUS current
			DESCRIPTION
				"External reference alarm mask, where:
				0 = Unmasked
				1 = Masked"
			::= { cdm570AlarmMask 8 }
		
		cdm570ODU OBJECT IDENTIFIER ::= { cdm570Config 8 }
		
		cdm570Monitor OBJECT IDENTIFIER ::= { cdm570Objects 3 }
		
		cdm570Alarms OBJECT IDENTIFIER ::= { cdm570Monitor 1 }
		
		cdm570UnitAlarms OBJECT-TYPE
			SYNTAX INTEGER
				{
				noFaults(0),
				powerSupply5volts(1),
				powerSupply12volts(2),
				powerSupplyNeg5volts(3),
				powerSupply23volts(4),
				powerSupplyNeg12volts(5),
				txSynthesizerLock(6),
				rx1stLOSynthesizerLock(7),
				rx2ndLOSynthesizerLock(8),
				refPLLLock(9),
				mpp50Fault(14),
				checksumErrorEEPROM(15)
				}
			MAX-ACCESS read-only
			STATUS current
			DESCRIPTION
				"Modem Unit Faults:
				
				Value    Description of unit fault
				
				  0      No faults
				  1      +5 Volt power supply 
				  2      +12 Volt power supply 
				  3      -5 Volt power supply 
				  4      +23 Volt power supply 
				  5      -12 Volt power supply 
				  6      Tx synthesizer lock
				  7      Rx 1st LO synthesize lock
				  8      Rx 2nd LO synthesize lock
				  9      Ref PLL lock
				 14      MPP50 (IP Module) Fault
				 15      EEPROM checksum error
				"
			::= { cdm570Alarms 1 }
		
		cdm570TxAlarms OBJECT-TYPE
			SYNTAX INTEGER
				{
				txTrafficOK(0),
				noClockFromTerrestrialInterface(1),
				txFIFOSlip(3),
				lostExternalReference(5),
				aupcUpperLimitReached(7),
				aisDetectedOnIncomingData(9),
				bipolarViolationOnG703Interface(11)
				}
			MAX-ACCESS read-only
			STATUS current
			DESCRIPTION
				"Modem TX Traffic Faults:
				
				Value    Description of Tx Traffic status
				
				  0      Tx traffic OK
				  1      No clock from terrestrial interface 
				  3      Tx FIFO slip
				  5      Loss of External Reference 
				  7      AUPC upper limit reached
				  9      AIS Detected on incoming data 
				  11     Bipolar violation on G.705 interface
				"
			::= { cdm570Alarms 2 }
		
		cdm570RxAlarms OBJECT-TYPE
			SYNTAX INTEGER
				{
				rxTrafficOK(0),
				demodulatorUnlocked(1),
				agcAlarmSignalOutOfRange(3),
				rsFrameSyncAlarm(5),
				edmacFrameSyncAlarm(7),
				bufferUnderflow(10),
				bufferOverflow(11),
				ebNoAlarm(13),
				aisDetectedOnIncomingData(15)
				}
			MAX-ACCESS read-only
			STATUS current
			DESCRIPTION
				"Modem RX Traffic Faults
				
				Value   Description of status parameter
				
				  0      Rx Traffic OK
				  1      Demodulator unlocked 
				  3      AGC Alarm - signal out of range
				  5      RS Frame sync alarm
				  7      EDMAC Frame sync alarm
				  10     Buffer underflow
				  11     Buffer overflow
				  13     Eb/No alarm
				  15     AIS detected on incoming data
				"
			::= { cdm570Alarms 3 }
		
		cdm570RxParams OBJECT IDENTIFIER ::= { cdm570Monitor 2 }
		
		cdm570RxBERMultiplier OBJECT-TYPE
			SYNTAX INTEGER (0..999999999 | 2147483647)
			UNITS "Scale Factor by  10E-10"
			MAX-ACCESS read-only
			STATUS current
			DESCRIPTION
				"Estimated corrected BER.  The BER is calculated 
				by mubliplying the Multiplier by 10E-10.
				
				Calculuation:
				RxBER = (Multiplier) * 0.0000000001
				
				Returns 2147483647 (max int) if demod is unlocked."
			::= { cdm570RxParams 1 }
		
		cdm570BufferFillState OBJECT-TYPE
			SYNTAX INTEGER (-1 | 0 | 1..99)
			UNITS "% (percentage)"
			MAX-ACCESS read-only
			STATUS current
			DESCRIPTION
				"Unit returns the value of the buffer fill state, 
				between 1 to 99%.
				Returns 0 if demodulator is unlocked.
				Returns -1 if buffer is disabled."
			::= { cdm570RxParams 2 }
		
		cdm570RxFrequencyOffset OBJECT-TYPE
			SYNTAX INTEGER (-200000..200000 | 999900)
			UNITS "Hz"
			MAX-ACCESS read-only
			STATUS current
			DESCRIPTION
				"Unit returns the value of the measured frequency 
				offset of the carrier being demodulated in Hz.
				Units = Hz.
				Resolution 100 Hz.
				Range = -200,000 Hz to 0 Hz and 
				        0 Hz to 200,000 Hz."
			::= { cdm570RxParams 3 }
		
		cdm570RxSignalLevel OBJECT-TYPE
			SYNTAX INTEGER (-100 | -99..-5 | -4)
			UNITS "dBm"
			MAX-ACCESS read-only
			STATUS current
			DESCRIPTION
				"Unit returns the value of the Rx signal level, 
				in dBm, between -99 dBm and -5 dBm.
				Returns -100 if signal is less than -99 dBm.
				Returns  -4 if signal is greater than -5 dBm."
			::= { cdm570RxParams 4 }
		
		cdm570RxEbNo OBJECT-TYPE
			SYNTAX INTEGER (0..160 | 999)
			UNITS "0.1 dB"
			MAX-ACCESS read-only
			STATUS current
			DESCRIPTION
				"Unit returns the value of Eb/No, between 
				0 and 16 db.
				Units = 0.1 dB.
				Resolution 0.1 dB.
				
				Returns 999 if demod is unlocked.
				
				For values greater than 16 dB, the reply 
				will be 160."
			::= { cdm570RxParams 5 }
		
		cdm570EventLog OBJECT IDENTIFIER ::= { cdm570Monitor 3 }
		
		cdm570StoredEventsTable OBJECT-TYPE
			SYNTAX SEQUENCE OF Cdm570StoredEventsEntry
			MAX-ACCESS not-accessible
			STATUS current
			DESCRIPTION
				"The table for stored events."
			::= { cdm570EventLog 1 }
		
		cdm570StoredEventsEntry OBJECT-TYPE
			SYNTAX Cdm570StoredEventsEntry
			MAX-ACCESS not-accessible
			STATUS current
			DESCRIPTION
				"The entry for the stored events table."
			INDEX { cdm570EventIndex }
			::= { cdm570StoredEventsTable 1 }
		
		Cdm570StoredEventsEntry ::=
			SEQUENCE { 
				cdm570EventIndex
					INTEGER,
				cdm570EventDate
					DisplayString,
				cdm570EventTime
					DisplayString,
				cdm570EventDescription
					DisplayString
			 }

		cdm570EventIndex OBJECT-TYPE
			SYNTAX INTEGER (1..255)
			MAX-ACCESS read-only
			STATUS current
			DESCRIPTION
				"The index for stored events table."
			::= { cdm570StoredEventsEntry 1 }
		
		cdm570EventDate OBJECT-TYPE
			SYNTAX DisplayString (SIZE (6))
			MAX-ACCESS read-only
			STATUS current
			DESCRIPTION
				"The date of the event in the form ddmmyy, where
				dd = day of the month (01 to 31)
				mm = month (01 to 12)
				yy = year (00 to 99)"
			::= { cdm570StoredEventsEntry 2 }
		
		cdm570EventTime OBJECT-TYPE
			SYNTAX DisplayString (SIZE (6))
			MAX-ACCESS read-only
			STATUS current
			DESCRIPTION
				"The time of the event in the form hhmmss, 
				indicating the time from midnight, where:
				hh = hours (00 to 23)
				mm = minutes (00 to 59)
				ss = seconds (00 to 59)"
			::= { cdm570StoredEventsEntry 3 }
		
		cdm570EventDescription OBJECT-TYPE
			SYNTAX DisplayString
			MAX-ACCESS read-only
			STATUS current
			DESCRIPTION
				"The event description string with following format:
				{1 of the following: Clear, Fault, Info} - 
				{Texual Description of Event}"
			::= { cdm570StoredEventsEntry 4 }
		
		cdm570ClearAllStoredEvents OBJECT-TYPE
			SYNTAX INTEGER { clearAll(1) }
			MAX-ACCESS read-write
			STATUS current
			DESCRIPTION
				"Forces the software to clear the event log.
				This is a command only."
			::= { cdm570EventLog 2 }
		
		cdm570Statistics OBJECT IDENTIFIER ::= { cdm570Monitor 4 }
		
		cdm570StatisticsSampleInterval OBJECT-TYPE
			SYNTAX INTEGER
				{
				disabled(0),
				mins10(1),
				mins20(2),
				mins30(3),
				mins40(4),
				mins50(5),
				mins60(6),
				mins70(7),
				mins80(8),
				mins90(9)
				}
			MAX-ACCESS read-write
			STATUS current
			DESCRIPTION
				"Used to set the sample interval for the 
				statistics logging function, where the 
				enumerated lists goes from 0 to 9 in 
				10 minute steps.
				
				Setting 0 disables the statistics logging 
				function."
			::= { cdm570Statistics 1 }
		
		cdm570StoredStatisticsTable OBJECT-TYPE
			SYNTAX SEQUENCE OF Cdm570StoredStatisticsEntry
			MAX-ACCESS not-accessible
			STATUS current
			DESCRIPTION
				"Description."
			::= { cdm570Statistics 2 }
		
		cdm570StoredStatisticsEntry OBJECT-TYPE
			SYNTAX Cdm570StoredStatisticsEntry
			MAX-ACCESS not-accessible
			STATUS current
			DESCRIPTION
				"Entry for stored statistics table."
			INDEX { cdm570StatisticIndex }
			::= { cdm570StoredStatisticsTable 1 }
		
		Cdm570StoredStatisticsEntry ::=
			SEQUENCE { 
				cdm570StatisticIndex
					INTEGER,
				cdm570StatisticDate
					DisplayString,
				cdm570StatisticTime
					DisplayString,
				cdm570StatisticMinEbNo
					INTEGER,
				cdm570StatisticAvgEbNo
					INTEGER,
				cdm570StatisticMaxTxPowerIncrease
					INTEGER,
				cdm570StatisticAvgTxPowerIncrease
					INTEGER
			 }

		cdm570StatisticIndex OBJECT-TYPE
			SYNTAX INTEGER (1..255)
			MAX-ACCESS read-only
			STATUS current
			DESCRIPTION
				"Index for stored statistics table."
			::= { cdm570StoredStatisticsEntry 1 }
		
		cdm570StatisticDate OBJECT-TYPE
			SYNTAX DisplayString (SIZE (6))
			MAX-ACCESS read-only
			STATUS current
			DESCRIPTION
				"The date of the statistic in the 
				form ddmmyy, where:
				dd = day of the month (01 to 31)
				mm = month (01 to 12)
				yy = year (00 to 99)"
			::= { cdm570StoredStatisticsEntry 2 }
		
		cdm570StatisticTime OBJECT-TYPE
			SYNTAX DisplayString (SIZE (6))
			MAX-ACCESS read-only
			STATUS current
			DESCRIPTION
				"The time of the statistic in the form hhmmss, 
				indicating the time from midnight, where:
				hh = hours (00 to 23)
				mm = minutes (00 to 59)
				ss = seconds (00 to 59)"
			::= { cdm570StoredStatisticsEntry 3 }
		
		cdm570StatisticMinEbNo OBJECT-TYPE
			SYNTAX INTEGER (0..160 | 999)
			UNITS "0.1 dB"
			MAX-ACCESS read-only
			STATUS current
			DESCRIPTION
				"Minimum Eb/No during sample period.
				Units = 0.1 dB.
				Returns 999 if demod was unlocked 
				during sample period.
				"
			::= { cdm570StoredStatisticsEntry 4 }
		
		cdm570StatisticAvgEbNo OBJECT-TYPE
			SYNTAX INTEGER (0..160 | 999)
			UNITS "0.1 dB"
			MAX-ACCESS read-only
			STATUS current
			DESCRIPTION
				"Minimum Eb/No during sample period.
				Units = 0.1 dB.
				Returns 999 if demod was unlocked 
				during sample period."
			::= { cdm570StoredStatisticsEntry 5 }
		
		cdm570StatisticMaxTxPowerIncrease OBJECT-TYPE
			SYNTAX INTEGER (0..99)
			UNITS "0.1 dB"
			MAX-ACCESS read-only
			STATUS current
			DESCRIPTION
				"Max. Tx power level increase during 
				sample period.
				Units = 0.1 dB"
			::= { cdm570StoredStatisticsEntry 6 }
		
		cdm570StatisticAvgTxPowerIncrease OBJECT-TYPE
			SYNTAX INTEGER (0..99)
			UNITS "0.1 dB"
			MAX-ACCESS read-only
			STATUS current
			DESCRIPTION
				"Average Tx power level increase 
				during sample period.
				Units = 0.1 dB"
			::= { cdm570StoredStatisticsEntry 7 }
		
		cdm570ClearAllStoredStatistics OBJECT-TYPE
			SYNTAX INTEGER { clearAll(1) }
			MAX-ACCESS read-write
			STATUS current
			DESCRIPTION
				"Forces the software to clear the statistics log.
				This is a command only."
			::= { cdm570Statistics 3 }
		
		cdm570AUPCParams OBJECT IDENTIFIER ::= { cdm570Monitor 5 }
		
		cdm570AUPCRemoteDemodEbNo OBJECT-TYPE
			SYNTAX INTEGER (0 | 20..160 | 999)
			UNITS "0.1 dB"
			MAX-ACCESS read-only
			STATUS current
			DESCRIPTION
				"Returns the value of the Eb/No ofthe remote 
				demodulator.
				Units = 0.1 dB
				Responds 999 = remote demod unlocked.
				Responds 0   = EDMAC is disabled."
			::= { cdm570AUPCParams 1 }
		
		cdm570AUPCTxPowerIncrease OBJECT-TYPE
			SYNTAX INTEGER (0..90 | 999)
			UNITS "0.1 dB"
			MAX-ACCESS read-only
			STATUS current
			DESCRIPTION
				"Returns the increase in Tx power level, in 
				0.1 dB (from the nominal setting) due to 
				the action of AUPC.
				Responds with 999 if AUPC is disabled."
			::= { cdm570AUPCParams 2 }
		
		cdm570ODUParams OBJECT IDENTIFIER ::= { cdm570Monitor 6 }
		
		cdm570Test OBJECT IDENTIFIER ::= { cdm570Objects 4 }
		
		cdm570UnitTestMode OBJECT-TYPE
			SYNTAX INTEGER
				{
				normalMode(0),
				ifLoopBack(1),
				digitalLoopBack(2),
				ioLoopBack(3),
				rfLoopback(4),
				txCW(5),
				txAlternatingPattern(6)
				}
			MAX-ACCESS read-write
			STATUS current
			DESCRIPTION
				"Unit Test Mode where:
				0 = Normal Mode
				1 = IF Loopback
				2 = Digital Loopback
				3 = IO Loopback
				4 = RF Loopback
				5 = Tx CW
				6 = Tx Alternating Pattern"
			::= { cdm570Test 1 }
		
		cdm570SaveLoad OBJECT IDENTIFIER ::= { cdm570Objects 5 }
		
		cdm570ConfigurationSave OBJECT-TYPE
			SYNTAX INTEGER (0..9)
			MAX-ACCESS read-write
			STATUS current
			DESCRIPTION
				"Causes the device to store the current modem 
				configuration in configuration memory location 
				defined by the argument (0 to 9).
				This is a COMMAND ONLY. Get always responds with 0."
			::= { cdm570SaveLoad 1 }
		
		cdm570ConfigurationLoad OBJECT-TYPE
			SYNTAX INTEGER (0..9)
			MAX-ACCESS read-write
			STATUS current
			DESCRIPTION
				"Causes the device to retrieve a previously 
				stored modem configuration from configuration 
				memory location defined by the argument (0 to 9).
				This is a COMMAND ONLY. Get always responds with 0."
			::= { cdm570SaveLoad 2 }
		
		cdm570Util OBJECT IDENTIFIER ::= { cdm570Objects 6 }
		
		cdm570Buffer OBJECT IDENTIFIER ::= { cdm570Util 1 }
		
		cdm570ReCenterBuffer OBJECT-TYPE
			SYNTAX INTEGER { reCenter(1) }
			MAX-ACCESS read-write
			STATUS current
			DESCRIPTION
				"Forces the software to recenter the receive 
				Plesiochronous/Doppler buffer.  
				This is a command only."
			::= { cdm570Buffer 1 }
		
		cdm570RealTimeClock OBJECT IDENTIFIER ::= { cdm570Util 2 }
		
		cdm570RTCDate OBJECT-TYPE
			SYNTAX DisplayString (SIZE (8))
			MAX-ACCESS read-write
			STATUS current
			DESCRIPTION
				"A date in the form dd/mm/yy, where
				dd = day of the month (01 to 31)
				mm = month (01 to 12)
				yy = year (00 to 99)"
			::= { cdm570RealTimeClock 1 }
		
		cdm570RTCTime OBJECT-TYPE
			SYNTAX DisplayString (SIZE (8))
			MAX-ACCESS read-write
			STATUS current
			DESCRIPTION
				"A time in the form hh:mm:ss, indicating the time
				from midnight, where:
				hh = hours (00 to 23)
				mm = minutes (00 to 59)
				ss = seconds (00 to 59)"
			::= { cdm570RealTimeClock 2 }
		
		cdm570InternalReference OBJECT IDENTIFIER ::= { cdm570Util 3 }
		
		cdm570WarmUpDelay OBJECT-TYPE
			SYNTAX INTEGER
				{
				disable(0),
				enable(1)
				}
			MAX-ACCESS read-write
			STATUS current
			DESCRIPTION
				"Warm-up delay for internal frequency reference 
				(OCXO), where:
				0 = Disabled (instant on - no delay for 
				              OCXO to reach temperature)
				1 = Enabled (unit waits until OCXO reaches 
				             correct temperature)"
			::= { cdm570InternalReference 2 }
		
		cdm570WarmUpCountdown OBJECT-TYPE
			SYNTAX INTEGER (0..200)
			UNITS "secs"
			MAX-ACCESS read-write
			STATUS current
			DESCRIPTION
				"As a query, returns the Warm-up delay countdown 
				in seconds remaining. As a command, only takes 
				the argument 0 and is used to truncate the 
				warm-up delay period to zero, forcing the unit 
				into 'instanct-on' mode."
			::= { cdm570InternalReference 3 }
		
		cdm570ID OBJECT IDENTIFIER ::= { cdm570Util 4 }
		
		cdm570CircuitID OBJECT-TYPE
			SYNTAX DisplayString (SIZE (0..24))
			MAX-ACCESS read-write
			STATUS current
			DESCRIPTION
				"Sets or queries the user-defined Circuit 
				ID string, which is a fixed length of 
				24 characters.
				
				Valid characters include: 
				Space ( ) * + - , . / 0 thru 9 and A thru Z "
			::= { cdm570ID 1 }
		
		cdm570Redundancy OBJECT IDENTIFIER ::= { cdm570Util 5 }
		
		cdm570RedundancyState OBJECT-TYPE
			SYNTAX INTEGER
				{
				offline(0),
				online(1)
				}
			MAX-ACCESS read-only
			STATUS current
			DESCRIPTION
				"Unit returns the redundancy state of the unit, 
				where:
				0 = Offline
				1 = Online"
			::= { cdm570Redundancy 1 }
		
		cdm570ForceRedundentSwitch OBJECT-TYPE
			SYNTAX INTEGER { forceSwitch(1) }
			MAX-ACCESS read-write
			STATUS current
			DESCRIPTION
				"Force redundundent switch command."
			::= { cdm570Redundancy 2 }
		
		cdm570ODUComms OBJECT IDENTIFIER ::= { cdm570Util 6 }
		
		cdm570ODUCommsEnabled OBJECT-TYPE
			SYNTAX INTEGER
				{
				disabled(0),
				enabled(1)
				}
			MAX-ACCESS read-write
			STATUS current
			DESCRIPTION
				"ODU Comms, where
				0 = Disabled
				1 = Enabled"
			::= { cdm570ODUComms 1 }
		
		cdm570Notifications OBJECT IDENTIFIER ::= { cdm570 2 }
		
		cdm570NotificationsPrefix OBJECT IDENTIFIER ::= { cdm570Notifications 0 }
		
		cdm570UnitAlarm NOTIFICATION-TYPE
			OBJECTS { cdm570UnitAlarms }
			STATUS current
			DESCRIPTION
				"Modem Unit Faults Trap"
			::= { cdm570NotificationsPrefix 1 }
		
		cdm570TxTrafficAlarm NOTIFICATION-TYPE
			OBJECTS { cdm570TxAlarms }
			STATUS current
			DESCRIPTION
				"Modem TX Traffic Faults Trap"
			::= { cdm570NotificationsPrefix 2 }
		
		cdm570RxTrafficAlarm NOTIFICATION-TYPE
			OBJECTS { cdm570RxAlarms }
			STATUS current
			DESCRIPTION
				"Modem RX Traffic Faults Trap"
			::= { cdm570NotificationsPrefix 3 }
		
		cdm570Conformance OBJECT IDENTIFIER ::= { cdm570 3 }
		
		cdm570Groups OBJECT IDENTIFIER ::= { cdm570Conformance 1 }
		
		cdm570ObjectsGroup OBJECT-GROUP
			OBJECTS { cdm570SerialNumber, cdm570Temperature, cdm570TurboOption, cdm570ModelNumber, cdm570DataRateOption, 
				cdm570HigherOrderModulation, cdm570IPOption, cdm570RSCodecOption, cdm570FirmwareRevision, cdm570IpAddress, 
				cdm570IpSubnetMask, cdm570DefaultGateway, cdm570MacAddress, cdm570AccessListEnforcement, cdm570AccessListIndex, 
				cdm570AccessIPAddress, cdm570AccessSubnetMaskLength, cdm570SNMPTrapDestinationIpAddress1, cdm570SNMPTrapDestinationIpAddress2, cdm570SNMPTrapCommunity, 
				cdm570SNMPTrapVersion, cdm570TxFrequency, cdm570TxDataRate, cdm570TxFECCodeRate, cdm570TxModType, 
				cdm570TxFECType, cdm570TxSpectrumInvert, cdm570TxDataInvert, cdm570TxClockSource, cdm570TxScrambler, 
				cdm570TxPowerLevel, cdm570TxCarrierState, cdm570RxFrequency, cdm570RxDataRate, cdm570RxFECCodeRate, 
				cdm570RxDemodType, cdm570RxFECType, cdm570RxEbNoAlarmPoint, cdm570RxSpectrumInvert, cdm570RxDataInvert, 
				cdm570RxBufferSize, cdm570RxDescrambler, cdm570RxDemodAcqSweepWidth, cdm570FramingMode, cdm570EDMACMode, 
				cdm570EDMACAddress, cdm570AUPCEnable, cdm570AUPCRemoteDemodTargetEbNo, cdm570AUPCTxPowerMaxIncrease, cdm570AUPCActionOnMaxPower, 
				cdm570AUPCActionOnRemoteDemodUnlock, cdm570DataInterface, cdm570RTS, cdm570T1LineBuildOut, cdm570ReferenceFrequency, 
				cdm570AlarmMaskTxFIFO, cdm570AlarmMaskG703BPV, cdm570AlarmMaskTxAIS, cdm570AlarmMaskRxAGC, cdm570AlarmMaskEbNoAlarm, 
				cdm570AlarmMaskRxAIS, cdm570AlarmMaskBufferSlip, cdm570AlarmMaskExtReference, cdm570UnitAlarms, cdm570TxAlarms, 
				cdm570RxAlarms, cdm570RxBERMultiplier, cdm570BufferFillState, cdm570RxFrequencyOffset, cdm570RxSignalLevel, 
				cdm570RxEbNo, cdm570EventIndex, cdm570EventDate, cdm570EventTime, cdm570EventDescription, 
				cdm570ClearAllStoredEvents, cdm570StatisticsSampleInterval, cdm570StatisticIndex, cdm570StatisticDate, cdm570StatisticTime, 
				cdm570StatisticMinEbNo, cdm570StatisticAvgEbNo, cdm570StatisticMaxTxPowerIncrease, cdm570StatisticAvgTxPowerIncrease, cdm570ClearAllStoredStatistics, 
				cdm570AUPCRemoteDemodEbNo, cdm570AUPCTxPowerIncrease, cdm570UnitTestMode, cdm570ConfigurationSave, cdm570ConfigurationLoad, 
				cdm570ReCenterBuffer, cdm570RTCDate, cdm570RTCTime, cdm570WarmUpDelay, cdm570WarmUpCountdown, 
				cdm570CircuitID, cdm570RedundancyState, cdm570ForceRedundentSwitch, cdm570TxSymbolRate, cdm570RxSymbolRate, 
				cdm570ODUCommsEnabled }
			STATUS current
			DESCRIPTION
				"CDM-570 (Both L-Band and IF-Band) Objects Group."
			::= { cdm570Groups 1 }
		
		cdm570NotificationsGroup NOTIFICATION-GROUP
			NOTIFICATIONS { cdm570UnitAlarm, cdm570TxTrafficAlarm, cdm570RxTrafficAlarm }
			STATUS current
			DESCRIPTION
				"CDM-570 (Both L-Band and IF-Band) Notifications Group."
			::= { cdm570Groups 2 }
		
		cdm570Compliances OBJECT IDENTIFIER ::= { cdm570Conformance 2 }
		
		cdm570Compliance MODULE-COMPLIANCE
			STATUS current
			DESCRIPTION
				"CDM-570 (Both L-Band and IF-Band) Compliance."
			MODULE -- this module
				MANDATORY-GROUPS { cdm570ObjectsGroup, cdm570NotificationsGroup }
			::= { cdm570Compliances 1 }
		
	
	END

--
-- CDM-570.my
--
