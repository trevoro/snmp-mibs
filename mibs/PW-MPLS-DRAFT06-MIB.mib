-- extracted from draft-ietf-pwe3-pw-mpls-mib-06.txt
-- at Thu Jul  8 06:21:50 2004

  PW-MPLS-DRAFT06-MIB DEFINITIONS ::= BEGIN 
   
  IMPORTS 
     MODULE-IDENTITY, OBJECT-TYPE,  
     Unsigned32 
        FROM SNMPv2-SMI 
   
     MODULE-COMPLIANCE, OBJECT-GROUP 
        FROM SNMPv2-CONF 
   
     StorageType 
        FROM SNMPv2-TC 
   
     InterfaceIndexOrZero 
        FROM IF-MIB 
   
     MplsTunnelIndex, MplsTunnelInstanceIndex, 
     MplsLdpIdentifier, MplsLsrIdentifier 
        FROM MPLS-TC-STD-MIB 
   
    MplsIndexType 
        FROM MPLS-LSR-STD-MIB 
      
     PwVcIndexType, pwStdMIB 
        FROM PW-TC-DRAFT05-MIB 
   
     pwVcIndex 
        FROM PW-DRAFT05-MIB 
   
  ; 
   
  pwVcMplsMIB MODULE-IDENTITY 
     LAST-UPDATED "200406131200Z"  -- 13 June 2004 12:00:00 GMT 
     ORGANIZATION "Pseudo Wire Edge to Edge Emulation (PWE3) Working 
                   Group" 
     CONTACT-INFO 
         " 
          David Zelig 
          Postal: Corrigent Systems 
                  126, Yigal Alon St. 
                  Tel Aviv, ISRAEL 
                  Phone: +972-3-6945273 
          E-mail: davidz@corrigent.com 
   
          Thomas D. Nadeau 
          Postal: Cisco Systems, Inc. 
                  250 Apollo Drive 
                  Chelmsford, MA 01824 
                     Pseudo Wire (PW) Over MPLS             June 2004 
                    Management Information Base 


          Tel:    +1-978-497-3051 
          Email:  tnadeau@cisco.com 
   
          Dave Danenberg 
          Email:  dave_danenberg@yahoo.com 
       
          Sharon Mantin 
          Postal:  AxONLink (Israel) Ltd  
                   9 Bareket St.  
                   Petah Tikva 49517, Israel  
          Tel:     +972-3-9263972  
          Email:   sharon.mantin@axonlink.com 
           
          The PWE3 Working Group (email distribution pwe3@ietf.org, 
          http://www.ietf.org/html.charters/pwe3-charter.html) 
         " 
     DESCRIPTION 
         "This MIB module complements the PW MIB module for PW  
          operation over MPLS. 
   
         Copyright (C) The Internet Society (date).  This version 
         of this MIB module is part of RFC yyyy;  see the RFC 
         itself for full legal notices. 
  -- RFC Ed.: replace yyyy with actual RFC number & remove this note 
         " 
      
     -- Revision history. 
   
     REVISION 
         "200406131200Z"  -- 13 June 2004 12:00:00 GMT 
     DESCRIPTION 
   
        "Draft-ietf-pwe3-pw-mpls-mib-06 version. Changes from  
         previous version: 
         1) Compliance section details. 
        " 
   
     REVISION 
         "200402121200Z"  -- 12 February 2004 12:00:00 GMT 
     DESCRIPTION 
   
        "Draft-ietf-pwe3-pw-mpls-mib-05 version. Changes from  
         previous version: 
         1) Add inbound/outbound index for the nonTe mapping table 
         2) Clarify the pwVcMplsTeMappingTunnelInstance usage in  
            pwVcMplsTeMappingTable. 
         3) Remove an index from pwVcMplsOutboundTable and adding 
            an indication of Te or non-TE usage. 
         4) Removing the RowStatus from the outbound tables since it 
            possible to configure a PW to a single TE tunnel head-end 
            and/or a single nonTE tunnel, so the agent can open the 
                     Pseudo Wire (PW) Over MPLS             June 2004 
                    Management Information Base 


            row automatically. 
         5) Adding a nonTe inbound table in order to enable a quick 
            search for a PW based on pwVcIndex. 
        " 
     REVISION 
         "200311301200Z"  -- 30 November 2003 12:00:00 EST 
     DESCRIPTION 
        "Draft-ietf-pwe3-pw-mpls-mib-04 version. Changes from  
         previous version: 
         1) Adapting description to MIB boilerplate. 
         2) Module OID changed to PWE3 tree. 
         3) Sync descriptions of various items to table structure and 
            removing unnecessary references. 
        " 
     REVISION 
         "200307291200Z"  -- 29 July 2003 12:00:00 EST 
     DESCRIPTION 
        "Draft-ietf-pwe3-pw-mpls-mib-02 version. Changes from  
         previous version: 
         1) Removing inbound table (no strict mode and no knowledge  
            of inbound tunnel). 
         2) Provisioning (i.e. RowCreate) done via mapping tables. 
            Outbound table is now read only for sorted search for 
            pwVcIndex. 
        " 
   
     REVISION 
         "200206021200Z"  -- 02 June 2002 12:00:00 EST 
     DESCRIPTION 
        "Draft-ietf-pwe3-pw-mpls-mib-00 version. Changes from  
         previous version: 
         1) Splitting the mapping table into two tables, one for 
            Non TE application and one for TE application. 
         2) Object types alignment with MPLS MIBs. 
        " 
     REVISION 
         "200201291200Z"  -- 29 January 2002 12:00:00 EST 
     DESCRIPTION 
        "Changes from previous version: 
         1) Add LDP entity association. 
         2) Clarify inbound/outbound directions. 
         3) Simplify indexing of outbound and inbound tables 
            and providing get next variables. 
        " 
     REVISION 
         "200111071200Z"  -- 7 November 2001 12:00:00 EST 
     DESCRIPTION 
        "Changes from previous version: 
         1) Remove Vc instance from table indexing. 
         2) Update descriptions of indexing and protection. 
         3) Remove the need for MPLS-LSR in case of VC only. 
                     Pseudo Wire (PW) Over MPLS             June 2004 
                    Management Information Base 


         4) Change pwVcMplsMplsType to BITS in order to enable 
            multiple types of outer tunnel. 
         5) Add ifindex to outer tunnel tables to support vcOnly  
            option. 
         6) change naming of outbound, inbound and mapping tables to  
            reflect addition of VC only port ifindexes. 
         7) Adapt order of items in mapping table to SNMP convention. 
        " 
     REVISION 
         "200107111200Z"  -- July 11 2001 12:00:00 EST 
     DESCRIPTION 
        "draft-zelig-pw-mib-00.txt - initial version" 
   
         ::= { pwStdMIB 1 } -- To be assigned by IANA  
                            -- the value 3 is requested for this 
                            -- specific Module. 
   
  -- Top-level components of this MIB. 
   
  -- Tables, Scalars 
  pwVcMplsObjects       OBJECT IDENTIFIER 
                                ::= { pwVcMplsMIB 1 } 
  -- Conformance 
  pwVcMplsConformance   OBJECT IDENTIFIER  
                                ::= { pwVcMplsMIB 2 } 
   
  -- PW MPLS table 
   
  pwVcMplsTable   OBJECT-TYPE 
     SYNTAX        SEQUENCE OF PwVcMplsEntry 
     MAX-ACCESS    not-accessible 
     STATUS        current 
     DESCRIPTION 
         "This table controls MPLS specific parameters when the PW is 
          going to be carried over MPLS PSN." 
     ::= { pwVcMplsObjects 1 } 
   
  pwVcMplsEntry   OBJECT-TYPE 
     SYNTAX        PwVcMplsEntry 
     MAX-ACCESS    not-accessible 
     STATUS        current 
     DESCRIPTION 
          "A row in this table represents parameters specific to MPLS  
           PSN for a pseudo wire (PW). The row is created  
           automatically by the local agent if the pwVcPsnType is  
           MPLS. It is indexed by pwVcIndex, which uniquely  
           identifying a singular PW. 
          " 
     INDEX  { pwVcIndex } 
   
        ::= { pwVcMplsTable 1 } 


   
  PwVcMplsEntry ::= SEQUENCE { 
        pwVcMplsMplsType          BITS, 
        pwVcMplsExpBitsMode       INTEGER, 
        pwVcMplsExpBits           Unsigned32, 
        pwVcMplsTtl               Unsigned32, 
        pwVcMplsLocalLdpID        MplsLdpIdentifier, 
        pwVcMplsLocalLdpEntityID  MplsLsrIdentifier, 
        pwVcMplsPeerLdpID         MplsLdpIdentifier, 
        pwVcMplsStorageType       StorageType 
     } 
   
  pwVcMplsMplsType OBJECT-TYPE  
     SYNTAX   BITS { 
         mplsTe    (0), 
         mplsNonTe (1), 
         vcOnly    (2) 
              } 
     MAX-ACCESS    read-write 
     STATUS        current 
     DESCRIPTION 
          "Set by the operator to indicate the outer tunnel types, if 
           exists. mplsTe(0) is used if the outer tunnel was set-up  
           by MPLS-TE, and mplsNonTe(1) is used the outer tunnel was  
           set up by LDP or manually. Combination of mplsTe(0) and  
           mplsNonTe(1) may exist together. 
           vcOnly(2) is used if there is no outer tunnel label, i.e. 
           in static provisioning without MPLS tunnel. vcOnly(2) 
           cannot be combined with mplsNonTe(1) or mplsTe(0)." 
     DEFVAL { { mplsNonTe } } 
     ::= { pwVcMplsEntry 1 } 
   
   
  pwVcMplsExpBitsMode OBJECT-TYPE  
     SYNTAX   INTEGER { 
         outerTunnel      (1), 
         specifiedValue   (2), 
         serviceDependant (3) 
              } 
              
     MAX-ACCESS    read-write 
     STATUS        current 
     DESCRIPTION 
         "Set by the operator to indicate the way the PW shim label 
          EXP bits are to be determined. The value of outerTunnel(1) 
          is used where there is an outer tunnel - pwVcMplsMplsType  
          is mplsTe(0) or mplsNonTe(1). Note that in this case there  
          is no need to mark the PW label with the EXP bits since the 
          PW label is not visible to the intermediate nodes. 
          If there is no outer tunnel, specifiedValue(2) indicates  
          that the value is specified by pwVcMplsExpBits, and  


          serviceDependant(3) indicates that the EXP bits are setup  
          based on a rule specified in the emulated service specific  
          tables, for example when the EXP bits are a function of  
          802.1p marking for Ethernet emulated service." 
   
     DEFVAL { outerTunnel } 
     ::= { pwVcMplsEntry 2 } 
   
  pwVcMplsExpBits OBJECT-TYPE  
     SYNTAX        Unsigned32 (0..7) 
     MAX-ACCESS    read-write 
     STATUS        current 
     DESCRIPTION 
          "Set by the operator to indicate the MPLS EXP bits to be  
           used on the PW shim label if pwVcMplsExpBitsMode is   
           specifiedValue(2), zero otherwise." 
     DEFVAL { 0 } 
     ::= { pwVcMplsEntry 3 } 
   
  pwVcMplsTtl OBJECT-TYPE  
     SYNTAX        Unsigned32 (0..255) 
     MAX-ACCESS    read-write 
     STATUS        current 
     DESCRIPTION 
          "Set by the operator to indicate the PW TTL value to be  
           used on the PW shim label." 
     DEFVAL { 2 } 
     ::= { pwVcMplsEntry 4 } 
   
  pwVcMplsLocalLdpID OBJECT-TYPE  
     SYNTAX        MplsLdpIdentifier 
     MAX-ACCESS    read-write 
     STATUS        current 
     DESCRIPTION 
          "The local LDP identifier of the LDP entity creating 
           this PW in the local node. As the PW labels are always 
           set from the per platform label space, the last two octets  
           in the LDP ID MUST be always both zeros." 
     REFERENCE 
          "'LDP specifications', RFC 3036 section 2.2.2." 
     ::= { pwVcMplsEntry 5 } 
   
  pwVcMplsLocalLdpEntityID OBJECT-TYPE  
     SYNTAX        MplsLsrIdentifier 
     MAX-ACCESS    read-write 
     STATUS        current 
     DESCRIPTION 
          "The local node LDP Entity ID of the LDP entity creating 
           this PW. Should return the value of all zeros if not  
           used." 
     ::= { pwVcMplsEntry 6 } 


   
  pwVcMplsPeerLdpID OBJECT-TYPE  
     SYNTAX        MplsLdpIdentifier 
     MAX-ACCESS    read-only 
     STATUS        current 
     DESCRIPTION 
          "The peer LDP identifier as identified from the LDP  
           session. Should return the value of zero if not applicable 
           or not known yet." 
     ::= { pwVcMplsEntry 7 } 
   
  pwVcMplsStorageType OBJECT-TYPE  
     SYNTAX        StorageType 
     MAX-ACCESS    read-write 
     STATUS        current 
     DESCRIPTION 
         "This variable indicates the storage type for this row." 
     ::= { pwVcMplsEntry 8 } 
   
  -- End of PW MPLS table 
   
  -- Pseudo Wire MPLS Outbound Tunnel table 
   
  pwVcMplsOutboundTable   OBJECT-TYPE 
     SYNTAX        SEQUENCE OF PwVcMplsOutboundEntry 
     MAX-ACCESS    not-accessible 
     STATUS        current 
     DESCRIPTION 
         "This table reports and configure the current outbound MPLS  
          tunnels (i.e. toward the PSN) or the physical interface in  
          case of PW label only that carry the PW traffic. It also  
          reports the current outer tunnel and LSP which forward the  
          PW traffic." 
     ::= { pwVcMplsObjects 2 } 
   
  pwVcMplsOutboundEntry OBJECT-TYPE 
     SYNTAX        PwVcMplsOutboundEntry 
     MAX-ACCESS    not-accessible 
     STATUS        current 
     DESCRIPTION 
         "A row in this table configured the outer tunnel used for  
          carrying the PW traffic toward the PSN. 
          In the case of PW label only, it configures the interface  
          that will carry the PW traffic. 
   
          An entry in this table augments the pwVcMplsEntry, and is 
          created automatically when the corresponding row has been 
          created by the agent in the pwVcMplsEntry. 
   
          This table points to the appropriate MPLS MIB module.  
          In the MPLS-TE case, the 3 variables relevant to the  


          indexing of a TE tunnel head-end are used as in  
          MPLS-TE-STD-MIB are to be configured, and the tunnel  
          instance indicates the LSP that is currently in use for  
          forwarding the traffic. 
   
          In case of signaled Non-TE MPLS (an outer tunnel label  
          assigned by LDP) the table points to the XC entry in the  
          LSR-STD-MIB. If the Non-TE MPLS tunnel is manually  
          configured, the operator configure the XC pointer to this 
          tunnel. 
   
          In case of PW label only (no outer tunnel) the ifIndex of  
          the port to carry the PW is configured here.  
           
          It is possible to associate a PW to one TE tunnel head-end  
          and a non-TE tunnel together. An indication in this table  
          will report the currently active one, In addition, in the  
          TE case the table reports the active tunnel instance  
          (i.e. the specific LSP in use). 
         "     
   
     AUGMENTS { pwVcMplsEntry } 
    
        ::= { pwVcMplsOutboundTable 1 } 
   
  PwVcMplsOutboundEntry ::= SEQUENCE { 
        pwVcMplsOutboundLsrXcIndex           MplsIndexType, 
        pwVcMplsOutboundTunnelIndex          MplsTunnelIndex, 
        pwVcMplsOutboundTunnelInstance       MplsTunnelInstanceIndex, 
        pwVcMplsOutboundTunnelLclLSR         MplsLsrIdentifier, 
        pwVcMplsOutboundTunnelPeerLSR        MplsLsrIdentifier, 
        pwVcMplsOutboundIfIndex              InterfaceIndexOrZero, 
        pwVcMplsOutboundTunnelTypeInUse      INTEGER 
        } 
   
  pwVcMplsOutboundLsrXcIndex      OBJECT-TYPE 
     SYNTAX        MplsIndexType 
     MAX-ACCESS    read-write 
     STATUS        current 
     DESCRIPTION 
         "This object is applicable if pwVcMplsMplsType mplsNonTe(1) 
          bit is set, and MUST return a value of zero otherwise. 
          If the outer tunnel is signaled, the object is read-only  
          and indicate the XC index in the MPLS-LSR-STD-MIB of the 
          outer tunnel toward the peer. Otherwise (tunnel is set-up  
          manually) the operator define the XC index of the manually  
          created outer tunnel through this object. 
         " 
     ::= { pwVcMplsOutboundEntry 1 } 
   
  pwVcMplsOutboundTunnelIndex         OBJECT-TYPE 


     SYNTAX        MplsTunnelIndex 
     MAX-ACCESS    read-write 
     STATUS        current 
     DESCRIPTION 
         "This object is applicable if pwVcMplsMplsType mplsTe(0) 
          bit is set, and MUST return a value of zero otherwise. 
          It is Part of set of indexes for outbound tunnel. 
          The operator set this object to represent the desired 
          tunnel head-end toward the peer for carrying the PW  
          traffic. 
         " 
     ::= { pwVcMplsOutboundEntry  2 }  
   
  pwVcMplsOutboundTunnelInstance      OBJECT-TYPE 
     SYNTAX        MplsTunnelInstanceIndex 
     MAX-ACCESS    read-only 
     STATUS        current 
     DESCRIPTION 
         "This object is applicable if pwVcMplsMplsType mplsTe(0)  
          bit is set, and MUST return a value of zero otherwise. 
          It indicates the actual tunnel instance that is currently  
          active and carrying the PW traffic - it should return the  
          value of zero until if the information from the MPLS-TE  
          application is not yet known. 
         " 
     ::= { pwVcMplsOutboundEntry   3 }  
   
  pwVcMplsOutboundTunnelLclLSR        OBJECT-TYPE 
     SYNTAX        MplsLsrIdentifier 
     MAX-ACCESS    read-write 
     STATUS        current 
     DESCRIPTION  
         "This object is applicable if pwVcMplsMplsType mplsTe(0)  
          bit is set, and MUST return a value of all zeros otherwise. 
          It is part of set of indexes for outbound tunnel. 
          The operator set this object to represent the desired 
          tunnel head-end toward the peer for carrying the PW  
          traffic. 
         " 
     ::= { pwVcMplsOutboundEntry   4 }  
   
  pwVcMplsOutboundTunnelPeerLSR       OBJECT-TYPE 
     SYNTAX        MplsLsrIdentifier 
     MAX-ACCESS    read-write 
     STATUS        current 
     DESCRIPTION 
         "This object is applicable if pwVcMplsMplsType mplsTe(0) 
          bit is set, and MUST return a value of zero otherwise. 
          It is part of set of indexes for outbound tunnel. It is 
          typically equal to pwVcPeerAddr. 
         " 


     ::= { pwVcMplsOutboundEntry   5 }  
   
  pwVcMplsOutboundIfIndex       OBJECT-TYPE 
     SYNTAX         InterfaceIndexOrZero 
     MAX-ACCESS     read-write 
     STATUS         current 
     DESCRIPTION 
         "This object is applicable if pwVcMplsMplsType mplsTe(0) 
          bit is set, and MUST return a value of zero otherwise. 
          The operator configure the ifIndex of the outbound port 
          in this case. 
         " 
     ::= { pwVcMplsOutboundEntry   6 } 
   
  pwVcMplsOutboundTunnelTypeInUse OBJECT-TYPE 
     SYNTAX         INTEGER { 
                    notYetKnown (1), 
                    mplsTe      (2), 
                    mplsNonTe   (3), 
                    vcOnly      (4) 
     } 
     MAX-ACCESS     read-only 
     STATUS         current 
     DESCRIPTION 
         "This object indicates the current tunnel that is carrying 
          the PW traffic. 
          The value of notYetKnown(1) should be used if the agent is  
          currently unable to determine which tunnel or interface is  
          carrying the PW, for example because both tunnels are in  
          operational status down. 
         " 
     ::= { pwVcMplsOutboundEntry   7 } 
   
   
  -- End of PW MPLS Outbound Tunnel table 
   
  -- PW MPLS inbound table 
   
  pwVcMplsInboundTable OBJECT-TYPE  
     SYNTAX           SEQUENCE OF PwVcMplsInboundEntry 
     MAX-ACCESS       not-accessible 
     STATUS           current 
     DESCRIPTION 
         "This table indicates the PW LDP XC entry in the  
          MPLS-LSR-STD-MIB for signaled PWs. 
         " 
     ::= { pwVcMplsObjects 3 } 
   
  pwVcMplsInboundEntry OBJECT-TYPE 
     SYNTAX           PwVcMplsInboundEntry 
     MAX-ACCESS       not-accessible 


     STATUS           current 
     DESCRIPTION 
          "A row in this table is created by the agent  
           for each signaled PW, and shows the XC index related to  
           the PW signaling in the inbound direction in the  
           MPLS-LSR-STD-MIB that controls and display the information 
           for all the LDP signaling processes in the local node. 
          " 
   
     INDEX  { pwVcIndex } 
   
        ::= { pwVcMplsInboundTable 1 } 
   
  PwVcMplsInboundEntry ::= SEQUENCE { 
        pwVcMplsInboundXcIndex           MplsIndexType 
     } 
   
  pwVcMplsInboundXcIndex OBJECT-TYPE 
     SYNTAX        MplsIndexType 
     MAX-ACCESS    read-only 
     STATUS        current 
     DESCRIPTION 
         "The XC index representing this PW in the inbound  
          direction. Should return the value of zero if the  
          information is not yet known." 
     ::= { pwVcMplsInboundEntry 1 } 
   
  -- End of PW MPLS inbound table 
   
  -- PW to Non-TE mapping Table. 
   
  pwVcMplsNonTeMappingTable OBJECT-TYPE  
     SYNTAX           SEQUENCE OF PwVcMplsNonTeMappingEntry 
     MAX-ACCESS       not-accessible 
     STATUS           current 
     DESCRIPTION 
         "This table indicates outbound Tunnel to a PW in non-TE  
          applications, maps the PW to it's (inbound) XC entry, and  
          indicates the PW to physical interface mapping for a PW  
          label to physical interface a PW label is in use without  
          outer tunnel. 
         " 
     ::= { pwVcMplsObjects 4 } 
   
  pwVcMplsNonTeMappingEntry OBJECT-TYPE 
     SYNTAX           PwVcMplsNonTeMappingEntry 
     MAX-ACCESS       not-accessible 
     STATUS           current 
     DESCRIPTION 
          "A row in this table displays the association 
           between the PW and 


           - it's non-TE MPLS outbound outer Tunnel or, 
           - it's XC entry in the MPLS-LSR-STD-MIB,  
           - it's physical interface if there is no outer tunnel  
             (PW label only) and manual configuration. 
            
           Rows are created in this table by the by the  
           agent depending on the setting of pwVcMplsMplsType: 
   
           - If pwVcMplsMplsType mplsNonTe(1) bit is set, the agent  
           creates a row for the outbound direction  
           (pwVcMplsNonTeMappingDirection set to psnBound(1)).  
           The pwVcMplsNonTeMappingXcIndex holds the XC index in the  
           MPLS-LSR-STD-MIB of the PSN bound outer tunnel.  
           pwVcMplsNonTeMappingIfIndex MUST be zero for this row. 
   
           - If pwVcMplsMplsType vcOnly(2) bit is set, the agent  
           creates a row for the outbound direction  
           (pwVcMplsNonTeMappingDirection set to psnBound(1)).  
           The pwVcMplsNonTeMappingIfIndex holds the ifIndex of the  
           physical port this PW will use in the outbound direction. 
           pwVcMplsNonTeMappingXcIndex MUST be zero for this row. 
   
           - If the PW has been set-up by signaling protocol (i.e.  
           pwVcOwner equal pwIdFecSignaling(2) or  
           genFecSignaling(3)), the agent creates a row for the  
           inbound direction (pwVcMplsNonTeMappingDirection set to  
           fromPsn(2)). 
           The pwVcMplsNonTeMappingXcIndex holds the XC index in the  
           MPLS-LSR-STD-MIB of the PW LDP generated XC entry.  
           pwVcMplsNonTeMappingIfIndex MUST be zero for this row. 
   
           An application can use this table to quickly retrieve the  
           PW carried over specific non-TE MPLS outer tunnel or  
           physical interface. 
           " 
   
     INDEX  { pwVcMplsNonTeMappingDirection, 
              pwVcMplsNonTeMappingXcIndex, 
              pwVcMplsNonTeMappingIfIndex, 
              pwVcMplsNonTeMappingVcIndex } 
   
        ::= { pwVcMplsNonTeMappingTable 1 } 
   
  PwVcMplsNonTeMappingEntry ::= SEQUENCE { 
        pwVcMplsNonTeMappingDirection         INTEGER, 
        pwVcMplsNonTeMappingXcIndex           MplsIndexType, 
        pwVcMplsNonTeMappingIfIndex           InterfaceIndexOrZero, 
        pwVcMplsNonTeMappingVcIndex           PwVcIndexType 
     } 
   
  pwVcMplsNonTeMappingDirection OBJECT-TYPE 


     SYNTAX        INTEGER { 
                   psnBound (1),  
                   fromPsn  (2)  
     } 
     MAX-ACCESS    not-accessible 
     STATUS        current 
     DESCRIPTION 
         "Index for the conceptual XC row identifying Tunnel to PW  
          mappings, indicating the direction of packet flow the entry 
          is related too. 
          psnBound(1) indicates that the entry is related to 
          packets toward the PSN.   
          fromPsn(2) indicates that the entry is related to  
          packets coming from the PSN. 
         " 
     ::= { pwVcMplsNonTeMappingEntry 1 } 
   
  pwVcMplsNonTeMappingXcIndex OBJECT-TYPE 
     SYNTAX        MplsIndexType 
     MAX-ACCESS    not-accessible 
     STATUS        current 
     DESCRIPTION 
         "See the description clause of pwVcMplsNonTeMappingEntry for 
          the usage guidelines of this object." 
     ::= { pwVcMplsNonTeMappingEntry 2 } 
   
  pwVcMplsNonTeMappingIfIndex  OBJECT-TYPE 
     SYNTAX        InterfaceIndexOrZero 
     MAX-ACCESS    not-accessible 
     STATUS        current 
     DESCRIPTION 
         "See the description clause of pwVcMplsNonTeMappingEntry for 
          the usage guidelines of this object." 
     ::= { pwVcMplsNonTeMappingEntry 3 } 
   
  pwVcMplsNonTeMappingVcIndex  OBJECT-TYPE 
     SYNTAX        PwVcIndexType 
     MAX-ACCESS    read-only 
     STATUS        current 
     DESCRIPTION 
         "The value that represent the PW in the pwVcTable." 
     ::= { pwVcMplsNonTeMappingEntry 4 } 
   
  -- End of PW to Non-TE mapping Table. 
   
  -- PW to TE MPLS tunnels mapping Table. 
   
  pwVcMplsTeMappingTable OBJECT-TYPE  
     SYNTAX           SEQUENCE OF PwVcMplsTeMappingEntry 
     MAX-ACCESS       not-accessible 
     STATUS           current 


     DESCRIPTION 
         "This table enable the retrieval of a PW association to the  
          outbound MPLS tunnel for MPLS-TE applications." 
     ::= { pwVcMplsObjects 5 } 
   
  pwVcMplsTeMappingEntry OBJECT-TYPE 
     SYNTAX           PwVcMplsTeMappingEntry 
     MAX-ACCESS       not-accessible 
     STATUS           current 
     DESCRIPTION 
          "A row in this table represents the association 
           between a PW and it's MPLS-TE outer (head-end) Tunnel. 
            
           An application can use this table to quickly retrieve the  
           list of the PWs that are configured on a specific MPLS TE  
           outer tunnel. 
            
           The pwVcMplsTeMappingTunnelInstance reports the actual 
           LSP out of the tunnel head-end that is currently  
           forwarding the traffic. 
   
           The table in indexed by the head-end indexes of a TE  
           tunnel and the PW index. 
          " 
   
     INDEX  { pwVcMplsTeMappingTunnelIndex,  
              pwVcMplsTeMappingTunnelInstance, 
              pwVcMplsTeMappingTunnelPeerLsrID, 
              pwVcMplsTeMappingTunnelLocalLsrID, 
              pwVcMplsTeMappingVcIndex } 
   
        ::= { pwVcMplsTeMappingTable 1 } 
   
  PwVcMplsTeMappingEntry ::= SEQUENCE { 
        pwVcMplsTeMappingTunnelIndex       MplsTunnelIndex, 
        pwVcMplsTeMappingTunnelInstance    MplsTunnelInstanceIndex, 
        pwVcMplsTeMappingTunnelPeerLsrID   MplsLsrIdentifier, 
        pwVcMplsTeMappingTunnelLocalLsrID  MplsLsrIdentifier, 
        pwVcMplsTeMappingVcIndex           PwVcIndexType 
     } 
   
  pwVcMplsTeMappingTunnelIndex OBJECT-TYPE 
     SYNTAX        MplsTunnelIndex 
     MAX-ACCESS    not-accessible 
     STATUS        current 
     DESCRIPTION 
         "Primary index for the conceptual row identifying the  
          MPLS-TE tunnel that is carrying the PW traffic." 
     ::= { pwVcMplsTeMappingEntry 1 } 
   
  pwVcMplsTeMappingTunnelInstance OBJECT-TYPE 


     SYNTAX        MplsTunnelInstanceIndex 
     MAX-ACCESS    not-accessible 
     STATUS        current 
     DESCRIPTION 
         "This object identify the MPLS-TE LSP that is carrying the  
          PW traffic. Should return the value of zero if the  
          information of the specific LSP is not yet known. 
          Note that based on the recommendation in the  
          MPLS-TC-STD-MIB, instance index 0 should refer to the  
          configured tunnel interface." 
     ::= { pwVcMplsTeMappingEntry 2 } 
   
  pwVcMplsTeMappingTunnelPeerLsrID  OBJECT-TYPE 
     SYNTAX        MplsLsrIdentifier 
     MAX-ACCESS    not-accessible 
     STATUS        current 
     DESCRIPTION 
         "Identifies the Peer LSR when the outer tunnel is MPLS-TE  
          based." 
     ::= { pwVcMplsTeMappingEntry 3 } 
   
  pwVcMplsTeMappingTunnelLocalLsrID  OBJECT-TYPE 
     SYNTAX        MplsLsrIdentifier 
     MAX-ACCESS    not-accessible 
     STATUS        current 
     DESCRIPTION 
         "Identifies the local LSR." 
     ::= { pwVcMplsTeMappingEntry 4 } 
   
  pwVcMplsTeMappingVcIndex  OBJECT-TYPE 
     SYNTAX        PwVcIndexType 
     MAX-ACCESS    read-only 
     STATUS        current 
     DESCRIPTION 
         "The value that represent the PW in the pwVcTable." 
     ::= { pwVcMplsTeMappingEntry 5 } 
   
  -- End of PW to TE MPLS tunnels mapping Table. 
   
  -- conformance information 
   
  pwVcMplsGroups      OBJECT IDENTIFIER ::= { pwVcMplsConformance 1 } 
  pwVcMplsCompliances OBJECT IDENTIFIER ::= { pwVcMplsConformance 2 } 
   
  -- Compliance requirement for fully compliant implementations. 
   
  pwMplsModuleFullCompliance MODULE-COMPLIANCE 
      STATUS  current 
      DESCRIPTION 
              "The compliance statement for agents that provide full 
               support for PW-MPLS MIB Module. Such devices can 


               then be monitored and also be configured using 
               this MIB module." 
   
     MODULE  -- this module 
     MANDATORY-GROUPS { pwVcMplsGroup, 
                        pwVcMplsOutboundMainGroup, 
                        pwVcMplsInboundGroup, 
                        pwVcMplsMappingGroup 
                       } 
   
     GROUP        pwVcMplsOutboundTeGroup 
     DESCRIPTION "This group MUST be supported if the implementation 
                  allows MPLS TE tunnels to carry PW traffic.  
                  " 
   
     OBJECT       pwVcMplsMplsType 
     DESCRIPTION "Support of vcOnly(2) is not required. At least one 
                  of mplsTe(0) or mplsNonTe(1) MUST be supported if  
                  signaling of PW is supported. 
                  " 
   
     OBJECT       pwVcMplsExpBitsMode 
     DESCRIPTION "Support of specifiedValue(2) and 
  serviceDependant(3) 
                  is optional. 
                  " 
   
     OBJECT       pwVcMplsLocalLdpID 
     MIN-ACCESS   read-only 
     DESCRIPTION "A read-write access is required if the  
                  implementation supports more than one LDP entity  
                  identifier for PW signaling. 
                  " 
   
     OBJECT       pwVcMplsLocalLdpEntityID 
     MIN-ACCESS   read-only 
     DESCRIPTION "A read-write access is required if the  
                  implementation supports more than one LDP entity  
                  index for PW signaling. 
                  " 
   
     OBJECT       pwVcMplsOutboundLsrXcIndex 
     MIN-ACCESS   read-only 
     DESCRIPTION "A value other than zero MUST be supported if the 
                  implementation support non TE signaling of the  
                  outer tunnel. 
                  A read-write access MUST be supported if the 
                  implementation supports manually setting of the PW 
                  labels and carrying them over non-TE tunnels. 
                  " 


     OBJECT       pwVcMplsOutboundIfIndex 
     MIN-ACCESS   read-only 
     DESCRIPTION "A value other than zero and read-write operations 
                  MUST be supported if the implementation supports  
                  manully configured PW without MPLS outer tunnel. 
                  " 
      ::= { pwVcMplsCompliances 1 } 
   
  -- Compliance requirement for Read Only compliant implementations. 
   
  pwMplsModuleReadOnlyCompliance MODULE-COMPLIANCE 
      STATUS  current 
      DESCRIPTION 
              "The compliance statement for agents that provide read 
               only support for PW-MPLS MIB Module. Such devices can 
               then be monitored but cannot be configured using this 
               MIB module." 
   
     MODULE  -- this module 
     MANDATORY-GROUPS { pwVcMplsGroup, 
                        pwVcMplsOutboundMainGroup, 
                        pwVcMplsInboundGroup, 
                        pwVcMplsMappingGroup 
                       } 
   
     GROUP        pwVcMplsOutboundTeGroup 
     DESCRIPTION "This group MUST be supported if the implementation 
                  allows MPLS TE tunnels to carry PW traffic.  
                  " 
   
     OBJECT       pwVcMplsMplsType 
     MIN-ACCESS   read-only 
     DESCRIPTION "Write access is not required. 
                  Support of vcOnly(2) is not required. At least one 
                  of mplsTe(0) or mplsNonTe(1) MUST be supported if  
                  signaling of PW is supported. 
                  " 
   
     OBJECT       pwVcMplsExpBitsMode 
     MIN-ACCESS   read-only 
     DESCRIPTION "Write access is not required. 
                  Support of specifiedValue(2) and 
  serviceDependant(3) 
                  is optional. 
                  " 
   
     OBJECT       pwVcMplsExpBits 
     MIN-ACCESS   read-only 
     DESCRIPTION "Write access is not required. 
                  " 


     OBJECT       pwVcMplsTtl 
     MIN-ACCESS   read-only 
     DESCRIPTION "Write access is not required. 
                  " 
   
     OBJECT       pwVcMplsLocalLdpID 
     MIN-ACCESS   read-only 
     DESCRIPTION "Write access is not required. 
                  " 
   
     OBJECT       pwVcMplsLocalLdpEntityID 
     MIN-ACCESS   read-only 
     DESCRIPTION "Write access is not required. 
                  " 
   
     OBJECT       pwVcMplsStorageType 
     MIN-ACCESS   read-only 
     DESCRIPTION "Write access is not required. 
                  " 
   
     OBJECT       pwVcMplsOutboundLsrXcIndex 
     MIN-ACCESS   read-only 
     DESCRIPTION "Write access is not required. 
                  A value other than zero MUST be supported if the 
                  implementation support non TE signaling of the  
                  outer tunnel. 
                  " 
   
     OBJECT       pwVcMplsOutboundTunnelIndex 
     MIN-ACCESS   read-only 
     DESCRIPTION "Write access is not required. 
                  " 
   
     OBJECT       pwVcMplsOutboundTunnelLclLSR 
     MIN-ACCESS   read-only 
     DESCRIPTION "Write access is not required. 
                  " 
   
     OBJECT       pwVcMplsOutboundTunnelPeerLSR 
     MIN-ACCESS   read-only 
     DESCRIPTION "Write access is not required. 
                  " 
   
     OBJECT       pwVcMplsOutboundIfIndex 
     MIN-ACCESS   read-only 
     DESCRIPTION "Write access is not required. 
                  A value other than zero MUST be supported if the  
                  implementation supports manually configured PW  
                  without MPLS outer tunnel. 
                  " 


      ::= { pwVcMplsCompliances 2 } 
   
   
  -- Units of conformance. 
   
  pwVcMplsGroup OBJECT-GROUP  
     OBJECTS { 
              pwVcMplsMplsType, 
              pwVcMplsExpBitsMode, 
              pwVcMplsExpBits, 
              pwVcMplsTtl, 
              pwVcMplsLocalLdpID, 
              pwVcMplsLocalLdpEntityID, 
              pwVcMplsPeerLdpID, 
              pwVcMplsStorageType 
            } 
                
     STATUS  current 
     DESCRIPTION 
         "Collection of objects needed for PW over MPLS PSN  
          configuration." 
     ::= { pwVcMplsGroups 1 } 
   
   
   
  pwVcMplsOutboundMainGroup OBJECT-GROUP  
     OBJECTS { 
              pwVcMplsOutboundLsrXcIndex, 
              pwVcMplsOutboundIfIndex, 
              pwVcMplsOutboundTunnelTypeInUse 
            } 
                
     STATUS  current 
     DESCRIPTION 
         "Collection of objects needed for outbound association of  
          PW and MPLS tunnel." 
     ::= { pwVcMplsGroups 2 } 
   
  pwVcMplsOutboundTeGroup OBJECT-GROUP  
     OBJECTS { 
              pwVcMplsOutboundTunnelIndex, 
              pwVcMplsOutboundTunnelInstance, 
              pwVcMplsOutboundTunnelLclLSR, 
              pwVcMplsOutboundTunnelPeerLSR 
            } 
                
     STATUS  current 
     DESCRIPTION 
         "Collection of objects needed for outbound association of  
          PW and MPLS TE tunnel." 
     ::= { pwVcMplsGroups 3 } 


   
  pwVcMplsInboundGroup OBJECT-GROUP  
     OBJECTS {  
              pwVcMplsInboundXcIndex 
            } 
                
     STATUS  current 
     DESCRIPTION 
         "Collection of objects needed for inbound PW presentation. 
          This group MUST be supported if PW signaling through LDP is  
          used." 
     ::= { pwVcMplsGroups 4 } 
   
  pwVcMplsMappingGroup OBJECT-GROUP  
     OBJECTS { 
              pwVcMplsNonTeMappingVcIndex, 
              pwVcMplsTeMappingVcIndex 
            } 
              
     STATUS  current 
     DESCRIPTION 
         "Collection of objects needed for mapping association of  
          PW and MPLS tunnel." 
     ::= { pwVcMplsGroups 5 } 
   
  END -- of PW MPLS MIB Module
