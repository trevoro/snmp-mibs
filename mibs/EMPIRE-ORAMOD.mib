-- $Id: oramod.asn1,v 1.1.1.1.4.2 2004/11/03 17:43:19 mzink Exp $
-- Concord Communications Private Enterprise MIB
-- for Oracle Server monitoring and management
-- http://www.concord.com/
-- http://www.empire.com/

-- Oracle MIB
-- Mon Jul 24 15:53:08 EDT 2000

-- Copyright 2001 Concord Communications Inc.  All Rights Reserved
--
-- THIS SOFTWARE IS THE CONFIDENTIAL PROPERTY OF CONCORD COMMUNICATIONS
-- AND IS DISTRIBUTED AND AVAILABLE FOR USE ONLY UNDER LICENSE FROM
-- CONCORD. ANY COPYING, DISTRIBUTION OR USE OF THIS SOFTWARE IN
-- CONTRAVENTION OF THE SOFTWARE LICENSE FROM CONCORD IS PROHIBITED.
--

EMPIRE-ORAMOD DEFINITIONS ::= BEGIN
	IMPORTS
                OBJECT-TYPE
			FROM RFC-1212
                TRAP-TYPE
			FROM RFC-1215
                DisplayString 
			FROM RFC1213-MIB
                enterprises, TimeTicks, Counter, Gauge
                        FROM RFC1155-SMI;

	empire 	   	OBJECT IDENTIFIER ::= { enterprises 546 }
        applications    OBJECT IDENTIFIER ::= { empire 16 }
        oracledb        OBJECT IDENTIFIER ::= { applications 4 }

-- Total Footprint information
        oramodTtlFootprt  OBJECT IDENTIFIER ::= { oracledb 12 }

-- Configuration information
        oramodCfg       OBJECT IDENTIFIER ::= { oracledb 10 }

	oramodDbCfg          OBJECT IDENTIFIER ::= { oramodCfg 1 }
        oramodCfgDf    	     OBJECT IDENTIFIER ::= { oramodCfg 2 }
	oramodCfgLf          OBJECT IDENTIFIER ::= { oramodCfg 3 }
	oramodCfgSga         OBJECT IDENTIFIER ::= { oramodCfg 4 }

-- Performance information
        oramodPerf     OBJECT IDENTIFIER ::= { oracledb 11 }
        oramodFootprint OBJECT IDENTIFIER ::= { oramodPerf 1 }
        oramodMetrics OBJECT IDENTIFIER ::= { oramodPerf 2 }
        oramodSGA OBJECT IDENTIFIER ::= { oramodPerf 3 }
        oramodRedoLogBuf OBJECT IDENTIFIER ::= { oramodPerf 4 }
        oramodRollBack OBJECT IDENTIFIER ::= { oramodPerf 5 }
        oramodWaits OBJECT IDENTIFIER ::= { oramodPerf 6 }
        oramodExpSql OBJECT IDENTIFIER ::= { oramodPerf 7 }
        oramodTblsp OBJECT IDENTIFIER ::= { oramodPerf 8 }
        oramodLocks OBJECT IDENTIFIER ::= { oramodPerf 9 }
        oramodBackups OBJECT IDENTIFIER ::= { oramodPerf 10 }
        oramodArchive OBJECT IDENTIFIER ::= { oramodPerf 11 }

      -- Footprint Descriptions
      oramodFootprt OBJECT IDENTIFIER ::= { oramodFootprint 1 }
      -- File Footprint Description
      oramodFFootprt OBJECT IDENTIFIER ::= { oramodFootprint 2 }
      -- SGA Tables
      oramodSgaDddAgg OBJECT IDENTIFIER ::= { oramodSGA 1 }
      oramodSgaDlci OBJECT IDENTIFIER ::= { oramodSGA 2 }
      -- Locks
      oramodLock OBJECT IDENTIFIER ::= { oramodLocks 1 }
      oramodLatch OBJECT IDENTIFIER ::= { oramodLocks 2 }
      -- Physical Backups
      oramodBackup OBJECT IDENTIFIER ::= { oramodBackups 1 }
      -- Archive 
      oramodArcDest OBJECT IDENTIFIER ::= { oramodArchive 1 }
--
-- Types and textual conventions used within our oracledb mib spec
-- 

   --DateAndTime ::= OCTET STRING (SIZE (8))

   --        A date-time specification for the local time of day.
   --        This data type is intended to provide a consistent
   --        method of reporting date information.
   --
   --            field  octets  contents                  range
   --            _____  ______  ________                  _____
   --              1      1-2   year                      0..65536
   --                           (in network byte order)
   --              2       3    month                     1..12
   --              3       4    day                       1..31
   --              4       5    hour                      0..23
   --              5       6    minutes                   0..59
   --              6       7    seconds                   0..60
   --                           (use 60 for leap-second)
   --              7       8    deci-seconds              0..9
   --              8       9    direction from UTC        "+" / "-"
   --                           (in ascii notation)


--
-- Main MIB branch contains module-related items like version,
-- licensing info, etc.
-- 

	oraModVersion OBJECT-TYPE
		SYNTAX DisplayString
		ACCESS read-only
		STATUS mandatory
		DESCRIPTION
		   "Description and version number of this installation."
		::= { oracledb 1 }


        oraModMode OBJECT-TYPE
                SYNTAX INTEGER {
                    fullMode(1),
                    restrictedMode(2)
                }
                ACCESS read-only
                STATUS mandatory
                DESCRIPTION
                   "This object indicates if the Oracle Module is in
                    full-mode or restricted-mode.  Restricted-mode
                    is entered, when SystemEDGE 4.0 and higher,
                    fails to find a valid license.  Once
                    a valid license has been allocated and
                    set, the module will then transition to
                    fullMode(1)"
                ::= { oracledb 2 }

        oraFlag OBJECT-TYPE
                SYNTAX DisplayString
                ACCESS read-only
                STATUS mandatory
                DESCRIPTION
                   "Performance  flags for this installation."
                ::= { oracledb 3 }


-- Total Footprint of all of the Oracle "Instances" in terms of resource 
-- consumption (e.g. CPU, disk, memory)

        --oramodTtlFootprt  OBJECT IDENTIFIER ::= { oracledb 12 }

        oramodTtlCPUTIME OBJECT-TYPE
		SYNTAX INTEGER
		ACCESS read-only
		STATUS mandatory
		DESCRIPTION
                   "CPU time, in seconds, accumulated by Oracle
                    which includes all its core components and
                    instance.  Because core components can
                    come and go, the accumulated cpu time can
                    fluctuate therefore making this variable
                    unsuitable as a counter." 
		::= { oramodTtlFootprt 1 }

        oramodTtlPERCENTCPU OBJECT-TYPE
		SYNTAX INTEGER (0..100)
		ACCESS read-only
		STATUS mandatory
		DESCRIPTION
                   "The percentage of CPU utilization, by Oracle,
                    over the last sample interval.  Since fractions
                    are not supported by SNMP, the value reported is
                    the percentage multipled by 100.  It is the sum of
                    the CPU utilization of all the Oracle core
                    services and components.  Its gives a
                    good indication of the CPU resource consumption by
                    the entire Oracle application'"
		::= { oramodTtlFootprt 2 }

        oramodTtlMEMSIZE OBJECT-TYPE
		SYNTAX Gauge
		ACCESS read-only
		STATUS mandatory
		DESCRIPTION
 		    "The combined size of Oracle's text, data,
                     and stack segments in KBytes.  It is the
                     summation of the process sizes for all the core
                     Oracle services and optional connectors." 
		::= { oramodTtlFootprt 3 }

        oramodTtlRSS OBJECT-TYPE
		SYNTAX Gauge
		ACCESS read-only
		STATUS mandatory
		DESCRIPTION
		    "The real memory (resident set) size of Oracle
                     in KBytes.  It is the summation of the process
                     RSS for all the core Oracle services and
                     optional connectors."  
		::= { oramodTtlFootprt 4 }

        oramodTtlPERCENTMEM OBJECT-TYPE
		SYNTAX INTEGER (0..100)
		ACCESS read-only
		STATUS mandatory
		DESCRIPTION
		   "The percentage (0-100) of real memory used by
		    the Oracle Application which includes core
                    services and optional connectors." 
		::= { oramodTtlFootprt 5 }

        oramodTtlTHREADS OBJECT-TYPE
		SYNTAX Gauge
		ACCESS read-only
		STATUS mandatory
		DESCRIPTION
                   "The total number of threads operating within the
                    respective Oracle components as seen by the
                    operating system.  Monitoring the number of
                    threads can help with performance tuning resource
                    contention issues that may be brought about by too
                    many threads or can help identify if too few
                    threads have too great of a workload." 
		::= { oramodTtlFootprt 6 }

        oramodTtlINBLKS OBJECT-TYPE
		SYNTAX Gauge
		ACCESS read-only
		STATUS mandatory
		DESCRIPTION
			" The number of blocks of data input by the processes."
		::= { oramodTtlFootprt 7 }

        oramodTtlOUTBLKS OBJECT-TYPE
		SYNTAX Gauge
		ACCESS read-only
		STATUS mandatory
		DESCRIPTION
			" The number of blocks of data put by the processes."
		::= { oramodTtlFootprt 8 }

        oramodTtlMSGSSENT OBJECT-TYPE
		SYNTAX Counter
		ACCESS read-only
		STATUS mandatory
		DESCRIPTION
			" The number of messages sent by the processes."
		::= { oramodTtlFootprt 9 }

        oramodTtlMSGSRCVD OBJECT-TYPE
		SYNTAX Counter
		ACCESS read-only
		STATUS mandatory
		DESCRIPTION
		" The number of messages received by the processes."
		::= { oramodTtlFootprt 10 }

        oramodTtlSYSCALLS OBJECT-TYPE
		SYNTAX Counter
		ACCESS read-only
		STATUS mandatory
		DESCRIPTION
		" The number of system calls invoked by the processes."
		::= { oramodTtlFootprt 11 }

        oramodTtlMINORPGFLTS OBJECT-TYPE
		SYNTAX Counter
		ACCESS read-only
		STATUS mandatory
		DESCRIPTION
		" The number of minor page faults incurred by the process.
	 	Minor faults do not require I/O to retrieve the page."
		::= { oramodTtlFootprt 12 }

        oramodTtlMAJORPGFLTS OBJECT-TYPE
		SYNTAX Counter
		ACCESS read-only
		STATUS mandatory
		DESCRIPTION
		" The number of major page faults incurred by the process.
	 	Minor faults require I/O to retrieve the page."
		::= { oramodTtlFootprt 13 }

        oramodTtlNUMSWAPS OBJECT-TYPE
		SYNTAX Counter
		ACCESS read-only
		STATUS mandatory
		DESCRIPTION
		" The number of times the processes have been swapped."
		::= { oramodTtlFootprt 14 }

        oramodTtlVOLCNTX OBJECT-TYPE
		SYNTAX Counter
		ACCESS read-only
		STATUS mandatory
		DESCRIPTION
		" The number of voluntary context switches incurred by the 
		processes. Voluntary contest switches occur when the processor
		voluntary gives up the CPU (e.g. waiting on I/O)."
		::= { oramodTtlFootprt 15 }

        oramodTtlINVOLCNTX OBJECT-TYPE
                SYNTAX Counter
                ACCESS read-only
                STATUS mandatory
                DESCRIPTION
                   "The number of involuntary context switches
                    incurred by the processes.  An involuntary context
                    switch occurs when the process has executed for
                    the duration of its time quantum and is switched
                    out by the process scheduler."
		::= { oramodTtlFootprt 16 }

        oramodTtlDISKSIZE OBJECT-TYPE
                SYNTAX INTEGER 
                ACCESS read-only
                STATUS mandatory
                DESCRIPTION
                   "The size, in KBytes of the Oracle root directory
                    and all the Database Disk storage areas."
		::= { oramodTtlFootprt 17 }


-- This is the master index of databases.
-- Contains the most important scalar creation information from
-- v$database and v$parameter.

        oramodDbCfgTable OBJECT-TYPE
                SYNTAX SEQUENCE OF OramodDbCfgEntry
                ACCESS not-accessible
                STATUS mandatory
                DESCRIPTION
                   "This table describes the instance names, index numbers
		    and initial startup information."
                ::= { oramodDbCfg 1 }

        oramodDbCfgEntry OBJECT-TYPE
                SYNTAX OramodDbCfgEntry
                ACCESS not-accessible
                STATUS mandatory
                DESCRIPTION
                   "An entry in the Oracle Configuration table."
                INDEX { oramodDbCfgSIDINDX }
                ::= {  oramodDbCfgTable 1 }

        OramodDbCfgEntry ::= SEQUENCE{
                oramodDbCfgSIDINDX
                        INTEGER,
                oramodDbCfgSID
                        DisplayString,
		oramodDbCfgVERSION 
                        DisplayString,
		oramodDbCfgHOME 
			DisplayString,
		oramodDbCfgBASE 
			DisplayString,
                oramodDbCfgID
                        INTEGER,
                oramodDbCfgCRTDT
                        DisplayString,
                oramodDbCfgLOGMODE
                        DisplayString,
                oramodDbCfgCTRLFILETYPE
                        DisplayString,
                oramodDbCfgOPENMODE
                        DisplayString,
                oramodDbCfgMAXPROCESS
                        INTEGER,
                oramodDbCfgMAXSESSION
                        INTEGER,
                oramodDbCfgTIMEDSTATISTICS
                        DisplayString,
                oramodDbCfgCPUCNT
                        INTEGER,
                oramodDbCfgSHAREDPOOLSIZE
                        INTEGER,
                oramodDbCfgSHAREDPOOLRSSIZE
                        INTEGER,
                oramodDbCfgLARGEPOOLSIZE
                        INTEGER,
                oramodDbCfgJAVAPOOLSIZE
                        INTEGER,
                oramodDbCfgCNTRLFILES
                        DisplayString,
                oramodDbCfgDBBLKBUFF
                        INTEGER,
                oramodDbCfgDBBLKSIZE
                        INTEGER,
                oramodDbCfgCKPTINTRVL
                        INTEGER,
                oramodDbCfgDBFILES
                        INTEGER,
                oramodDbCfgSORTAREASIZE
                        INTEGER,
                oramodDbCfgOPENCURSORS
                        INTEGER,
                oramodDbCfgTRNSACTNS
                        INTEGER,
                oramodDbCfgTRNSACTNSPERSEG
                        INTEGER,
                oramodDbCfgMAXROLLSEG
                        INTEGER
        }

        oramodDbCfgSIDINDX OBJECT-TYPE
                SYNTAX INTEGER (1..2147483647)
                ACCESS read-only
                STATUS mandatory
                DESCRIPTION
		   "Sid's Index Number."
                ::= { oramodDbCfgEntry 1 }

	oramodDbCfgSID OBJECT-TYPE
		SYNTAX DisplayString
		ACCESS read-only
		STATUS mandatory
		DESCRIPTION
		   "Database Name."
		::= { oramodDbCfgEntry 2 }

	oramodDbCfgVERSION OBJECT-TYPE
		SYNTAX DisplayString
		ACCESS read-only
		STATUS mandatory
		DESCRIPTION
		   "Description and version of this Oracle installation
		    from v$version"
		::= { oramodDbCfgEntry 3 }

        oramodDbCfgHOME OBJECT-TYPE
                SYNTAX DisplayString 
                ACCESS read-only
                STATUS mandatory
                DESCRIPTION
                   "The Installation Directory for Oracle or ORACLEHOME."
		::= { oramodDbCfgEntry 4 }

        oramodDbCfgBASE OBJECT-TYPE
                SYNTAX DisplayString 
                ACCESS read-only
                STATUS mandatory
                DESCRIPTION
                   "The Base Directory for Oracle or ORACLEBASE."
		::= { oramodDbCfgEntry 5 }

        oramodDbCfgID OBJECT-TYPE
		SYNTAX INTEGER 
		ACCESS read-only
		STATUS mandatory
		DESCRIPTION
                   "The database ID calculated when the database is created
		and stored in all file headers (521382036)."
		::= { oramodDbCfgEntry 6 }

        oramodDbCfgCRTDT OBJECT-TYPE
		SYNTAX DisplayString
		ACCESS read-only
		STATUS mandatory
		DESCRIPTION
                   "The original creation date and time of the database."
		::= { oramodDbCfgEntry 7 }

        oramodDbCfgLOGMODE OBJECT-TYPE
		SYNTAX DisplayString
		ACCESS read-only
		STATUS mandatory
		DESCRIPTION
                   "The Archive log mode: NOARCHIVELOG or ARCHIVELOG."
		::= { oramodDbCfgEntry 8 }

        oramodDbCfgCTRLFILETYPE OBJECT-TYPE
		SYNTAX DisplayString
		ACCESS read-only
		STATUS mandatory
		DESCRIPTION
                   "Control File Type. Can be the following types : 
		CURRENT,STANDBY,CLONE,BACKUP,CREATED."
		::= { oramodDbCfgEntry 9 }

        oramodDbCfgOPENMODE OBJECT-TYPE
		SYNTAX DisplayString
		ACCESS read-only
		STATUS mandatory
		DESCRIPTION
                   "Shows whether the database is set to READ WRITE 
		or READ ONLY (NEW TO 8i.)."
		::= { oramodDbCfgEntry 10 } 

        oramodDbCfgMAXPROCESS OBJECT-TYPE
		SYNTAX INTEGER (1..2147483647) 
		ACCESS read-only
		STATUS mandatory
		DESCRIPTION
                   "For a multiple-process operation, this parameter 
		specifies the maximum number of user processes that can 
		simultaneously connect to an Oracle server. The PROCESSES 
		parameter is used to derive the SESSIONS INIT.ORA parameter.
		The default is 50. Typical range 6 - OS/dependent" 
		::= { oramodDbCfgEntry 11 }

        oramodDbCfgMAXSESSION OBJECT-TYPE
		SYNTAX INTEGER (1..2147483647) 
		ACCESS read-only
		STATUS mandatory
		DESCRIPTION
                   "Maximum number of User and System Sessions." 
		::= { oramodDbCfgEntry 12 }

        oramodDbCfgTIMEDSTATISTICS OBJECT-TYPE
		SYNTAX DisplayString
		ACCESS read-only
		STATUS mandatory
		DESCRIPTION
                   "TRUE/FALSE: sets timing on. Should be false for 
		maximum performance." 
		::= { oramodDbCfgEntry 13 }

        oramodDbCfgCPUCNT OBJECT-TYPE
		SYNTAX INTEGER (1..2147483647) 
		ACCESS read-only
		STATUS mandatory
		DESCRIPTION
                   "The maximum number of CPU's for this instance." 
		::= { oramodDbCfgEntry 14 }

        oramodDbCfgSHAREDPOOLSIZE OBJECT-TYPE
		SYNTAX INTEGER (1..2147483647) 
		ACCESS read-only
		STATUS mandatory
		DESCRIPTION
                   "Shared Pool Size Size in Kbytes. Controls the size of the
		memory area used for parsing and executing SQL statements.
		The default is 3.5 Mbytes. Typical Range 300 Kbytes. It is O/S
		dependent. " 
		::= { oramodDbCfgEntry 15 }

        oramodDbCfgSHAREDPOOLRSSIZE OBJECT-TYPE
		SYNTAX INTEGER  (1..2147483647) 
		ACCESS read-only
		STATUS mandatory
		DESCRIPTION
                   "Shared Pool Reserved Size Kbytes." 
		::= { oramodDbCfgEntry 16 }

        oramodDbCfgLARGEPOOLSIZE OBJECT-TYPE
		SYNTAX INTEGER (1..2147483647) 
		ACCESS read-only
		STATUS mandatory
		DESCRIPTION
                   "Large Pool Reserved Size Kbytes." 
		::= { oramodDbCfgEntry 17 }

        oramodDbCfgJAVAPOOLSIZE OBJECT-TYPE
		SYNTAX INTEGER (1..2147483647) 
		ACCESS read-only
		STATUS mandatory
		DESCRIPTION
                   "Java Pool Size in Kbytes Default is (20000K) " 
		::= { oramodDbCfgEntry 18 }

        oramodDbCfgCNTRLFILES OBJECT-TYPE
		SYNTAX DisplayString
		ACCESS read-only
		STATUS mandatory
		DESCRIPTION
                   "Name and path of control files. String of file names." 
		::= { oramodDbCfgEntry 19 }

        oramodDbCfgDBBLKBUFF OBJECT-TYPE
		SYNTAX INTEGER (1..2147483647)  
		ACCESS read-only
		STATUS mandatory
		DESCRIPTION
                   "Number of Database Block Buffers in blocks. Controls 
		how much memory is available in the buffer cache for data 
		blocks. Default is (26240)" 
		::= { oramodDbCfgEntry 20 }

        oramodDbCfgDBBLKSIZE OBJECT-TYPE
		SYNTAX INTEGER (1024..8192)
		ACCESS read-only
		STATUS mandatory
		DESCRIPTION
                   "Size of Database Blocks. O/S dependent" 
		::= { oramodDbCfgEntry 21 }

        oramodDbCfgCKPTINTRVL OBJECT-TYPE
		SYNTAX INTEGER (1..2147483647)  
		ACCESS read-only
		STATUS mandatory
		DESCRIPTION
                   "Redo Log Checkpoint Interval." 
		::= { oramodDbCfgEntry 22 }

        oramodDbCfgDBFILES OBJECT-TYPE
		SYNTAX INTEGER (1..2147483647)  
		ACCESS read-only
		STATUS mandatory
		DESCRIPTION
                   "Maximum Number of Database Files." 
		::= { oramodDbCfgEntry 23 }

        oramodDbCfgSORTAREASIZE OBJECT-TYPE
		SYNTAX INTEGER (1..2147483647)  
		ACCESS read-only
		STATUS mandatory
		DESCRIPTION
                   "Maximum Sort Area Size. Controls the amount of memory
		allocated to each process in the Process Global Area for
		any sorting activity (for multithreaded server this is 
		allocated in the shared pool). When a process needs more 
		memory than is available for a sort, disk space must be 
		allocated in the temporary tablespace. Tuning is based on 
		the transaction mix of the application. The default 
		(O/S dependent) is adequate for most DB operations.  " 
		::= { oramodDbCfgEntry 24 }

        oramodDbCfgOPENCURSORS OBJECT-TYPE
		SYNTAX INTEGER (1..2147483647) 
		ACCESS read-only
		STATUS mandatory
		DESCRIPTION
                   "Maximum open cursors a single-user process can have 
		at once. Typical Range (1 - 2147483647)." 
		::= { oramodDbCfgEntry 25 }

        oramodDbCfgTRNSACTNS OBJECT-TYPE
		SYNTAX INTEGER (1..2147483647)  
		ACCESS read-only
		STATUS mandatory
		DESCRIPTION
                   "Maximum number of concurrent transactions allowed at 
		one time." 
		::= { oramodDbCfgEntry 26 }

        oramodDbCfgTRNSACTNSPERSEG OBJECT-TYPE
		SYNTAX INTEGER (1..2147483647)  
		ACCESS read-only
		STATUS mandatory
		DESCRIPTION
                   "Maximum number of concurrent transactions per segment.
		Default is 30. O/S dependent." 
		::= { oramodDbCfgEntry 27 }

        oramodDbCfgMAXROLLSEG OBJECT-TYPE
		SYNTAX INTEGER (1..65536) 
		ACCESS read-only
		STATUS mandatory
		DESCRIPTION
                   "Maximum number of rollback segments." 
		::= { oramodDbCfgEntry 28 }

--
-- Oracle configuration information from v$datafile and v$datafileheader
--        oramodCfgDf    OBJECT IDENTIFIER ::= { oramodCfg 3 }

        oramodCfgDfTable OBJECT-TYPE
                SYNTAX SEQUENCE OF OramodCfgDfEntry
                ACCESS not-accessible
                STATUS mandatory
                DESCRIPTION
                   "This table describes the database files for the database."
                ::= { oramodCfgDf 1 }

        oramodCfgDfEntry OBJECT-TYPE
                SYNTAX OramodCfgDfEntry
                ACCESS not-accessible
                STATUS mandatory
                DESCRIPTION
                   "An entry in the Oracle v$datafile table."
                INDEX { oramodCfgDfSIDINDX, oramodCfgDfFILENUM }
                ::= {  oramodCfgDfTable 1 }

        OramodCfgDfEntry ::= SEQUENCE{
                oramodCfgDfSIDINDX
                        INTEGER,
                oramodCfgDfFILENUM
                        INTEGER,
                oramodCfgDfSTATUS
                        DisplayString,
                oramodCfgDfENABLED
                        DisplayString,
                oramodCfgDfUNRCVRBLECHG
                        INTEGER,
                oramodCfgDfUNRCVRBLETIME
                        INTEGER,
                oramodCfgDfKBYTES
                        INTEGER,
                oramodCfgDfCRTKBYTES
                        INTEGER,
                oramodCfgDfFNAME
                        DisplayString,
                oramodCfgDfCRTTIME
                        DisplayString,
                oramodCfgDfTBLESPACENUM
                        INTEGER,
                oramodCfgDfTBLESPACERFILENUM
                        INTEGER,
                oramodCfgDfBLOCKS
                        INTEGER,
                oramodCfgDfBLOCKSIZE
                        INTEGER,
                oramodCfgDfERROR
                        INTEGER,
                oramodCfgDfRECOVER
                        DisplayString,
                oramodCfgDfRSTLOGSCHGNUM
                        INTEGER,
                oramodCfgDfRSTLOGSTIME
			DisplayString
        }

        oramodCfgDfSIDINDX OBJECT-TYPE
                SYNTAX INTEGER (1..2147483647)
                ACCESS read-only
                STATUS mandatory
                DESCRIPTION
		   "Sid Index Number."
                ::= { oramodCfgDfEntry 1 }

        oramodCfgDfFILENUM OBJECT-TYPE
                SYNTAX INTEGER
                ACCESS read-only
                STATUS mandatory
                DESCRIPTION
		   "File Identification Number."
                ::= { oramodCfgDfEntry 2 }

        oramodCfgDfSTATUS OBJECT-TYPE
                SYNTAX DisplayString
                ACCESS read-only
                STATUS mandatory
                DESCRIPTION
		   "Type of file (system or user) and its status.
		Values: OFFLINE, ONLINE, SYSTEM, RECOVER, SYSOFF(an offline
		file from the SYSTEM tablespace)."
                ::= { oramodCfgDfEntry 3 }

        oramodCfgDfENABLED OBJECT-TYPE
                SYNTAX DisplayString
                ACCESS read-only
                STATUS mandatory
                DESCRIPTION
		   "Describes how accessible the file is from SQL. Can be
		DISABLED, READ ONLY, READ WRITE and UNKNOWN."
                ::= { oramodCfgDfEntry 4 }

        oramodCfgDfUNRCVRBLECHG OBJECT-TYPE
                SYNTAX INTEGER (1..2147483647)
                ACCESS read-only
                STATUS mandatory
                DESCRIPTION
		   "The last unrecoverbale change number made to this datafile.
		Always updated when an unrecoverable operation completes."
                ::= { oramodCfgDfEntry 5 }

        oramodCfgDfUNRCVRBLETIME OBJECT-TYPE
                SYNTAX INTEGER (1..2147483647)
                ACCESS read-only
                STATUS mandatory
                DESCRIPTION
		   "The last unrecoverbale change time made to this datafile.
		Always updated when an unrecoverable operation completes."
                ::= { oramodCfgDfEntry 6 }

        oramodCfgDfKBYTES OBJECT-TYPE
                SYNTAX INTEGER (1..2147483647)
                ACCESS read-only
                STATUS mandatory
                DESCRIPTION
		   "Current size in kbytes; 0 if unaccessible."
                ::= { oramodCfgDfEntry 7 }

        oramodCfgDfCRTKBYTES OBJECT-TYPE
                SYNTAX INTEGER (1..2147483647)
                ACCESS read-only
                STATUS mandatory
                DESCRIPTION
		   "Size when created."
                ::= { oramodCfgDfEntry 8 }

        oramodCfgDfFNAME OBJECT-TYPE
                SYNTAX DisplayString
                ACCESS read-only
                STATUS mandatory
                DESCRIPTION
		   "Name of the file."
                ::= { oramodCfgDfEntry 9 }

        oramodCfgDfCRTTIME OBJECT-TYPE
                SYNTAX DisplayString 
                ACCESS read-only
                STATUS mandatory
                DESCRIPTION
		   "Time at which the datafile was created."
                ::= { oramodCfgDfEntry 10 }

        oramodCfgDfTBLESPACENUM OBJECT-TYPE
                SYNTAX INTEGER (1..2147483647)
                ACCESS read-only
                STATUS mandatory
                DESCRIPTION
		   "Tablespace Number."
                ::= { oramodCfgDfEntry 11 }

        oramodCfgDfTBLESPACERFILENUM OBJECT-TYPE
                SYNTAX INTEGER (1..2147483647)
                ACCESS read-only
                STATUS mandatory
                DESCRIPTION
		   "Tablespace Relative Df Number."
                ::= { oramodCfgDfEntry 12 }

        oramodCfgDfBLOCKS OBJECT-TYPE
                SYNTAX INTEGER (0..2147483647)
                ACCESS read-only
                STATUS mandatory
                DESCRIPTION
		   "Current datafile size in blocks; 0 if inaccessible."
                ::= { oramodCfgDfEntry 13 }

        oramodCfgDfBLOCKSIZE OBJECT-TYPE
                SYNTAX INTEGER (0..2147483647)
                ACCESS read-only
                STATUS mandatory
                DESCRIPTION
		   "Block size of the datafile."
                ::= { oramodCfgDfEntry 14 }

-- Oracle configuration information from v$datafileheader

        oramodCfgDfERROR OBJECT-TYPE
                SYNTAX INTEGER (0..2147483647)
                ACCESS read-only
                STATUS mandatory
                DESCRIPTION
		   "NULL if the header read success. If error must restore." 
                ::= { oramodCfgDfEntry 15 }

        oramodCfgDfRECOVER OBJECT-TYPE
                SYNTAX DisplayString
                ACCESS read-only
                STATUS mandatory
                DESCRIPTION
		   "YES/NO File needs media recovery." 
                ::= { oramodCfgDfEntry 16 }

        oramodCfgDfRSTLOGSCHGNUM OBJECT-TYPE
                SYNTAX INTEGER (0..2147483647)
                ACCESS read-only
                STATUS mandatory
                DESCRIPTION
		   "Reset Logs change number." 
                ::= { oramodCfgDfEntry 17 }

        oramodCfgDfRSTLOGSTIME OBJECT-TYPE
                SYNTAX DisplayString
                ACCESS read-only
                STATUS mandatory
                DESCRIPTION
		   "Reset Logs timestamp." 
                ::= { oramodCfgDfEntry 18 }


--
-- Oracle configuration information from v$logfile. Redo Logs location 
-- and status.
--	oramodCfgLf  OBJECT IDENTIFIER ::= { oramodCfg 8 }

        oramodCfgLfTable OBJECT-TYPE
                SYNTAX SEQUENCE OF OramodCfgLfEntry
                ACCESS not-accessible
                STATUS mandatory
                DESCRIPTION
                   "This table describes the redo log files locations
                    for each Oracle installation from v$logfile."
                ::= { oramodCfgLf 1 }

        oramodCfgLfEntry OBJECT-TYPE
                SYNTAX OramodCfgLfEntry
                ACCESS not-accessible
                STATUS mandatory
                DESCRIPTION
                   "An entry in the Oracle Logfile table."
                INDEX { oramodCfgLfSIDINDX, oramodCfgLfMEMBERINDX }
                ::= {  oramodCfgLfTable 1 }

        OramodCfgLfEntry ::= SEQUENCE{
                oramodCfgLfSIDINDX
                        INTEGER,
                oramodCfgLfMEMBERINDX
                        INTEGER,
                oramodCfgLfGROUPNUM
                        INTEGER,
                oramodCfgLfSTATUS
                        DisplayString,
                oramodCfgLfMEMBER
                        DisplayString
        }

        oramodCfgLfSIDINDX OBJECT-TYPE
                SYNTAX INTEGER (1..2147483647)
                ACCESS read-only
                STATUS mandatory
                DESCRIPTION
		   "Sid Index Number."
                ::= { oramodCfgLfEntry 1 }

	oramodCfgLfMEMBERINDX OBJECT-TYPE
		SYNTAX INTEGER (1..2147482647)
		ACCESS read-only
		STATUS mandatory
		DESCRIPTION
		   "Logfile member index."
		::= { oramodCfgLfEntry 2 }

        oramodCfgLfGROUPNUM OBJECT-TYPE
		SYNTAX INTEGER (1..2147482647)
                ACCESS read-only
                STATUS mandatory
                DESCRIPTION
		   "Group Number."
                ::= { oramodCfgLfEntry 3 }

	oramodCfgLfSTATUS OBJECT-TYPE
		SYNTAX DisplayString
		ACCESS read-only
		STATUS mandatory
		DESCRIPTION
		   "Status of File."
		::= { oramodCfgLfEntry 4 }

	oramodCfgLfMEMBER OBJECT-TYPE
		SYNTAX DisplayString
		ACCESS read-only
		STATUS mandatory
		DESCRIPTION
		   "File name and path."
		::= { oramodCfgLfEntry 5 }

-- Oracle System Global Area (SGA) configuration information from v$sga.
-- The SGA is a common database storage area for information that supports
-- current sessions. As the values of its attributes are configured in the
-- INIT.ORA file, they do not change while the database instance is running.

--	oramodCfgSga  OBJECT IDENTIFIER ::= { oramodCfg 9 }

        oramodCfgSgaTable OBJECT-TYPE
                SYNTAX SEQUENCE OF OramodCfgSgaEntry
                ACCESS not-accessible
                STATUS mandatory
                DESCRIPTION
                   "This table summarizes the system global area."
                ::= { oramodCfgSga 1 }

        oramodCfgSgaEntry OBJECT-TYPE
                SYNTAX OramodCfgSgaEntry
                ACCESS not-accessible
                STATUS mandatory
                DESCRIPTION
                   "An entry in the Oracle Sga table."
                INDEX { oramodCfgSgaSIDINDX }
                ::= {  oramodCfgSgaTable 1 }

        OramodCfgSgaEntry ::= SEQUENCE {
                oramodCfgSgaSIDINDX
                        INTEGER,
                oramodCfgSgaTOTALMEMALLOC
                        INTEGER,
                oramodCfgSgaFIXEDSGA
                        INTEGER,
                oramodCfgSgaVARIABLE
                        INTEGER,
                oramodCfgSgaDBBUFF
                        INTEGER,
                oramodCfgSgaREDOBUFF
                        INTEGER
        }

        oramodCfgSgaSIDINDX OBJECT-TYPE
                SYNTAX INTEGER (1..2147483647)
                ACCESS read-only
                STATUS mandatory
                DESCRIPTION
		   "Sid Index Number."
                ::= { oramodCfgSgaEntry 1 }

        oramodCfgSgaTOTALMEMALLOC OBJECT-TYPE
		SYNTAX INTEGER (1..2147482647)
                ACCESS read-only
                STATUS mandatory
                DESCRIPTION
		  "Total real memory allocated. Summation of values in v$sga."
                ::= { oramodCfgSgaEntry 2 }

        oramodCfgSgaFIXEDSGA OBJECT-TYPE
                SYNTAX INTEGER (1..2147483647) 
                ACCESS read-only
                STATUS mandatory
                DESCRIPTION
		  "Fixed memory allocated in Kbytes"
                ::= { oramodCfgSgaEntry 3 }

        oramodCfgSgaVARIABLE OBJECT-TYPE
                SYNTAX INTEGER (1..2147483647) 
                ACCESS read-only
                STATUS mandatory
                DESCRIPTION
		  "Variable Memory allocated in the SGA"
                ::= { oramodCfgSgaEntry 4 }

        oramodCfgSgaDBBUFF OBJECT-TYPE
                SYNTAX INTEGER (1..2147483647) 
                ACCESS read-only
                STATUS mandatory
                DESCRIPTION
		  "Database buffers allocated in Kbytes. Typical Range is
		4 Kbytes - 2 Gbytes.  "
                ::= { oramodCfgSgaEntry 5 }

        oramodCfgSgaREDOBUFF OBJECT-TYPE
                SYNTAX INTEGER (1..2147483647) 
                ACCESS read-only
                STATUS mandatory
                DESCRIPTION
		  "Redo Buffers allocated in Kbytes"
                ::= { oramodCfgSgaEntry 6 }


-- Oracle Performance Group 
-- Footprint of the Oracle "Instance" in terms of resource consumption
-- (e.g. CPU, disk, memory)

        --oramodFootprint OBJECT IDENTIFIER ::= { oramodPerf 1 }

        oramodFootprtTable OBJECT-TYPE
                SYNTAX SEQUENCE OF OramodFootprtEntry
                ACCESS not-accessible
                STATUS mandatory
                DESCRIPTION
                   "This table describes the system footprint."
                ::= { oramodFootprt 1 }

        oramodFootprtEntry OBJECT-TYPE
                SYNTAX OramodFootprtEntry
                ACCESS not-accessible
                STATUS mandatory
                DESCRIPTION
                   "An entry in the Oracle Footprint table."
                INDEX { oramodFootprtSIDINDX }
                ::= {  oramodFootprtTable 1 }

        OramodFootprtEntry ::= SEQUENCE {
                oramodFootprtSIDINDX
                        INTEGER,
		oramodFootprtCPUTIME 
                        INTEGER,
		oramodFootprtPERCENTCPU 
                        INTEGER,
		oramodFootprtMEMSIZE 
                        Gauge,
		oramodFootprtRSS 
                        Gauge,
		oramodFootprtPERCENTMEM 
                        INTEGER,
		oramodFootprtTHREADS 
                        Gauge,
		oramodFootprtINBLKS 
                        Gauge,
		oramodFootprtOUTBLKS 
                        Gauge,
		oramodFootprtMSGSSENT 
                        Counter,
		oramodFootprtMSGSRCVD 
                        Counter,
		oramodFootprtSYSCALLS 
                        Counter,
		oramodFootprtMINORPGFLTS 
                        Counter,
		oramodFootprtMAJORPGFLTS 
                        Counter,
		oramodFootprtNUMSWAPS 
                        Counter,
		oramodFootprtVOLCNTX 
                        Counter,
		oramodFootprtINVOLCNTX 
                        Counter,
		oramodFootprtHOMESIZE
                        Gauge,
		oramodFootprtDBDISKSIZE 
                        Gauge,
		oramodFootprtLASTUPDATE 
                        TimeTicks
			
        }

        oramodFootprtSIDINDX OBJECT-TYPE
                SYNTAX INTEGER (1..2147483647)
                ACCESS read-only
                STATUS mandatory
                DESCRIPTION
		   "Empire's Index Number."
                ::= { oramodFootprtEntry 1 }

        oramodFootprtCPUTIME OBJECT-TYPE
		SYNTAX INTEGER
		ACCESS read-only
		STATUS mandatory
		DESCRIPTION
                   "CPU time, in seconds, accumulated by Oracle
                    which includes all its core components and
                    instance.  Because core components can
                    come and go, the accumulated cpu time can
                    fluctuate therefore making this variable
                    unsuitable as a counter." 
		::= { oramodFootprtEntry 2 }

        oramodFootprtPERCENTCPU OBJECT-TYPE
		SYNTAX INTEGER (0..100)
		ACCESS read-only
		STATUS mandatory
		DESCRIPTION
                   "The percentage of CPU utilization, by Oracle,
                    over the last sample interval.  Since fractions
                    are not supported by SNMP, the value reported is
                    the percentage multipled by 100.  It is the sum of
                    the CPU utilization of all the Oracle core
                    services and components.  Its gives a
                    good indication of the CPU resource consumption by
                    the entire Oracle application'"
		::= { oramodFootprtEntry 3 }

        oramodFootprtMEMSIZE OBJECT-TYPE
		SYNTAX Gauge
		ACCESS read-only
		STATUS mandatory
		DESCRIPTION
 		    "The combined size of Oracle's text, data,
                     and stack segments in KBytes.  It is the
                     summation of the process sizes for all the core
                     Oracle services and optional connectors." 
		::= { oramodFootprtEntry 4 }

        oramodFootprtRSS OBJECT-TYPE
		SYNTAX Gauge
		ACCESS read-only
		STATUS mandatory
		DESCRIPTION
		    "The real memory (resident set) size of Oracle
                     in KBytes.  It is the summation of the process
                     RSS for all the core Oracle services and
                     optional connectors."  
		::= { oramodFootprtEntry 5 }

        oramodFootprtPERCENTMEM OBJECT-TYPE
		SYNTAX INTEGER (0..100)
		ACCESS read-only
		STATUS mandatory
		DESCRIPTION
		   "The percentage (0-100) of real memory used by
		    the Oracle Application which includes core
                    services and optional connectors." 
		::= { oramodFootprtEntry 6 }

        oramodFootprtTHREADS OBJECT-TYPE
		SYNTAX Gauge
		ACCESS read-only
		STATUS mandatory
		DESCRIPTION
                   "The total number of threads operating within the
                    respective Oracle components as seen by the
                    operating system.  Monitoring the number of
                    threads can help with performance tuning resource
                    contention issues that may be brought about by too
                    many threads or can help identify if too few
                    threads have too great of a workload." 
		::= { oramodFootprtEntry 7 }

        oramodFootprtINBLKS OBJECT-TYPE
		SYNTAX Gauge
		ACCESS read-only
		STATUS mandatory
		DESCRIPTION
			" The number of blocks of data input by the processes."
		::= { oramodFootprtEntry 8 }

        oramodFootprtOUTBLKS OBJECT-TYPE
		SYNTAX Gauge
		ACCESS read-only
		STATUS mandatory
		DESCRIPTION
			" The number of blocks of data put by the processes."
		::= { oramodFootprtEntry 9 }

        oramodFootprtMSGSSENT OBJECT-TYPE
		SYNTAX Counter
		ACCESS read-only
		STATUS mandatory
		DESCRIPTION
			" The number of messages sent by the processes."
		::= { oramodFootprtEntry 10 }

        oramodFootprtMSGSRCVD OBJECT-TYPE
		SYNTAX Counter
		ACCESS read-only
		STATUS mandatory
		DESCRIPTION
		" The number of messages received by the processes."
		::= { oramodFootprtEntry 11 }

        oramodFootprtSYSCALLS OBJECT-TYPE
		SYNTAX Counter
		ACCESS read-only
		STATUS mandatory
		DESCRIPTION
		" The number of system calls invoked by the processes."
		::= { oramodFootprtEntry 12 }

        oramodFootprtMINORPGFLTS OBJECT-TYPE
		SYNTAX Counter
		ACCESS read-only
		STATUS mandatory
		DESCRIPTION
		" The number of minor page faults incurred by the process.
	 	Minor faults do not require I/O to retrieve the page."
		::= { oramodFootprtEntry 13 }

        oramodFootprtMAJORPGFLTS OBJECT-TYPE
		SYNTAX Counter
		ACCESS read-only
		STATUS mandatory
		DESCRIPTION
		" The number of major page faults incurred by the process.
	 	Minor faults require I/O to retrieve the page."
		::= { oramodFootprtEntry 14 }

        oramodFootprtNUMSWAPS OBJECT-TYPE
		SYNTAX Counter
		ACCESS read-only
		STATUS mandatory
		DESCRIPTION
		" The number of times the processes have been swapped."
		::= { oramodFootprtEntry 15 }

        oramodFootprtVOLCNTX OBJECT-TYPE
		SYNTAX Counter
		ACCESS read-only
		STATUS mandatory
		DESCRIPTION
		" The number of voluntary context switches incurred by the 
		processes. Voluntary contest switches occur when the processor
		voluntary gives up the CPU (e.g. waiting on I/O)."
		::= { oramodFootprtEntry 16 }

        oramodFootprtINVOLCNTX OBJECT-TYPE
                SYNTAX Counter
                ACCESS read-only
                STATUS mandatory
                DESCRIPTION
                   "The number of involuntary context switches
                    incurred by the processes.  An involuntary context
                    switch occurs when the process has executed for
                    the duration of its time quantum and is switched
                    out by the process scheduler."
		::= { oramodFootprtEntry 17 }

        oramodFootprtHOMESIZE OBJECT-TYPE
                SYNTAX Gauge 
                ACCESS read-only
                STATUS mandatory
                DESCRIPTION
                   "The size, in KBytes of the Oracle root directory
                    and all files beneath it."
		::= { oramodFootprtEntry 18 }

        oramodFootprtDBDISKSIZE OBJECT-TYPE
                SYNTAX Gauge
                ACCESS read-only
                STATUS mandatory
                DESCRIPTION
                   "The size, in KBytes, of all the Oracle Database disk
                    storage areas.  It is a summation of all database
                    files. Summing these components in one location presents
                    an easy and convenient MIB object to poll and
                    self-monitor."
		::= { oramodFootprtEntry 19 }

        oramodFootprtLASTUPDATE OBJECT-TYPE
                SYNTAX TimeTicks
                ACCESS read-only
                STATUS mandatory
                DESCRIPTION
                   "The time (based on sysUpTime) that the last update
                    of all variables in the table was completed."
		::= { oramodFootprtEntry 20 }


-- Oracle Individual Instance Files and Sizes 
      --oramodFFootprt OBJECT IDENTIFIER ::= { oramodFootprint 2 }

        oramodFFootprtTable OBJECT-TYPE
                SYNTAX SEQUENCE OF OramodFFootprtEntry
                ACCESS not-accessible
                STATUS mandatory
                DESCRIPTION
                   "This table describes the system footprint."
                ::= { oramodFFootprt 1 }

        oramodFFootprtEntry OBJECT-TYPE
                SYNTAX OramodFFootprtEntry
                ACCESS not-accessible
                STATUS mandatory
                DESCRIPTION
                   "An entry in the Oracle File Footprint table."
                INDEX { oramodFFootprtSIDINDX, oramodFFootprtFILEINDX  }
                ::= {  oramodFFootprtTable 1 }

        OramodFFootprtEntry ::= SEQUENCE {
                oramodFFootprtSIDINDX
                        INTEGER,
		oramodFFootprtFILEINDX
                        INTEGER,
		oramodFFootprtFILETYPE 
                        DisplayString,
		oramodFFootprtFILENAME 
                        DisplayString,
		oramodFFootprtCRTTS
                        DisplayString,
		oramodFFootprtCRTKBYTES
                        INTEGER,
		oramodFFootprtKBYTES
                        INTEGER,
		oramodFFootprtBLOCKS
                        INTEGER,
		oramodFFootprtSTATUS 
                        DisplayString,
		oramodFFootprtRECOVER 
                        DisplayString,
		oramodFFootprtAVGIOTIM 
                        DisplayString
        }

        oramodFFootprtSIDINDX OBJECT-TYPE
                SYNTAX INTEGER (1..2147483647)
                ACCESS read-only
                STATUS mandatory
                DESCRIPTION
		   "Sid Index Number."
                ::= { oramodFFootprtEntry 1 }

        oramodFFootprtFILEINDX OBJECT-TYPE
                SYNTAX INTEGER (1..2147483647)
                ACCESS read-only
                STATUS mandatory
                DESCRIPTION
		   "File Index Number."
                ::= { oramodFFootprtEntry 2 }

        oramodFFootprtFILETYPE OBJECT-TYPE
                SYNTAX DisplayString 
                ACCESS read-only
                STATUS mandatory
                DESCRIPTION
		   "File Type."
                ::= { oramodFFootprtEntry 3 }

        oramodFFootprtFILENAME OBJECT-TYPE
                SYNTAX DisplayString 
                ACCESS read-only
                STATUS mandatory
                DESCRIPTION
		   "File Name. "
                ::= { oramodFFootprtEntry 4 }

        oramodFFootprtCRTTS OBJECT-TYPE
                SYNTAX DisplayString 
                ACCESS read-only
                STATUS mandatory
                DESCRIPTION
		   "Last update timestamp."
                ::= { oramodFFootprtEntry 5 }

        oramodFFootprtCRTKBYTES OBJECT-TYPE
                SYNTAX INTEGER 
                ACCESS read-only
                STATUS mandatory
                DESCRIPTION
		   "File creation kbytes."
                ::= { oramodFFootprtEntry 6 }

        oramodFFootprtKBYTES OBJECT-TYPE
                SYNTAX INTEGER 
                ACCESS read-only
                STATUS mandatory
                DESCRIPTION
		   "File kbytes."
                ::= { oramodFFootprtEntry 7 }

        oramodFFootprtBLOCKS OBJECT-TYPE
                SYNTAX INTEGER 
                ACCESS read-only
                STATUS mandatory
                DESCRIPTION
		   "File blocks."
                ::= { oramodFFootprtEntry 8 }

        oramodFFootprtSTATUS OBJECT-TYPE
                SYNTAX DisplayString 
                ACCESS read-only
                STATUS mandatory
                DESCRIPTION
		   "File Status."
                ::= { oramodFFootprtEntry 9 }

        oramodFFootprtRECOVER OBJECT-TYPE
                SYNTAX DisplayString 
                ACCESS read-only
                STATUS mandatory
                DESCRIPTION
		   "Last Recover timestamp."
                ::= { oramodFFootprtEntry 10 }

        oramodFFootprtAVGIOTIM OBJECT-TYPE
                SYNTAX DisplayString 
                ACCESS read-only
                STATUS mandatory
                DESCRIPTION
		   "File average I/O time."
                ::= { oramodFFootprtEntry 11 }

--      oramodMetric OBJECT IDENTIFIER ::= { oramodPerf 2 }
--      Metrics Data : This table is used to give an overall indication of the 
--	performance of each instance. The first 17 entries are ratios 
--      based on the variables of the private Oracle Database MIB that Oracle
-- 	reccomends monitoring. 

        oramodMetricsTable OBJECT-TYPE
                SYNTAX SEQUENCE OF OramodMetricsEntry
                ACCESS not-accessible
                STATUS mandatory
                DESCRIPTION
                   "This table describes the database metrics."
                ::= { oramodMetrics 1 }

        oramodMetricsEntry OBJECT-TYPE
                SYNTAX OramodMetricsEntry
                ACCESS not-accessible
                STATUS mandatory
                DESCRIPTION
                   "An entry in the Metrics table."
                INDEX { oramodMetricsSIDINDX }
                ::= {  oramodMetricsTable 1 }

        OramodMetricsEntry ::= SEQUENCE {
                oramodMetricsSIDINDX
                        INTEGER,
		oramodMetricsBCPT 
                        Gauge,
		oramodMetricsBGR 
                        Gauge,
		oramodMetricsBVPT 
                        Gauge,
		oramodMetricsCHR 
                        Gauge,
		oramodMetricsCR 
                        Gauge,
		oramodMetricsCPT 
                        Gauge,
		oramodMetricsCBR 
                        Gauge,
		oramodMetricsCCR 
                        Gauge,
		oramodMetricsCRR 
                        Gauge,
		oramodMetricsLCM 
                        Gauge,
		oramodMetricsRTUC 
                        Gauge,
		oramodMetricsRLSW 
                        Gauge,
		oramodMetricsRSR 
                        Gauge,
		oramodMetricsSOR 
                        Gauge,
		oramodMetricsTRR 
                        Gauge,
		oramodMetricsUCR 
                        Gauge,
		oramodMetricsUCPP 
                        Gauge,
		oramodMetricsURR 
                        Gauge,
		oramodMetricsSGALCE 
                        Gauge,
		oramodMetricsSGADDCE 
                        Gauge,
		oramodMetricsDBTOTALRW 
                        Counter,
		oramodMetricsDBBLKCHG 
                        Counter,
		oramodMetricsDBBLKGET 
                        Counter,
		oramodMetricsDBCNSTGET
                        Counter,
		oramodMetricsDBPHYSREAD  
                        Counter,
		oramodMetricsDBSORTDISK 
                        Counter,
		oramodMetricsDBSORTMEM 
                        Counter,
		oramodMetricsBLKFREEWAIT 
                        Gauge,
		oramodMetricsMTHRDQUEUEWAIT 
                        Gauge,
		oramodMetricsSESSHIWTRMEM 
                        Counter,
		oramodMetricsSESSCURRMEM 
                        Counter,
		oramodMetricsSESSHIWTR 
                        Counter,
		oramodMetricsSESSCURRENT 
                        Gauge,
		oramodMetricsUSERCOMMITS 
                        Counter,
		oramodMetricsUSERROLLBACK 
                        Counter,
		oramodMetricsUSERCALLS 
                        Counter,
                oramodMetricsDBPHYSWRTS 
                        Counter,
                oramodMetricsTBLSCANROWS 
                        Counter,
                oramodMetricsTBLFTCHROWID 
                        Counter,
                oramodMetricsTBLFTCHCROW 
                        Counter,
                oramodMetricsRECRSVCALLS 
                        Counter,
                oramodMetricsCNSTCHGS 
                        Counter,
                oramodMetricsPARSECNT 
                        Counter,
                oramodMetricsCPUTM 
                        INTEGER,
                oramodMetricsLOGFILESWTCH 
                        INTEGER,
                oramodMetricsARCHIVER 
                        DisplayString,
                oramodMetricsDATABASESTATUS 
                        DisplayString,
                oramodMetricsSHUTDOWNPENDING 
                        DisplayString,
                oramodMetricsLASTUPDATE
                        TimeTicks

        }

        oramodMetricsSIDINDX OBJECT-TYPE
                SYNTAX INTEGER (1..2147483647)
                ACCESS read-only
                STATUS mandatory
                DESCRIPTION
		   "Sid Index Number."
                ::= { oramodMetricsEntry 1 }

        oramodMetricsBCPT OBJECT-TYPE
		SYNTAX Gauge
		ACCESS read-only
		STATUS mandatory
		DESCRIPTION
                   "Block Changes Per Transaction scaled by 100. 
		This ratio measures the amount of DML work that each transaction
	 	performs. Creating or dropping indexes impact this value,
		because changes to index blocks increment it."
		::= { oramodMetricsEntry 2 }

        oramodMetricsBGR OBJECT-TYPE
		SYNTAX Gauge
		ACCESS read-only
		STATUS mandatory
		DESCRIPTION
                   "Block Get Rate Per Second scaled by 100. This ratio
		determines the block get rate per second. It is a basic 
		measurement of the rate at which the application systems
	 	reference the database. "
		::= { oramodMetricsEntry 3 }

        oramodMetricsBVPT OBJECT-TYPE
		SYNTAX Gauge
		ACCESS read-only
		STATUS mandatory
		DESCRIPTION
                   "Block Vists Per Transaction scaled by 100. This ratio
 		measures the work database load imposed per transaction. It
		is a basic measurement of the application workload.  If it
		is moving independently, then this strongly indicates that
	 	there has been a change in the application workload."
		::= { oramodMetricsEntry 4 }

        oramodMetricsCHR OBJECT-TYPE
		SYNTAX Gauge
		ACCESS read-only
		STATUS mandatory
		DESCRIPTION
                  "Cache Hit Ratio scaled by 100. Measures the effectiveness 
		of the hits against the buffer cache. Whenever Oracle reads
		data from disk, it places that data into the buffer cache. 
		Data is aged out of the buffer cache using a least recently 
		used algorithm. Oracle looks in the buffer cache first for 
		data requests.  If the data is not there, Oracle searches the 
		disk based data files that comprise the database. On most 
		production systems, Oracle should not have to resort to disk 
		reads more than 20% of the time. So, if the buffer cache hit 
		ratio is less than 80%, you should consider increasing the 
		database buffer cache in the System Global Area. This can be 
		done by increasing the value for DBBLOCKBUFFER in the 
		initialization parameter file."
		::= { oramodMetricsEntry 5 }

        oramodMetricsCR OBJECT-TYPE
		SYNTAX Gauge
		ACCESS read-only
		STATUS mandatory
		DESCRIPTION
                   "Call Rate over time. The number of user and recursive 
		calls over time. This ratio measures the work demand
		rate being placed on the instance from all work sources."
		::= { oramodMetricsEntry 6 }

        oramodMetricsCPT OBJECT-TYPE
		SYNTAX Gauge
		ACCESS read-only
		STATUS mandatory
		DESCRIPTION
                   "Calls Per Transaction scaled by 100. The number of 
		database requests per committed transaction. Can be used to 
		detect changes in the application, or in the way in which
		it is normally used. Ad hoc queries will cause this value
		to sharply increase. "
		::= { oramodMetricsEntry 7 }

        oramodMetricsCBR OBJECT-TYPE
		SYNTAX Gauge
		ACCESS read-only
		STATUS mandatory
		DESCRIPTION
                   "Changed Blocks scaled by 100. Measures the balance between
		queris and data manipulation language (DML) within the database 
		applications. Can be used to detect changes in application 
		usage or indexes."
		::= { oramodMetricsEntry 8 }

        oramodMetricsCCR OBJECT-TYPE
		SYNTAX Gauge
		ACCESS read-only
		STATUS mandatory
		DESCRIPTION
                   "Consistent Change Ratio scaled by 100. The ratio of database		consistent changes and consistent gets. It measures the extent
		to which applications are having to exercise the read 
		consistency mechanism. Update and delete operations are 
		subject to read consistency. "
		::= { oramodMetricsEntry 9 }

	oramodMetricsCRR OBJECT-TYPE
		SYNTAX Gauge
		ACCESS read-only
		STATUS mandatory
		DESCRIPTION
                   "Continued Row Ratio scaled by 100. Measures the space 
		useage of data blocks. Should be close to zero, except in
		applications handling long LONG columns. If this ratio 
		increases over time, usually PCTFREE has been set too low on 
		one or more tables."
		::= { oramodMetricsEntry 10 }

        oramodMetricsLCM OBJECT-TYPE
		SYNTAX Gauge
		ACCESS read-only
		STATUS mandatory
		DESCRIPTION
                   "Library Cache Miss Ratio scaled by 100. The ratio of
		missed requests and reloads to access library cached 
		objects since instance startup. The library cache is 
		a memory structure containing shared SQL and PL/SQL areas.
		Monitoring the library cache is important to determine 
		whether or not to resize the shared pool. If this ratio
		increases over time, then resource useage can be expected
		to increase. A rising library cache miss ratio may be due
		to wider use of application functionality causing more SQL
		statements and stored procedures to be active that had 
		been previously."
		::= { oramodMetricsEntry 11 }

        oramodMetricsRTUC OBJECT-TYPE
		SYNTAX Gauge
		ACCESS read-only
		STATUS mandatory
		DESCRIPTION
                   "Recursive To User Call Ratio scaled by 100. The ratio of
		recursive and user or application calls. A change in this
		ratio can reflect an application change or the need to adjust
		the size of the shared pool."
		::= { oramodMetricsEntry 12 }

        oramodMetricsRLSW OBJECT-TYPE
		SYNTAX Gauge
		ACCESS read-only
		STATUS mandatory
		DESCRIPTION
                   "Redo Log Space Wait Ratio scaled by 100. It shows the 
		rate at which failures are occuring in writing to the redo
		log space and is used to measure memory allocation.  If this
		ratio is greater than 1/5,000, the the redo log buffer should
		be increased until the redo log space wait ratio stops
		failing. "
		::= { oramodMetricsEntry 13 }

        oramodMetricsRSR OBJECT-TYPE
		SYNTAX Gauge
		ACCESS read-only
		STATUS mandatory
		DESCRIPTION
                   "Row Source Ratio scaled by 100. It shows the percentage 
		of total rows retrieved which came from full table scans. If
		this percentage start to rise above zero, the interpretation
		of other statistics may need to be reviewed."
		::= { oramodMetricsEntry 14 }

        oramodMetricsSOR OBJECT-TYPE
		SYNTAX Gauge
		ACCESS read-only
		STATUS mandatory
		DESCRIPTION
                   "Sort Overflow Ratio scaled by 100. Indicates the number
		of sorts which are using temporary segments. Under restrictive
		circumstances when there is a predominance of medium sorts,
		increasing the sort area size may be effective. "
		::= { oramodMetricsEntry 15 }


        oramodMetricsTRR OBJECT-TYPE
		SYNTAX Gauge
		ACCESS read-only
		STATUS mandatory
		DESCRIPTION
                   "Transaction Rate Ratio scaled by 100. The rate at which
		users or applications are committing transactions. If a fall
		in this value is associated with a rise in the number of
		connected users or vice versa, an administrator should
		be concerned. Changes in application structure or work 
		patterns can also distort this figure."
		::= { oramodMetricsEntry 16 }

        oramodMetricsUCR OBJECT-TYPE
		SYNTAX Gauge
		ACCESS read-only
		STATUS mandatory
		DESCRIPTION
                   "User Call Rate Ratio scaled by 100. The rate at which
		client users or applications are requesting sql statements.
		Measures the work demand rate being posed by client side
		applications running under the instance. May not be directly
		comparable across application system version changes where 
		code has been moved from client to server or vice versa."
		::= { oramodMetricsEntry 17 }

        oramodMetricsUCPP OBJECT-TYPE
		SYNTAX Gauge
		ACCESS read-only
		STATUS mandatory
		DESCRIPTION
                   "User Calls Per Parse Ratio scaled by 100. The ratio of
		user calls to parse in the shared SQL area.  Indicates how
		well the application is managing its context area. If it 
		changes, then application change is the most likely 
		explanation, but it may indicate the useage patterns are
		changing and users are moving from one module to another 
		either more frequently or less frequently. Although the
		shared SQL area makes the maximizing of this ratio less
		important than with earlier versions of Oracle, it is still
		possible to reduce resource usage by raising this ratio. "
		::= { oramodMetricsEntry 18 }

        oramodMetricsURR OBJECT-TYPE
		SYNTAX Gauge
		ACCESS read-only
		STATUS mandatory
		DESCRIPTION
                   "User Rollback Ratio scaled by 100. The ratio of user or
		application transaction rollbacks. Indicates the rate at 
		which application transactions are failing. Rolling back
		a transaction uses significant resources, and would seem
		to indicate that all of the resources expended in 
		executing the transaction have been wasted. "
		::= { oramodMetricsEntry 19 }

        oramodMetricsSGALCE OBJECT-TYPE
		SYNTAX Gauge
		ACCESS read-only
		STATUS mandatory
		DESCRIPTION
                   "Library Cache Efficiency Percentage scaled by 100. The 
		percentage that a SQL statement did not need to be reloaded
		because it was already in the library cache. This percentage
		should be 100. If not, try resizing the SHAREDPOOLSIZE
		in the initialization file."
		::= { oramodMetricsEntry 20 }

        oramodMetricsSGADDCE OBJECT-TYPE
		SYNTAX Gauge
		ACCESS read-only
		STATUS mandatory
		DESCRIPTION
                   "Data Dictionary Cache Efficiency Percentage scaled by 100.
		Shows the ratio of gets to misses within the shared pool. The
		ratio should be less than 0.1. Various database operations
		cause the RDBMS to access its system tables. These system
		tables are stored in the Oracle data dictionary. The objects
		in the data dictionary are stored in the system tablespace.
		When the RDBMS needs access to its system tables, the tables
		are read into the data dictionary cache. Resizing the shared
		pool can affect this ratio. "
		::= { oramodMetricsEntry 21 }

        -- next 7 from v$sysstat
        oramodMetricsDBTOTALRW OBJECT-TYPE
		SYNTAX Counter
		ACCESS read-only
		STATUS mandatory
		DESCRIPTION
                  "The total number of physical reads and physical writes
		since instance startup. See individual descriptions below." 
		::= { oramodMetricsEntry 22 }

        oramodMetricsDBBLKCHG OBJECT-TYPE
		SYNTAX Counter 
		ACCESS read-only
		STATUS mandatory
		DESCRIPTION
                  "The total number of database block changes. It is 
		incremented each time that a database block is in memory 
		to create a dirty block. This statistic is a rough 
		indication of total database work. Increments at several 
		thousand per second in the largest systems, so this variable 
		is definitely a wraparound candidate." 
		::= { oramodMetricsEntry 23 }

        oramodMetricsDBBLKGET OBJECT-TYPE
		SYNTAX Counter
		ACCESS read-only
		STATUS mandatory
		DESCRIPTION
                  "The total number of database block gets since instance
		startup. It is incremented each time the buffer manager is 
		asked for a database block in current mode, regardless of 
		read consistency. This mode is used to locate blocks which 
		are to be updated, and also to access control information 
		such as segment headers. Only if the requested block is not 
		found in Oracle's Buffer cache will a db block get result in
		 physical I/O. " 
		::= { oramodMetricsEntry 24 }

        oramodMetricsDBCNSTGET OBJECT-TYPE
		SYNTAX Counter
		ACCESS read-only
		STATUS mandatory
		DESCRIPTION
                  "The total number of consistent gets since instance startup.
		This value is incremented each time that the Oracle Buffer 
		Manager is requested to locate a database block as part of 
		a read consistent operation (a query). Only if the requested 
		block is not found in Oracle's Buffer Cache will consistent get
		result in physical I/O.  Increments at several thousand per 
		second in the largest systems, so this variable is definitely 
		a wraparound candidate." 
		::= { oramodMetricsEntry 25 }

        oramodMetricsDBPHYSREAD OBJECT-TYPE
		SYNTAX Counter
		ACCESS read-only
		STATUS mandatory
		DESCRIPTION
                  "The total number of physical reads since instance startup. 
                It increments each time a DB Block is retrieved from the disk
		subsystem, but is not necessarily equal to the number of I/O
		requests made to the host operating system, as multiblock I/O
		may be used. A physical read can be viewed as an SGA Buffer
		Cache miss, hampering throughput (contention induction) and 
		CPU (code pathlength) processing. Unlikely to increment at a 
		rate greater than a few hundred per second."
		::= { oramodMetricsEntry 26 }

        oramodMetricsDBSORTDISK OBJECT-TYPE
		SYNTAX Counter
		ACCESS read-only
		STATUS mandatory
		DESCRIPTION
                  "The total number of database disk sorts since instance
		startup. It increments for each sort which has to allocate 
		disk work space. Should be zero." 
		::= { oramodMetricsEntry 27 }

        oramodMetricsDBSORTMEM OBJECT-TYPE
		SYNTAX Counter 
		ACCESS read-only
		STATUS mandatory
		DESCRIPTION
                  "The total number of database memory sorts since instance
		startup. It is incremented for each sort which does not require
		the allocation of work. Unlikely to increment faster than 
		tens per second, except in the largest systems."
		::= { oramodMetricsEntry 28 }

        oramodMetricsBLKFREEWAIT OBJECT-TYPE
		SYNTAX Gauge
		ACCESS read-only
		STATUS mandatory
		DESCRIPTION
                 "The percent that a request resulted in a wait for a 
		free block. Should be less than 1%. To reduce contention
		for a table's free list the table must be recreated with a
		larger value in the FREELISTS storage parameter."
		::= { oramodMetricsEntry 29 }

        oramodMetricsMTHRDQUEUEWAIT OBJECT-TYPE
		SYNTAX Gauge
		ACCESS read-only
		STATUS mandatory
		DESCRIPTION
                  "The number of seconds waited in queue
		for multi-threaded servers."
		::= { oramodMetricsEntry 30 }

        oramodMetricsSESSHIWTRMEM OBJECT-TYPE
		SYNTAX Counter
		ACCESS read-only
		STATUS mandatory
		DESCRIPTION
                "The maximum highwater amount of session memory used."
		::= { oramodMetricsEntry 31 }

        oramodMetricsSESSCURRMEM OBJECT-TYPE
	 	SYNTAX Counter 
		ACCESS read-only
		STATUS mandatory
		DESCRIPTION
                "The current maximum amount of session memory used."
		::= { oramodMetricsEntry 32 }

        oramodMetricsSESSHIWTR OBJECT-TYPE
		SYNTAX Counter
		ACCESS read-only
		STATUS mandatory
		DESCRIPTION
                "The highwater mark for number of sessions."
		::= { oramodMetricsEntry 33 }

        oramodMetricsSESSCURRENT OBJECT-TYPE
		SYNTAX Gauge
		ACCESS read-only
		STATUS mandatory
		DESCRIPTION
                "The current number of sessions."
		::= { oramodMetricsEntry 34 }

        oramodMetricsUSERCOMMITS OBJECT-TYPE
		SYNTAX Counter
		ACCESS read-only
		STATUS mandatory
		DESCRIPTION
                "Records the number of database transactions successfully
		 completed and records the number of aborted database 
		transactions. In most real world applications, the value is 
		less the 1 per second."
		::= { oramodMetricsEntry 35 }

        oramodMetricsUSERROLLBACK OBJECT-TYPE
		SYNTAX Counter 
		ACCESS read-only
		STATUS mandatory
		DESCRIPTION
                "The number of transactions rolled back since instance startup."
		::= { oramodMetricsEntry 36 }

        oramodMetricsUSERCALLS OBJECT-TYPE
		SYNTAX Counter
		ACCESS read-only
		STATUS mandatory
		DESCRIPTION
                "The number of transactions started since instance startup."
		::= { oramodMetricsEntry 37 }

        oramodMetricsDBPHYSWRTS OBJECT-TYPE
		SYNTAX Counter
		ACCESS read-only
		STATUS mandatory
		DESCRIPTION
                  "The total number of physical writes since instance startup. 
                It increments each time a DB Block is written to the disk. 
		All writes are performed either by DBWR or LGWR, two background 		processes responsible for getting Blocks out of the SGA and back 		on disk." 
		::= { oramodMetricsEntry 38 }

        oramodMetricsTBLSCANROWS OBJECT-TYPE
		SYNTAX Counter
		ACCESS read-only
		STATUS mandatory
		DESCRIPTION
                "The number of rows retrieved through table scans since 
		instance startup."
		::= { oramodMetricsEntry 39 }

        oramodMetricsTBLFTCHROWID OBJECT-TYPE
		SYNTAX Counter
		ACCESS read-only
		STATUS mandatory
		DESCRIPTION
                "The number of rows retrieved through table fetches by 
		rowid since instance startup."
		::= { oramodMetricsEntry 40 }

        oramodMetricsTBLFTCHCROW OBJECT-TYPE
		SYNTAX Counter
		ACCESS read-only
		STATUS mandatory
		DESCRIPTION
                "The number of rows retrieved through table fetches by 
		continued row since instance startup."
		::= { oramodMetricsEntry 41 }

        oramodMetricsRECRSVCALLS OBJECT-TYPE
		SYNTAX Counter
		ACCESS read-only
		STATUS mandatory
		DESCRIPTION
                "The number of recursive calls since instance startup."
		::= { oramodMetricsEntry 42 }

        oramodMetricsCNSTCHGS OBJECT-TYPE
		SYNTAX Counter
		ACCESS read-only
		STATUS mandatory
		DESCRIPTION
                "The number of consistent changes since instance startup."
		::= { oramodMetricsEntry 43 }

        oramodMetricsPARSECNT OBJECT-TYPE
		SYNTAX Counter
		ACCESS read-only
		STATUS mandatory
		DESCRIPTION
                "The number of parses since instance startup."
		::= { oramodMetricsEntry 44 }

        oramodMetricsCPUTM OBJECT-TYPE
		SYNTAX INTEGER
		ACCESS read-only
		STATUS mandatory
		DESCRIPTION
                "The amount of time taken to work requests."
		::= { oramodMetricsEntry 45 }

        oramodMetricsLOGFILESWTCH OBJECT-TYPE
		SYNTAX INTEGER
		ACCESS read-only
		STATUS mandatory
		DESCRIPTION
                "The number of redo log file switches."
		::= { oramodMetricsEntry 46 }

        oramodMetricsARCHIVER OBJECT-TYPE
                SYNTAX DisplayString 
		ACCESS read-only
		STATUS mandatory
		DESCRIPTION
                "The database archiver."
		::= { oramodMetricsEntry 47 }

        oramodMetricsDATABASESTATUS OBJECT-TYPE
                SYNTAX DisplayString 
		ACCESS read-only
		STATUS mandatory
		DESCRIPTION
                "The status of the database."
		::= { oramodMetricsEntry 48 }

        oramodMetricsSHUTDOWNPENDING OBJECT-TYPE
                SYNTAX DisplayString 
		ACCESS read-only
		STATUS mandatory
		DESCRIPTION
                "The shutdown status of the database."
		::= { oramodMetricsEntry 49 }

        oramodMetricsLASTUPDATE OBJECT-TYPE
                SYNTAX TimeTicks
                ACCESS read-only
                STATUS mandatory
                DESCRIPTION
                   "The time (based on sysUpTime) that the last update
                    of all variables in the table was completed."
		::= { oramodMetricsEntry 50 }



-- This table provides aggragete summary information of the performance of the 
-- dictionary cache.  Each user and data request that connects to the database
-- references the data dictionary. The data dictionary cache is an area of the
-- shared pool that contains data dictionary information in memory. These 
-- values are internal but you can influence the amount of resources they get
-- by increasing the value in init.ora for the parameter sharedpoolsize. 
-- The object is to keep as much of the data dictionary information in memory
-- as possible. This is a sumation of each relevent column in v$rowcache for
-- every row.

-- Data Dictionary Aggregate information
      --oramodSgaDddAgg OBJECT IDENTIFIER ::= { oramodSGA 3 }

        oramodSgaDddAggTable OBJECT-TYPE
                SYNTAX SEQUENCE OF OramodSgaDddAggEntry
                ACCESS not-accessible
                STATUS mandatory
                DESCRIPTION
                   "This table describes the data dictionary aggregates."
                ::= { oramodSgaDddAgg 1 }

        oramodSgaDddAggEntry OBJECT-TYPE
                SYNTAX OramodSgaDddAggEntry
                ACCESS not-accessible
                STATUS mandatory
                DESCRIPTION
                   "An entry in the Data Dictionary Aggregate table."
                INDEX { oramodSGAAGGSIDINDX }
                ::= {  oramodSgaDddAggTable 1 }

        OramodSgaDddAggEntry ::= SEQUENCE {
                oramodSGAAGGSIDINDX
                        INTEGER,
                oramodSGAAGGCNT
                        Counter,
                oramodSGAAGGUSGE
                        Counter,
                oramodSGAAGGFIX
                        Counter,
                oramodSGAAGGGET
                        Counter,
                oramodSGAAGGGETMISS
                        Counter,
                oramodSGAAGGSCAN
                        Counter,
                oramodSGAAGGSCANMISS
                        Counter,
                oramodSGAAGGSCANCPLT
                        Counter,
                oramodSGAAGGMODS
                        Counter,
                oramodSGAAGGFLUSH
                        Counter
        }

        oramodSGAAGGSIDINDX OBJECT-TYPE
                SYNTAX INTEGER (1..2147483647)
                ACCESS read-only
                STATUS mandatory
                DESCRIPTION
		   "Sid Index Number."
                ::= { oramodSgaDddAggEntry 1 }

        oramodSGAAGGCNT OBJECT-TYPE
                SYNTAX Counter
                ACCESS read-only
                STATUS mandatory
                DESCRIPTION
		   "Total number of entries in the data dictionary cache
		since instance startup."
                ::= { oramodSgaDddAggEntry 2 }

        oramodSGAAGGUSGE OBJECT-TYPE
                SYNTAX Counter
                ACCESS read-only
                STATUS mandatory
                DESCRIPTION
		   "The total number of cache entries with valid data since
		instance startup."
                ::= { oramodSgaDddAggEntry 3 }

        oramodSGAAGGFIX OBJECT-TYPE
                SYNTAX Counter
                ACCESS read-only
                STATUS mandatory
                DESCRIPTION
		   "The total number of fixed entries in the data dictionary
		cache since instance startup."
                ::= { oramodSgaDddAggEntry 4 }

        oramodSGAAGGGET OBJECT-TYPE
                SYNTAX Counter
                ACCESS read-only
                STATUS mandatory
                DESCRIPTION
		   "The total number of information requests since instance
		startup." 
                ::= { oramodSgaDddAggEntry 5 }

        oramodSGAAGGGETMISS OBJECT-TYPE
                SYNTAX Counter
                ACCESS read-only
                STATUS mandatory
                DESCRIPTION
		   "The total number of informations requests resulting in 
		cache misses since instance startup." 
                ::= { oramodSgaDddAggEntry 6 }

        oramodSGAAGGSCAN OBJECT-TYPE
                SYNTAX Counter
                ACCESS read-only
                STATUS mandatory
                DESCRIPTION
		   "The total number of scan requests since instance startup." 
                ::= { oramodSgaDddAggEntry 7 }

        oramodSGAAGGSCANMISS OBJECT-TYPE
                SYNTAX Counter
                ACCESS read-only
                STATUS mandatory
                DESCRIPTION
		   "The total number of scan requests resulting in misses
		since instance startup." 
                ::= { oramodSgaDddAggEntry 8 }

        oramodSGAAGGSCANCPLT OBJECT-TYPE
                SYNTAX Counter
                ACCESS read-only
                STATUS mandatory
                DESCRIPTION
		  "For subordinate entries, the total number of times 
		list was scanned completely since instance startup."
                ::= { oramodSgaDddAggEntry 9 }

        oramodSGAAGGMODS OBJECT-TYPE
                SYNTAX Counter
                ACCESS read-only
                STATUS mandatory
                DESCRIPTION
		  "The total number of inserts, updates, and deletions
		since instance startup."
                ::= { oramodSgaDddAggEntry 10 }

        oramodSGAAGGFLUSH OBJECT-TYPE
                SYNTAX Counter
                ACCESS read-only
                STATUS mandatory
                DESCRIPTION
		  "The total number of times flushed to disk since instance
		startup."
                ::= { oramodSgaDddAggEntry 11 }

-- This table provides information about SQL and PL/SQL statements that 
-- are stored in the library cache. Oracle stores the execution plan of SQL 
-- statements so that less processing is necessary for subsequent executions.
-- Information is pulled from the view v$librarycache. The library cache is 
-- the most important area of the shared pool to tune. A least recently used
-- algorithm is used to manage the cache. Goals are to hold the 
-- majority of SQL statements and to reduce the number of statements that 
-- have to be reparsed.  Continuous aging and reparsing of statements 
-- degredates perfomance.

      --oramodSgaDlci OBJECT IDENTIFIER ::= { oramodSGA 5 }

        oramodSgaDlciTable OBJECT-TYPE
                SYNTAX SEQUENCE OF OramodSgaDlciEntry
                ACCESS not-accessible
                STATUS mandatory
                DESCRIPTION
                  "This table describes the detailed library cache information."
                ::= { oramodSgaDlci 1 }

        oramodSgaDlciEntry OBJECT-TYPE
                SYNTAX OramodSgaDlciEntry
                ACCESS not-accessible
                STATUS mandatory
                DESCRIPTION
                   "An entry in the Library Cache table."
                INDEX { oramodSGADLCISIDINDX, oramodSGADLCIINDX }
                ::= {  oramodSgaDlciTable 1 }

        OramodSgaDlciEntry ::= SEQUENCE {
      		oramodSGADLCISIDINDX
			INTEGER,
      		oramodSGADLCIINDX
			INTEGER,
	        oramodSGADLCINAME
                        DisplayString,
                oramodSGADLCIGET
                        Counter,
                oramodSGADLCIGETHIT
                        Counter,
                oramodSGADLCIGETHITRT
                        Gauge,
                oramodSGADLCIPIN
                        Counter,
                oramodSGADLCIPINHIT
                        Counter,
                oramodSGADLCIPINHITRT
                        Gauge,
                oramodSGADLCIRELOAD
                        Counter,
                oramodSGADLCIINVALID
                        Counter
        }
        oramodSGADLCISIDINDX OBJECT-TYPE
                SYNTAX INTEGER (1..2147483647)
                ACCESS read-only
                STATUS mandatory
                DESCRIPTION
		   "Sid Index Number."
                ::= { oramodSgaDlciEntry 1 }

        oramodSGADLCIINDX OBJECT-TYPE
                SYNTAX INTEGER (1..2147483647)
                ACCESS read-only
                STATUS mandatory
                DESCRIPTION
		   "Namespace Index Number."
                ::= { oramodSgaDlciEntry 2 }

        oramodSGADLCINAME OBJECT-TYPE
                SYNTAX DisplayString
                ACCESS read-only
                STATUS mandatory
                DESCRIPTION
		   "Library Cache Namespace. (SQL AREA, TABLE/PROCEDURE, BODY, 
		TRIGGER, INDEX, CLUSTER, OBJECT, PIPE)"
                ::= { oramodSgaDlciEntry 3 }

        oramodSGADLCIGET OBJECT-TYPE
                SYNTAX Counter 
                ACCESS read-only
                STATUS mandatory
                DESCRIPTION
		   "The total number of request handles to library namespace
		since instance startup Typical range (0..500,00)." 
                ::= { oramodSgaDlciEntry 4 }

        oramodSGADLCIGETHIT OBJECT-TYPE
                SYNTAX Counter 
                ACCESS read-only
                STATUS mandatory
                DESCRIPTION
		   "The total number of times handles are already allocated
		in the cache. If the handle is not already allocated it is a
		miss." 
                ::= { oramodSgaDlciEntry 5 }

        oramodSGADLCIGETHITRT OBJECT-TYPE
                SYNTAX Gauge
                ACCESS read-only
                STATUS mandatory
                DESCRIPTION
		   "The Get/Hit ratio determines the percentage of parse 
		calls that find a cursor to share. The value is derived from 
		GETHITS divided by GETS. Should be in the high 90s which 
		indicates that most of the handles the system has tried to get
		are cached." 
                ::= { oramodSgaDlciEntry 6 }

        oramodSGADLCIPIN OBJECT-TYPE
                SYNTAX Counter 
                ACCESS read-only
                STATUS mandatory
                DESCRIPTION
		   "The total number of pin requests for objects in the cache
		since instance startup." 
                ::= { oramodSgaDlciEntry 7 }

        oramodSGADLCIPINHIT OBJECT-TYPE
                SYNTAX Counter 
                ACCESS read-only
                STATUS mandatory
                DESCRIPTION
		   "The number of pin hits or executions of objects that 
		are already allocated and initiated in the cache. Otherwise, 
		it is a miss, and the system has to reallocate and initialize
		it with data queried from the database or generate the data." 
                ::= { oramodSgaDlciEntry 8 }

        oramodSGADLCIPINHITRT OBJECT-TYPE
                SYNTAX Gauge
                ACCESS read-only
                STATUS mandatory
                DESCRIPTION
		   "The ratio of PINHITS to PINS. Values close to 100 indicate
		that most of the objects the system has tried to pin and 
		access have been cached." 
                ::= { oramodSgaDlciEntry 9 }

        oramodSGADLCIRELOAD OBJECT-TYPE
                SYNTAX Counter 
                ACCESS read-only
                STATUS mandatory
                DESCRIPTION
		  "Number of times a statement had to be reparsed in order to
		be executed. Statements are reloaded due to aging or 
		invalidation. Should never be more that one percent of PINS.
		 Goal is the have close to zero reloads."
                ::= { oramodSgaDlciEntry 10 }

        oramodSGADLCIINVALID OBJECT-TYPE
                SYNTAX Counter 
                ACCESS read-only
                STATUS mandatory
                DESCRIPTION
		  "The number of times that non-persistant library objects
	 	(like SQL areas) have been invalidated."
                ::= { oramodSgaDlciEntry 11 }

-- Redo Log information from view v$sysstat. Redo Logs are used to perform
-- database recoveries. Oracle stores data that is being changed by 
-- transactions in the redo log buffers. Performance can be improved by 
-- alternating the placement of the redo logs on disk. Since Oracle will 
-- read the prior log to archive it, disk head contention will
-- occur if the logs are on the same disk. By placing them on different disks,
-- one disk can be read while the other is being written to. 

        --oramodRedoLogBuf OBJECT IDENTIFIER ::= { oramodPerf 7 }

        oramodRedoLogBufTable OBJECT-TYPE
                SYNTAX SEQUENCE OF OramodRedoLogBufEntry
                ACCESS not-accessible
                STATUS mandatory
                DESCRIPTION
                  "This table describes the Redo Log information."
                ::= { oramodRedoLogBuf 1 }

        oramodRedoLogBufEntry OBJECT-TYPE
                SYNTAX OramodRedoLogBufEntry
                ACCESS not-accessible
                STATUS mandatory
                DESCRIPTION
                   "An entry in the Redo Log table."
                INDEX { oramodREDOSIDINDX }
                ::= {  oramodRedoLogBufTable 1 }

        OramodRedoLogBufEntry ::= SEQUENCE {
      		oramodREDOSIDINDX
			INTEGER,
		oramodREDOBLKWRT 
			Counter,
		oramodREDOENTRIES 
			Counter,
		oramodREDOSIZE 
			INTEGER,
		oramodREDOSPACERQST 
			Counter,
		oramodREDOSPACEWAIT 
			Counter,
		oramodREDOSYNCHWRT 
			Counter,
		oramodREDOSYNCHTM 
			INTEGER,
		oramodREDOWASTAGE 
			Counter,
		oramodREDORETRIES 
			Counter,
		oramodREDOLASTUPDATE 
                        TimeTicks
	}

        oramodREDOSIDINDX OBJECT-TYPE
                SYNTAX INTEGER (1..2147483647)
                ACCESS read-only
                STATUS mandatory
                DESCRIPTION
		   "Sid Index Number."
                ::= { oramodRedoLogBufEntry 1 }

        oramodREDOBLKWRT OBJECT-TYPE
		SYNTAX Counter
		ACCESS read-only
		STATUS mandatory
		DESCRIPTION
                  "The total number of redo blocks written since instance
		startup."
		::= { oramodRedoLogBufEntry 2 }

        oramodREDOENTRIES OBJECT-TYPE
		SYNTAX Counter
		ACCESS read-only
		STATUS mandatory
		DESCRIPTION
                  "The total number of redo entries in the redo log since
		instance startup."
		::= { oramodRedoLogBufEntry 3 }

        oramodREDOSIZE OBJECT-TYPE
		SYNTAX INTEGER
		ACCESS read-only
		STATUS mandatory
		DESCRIPTION
                  "The size of the redo log."
		::= { oramodRedoLogBufEntry 4 }

        oramodREDOSPACERQST OBJECT-TYPE
		SYNTAX Counter
		ACCESS read-only
		STATUS mandatory
		DESCRIPTION
                  "The number of redo log space requests. Should be close 
		to zero. A nonzero value means the the buffer may be too small. 		Increase the size of the buffer so that processes are not 
		waiting. The INIT.ora parameter LOGBUFFER controls the 
		size of the redo log buffer."
		::= { oramodRedoLogBufEntry 5 }

        oramodREDOSPACEWAIT OBJECT-TYPE
		SYNTAX Counter
		ACCESS read-only
		STATUS mandatory
		DESCRIPTION
                  "The total number of redo log space wait time since
		instance startup"
		::= { oramodRedoLogBufEntry 6 }

        oramodREDOSYNCHWRT OBJECT-TYPE
		SYNTAX Counter
		ACCESS read-only
		STATUS mandatory
		DESCRIPTION
                  "The total number of redo synch writes since instance
		startup."
		::= { oramodRedoLogBufEntry 7 }

        oramodREDOSYNCHTM OBJECT-TYPE
		SYNTAX INTEGER
		ACCESS read-only
		STATUS mandatory
		DESCRIPTION
                  "The amount of redo log synch time."
		::= { oramodRedoLogBufEntry 8 }

        oramodREDOWASTAGE OBJECT-TYPE
		SYNTAX Counter
		ACCESS read-only
		STATUS mandatory
		DESCRIPTION
                  "The total amount of redo log wastage."
		::= { oramodRedoLogBufEntry 9 }

        oramodREDORETRIES OBJECT-TYPE
		SYNTAX Counter
		ACCESS read-only
		STATUS mandatory
		DESCRIPTION
                  "The total number of redo retries."
		::= { oramodRedoLogBufEntry 10 }

        oramodREDOLASTUPDATE OBJECT-TYPE
                SYNTAX TimeTicks
                ACCESS read-only
                STATUS mandatory
                DESCRIPTION
                   "The time (based on sysUpTime) that the last update
                    of all variables in the table was completed."
		::= { oramodRedoLogBufEntry 11 }

-- Rollback Segment information
	-- This table records cumulative statistics about all rollback segment
	-- usage since the database was last started. To simplify the
	-- management of multiple rollback segment entries within a rollback
	-- segment, try to size the rollback segment so that each of its 
	-- extents is large enough to support a typical transaction.
 
        --oramodRollBack OBJECT IDENTIFIER ::= { oramodPerf 5 }

        oramodRollBackTable OBJECT-TYPE
                SYNTAX SEQUENCE OF OramodRollBackEntry
                ACCESS not-accessible
                STATUS mandatory
                DESCRIPTION
                  "This table describes any rollback segments."
                ::= { oramodRollBack 1 }

        oramodRollBackEntry OBJECT-TYPE
                SYNTAX OramodRollBackEntry
                ACCESS not-accessible
                STATUS mandatory
                DESCRIPTION
                   "An entry in the rollstat table."
                INDEX { oramodRollBackSIDINDX, oramodRollBackSEGINDX }
                ::= {  oramodRollBackTable 1 }

        OramodRollBackEntry ::= SEQUENCE {
                oramodRollBackSIDINDX
                        INTEGER,
                oramodRollBackSEGINDX
                        INTEGER,
                oramodRollBackSEGNAME
                        DisplayString,
                oramodRollBackEXTENTS
                        Counter,
                oramodRollBackRSSIZE
                        Counter,
                oramodRollBackWRITES
                        Counter,
                oramodRollBackGETS
                        Counter,
                oramodRollBackWAITS
                        Counter,
                oramodRollBackOPTSIZE
                        INTEGER,
                oramodRollBackSHRINKS
                        Counter,
                oramodRollBackWRAPS
                        Counter,
                oramodRollBackEXTENDS
                        Counter,
                oramodRollBackAVESHRINK
                        INTEGER,
                oramodRollBackAVEACTIVE
                        Counter,
                oramodRollBackSTATUS
                        INTEGER
        }

        oramodRollBackSIDINDX OBJECT-TYPE
                SYNTAX INTEGER (1..2147483647)
                ACCESS read-only
                STATUS mandatory
                DESCRIPTION
		   "SID Index Number."
                ::= { oramodRollBackEntry 1 }


        oramodRollBackSEGINDX OBJECT-TYPE
                SYNTAX INTEGER
                ACCESS read-only
                STATUS mandatory
                DESCRIPTION
		   "Undo Segment Number used as an index."
                ::= { oramodRollBackEntry 2 }

        oramodRollBackSEGNAME OBJECT-TYPE
                SYNTAX DisplayString
                ACCESS read-only
                STATUS mandatory
                DESCRIPTION
		   "Rollback Segment Name."
                ::= { oramodRollBackEntry 3 }

        oramodRollBackEXTENTS OBJECT-TYPE
                SYNTAX Counter
                ACCESS read-only
                STATUS mandatory
                DESCRIPTION
		   "The total number of Segment Extends since instance
		startup."
                ::= { oramodRollBackEntry 4 }

        oramodRollBackRSSIZE OBJECT-TYPE
                SYNTAX Counter
                ACCESS read-only
                STATUS mandatory
                DESCRIPTION
		   "The size of the Rollback Segment."
                ::= { oramodRollBackEntry 5 }

        oramodRollBackWRITES OBJECT-TYPE
                SYNTAX Counter
                ACCESS read-only
                STATUS mandatory
                DESCRIPTION
		   "The total number of Segment Writes since instance startup."
                ::= { oramodRollBackEntry 6 }

        oramodRollBackGETS OBJECT-TYPE
                SYNTAX Counter
                ACCESS read-only
                STATUS mandatory
                DESCRIPTION
		   "The total number of Rollback Segment Gets since 
		instance startup."
                ::= { oramodRollBackEntry 7 }

        oramodRollBackWAITS OBJECT-TYPE
                SYNTAX Counter
                ACCESS read-only
                STATUS mandatory
                DESCRIPTION
		   "The total number of Segment Waits since instance startup."
                ::= { oramodRollBackEntry 8 }

        oramodRollBackOPTSIZE OBJECT-TYPE
                SYNTAX INTEGER
                ACCESS read-only
                STATUS mandatory
                DESCRIPTION
		   "The Optimal Size of the Rollback Segment. This size should
		be set based on application usage to minimize space management
		issues."
                ::= { oramodRollBackEntry 9 }

        oramodRollBackSHRINKS OBJECT-TYPE
                SYNTAX Counter
                ACCESS read-only
                STATUS mandatory
                DESCRIPTION
		   "The total number of Rollback Segment Shrinks since
		instance startup. Rollback Segments shrink back to their
		optimal size after extends have occurred."
                ::= { oramodRollBackEntry 10 }

        oramodRollBackWRAPS OBJECT-TYPE
                SYNTAX Counter
                ACCESS read-only
                STATUS mandatory
                DESCRIPTION
		   " The total number of Rollback Segment wraps since instance
		startup. When a transaction's rollback segment entry cannot be
		stored within a single extent, the entry wraps into a second
		extent within the rollback segment. If this value is non-zero,
		try recreating the rollback segments with larger extent sizes."
                ::= { oramodRollBackEntry 11 }

        oramodRollBackEXTENDS OBJECT-TYPE
                SYNTAX Counter
                ACCESS read-only
                STATUS mandatory
                DESCRIPTION
		   "Rollback Segment extends. Extensions indicate that the
		rollback segments are handling larger transactions than they
		were designed for; and if the entire rollback segment cannot
		handle a transaction's rollback information, a single extent 
		will not be able to hold it either. Thus, rollback segments
		that extend will frequently have a high number of wraps."
                ::= { oramodRollBackEntry 12 }

        oramodRollBackAVESHRINK OBJECT-TYPE
                SYNTAX INTEGER
                ACCESS read-only
                STATUS mandatory
                DESCRIPTION
		   "The average shrink size of the Rollback Segment since
		this instance startup."
                ::= { oramodRollBackEntry 13 }

        oramodRollBackAVEACTIVE OBJECT-TYPE
                SYNTAX Counter
                ACCESS read-only
                STATUS mandatory
                DESCRIPTION
		   "Segment average active."
                ::= { oramodRollBackEntry 14 }

        oramodRollBackSTATUS OBJECT-TYPE
                SYNTAX INTEGER
                ACCESS read-only
                STATUS mandatory
                DESCRIPTION
		   "Segment status."
                ::= { oramodRollBackEntry 15 }

-- Resource waits from the v$systemevent table. Wait time is the largest
-- contributor to total response time. This table can be used to identify
-- events contributing the highest amounts of wait times."

      --oramodWaits OBJECT IDENTIFIER ::= { oramodWaits 2 }
      -- Thirteen entries per instance

        oramodWaitsTable OBJECT-TYPE
                SYNTAX SEQUENCE OF OramodWaitsEntry
                ACCESS not-accessible
                STATUS mandatory
                DESCRIPTION
                  "This table describes resource waits."
                ::= { oramodWaits 1 }

        oramodWaitsEntry OBJECT-TYPE
                SYNTAX OramodWaitsEntry
                ACCESS not-accessible
                STATUS mandatory
                DESCRIPTION
                   "An entry in the waits table."
                INDEX { oramodWaitsSIDINDX, oramodWaitsEVENTINDX }
                ::= {  oramodWaitsTable 1 }

        OramodWaitsEntry ::= SEQUENCE {
          	oramodWaitsSIDINDX
                        INTEGER,
          	oramodWaitsEVENTINDX
                        INTEGER,
	        oramodWaitsEVENT
                        DisplayString,
                oramodWaitsTOTALWAITS
                        Counter,
                oramodWaitsTOTALTIMOUT
                        Counter,
                oramodWaitsTIMEWAITED
                        Counter,
                oramodWaitsAVGWAIT
                        Counter
        }

        oramodWaitsSIDINDX OBJECT-TYPE
                SYNTAX INTEGER (1..2147483647)
                ACCESS read-only
                STATUS mandatory
                DESCRIPTION
		   "Sid Index Number."
                ::= { oramodWaitsEntry 1 }

        oramodWaitsEVENTINDX OBJECT-TYPE
                SYNTAX INTEGER (1..2147483647)
                ACCESS read-only
                STATUS mandatory
                DESCRIPTION
		   "Event's Index Number."
                ::= { oramodWaitsEntry 2 }

        oramodWaitsEVENT OBJECT-TYPE
                SYNTAX DisplayString
                ACCESS read-only
                STATUS mandatory
                DESCRIPTION
		   "Resource Name."
                ::= { oramodWaitsEntry 3 }

        oramodWaitsTOTALWAITS OBJECT-TYPE
                SYNTAX Counter
                ACCESS read-only
                STATUS mandatory
                DESCRIPTION
		   "Resource Total Waits."
                ::= { oramodWaitsEntry 4 }

        oramodWaitsTOTALTIMOUT OBJECT-TYPE
                SYNTAX Counter
                ACCESS read-only
                STATUS mandatory
                DESCRIPTION
		   "Resource Total Timeouts."
                ::= { oramodWaitsEntry 5 }

        oramodWaitsTIMEWAITED OBJECT-TYPE
                SYNTAX Counter
                ACCESS read-only
                STATUS mandatory
                DESCRIPTION
		   "Resource Total Waited."
                ::= { oramodWaitsEntry 6 }

        oramodWaitsAVGWAIT OBJECT-TYPE
                SYNTAX Counter
                ACCESS read-only
                STATUS mandatory
                DESCRIPTION
		   "Resource average wait."
                ::= { oramodWaitsEntry 7}


-- Expensive SQL for each instance. Nothing will reduce the overall performance
-- of a system faster than bad application SQL. Use this table to monitor
-- statements that are running overlong or require many disk reads. 

        oramodExpSqlTable OBJECT-TYPE
                SYNTAX SEQUENCE OF OramodExpSqlEntry
                ACCESS not-accessible
                STATUS mandatory
                DESCRIPTION
                  "This table describes expensive sql."
                ::= { oramodExpSql 1 }

        oramodExpSqlEntry OBJECT-TYPE
                SYNTAX OramodExpSqlEntry
                ACCESS not-accessible
                STATUS mandatory
                DESCRIPTION
                   "An entry in the v$sqlarea table."
                INDEX { oramodExpSqlSIDINDX, oramodExpSqlSQLINDX }
                ::= {  oramodExpSqlTable 1 }

        OramodExpSqlEntry ::= SEQUENCE {
                oramodExpSqlSIDINDX
                        INTEGER,
                oramodExpSqlSQLINDX
                        INTEGER,
                oramodExpSqlEXECUTION
                        Gauge,
                oramodExpSqlDISKREAD
                        Gauge,
                oramodExpSqlPARSECNT
                        Gauge,
                oramodExpSqlBUFFGETS
                        Gauge,
                oramodExpSqlSORTS
                        Gauge,
                oramodExpSqlSQL
                        DisplayString 
        }

        oramodExpSqlSIDINDX OBJECT-TYPE
                SYNTAX INTEGER (1..2147483647)
                ACCESS read-only
                STATUS mandatory
                DESCRIPTION
		   "Sid Index Number."
                ::= { oramodExpSqlEntry 1 }

        oramodExpSqlSQLINDX OBJECT-TYPE
                SYNTAX INTEGER (1..2147483647)
                ACCESS read-only
                STATUS mandatory
                DESCRIPTION
		   "SQL Statement Index Number."
                ::= { oramodExpSqlEntry 2 }

        oramodExpSqlEXECUTION OBJECT-TYPE
                SYNTAX Gauge
                ACCESS read-only
                STATUS mandatory
                DESCRIPTION
		   "Number of Executions."
                ::= { oramodExpSqlEntry 3 }

        oramodExpSqlDISKREAD OBJECT-TYPE
                SYNTAX Gauge
                ACCESS read-only
                STATUS mandatory
                DESCRIPTION
		   "Number of Disk Reads."
                ::= { oramodExpSqlEntry 4 }

        oramodExpSqlPARSECNT OBJECT-TYPE
                SYNTAX Gauge
                ACCESS read-only
                STATUS mandatory
                DESCRIPTION
		   "Number of Parses. Parsing is the work done by the
		database to validate the SQL statement and generate the
		query plan used for execution. When the parse count is 
		close to that of executions for a given statement, you may
		be continually reparsing that statement. You can reduce 
		parsing by making sure that statements are reused as much 
		as possible in the shared pool. In general, a large number
		of hard parses indicates that more memory is needed for 
		the shared pool."
                ::= { oramodExpSqlEntry 5 }

        oramodExpSqlBUFFGETS OBJECT-TYPE
                SYNTAX Gauge
                ACCESS read-only
                STATUS mandatory
                DESCRIPTION
		   "Number of Buffer Gets."
                ::= { oramodExpSqlEntry 6 }

        oramodExpSqlSORTS OBJECT-TYPE
                SYNTAX Gauge
                ACCESS read-only
                STATUS mandatory
                DESCRIPTION
		   "Number of Sorts."
                ::= { oramodExpSqlEntry 7 }

       oramodExpSqlSQL OBJECT-TYPE
                SYNTAX DisplayString 
                ACCESS read-only
                STATUS mandatory
                DESCRIPTION
		   "Sql Statement truncated."
                ::= { oramodExpSqlEntry 8 }


-- Tablespace Information. This table is used to monitor fragmentation 
-- within each database tablespace. For maximum performance there must be 
-- enough large chunks of free block space to fill database requests. This
-- table describes the amount of space left in each tablespace after the 
-- next largest extent of any table in the tablespace is allocated. 
-- Returns a row for each tablespace containing tables.   

        oramodTblspTable OBJECT-TYPE
                SYNTAX SEQUENCE OF OramodTblspEntry
                ACCESS not-accessible
                STATUS mandatory
                DESCRIPTION
                  "List Fragmentation Information."
                ::= { oramodTblsp 1 }

        oramodTblspEntry OBJECT-TYPE
                SYNTAX OramodTblspEntry
                ACCESS not-accessible
                STATUS mandatory
                DESCRIPTION
                   "An entry from the dbafreespace table."
              INDEX { oramodTblspSIDINDX, oramodTblspTBLSPINDX}
                ::= {  oramodTblspTable 1 }

        OramodTblspEntry ::= SEQUENCE {
          	oramodTblspSIDINDX
                        INTEGER,
          	oramodTblspTBLSPINDX
                        INTEGER,
	        oramodTblspTBLSPNAME
                        DisplayString,
	        oramodTblspFILENAME
                        DisplayString,
                oramodTblspEXTENTS
                        Gauge,
                oramodTblspLRGEXTENT
                        Gauge,
                oramodTblspSMEXTENT
                        Gauge,
                oramodTblspINCREMENTBY
                        INTEGER,
                oramodTblspBYTESCOALSD
                        Gauge,
                oramodTblspBYTESFREE
                        Gauge
        }

        oramodTblspSIDINDX OBJECT-TYPE
                SYNTAX INTEGER (1..2147483647)
                ACCESS read-only
                STATUS mandatory
                DESCRIPTION
		   "Sid Index Number."
                ::= { oramodTblspEntry 1 }

        oramodTblspTBLSPINDX OBJECT-TYPE
                SYNTAX INTEGER (1..2147483647)
                ACCESS read-only
                STATUS mandatory
                DESCRIPTION
		   "Tablespace Index Number."
                ::= { oramodTblspEntry 2 }

        oramodTblspTBLSPNAME OBJECT-TYPE
                SYNTAX DisplayString
                ACCESS read-only
                STATUS mandatory
                DESCRIPTION
		   "Tablespace Name."
                ::= { oramodTblspEntry 3 }

        oramodTblspFILENAME OBJECT-TYPE
                SYNTAX DisplayString
                ACCESS read-only
                STATUS mandatory
                DESCRIPTION
		   "File Name."
                ::= { oramodTblspEntry 4 }

        oramodTblspEXTENTS OBJECT-TYPE
                SYNTAX Gauge
                ACCESS read-only
                STATUS mandatory
                DESCRIPTION
		   "The number of extents."
                ::= { oramodTblspEntry 5 }

        oramodTblspLRGEXTENT OBJECT-TYPE
                SYNTAX Gauge
                ACCESS read-only
                STATUS mandatory
                DESCRIPTION
		   "Size in bytes of the largest extent."
                ::= { oramodTblspEntry 6 }

        oramodTblspSMEXTENT OBJECT-TYPE
                SYNTAX Gauge
                ACCESS read-only
                STATUS mandatory
                DESCRIPTION
		   "Size in bytes of the smallest extent."
                ::= { oramodTblspEntry 7 }

        oramodTblspINCREMENTBY OBJECT-TYPE
                SYNTAX INTEGER
                ACCESS read-only
                STATUS mandatory
                DESCRIPTION
		   "Size in bytes of the next extent increment."
                ::= { oramodTblspEntry 8 }

        oramodTblspBYTESCOALSD OBJECT-TYPE
                SYNTAX Gauge
                ACCESS read-only
                STATUS mandatory
                DESCRIPTION
		   "The number of free bytes that were coalesed. If
		this number does not match bytesfree then the tablespace
		has some extents that can be coalesced."
                ::= { oramodTblspEntry 9 }

        oramodTblspBYTESFREE OBJECT-TYPE
                SYNTAX Gauge
                ACCESS read-only
                STATUS mandatory
                DESCRIPTION
		   "The total number of free bytes available." 
                ::= { oramodTblspEntry 10 }

-- Locks - A table of lock holders and requestors. Locks are used to protect
-- a data structure. It can be held continuously until a commit or rollback
-- takes place. This table can be used to check for lock contention. 


        oramodLockTable OBJECT-TYPE
                SYNTAX SEQUENCE OF OramodLockEntry
                ACCESS not-accessible
                STATUS mandatory
                DESCRIPTION
                  "Lock Holders and Requestors"
                ::= { oramodLock 1 }

        oramodLockEntry OBJECT-TYPE
                SYNTAX OramodLockEntry
                ACCESS not-accessible
                STATUS mandatory
                DESCRIPTION
                   "An entry from the lock and session tables."
                INDEX { oramodLockSIDINDX, oramodLockUSERINDX }
                ::= {  oramodLockTable 1 }

        OramodLockEntry ::= SEQUENCE {
                oramodLockSIDINDX
                        INTEGER,
                oramodLockUSERINDX
                        INTEGER,
                oramodLockUSERNAME
                        DisplayString,
                oramodLockOBJECT
                        DisplayString,
                oramodLockTYPE
                        DisplayString,
                oramodLockMODE
                        INTEGER,
                oramodLockCTIME
                        INTEGER,
                oramodLockBLOCK
                        INTEGER
        }

        oramodLockSIDINDX OBJECT-TYPE
                SYNTAX INTEGER
                ACCESS read-only
                STATUS mandatory
                DESCRIPTION
		   "Sid Index Number."
                ::= { oramodLockEntry 1 }

        oramodLockUSERINDX OBJECT-TYPE
                SYNTAX INTEGER
                ACCESS read-only
                STATUS mandatory
                DESCRIPTION
		   "User's Index Number."
                ::= { oramodLockEntry 2 }

        oramodLockUSERNAME OBJECT-TYPE
                SYNTAX DisplayString
                ACCESS read-only
                STATUS mandatory
                DESCRIPTION
		   "User Name holding the lock."
                ::= { oramodLockEntry 3 }

        oramodLockOBJECT OBJECT-TYPE
                SYNTAX DisplayString
                ACCESS read-only
                STATUS mandatory
                DESCRIPTION
		   "The name of the locked object."
                ::= { oramodLockEntry 4 }

        oramodLockTYPE OBJECT-TYPE
                SYNTAX DisplayString
                ACCESS read-only
                STATUS mandatory
                DESCRIPTION
		   "Object Type."
                ::= { oramodLockEntry 5 }

        oramodLockMODE OBJECT-TYPE
                SYNTAX INTEGER
                ACCESS read-only
                STATUS mandatory
                DESCRIPTION
		   "Lock Mode held (Null, Row share, Row exclusive, Share,
		Share row exclusive, Exclusive)."
                ::= { oramodLockEntry 6 }

        oramodLockCTIME OBJECT-TYPE
                SYNTAX INTEGER
                ACCESS read-only
                STATUS mandatory
                DESCRIPTION
		   "Time since current mode was granted."
                ::= { oramodLockEntry 7 }

        oramodLockBLOCK OBJECT-TYPE
                SYNTAX INTEGER
                ACCESS read-only
                STATUS mandatory
                DESCRIPTION
		   "The lock is blocking another lock."
                ::= { oramodLockEntry 8 }


--Latches - A table of latches held per instance. Latches are used to prevent
-- access to Oracle's internal memory structures while a process is accessing
-- them.  Too much time spent waiting for latches or increasing misses can  
-- indicate performance issues.

        oramodLatchTable OBJECT-TYPE
                SYNTAX SEQUENCE OF OramodLatchEntry
                ACCESS not-accessible
                STATUS mandatory
                DESCRIPTION
                  "Latch information."
                ::= { oramodLatch 1 }

        oramodLatchEntry OBJECT-TYPE
                SYNTAX OramodLatchEntry
                ACCESS not-accessible
                STATUS mandatory
                DESCRIPTION
                   "An entry from the latch table."
                INDEX { oramodLatchSIDINDX, oramodLatchLATCHINDX }
                ::= {  oramodLatchTable 1 }

        OramodLatchEntry ::= SEQUENCE {
                oramodLatchSIDINDX
                        INTEGER,
                oramodLatchLATCHINDX
                        INTEGER,
                oramodLatchLATCHNUM
                        INTEGER,
                oramodLatchLATCHNAME
                        DisplayString,
                oramodLatchGETS
                        Counter,
                oramodLatchMISSES
                        Counter,
                oramodLatchSLEEPS
                        Counter,
                oramodLatchIMDGETS
                        Counter,
                oramodLatchIMDMISSES
                        Counter,
                oramodLatchWAITSHOLDING
                        Counter,
                oramodLatchSPINGETS
                        Counter
        }

        oramodLatchSIDINDX OBJECT-TYPE
                SYNTAX INTEGER
                ACCESS read-only
                STATUS mandatory
                DESCRIPTION
		   "Sid Index Number."
                ::= { oramodLatchEntry 1 }

        oramodLatchLATCHINDX OBJECT-TYPE
                SYNTAX INTEGER
                ACCESS read-only
                STATUS mandatory
                DESCRIPTION
		   "Latch Index Number."
                ::= { oramodLatchEntry 2 }

        oramodLatchLATCHNUM OBJECT-TYPE
                SYNTAX INTEGER
                ACCESS read-only
                STATUS mandatory
                DESCRIPTION
		   "Latch Number."
                ::= { oramodLatchEntry 3 }

        oramodLatchLATCHNAME OBJECT-TYPE
                SYNTAX DisplayString
                ACCESS read-only
                STATUS mandatory
                DESCRIPTION
		   "Latch Name."
                ::= { oramodLatchEntry 4 }

        oramodLatchGETS OBJECT-TYPE
                SYNTAX Counter
                ACCESS read-only
                STATUS mandatory
                DESCRIPTION
		   "Latch Gets. Reflects the proportion of times requests
	 	for latches are satisfied without waiting. Should be high."
                ::= { oramodLatchEntry 5 }

        oramodLatchMISSES OBJECT-TYPE
                SYNTAX Counter
                ACCESS read-only
                STATUS mandatory
                DESCRIPTION
		   "Latch Misses."
                ::= { oramodLatchEntry 6 }

        oramodLatchSLEEPS OBJECT-TYPE
                SYNTAX Counter
                ACCESS read-only
                STATUS mandatory
                DESCRIPTION
		   "Latch Sleeps."
                ::= { oramodLatchEntry 7 }

        oramodLatchIMDGETS OBJECT-TYPE
                SYNTAX Counter
                ACCESS read-only
                STATUS mandatory
                DESCRIPTION
		   "Latch Immediate Gets."
                ::= { oramodLatchEntry 8 }

        oramodLatchIMDMISSES OBJECT-TYPE
                SYNTAX Counter
                ACCESS read-only
                STATUS mandatory
                DESCRIPTION
		   "Latch Immediate Misses."
                ::= { oramodLatchEntry 9 }

        oramodLatchWAITSHOLDING OBJECT-TYPE
                SYNTAX Counter
                ACCESS read-only
                STATUS mandatory
                DESCRIPTION
		   "Latch Immediate Misses. When a session cannot acquire
		a latch, it goes into active wait and repeatedly trys
		to acquire the latch impaitiently."
                ::= { oramodLatchEntry 10 }

        oramodLatchSPINGETS OBJECT-TYPE
                SYNTAX Counter
                ACCESS read-only
                STATUS mandatory
                DESCRIPTION
		   "Latch Spin Gets. Some latch types will lock into a 
		tight loop testing the latch and trying to get it. Spinning
		uses significant CPU resources. The number of spins depends
		on the spincount set it the init.ora file. Once the number
		of spincounts has been reached the prcess will back off 
		and sleep."
                ::= { oramodLatchEntry 11 }

-- Backup - A table of physical backup information.  

        oramodBackupTable OBJECT-TYPE
                SYNTAX SEQUENCE OF OramodBackupEntry
                ACCESS not-accessible
                STATUS mandatory
                DESCRIPTION
                  "Backup Information"
                ::= { oramodBackup 1 }

        oramodBackupEntry OBJECT-TYPE
                SYNTAX OramodBackupEntry
                ACCESS not-accessible
                STATUS mandatory
                DESCRIPTION
                   "An entry from the backup table."
                INDEX { oramodBackupSIDINDX, oramodBackupFILENUM }
                ::= {  oramodBackupTable 1 }

        OramodBackupEntry ::= SEQUENCE {
                oramodBackupSIDINDX
                        INTEGER,
                oramodBackupFILENUM
                        INTEGER,
                oramodBackupSTATUS
                        DisplayString,
                oramodBackupCHANGENUM
                        INTEGER,
                oramodBackupDATE
                        DisplayString
        }

        oramodBackupSIDINDX OBJECT-TYPE
                SYNTAX INTEGER
                ACCESS read-only
                STATUS mandatory
                DESCRIPTION
		   "Sid Index Number."
                ::= { oramodBackupEntry 1 }

        oramodBackupFILENUM OBJECT-TYPE
                SYNTAX INTEGER
                ACCESS read-only
                STATUS mandatory
                DESCRIPTION
		   "Backup File Index Number."
                ::= { oramodBackupEntry 2 }

        oramodBackupSTATUS OBJECT-TYPE
                SYNTAX DisplayString
                ACCESS read-only
                STATUS mandatory
                DESCRIPTION
		   "Status of the backup."
                ::= { oramodBackupEntry 3 }

        oramodBackupCHANGENUM OBJECT-TYPE
                SYNTAX INTEGER
                ACCESS read-only
                STATUS mandatory
                DESCRIPTION
		   "The change number of the backup file."
                ::= { oramodBackupEntry 4 }

        oramodBackupDATE OBJECT-TYPE
                SYNTAX DisplayString
                ACCESS read-only
                STATUS mandatory
                DESCRIPTION
		   "Date of the Backup."
                ::= { oramodBackupEntry 5 }


-- Archive - A table of archive information. 

        oramodArcDestTable OBJECT-TYPE
                SYNTAX SEQUENCE OF OramodArcDestEntry
                ACCESS not-accessible
                STATUS mandatory
                DESCRIPTION
                  "Archive Information."
                ::= { oramodArcDest 1 }

        oramodArcDestEntry OBJECT-TYPE
                SYNTAX OramodArcDestEntry
                ACCESS not-accessible
                STATUS mandatory
                DESCRIPTION
                   "An entry from the archive destination table."
                INDEX { oramodArcDestSIDINDX, oramodArcDestARCINDX  }
                ::= {  oramodArcDestTable 1 }

        OramodArcDestEntry ::= SEQUENCE {
                oramodArcDestSIDINDX
                        INTEGER,
                oramodArcDestARCINDX
                        INTEGER,
                oramodArcDestARCMODE
                        DisplayString,
                oramodArcDestSTATUS
                        DisplayString,
                oramodArcDestDEST
                        DisplayString
        }

        oramodArcDestSIDINDX OBJECT-TYPE
                SYNTAX INTEGER
                ACCESS read-only
                STATUS mandatory
                DESCRIPTION
		   "Sid Index Number."
                ::= { oramodArcDestEntry 1 }

        oramodArcDestARCINDX OBJECT-TYPE
                SYNTAX INTEGER
                ACCESS read-only
                STATUS mandatory
                DESCRIPTION
		   "Index of Archive log."
                ::= { oramodArcDestEntry 2 }

        oramodArcDestARCMODE OBJECT-TYPE
                SYNTAX DisplayString
                ACCESS read-only
                STATUS mandatory
                DESCRIPTION
		   "Mode of Archive log."
                ::= { oramodArcDestEntry 3 }

        oramodArcDestSTATUS OBJECT-TYPE
                SYNTAX DisplayString
                ACCESS read-only
                STATUS mandatory
                DESCRIPTION
		   "Status of Archive Log File."
                ::= { oramodArcDestEntry 4 }

        oramodArcDestDEST OBJECT-TYPE
                SYNTAX DisplayString
                ACCESS read-only
                STATUS mandatory
                DESCRIPTION
		   "Archive Log File Destination."
                ::= { oramodArcDestEntry 5 }

END
