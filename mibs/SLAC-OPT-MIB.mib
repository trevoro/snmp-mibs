-- Version 2.15.1.1, modified   2001-05-31 17:28:38-04

        SLAC-OPT-MIB DEFINITIONS ::= BEGIN

        IMPORTS
                mgmt, NetworkAddress, Counter, Gauge, enterprises
		    FROM RFC1155-SMI

                OBJECT-TYPE
                    FROM RFC-1212;

               -- Codex MIB Group definitions

                         codex OBJECT IDENTIFIER ::= { enterprises 449 }
            cdxProductSpecific OBJECT IDENTIFIER ::= { codex 2 }
                       cdx6500 OBJECT IDENTIFIER ::= { cdxProductSpecific 1 }

         cdx6500Configuration  OBJECT IDENTIFIER ::= { cdx6500 2 }
       cdx6500CfgProtocolGroup OBJECT IDENTIFIER ::= { cdx6500Configuration 1 }
        cdx6500CfgGeneralGroup OBJECT IDENTIFIER ::= { cdx6500Configuration 2 }
    cdx6500PCTSLACStationGroup OBJECT IDENTIFIER ::= { cdx6500CfgProtocolGroup 10 }

             cdx6500Statistics OBJECT IDENTIFIER ::= { cdx6500 3 }
      cdx6500StatProtocolGroup OBJECT IDENTIFIER ::= { cdx6500Statistics 1 }
    cdx6500PSTSLACStationGroup OBJECT IDENTIFIER ::= { cdx6500StatProtocolGroup 7 }

               cdx6500Controls OBJECT IDENTIFIER ::= { cdx6500 4 }
        cdx6500ContSLACStation OBJECT IDENTIFIER ::= { cdx6500Controls 20 }

        -- Textual conventions

        Counter16  ::= INTEGER (0..65535)
	
        DisplayString ::= OCTET STRING

	-- TEXTUAL-CONVENTION
	--  Status
	--    mandatory
	--  Descr
	--    Represents the LEN Type list.

        -- This data type is used to model textual information taken
        -- from the NVT ASCII character set. By convention, objects
        -- with this syntax are declared as having SIZE (0..255)

        -- The SLAC Station Configuration Table
        -- This table contains Configuration paramaters 
        -- for the SLAC Station table.
	                      
        cdx6500PCTSLACStationTable OBJECT-TYPE
            SYNTAX SEQUENCE OF Cdx6500PCTSLACStationEntry
            ACCESS not-accessible
            STATUS mandatory
            DESCRIPTION
                "All of the configuration parameters relevant
                 to the SLAC Station table."
        ::= { cdx6500PCTSLACStationGroup 1 }

    	cdx6500PCTSLACStationEntry OBJECT-TYPE
            SYNTAX Cdx6500PCTSLACStationEntry
            ACCESS not-accessible
            STATUS mandatory
            DESCRIPTION
                "A row of SLAC station configuration parameters."
            INDEX { cdx6500slacsStationType, cdx6500slacsStationNum }
        ::= { cdx6500PCTSLACStationTable 1 }

        Cdx6500PCTSLACStationEntry ::=
            SEQUENCE {
		cdx6500slacsStationNum
		    INTEGER,
	 	cdx6500slacsStationType
		    INTEGER,
                cdx6500slacsFRPortNum
                    INTEGER,
                cdx6500slacsFRStationNum
                    INTEGER,
                cdx6500slacsExternAddr
                    DisplayString,
                cdx6500slacsInternAddr
                    DisplayString,
                cdx6500slacs1490encap
                    INTEGER,
                cdx6500slacsbnimacAddr
                    DisplayString,
                cdx6500slacsbanmacAddr
                    DisplayString,
                cdx6500slacsFrdlciRing
                    DisplayString,
                cdx6500slacsInterSap
                    DisplayString,
                cdx6500slacsExternSap
                    DisplayString,
                cdx6500slacsExternPU
                    INTEGER,
                cdx6500slacsLinkType
                    INTEGER,
                cdx6500slacsEthernetType
                    INTEGER,
                cdx6500slacsInitiateTest
                    INTEGER,
                cdx6500slacsRemoteCPName
                    DisplayString,
                cdx6500slacsLocalCPName
                    DisplayString,
                cdx6500slacsNumberDisplays
                    INTEGER,
                cdx6500slacsDownstrLU0
                    DisplayString,
                cdx6500slacsDownstrDis0
                    DisplayString,
                cdx6500slacsDownstrLU1
                    DisplayString,
                cdx6500slacsDownstrDis1
                    DisplayString,
                cdx6500slacsDownstrLU2
                    DisplayString,
                cdx6500slacsDownstrDis2
                    DisplayString,
                cdx6500slacsDownstrLU3
                    DisplayString,
                cdx6500slacsDownstrDis3
                    DisplayString,
                cdx6500slacsDownstrLU4
                    DisplayString,
                cdx6500slacsDownstrDis4
                    DisplayString,
                cdx6500slacsDownstrLU5
                    DisplayString,
                cdx6500slacsDownstrDis5
                    DisplayString,
                cdx6500slacsDownstrLU6
                    DisplayString,
                cdx6500slacsDownstrDis6
                    DisplayString,
                cdx6500slacsDownstrLU7
                    DisplayString,
                cdx6500slacsDownstrDis7
                    DisplayString,
                cdx6500slacsDownstrLU8
                    DisplayString,
                cdx6500slacsDownstrDis8
                    DisplayString,
                cdx6500slacsDownstrLU9
                    DisplayString,
                cdx6500slacsDownstrDis9
                    DisplayString,
                cdx6500slacsDownstrLU10
                    DisplayString,
                cdx6500slacsDownstrDis10
                    DisplayString,
                cdx6500slacsDownstrLU11
                    DisplayString,
                cdx6500slacsDownstrDis11
                    DisplayString,
                cdx6500slacsDownstrLU12
                    DisplayString,
                cdx6500slacsDownstrDis12
                    DisplayString,
                cdx6500slacsDownstrLU13
                    DisplayString,
                cdx6500slacsDownstrDis13
                    DisplayString,
                cdx6500slacsDownstrLU14
                    DisplayString,
                cdx6500slacsDownstrDis14
                    DisplayString,
                cdx6500slacsDownstrLU15
                    DisplayString,
                cdx6500slacsDownstrDis15
                    DisplayString,
                cdx6500slacsLLCProfile
                    DisplayString,
                cdx6500slacsQLLCStationAddr
                    DisplayString,
	        cdx6500slacsQLLCOptions
        	    DisplayString,
                cdx6500slacsXIDValue
                    DisplayString,
                cdx6500slacsX25NetworkPass
                    DisplayString,
                cdx6500slacsCallingAddr
                    DisplayString,
                cdx6500slacsProtocolID
                    DisplayString,
                cdx6500slacsAutocallMnu
                    DisplayString,
                cdx6500slacsCallTimer
                    INTEGER,
                cdx6500slacsMaximumCall
                    INTEGER,
                cdx6500slacsHuntgrpType
                    INTEGER,
                cdx6500slacsHuntgrpNumber
                    INTEGER,
                cdx6500slacsCUGMember
                    INTEGER,
                cdx6500slacsBillingRec
                    INTEGER,
                cdx6500slacsTrafficPrio
                    INTEGER,
                cdx6500slacsLLCOptions
                    DisplayString,
                cdx6500slacsProtectionLevel
                    INTEGER,
                cdx6500slacsReconnectTime
                    INTEGER,
                cdx6500slacsReconnectTries
                    INTEGER,
                cdx6500slacsIdleTimer
                    INTEGER,
                cdx6500slacsVerConnTimer
                    INTEGER,
                cdx6500slacsUnsuspendWait
                    INTEGER
                }

	cdx6500slacsStationNum OBJECT-TYPE
	    SYNTAX INTEGER (1..250)
	    ACCESS read-only
	    STATUS mandatory
	    DESCRIPTION
		"Refers to the station number for this type."
	::= { cdx6500PCTSLACStationEntry 1 }                        

	cdx6500slacsStationType OBJECT-TYPE
	    SYNTAX INTEGER {
			token-ring    (0),
			frame-relay   (1),
			ethernet      (2),
			ethernet-2    (3),
			token-ring-2  (4)}
            ACCESS read-only
            STATUS mandatory
            DESCRIPTION
                "Refers to the station type."
        ::= { cdx6500PCTSLACStationEntry 2 }

        cdx6500slacsFRPortNum OBJECT-TYPE
            SYNTAX INTEGER (1..54)
            ACCESS read-only
            STATUS mandatory
            DESCRIPTION
                "Refers to the physical Frame Relay port number."
        ::= { cdx6500PCTSLACStationEntry 3 }
                        
        cdx6500slacsFRStationNum OBJECT-TYPE
            SYNTAX INTEGER (1..32)
            ACCESS read-only
            STATUS mandatory
            DESCRIPTION
                "Refers to the Frame Relay Station Number"
        ::= { cdx6500PCTSLACStationEntry 4 }
                        
        cdx6500slacsExternAddr OBJECT-TYPE
            SYNTAX DisplayString (SIZE(17))
            ACCESS read-only
            STATUS mandatory
            DESCRIPTION
                "The MAC address of the External LAN device associated with this station."
        ::= { cdx6500PCTSLACStationEntry 5 }
                        
	cdx6500slacsInternAddr OBJECT-TYPE
            SYNTAX DisplayString (SIZE(17))
            ACCESS read-only
            STATUS mandatory
            DESCRIPTION
                "The station address on the multidrop line."
        ::= { cdx6500PCTSLACStationEntry 6 }

        cdx6500slacs1490encap OBJECT-TYPE
            SYNTAX INTEGER {
                  	  llc       (1),
                          ban       (2),
			  na	    (100)}
            ACCESS read-only
            STATUS mandatory
            DESCRIPTION
                "Frame level window size must be set to the same value in
                 devices at each end of the link.
		 NA = Not applicable"
        ::= { cdx6500PCTSLACStationEntry 7 }
                        

	cdx6500slacsbnimacAddr OBJECT-TYPE
            SYNTAX DisplayString (SIZE(17))
            ACCESS read-only
            STATUS mandatory
            DESCRIPTION
                "The Destination MAC address inserted into the BAN 
		 encapsulated frame."
        ::= { cdx6500PCTSLACStationEntry 8 }

        cdx6500slacsbanmacAddr OBJECT-TYPE
            SYNTAX DisplayString (SIZE(17))
            ACCESS read-only
            STATUS mandatory
            DESCRIPTION
                "The source MAC address inserted into the BAN 
		 encapsulated frame."
        ::= { cdx6500PCTSLACStationEntry 9 }

        cdx6500slacsFrdlciRing OBJECT-TYPE
            SYNTAX DisplayString (SIZE(3))
            ACCESS read-only
            STATUS mandatory
            DESCRIPTION
                "The virtual ring number that is shared with the 
		 other PUs that are associated with the same DLCI.
		 If 0 then ring number will not be inserted into RIF field."
        ::= { cdx6500PCTSLACStationEntry 10 }
         
        cdx6500slacsInterSap OBJECT-TYPE
            SYNTAX DisplayString (SIZE(2))
            ACCESS read-only
            STATUS mandatory
            DESCRIPTION
                "The local SAP of this station."
        ::= { cdx6500PCTSLACStationEntry 11 }

        cdx6500slacsExternSap OBJECT-TYPE
            SYNTAX DisplayString (SIZE(2))
            ACCESS read-only
            STATUS mandatory
            DESCRIPTION
                "The SAP of the device associated with this station."
        ::= { cdx6500PCTSLACStationEntry 12 }

        cdx6500slacsExternPU OBJECT-TYPE
            SYNTAX INTEGER {type-2 (1),
			    type-21 (2),
			    type-4 (3)}	 
            ACCESS read-only
            STATUS mandatory
            DESCRIPTION
                "The PU type of the device associated with this station."
        ::= { cdx6500PCTSLACStationEntry 13 }

        cdx6500slacsLinkType OBJECT-TYPE
            SYNTAX INTEGER {slac (1),
			    len  (2),
			    na   (100)}

            ACCESS read-only
            STATUS mandatory
            DESCRIPTION
                "The link type of this station."
        ::= { cdx6500PCTSLACStationEntry 14 }

        cdx6500slacsEthernetType OBJECT-TYPE
            SYNTAX INTEGER {ethernet (1),  
                            versionii (2),
		  	    na        (100)}
            ACCESS read-only
            STATUS mandatory
            DESCRIPTION
                "The type of ethernet frame (802.3 or Ethernet Version 2)
		 that is trasmitted for this station."
        ::= { cdx6500PCTSLACStationEntry 15 }

        cdx6500slacsInitiateTest OBJECT-TYPE
            SYNTAX INTEGER {	off (1),
			    	on  (2),
				wait (3),
				xid-wait (4),
				na       (100)}
            ACCESS read-only
            STATUS mandatory
            DESCRIPTION
                "Controls how TEST poll frames are locally initiated."
        ::= { cdx6500PCTSLACStationEntry 16 }

        cdx6500slacsRemoteCPName OBJECT-TYPE
            SYNTAX DisplayString (SIZE(8))
            ACCESS read-only
            STATUS mandatory
            DESCRIPTION
                "The control point name for the remote AS/400 that this station is
                 attaching to."
        ::= { cdx6500PCTSLACStationEntry 17 }

        cdx6500slacsLocalCPName OBJECT-TYPE
            SYNTAX DisplayString (SIZE(8))
            ACCESS read-only
            STATUS mandatory
            DESCRIPTION
                "The control point name associated with this station."
        ::= { cdx6500PCTSLACStationEntry 18 }

        cdx6500slacsNumberDisplays OBJECT-TYPE
            SYNTAX INTEGER (SIZE(0..16))
            ACCESS read-only
            STATUS mandatory
            DESCRIPTION
                "The number of Displays/Printers attached to the downstream controller."
        ::= { cdx6500PCTSLACStationEntry 19 }

        cdx6500slacsDownstrLU0 OBJECT-TYPE
            SYNTAX DisplayString (SIZE(2))
            ACCESS read-only
            STATUS mandatory
            DESCRIPTION
                "LU ID of the display/printer attached to the downstream controller."
        ::= { cdx6500PCTSLACStationEntry 20 }

        cdx6500slacsDownstrDis0 OBJECT-TYPE
            SYNTAX DisplayString (SIZE(8))
            ACCESS read-only
            STATUS mandatory
            DESCRIPTION
                "Workstation Type of the downstream display/printer."
        ::= { cdx6500PCTSLACStationEntry 21 }

        cdx6500slacsDownstrLU1 OBJECT-TYPE
            SYNTAX DisplayString (SIZE(2))
            ACCESS read-only
            STATUS mandatory
            DESCRIPTION
                "LU ID of the display/printer attached to the downstream controller."
        ::= { cdx6500PCTSLACStationEntry 22 }

        cdx6500slacsDownstrDis1 OBJECT-TYPE
            SYNTAX DisplayString (SIZE(8))
            ACCESS read-only
            STATUS mandatory
            DESCRIPTION
                "Workstation Type of the downstream display/printer."
        ::= { cdx6500PCTSLACStationEntry 23 }

        cdx6500slacsDownstrLU2 OBJECT-TYPE
            SYNTAX DisplayString (SIZE(2))
            ACCESS read-only
            STATUS mandatory
            DESCRIPTION
                "LU ID of the display/printer attached to the downstream controller."
        ::= { cdx6500PCTSLACStationEntry 24 }

        cdx6500slacsDownstrDis2 OBJECT-TYPE
            SYNTAX DisplayString (SIZE(8))
            ACCESS read-only
            STATUS mandatory
            DESCRIPTION
                "Workstation Type of the downstream display/printer."
        ::= { cdx6500PCTSLACStationEntry 25 }

        cdx6500slacsDownstrLU3 OBJECT-TYPE
            SYNTAX DisplayString (SIZE(2))
            ACCESS read-only
            STATUS mandatory
            DESCRIPTION
                "LU ID of the display/printer attached to the downstream controller."
        ::= { cdx6500PCTSLACStationEntry 26 }

        cdx6500slacsDownstrDis3 OBJECT-TYPE
            SYNTAX DisplayString (SIZE(8))
            ACCESS read-only
            STATUS mandatory
            DESCRIPTION
                "Workstation Type of the downstream display/printer."
        ::= { cdx6500PCTSLACStationEntry 27 }

        cdx6500slacsDownstrLU4 OBJECT-TYPE
            SYNTAX DisplayString (SIZE(2))
            ACCESS read-only
            STATUS mandatory
            DESCRIPTION
                "LU ID of the display/printer attached to the downstream controller."
        ::= { cdx6500PCTSLACStationEntry 28 }

        cdx6500slacsDownstrDis4 OBJECT-TYPE
            SYNTAX DisplayString (SIZE(8))
            ACCESS read-only
            STATUS mandatory
            DESCRIPTION
                "Workstation Type of the downstream display/printer."
        ::= { cdx6500PCTSLACStationEntry 29 }

        cdx6500slacsDownstrLU5 OBJECT-TYPE
            SYNTAX DisplayString (SIZE(2))
            ACCESS read-only
            STATUS mandatory
            DESCRIPTION
                "LU ID of the display/printer attached to the downstream controller."
        ::= { cdx6500PCTSLACStationEntry 30 }

        cdx6500slacsDownstrDis5 OBJECT-TYPE
            SYNTAX DisplayString (SIZE(8))
            ACCESS read-only
            STATUS mandatory
            DESCRIPTION
                "Workstation Type of the downstream display/printer."
        ::= { cdx6500PCTSLACStationEntry 31 }

        cdx6500slacsDownstrLU6 OBJECT-TYPE
            SYNTAX DisplayString (SIZE(2))
            ACCESS read-only
            STATUS mandatory
            DESCRIPTION
                "LU ID of the display/printer attached to the downstream controller."
        ::= { cdx6500PCTSLACStationEntry 32 }

        cdx6500slacsDownstrDis6 OBJECT-TYPE
            SYNTAX DisplayString (SIZE(8))
            ACCESS read-only
            STATUS mandatory
            DESCRIPTION
                "Workstation Type of the downstream display/printer."
        ::= { cdx6500PCTSLACStationEntry 33 }

        cdx6500slacsDownstrLU7 OBJECT-TYPE
            SYNTAX DisplayString (SIZE(2))
            ACCESS read-only
            STATUS mandatory
            DESCRIPTION
                "LU ID of the display/printer attached to the downstream controller."
        ::= { cdx6500PCTSLACStationEntry 34 }

        cdx6500slacsDownstrDis7 OBJECT-TYPE
            SYNTAX DisplayString (SIZE(8))
            ACCESS read-only
            STATUS mandatory
            DESCRIPTION
                "Workstation Type of the downstream display/printer."
        ::= { cdx6500PCTSLACStationEntry 35 }

        cdx6500slacsDownstrLU8 OBJECT-TYPE
            SYNTAX DisplayString (SIZE(2))
            ACCESS read-only
            STATUS mandatory
            DESCRIPTION
                "LU ID of the display/printer attached to the downstream controller."
        ::= { cdx6500PCTSLACStationEntry 36 }

        cdx6500slacsDownstrDis8 OBJECT-TYPE
            SYNTAX DisplayString (SIZE(8))
            ACCESS read-only
            STATUS mandatory
            DESCRIPTION
                "Workstation Type of the downstream display/printer."
        ::= { cdx6500PCTSLACStationEntry 37 }

        cdx6500slacsDownstrLU9 OBJECT-TYPE
            SYNTAX DisplayString (SIZE(2))
            ACCESS read-only
            STATUS mandatory
            DESCRIPTION
                "LU ID of the display/printer attached to the downstream controller."
        ::= { cdx6500PCTSLACStationEntry 38 }

        cdx6500slacsDownstrDis9 OBJECT-TYPE
            SYNTAX DisplayString (SIZE(8))
            ACCESS read-only
            STATUS mandatory
            DESCRIPTION
                "Workstation Type of the downstream display/printer."
        ::= { cdx6500PCTSLACStationEntry 39 }

        cdx6500slacsDownstrLU10 OBJECT-TYPE
            SYNTAX DisplayString (SIZE(2))
            ACCESS read-only
            STATUS mandatory
            DESCRIPTION
                "LU ID of the display/printer attached to the downstream controller."
        ::= { cdx6500PCTSLACStationEntry 40 }

        cdx6500slacsDownstrDis10 OBJECT-TYPE
            SYNTAX DisplayString (SIZE(8))
            ACCESS read-only
            STATUS mandatory
            DESCRIPTION
                "Workstation Type of the downstream display/printer."
        ::= { cdx6500PCTSLACStationEntry 41 }

        cdx6500slacsDownstrLU11 OBJECT-TYPE
            SYNTAX DisplayString (SIZE(2))
            ACCESS read-only
            STATUS mandatory
            DESCRIPTION
                "LU ID of the display/printer attached to the downstream controller."
        ::= { cdx6500PCTSLACStationEntry 42 }

        cdx6500slacsDownstrDis11 OBJECT-TYPE
            SYNTAX DisplayString (SIZE(8))
            ACCESS read-only
            STATUS mandatory
            DESCRIPTION
                "Workstation Type of the downstream display/printer."
        ::= { cdx6500PCTSLACStationEntry 43 }

        cdx6500slacsDownstrLU12 OBJECT-TYPE
            SYNTAX DisplayString (SIZE(2))
            ACCESS read-only
            STATUS mandatory
            DESCRIPTION
                "LU ID of the display/printer attached to the downstream controller."
        ::= { cdx6500PCTSLACStationEntry 44 }

        cdx6500slacsDownstrDis12 OBJECT-TYPE
            SYNTAX DisplayString (SIZE(8))
            ACCESS read-only
            STATUS mandatory
            DESCRIPTION
                "Workstation Type of the downstream display/printer."
        ::= { cdx6500PCTSLACStationEntry 45 }

        cdx6500slacsDownstrLU13 OBJECT-TYPE
            SYNTAX DisplayString (SIZE(2))
            ACCESS read-only
            STATUS mandatory
            DESCRIPTION
                "LU ID of the display/printer attached to the downstream controller."
        ::= { cdx6500PCTSLACStationEntry 46 }

        cdx6500slacsDownstrDis13 OBJECT-TYPE
            SYNTAX DisplayString (SIZE(8))
            ACCESS read-only
            STATUS mandatory
            DESCRIPTION
                "Workstation Type of the downstream display/printer."
        ::= { cdx6500PCTSLACStationEntry 47 }

        cdx6500slacsDownstrLU14 OBJECT-TYPE
            SYNTAX DisplayString (SIZE(2))
            ACCESS read-only
            STATUS mandatory
            DESCRIPTION
                "LU ID of the display/printer attached to the downstream controller."
        ::= { cdx6500PCTSLACStationEntry 48 }

        cdx6500slacsDownstrDis14 OBJECT-TYPE
            SYNTAX DisplayString (SIZE(8))
            ACCESS read-only
            STATUS mandatory
            DESCRIPTION
                "Workstation Type of the downstream display/printer."
        ::= { cdx6500PCTSLACStationEntry 49 }

        cdx6500slacsDownstrLU15 OBJECT-TYPE
            SYNTAX DisplayString (SIZE(2))
            ACCESS read-only
            STATUS mandatory
            DESCRIPTION
                "LU ID of the display/printer attached to the downstream controller."
        ::= { cdx6500PCTSLACStationEntry 50 }

        cdx6500slacsDownstrDis15 OBJECT-TYPE
            SYNTAX DisplayString (SIZE(8))
            ACCESS read-only
            STATUS mandatory
            DESCRIPTION
                "Workstation Type of the downstream display/printer."
        ::= { cdx6500PCTSLACStationEntry 51}

        cdx6500slacsLLCProfile OBJECT-TYPE
	    SYNTAX DisplayString (SIZE(8))
            ACCESS read-only
            STATUS mandatory
            DESCRIPTION
                "The name of this profile entry."
        ::= { cdx6500PCTSLACStationEntry 52 }

        cdx6500slacsQLLCStationAddr OBJECT-TYPE
            SYNTAX DisplayString (SIZE(2))
            ACCESS read-only
            STATUS mandatory
            DESCRIPTION
                "The station address used for QLLC control procedures."
        ::= { cdx6500PCTSLACStationEntry 53 }

        cdx6500slacsQLLCOptions OBJECT-TYPE
            SYNTAX DisplayString (SIZE(12))
            ACCESS read-only
            STATUS mandatory
            DESCRIPTION
                "The QLLC options enabled on this station."
        ::= { cdx6500PCTSLACStationEntry 54 }

        cdx6500slacsXIDValue OBJECT-TYPE
            SYNTAX DisplayString (SIZE(0..14))
            ACCESS read-only
            STATUS mandatory
            DESCRIPTION
                "This is the identification sent by an HPAD station when External PU."
        ::= { cdx6500PCTSLACStationEntry 55 }

        cdx6500slacsX25NetworkPass OBJECT-TYPE
            SYNTAX DisplayString (SIZE(0..24))
            ACCESS read-only
            STATUS mandatory
            DESCRIPTION
                "The X.25 Network Password, which is inserted in the 
	         CUD of the Call Request packet."
        ::= { cdx6500PCTSLACStationEntry 56 }

        cdx6500slacsCallingAddr OBJECT-TYPE
            SYNTAX DisplayString (SIZE(12))
            ACCESS read-only
            STATUS mandatory
            DESCRIPTION
                "This is the full Calling Address inserted into the Call Request
                 when autocalling is enabled."
        ::= { cdx6500PCTSLACStationEntry 57 }

	cdx6500slacsProtocolID OBJECT-TYPE
            SYNTAX DisplayString (SIZE(0..8))
            ACCESS read-only
            STATUS mandatory
            DESCRIPTION
                "The protocol identifier is the first four bytes of
                 the call user data. If not configured the PAD will use
                 C3000000 as the protocol ID in the call."
        ::= { cdx6500PCTSLACStationEntry 58 }

        cdx6500slacsAutocallMnu OBJECT-TYPE
            SYNTAX DisplayString (SIZE(0..255))
            ACCESS read-only
            STATUS mandatory
            DESCRIPTION
                "This mnemonic references the remote address which will 
                 be called when polling activity is detected on the slac line."
        ::= { cdx6500PCTSLACStationEntry 59 }
                                
        cdx6500slacsCallTimer OBJECT-TYPE
            SYNTAX INTEGER (0..300)
            ACCESS read-only
            STATUS mandatory
            DESCRIPTION
                "This specifies the time before the next call is made.  If 0 is
                 entered, the time to the next call is handled internally.
                 The time is in seconds."
        ::= { cdx6500PCTSLACStationEntry 60 }

        cdx6500slacsMaximumCall OBJECT-TYPE
	    SYNTAX INTEGER (0..255)
            ACCESS read-only
            STATUS mandatory
            DESCRIPTION
                "This specifies the time before the next call is made.  If 0 is
                 entered, the time to the next call is handled internally.
                 The time is in seconds."
        ::= { cdx6500PCTSLACStationEntry 61 }

        cdx6500slacsHuntgrpType OBJECT-TYPE
	    SYNTAX INTEGER {none (1),
			    sec  (2),
			    pri  (3),
		            na   (100)}
            ACCESS read-only
            STATUS mandatory
            DESCRIPTION
                "This indicates if the station is a hunt group station or not."
        ::= { cdx6500PCTSLACStationEntry 62 }

        cdx6500slacsHuntgrpNumber OBJECT-TYPE
            SYNTAX INTEGER (1..3)
            ACCESS read-only
            STATUS mandatory
            DESCRIPTION
                "Specifies this station's HuntGroup number within the selected
                 HuntGroup type."
        ::= { cdx6500PCTSLACStationEntry 63 }

	cdx6500slacsCUGMember OBJECT-TYPE
            SYNTAX DisplayString (SIZE(23))
            ACCESS read-only
            STATUS mandatory
            DESCRIPTION
                "The station may be a member of up to 8 different Closed User
                 Groups (CUGs). Each CUG membership must be a two digit number
                 (except --)and separated by a comma.
                 (e.g. 12,34,56,09,02,03).
                 --    - No CUG Membership
                 00-99 - CUG Membership"
        ::= { cdx6500PCTSLACStationEntry 64 }
                        
        cdx6500slacsBillingRec OBJECT-TYPE
            SYNTAX INTEGER {
                    off       (1),
                    on        (2),
                    newvalOff (50)
                    }
            ACCESS read-only
            STATUS mandatory
            DESCRIPTION
                "This controls whether billing (accounting) records will
                 be created for calls on this port.
                 off  -  Billing (accounting) records will not be created for
                         calls on this port.
                 on   -  Billing (accounting) records will be created for
                         calls on this port.
                 newvalOff - same functionality as 'off', new enumeration
                         added for RFC1155 compatibility."
        ::= { cdx6500PCTSLACStationEntry 65 }

        cdx6500slacsTrafficPrio OBJECT-TYPE
            SYNTAX INTEGER {
                    lowPriority       (1),
                    medPriority       (2),
                    hiPriority        (3),
                    xpPriority        (4),
                    newvalLowPriority (51)
                    }
            ACCESS read-only
            STATUS optional
            DESCRIPTION
                "This is the traffic priority of the SLAC station; low,
                 medium, high, or expedite.
                 newvalLowPriority : same functionality as 'lowPriority',
                 new enumeration added for RFC1155 compatibility."
        ::= { cdx6500PCTSLACStationEntry 66 }

        cdx6500slacsLLCOptions OBJECT-TYPE
            SYNTAX DisplayString (SIZE(23))
            ACCESS read-only
            STATUS mandatory
            DESCRIPTION
                "The LLC options enabled on this station."
        ::= { cdx6500PCTSLACStationEntry 67 }

        cdx6500slacsProtectionLevel OBJECT-TYPE
            SYNTAX INTEGER {
                    none       (1),
                    cp-only    (2),
                    full-dcp   (3),
                    newvalnone (51)
                    }
            ACCESS read-only
            STATUS mandatory
            DESCRIPTION
                "This specifies the level of data or connection protection 
                 which will be applied to calls to or from this port.  
                 The actual level for a call will be negotiated to the lesser 
                 of this level and the level configured for the other end of 
                 the call.
                 none       - No protection.
                 cpOnly     - Connection protection only.
                 fullDcp    - Full data and connection protection.
                 newvalNone - same functionality as 'none', new enumeration
                              added for RFC1155 compatibility."
        ::= { cdx6500PCTSLACStationEntry 68 }
                        
        cdx6500slacsReconnectTime OBJECT-TYPE
            SYNTAX INTEGER (1..128)
            ACCESS read-only
            STATUS mandatory
            DESCRIPTION
                "This specifies the number of seconds that DCP on the 
                 originating side will wait between reconnection attempts."
        ::= { cdx6500PCTSLACStationEntry 69 }
                        
        cdx6500slacsReconnectTries OBJECT-TYPE
            SYNTAX INTEGER (0..127)
            ACCESS read-only
            STATUS mandatory
            DESCRIPTION
                "This specifies the number of times that DCP on the originating
                 side will attempt to reconnect before clearing the call.  If 0
                 is entered, it will not attempt to reconnect."
        ::= { cdx6500PCTSLACStationEntry 70 }

        cdx6500slacsIdleTimer OBJECT-TYPE
            SYNTAX INTEGER (0..65534)
            ACCESS read-only
            STATUS mandatory
            DESCRIPTION
                "The Link Idle Timer is used by the SNA Dial on Demand feature
                 for determining how long the station should wait for a data
                 frame before bringing the X.25 call down. If a 0 is entered,
                 the call will never be brought down. The time is in seconds."
        ::= { cdx6500PCTSLACStationEntry 71 }

        cdx6500slacsVerConnTimer OBJECT-TYPE
            SYNTAX INTEGER (0..65534)
            ACCESS read-only
            STATUS mandatory
            DESCRIPTION
                "The Verify Connection Timer is used by the SNA Dial on
                 Demand feature for periodically verifying that the connection
                 to the remote station is still active, after the link has been
                 suspended. The timer specifies how long the the station waits
                 before verifying the connection. If a 0 is entered, the
                 connection will never be verified.  The time is in seconds."
        ::= { cdx6500PCTSLACStationEntry 72 }


        cdx6500slacsUnsuspendWait OBJECT-TYPE
            SYNTAX INTEGER (0..65534)
            ACCESS read-only
            STATUS mandatory
            DESCRIPTION
                "The Unsuspend Wait Timer is used by the SNA Dial on Demand
                 feature for determining how long the station will wait in
                 LINK-UNSUSPENDING state after receiving a call request before
                 bringing the station down. If a 0 is entered, the station
                 waits in LINK-UNSUSPENDED state forever.
                 Time is in seconds."
        ::= { cdx6500PCTSLACStationEntry 73 }

	-- The SLAC Profile Table
	-- This table contains Profile Configuration praramaters
	-- for the SLAC Profile table.

	cdx6500CfgSLACProfileTable OBJECT-TYPE
	    SYNTAX SEQUENCE OF Cdx6500CfgSLACProfileEntry
	    ACCESS not-accessible
	    STATUS mandatory
	    DESCRIPTION
		"All of the configuration parameters relevant
		to the SLAC Profile table."
	::= { cdx6500CfgGeneralGroup 28 }

	cdx6500CfgSLACProfileEntry OBJECT-TYPE
	    SYNTAX Cdx6500CfgSLACProfileEntry
            ACCESS not-accessible
            STATUS mandatory
            DESCRIPTION
                "A row of SLAC Profile configuration parameters."
            INDEX { cdx6500SLACprofProfileNum }
        ::= { cdx6500CfgSLACProfileTable 1 }

	Cdx6500CfgSLACProfileEntry ::=
	    SEQUENCE {
		cdx6500SLACprofProfileNum
		    INTEGER,
		cdx6500SLACprofProfileName
		    DisplayString,
	        cdx6500SLACprofT1Timer
		    INTEGER,
		cdx6500SLACprofT2AckTimer
		    INTEGER,
		cdx6500SLACprofTiTimer
		    INTEGER,
		cdx6500SLACprofN2Retry
		    INTEGER,
		cdx6500SLACprofN3Ack
		    INTEGER,
		cdx6500SLACprofTxwindow
		    INTEGER,
		cdx6500SLACprofTAStartup
		    INTEGER,
		cdx6500SLACprofRingNumber
		    DisplayString,
		cdx6500SLACprofBridgeID
		    INTEGER
		}
	
	cdx6500SLACprofProfileNum OBJECT-TYPE
	    SYNTAX INTEGER (1..8)
	    ACCESS read-only
            STATUS mandatory
            DESCRIPTION
                "Refers to the profile number."
        ::= { cdx6500CfgSLACProfileEntry 1 }

	cdx6500SLACprofProfileName OBJECT-TYPE
	    SYNTAX DisplayString (SIZE(8))
	    ACCESS read-only
	    STATUS mandatory
	    DESCRIPTION
		"The name of this profile entry, referenced by LLC-SDLC Conversion 
		stations for their LLC operating parameters."
        ::= { cdx6500CfgSLACProfileEntry 2 }

	cdx6500SLACprofT1Timer OBJECT-TYPE
	    SYNTAX INTEGER (1..25)
            ACCESS read-only
            STATUS mandatory
	    DESCRIPTION
		"This Ack Timer is used by a station to detect a failure of the 
		remote station to acknowledge an outstanding I frame or supervisory 
		frame with poll bit set to 1. Time is in seconds."
        ::= { cdx6500CfgSLACProfileEntry 3 }

	cdx6500SLACprofT2AckTimer OBJECT-TYPE
            SYNTAX INTEGER (1..255)
            ACCESS read-only
            STATUS mandatory
	    DESCRIPTION
		"The Receive Ack Timer is used by a station to determine how long 
		it will withhold acknowledgment of a frame(s) from the remote 
		station that require acknowledgment. This is a method of reducing the 
		amount of acknowledgments generated by a link station.  When this timer
		expires, the link station should immediately send an acknowledgment 
		for all received frames not yet acknowledged. Time is in tenths of seconds."
        ::= { cdx6500CfgSLACProfileEntry 4 }

	cdx6500SLACprofTiTimer OBJECT-TYPE
            SYNTAX INTEGER (2..255)
            ACCESS read-only
            STATUS mandatory
	    DESCRIPTION
		"The Idle Timer is used by a station to detect an inoperative condition 
		of the Logical Link. This timer is started when the link becomes idle 
		(no data to pass and no outstanding acknowledgments) and if it expires, 
		the station sends a supervisory frame with the poll bit set to 1. 
		Time is in seconds."
        ::= { cdx6500CfgSLACProfileEntry 5 }

	cdx6500SLACprofN2Retry OBJECT-TYPE
            SYNTAX INTEGER (1..20)
            ACCESS read-only
            STATUS mandatory
	    DESCRIPTION
		"This count defines the number of times an I frame or supervisory frame 
		with poll bit set to 1, will be transmitted, due to T1 acknowledgment 
		time-out, before the Logical Link will be declared down (inoperative)"
        ::= { cdx6500CfgSLACProfileEntry 6 }

	cdx6500SLACprofN3Ack OBJECT-TYPE
            SYNTAX INTEGER (1..15)
            ACCESS read-only
            STATUS mandatory
	    DESCRIPTION
		"The receive count is used in conjunction with T2 to reduce the amount 
		of acknowledgments a station generates. The receive count is used by a 
		station to determine how many frames it will receive from the remote 
		station while withholding acknowledgment of these frames. This is a 
		method of reducing the amount of acknowledgments generated by a link 
		station. When this count expires, the link station should immediately 
		send an acknowledgment for all received frames not yet acknowledged."
        ::= { cdx6500CfgSLACProfileEntry 7 }

	cdx6500SLACprofTxwindow OBJECT-TYPE
            SYNTAX INTEGER (1..255)
            ACCESS read-only
            STATUS mandatory
	    DESCRIPTION
		"Transmit Window Size is the maximum number of I frames a station may 
		transmit without acknowledgment."
        ::= { cdx6500CfgSLACProfileEntry 8 }

	cdx6500SLACprofTAStartup OBJECT-TYPE
            SYNTAX INTEGER (1..255)
            ACCESS read-only
            STATUS mandatory
	    DESCRIPTION
		"The TA Timer is used by a station as the retry timer when establishing 
		a logical link. Time is in seconds."
        ::= { cdx6500CfgSLACProfileEntry 9 }

	cdx6500SLACprofRingNumber OBJECT-TYPE
            SYNTAX DisplayString (SIZE(4))
            ACCESS read-only
            STATUS mandatory
	    DESCRIPTION
		"This is the ring number used by Frame Relay 1490 SLAC stations using 
		802.5 (BAN) encapsulation. If a value of zero is entered for this, this 
		ring number will not be inserted into the Route Indicator Field."
        ::= { cdx6500CfgSLACProfileEntry 10 }

	cdx6500SLACprofBridgeID OBJECT-TYPE
            SYNTAX INTEGER (1..15)
            ACCESS read-only
            STATUS mandatory
	    DESCRIPTION
		"This is the bridge id used by the SLAC stations using 802.5 encapsulation."
        ::= { cdx6500CfgSLACProfileEntry 11 }

        -- The SLAC Station Statistics Table
        -- This table contains Statistics paramaters 
        -- for the SLAC Station table.
                        
        cdx6500PSTSLACStationTable OBJECT-TYPE
            SYNTAX SEQUENCE OF Cdx6500PSTSLACStationEntry
            ACCESS not-accessible
            STATUS mandatory
            DESCRIPTION
                "All of the statistics parameters relevant
                 to the SLAC Station table."
        ::= { cdx6500PSTSLACStationGroup 1 }
                        
        cdx6500PSTSLACStationEntry OBJECT-TYPE
            SYNTAX Cdx6500PSTSLACStationEntry
            ACCESS not-accessible
            STATUS mandatory
            DESCRIPTION
                "A row of SLAC station Statistics parameters."
            INDEX { cdx6500slacsStationTypeStat, cdx6500slacsStationNumber }
        ::= { cdx6500PSTSLACStationTable 1 }
                        
        Cdx6500PSTSLACStationEntry ::=
            SEQUENCE {
		cdx6500slacsStationNumber
		    INTEGER,
		cdx6500slacsStationTypeStat
		    INTEGER,		
		cdx6500slacsStationStatus
		    DisplayString, 	
		cdx6500slacsFRPortNumStat
		    INTEGER,
		cdx6500slacsBurnedInAddrStat
		    DisplayString,
                cdx6500slacsExternAddrStat
                    DisplayString,
                cdx6500slacsInternAddrStat
                    DisplayString,
             	cdx6500slacsExternSapStat
                    DisplayString,  
             	cdx6500slacsInterSapStat
                    DisplayString,
		cdx6500slacsRIF
		    DisplayString,
		cdx6500slacsLastStatsReset
		    DisplayString,
		cdx6500slacsPVCStatus
		    DisplayString, 
		cdx6500slacsLLCState
		    DisplayString,
                cdx6500slacsCharInTotal
                    Counter,
                cdx6500slacsCharOutTotal
                    Counter,
                cdx6500slacsCharsInPerSec
                    INTEGER,
                cdx6500slacsCharsOutPerSec
                    INTEGER,
                cdx6500slacsINFOFramesInTotal
                    Counter,
                cdx6500slacsINFOFramesOutTotal
                    Counter,
                cdx6500slacsINFOFramesInPerSec
                    INTEGER,
                cdx6500slacsINFOFramesOutPerSec
                    INTEGER,
                cdx6500slacsPacketsQueued
                    INTEGER,
                cdx6500slacsTESTInFrames
                    Counter,
                cdx6500slacsTESTOutFrames
                    Counter,
		cdx6500slacsSABMEInFrames
		    Counter,
		cdx6500slacsSABMEOutFrames
		    Counter,
                cdx6500slacsRRInFrames
                    Counter,
                cdx6500slacsRROutFrames
                    Counter,
                cdx6500slacsRNRInFrames
                    Counter,
                cdx6500slacsRNROutFrames
                    Counter,
                cdx6500slacsUAInFrames
                    Counter,
                cdx6500slacsUAOutFrames
                    Counter,
                cdx6500slacsDMInFrames
                    Counter,
                cdx6500slacsDMOutFrames
                    Counter,
                cdx6500slacsXIDInFrames
                    Counter,
                cdx6500slacsXIDOutFrames
                    Counter,
                cdx6500slacsXIDNullInFrames
                    Counter,
                cdx6500slacsXIDNullOutFrames
                    Counter,
                cdx6500slacsXID0InFrames
                    Counter,
                cdx6500slacsXID0OutFrames
                    Counter,
                cdx6500slacsXID1InFrames
                    Counter,
                cdx6500slacsXID1OutFrames
                    Counter,
                cdx6500slacsXID3InFrames
                    Counter,
                cdx6500slacsXID3OutFrames
                    Counter, 
                cdx6500slacsREJInFrames
                    Counter,
                cdx6500slacsREJOutFrames
                    Counter,
                cdx6500slacsDISCInFrames
                    Counter,
                cdx6500slacsDISCOutFrames
                    Counter,
                cdx6500slacsFRMRInFrames
                    Counter,
                cdx6500slacsFRMROutFrames
                    Counter,
		cdx6500slacsOOSInFrames
		    Counter,
		cdx6500slacsBADInFrames
		    Counter,
		cdx6500slacsINFOFramesDropped
		    Counter,
		cdx6500slacsINFOPacketCongestion
		    Counter,
                cdx6500slacsQLLCState
                    DisplayString,
		cdx6500slacsQLLCStationAddrStat
		    DisplayString,		    
		cdx6500slacsDCPlevel
	  	    DisplayString,
                cdx6500slacsQSMInFrames
                    Counter16,
                cdx6500slacsQSMOutFrames
                    Counter16,
                cdx6500slacsQUAInFrames
                    Counter16,
                cdx6500slacsQUAOutFrames
                    Counter16,
                cdx6500slacsQRDInFrames
                    Counter16,
                cdx6500slacsQRDOutFrames
                    Counter16,
                cdx6500slacsQFRMRInFrames
                    Counter16,
                cdx6500slacsQFRMROutFrames
                    Counter16,
                cdx6500slacsQXIDInFrames
                    Counter16,
                cdx6500slacsQXIDOutFrames
                    Counter16,
		cdx6500slacsQRRInFrames
		    Counter16,
		cdx6500slacsQRROutFrames
		    Counter16,
                cdx6500slacsQDCInFrames
                    Counter16,
                cdx6500slacsQDCOutFrames
                    Counter16,
                cdx6500slacsQDMInFrames
                    Counter16,
                cdx6500slacsQDMOutFrames
                    Counter16,
                cdx6500slacsQTESTInFrames
                    Counter16,
                cdx6500slacsQTESTOutFrames
                    Counter16,
                cdx6500slacsQSSInFrames
                    Counter16,
                cdx6500slacsQSSOutFrames
                    Counter16,
                cdx6500slacsQRSInFrames
                    Counter16,
                cdx6500slacsQRSOutFrames
                    Counter16,
		cdx6500slacsVSNumber
                    INTEGER,
                cdx6500slacsVRNumber
                    INTEGER,
		cdx6500slacsNRNumber
		    INTEGER,
		cdx6500slacsNSNumber
		    INTEGER,
		cdx6500slacsNextAutocallTime
		    Counter16,
		cdx6500slacsCallStatus
		    DisplayString,
		cdx6500slacsNumAutocallAttempts
	            Counter16,
		cdx6500slacsLinkSuspendTime
		    Counter16,
		cdx6500slacsCallInRequests
		    Counter16,
		cdx6500slacsCallOutRequests
		    Counter16,
		cdx6500slacsCallInAccepts
		    Counter16,
		cdx6500slacsCallOutAccepts
                    Counter16,
 		cdx6500slacsClearInRequests
		    Counter16,
		cdx6500slacsClearOutRequests
		    Counter16,
		cdx6500slacsClearInConfirms
		    Counter16,
		cdx6500slacsClearOutConfirms
		    Counter16,
		cdx6500slacsLastCallDir
		    DisplayString,
		cdx6500slacsLastCalledAddr
		    DisplayString,
		cdx6500slacsCallingAddrStat
		    DisplayString,
		cdx6500slacsCallFacitlities
		    DisplayString,
		cdx6500slacsCallCUD
		    DisplayString,
		cdx6500slacsLastClearDir
		    DisplayString,
		cdx6500slacsLastClearCause
		    DisplayString,
		cdx6500slacsLastClearDiag
		    DisplayString,
		cdx6500slacsSNACharsInTotal
		    Counter16,
		cdx6500slacsSNACharsOutTotal
		    Counter16,
		cdx6500slacsSNAFramesInTotal
		    Counter16,
		cdx6500slacsSNAFramesOutTotal
		    Counter16,
		cdx6500slacsFlowCtrlOnRx
		    Counter16,
		cdx6500slacsFlowCtrlOffRx
		    Counter16,
		cdx6500slacsCurrentQueuedTx
		    Counter16,
		cdx6500slacsMaximumQueuedTx
		    Counter16,
		cdx6500slacsStnConnState
		    DisplayString,
		cdx6500slacsQLLCTxFlow
		    DisplayString,
		cdx6500slacsLUIDStatus
		    DisplayString, 
		cdx6500slacsSLACContext
		    DisplayString, 
		cdx6500slacsSTKCBContext
	  	    DisplayString, 
		cdx6500slacsSCBContext
		    DisplayString,
		cdx6500slacsQLLCContext
		    DisplayString,
		cdx6500slacsSLCMContext
		    DisplayString,
		cdx6500slacsSLACltContext
		    DisplayString,
		cdx6500slacsTRLTMContext
		    DisplayString,
		cdx6500slacsFRLTMContext
                    DisplayString,
		cdx6500slacsETHLTMContext
		    DisplayString
                }

        cdx6500slacsStationNumber OBJECT-TYPE
            SYNTAX INTEGER (1..32)
            ACCESS read-only
            STATUS mandatory
            DESCRIPTION
                "Station reference number."
        ::= { cdx6500PSTSLACStationEntry 1 }
	
        cdx6500slacsStationTypeStat OBJECT-TYPE
            SYNTAX INTEGER {
                        token-ring    (0),
                        frame-relay   (1),
                        ethernet      (2),
                        ethernet-2    (3),
                        token-ring-2  (4)}
            ACCESS read-only
            STATUS mandatory
            DESCRIPTION
                "Refers to the station type."
        ::= { cdx6500PSTSLACStationEntry 2 }
                        
	cdx6500slacsStationStatus OBJECT-TYPE
	    SYNTAX DisplayString (SIZE(0..255))
            ACCESS read-only
            STATUS mandatory
            DESCRIPTION
		"Refers to the station Status."
	::= { cdx6500PSTSLACStationEntry 3 }
                        
	cdx6500slacsFRPortNumStat OBJECT-TYPE
            SYNTAX INTEGER (1..54)
            ACCESS read-only
            STATUS mandatory
            DESCRIPTION
                "Refers to the physical Frame Relay port number."
        ::= { cdx6500PSTSLACStationEntry 4 }

	cdx6500slacsBurnedInAddrStat OBJECT-TYPE
            SYNTAX DisplayString (SIZE(17))
            ACCESS read-only
            STATUS mandatory
            DESCRIPTION
		"The burned-in MAC address of the LAN device associated with this station."
        ::= { cdx6500PSTSLACStationEntry 5 }

        cdx6500slacsExternAddrStat OBJECT-TYPE
            SYNTAX DisplayString (SIZE(17))
            ACCESS read-only
            STATUS mandatory
            DESCRIPTION
                "The MAC address of the External LAN device associated with this station."
        ::= { cdx6500PSTSLACStationEntry 6 }

        cdx6500slacsInternAddrStat OBJECT-TYPE
            SYNTAX DisplayString (SIZE(17))
            ACCESS read-only
            STATUS mandatory
            DESCRIPTION
                "The station address on the multidrop line."
        ::= { cdx6500PSTSLACStationEntry 7 }

        cdx6500slacsExternSapStat OBJECT-TYPE
            SYNTAX DisplayString (SIZE(2))
            ACCESS read-only
            STATUS mandatory
            DESCRIPTION
                "The SAP of the device associated with this station."
        ::= { cdx6500PSTSLACStationEntry 8 }

	cdx6500slacsInterSapStat OBJECT-TYPE
            SYNTAX DisplayString (SIZE(2))
            ACCESS read-only
            STATUS mandatory
	    DESCRIPTION
		"The local SAP of this station."
        ::= { cdx6500PSTSLACStationEntry 9 }

	cdx6500slacsRIF OBJECT-TYPE
	    SYNTAX DisplayString (SIZE(0..255))
            ACCESS read-only
            STATUS mandatory
            DESCRIPTION
                "Refers to routing information field used in all frames."

	::= { cdx6500PSTSLACStationEntry 10 }
    
	cdx6500slacsLastStatsReset OBJECT-TYPE
            SYNTAX DisplayString (SIZE(0..255))
            ACCESS read-only
            STATUS mandatory
            DESCRIPTION
		"Indicates the date and time the station statistics was last reset."
        ::= { cdx6500PSTSLACStationEntry 11 }

	cdx6500slacsPVCStatus OBJECT-TYPE
            SYNTAX DisplayString (SIZE(0..255))
            ACCESS read-only
            STATUS mandatory
            DESCRIPTION
                "Refers to the PVC status of TR connection."
        ::= { cdx6500PSTSLACStationEntry 12 }

	cdx6500slacsLLCState OBJECT-TYPE
	    SYNTAX DisplayString (SIZE(0..255))
	    ACCESS read-only
            STATUS mandatory
            DESCRIPTION
                "LLC protocol state of this station."
        ::= { cdx6500PSTSLACStationEntry 13 }

        cdx6500slacsCharInTotal OBJECT-TYPE
            SYNTAX Counter
            ACCESS read-only
            STATUS mandatory
            DESCRIPTION
                "Total number of characters received until now, not 
                 including SLAC header characters."
        ::= { cdx6500PSTSLACStationEntry 14 }
                        
        cdx6500slacsCharOutTotal OBJECT-TYPE
            SYNTAX Counter
            ACCESS read-only
            STATUS mandatory
            DESCRIPTION
                "Total number of characters transmitted until now, not 
                 including SLAC header characters."
        ::= { cdx6500PSTSLACStationEntry 15 }
                        
        cdx6500slacsCharsInPerSec OBJECT-TYPE
            SYNTAX INTEGER
            ACCESS read-only
            STATUS mandatory
            DESCRIPTION
                "The average number of characters received per second 
                 during the previous minute."
        ::= { cdx6500PSTSLACStationEntry 16 }
                        
        cdx6500slacsCharsOutPerSec OBJECT-TYPE
            SYNTAX INTEGER
            ACCESS read-only
            STATUS mandatory
            DESCRIPTION
                "The average number of characters transmitted per second 
                 during the previous minute."
        ::= { cdx6500PSTSLACStationEntry 17 }
                        
        cdx6500slacsINFOFramesInTotal OBJECT-TYPE
            SYNTAX Counter
            ACCESS read-only
            STATUS mandatory
            DESCRIPTION
                "Total number of information frames received until now."
        ::= { cdx6500PSTSLACStationEntry 18 }
                        
        cdx6500slacsINFOFramesOutTotal OBJECT-TYPE
            SYNTAX Counter
            ACCESS read-only
            STATUS mandatory
            DESCRIPTION
                "Total number of information frames transmitted until now."
        ::= { cdx6500PSTSLACStationEntry 19 }
                        
        cdx6500slacsINFOFramesInPerSec OBJECT-TYPE
            SYNTAX INTEGER
            ACCESS read-only
            STATUS mandatory
            DESCRIPTION
                "The average number of frames received per second 
                 during the previous minute."
        ::= { cdx6500PSTSLACStationEntry 20 }
                        
        cdx6500slacsINFOFramesOutPerSec OBJECT-TYPE
            SYNTAX INTEGER
            ACCESS read-only
            STATUS mandatory
            DESCRIPTION
                "The average number of frames transmitted per second 
                 during the previous minute."
        ::= { cdx6500PSTSLACStationEntry 21 }
                        
        cdx6500slacsPacketsQueued OBJECT-TYPE
            SYNTAX INTEGER
	    ACCESS read-only
	    STATUS mandatory
	    DESCRIPTION
                "Total number of packets queued at the SLAC protocol layer 
                 by the transmitter."
        ::= { cdx6500PSTSLACStationEntry 22 }

        cdx6500slacsTESTInFrames OBJECT-TYPE
            SYNTAX Counter
            ACCESS read-only
            STATUS mandatory
            DESCRIPTION
                "Total number of TEST frames received until the present time."
        ::= { cdx6500PSTSLACStationEntry 23 }

        cdx6500slacsTESTOutFrames OBJECT-TYPE
            SYNTAX Counter
            ACCESS read-only
            STATUS mandatory
            DESCRIPTION
                "Total number of TEST frames transmitted until the present 
                 time."
        ::= { cdx6500PSTSLACStationEntry 24 }

	cdx6500slacsSABMEInFrames OBJECT-TYPE
            SYNTAX Counter
            ACCESS read-only
            STATUS mandatory
            DESCRIPTION
		"Total number of SABME frames received until the present time."
	::= { cdx6500PSTSLACStationEntry 25 }

        cdx6500slacsSABMEOutFrames OBJECT-TYPE
            SYNTAX Counter
            ACCESS read-only
            STATUS mandatory
            DESCRIPTION
                "Total number of SABME frames transmitted until the present time."
        ::= { cdx6500PSTSLACStationEntry 26 }

        cdx6500slacsRRInFrames OBJECT-TYPE
            SYNTAX Counter
            ACCESS read-only
            STATUS mandatory
            DESCRIPTION
                "Total number of RR frames received until the present time."
        ::= { cdx6500PSTSLACStationEntry 27 }

        cdx6500slacsRROutFrames OBJECT-TYPE
            SYNTAX Counter
            ACCESS read-only
            STATUS mandatory
            DESCRIPTION
                "Total number of RR frames transmitted until the present time."
        ::= { cdx6500PSTSLACStationEntry 28 }

        cdx6500slacsRNRInFrames OBJECT-TYPE
            SYNTAX Counter
            ACCESS read-only
            STATUS mandatory
            DESCRIPTION
                "Total number of RNR frames received until the present time."
        ::= { cdx6500PSTSLACStationEntry 29 }

        cdx6500slacsRNROutFrames OBJECT-TYPE
            SYNTAX Counter
            ACCESS read-only
            STATUS mandatory
            DESCRIPTION
                "Total number of RNR frames transmitted until the present time."
        ::= { cdx6500PSTSLACStationEntry 30 }

        cdx6500slacsUAInFrames OBJECT-TYPE
            SYNTAX Counter
            ACCESS read-only
            STATUS mandatory
            DESCRIPTION
                "Total number of UA frames received until the present time."
        ::= { cdx6500PSTSLACStationEntry 31 }

        cdx6500slacsUAOutFrames OBJECT-TYPE
            SYNTAX Counter
            ACCESS read-only
            STATUS mandatory
            DESCRIPTION
                "Total number of UA frames transmitted until the present time."
        ::= { cdx6500PSTSLACStationEntry 32 }

        cdx6500slacsDMInFrames OBJECT-TYPE
            SYNTAX Counter
            ACCESS read-only
            STATUS mandatory
            DESCRIPTION
                "Total number of DM frames received until the present time."
        ::= { cdx6500PSTSLACStationEntry 33 }

        cdx6500slacsDMOutFrames OBJECT-TYPE
            SYNTAX Counter
            ACCESS read-only
            STATUS mandatory
            DESCRIPTION
                "Total number of DM frames transmitted until the present time."
        ::= { cdx6500PSTSLACStationEntry 34 }

        cdx6500slacsXIDInFrames OBJECT-TYPE
            SYNTAX Counter
            ACCESS read-only
            STATUS mandatory
            DESCRIPTION
                "Total number of XID frames received until the present time."
        ::= { cdx6500PSTSLACStationEntry 35 }

        cdx6500slacsXIDOutFrames OBJECT-TYPE
            SYNTAX Counter
            ACCESS read-only
            STATUS mandatory
            DESCRIPTION
                "Total number of XID frames transmitted until the present time."
        ::= { cdx6500PSTSLACStationEntry 36 }
	

	cdx6500slacsXIDNullInFrames OBJECT-TYPE
            SYNTAX Counter
            ACCESS read-only
            STATUS mandatory
            DESCRIPTION
                "Total number of XID Null frames received until the present time."
        ::= { cdx6500PSTSLACStationEntry 37 }

        cdx6500slacsXIDNullOutFrames OBJECT-TYPE
            SYNTAX Counter
            ACCESS read-only
            STATUS mandatory
            DESCRIPTION
                "Total number of XID Null frames transmitted until the present time."
        ::= { cdx6500PSTSLACStationEntry 38 }

        cdx6500slacsXID0InFrames OBJECT-TYPE
            SYNTAX Counter
            ACCESS read-only
            STATUS mandatory
            DESCRIPTION
                "Total number of XID Format 0 frames received until the present time."
        ::= { cdx6500PSTSLACStationEntry 39 }

        cdx6500slacsXID0OutFrames OBJECT-TYPE
            SYNTAX Counter
            ACCESS read-only
            STATUS mandatory
            DESCRIPTION
                "Total number of XID Format 0 frames transmitted until the present time."
        ::= { cdx6500PSTSLACStationEntry 40 }

        cdx6500slacsXID1InFrames OBJECT-TYPE
            SYNTAX Counter
            ACCESS read-only
            STATUS mandatory
            DESCRIPTION
                "Total number of XID Format 1 frames received until the present time."
        ::= { cdx6500PSTSLACStationEntry 41 }

        cdx6500slacsXID1OutFrames OBJECT-TYPE
            SYNTAX Counter
            ACCESS read-only
            STATUS mandatory
            DESCRIPTION
                "Total number of XID Format 1 frames transmitted until the present time."
        ::= { cdx6500PSTSLACStationEntry 42 }

        cdx6500slacsXID3InFrames OBJECT-TYPE
            SYNTAX Counter
            ACCESS read-only
            STATUS mandatory
            DESCRIPTION
                "Total number of XID Format 3 frames received until the present time."
        ::= { cdx6500PSTSLACStationEntry 43 }

        cdx6500slacsXID3OutFrames OBJECT-TYPE
            SYNTAX Counter
            ACCESS read-only
            STATUS mandatory
            DESCRIPTION
                "Total number of XID Format 3 frames transmitted until the present time."
        ::= { cdx6500PSTSLACStationEntry 44 }
	
        cdx6500slacsREJInFrames OBJECT-TYPE
            SYNTAX Counter
            ACCESS read-only
            STATUS mandatory
            DESCRIPTION
                "Total number of REJ frames received until the present time."
        ::= { cdx6500PSTSLACStationEntry 45 }

        cdx6500slacsREJOutFrames OBJECT-TYPE
            SYNTAX Counter
            ACCESS read-only
            STATUS mandatory
            DESCRIPTION
                "Total number of REJ frames transmitted until the present time."
        ::= { cdx6500PSTSLACStationEntry 46 }

        cdx6500slacsDISCInFrames OBJECT-TYPE
            SYNTAX Counter
            ACCESS read-only
            STATUS mandatory
            DESCRIPTION
                "Total number of DISC frames received until the present time."
        ::= { cdx6500PSTSLACStationEntry 47 }

        cdx6500slacsDISCOutFrames OBJECT-TYPE
            SYNTAX Counter
            ACCESS read-only
            STATUS mandatory
            DESCRIPTION
                "Total number of DISC frames transmitted until the present 
                 time."
        ::= { cdx6500PSTSLACStationEntry 48 }

        cdx6500slacsFRMRInFrames OBJECT-TYPE
            SYNTAX Counter
            ACCESS read-only
            STATUS mandatory
            DESCRIPTION
                "Total number of FRMR frames received until the present time."
        ::= { cdx6500PSTSLACStationEntry 49 }

        cdx6500slacsFRMROutFrames OBJECT-TYPE
            SYNTAX Counter
            ACCESS read-only
            STATUS mandatory
            DESCRIPTION
                "Total number of FRMR frames transmitted until the present 
                 time."
        ::= { cdx6500PSTSLACStationEntry 50 }

        cdx6500slacsOOSInFrames OBJECT-TYPE
            SYNTAX Counter
            ACCESS read-only
            STATUS mandatory
            DESCRIPTION
                "Total number of out of sequence frames 
		that were received until the present time."
        ::= { cdx6500PSTSLACStationEntry 51 }

        cdx6500slacsBADInFrames OBJECT-TYPE
            SYNTAX Counter
            ACCESS read-only
            STATUS mandatory
            DESCRIPTION
                "Total number of bad frames received until the present time."
        ::= { cdx6500PSTSLACStationEntry 52 }

        cdx6500slacsINFOFramesDropped OBJECT-TYPE
            SYNTAX Counter
            ACCESS read-only
            STATUS mandatory
            DESCRIPTION
                "Total number of frames dropped until the present time."
        ::= { cdx6500PSTSLACStationEntry 53 }

        cdx6500slacsINFOPacketCongestion OBJECT-TYPE
            SYNTAX Counter
            ACCESS read-only
            STATUS mandatory
            DESCRIPTION
                "Total number of congested frames
                that were received until the present time."
        ::= { cdx6500PSTSLACStationEntry 54 }

        cdx6500slacsQLLCState OBJECT-TYPE
            SYNTAX DisplayString (SIZE(0..255))
            ACCESS read-only
            STATUS mandatory
            DESCRIPTION
                "Indicates the status of the QLLC layer:
                 INOPERATIVE : No connection exists with the station.
                 LINK-CLOSED : X.25 call is connected, but there has 
                               been no successful QXID exchange and 
                               data cannot pass.
                 LINK-OPENING: The X.25 call is connected and there has
                               been a successful QXID exchange. However,
                               there has been no QUA or QDM response to
                               a QSM command.
                 LINK-OPENED : X.25 call is connected and data is 
                               passing.
                 LINK-CLOSING: Disconnect in process. Station may come
                               back up after an SVC clear or PVC reset.
                               If it does not, boot the station to
                               clear it.
                 LINK-RECOVERY: X.25 call is connected and the station
                                has sent a QFRMR packet over the link.
                                Station may come back up after SVC clear
                                or PVC reset. If it does not recover,
                                boot the station to clear it.
                 NOTE: This value is not supported by the 6500."
        ::= { cdx6500PSTSLACStationEntry 55 }

        cdx6500slacsQLLCStationAddrStat OBJECT-TYPE
            SYNTAX DisplayString (SIZE(2))
            ACCESS read-only
            STATUS mandatory
            DESCRIPTION
                "The station address used for QLLC control procedures."
        ::= { cdx6500PSTSLACStationEntry 56 }

	cdx6500slacsDCPlevel OBJECT-TYPE
	    SYNTAX DisplayString (SIZE(0..10))
            ACCESS read-only
            STATUS mandatory
            DESCRIPTION
		"The current Data Connection/Protection level of this station."
        ::= { cdx6500PSTSLACStationEntry 57 }

        cdx6500slacsQSMInFrames OBJECT-TYPE
            SYNTAX Counter16
            ACCESS read-only
            STATUS mandatory
            DESCRIPTION
                "Total number of QSM packets received until the present time."
        ::= { cdx6500PSTSLACStationEntry 58 }

        cdx6500slacsQSMOutFrames OBJECT-TYPE
            SYNTAX Counter16
            ACCESS read-only
            STATUS mandatory
            DESCRIPTION
                "Total number of QSM packets transmitted until the present 
                 time."
        ::= { cdx6500PSTSLACStationEntry 59 }

        cdx6500slacsQUAInFrames OBJECT-TYPE
            SYNTAX Counter16
            ACCESS read-only
            STATUS mandatory
            DESCRIPTION
                "Total number of QUA packets received until the present time."
        ::= { cdx6500PSTSLACStationEntry 60 }

        cdx6500slacsQUAOutFrames OBJECT-TYPE
            SYNTAX Counter16
            ACCESS read-only
            STATUS mandatory
            DESCRIPTION
                "Total number of QUA packets transmitted until the present 
                 time."
        ::= { cdx6500PSTSLACStationEntry 61 }

        cdx6500slacsQRDInFrames OBJECT-TYPE
            SYNTAX Counter16
            ACCESS read-only
            STATUS mandatory
            DESCRIPTION
                "Total number of QRD packets received until the present time."
        ::= { cdx6500PSTSLACStationEntry 62 }

        cdx6500slacsQRDOutFrames OBJECT-TYPE
            SYNTAX Counter16
            ACCESS read-only
            STATUS mandatory
            DESCRIPTION
                "Total number of QRD packets transmitted until the present 
                 time."
        ::= { cdx6500PSTSLACStationEntry 63 }

        cdx6500slacsQFRMRInFrames OBJECT-TYPE
            SYNTAX Counter16
            ACCESS read-only
            STATUS mandatory
            DESCRIPTION
                "Total number of QFRMR packets received until the present time."
        ::= { cdx6500PSTSLACStationEntry 64 }

        cdx6500slacsQFRMROutFrames OBJECT-TYPE
            SYNTAX Counter16
            ACCESS read-only
            STATUS mandatory
            DESCRIPTION
                "Total number of QFRMR packets transmitted until the present 
                 time."
        ::= { cdx6500PSTSLACStationEntry 65 }

        cdx6500slacsQXIDInFrames OBJECT-TYPE
            SYNTAX Counter16
            ACCESS read-only
            STATUS mandatory
            DESCRIPTION
                "Total number of QXID packets received until the present time."
        ::= { cdx6500PSTSLACStationEntry 66 }

        cdx6500slacsQXIDOutFrames OBJECT-TYPE
            SYNTAX Counter16
            ACCESS read-only
            STATUS mandatory
            DESCRIPTION
                "Total number of QXID packets transmitted until the present 
                 time."
        ::= { cdx6500PSTSLACStationEntry 67 }

        cdx6500slacsQRRInTotal OBJECT-TYPE
            SYNTAX Counter16
            ACCESS read-only
            STATUS mandatory
            DESCRIPTION
                "Total number of QRR packets received until the present time."
        ::= { cdx6500PSTSLACStationEntry 68 }

        cdx6500slacsQRROutTotal OBJECT-TYPE
            SYNTAX Counter16
            ACCESS read-only
            STATUS mandatory
            DESCRIPTION
                "Total number of QRR packets transmitted until the present time."
        ::= { cdx6500PSTSLACStationEntry 69 }

        cdx6500slacsQDCInFrames OBJECT-TYPE
            SYNTAX Counter16
            ACCESS read-only
            STATUS mandatory
            DESCRIPTION
                "Total number of QDC packets received until the present time."
        ::= { cdx6500PSTSLACStationEntry 70 }

        cdx6500slacsQDCOutFrames OBJECT-TYPE
            SYNTAX Counter16
            ACCESS read-only
            STATUS mandatory
            DESCRIPTION
                "Total number of QDC packets transmitted until the present 
                 time."
        ::= { cdx6500PSTSLACStationEntry 71 }

        cdx6500slacsQDMInFrames OBJECT-TYPE
            SYNTAX Counter16
            ACCESS read-only
            STATUS mandatory
            DESCRIPTION
                "Total number of QDM packets received until the present time."
        ::= { cdx6500PSTSLACStationEntry 72 }

        cdx6500slacsQDMOutFrames OBJECT-TYPE
            SYNTAX Counter16
            ACCESS read-only
            STATUS mandatory
            DESCRIPTION
                "Total number of QDM packets transmitted until the present 
                 time."
        ::= { cdx6500PSTSLACStationEntry 73 }

        cdx6500slacsQTESTInFrames OBJECT-TYPE
            SYNTAX Counter16
            ACCESS read-only
            STATUS mandatory
            DESCRIPTION
                "Total number of QTEST packets received until the present time."
        ::= { cdx6500PSTSLACStationEntry 74 }

        cdx6500slacsQTESTOutFrames OBJECT-TYPE
            SYNTAX Counter16
            ACCESS read-only
            STATUS mandatory
            DESCRIPTION
                "Total number of QTEST packets transmitted until the present 
                 time."
        ::= { cdx6500PSTSLACStationEntry 75 }

        cdx6500slacsQSSInFrames OBJECT-TYPE
            SYNTAX Counter16
            ACCESS read-only
            STATUS mandatory
            DESCRIPTION
                "Total number of QSS packets received until the present time."
        ::= { cdx6500PSTSLACStationEntry 76 }

        cdx6500slacsQSSOutFrames OBJECT-TYPE
            SYNTAX Counter16
            ACCESS read-only
            STATUS mandatory
            DESCRIPTION
                "Total number of QSS packets transmitted until the present time."
        ::= { cdx6500PSTSLACStationEntry 77 }

        cdx6500slacsQRSInFrames OBJECT-TYPE
            SYNTAX Counter16
            ACCESS read-only
            STATUS mandatory
            DESCRIPTION
                "Total number of QRS packets received until the present time."
        ::= { cdx6500PSTSLACStationEntry 78 }

        cdx6500slacsQRSOutFrames OBJECT-TYPE
            SYNTAX Counter16
            ACCESS read-only
            STATUS mandatory
            DESCRIPTION
                "Total number of QRS packets transmitted until the present time."
        ::= { cdx6500PSTSLACStationEntry 79 }

	cdx6500slacsVSNumber OBJECT-TYPE
            SYNTAX INTEGER (0..128)
            ACCESS read-only
            STATUS mandatory
            DESCRIPTION
                "Next VS seuqunce number this station expects."
        ::= { cdx6500PSTSLACStationEntry 80 }

        cdx6500slacsVRNumber OBJECT-TYPE
            SYNTAX INTEGER (0..128)
            ACCESS read-only
            STATUS mandatory
            DESCRIPTION
                "Next VR seuqunce number this station expects."
        ::= { cdx6500PSTSLACStationEntry 81 }

        cdx6500slacsNRNumber OBJECT-TYPE
            SYNTAX INTEGER (0..128)
            ACCESS read-only
            STATUS mandatory
            DESCRIPTION
                "Next NR seuqunce number this station expects."
        ::= { cdx6500PSTSLACStationEntry 82 }

        cdx6500slacsNSNumber OBJECT-TYPE
            SYNTAX INTEGER (0..128)
            ACCESS read-only
            STATUS mandatory
            DESCRIPTION
                "Next NS seuqunce number this station expects."
        ::= { cdx6500PSTSLACStationEntry 83 }

	cdx6500slacsNextAutocallTime OBJECT-TYPE
	    SYNTAX Counter16
            ACCESS read-only
            STATUS mandatory
            DESCRIPTION
                "Number of seconds between elapsed autocall attempts."
        ::= { cdx6500PSTSLACStationEntry 84 }

	cdx6500slacsCallStatus OBJECT-TYPE
            SYNTAX DisplayString (SIZE(0..255))
            ACCESS read-only
            STATUS mandatory
            DESCRIPTION
                "Refers to the autocall status."
        ::= { cdx6500PSTSLACStationEntry 85 }

	cdx6500slacsNumAutocallAttempts OBJECT-TYPE
            SYNTAX Counter16
            ACCESS read-only
            STATUS mandatory
            DESCRIPTION
                "The maximum number of autocall attempts."
        ::= { cdx6500PSTSLACStationEntry 86 }

	cdx6500slacsLinkSuspendTime OBJECT-TYPE
            SYNTAX Counter16
            ACCESS read-only
            STATUS mandatory
            DESCRIPTION
                "The current value of the Dial on Demand Link Idle Timer."
        ::= { cdx6500PSTSLACStationEntry 87 }

	cdx6500slacsCallInRequests OBJECT-TYPE
	    SYNTAX Counter16
            ACCESS read-only
            STATUS mandatory
            DESCRIPTION
                "The number of autocall requests received."
        ::= { cdx6500PSTSLACStationEntry 88 }

	cdx6500slacsCallOutRequests OBJECT-TYPE
            SYNTAX Counter16
            ACCESS read-only
            STATUS mandatory
            DESCRIPTION
                "The number of autocall requests transmitted."
        ::= { cdx6500PSTSLACStationEntry 89 }

	cdx6500slacsCallInAccepts OBJECT-TYPE
            SYNTAX Counter16
            ACCESS read-only
            STATUS mandatory
            DESCRIPTION
                "The number of incoming calls accpeted."
        ::= { cdx6500PSTSLACStationEntry 90 }

	cdx6500slacsCallOutAccepts OBJECT-TYPE
            SYNTAX Counter16
            ACCESS read-only
            STATUS mandatory
            DESCRIPTION
                "The number of outgoing calls accepted."
        ::= { cdx6500PSTSLACStationEntry 91 }

 	cdx6500slacsClearInRequests OBJECT-TYPE
	    SYNTAX Counter16
	    ACCESS read-only
            STATUS mandatory
            DESCRIPTION
                "The number of incoming clear request packets."
        ::= { cdx6500PSTSLACStationEntry 92 }

	cdx6500slacsClearOutRequests OBJECT-TYPE
	    SYNTAX Counter16
	    ACCESS read-only
	    STATUS mandatory
	    DESCRIPTION
                "The number of outgoing clear request packets."
        ::= { cdx6500PSTSLACStationEntry 93 }

	cdx6500slacsClearInConfirms OBJECT-TYPE
	    SYNTAX Counter16
	    ACCESS read-only
            STATUS mandatory
            DESCRIPTION
                "The number of incoming CLEAR confirmed packets."
        ::= { cdx6500PSTSLACStationEntry 94 }
	
	cdx6500slacsClearOutConfirms OBJECT-TYPE
	    SYNTAX Counter16
            ACCESS read-only
            STATUS mandatory
            DESCRIPTION
                "The number of outgoing CLEAR confirmed packets."
        ::= { cdx6500PSTSLACStationEntry 95 }

	cdx6500slacsLastCallDir OBJECT-TYPE
            SYNTAX DisplayString (SIZE(0..255))
            ACCESS read-only
            STATUS mandatory
            DESCRIPTION
                "Identifies the direction of last call."
        ::= { cdx6500PSTSLACStationEntry 96 }

	cdx6500slacsLastCalledAddr OBJECT-TYPE
            SYNTAX DisplayString (SIZE(0..255))
            ACCESS read-only
            STATUS mandatory
            DESCRIPTION
                "The address that was called in the last call."
        ::= { cdx6500PSTSLACStationEntry 97 }

	cdx6500slacsCallingAddrStat OBJECT-TYPE
            SYNTAX DisplayString (SIZE(0..255))
            ACCESS read-only
            STATUS mandatory
            DESCRIPTION
                "The address of the device that placed the last call."
        ::= { cdx6500PSTSLACStationEntry 98 }

	cdx6500slacsCallFacitlities OBJECT-TYPE
            SYNTAX DisplayString (SIZE(0..255))
            ACCESS read-only
            STATUS mandatory
            DESCRIPTION
                "The facility field of the last call."
        ::= { cdx6500PSTSLACStationEntry 99 }
		   
	cdx6500slacsCallCUD OBJECT-TYPE
            SYNTAX DisplayString (SIZE(0..255))
            ACCESS read-only
            STATUS mandatory
            DESCRIPTION
                "Refers to the Call User Data field of the last call."
        ::= { cdx6500PSTSLACStationEntry 100 }

	cdx6500slacsLastClearDir OBJECT-TYPE
            SYNTAX DisplayString (SIZE(0..255))
            ACCESS read-only
            STATUS mandatory
            DESCRIPTION
                "The direction of the last clear request packets."
        ::= { cdx6500PSTSLACStationEntry 101 }

	cdx6500slacsLastClearCause OBJECT-TYPE
            SYNTAX DisplayString (SIZE(0..255))
            ACCESS read-only
            STATUS mandatory
            DESCRIPTION
                "The cause of the last clear request."
        ::= { cdx6500PSTSLACStationEntry 102 }

	cdx6500slacsLastClearDiag OBJECT-TYPE
            SYNTAX DisplayString (SIZE(0..255))
            ACCESS read-only
            STATUS mandatory
            DESCRIPTION
                "The diagnotics of last clear request."
        ::= { cdx6500PSTSLACStationEntry 103 }
		
	cdx6500slacsSNACharsInTotal OBJECT-TYPE
            SYNTAX Counter16
            ACCESS read-only
            STATUS mandatory
            DESCRIPTION
                "Total number of characters received until now."
        ::= { cdx6500PSTSLACStationEntry 104 }

	cdx6500slacsSNACharsOutTotal OBJECT-TYPE
            SYNTAX Counter16
            ACCESS read-only
            STATUS mandatory
            DESCRIPTION
                "Total number of characters transmitted until now."
        ::= { cdx6500PSTSLACStationEntry 105 }

	cdx6500slacsSNAFramesInTotal OBJECT-TYPE
            SYNTAX Counter16
            ACCESS read-only
            STATUS mandatory
            DESCRIPTION
                "Total number of information frames received until now."
        ::= { cdx6500PSTSLACStationEntry 106 }

	cdx6500slacsSNAFramesOutTotal OBJECT-TYPE
            SYNTAX Counter16
            ACCESS read-only
            STATUS mandatory
            DESCRIPTION
                "Total number of information frames transmitted until now."
        ::= { cdx6500PSTSLACStationEntry 107 }

	cdx6500slacsFlowCtrlOnRx OBJECT-TYPE
            SYNTAX Counter16
            ACCESS read-only
            STATUS mandatory
            DESCRIPTION
                "The number of times QLLC detected flow control, 
		 indicating network congestion."
        ::= { cdx6500PSTSLACStationEntry 108 }

	cdx6500slacsFlowCtrlOffRx OBJECT-TYPE
            SYNTAX Counter16
            ACCESS read-only
            STATUS mandatory
            DESCRIPTION
                "The number of times QLLC detected no flow control, 
		 indicating no network congestion."
        ::= { cdx6500PSTSLACStationEntry 109 }

	cdx6500slacsCurrentQueuedTx OBJECT-TYPE
            SYNTAX Counter16
            ACCESS read-only
            STATUS mandatory
            DESCRIPTION
                "The current number of queued data packets awaiting transmission."
        ::= { cdx6500PSTSLACStationEntry 110 }

	cdx6500slacsMaximumQueuedTx OBJECT-TYPE
            SYNTAX Counter16
            ACCESS read-only
            STATUS mandatory
            DESCRIPTION
                "The maximum number of queued data packets awaiting transmission."
        ::= { cdx6500PSTSLACStationEntry 111 }

	cdx6500slacsStnConnState OBJECT-TYPE	
            SYNTAX DisplayString (SIZE(0..255))	
            ACCESS read-only	
            STATUS mandatory		
            DESCRIPTION	
                "Current state of the connection between the 5393-type controller
		 and LAN:	
		 RECONFIGURING:   SLAC station is currently disabled and is waiting
				  for reconfiguration or enable commands.
		 AS400 LINE DOWN: The AS/400 connection for is not active.
		 QLLC LINE DOWN:  The AS/400 line is active, but the QLLC connection
				  is inactive.
		 ALLOCATING:	  The AS/400 and QLLC connection is active, and LU6.2 
				  session is being allocated.
		 PARTIALLY ALLOCATED: The first part of LU6.2 session allocation is 
				      completed.
		 WAITING FOR LSTRT:   XID exchange is complete, QLLC is waiting for 
				      controller to enter NRM state.
		 ALLOCATED:	  The LU6.2 session is fully allocated."
        ::= { cdx6500PSTSLACStationEntry 112 }
	 
	cdx6500slacsQLLCTxFlow OBJECT-TYPE
            SYNTAX DisplayString (SIZE(0..255))
            ACCESS read-only
            STATUS mandatory
            DESCRIPTION
                "The current flow state for sending data:
		 CLEAR:	 No network congestion.
		 BLOCKED:Flow control conition exists, network congestion."
        ::= { cdx6500PSTSLACStationEntry 113 }
		
	cdx6500slacsLUIDStatus OBJECT-TYPE
            SYNTAX DisplayString (SIZE(0..255))
            ACCESS read-only
            STATUS mandatory
            DESCRIPTION
                "The status of each configured remote workstation in the format:
		     (LU ID) - LU ID Status
		 INITIALIZING: The remoste workstation session is being intialized,
			       no active connection exists.
		 POWERED OFF:  The remote workstation is powered off or disconnected.
		 ALLOCATING:   The LU6.2 session for the remote workstation is being
			       allocated.
		 ALLOCATED:    The LU6.2 session for the remote workstation is now 
			       allocated.
		 DEALLOCATING: The LU6.2 session for the remote station is being
	                       deallocated."
        ::= { cdx6500PSTSLACStationEntry 114 }

	cdx6500slacsSLACContext OBJECT-TYPE
            SYNTAX DisplayString (SIZE(0..255))
            ACCESS read-only
            STATUS mandatory
            DESCRIPTION
                "The address where the main SLAC module information resides."
        ::= { cdx6500PSTSLACStationEntry 115 }

	cdx6500slacsSTKCBContext OBJECT-TYPE
            SYNTAX DisplayString (SIZE(0..255))
            ACCESS read-only
            STATUS mandatory
            DESCRIPTION
                "The address where the STKCB module information resides."
        ::= { cdx6500PSTSLACStationEntry 116 }

	cdx6500slacsSCBContext OBJECT-TYPE
            SYNTAX DisplayString (SIZE(0..255))
            ACCESS read-only
            STATUS mandatory
            DESCRIPTION
                "The address where the SCB module information resides."
        ::= { cdx6500PSTSLACStationEntry 117 }
	
	cdx6500slacsQLLCContext  OBJECT-TYPE
            SYNTAX DisplayString (SIZE(0..255))
            ACCESS read-only
            STATUS mandatory
            DESCRIPTION
                "The address where the QLLC module information resides."
        ::= { cdx6500PSTSLACStationEntry 118 }

	cdx6500slacsSLCMContext OBJECT-TYPE
            SYNTAX DisplayString (SIZE(0..255))
            ACCESS read-only
            STATUS mandatory
            DESCRIPTION
                "The address where the SLCM module information resides."
        ::= { cdx6500PSTSLACStationEntry 119 }

	cdx6500slacsSLACltContext OBJECT-TYPE
            SYNTAX DisplayString (SIZE(0..255))
            ACCESS read-only
            STATUS mandatory
            DESCRIPTION
                "The address where the SLAC-LT module information resides."
        ::= { cdx6500PSTSLACStationEntry 120 }

	cdx6500slacsTRLTMContext OBJECT-TYPE
            SYNTAX DisplayString (SIZE(0..255))
            ACCESS read-only
            STATUS mandatory
            DESCRIPTION
                "The address where the Token-Ring module information resides."
        ::= { cdx6500PSTSLACStationEntry 121 }

        cdx6500slacsFRLTMContext OBJECT-TYPE
            SYNTAX DisplayString (SIZE(0..255))
            ACCESS read-only
            STATUS mandatory
            DESCRIPTION
                "The address where the Frame Relay module information resides."
        ::= { cdx6500PSTSLACStationEntry 122 }

	cdx6500slacsETHLTMContext OBJECT-TYPE
            SYNTAX DisplayString (SIZE(0..255))
            ACCESS read-only
            STATUS mandatory
            DESCRIPTION
                "The address where the Ethernet module information resides."
        ::= { cdx6500PSTSLACStationEntry 123 }


        -- The SLAC Station Controls Table
        -- This table contains Control paramaters 
        -- for the SLAC Station table.
                        
        cdx6500ContSLACStationTable OBJECT-TYPE
            SYNTAX SEQUENCE OF Cdx6500ContSLACStationEntry
            ACCESS not-accessible
            STATUS mandatory
            DESCRIPTION
                "All of the control parameters relevant
                 to the SLAC Station table."
        ::= { cdx6500ContSLACStation 1 }
                        
        cdx6500ContSLACStationEntry OBJECT-TYPE
            SYNTAX Cdx6500ContSLACStationEntry
            ACCESS not-accessible
            STATUS mandatory
            DESCRIPTION
                "A row of SLAC Station Control parameters."
            INDEX { cdx6500slacsContStationType, cdx6500slacsContStationNum }
        ::= { cdx6500ContSLACStationTable 1 }
                        
        Cdx6500ContSLACStationEntry ::=
             SEQUENCE {
                 cdx6500slacsContStationType
                     INTEGER,
                 cdx6500slacsContStationNum
                     INTEGER,
                 cdx6500slacsContBootStation
                     INTEGER,
                 cdx6500slacsContDisableStation
                     INTEGER,
                 cdx6500slacsContEnableStation
                     INTEGER,
                 cdx6500slacsContResetStnStats
                     INTEGER
                 }
                        
        cdx6500slacsContStationType OBJECT-TYPE
            SYNTAX INTEGER {
                token-ring                    (0),
                frame-relay                   (1),
                ethernet                      (2),
                second-ethernet                  (3),
                second-token-ring                (4)}
            ACCESS not-accessible
            STATUS mandatory
            DESCRIPTION
                "Refers to the physical port number."
        ::= { cdx6500ContSLACStationEntry 1 }
                        
        cdx6500slacsContStationNum OBJECT-TYPE
            SYNTAX INTEGER (1..250)
            ACCESS not-accessible
            STATUS mandatory
            DESCRIPTION
                "Station reference number."
        ::= { cdx6500ContSLACStationEntry 2 }
                        
        cdx6500slacsContBootStation OBJECT-TYPE
            SYNTAX INTEGER {
                    boot   (1),
                    noBoot (2)
                    }
            ACCESS write-only
            STATUS mandatory
            DESCRIPTION
                "Boots the specified SLAC station.
                 boot   - Boot Station
                 noBoot - Do not boot Station"
        ::= { cdx6500ContSLACStationEntry 3 }
                        
        cdx6500slacsContDisableStation OBJECT-TYPE
            SYNTAX INTEGER {
                    disable   (1),
                    noDisable (2)
                    }
            ACCESS write-only
            STATUS mandatory
            DESCRIPTION
                "Disables the specified SLAC station.
                 disable   - Disable Station.
                 noDisable - Do not disable Station."
        ::= { cdx6500ContSLACStationEntry 4 }
                        
        cdx6500slacsContEnableStation OBJECT-TYPE
            SYNTAX INTEGER {
                    enable   (1),
                    noEnable (2)
                    }
            ACCESS write-only
            STATUS mandatory
            DESCRIPTION
                "Enables the specified SLAC station.
                 enable   - Enable Station.
                 noEnable - Not not enable Station."
        ::= { cdx6500ContSLACStationEntry 5 }
                        
        cdx6500slacsContResetStnStats OBJECT-TYPE
            SYNTAX INTEGER {
                    reset   (1),
                    noReset (2)
                    }
            ACCESS write-only
            STATUS mandatory
            DESCRIPTION
                "Resets statistics for the specified SLAC station
                 reset   - Reset Station Statistics
                 noReset - Do not reset Station Statistics"
        ::= { cdx6500ContSLACStationEntry 6 }

        END
