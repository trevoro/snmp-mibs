-- $Id: apachemod.asn1,v 1.1.2.1 2004/06/10 17:24:16 ginger Exp $
-- $Log: apachemod.asn1,v $
-- Revision 1.1.2.1  2004/06/10 17:24:16  ginger
-- New build environment
--
-- Revision 1.1.1.1  2003/04/29 19:04:01  greg
-- init cvs
--
-- # Revision 1.2  2002/07/26  14:36:09  rdk
-- # Checkpoint for June/July2002 release
-- #
-- # Revision 1.1  2001/12/10  21:10:14  rdk
-- # Initial revision
-- #
--
-- Concord Communications, Inc. Private Enterprise MIB for
-- Apache Web Server monitoring and management

-- Pre-release Apache MIB
-- Last updated Tue Dec 12 10:25:04 EDT 2000
-- Russ Clark, rjc@empire.com

-- COPYRIGHT 2000 Concord Communications, Inc. ALL RIGHTS RESERVED.
-- THIS DOCUMENT CONTAINS CONFIDENTIAL AND TRADE SECRET INFORMATION OF 
-- THE Concord Communications, Inc.  COPYRIGHT NOTICE IS PRECAUTIONARY 
-- ONLY AND DOES NOT IMPLY PUBLICATION.

-- No part of this document may be reproduced, transmitted, transcribed,
-- stored in a retrieval system, or translated into any language or
-- computer language, in any form or by any means, without
-- prior written consent of Empire Technologies, Inc.

EMPIRE-APACHEMOD DEFINITIONS ::= BEGIN
	IMPORTS
                OBJECT-TYPE
			FROM RFC-1212
		TRAP-TYPE
			FROM RFC-1215
                DisplayString
                        FROM RFC1213-MIB
                enterprises, TimeTicks, Counter, Gauge
                        FROM RFC1155-SMI;

	empire 	   	OBJECT IDENTIFIER ::= { enterprises 546 }
        applications    OBJECT IDENTIFIER ::= { empire 16 }
	apacheSrv	OBJECT IDENTIFIER ::= { applications 3 }

--
-- Main MIB branch contains module-related items like version,
-- licensing info, etc.
-- 

	apacheModVersion OBJECT-TYPE
		SYNTAX DisplayString
		ACCESS read-only
		STATUS mandatory
		DESCRIPTION
		   "Description and version number of this module
		    for licensing."
		::= { apacheSrv 1 }

        apacheModMode OBJECT-TYPE
                SYNTAX INTEGER {
                    fullMode(1),
                    restrictedMode(2)
                }
                ACCESS read-only
                STATUS mandatory
                DESCRIPTION
                   "This object indicates if the Apache Module is in
                    full-mode or restricted-mode.  Restricted-mode
                    is entered, when SystemEDGE 4.0 and higher,
                    fails to find a valid license.  Once
                    a valid license has been allocated and
                    set, the module will then transition to
                    fullMode(1)"
                ::= { apacheSrv 2 }


-- 
-- Global Configuration Group
--
-- Apache configuration information with tuning parameters. 
-- Organized as a table to support systems with multiple apache servers.

        apacheConfigTable OBJECT-TYPE
                SYNTAX SEQUENCE OF ApacheConfigEntry
                ACCESS not-accessible
                STATUS mandatory
                DESCRIPTION
                   "This table describes the configuration settings
                    for each Apache installation."
                ::= { apacheSrv 10 }

        apacheConfigEntry OBJECT-TYPE
                SYNTAX ApacheConfigEntry
                ACCESS not-accessible
                STATUS mandatory
                DESCRIPTION
                   "An entry in the Apache Configuration table."
                INDEX { apacheConfigPort }
                ::= {  apacheConfigTable 1 }

        ApacheConfigEntry ::= SEQUENCE {
                apacheConfigPort
                        INTEGER,
                apacheConfigVersion
                        DisplayString,
                apacheConfigPID
                        INTEGER,
                apacheConfigRunMode
                        DisplayString,
                apacheConfigUser
                        DisplayString,
                apacheConfigGroup
                        DisplayString,
                apacheConfigHostname
                        DisplayString,
                apacheConfigStartProcs
                        INTEGER,
                apacheConfigMinIdleProcs
                        INTEGER,
                apacheConfigMaxIdleProcs
                        INTEGER,
                apacheConfigMaxProcs
                        INTEGER,
                apacheConfigRequestsMaxPerChild
                        INTEGER,
                apacheConfigRequestsKeepAlive
                        INTEGER,
                apacheConfigRequestsMaxPerConn
                        INTEGER,
                apacheConfigThreadsPerChild
                        INTEGER,
                apacheConfigConnectionTimeout
                        INTEGER,
                apacheConfigKeepAliveTimeout
                        INTEGER,
                apacheConfigServerRoot
                        DisplayString,
                apacheConfigConfigFile
                        DisplayString,
                apacheConfigPIDFile
                        DisplayString,
                apacheConfigScoreboardFile
                        DisplayString,
                apacheConfigDocumentRoot
                        DisplayString,
                apacheConfigAccessLogFile
                        DisplayString,
                apacheConfigErrorLogFile
                        DisplayString,
                apacheConfigScriptLogFile
                        DisplayString
        }

        apacheConfigPort OBJECT-TYPE
                SYNTAX INTEGER
                ACCESS read-only
                STATUS mandatory
                DESCRIPTION
		   "The TCP port currently used by this Apache configuration.
                    This value serves as the index for this table."
                ::= { apacheConfigEntry 1 }

	apacheConfigVersion OBJECT-TYPE
		SYNTAX DisplayString
		ACCESS read-only
		STATUS mandatory
		DESCRIPTION
		   "Apache Web Server version number 
                    and description."
		::= { apacheConfigEntry 2 }

	apacheConfigPID OBJECT-TYPE
		SYNTAX INTEGER 
		ACCESS read-only
		STATUS mandatory
		DESCRIPTION
		   "The process ID (PID) of the master Apache process.  
                    If the server is not running, 0 is returned."
		::= { apacheConfigEntry 3 }

	apacheConfigRunMode OBJECT-TYPE
		SYNTAX DisplayString
		ACCESS read-only
		STATUS mandatory
		DESCRIPTION
		   "The current operating mode. (e.g. standalone)" 
		::= { apacheConfigEntry 4 }

	apacheConfigUser OBJECT-TYPE
		SYNTAX DisplayString
		ACCESS read-only
		STATUS mandatory
		DESCRIPTION
		   "The user currently running the server processes."
		::= { apacheConfigEntry 5 }

	apacheConfigGroup OBJECT-TYPE
		SYNTAX DisplayString
		ACCESS read-only
		STATUS mandatory
		DESCRIPTION
		   "The group currently running the server processes."
		::= { apacheConfigEntry 6 }

	apacheConfigHostname OBJECT-TYPE
		SYNTAX DisplayString
		ACCESS read-only
		STATUS mandatory
		DESCRIPTION
		   "The hostname used by this Apache configuration."
		::= { apacheConfigEntry 7 }

        apacheConfigStartProcs OBJECT-TYPE
                SYNTAX INTEGER
                ACCESS read-only
                STATUS mandatory
                DESCRIPTION
                   "The number of server processes started by Apache
                    at startup."
                ::= { apacheConfigEntry 8 }

        apacheConfigMinIdleProcs OBJECT-TYPE
                SYNTAX INTEGER
                ACCESS read-only
                STATUS mandatory
                DESCRIPTION
                   "The minimum number of idle server processes 
                    maintained by Apache."
                ::= { apacheConfigEntry 9 }

        apacheConfigMaxIdleProcs OBJECT-TYPE
                SYNTAX INTEGER
                ACCESS read-only
                STATUS mandatory
                DESCRIPTION
                   "The maximum number of idle server processes 
                    maintained by Apache."
                ::= { apacheConfigEntry 10 }

        apacheConfigMaxProcs OBJECT-TYPE
                SYNTAX INTEGER
                ACCESS read-only
                STATUS mandatory
                DESCRIPTION
                   "The maximum total number of server processes 
                    allowed by Apache."
                ::= { apacheConfigEntry 11 }

        apacheConfigRequestsMaxPerChild OBJECT-TYPE
                SYNTAX INTEGER
                ACCESS read-only
                STATUS mandatory
                DESCRIPTION
                   "The number of requests handled by a server process
                    before it is recycled by Apache."
                ::= { apacheConfigEntry 12 }

        apacheConfigRequestsKeepAlive OBJECT-TYPE
                SYNTAX INTEGER
                ACCESS read-only
                STATUS mandatory
                DESCRIPTION
                   "Is keep-alive enabled for persistent connections?
                    disabled(0) or enabled(1)"
                ::= { apacheConfigEntry 13 }

        apacheConfigRequestsMaxPerConn OBJECT-TYPE
                SYNTAX INTEGER
                ACCESS read-only
                STATUS mandatory
                DESCRIPTION
                   "The number of requests handled in a single connection
                    if keep-alive is on."
                ::= { apacheConfigEntry 14 }

        apacheConfigThreadsPerChild OBJECT-TYPE
                SYNTAX INTEGER
                ACCESS read-only
                STATUS mandatory
                DESCRIPTION
                   "The maximum number of threads per child process."
                ::= { apacheConfigEntry 15 }

        apacheConfigConnectionTimeout OBJECT-TYPE
                SYNTAX INTEGER
                ACCESS read-only
                STATUS mandatory
                DESCRIPTION
                   "The timeout value for closing inactive connections."
                ::= { apacheConfigEntry 16 }

        apacheConfigKeepAliveTimeout OBJECT-TYPE
                SYNTAX INTEGER
                ACCESS read-only
                STATUS mandatory
                DESCRIPTION
                   "The keep-alive timeout value for open connections."
                ::= { apacheConfigEntry 17 }

        apacheConfigServerRoot OBJECT-TYPE
                SYNTAX DisplayString
                ACCESS read-only
                STATUS mandatory
                DESCRIPTION
                   "The root directory for this Apache installation."
                ::= { apacheConfigEntry 18 }

        apacheConfigConfigFile OBJECT-TYPE
                SYNTAX DisplayString
                ACCESS read-only
                STATUS mandatory
                DESCRIPTION
                   "The current configuration file for this 
                    Apache installation."
                ::= { apacheConfigEntry 19 }

        apacheConfigPIDFile OBJECT-TYPE
                SYNTAX DisplayString
                ACCESS read-only
                STATUS mandatory
                DESCRIPTION
                   "The current PID file for this 
                    Apache installation."
                ::= { apacheConfigEntry 20 }

        apacheConfigScoreboardFile OBJECT-TYPE
                SYNTAX DisplayString
                ACCESS read-only
                STATUS mandatory
                DESCRIPTION
                   "The current scoreboard file for this 
                    Apache installation."
                ::= { apacheConfigEntry 21 }

        apacheConfigDocumentRoot OBJECT-TYPE
                SYNTAX DisplayString
                ACCESS read-only
                STATUS mandatory
                DESCRIPTION
                   "The current document root directory for this 
                    Apache installation."
                ::= { apacheConfigEntry 22 }

        apacheConfigAccessLogFile OBJECT-TYPE
                SYNTAX DisplayString
                ACCESS read-only
                STATUS mandatory
                DESCRIPTION
                   "The current access or transaction log file for this 
                    Apache installation."
                ::= { apacheConfigEntry 23 }

        apacheConfigErrorLogFile OBJECT-TYPE
                SYNTAX DisplayString
                ACCESS read-only
                STATUS mandatory
                DESCRIPTION
                   "The current error log file for this 
                    Apache installation."
                ::= { apacheConfigEntry 24 }

        apacheConfigScriptLogFile OBJECT-TYPE
                SYNTAX DisplayString
                ACCESS read-only
                STATUS mandatory
                DESCRIPTION
                   "The current script log file for this 
                    Apache installation."
                ::= { apacheConfigEntry 25 }


-- 
-- Performance Group
--
-- Apache performance group which includes footprint information, server
-- performance, and counters/gauges for overall data flow through Apache.

	apachePerformance OBJECT IDENTIFIER ::= { apacheSrv 11 }

-- Footprint of Apache in terms of resource consumption
-- (e.g. CPU, disk, memory)

        apacheFootprintTable OBJECT-TYPE
                SYNTAX SEQUENCE OF ApacheFootprintEntry
                ACCESS not-accessible
                STATUS mandatory
                DESCRIPTION
                   "This table reports the performance footprint
                    for each Apache service."
                ::= { apachePerformance 1 }

        apacheFootprintEntry OBJECT-TYPE
                SYNTAX ApacheFootprintEntry
                ACCESS not-accessible
                STATUS mandatory
                DESCRIPTION
                   "An entry in the Apache Performance Footprint table."
                INDEX { apacheFootprintPort }
                ::= {  apacheFootprintTable 1 }

        ApacheFootprintEntry ::= SEQUENCE {
                apacheFootprintPort
                        INTEGER,
                apacheFootprintCPUTime
                        INTEGER,
                apacheFootprintPercentCPU
                        INTEGER,
                apacheFootprintTotalMEMSize
                        Gauge,
                apacheFootprintTotalRSS
                        Gauge,
                apacheFootprintPercentMEM
                        INTEGER,
                apacheFootprintNumThreads
                        Gauge,
                apacheFootprintInBlks
                        Counter,
                apacheFootprintOutBlks
                        Counter,
                apacheFootprintMsgsSent
                        Counter,
                apacheFootprintMsgsRecv
                        Counter,
                apacheFootprintSysCalls
                        Counter,
                apacheFootprintMinorPgFlts
                        Counter,
                apacheFootprintMajorPgFlts
                        Counter,
                apacheFootprintNumSwaps
                        Counter,
                apacheFootprintVolCtx
                        Counter,
                apacheFootprintInvolCtx
                        Counter,
                apacheFootprintTotalLogSize
                        Gauge,
                apacheFootprintDocSize
                        Gauge,
                apacheFootprintTotalDiskSize
                        Gauge
        }

        apacheFootprintPort OBJECT-TYPE
                SYNTAX INTEGER
                ACCESS read-only
                STATUS mandatory
                DESCRIPTION
		   "The TCP port currently used by this Apache configuration.
                    This value serves as the index for this table."
                ::= { apacheFootprintEntry 1 }

        apacheFootprintCPUTime OBJECT-TYPE
                SYNTAX INTEGER
                ACCESS read-only
                STATUS mandatory
                DESCRIPTION
                   "CPU time, in seconds, accumulated by Apache
                    which includes all Apache processes."
                ::= { apacheFootprintEntry 2 }

        apacheFootprintPercentCPU OBJECT-TYPE
                SYNTAX INTEGER (0..100)
                ACCESS read-only
                STATUS mandatory
                DESCRIPTION
                   "The percentage of CPU utilization, by Apache,
                    over the last sample interval.  Since fractions
                    are not supported by SNMP, the value reported is
                    the percentage multiplied by 100.  It is the sum of
                    the CPU utilization of all the Apache processes.
                    Its gives a good indication of the CPU resource 
                    consumption by the entire Apache server."
                ::= { apacheFootprintEntry 3 }

        apacheFootprintTotalMEMSize OBJECT-TYPE
                SYNTAX Gauge
                ACCESS read-only
                STATUS mandatory
                DESCRIPTION
                    "The combined size of Apache's text, data,
                     and stack segments in KBytes.  It is the
                     summation of the process sizes for all
                     Apache server processes."
                ::= { apacheFootprintEntry 4 }

        apacheFootprintTotalRSS OBJECT-TYPE
                SYNTAX Gauge
                ACCESS read-only
                STATUS mandatory
                DESCRIPTION
                    "The real memory (resident set) size of Apache 
                     in KBytes.  It is the summation of the process
                     RSS for all Apache server processes."
                ::= { apacheFootprintEntry 5 }

        apacheFootprintPercentMEM OBJECT-TYPE
                SYNTAX INTEGER (0..100)
                ACCESS read-only
                STATUS mandatory
                DESCRIPTION
                   "The percentage (0-100) of real memory used by
                    Apache which includes all Apache server processes."
                ::= { apacheFootprintEntry 6 }

        apacheFootprintNumThreads OBJECT-TYPE
                SYNTAX Gauge
                ACCESS read-only
                STATUS mandatory
                DESCRIPTION
                   "The number of threads executing within all Apache
                    processes.  Note, on some systems, the operating
                    system may be un-aware of user-level threads
                    executing within the process.  This object
                    reflects the number of threads executing within
                    the process that the operating system is aware of."
                ::= { apacheFootprintEntry 7 }

        apacheFootprintInBlks OBJECT-TYPE
                SYNTAX Counter
                ACCESS read-only
                STATUS mandatory
                DESCRIPTION
                   "The number of blocks of data input by the processes."
        ::= { apacheFootprintEntry 8 }

        apacheFootprintOutBlks OBJECT-TYPE
                SYNTAX Counter
                ACCESS read-only
                STATUS mandatory
                DESCRIPTION
                   "The number of blocks of data output by the processes."
        ::= { apacheFootprintEntry 9 }

        apacheFootprintMsgsSent OBJECT-TYPE
                SYNTAX Counter
                ACCESS read-only
                STATUS mandatory
                DESCRIPTION
                   "The number of messages sent by the processes."
        ::= { apacheFootprintEntry 10 }

        apacheFootprintMsgsRecv OBJECT-TYPE
                SYNTAX Counter
                ACCESS read-only
                STATUS mandatory
                DESCRIPTION
                   "The number of messages received by the processes."
        ::= { apacheFootprintEntry 11 }

        apacheFootprintSysCalls OBJECT-TYPE
                SYNTAX Counter
                ACCESS read-only
                STATUS mandatory
                DESCRIPTION
                   "The number of system calls invoked by the processes."
        ::= { apacheFootprintEntry 12 }

        apacheFootprintMinorPgFlts OBJECT-TYPE
                SYNTAX Counter
                ACCESS read-only
                STATUS mandatory
                DESCRIPTION
                   "The number of minor page faults incurred by the
                    processes.  Minor faults do not require I/O to
                    retrieve the page."
        ::= { apacheFootprintEntry 13 }

        apacheFootprintMajorPgFlts OBJECT-TYPE
                SYNTAX Counter
                ACCESS read-only
                STATUS mandatory
                DESCRIPTION
                   "The number of major page faults incurred by the
                    processes.  Major faults require I/O to retrieve the
                    page."
        ::= { apacheFootprintEntry 14 }

        apacheFootprintNumSwaps OBJECT-TYPE
                SYNTAX Counter
                ACCESS read-only
                STATUS mandatory
                DESCRIPTION
                   "The number of times the processes have been swapped."
        ::= { apacheFootprintEntry 15 }

        apacheFootprintVolCtx OBJECT-TYPE
                SYNTAX Counter
                ACCESS read-only
                STATUS mandatory
                DESCRIPTION
                   "The number of voluntary context switches incurred
                    by the processes.  Voluntary context switches occur
                    when the processor 'voluntary' gives up the CPU
                    (e.g. waiting on I/O.)"
        ::= { apacheFootprintEntry 16 }

        apacheFootprintInvolCtx OBJECT-TYPE
                SYNTAX Counter
                ACCESS read-only
                STATUS mandatory
                DESCRIPTION
                   "The number of involuntary context switches
                    incurred by the processes.  An involuntary context
                    switch occurs when the process has executed for
                    the duration of its time quantum and is switched
                    out by the process scheduler."
        ::= { apacheFootprintEntry 17 }

        apacheFootprintTotalLogSize OBJECT-TYPE
                SYNTAX Gauge 
                ACCESS read-only
                STATUS mandatory
                DESCRIPTION
                   "The size, in KBytes of the Apache service logs. This number
                    is the sum of the access and error log file sizes."
                ::= { apacheFootprintEntry 18 }

        apacheFootprintDocSize OBJECT-TYPE
                SYNTAX Gauge 
                ACCESS read-only
                STATUS mandatory
                DESCRIPTION
                   "The size, in KBytes of the Apache document root directory
                    and all files beneath it."
                ::= { apacheFootprintEntry 19 }

        apacheFootprintTotalDiskSize OBJECT-TYPE
                SYNTAX Gauge
                ACCESS read-only
                STATUS mandatory
                DESCRIPTION
                   "The size, in KBytes, of all the Apache disk
                    storage areas.  It is a summation of log sizes,
                    and service directories.  Summing
                    these storage components in one location presents
                    an easy and convenient MIB object to poll and
                    self-monitor."
                ::= { apacheFootprintEntry 20 }

-- Apache performance metrics and counters useful for capacity planning
-- and real-time performance monitoring.

        apacheServerPerfTable OBJECT-TYPE
                SYNTAX SEQUENCE OF ApacheServerPerfEntry
                ACCESS not-accessible
                STATUS mandatory
                DESCRIPTION
                   "This table reports the performance of
                    each Apache service."
                ::= { apachePerformance 2 }

        apacheServerPerfEntry OBJECT-TYPE
                SYNTAX ApacheServerPerfEntry
                ACCESS not-accessible
                STATUS mandatory
                DESCRIPTION
                   "An entry in the Apache Server Performance table."
                INDEX { apacheServerPerfPort }
                ::= {  apacheServerPerfTable 1 }

        ApacheServerPerfEntry ::= SEQUENCE {
                apacheServerPerfPort
                        INTEGER,
                apacheServerPerfUptime
                        Counter,
                apacheServerPerfTotalAccesses
                        Counter,
                apacheServerPerfTotalTraffic
                        Counter,
                apacheServerPerfCurrentUsers
                        Gauge,
                apacheServerPerfCurrentIdleProcs
                        Gauge,
                apacheServerPerfCurrentStartupProcs
                        Gauge,
                apacheServerPerfCurrentReadProcs
                        Gauge,
                apacheServerPerfCurrentReplyProcs
                        Gauge,
                apacheServerPerfCurrentKeepAliveProcs
                        Gauge,
                apacheServerPerfCurrentDNSProcs
                        Gauge,
                apacheServerPerfCurrentLoggingProcs
                        Gauge,
                apacheServerPerfCurrentFinishingProcs
                        Gauge,
                apacheServerPerfCurrentTotalProcs
                        Gauge,
                apacheServerPerfCurrentBusyProcs
                        Gauge

        }

        apacheServerPerfPort OBJECT-TYPE
                SYNTAX INTEGER
                ACCESS read-only
                STATUS mandatory
                DESCRIPTION
		   "The TCP port currently used by this Apache configuration.
                    This value serves as the index for this table."
                ::= { apacheServerPerfEntry 1 }

        apacheServerPerfUptime OBJECT-TYPE
                SYNTAX Counter 
                ACCESS read-only
                STATUS mandatory
                DESCRIPTION
                   "Number of seconds the Apache server has been up."
                ::= { apacheServerPerfEntry 2 }

        apacheServerPerfTotalAccesses OBJECT-TYPE
                SYNTAX Counter 
                ACCESS read-only
                STATUS mandatory
                DESCRIPTION
                   "Number of accesses (hits) to this server since
                    it was last started."
                ::= { apacheServerPerfEntry 3 }

        apacheServerPerfTotalTraffic OBJECT-TYPE
                SYNTAX Counter 
                ACCESS read-only
                STATUS mandatory
                DESCRIPTION
                   "Number of KBytes transferred by this server since
                    it was last started."
                ::= { apacheServerPerfEntry 4 }

        apacheServerPerfCurrentUsers OBJECT-TYPE
                SYNTAX Gauge 
                ACCESS read-only
                STATUS mandatory
                DESCRIPTION
                    "Number of current active users (connections) maintained by 
                     the Apache server."
                ::= { apacheServerPerfEntry 5 }

        apacheServerPerfCurrentIdleProcs OBJECT-TYPE
                SYNTAX Gauge 
                ACCESS read-only
                STATUS mandatory
                DESCRIPTION
                    "Number of current idle processes available on 
                     the Apache server."
                ::= { apacheServerPerfEntry 6 }

        apacheServerPerfCurrentStartupProcs OBJECT-TYPE
                SYNTAX Gauge 
                ACCESS read-only
                STATUS mandatory
                DESCRIPTION
                    "Number of processes currently in startup on 
                     the Apache server."
                ::= { apacheServerPerfEntry 7 }

        apacheServerPerfCurrentReadProcs OBJECT-TYPE
                SYNTAX Gauge 
                ACCESS read-only
                STATUS mandatory
                DESCRIPTION
                    "Number of processes currently reading requests on
                     the Apache server."
                ::= { apacheServerPerfEntry 8 }

        apacheServerPerfCurrentReplyProcs OBJECT-TYPE
                SYNTAX Gauge 
                ACCESS read-only
                STATUS mandatory
                DESCRIPTION
                    "Number of processes currently replying to requests on
                     the Apache server."
                ::= { apacheServerPerfEntry 9 }

        apacheServerPerfCurrentKeepAliveProcs OBJECT-TYPE
                SYNTAX Gauge 
                ACCESS read-only
                STATUS mandatory
                DESCRIPTION
                    "Number of processes currently in keep-alive on
                     the Apache server."
                ::= { apacheServerPerfEntry 10 }

        apacheServerPerfCurrentDNSProcs OBJECT-TYPE
                SYNTAX Gauge 
                ACCESS read-only
                STATUS mandatory
                DESCRIPTION
                    "Number of processes currently doing a DNS lookup on
                     the Apache server."
                ::= { apacheServerPerfEntry 11 }

        apacheServerPerfCurrentLoggingProcs OBJECT-TYPE
                SYNTAX Gauge 
                ACCESS read-only
                STATUS mandatory
                DESCRIPTION
                    "Number of processes currently logging transactions on
                     the Apache server."
                ::= { apacheServerPerfEntry 12 }

        apacheServerPerfCurrentFinishingProcs OBJECT-TYPE
                SYNTAX Gauge 
                ACCESS read-only
                STATUS mandatory
                DESCRIPTION
                    "Number of processes currently finishing transactions on
                     the Apache server."
                ::= { apacheServerPerfEntry 13 }

        apacheServerPerfCurrentTotalProcs OBJECT-TYPE
                SYNTAX Gauge 
                ACCESS read-only
                STATUS mandatory
                DESCRIPTION
                    "Total number of Apache processes currently running on
                     the Apache server."
                ::= { apacheServerPerfEntry 14 }

        apacheServerPerfCurrentBusyProcs OBJECT-TYPE
                SYNTAX Gauge 
                ACCESS read-only
                STATUS mandatory
                DESCRIPTION
                    "Total number of Apache processes currently busy.
                     This is the sum of 
                        apacheServerPerfCurrentStartupProcs,
                        apacheServerPerfCurrentReadProcs,
                        apacheServerPerfCurrentReplyProcs,
                        apacheServerPerfCurrentKeepAliveProcs,
                        apacheServerPerfCurrentDNSProcs,
                        apacheServerPerfCurrentLoggingProcs,
                        apacheServerPerfCurrentFinishingProcs"
                ::= { apacheServerPerfEntry 15 }



END
