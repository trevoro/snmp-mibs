-- *****************************************************************
-- RBN-CPU-METER-MIB	The RBN CPU utilization MIB
--
-- Copyright (c) 1999 RedBack Networks, Inc.
-- All rights reserved.
-- 
-- *****************************************************************

RBN-CPU-METER-MIB DEFINITIONS ::= BEGIN

IMPORTS
	TEXTUAL-CONVENTION FROM SNMPv2-TC
	MODULE-IDENTITY,
	Integer32, OBJECT-TYPE
		FROM SNMPv2-SMI
	MODULE-COMPLIANCE,
	OBJECT-GROUP
		FROM SNMPv2-CONF
	rbnMgmt
		FROM RBN-SMI;

rbnCpuMeterMIB MODULE-IDENTITY
	LAST-UPDATED	"9906162300Z"
	ORGANIZATION	"RedBack Networks, Inc."
	CONTACT-INFO
		"	RedBack Networks, Inc.

		Postal:	1389 Moffett Park Drive
			Sunnyvale, CA  94089-1134
			USA

		 Phone:	+1 408 548 3500
		   Fax: +1 408 548 3599

		E-mail:	mib-info@RedBackNetworks.com"
	DESCRIPTION
		"This management information module measures  CPU 
                 utilization on a Redback Networks Control Engine (CE)."
    REVISION      "9906162300Z"
    DESCRIPTION
        "Creation of the CPU meter MIB."
	::= { rbnMgmt 6 }


rbnCpuMeterMIBObjects OBJECT IDENTIFIER
	::= { rbnCpuMeterMIB 1 }

rbnCpuMeterMIBConformance OBJECT IDENTIFIER
	::= { rbnCpuMeterMIB 2 }


Percentage ::= TEXTUAL-CONVENTION
    STATUS current
    DESCRIPTION
    "This Textual Convention describes an object that stores 
     a whole integer percentage value."
    SYNTAX Integer32 (0..100)    

-- MIB Objects

rbnCpuMeterFiveSecondAvg OBJECT-TYPE
	SYNTAX	    Percentage
	MAX-ACCESS  read-only
	STATUS	    current
	DESCRIPTION
		"Provides the CPU usage percentage over the first five
                 second period in the scheduler."
	::= { rbnCpuMeterMIBObjects 1 }

rbnCpuMeterOneMinuteAvg OBJECT-TYPE
	SYNTAX	    Percentage
	MAX-ACCESS  read-only
	STATUS	    current
	DESCRIPTION
		"Provides a cumulative average of the CPU usage percentage
                 over a one minute period."
	::= { rbnCpuMeterMIBObjects 2 }

rbnCpuMeterFiveMinuteAvg OBJECT-TYPE
	SYNTAX	    Percentage
	MAX-ACCESS  read-only
	STATUS	    current
	DESCRIPTION
		"Provides a cumulative average of the CPU usage percentage
                 over a five minute period." 
	::= { rbnCpuMeterMIBObjects 3 }


-- Conformance Information


rbnCpuMeterMIBGroups OBJECT IDENTIFIER ::= 
	{ rbnCpuMeterMIBConformance 1 }

rbnCpuMeterMIBCompliances OBJECT IDENTIFIER ::=
	{ rbnCpuMeterMIBConformance 2 }

-- Compliance Statements

rbnCpuMeterMIBCompliance MODULE-COMPLIANCE
	STATUS	    current
	DESCRIPTION
		"The compliance statement for the CPU meter MIB."
	MODULE	    -- this module
	MANDATORY-GROUPS 
                {
		    rbnCpuMeterStatsGroup
		}
	::= { rbnCpuMeterMIBCompliances 1 }

-- Units of Conformance

rbnCpuMeterStatsGroup OBJECT-GROUP
	OBJECTS 
              {
		rbnCpuMeterFiveSecondAvg,
                rbnCpuMeterOneMinuteAvg,
                rbnCpuMeterFiveMinuteAvg
	      }
	STATUS	    current
	DESCRIPTION
		"A collection of objects providing CPU utilization
                 information."
	::= { rbnCpuMeterMIBGroups 1 }

END
