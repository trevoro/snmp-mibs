-------------------------------------------------------------------------------
-- file: SdslStats.mib 
--
-- description:
--      This file contains the SNMP definitions for the SDSL Port Stats area.
--
-- history:
--      %%history-start%%
--      1999.05.17 jlafaye 31A1274: Rennes merge 
--      1999.07.09 gbuzulie P.287086,P.282195,P.286946: check problem of 
--        compile,add nncSdslNearEndRawCRCError counter in 
--        nncSdslNearEndRawTable, nncSdslLineStatus INTEGER change to 1..34 
--        comments are modified 
--      %%history-end%%
--
-- Copyright 1998 Newbridge Networks Corporation.  All Rights Reserved.
-------------------------------------------------------------------------------

SDSL-STATS-MIB DEFINITIONS ::= BEGIN

    IMPORTS
        MODULE-IDENTITY, OBJECT-TYPE, NOTIFICATION-TYPE,
        Counter32, Gauge32
            FROM SNMPv2-SMI
        TEXTUAL-CONVENTION, TruthValue
            FROM SNMPv2-TC
        ifIndex
            FROM IF-MIB
        nncExtensions
            FROM NNCGNI0001-SMI;

    nncSdslStatistics MODULE-IDENTITY
        LAST-UPDATED  "9809301200Z"
        ORGANIZATION  "Newbridge Networks Corporation"
        CONTACT-INFO
                  "Newbridge Networks Corporation
                   Postal: 600 March Road
                   Kanata, Ontario
                   Canada K2K 2E6
 
                   Phone:  +1 613 591 3600
                   Fax:    +1 613 591 3680"
 
        DESCRIPTION   "This module contains definitions for SDSL Ports Stats."
 
  ::= { nncExtensions 64 }


------------------------------------------------------------------------

    nncSdslStatisticsObjects    OBJECT IDENTIFIER ::= { nncSdslStatistics 1 }

------------------------------------------------------------------------

        --
        -- PHYSICAL LINE STATUS TABLE
        --
        nncSdslLineStatusTable    OBJECT-TYPE
            SYNTAX                SEQUENCE OF NncSdslLineStatusEntry
            MAX-ACCESS            not-accessible
            STATUS                current
            DESCRIPTION
                "Table that contains the Status of all SDSL Lines."
        ::= { nncSdslStatisticsObjects 1 }

        nncSdslLineStatusEntry    OBJECT-TYPE
            SYNTAX                NncSdslLineStatusEntry
            MAX-ACCESS            not-accessible
            STATUS                current
            DESCRIPTION           "The Status of an SDSL Line."
            INDEX                 { ifIndex }
        ::= { nncSdslLineStatusTable 1 }

        NncSdslLineStatusEntry ::=
            SEQUENCE {
                nncSdslLineStatus    INTEGER
            }

            nncSdslLineStatus    OBJECT-TYPE
                SYNTAX           INTEGER(1..34)
                MAX-ACCESS       read-only
                STATUS           current
                DESCRIPTION
                    "Status indicates current state of the line.

                    Unknown                             0
                    Operational                         1
                    Near End Loss Of Cell Delineation   2
                    Near End Loss Of Signal             3
                    Near End Loss Of Power              34"
            ::= { nncSdslLineStatusEntry 1 }


        --
        -- NEAR END RAW COUNTERS TABLE
        --
        nncSdslNearEndRawTable    OBJECT-TYPE
            SYNTAX                SEQUENCE OF NncSdslNearEndRawEntry
            MAX-ACCESS            not-accessible
            STATUS                current
            DESCRIPTION
	        "Table that contains the Near End RAW Stats of all SDSL Ports."
        ::= { nncSdslStatisticsObjects 2 }

        nncSdslNearEndRawEntry    OBJECT-TYPE
            SYNTAX                NncSdslNearEndRawEntry
            MAX-ACCESS            not-accessible
            STATUS                current
            DESCRIPTION           "The Near End Raw Stats of an SDSL Port."
            INDEX                 { ifIndex }
        ::= { nncSdslNearEndRawTable 1 }

        NncSdslNearEndRawEntry ::=
            SEQUENCE {
                nncSdslNearEndRawLOS      Counter32,
                nncSdslNearEndRawLowNM    Counter32,
                nncSdslNearEndRawLPR      Counter32,
                nncSdslNearEndRawLOCD     Counter32,
                nncSdslNearEndRawCRCError Counter32
            }

            nncSdslNearEndRawLOS    OBJECT-TYPE
                SYNTAX              Counter32
                MAX-ACCESS          read-only
                STATUS              current
                DESCRIPTION
                    "Count of the number of Loss of Signal failures since
                     system reset."
            ::= { nncSdslNearEndRawEntry 1 }

            nncSdslNearEndRawLowNM    OBJECT-TYPE
                SYNTAX                Counter32
                MAX-ACCESS            read-only
                STATUS                current
                DESCRIPTION
                    "Count of the number of Low Noise Margin failures since
                     system reset."
            ::= { nncSdslNearEndRawEntry 2 }

            nncSdslNearEndRawLPR    OBJECT-TYPE
                SYNTAX              Counter32
                MAX-ACCESS          read-only
                STATUS              current
                DESCRIPTION
                    "Count of the number of Loss of Power failures since
                     system reset."
            ::= { nncSdslNearEndRawEntry 3 }

            nncSdslNearEndRawLOCD    OBJECT-TYPE
                SYNTAX               Counter32
                MAX-ACCESS           read-only
                STATUS               current
                DESCRIPTION
                    "Count of the number of Loss of Cell Delineation failures
                     since system reset."
            ::= { nncSdslNearEndRawEntry 4 }

            nncSdslNearEndRawCRCError OBJECT-TYPE
                SYNTAX               Counter32
                MAX-ACCESS           read-only
                STATUS               current
                DESCRIPTION
                    "Count of the number of CRC Errors since system reset."
            ::= { nncSdslNearEndRawEntry 5 }

        --
        -- NEAR END 15 MINUTES CURRENT COUNTERS TABLE
        --
        nncSdslNearEndCurr15MinTable    OBJECT-TYPE
            SYNTAX                      SEQUENCE OF NncSdslNearEndCurr15MinEntry
            MAX-ACCESS                  not-accessible
            STATUS                      current
            DESCRIPTION
	        "Table that contains the Near End 15 minutes current Stats
		 of all SDSL Ports."
        ::= { nncSdslStatisticsObjects 3 }

        nncSdslNearEndCurr15MinEntry    OBJECT-TYPE
            SYNTAX                      NncSdslNearEndCurr15MinEntry
            MAX-ACCESS                  not-accessible
            STATUS                      current
            DESCRIPTION                 "The Near End 15 minutes current Stats 
	                                 of an SDSL Port."
            INDEX                       { ifIndex }
        ::= { nncSdslNearEndCurr15MinTable 1 }

        NncSdslNearEndCurr15MinEntry ::=
            SEQUENCE {
                nncSdslNearEndCurr15MinTimeElapsed    Gauge32,
                nncSdslNearEndCurr15MinLOSS           Gauge32,
                nncSdslNearEndCurr15MinLOSWS          Gauge32,
                nncSdslNearEndCurr15MinLowNMS         Gauge32,
                nncSdslNearEndCurr15MinLPRS           Gauge32,
                nncSdslNearEndCurr15MinErrS           Gauge32
            }

            nncSdslNearEndCurr15MinTimeElapsed    OBJECT-TYPE
                SYNTAX                            Gauge32(0..900)
                UNITS                             "seconds"
                MAX-ACCESS                        read-only
                STATUS                            current
                DESCRIPTION
                    "Total elapsed seconds in this interval.
                     A full interval is 900 seconds."
            ::= { nncSdslNearEndCurr15MinEntry 1 }

            nncSdslNearEndCurr15MinLOSS    OBJECT-TYPE
                SYNTAX                     Gauge32
                MAX-ACCESS                 read-only
                STATUS                     current
                DESCRIPTION
                    "Count of the number of seconds in Loss of Signal status
                     not due to a Loss of Power in the current 15 minutes
                     interval."
            ::= { nncSdslNearEndCurr15MinEntry 2 }

            nncSdslNearEndCurr15MinLOSWS    OBJECT-TYPE
                SYNTAX                      Gauge32
                MAX-ACCESS                  read-only
                STATUS                      current
                DESCRIPTION
                    "Count of the number of seconds in Loss of Synch Word
                     status not followed by a Loss of Signal in the current
                     15 minutes interval."
            ::= { nncSdslNearEndCurr15MinEntry 3 }

            nncSdslNearEndCurr15MinLowNMS    OBJECT-TYPE
                SYNTAX                       Gauge32
                MAX-ACCESS                   read-only
                STATUS                       current
                DESCRIPTION
                    "Count of the number of seconds in Low Noise Margin
                     status in the current 15 minutes interval."
            ::= { nncSdslNearEndCurr15MinEntry 4 }

            nncSdslNearEndCurr15MinLPRS    OBJECT-TYPE
                SYNTAX                     Gauge32
                MAX-ACCESS                 read-only
                STATUS                     current
                DESCRIPTION
                    "Count of the number of seconds in Loss of Power status
                     in the current 15 minutes interval."
            ::= { nncSdslNearEndCurr15MinEntry 5 }

            nncSdslNearEndCurr15MinErrS    OBJECT-TYPE
                SYNTAX                     Gauge32
                MAX-ACCESS                 read-only
                STATUS                     current
                DESCRIPTION
                    "Count of Errored Seconds in the current 15 minutes
                     interval. The errored second parameter is a count of
                     one-second intervals containing one or more of the
                     anomolies or defects previously defined."
            ::= { nncSdslNearEndCurr15MinEntry 6 }


        --
        -- NEAR END 1 DAY CURRENT COUNTERS TABLE
        --
        nncSdslNearEndCurr1DayTable    OBJECT-TYPE
            SYNTAX                     SEQUENCE OF NncSdslNearEndCurr1DayEntry
            MAX-ACCESS                 not-accessible
            STATUS                     current
            DESCRIPTION
	        "Table that contains the Near End 1 Day current Stats
		 of all SDSL Ports."
        ::= { nncSdslStatisticsObjects 4 }

        nncSdslNearEndCurr1DayEntry    OBJECT-TYPE
            SYNTAX                     NncSdslNearEndCurr1DayEntry
            MAX-ACCESS                 not-accessible
            STATUS                     current
            DESCRIPTION                "The Near End 1 Day current Stats 
	                                of an SDSL Port."
            INDEX                      { ifIndex }
        ::= { nncSdslNearEndCurr1DayTable 1 }

        NncSdslNearEndCurr1DayEntry ::=
            SEQUENCE {
                nncSdslNearEndCurr1DayTimeElapsed     Gauge32,
                nncSdslNearEndCurr1DayLOSS            Gauge32,
                nncSdslNearEndCurr1DayLOSWS           Gauge32,
                nncSdslNearEndCurr1DayLowNMS          Gauge32,
                nncSdslNearEndCurr1DayLPRS            Gauge32,
                nncSdslNearEndCurr1DayErrS            Gauge32
            }
	    
            nncSdslNearEndCurr1DayTimeElapsed    OBJECT-TYPE
                SYNTAX                           Gauge32
                UNITS                            "seconds"
                MAX-ACCESS                       read-only
                STATUS                           current
                DESCRIPTION
                    "Number of seconds that have elapses since the beginning
                     of the current 1 Day interval."
            ::= { nncSdslNearEndCurr1DayEntry 1 }

            nncSdslNearEndCurr1DayLOSS    OBJECT-TYPE
                SYNTAX                    Gauge32
                MAX-ACCESS                read-only
                STATUS                    current
                DESCRIPTION
                    "Count of the number of seconds in Loss of Signal status
                     not due to a Loss of Power during the current day."
            ::= { nncSdslNearEndCurr1DayEntry 2 }

            nncSdslNearEndCurr1DayLOSWS    OBJECT-TYPE
                SYNTAX                     Gauge32
                MAX-ACCESS                 read-only
                STATUS                     current
                DESCRIPTION
                    "Count of the number of seconds in Loss of Synch Word
                     status not followed by a Loss of Signal during the
                     current day."
            ::= { nncSdslNearEndCurr1DayEntry 3 }

            nncSdslNearEndCurr1DayLowNMS    OBJECT-TYPE
                SYNTAX                      Gauge32
                MAX-ACCESS                  read-only
                STATUS                      current
                DESCRIPTION
                    "Count of the number of seconds in Low Noise Margin
                     status during the current day."
            ::= { nncSdslNearEndCurr1DayEntry 4 }

            nncSdslNearEndCurr1DayLPRS    OBJECT-TYPE
                SYNTAX                    Gauge32
                MAX-ACCESS                read-only
                STATUS                    current
                DESCRIPTION
                    "Count of the number of seconds in Loss of Power status
                     during the current day."
            ::= { nncSdslNearEndCurr1DayEntry 5 }

            nncSdslNearEndCurr1DayErrS    OBJECT-TYPE
                SYNTAX                    Gauge32
                MAX-ACCESS                read-only
                STATUS                    current
                DESCRIPTION
                    "Count of Errored Seconds during the current day.
                     The errored second parameter is a count of one-second
                     intervals containing one or more of the anomolies or
                     defects previously defined."
            ::= { nncSdslNearEndCurr1DayEntry 6 }


        --
        -- NEAR END 1 DAY PREVIOUS COUNTERS TABLE
        --
        nncSdslNearEndPrev1DayTable    OBJECT-TYPE
            SYNTAX                     SEQUENCE OF NncSdslNearEndPrev1DayEntry
            MAX-ACCESS                 not-accessible
            STATUS                     current
            DESCRIPTION
	        "Table that contains the Near End 1 DAY PREVIOUS Stats
		 of all SDSL Ports."
        ::= { nncSdslStatisticsObjects 5 }

        nncSdslNearEndPrev1DayEntry    OBJECT-TYPE
            SYNTAX                     NncSdslNearEndPrev1DayEntry
            MAX-ACCESS                 not-accessible
            STATUS                     current
            DESCRIPTION                "The Near End 1 Day PREVIOUS Stats 
	                                of an SDSL Port."
            INDEX                      { ifIndex }
        ::= { nncSdslNearEndPrev1DayTable 1 }

        NncSdslNearEndPrev1DayEntry ::=
            SEQUENCE {
                nncSdslNearEndPrev1DayMoniSecs     Gauge32,
                nncSdslNearEndPrev1DayLOSS         Gauge32,
                nncSdslNearEndPrev1DayLOSWS        Gauge32,
                nncSdslNearEndPrev1DayLowNMS       Gauge32,
                nncSdslNearEndPrev1DayLPRS         Gauge32,
                nncSdslNearEndPrev1DayErrS         Gauge32,
                nncSdslNearEndPrev1DayValidData    TruthValue
            }

            nncSdslNearEndPrev1DayMoniSecs    OBJECT-TYPE
                SYNTAX                        Gauge32
                UNITS                         "seconds"
                MAX-ACCESS                    read-only
                STATUS                        current
                DESCRIPTION
                    "The time in the PREVIOUS 1-day interval over which
                     the performance monitoring information is actually 
                     counted. This value will normally be the same as the 
                     total interval duration except in a situation where 
                     performance monitoring information can not be collected 
                     for any reason.  Typically Elapsed 1-day Time will be 
                     copied into Monitored Seconds when the 1-day roll-over 
                     occurs."
            ::= { nncSdslNearEndPrev1DayEntry 1 }

            nncSdslNearEndPrev1DayLOSS    OBJECT-TYPE
                SYNTAX                    Gauge32
                MAX-ACCESS                read-only
                STATUS                    current
                DESCRIPTION
                    "Count of the number of seconds in Loss of Signal status
                     not due to a Loss of Power within the most recent
                     PREVIOUS 1 day period."
            ::= { nncSdslNearEndPrev1DayEntry 2 }

            nncSdslNearEndPrev1DayLOSWS    OBJECT-TYPE
                SYNTAX                     Gauge32
                MAX-ACCESS                 read-only
                STATUS                     current
                DESCRIPTION
                    "Count of the number of seconds in Loss of Synch Word
                     status not followed by a Loss of Signal within the most
                     recent PREVIOUS 1 day period."
            ::= { nncSdslNearEndPrev1DayEntry 3 }

            nncSdslNearEndPrev1DayLowNMS    OBJECT-TYPE
                SYNTAX                      Gauge32
                MAX-ACCESS                  read-only
                STATUS                      current
                DESCRIPTION
                    "Count of the number of seconds in Low Noise Margin
                     status within the most recent PREVIOUS 1 day period."
            ::= { nncSdslNearEndPrev1DayEntry 4 }

            nncSdslNearEndPrev1DayLPRS    OBJECT-TYPE
                SYNTAX                    Gauge32
                MAX-ACCESS                read-only
                STATUS                    current
                DESCRIPTION
                    "Count of the number of seconds in Loss of Power status
                     within the most recent PREVIOUS 1 day period."
            ::= { nncSdslNearEndPrev1DayEntry 5 }

            nncSdslNearEndPrev1DayErrS    OBJECT-TYPE
                SYNTAX                    Gauge32
                MAX-ACCESS                read-only
                STATUS                    current
                DESCRIPTION
                    "Count of Errored Seconds within the most recent PREVIOUS
                     1 day period.
                     The errored second parameter is a count of one-second
                     intervals containing one or more of the anomolies or
                     defects previously defined."
            ::= { nncSdslNearEndPrev1DayEntry 6 }

            nncSdslNearEndPrev1DayValidData    OBJECT-TYPE
                SYNTAX                         TruthValue
                MAX-ACCESS                     read-only
                STATUS                         current
                DESCRIPTION
                    "This variable indicates if there is valid data
                     for this interval."
            ::= { nncSdslNearEndPrev1DayEntry 7 }


        --
        -- ALL FAR END COUNTERS TABLE
        --
        nncSdslFarEndAllTable    OBJECT-TYPE
            SYNTAX               SEQUENCE OF NncSdslFarEndAllEntry
            MAX-ACCESS           not-accessible
            STATUS               current
            DESCRIPTION
	        "Table that contains ALL the Far End Stats
		 of all SDSL Ports."
        ::= { nncSdslStatisticsObjects 6 }

        nncSdslFarEndAllEntry    OBJECT-TYPE
            SYNTAX               NncSdslFarEndAllEntry
            MAX-ACCESS           not-accessible
            STATUS               current
            DESCRIPTION          "ALL the Far End Stats of an SDSL Port."
            INDEX                { ifIndex }
        ::= { nncSdslFarEndAllTable 1 }

        NncSdslFarEndAllEntry ::=
            SEQUENCE {
                nncSdslFarEndRawLOCD                 Counter32,
                nncSdslFarEndCurr15MinTimeElapsed    Gauge32,
                nncSdslFarEndCurr15MinErrS           Gauge32,
                nncSdslFarEndCurr1DayTimeElapsed     Gauge32,
                nncSdslFarEndCurr1DayErrS            Gauge32,
                nncSdslFarEndPrev1DayMoniSecs        Gauge32,
                nncSdslFarEndPrev1DayErrS            Gauge32,
                nncSdslFarEndPrev1DayValidData       TruthValue
            }

            -- RAW COUNTERS
            --
            nncSdslFarEndRawLOCD    OBJECT-TYPE
                SYNTAX              Counter32
                MAX-ACCESS          read-only
                STATUS              current
                DESCRIPTION
                    "Count of the number of Loss of Cell Delineation failures
                     since system reset."
            ::= { nncSdslFarEndAllEntry 1 }

            -- 15 MIN CURRENT COUNTERS
            --
            nncSdslFarEndCurr15MinTimeElapsed    OBJECT-TYPE
                SYNTAX                           Gauge32(0..900)
                UNITS                            "seconds"
                MAX-ACCESS                       read-only
                STATUS                           current
                DESCRIPTION
                    "Total elapsed seconds in this interval.
                     A full interval is 900 seconds."
            ::= { nncSdslFarEndAllEntry 2 }

            nncSdslFarEndCurr15MinErrS    OBJECT-TYPE
                SYNTAX                    Gauge32
                MAX-ACCESS                read-only
                STATUS                    current
                DESCRIPTION
                    "Count of Errored Seconds in the current 15 minutes
                     interval.  
                     The errored second parameter is a count of one-second
                     intervals containing one or more of the anomolies or
                     defects previously defined."
            ::= { nncSdslFarEndAllEntry 3 }

            -- 1 DAY CURRENT COUNTERS
            --
            nncSdslFarEndCurr1DayTimeElapsed    OBJECT-TYPE
                SYNTAX                          Gauge32
                UNITS                           "seconds"
                MAX-ACCESS                      read-only
                STATUS                          current
                DESCRIPTION
                    "Number of seconds that have elapses since the beginning
                     of the current 1 Day interval."
            ::= { nncSdslFarEndAllEntry 4 }

            nncSdslFarEndCurr1DayErrS    OBJECT-TYPE
                SYNTAX                   Gauge32
                MAX-ACCESS               read-only
                STATUS                   current
                DESCRIPTION
                    "Count of Errored Seconds in the current 15 minutes
                     interval.  
                     The errored second parameter is a count of one-second
                     intervals containing one or more of the anomolies or
                     defects previously defined."
            ::= { nncSdslFarEndAllEntry 5 }

            -- 1 DAY PREVIOUS COUNTERS
            --
            nncSdslFarEndPrev1DayMoniSecs    OBJECT-TYPE
                SYNTAX                       Gauge32
                UNITS                        "seconds"
                MAX-ACCESS                   read-only
                STATUS                       current
                DESCRIPTION
                    "The time in the PREVIOUS 1-day interval over which
                     the performance monitoring information is actually
                     counted. This value will normally be the same as the
                     total interval duration except in a situation where
                     performance monitoring information can not be collected
                     for any reason.  Typically Elapsed 1-day Time will be
                     copied into Monitored Seconds when the 1-day roll-over
                     occurs."
            ::= { nncSdslFarEndAllEntry 6 }

            nncSdslFarEndPrev1DayErrS    OBJECT-TYPE
                SYNTAX                   Gauge32
                MAX-ACCESS               read-only
                STATUS                   current
                DESCRIPTION
                    "Count of Errored Seconds within the most recent
                     PREVIOUS 1 day period.
                     The errored second parameter is a count of one-second
                     intervals containing one or more of the anomolies or
                     defects previously defined."
            ::= { nncSdslFarEndAllEntry 7 }

            nncSdslFarEndPrev1DayValidData    OBJECT-TYPE
                SYNTAX                        TruthValue
                MAX-ACCESS                    read-only
                STATUS                        current
                DESCRIPTION
                    "This variable indicates if there is valid data
                     for this interval."
            ::= { nncSdslFarEndAllEntry 8 }


        --
        -- NEAR END INTERVALS COUNTERS TABLE
        --
        nncSdslNearEndIntTable    OBJECT-TYPE
            SYNTAX                SEQUENCE OF NncSdslNearEndIntEntry
            MAX-ACCESS            not-accessible
            STATUS                current
            DESCRIPTION
	        "Table that contains the Near End 15 Minutes Intervals Stats
		 of all SDSL Ports."
        ::= { nncSdslStatisticsObjects 7 }

        nncSdslNearEndIntEntry    OBJECT-TYPE
            SYNTAX                NncSdslNearEndIntEntry
            MAX-ACCESS            not-accessible
            STATUS                current
            DESCRIPTION           "One interval of Near End Stats
	                           of an SDSL Port."
            INDEX                 { ifIndex, nncSdslNearEndIntNumber }
        ::= { nncSdslNearEndIntTable 1 }

        NncSdslNearEndIntEntry ::=
            SEQUENCE {
                nncSdslNearEndIntNumber       INTEGER,
                nncSdslNearEndIntLOSS         Gauge32,
                nncSdslNearEndIntLOSWS        Gauge32,
                nncSdslNearEndIntLowNMS       Gauge32,
                nncSdslNearEndIntLPRS         Gauge32,
                nncSdslNearEndIntErrS         Gauge32,
                nncSdslNearEndIntValidData    TruthValue
            }

            nncSdslNearEndIntNumber OBJECT-TYPE
                SYNTAX      INTEGER(1..96)
                MAX-ACCESS  not-accessible
                STATUS      current
                DESCRIPTION
                    "Performance Data Interval number.  1 is the
                    the most recent interval; interval 96 is 24
                    hours ago.  Interval 2..96 are optional."
            ::= { nncSdslNearEndIntEntry 1 }
 
            nncSdslNearEndIntLOSS    OBJECT-TYPE
                SYNTAX               Gauge32
                MAX-ACCESS           read-only
                STATUS               current
                DESCRIPTION
                    "Count of seconds in the interval when there was
                     Loss of Signal not due to a Loss of Power."
            ::= { nncSdslNearEndIntEntry 2 }

            nncSdslNearEndIntLOSWS    OBJECT-TYPE
                SYNTAX                Gauge32
                MAX-ACCESS            read-only
                STATUS                current
                DESCRIPTION
                    "Count of seconds in the interval when there was
                     Loss of Signal not folloew by Loss of Signal."
            ::= { nncSdslNearEndIntEntry 3 }

            nncSdslNearEndIntLowNMS    OBJECT-TYPE
                SYNTAX                 Gauge32
                MAX-ACCESS             read-only
                STATUS                 current
                DESCRIPTION
                    "Count of seconds in the interval when there was
                     Low Noise Margin."
            ::= { nncSdslNearEndIntEntry 4 }

            nncSdslNearEndIntLPRS    OBJECT-TYPE
                SYNTAX               Gauge32
                MAX-ACCESS           read-only
                STATUS               current
                DESCRIPTION
                    "Count of seconds in the interval when there was
                     Loss of Power."
            ::= { nncSdslNearEndIntEntry 5 }

            nncSdslNearEndIntErrS    OBJECT-TYPE
                SYNTAX               Gauge32
                MAX-ACCESS           read-only
                STATUS               current
                DESCRIPTION
                    "Count of Errored Seconds in the interval.
                     The errored second parameter is a count of one-second
                     intervals containing one or more of the anomolies or
                     defects previously defined."
            ::= { nncSdslNearEndIntEntry 6 }

            nncSdslNearEndIntValidData    OBJECT-TYPE
                SYNTAX                    TruthValue
                MAX-ACCESS                read-only
                STATUS                    current
                DESCRIPTION
                    "This variable indicates if there is valid data
                     for this interval."
            ::= { nncSdslNearEndIntEntry 7 }


        --
        -- FAR END INTERVALS COUNTERS TABLE
        --
        nncSdslFarEndIntTable    OBJECT-TYPE
            SYNTAX               SEQUENCE OF NncSdslFarEndIntEntry
            MAX-ACCESS           not-accessible
            STATUS               current
            DESCRIPTION
	        "Table that contains the Far End 15 Minutes Intervals Stats
		 of all SDSL Ports."
        ::= { nncSdslStatisticsObjects 8 }

        nncSdslFarEndIntEntry    OBJECT-TYPE
            SYNTAX               NncSdslFarEndIntEntry
            MAX-ACCESS           not-accessible
            STATUS               current
            DESCRIPTION          "One interval of Far End Stats
	                          of an SDSL Port."
            INDEX                { ifIndex, nncSdslFarEndIntNumber }
        ::= { nncSdslFarEndIntTable 1 }

        NncSdslFarEndIntEntry ::=
            SEQUENCE {
                nncSdslFarEndIntNumber       INTEGER,
                nncSdslFarEndIntErrS         Gauge32,
                nncSdslFarEndIntValidData    TruthValue
            }

            nncSdslFarEndIntNumber OBJECT-TYPE
                SYNTAX      INTEGER(1..96)
                MAX-ACCESS  not-accessible
                STATUS      current
                DESCRIPTION
                    "Performance Data Interval number.  1 is the
                    the most recent interval; interval 96 is 24
                    hours ago.  Interval 2..96 are optional."
            ::= { nncSdslFarEndIntEntry 1 }
 
            nncSdslFarEndIntErrS    OBJECT-TYPE
                SYNTAX              Gauge32
                MAX-ACCESS          read-only
                STATUS              current
                DESCRIPTION
                    "Count of Errored Seconds in the interval.
                     The errored second parameter is a count of one-second
                     intervals containing one or more of the anomolies or
                     defects previously defined."
            ::= { nncSdslFarEndIntEntry 2 }

            nncSdslFarEndIntValidData    OBJECT-TYPE
                SYNTAX                   TruthValue
                MAX-ACCESS               read-only
                STATUS                   current
                DESCRIPTION
                    "This variable indicates if there is valid data
                     for this interval."
            ::= { nncSdslFarEndIntEntry 3 }


-------------------------------------------------------------------------------
--      Review Minutes 
-------------------------------------------------------------------------------
--      MINUTES-BEGIN
--              REVIEW-DATE  "1998.09.29"
--              BODY  "
--
--      
--      TO:     Randy JONES, Karl TOOMPU, Chuong NGO and Francis OUATON,
--              Fabrice GIL
--      FROM:   Fred MAYMIL
--
--      A message was sent out on 1998.09.17 to electronically review
--      SdslStats.mib.
--
--      Outcome:
--
--      It was the consensus of the review team that this file is 
--      acceptable with the few indicated modifications
--      (note that the low number of comment is greatly due to the fact
--       that this SDSL Mib comes partially from the SDSL Mib defined by
--       the ADSL Forum)
--
--      Actions:
--      A1 -    Fred MAYMIL to update the file as indicated in Comments below.  
--              Response:                       Status: completed
--
--      Comments:
--      1) -    Misuse of the word "Card" instead of Port in some comments.
--      2) -    Use "Far End" and "Near End" instead of "Atuc" and "Atur" 
--              inherited from ASDL Mib in almost all object names.
--      3) -    Split second Table "nncSdslNearEndTable" too big for SNMP v1 
--              in 4 smaller Tables "Raw", "Curr15Min", "Curr1Day", "Prev1Day".
--      4) -    Add "nnc" prefix to each object name to emphasize the fact that
--              this Mib is a Newbridge Private Mib.
-- 
--      "
--
--      END-MINUTES
--
--
--      MINUTES-BEGIN
--              REVIEW-DATE  "1999.07.07"
--              BODY  "
--
--      
--      TO:     Jeffrey B.KENNEY and Fred MAYMIL,
--              Fabrice GIL
--      FROM:   Gil BUZULIER
--
--      A message was sent out on 1999.07.07 to electronically review
--      SdslStats.mib.
--
--      Outcome:
--
--      It was the consensus of the review team that this file is 
--      acceptable with the few indicated modifications
--
--      Actions:
--      A1 -    Gil Buzulier to update the file as indicated in Comments below.  
--              Response:                       Status: completed
--
--      Comments:
--      1) -    modify comments to take into account the last state of 
--		nncSdslLineStatus counter.
--      2) -    Add nncSdslFarEndIntNumber and nncSdslNearEndIntNumber
--		counters to resolve an error of compilation. 
--      3) -    Add nncSdslNearEndRawCRCError counter in the nncSdslNearEndRawTable.
-- 
--      "
--
--      END-MINUTES
-------------------------------------------------------------------------------


END
