ACC-CALLEDNUMBER DEFINITIONS ::= BEGIN

    IMPORTS
 	       OBJECT-TYPE FROM RFC1155-SMI
			 accTrapLogSeqNum FROM ACC-SYSTEM
	accBRG, DisplayString, RowStatus, IfIndex, SmdsAddress
             FROM ACC-MIB;

-- Called Number Group
    accCalledNumber OBJECT IDENTIFIER ::= { accBRG 66 }
	-- The Called Number Table Group
	-- A table of called party numbers which map a given called
	-- party number and bearer type into a service profile name.
	accCalledNumberTable OBJECT-TYPE
	    SYNTAX SEQUENCE OF AccCalledNumberEntry
	    ACCESS not-accessible
	    STATUS mandatory
	    DESCRIPTION
	       "The Called Number Table"
	    ::= { accCalledNumber 1 }
	accCalledNumberEntry OBJECT-TYPE
	    SYNTAX AccCalledNumberEntry
	    ACCESS not-accessible
	    STATUS mandatory
	    DESCRIPTION
	       "An entry in the Called Number Table"
	    INDEX  { accCalledNumberGroup }
	    ::= { accCalledNumberTable 1 }
	AccCalledNumberEntry ::= SEQUENCE {
	    accCalledNumberGroup        INTEGER,
	    accCalledNumberType         INTEGER,
	    accCalledNumberDigits       DisplayString,
	    accCalledNumberServProfile  DisplayString,
	    accCalledNumberStatus       INTEGER,
	    accCalledNumberAction       INTEGER,
	    accCalledNumberEgressInfc   INTEGER,
	    accCalledNumberEgressType   INTEGER,
	    accCalledNumberEgressNumber OCTET STRING
	}
	accCalledNumberGroup OBJECT-TYPE
	    SYNTAX INTEGER (1..127)
	    ACCESS read-only
	    STATUS mandatory
	    DESCRIPTION
	       "The index of a number group defined in the Called Number 
	        Table.  A number group is a set directory numbers and 
	        bearer types assigned to an interface by the telephone 
	        company."
	    ::= { accCalledNumberEntry 1 }
	accCalledNumberType OBJECT-TYPE
	    SYNTAX INTEGER {
		cm56(1),
		cm64(2),
		udi(3),
		rdi(4),
		data(7),
		voice(8),
		audio(16),
		modem(24),
		any(31)
	    }
	    ACCESS read-only
	    STATUS mandatory
	    DESCRIPTION
	       "The bearer types supported for this called number.  Used 
	        for matching an entry in the Called Number Table with the 
	        bearer capabilites of a switched connection.  This object is 
	        treated as a bit mask."
	    ::= { accCalledNumberEntry 2 }
	accCalledNumberDigits OBJECT-TYPE
	    SYNTAX DisplayString -- (SIZE (0..16))
	    ACCESS read-only
	    STATUS mandatory
	    DESCRIPTION
	       "The string of digits comprising the directory number.  A 
	        null directory number is allowed which matches any called 
	        number."
	    ::= { accCalledNumberEntry 3 }
	accCalledNumberServProfile OBJECT-TYPE
	    SYNTAX DisplayString -- (SIZE (0..16))
	    ACCESS read-write
	    STATUS mandatory
	    DESCRIPTION
	       "The name of a service profile defined in the Service Profile 
	        Table.  If no service profile is configured, a profile with the 
	        name DEFAULT will be used instead."
	    ::= { accCalledNumberEntry 4 }
	accCalledNumberStatus OBJECT-TYPE
	    SYNTAX INTEGER {
		add(1),
		delete(2)
	    }
	    ACCESS read-write
	    STATUS mandatory
	    DESCRIPTION
	       "The status of this entry"
	    ::= { accCalledNumberEntry 5 }
	accCalledNumberAction OBJECT-TYPE
	    SYNTAX INTEGER {
		accept (1),
		reject (2),
		switch (3)
	    }
	    ACCESS read-write
	    STATUS mandatory
	    DESCRIPTION
	    " Action to take with the call "
	    ::= { accCalledNumberEntry 7 }
	accCalledNumberEgressInfc OBJECT-TYPE
	    SYNTAX INTEGER
	    ACCESS read-write
	    STATUS mandatory
	    DESCRIPTION
	    " Egress interface for switched calls "
	    ::= { accCalledNumberEntry 8 }
	accCalledNumberEgressType OBJECT-TYPE
	    SYNTAX INTEGER {
		cm64 (1),
		cm56 (2),
		udi (3),
		rdi (4),
		v-110 (5),
		data (7),
		voice (8),
		audio (16),
		modem (24),
		any (31)
	    }
	    ACCESS read-write
	    STATUS mandatory
	    DESCRIPTION
	    " Call type for egress call of a switched call "
	    ::= { accCalledNumberEntry 9 }
	accCalledNumberEgressNumber OBJECT-TYPE
	    SYNTAX OCTET STRING
	    ACCESS read-write
	    STATUS mandatory
	    DESCRIPTION
	    " Called number to use for egress call of switched call "
	    ::= { accCalledNumberEntry 10 }

END
