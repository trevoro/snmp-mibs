--
-- This SMIv2 module has been generated by smidump 0.2-cvs. Do not edit.
--

SONUS-SYSTEM-TIMING-MIB DEFINITIONS ::= BEGIN

IMPORTS
    Integer32, MODULE-IDENTITY, NOTIFICATION-TYPE, OBJECT-TYPE
        FROM SNMPv2-SMI
    DisplayString, RowStatus
        FROM SNMPv2-TC
    sonusEventClass, sonusEventDescription, sonusEventLevel, 
    sonusShelfIndex, sonusSlotIndex
        FROM SONUS-COMMON-MIB
    sonusSystemMIBs
        FROM SONUS-SMI
    HwTypeID, SonusAdminState, SonusEventString, SonusMtaSlotIndex, 
    SonusShelfIndex, SonusSlotIndex, SonusTimingSource
        FROM SONUS-TC;

sonusSystemTimingMIB MODULE-IDENTITY
    LAST-UPDATED    "200102030000Z"
    ORGANIZATION    
            "Sonus Networks, Inc."
    CONTACT-INFO    
            "   Customer Support    
             Sonus Networks, Inc,
             5 carlisle Road
             Westford, MA 01886
             USA
             
             Tel: 978-692-8999
             Fax: 978-392-9118
             E-mail: cs.snmp@sonusnet.com"
    DESCRIPTION     
            "The MIB Module for System Timing management."
    ::= { sonusSystemMIBs 3 }


sonusSystemTimingMIBObjects OBJECT IDENTIFIER
    ::= { sonusSystemTimingMIB 1 }

sonusStShelfAdmnTable OBJECT-TYPE
    SYNTAX          SEQUENCE OF SonusStShelfAdmnEntry
    MAX-ACCESS      not-accessible
    STATUS          current
    DESCRIPTION     
            "  "
    ::= { sonusSystemTimingMIBObjects 1 }

sonusStShelfAdmnEntry OBJECT-TYPE
    SYNTAX          SonusStShelfAdmnEntry
    MAX-ACCESS      not-accessible
    STATUS          current
    DESCRIPTION     
            "  "
    INDEX           { sonusStShelfAdmnShelfIndex }
    ::= { sonusStShelfAdmnTable 1 }

SonusStShelfAdmnEntry ::=
    SEQUENCE {
        sonusStShelfAdmnShelfIndex      SonusShelfIndex,
        sonusStShelfAdmnFailoverGuardTime Integer32,
        sonusStShelfAdmnRecoveryGuardTime Integer32,
        sonusStShelfAdmnTransmitRemoteAlarm   INTEGER,
        sonusStShelfAdmnRevertRefSwitching  INTEGER,
        sonusStShelfAdmnRevertMtaSwitching  INTEGER,
        sonusStShelfAdmnRevertInsertDelay Integer32,
        sonusStShelfAdmnFreeRunAlarm    INTEGER,
        sonusStShelfAdmnTimingSourceAction  INTEGER,
        sonusStShelfAdmnRowStatus       RowStatus,
        sonusStShelfAdmnSourceReconfigAlg INTEGER,
        sonusStShelfAdmnMtaSourceAffinity INTEGER
    }

sonusStShelfAdmnShelfIndex OBJECT-TYPE
    SYNTAX          SonusShelfIndex
    MAX-ACCESS      read-only
    STATUS          current
    DESCRIPTION     
            "Identifies the target shelf within the node."
    ::= { sonusStShelfAdmnEntry 1 }

sonusStShelfAdmnFailoverGuardTime OBJECT-TYPE
    SYNTAX          Integer32 (2..5)
    MAX-ACCESS      read-write
    STATUS          current
    DESCRIPTION     
            " Indicates how long a timing source can be faulting 
             before switchover to another source is initiated "
    DEFVAL          { 2 }
    ::= { sonusStShelfAdmnEntry 2 }

sonusStShelfAdmnRecoveryGuardTime OBJECT-TYPE
    SYNTAX          Integer32 (15..120)
    MAX-ACCESS      read-write
    STATUS          current
    DESCRIPTION     
            " Indicates how long a timing source must be valid for, after
             it has faulted, before it will be considered valid again. "
    DEFVAL          { 15 }
    ::= { sonusStShelfAdmnEntry 3 }

sonusStShelfAdmnTransmitRemoteAlarm OBJECT-TYPE
    SYNTAX          INTEGER { disabled(1), enabled(2) }
    MAX-ACCESS      read-write
    STATUS          current
    DESCRIPTION     
            " Not Supported "
    DEFVAL          { disabled }
    ::= { sonusStShelfAdmnEntry 4 }

sonusStShelfAdmnRevertRefSwitching OBJECT-TYPE
    SYNTAX          INTEGER { disabled(1), enabled(2) }
    MAX-ACCESS      read-write
    STATUS          current
    DESCRIPTION     
            " If enabled, then a timing source which has failed, but then 
             becomes valid again, will be reconsidered for use.
             	  If disabled, then once a timing source fails, it will never
                 be automatically reconsidered for use. To use the source again
             	  requires manual user intervention. "
    DEFVAL          { enabled }
    ::= { sonusStShelfAdmnEntry 5 }

sonusStShelfAdmnRevertMtaSwitching OBJECT-TYPE
    SYNTAX          INTEGER { disabled(1), enabled(2) }
    MAX-ACCESS      read-write
    STATUS          current
    DESCRIPTION     
            " If enabled, then an MTA which is hot-inserted will 
             automatically be brought on line and made available for use.
             If disabled, then an MTA which is hot-inserted will require
             manual user configuration before being available for use. "
    DEFVAL          { enabled }
    ::= { sonusStShelfAdmnEntry 6 }

sonusStShelfAdmnRevertInsertDelay OBJECT-TYPE
    SYNTAX          Integer32 (100..300)
    MAX-ACCESS      read-write
    STATUS          current
    DESCRIPTION     
            " MTA warm-up period. When an MTA is hot-inserted, the card 
             will be allowed to warm up and stabilize for this amount
             of time before being put back into service.
             
             This warm-up period is also used during cold start of a shelf. "
    DEFVAL          { 100 }
    ::= { sonusStShelfAdmnEntry 7 }

sonusStShelfAdmnFreeRunAlarm OBJECT-TYPE
    SYNTAX          INTEGER { disabled(1), enabled(2) }
    MAX-ACCESS      read-write
    STATUS          current
    DESCRIPTION     
            " Not Supported "
    DEFVAL          { disabled }
    ::= { sonusStShelfAdmnEntry 8 }

sonusStShelfAdmnTimingSourceAction OBJECT-TYPE
    SYNTAX          INTEGER { none(1), resequence(2) }
    MAX-ACCESS      read-write
    STATUS          current
    DESCRIPTION     
            " Resequence will cause the timing sequence list to be re-evaluated.
             This may cause the current active timing source to change. "
    DEFVAL          { none }
    ::= { sonusStShelfAdmnEntry 9 }

sonusStShelfAdmnRowStatus OBJECT-TYPE
    SYNTAX          RowStatus
    MAX-ACCESS      read-write
    STATUS          current
    DESCRIPTION     
            " This object indicates the row status for this table."
    ::= { sonusStShelfAdmnEntry 10 }

sonusStShelfAdmnSourceReconfigAlg OBJECT-TYPE
    SYNTAX          INTEGER { ordered-list(1), ssm-quality(2) }
    MAX-ACCESS      read-write
    STATUS          current
    DESCRIPTION     
            " This object indicates which algorithm should be used to select timing sources
             for use as System Synchronized sources. Selecting Ordered_list causes sources
             to be selected for use in strict numerical order, as assigned by default or by 
             the operator. Selecting SSM_Quality will cause sources to be selected based upon
             the quality level of the timing source, as indicated by the sources Synchronized
             Status Messages.
             
             Do not select SSM_Quality unless all configured timing sources support SSM's"
    DEFVAL          { ordered-list }
    ::= { sonusStShelfAdmnEntry 11 }

sonusStShelfAdmnMtaSourceAffinity OBJECT-TYPE
    SYNTAX          INTEGER { none(1), sticky(2) }
    MAX-ACCESS      read-write
    STATUS          current
    DESCRIPTION     
            " This object works in conjunction with the Source Reconfiguration Algorithm object. 
             If sticky is selected, System Timing Manager will exhaust oll timing sources on an
             MTA at all quality levels before selecting a timing source on the alternate MTA.
             If none is selected, timing sources will be chosen based on stratum quality only,
             reguardless of which MTA is providing the source.
             
             This object has no effect when the Source Reconfiguration Algorithm is set to Ordered_list."
    DEFVAL          { sticky }
    ::= { sonusStShelfAdmnEntry 12 }

sonusStShelfStatTable OBJECT-TYPE
    SYNTAX          SEQUENCE OF SonusStShelfStatEntry
    MAX-ACCESS      not-accessible
    STATUS          current
    DESCRIPTION     
            "  "
    ::= { sonusSystemTimingMIBObjects 2 }

sonusStShelfStatEntry OBJECT-TYPE
    SYNTAX          SonusStShelfStatEntry
    MAX-ACCESS      not-accessible
    STATUS          current
    DESCRIPTION     
            "  "
    INDEX           { sonusStShelfStatShelfIndex }
    ::= { sonusStShelfStatTable 1 }

SonusStShelfStatEntry ::=
    SEQUENCE {
        sonusStShelfStatShelfIndex      SonusShelfIndex,
        sonusStShelfStatActiveMtaSlot   SonusMtaSlotIndex,
        sonusStShelfStatActiveSource    SonusTimingSource
    }

sonusStShelfStatShelfIndex OBJECT-TYPE
    SYNTAX          SonusShelfIndex
    MAX-ACCESS      read-only
    STATUS          current
    DESCRIPTION     
            "  "
    ::= { sonusStShelfStatEntry 1 }

sonusStShelfStatActiveMtaSlot OBJECT-TYPE
    SYNTAX          SonusMtaSlotIndex
    MAX-ACCESS      read-only
    STATUS          current
    DESCRIPTION     
            " Identifies which MTA is providing the System Synchronized Timing signal."
    ::= { sonusStShelfStatEntry 2 }

sonusStShelfStatActiveSource OBJECT-TYPE
    SYNTAX          SonusTimingSource
    MAX-ACCESS      read-only
    STATUS          current
    DESCRIPTION     
            " Identifies what timing source the active MTA is 
             using to provide System Synchronized Timing."
    ::= { sonusStShelfStatEntry 3 }

sonusStMtaAdmnTable OBJECT-TYPE
    SYNTAX          SEQUENCE OF SonusStMtaAdmnEntry
    MAX-ACCESS      not-accessible
    STATUS          current
    DESCRIPTION     
            "  "
    ::= { sonusSystemTimingMIBObjects 3 }

sonusStMtaAdmnEntry OBJECT-TYPE
    SYNTAX          SonusStMtaAdmnEntry
    MAX-ACCESS      not-accessible
    STATUS          current
    DESCRIPTION     
            "  "
    INDEX           { sonusStMtaAdmnShelfIndex, 
                      sonusStMtaAdmnMtaSlotIndex }
    ::= { sonusStMtaAdmnTable 1 }

SonusStMtaAdmnEntry ::=
    SEQUENCE {
        sonusStMtaAdmnShelfIndex        SonusShelfIndex,
        sonusStMtaAdmnMtaSlotIndex      SonusMtaSlotIndex,
        sonusStMtaAdmnState             SonusAdminState,
        sonusStMtaAdmnLineEncoding      INTEGER,
        sonusStMtaAdmnSsmChannelBit     INTEGER,
        sonusStMtaAdmnFramerMode        INTEGER,
        sonusStMtaAdmnFramerTransmitYellowAlarm       INTEGER,
        sonusStMtaAdmnLiuTransmitAllOnes INTEGER,
        sonusStMtaAdmnAction            INTEGER,
        sonusStMtaAdmnRowStatus         RowStatus
    }

sonusStMtaAdmnShelfIndex OBJECT-TYPE
    SYNTAX          SonusShelfIndex
    MAX-ACCESS      read-only
    STATUS          current
    DESCRIPTION     
            " Identifies the target shelf within the node. "
    ::= { sonusStMtaAdmnEntry 1 }

sonusStMtaAdmnMtaSlotIndex OBJECT-TYPE
    SYNTAX          SonusMtaSlotIndex
    MAX-ACCESS      read-only
    STATUS          current
    DESCRIPTION     
            " Identifies the target slot within the shelf. "
    ::= { sonusStMtaAdmnEntry 2 }

sonusStMtaAdmnState OBJECT-TYPE
    SYNTAX          SonusAdminState
    MAX-ACCESS      read-write
    STATUS          current
    DESCRIPTION     
            " If enabled, the MTA can participate in system timing. 
             If disabled, then it will be removed from service and
             not allowed to participate. All timing sequence entries
             bound to this node will be marked as out of service.
             In a non-redundant configuration the MTA admin state 
             cannot be disabled. "
    DEFVAL          { enabled }
    ::= { sonusStMtaAdmnEntry 3 }

sonusStMtaAdmnLineEncoding OBJECT-TYPE
    SYNTAX          INTEGER { ami(1), b8zs(2), hdb3(3) }
    MAX-ACCESS      read-write
    STATUS          current
    DESCRIPTION     
            " Select AMI or B8ZS line coding for BITS LIU.
             
             Select HDB3 for SETS LIU"
    DEFVAL          { b8zs }
    ::= { sonusStMtaAdmnEntry 4 }

sonusStMtaAdmnSsmChannelBit OBJECT-TYPE
    SYNTAX          INTEGER { sa4(1), sa5(2), sa6(3), sa7(4), sa8(5) }
    MAX-ACCESS      read-write
    STATUS          current
    DESCRIPTION     
            " MTA 20, E1 support only. Identifies which of the additional spare 
             bits, embedded within the framing pattern, contains the SSM channel "
    DEFVAL          { 1 }
    ::= { sonusStMtaAdmnEntry 5 }

sonusStMtaAdmnFramerMode OBJECT-TYPE
    SYNTAX          INTEGER { d4sf(1), esf(2), mf(3), mf-crc4(4) }
    MAX-ACCESS      read-write
    STATUS          current
    DESCRIPTION     
            " Select ESF or D4/SF for BITS framer.
             ESF should be selected if B8ZS has been selected for the line encoding. 
             D4/SF should be selected if AMI has been selected for the line encoding. 
             
             Select MF or MF-CRC4 for SETS framer"
    DEFVAL          { esf }
    ::= { sonusStMtaAdmnEntry 6 }

sonusStMtaAdmnFramerTransmitYellowAlarm OBJECT-TYPE
    SYNTAX          INTEGER { disabled(1), enabled(2) }
    MAX-ACCESS      read-write
    STATUS          current
    DESCRIPTION     
            " Not supported "
    DEFVAL          { disabled }
    ::= { sonusStMtaAdmnEntry 7 }

sonusStMtaAdmnLiuTransmitAllOnes OBJECT-TYPE
    SYNTAX          INTEGER { disabled(1), enabled(2) }
    MAX-ACCESS      read-write
    STATUS          current
    DESCRIPTION     
            " Not supported "
    DEFVAL          { disabled }
    ::= { sonusStMtaAdmnEntry 8 }

sonusStMtaAdmnAction OBJECT-TYPE
    SYNTAX          INTEGER { none(1), available(2) }
    MAX-ACCESS      read-write
    STATUS          current
    DESCRIPTION     
            " Selecting AVAILABLE will cause the MTA to be moved from
             the Out-Of-Service state to the Available-For-Use state.
             
             This command is necessary to manually make an MTA available for use
             after it has failed, and revertive MTA switching is not enabled. 
             
             This may cause the current active timing source to change. "
    DEFVAL          { none }
    ::= { sonusStMtaAdmnEntry 9 }

sonusStMtaAdmnRowStatus OBJECT-TYPE
    SYNTAX          RowStatus
    MAX-ACCESS      read-write
    STATUS          current
    DESCRIPTION     
            "This object indicates the row status for this table."
    ::= { sonusStMtaAdmnEntry 10 }

sonusStMtaStatTable OBJECT-TYPE
    SYNTAX          SEQUENCE OF SonusStMtaStatEntry
    MAX-ACCESS      not-accessible
    STATUS          current
    DESCRIPTION     
            "  "
    ::= { sonusSystemTimingMIBObjects 4 }

sonusStMtaStatEntry OBJECT-TYPE
    SYNTAX          SonusStMtaStatEntry
    MAX-ACCESS      not-accessible
    STATUS          current
    DESCRIPTION     
            "  "
    INDEX           { sonusStMtaStatShelfIndex, 
                      sonusStMtaStatMtaSlotIndex }
    ::= { sonusStMtaStatTable 1 }

SonusStMtaStatEntry ::=
    SEQUENCE {
        sonusStMtaStatShelfIndex        SonusShelfIndex,
        sonusStMtaStatMtaSlotIndex      SonusMtaSlotIndex,
        sonusStMtaStatOperStat          INTEGER,
        sonusStMtaStatMtaHwDesc         DisplayString,
        sonusStMtaStatMtaHwType         HwTypeID,
        sonusStMtaStatMtaHwTypeRev      Integer32,
        sonusStMtaStatMtaSerialNum      DisplayString,
        sonusStMtaStatMtaPartNum        DisplayString
    }

sonusStMtaStatShelfIndex OBJECT-TYPE
    SYNTAX          SonusShelfIndex
    MAX-ACCESS      read-only
    STATUS          current
    DESCRIPTION     
            "  "
    ::= { sonusStMtaStatEntry 1 }

sonusStMtaStatMtaSlotIndex OBJECT-TYPE
    SYNTAX          SonusMtaSlotIndex
    MAX-ACCESS      read-only
    STATUS          current
    DESCRIPTION     
            "  "
    ::= { sonusStMtaStatEntry 2 }

sonusStMtaStatOperStat OBJECT-TYPE
    SYNTAX          INTEGER { notPresent(1), fault(2), warmupDelay(3), 
                        inService(4), outOfService(5), available(6) }
    MAX-ACCESS      read-only
    STATUS          current
    DESCRIPTION     
            " Indicates the operational status of the MTA"
    ::= { sonusStMtaStatEntry 3 }

sonusStMtaStatMtaHwDesc OBJECT-TYPE
    SYNTAX          DisplayString (SIZE(0..16))
    MAX-ACCESS      read-only
    STATUS          current
    DESCRIPTION     
            " Description of the MTA hardware in the form of 'hwtype_hwRev'. "
    ::= { sonusStMtaStatEntry 4 }

sonusStMtaStatMtaHwType OBJECT-TYPE
    SYNTAX          HwTypeID
    MAX-ACCESS      read-only
    STATUS          current
    DESCRIPTION     
            " Description of the MTA hardware Type only. Entry 5+6 obsolete entry 4."
    ::= { sonusStMtaStatEntry 5 }

sonusStMtaStatMtaHwTypeRev OBJECT-TYPE
    SYNTAX          Integer32
    MAX-ACCESS      read-only
    STATUS          current
    DESCRIPTION     
            " Description of the MTA hardware type revision. Entry 5+6 obsolete entry 4."
    ::= { sonusStMtaStatEntry 6 }

sonusStMtaStatMtaSerialNum OBJECT-TYPE
    SYNTAX          DisplayString (SIZE(1..10))
    MAX-ACCESS      read-only
    STATUS          current
    DESCRIPTION     
            " Identifies the serial number of the server module.  
             This is the serial number assigned to the mta module in manufacturing."
    ::= { sonusStMtaStatEntry 7 }

sonusStMtaStatMtaPartNum OBJECT-TYPE
    SYNTAX          DisplayString (SIZE(1..10))
    MAX-ACCESS      read-only
    STATUS          current
    DESCRIPTION     
            " Identifies the part number of the server module. 
             This is the part number assigned to the mta module in manufacturing."
    ::= { sonusStMtaStatEntry 8 }

sonusStTimingSourceTable OBJECT-TYPE
    SYNTAX          SEQUENCE OF SonusStTimingSourceEntry
    MAX-ACCESS      not-accessible
    STATUS          current
    DESCRIPTION     
            "  "
    ::= { sonusSystemTimingMIBObjects 5 }

sonusStTimingSourceEntry OBJECT-TYPE
    SYNTAX          SonusStTimingSourceEntry
    MAX-ACCESS      not-accessible
    STATUS          current
    DESCRIPTION     
            "  "
    INDEX           { sonusStTimingSourceShelfIndex, 
                      sonusStTimingSourceMtaSlotIndex, 
                      sonusStTimingSource }
    ::= { sonusStTimingSourceTable 1 }

SonusStTimingSourceEntry ::=
    SEQUENCE {
        sonusStTimingSourceShelfIndex   SonusShelfIndex,
        sonusStTimingSourceMtaSlotIndex Integer32,
        sonusStTimingSource             SonusTimingSource,
        sonusStTimingSourceState        SonusAdminState,
        sonusStTimingSourceSequenceNum  Integer32,
        sonusStTimingSourceAction       INTEGER,
        sonusStTimingSourceRowStatus    RowStatus
    }

sonusStTimingSourceShelfIndex OBJECT-TYPE
    SYNTAX          SonusShelfIndex
    MAX-ACCESS      read-write
    STATUS          current
    DESCRIPTION     
            "  "
    ::= { sonusStTimingSourceEntry 1 }

sonusStTimingSourceMtaSlotIndex OBJECT-TYPE
    SYNTAX          Integer32 (1..2)
    MAX-ACCESS      read-write
    STATUS          current
    DESCRIPTION     
            " Indicates which MTA this timing node is bound to. "
    ::= { sonusStTimingSourceEntry 2 }

sonusStTimingSource OBJECT-TYPE
    SYNTAX          SonusTimingSource
    MAX-ACCESS      read-write
    STATUS          current
    DESCRIPTION     
            " Indicates which physical timing source is bound to this node.
             
             External BITS sources are used by MTA 10's, in T1 based chassis'.
             External SETS sources are used by MTA 2X's, in E1 based chassis'.
             REFCLK's are based upon timing recovered from a CNS or PNS Server card.
             HOLDOVER mimics the last known good source before it failed.
             OSCILLATOR is used when no other valid sources exist on the currently active
             MTA. "
    DEFVAL          { oscillator }
    ::= { sonusStTimingSourceEntry 3 }

sonusStTimingSourceState OBJECT-TYPE
    SYNTAX          SonusAdminState
    MAX-ACCESS      read-write
    STATUS          current
    DESCRIPTION     
            " If enabled, the source can participate in system timing. 
             If disabled, then it will be removed from service and
             not be allowed to participate. "
    DEFVAL          { enabled }
    ::= { sonusStTimingSourceEntry 4 }

sonusStTimingSourceSequenceNum OBJECT-TYPE
    SYNTAX          Integer32 (1..12)
    MAX-ACCESS      read-write
    STATUS          current
    DESCRIPTION     
            " The timing sequence number is automatically generated "
    ::= { sonusStTimingSourceEntry 5 }

sonusStTimingSourceAction OBJECT-TYPE
    SYNTAX          INTEGER { none(1), available(2) }
    MAX-ACCESS      read-write
    STATUS          current
    DESCRIPTION     
            " Selecting AVAILABLE will cause the timing source to be moved  
             from the Out-Of-Service state to the Available-For-Use state.
             
             This command is necessary to manually make a source available for use
             after it has failed, and revertive source switching is not enabled. 
             
             This may cause the current active timing source to change. "
    DEFVAL          { none }
    ::= { sonusStTimingSourceEntry 6 }

sonusStTimingSourceRowStatus OBJECT-TYPE
    SYNTAX          RowStatus
    MAX-ACCESS      read-write
    STATUS          current
    DESCRIPTION     
            "This object indicates the row status for this table."
    ::= { sonusStTimingSourceEntry 7 }

sonusStTimingSourceStatTable OBJECT-TYPE
    SYNTAX          SEQUENCE OF SonusStTimingSourceStatEntry
    MAX-ACCESS      not-accessible
    STATUS          current
    DESCRIPTION     
            "  "
    ::= { sonusSystemTimingMIBObjects 6 }

sonusStTimingSourceStatEntry OBJECT-TYPE
    SYNTAX          SonusStTimingSourceStatEntry
    MAX-ACCESS      not-accessible
    STATUS          current
    DESCRIPTION     
            "  "
    INDEX           { sonusStTimingSourceStatShelfIndex, 
                      sonusStTimingSourceStatMtaSlotIndex, 
                      sonusStTimingSourceStat }
    ::= { sonusStTimingSourceStatTable 1 }

SonusStTimingSourceStatEntry ::=
    SEQUENCE {
        sonusStTimingSourceStatShelfIndex SonusShelfIndex,
        sonusStTimingSourceStatMtaSlotIndex   SonusMtaSlotIndex,
        sonusStTimingSourceStat         SonusTimingSource,
        sonusStTimingSourceStatState    INTEGER,
        sonusStTimingSourceStatTraceability   INTEGER,
        sonusStTimingSourceStatLineState INTEGER
    }

sonusStTimingSourceStatShelfIndex OBJECT-TYPE
    SYNTAX          SonusShelfIndex
    MAX-ACCESS      read-only
    STATUS          current
    DESCRIPTION     
            " Indicates shelf. "
    ::= { sonusStTimingSourceStatEntry 1 }

sonusStTimingSourceStatMtaSlotIndex OBJECT-TYPE
    SYNTAX          SonusMtaSlotIndex
    MAX-ACCESS      read-only
    STATUS          current
    DESCRIPTION     
            " Indicates which MTA this timing node is bound to. "
    ::= { sonusStTimingSourceStatEntry 2 }

sonusStTimingSourceStat OBJECT-TYPE
    SYNTAX          SonusTimingSource
    MAX-ACCESS      read-only
    STATUS          current
    DESCRIPTION     
            " Indicates the physical timing source "
    DEFVAL          { oscillator }
    ::= { sonusStTimingSourceStatEntry 3 }

sonusStTimingSourceStatState OBJECT-TYPE
    SYNTAX          INTEGER { available(1), inservice(2), faulting(3), 
                        outofservice(4), cannotlocate(5), notpresent(6) }
    MAX-ACCESS      read-only
    STATUS          current
    DESCRIPTION     
            " Indicates the current overall state of the timing source, including 
             the hardware state, adminitrative mode and shelf configuration "
    ::= { sonusStTimingSourceStatEntry 4 }

sonusStTimingSourceStatTraceability OBJECT-TYPE
    SYNTAX          INTEGER { synchronizedunknown(1), stratum1(2), 
                        stratum2(3), stratumTNC(4), stratum3e(5), 
                        stratum3(6), stratumSonetMinimum(7), stratum4(8), 
                        reserved(9), dontUse(10), indeterminate(11), 
                        qualityunknown(12), g811(13), g812transit(14), 
                        g812local(15), sets(16), g704rsvdql1(17), 
                        g704rsvdql3(18), g704rsvdql5(19), 
                        g704rsvdql6(20), g704rsvdql7(21), 
                        g704rsvdql9(22), g704rsvdql10(23), 
                        g704rsvdql12(24), g704rsvdql13(25), 
                        g704rsvdql14(26) }
    MAX-ACCESS      read-only
    STATUS          current
    DESCRIPTION     
            " Indicates the Quality Level of the System Synchronized Timing Source"
    ::= { sonusStTimingSourceStatEntry 5 }

sonusStTimingSourceStatLineState OBJECT-TYPE
    SYNTAX          INTEGER { valid(1), notvalid(2) }
    MAX-ACCESS      read-only
    STATUS          current
    DESCRIPTION     
            " Indicates the current physical status of the timing source "
    ::= { sonusStTimingSourceStatEntry 6 }

sonusStChannelBindingTable OBJECT-TYPE
    SYNTAX          SEQUENCE OF SonusStChannelBindingEntry
    MAX-ACCESS      not-accessible
    STATUS          current
    DESCRIPTION     
            " This table describes how derived timing 
             sources should be mapped to the MTA hardware"
    ::= { sonusSystemTimingMIBObjects 7 }

sonusStChannelBindingEntry OBJECT-TYPE
    SYNTAX          SonusStChannelBindingEntry
    MAX-ACCESS      not-accessible
    STATUS          current
    DESCRIPTION     
            "  "
    INDEX           { sonusStChannelBindingShelfIndex, 
                      sonusStChannelBindingSlotIndex, 
                      sonusStChannelBindingChannel, 
                      sonusStChannelBindingRefClk }
    ::= { sonusStChannelBindingTable 1 }

SonusStChannelBindingEntry ::=
    SEQUENCE {
        sonusStChannelBindingShelfIndex SonusShelfIndex,
        sonusStChannelBindingSlotIndex  SonusSlotIndex,
        sonusStChannelBindingChannel    Integer32,
        sonusStChannelBindingRefClk     INTEGER,
        sonusStChannelBindingRowStatus  RowStatus
    }

sonusStChannelBindingShelfIndex OBJECT-TYPE
    SYNTAX          SonusShelfIndex
    MAX-ACCESS      read-only
    STATUS          current
    DESCRIPTION     
            "  "
    ::= { sonusStChannelBindingEntry 1 }

sonusStChannelBindingSlotIndex OBJECT-TYPE
    SYNTAX          SonusSlotIndex
    MAX-ACCESS      read-only
    STATUS          current
    DESCRIPTION     
            " Server slot number to provide a recovered clock source. The
             same server can be configured to provide both possible recovered 
             clocks as long as different channels(spans) are selected, and 
             the REFCLK each is bound to differs "
    ::= { sonusStChannelBindingEntry 2 }

sonusStChannelBindingChannel OBJECT-TYPE
    SYNTAX          Integer32
    MAX-ACCESS      read-only
    STATUS          current
    DESCRIPTION     
            " T1/E1 span or OC12 port number to provide the recovered clock source.
             T1 span range is 1-12(CNS10), 1-28(CNS30), E1 span range is 1-8(CNS20), 
             OC12 port number(PNS20) is 1 only."
    ::= { sonusStChannelBindingEntry 3 }

sonusStChannelBindingRefClk OBJECT-TYPE
    SYNTAX          INTEGER { refClkA(1), refClkB(2) }
    MAX-ACCESS      read-only
    STATUS          current
    DESCRIPTION     
            "  Backplane signal the recovered clock source should be 
             bound to. Each REFCLK must only be bound to a single 
             Server slot/span. "
    ::= { sonusStChannelBindingEntry 4 }

sonusStChannelBindingRowStatus OBJECT-TYPE
    SYNTAX          RowStatus
    MAX-ACCESS      read-write
    STATUS          current
    DESCRIPTION     
            "This object indicates the row status for this table."
    ::= { sonusStChannelBindingEntry 5 }

sonusSystemTimingMIBNotifications OBJECT IDENTIFIER
    ::= { sonusSystemTimingMIB 2 }

sonusSystemTimingMIBNotificationsPrefix OBJECT IDENTIFIER
    ::= { sonusSystemTimingMIBNotifications 0 }

sonusSystemTimingMIBNotificationsObjects OBJECT IDENTIFIER
    ::= { sonusSystemTimingMIBNotifications 1 }

sonusTimingSource OBJECT-TYPE
    SYNTAX          SonusTimingSource
    MAX-ACCESS      read-only
    STATUS          current
    DESCRIPTION     
            "  "
    ::= { sonusSystemTimingMIBNotificationsObjects 1 }

sonusTimingSource2 OBJECT-TYPE
    SYNTAX          SonusEventString
    MAX-ACCESS      read-only
    STATUS          current
    DESCRIPTION     
            "  "
    ::= { sonusSystemTimingMIBNotificationsObjects 2 }

sonusSystemTimingActiveFailedNotification NOTIFICATION-TYPE
    OBJECTS         { sonusShelfIndex, sonusSlotIndex, sonusTimingSource, 
                      sonusEventDescription, sonusEventClass, 
                      sonusEventLevel }
    STATUS          current
    DESCRIPTION     
            "This trap indicates that the currently 
             active System Timing clock source has failed."
    ::= { sonusSystemTimingMIBNotificationsPrefix 1 }

sonusSystemTimingActiveSwitchoverNotification NOTIFICATION-TYPE
    OBJECTS         { sonusShelfIndex, sonusSlotIndex, sonusTimingSource, 
                      sonusEventDescription, sonusEventClass, 
                      sonusEventLevel }
    STATUS          current
    DESCRIPTION     
            "This trap indicates that the active System Timing 
             clock source has been switched to another source."
    ::= { sonusSystemTimingMIBNotificationsPrefix 2 }

sonusSystemTimingOscillatorActiveNotification NOTIFICATION-TYPE
    OBJECTS         { sonusShelfIndex, sonusSlotIndex, 
                      sonusEventDescription, sonusEventClass, 
                      sonusEventLevel }
    STATUS          current
    DESCRIPTION     
            "This trap indicates that all external sources of
             System Timing have failed and that the current 
             source of timing is the MTA's internal oscillator."
    ::= { sonusSystemTimingMIBNotificationsPrefix 3 }

sonusSystemTimingMTAFailedNotification NOTIFICATION-TYPE
    OBJECTS         { sonusShelfIndex, sonusSlotIndex, 
                      sonusEventDescription, sonusEventClass, 
                      sonusEventLevel }
    STATUS          current
    DESCRIPTION     
            "This trap indicates that the MTA indicated 
             has failed or been removed from the shelf."
    ::= { sonusSystemTimingMIBNotificationsPrefix 4 }

sonusSystemTimingMTAOperationalNotification NOTIFICATION-TYPE
    OBJECTS         { sonusShelfIndex, sonusSlotIndex, 
                      sonusEventDescription, sonusEventClass, 
                      sonusEventLevel }
    STATUS          current
    DESCRIPTION     
            "This trap indicates that the specified MTA
             is now operational."
    ::= { sonusSystemTimingMIBNotificationsPrefix 6 }

sonusSystemTimingMTATotalFailureNotification NOTIFICATION-TYPE
    OBJECTS         { sonusShelfIndex, sonusEventDescription, 
                      sonusEventClass, sonusEventLevel }
    STATUS          current
    DESCRIPTION     
            "This trap indicates that no MTA's are available for 
             use to provide System Timing. They have either failed, 
             been removed from service or been removed from the shelf. 
             The shelf is no longer capable of being properly timed.
             
             Downstream Shelves or other equipment connected to this shelf's
             MITDC(Marlin Inter-chassis Timing Daisy Chain) may be affected."
    ::= { sonusSystemTimingMIBNotificationsPrefix 7 }

END -- end of module SONUS-SYSTEM-TIMING-MIB.
