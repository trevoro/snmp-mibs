-- QUANTA-MIB { iso(1) org(3) dod(6) internet(1) private(4) enterprises(1)
--		quanta(7244) server(1) high-density(1) s31MgmtAgent(1) }



BLADE-MIB DEFINITIONS ::= BEGIN


IMPORTS
	OBJECT-TYPE                            	FROM RFC-1212
	mib-2, DisplayString, PhysAddress      	FROM RFC1213-MIB
	TRAP-TYPE							FROM RFC-1215
	Counter, Gauge, IpAddress, enterprises 	FROM RFC1155-SMI;


-- Version:	V3.74
-- Date:	2011/05/06
-- Author:	sh
-- note:	1. add SYNTAX  for s31AgentTimeZone   2. add  s31AgentSmtpServerTable	3.remove s31AgentDaylightSavingTime	4.add SYNTAX  for s31SvrTempSensorStatus	5.fix SYNTAX  for s31TrapServerName  6. fix SYNTAX for s31AgentVirtualIoLan and  s31AgentVirtualIoFiberchannel
-- note:	7. add SEQUENCE  for s31FCSwitchBladeEntry  8. add SEQUENCE  for  s31AgentSmtpServerEntry  9. add  s31AgentSmtpTestMailEnable and s31AgentSmtpHostName		10. fix s31SysCtrlStatLed SYNTAX
-- note:	11.fix s31SvrCtrlBootMode SYNTAX  12.fix s31SvrRaidConfigType SYNTAX	13.add s31SwitchBladeIpMode ,s31SwitchBladeDhcpClientName ,s31SwitchBladeVlanId for  s31SwitchBladeTable
-- note:	14.add s31SvrBladeGuid	,s31SvrBladeBiosViomSettingStatus and s31SvrBladeDaughterCardType for s31SvrBladeTable	15. add s31SvrManufactureMac and s31SvrNicType for s31SvrNicInfoTable
-- note:	16. add s31FcPassThroughBladeActiveWwnn ,s31FcPassThroughBladeActiveWwpn ,s31FcPassThroughBladeManufactureWwnn and s31FcPassThroughBladeManufactureWwpn for s31FcPassThroughBladeInfoTable
-- note:	17. add new SYNTAX inventory and init-boot for s31SvrCtrlBootMode	18. add s31SvrIrmcTable and  s31SvrViomTable	19.add s31FCSwitchBladeFirmwareVersion
-- note:	20. add s31SwitchBladeFirmwareVersion	21. remove s31AgentDefaultRoute		22.remove s31AgentDnsEnable  23.remove s31TftpUpdateAction
-- note:	24. s31AgentDaylightSavingTime s31AgentDefaultRoute s31AgentSmtpRelayServer s31SysCtrlStatLed s31SvrTempSensorStatus return to the original condition flow mmb1
-- note:	25. Add bldServerVirtualizationError trap 26. Add s31SysPowerSupplyRedundancyMode 27. Add s31StorageBlade table 28. Update s31CpuType description, change s31KvmBladeUpdatestatus as integer type and update string
-- note:	29. Change s31SvrHostname order, add s31fscErrorlog table 
-- note:	30. Base on SimpleWeb MIB module validation modify some syntax errors.

-- note:	2008/08/01 - Fix OID define syntax error (s31SysPowerSupplyRedundancyMode).
-- note:	2008/08/11 - Change s31CpuType "amd-opteron(2)" to "amd-opteron(13)".
--			   - Add s31SvrTempSensorStatus "warning-temp-cold(8)" and "critical-temp-cold(9)".
--			   - Add s31FcPassThroughBladeFirmwareVersion
--			   - Add s31PhyBladeStatus
--			   - Add s31KvmBladeStatus, s31KvmBladeAdministrativeURL
--			   - Add s31FCSwitchBladeStatus, s31FCSwitchBladeAdministrativeURL
--			   - Add s31StorageBladeStatus, s31StorageBladeFWVersion, s31StorageBladeIdentSerialNumber, s31StorageBladeAdministrativeURL
--			   - All maximun blade number defintions follow BX900.
-- note:	2008/09/01 - Add s31PowerConsumptionHistory table
-- note:	2008/09/24 - Add s31SvrBladeCustomerProductName
-- note:	2008/10/14 - Add minimum support for IPv6 (report v6 addresses of other blades correctly)
-- note:		   - Add e-Keying trap
-- note:	2008/11/11 - Add VIOM flag, rack information and switch master/slave
--			   - Add MAC address for FC switches
-- note:	2008/11/19 - Add 's31StorageBladeCustomerProductName' as known to the end customer.
-- note:	2008/12/01 - Add 's31FcPassThroughBladeSlotId' to identify FC pass-through slot ID.
-- note:	2008/12/05 - Extend PXE source to support 12 interfaces
-- note:	2009/02/09 - Mark s31SysPowerSupplyRedundancyMode as obsolete; extend s31TftpUpdateEnable
-- note: 	2009/03/24 - Adapt eventlog definition to implementation
-- note: 	2009/04/02 - Extend LED state definitions
-- note: 	2009/05/19 - Add support for Infiniband switches and storage assignment
-- note: 	2009/05/19 - Fix definition of s31elOverviewSrc
-- note:	2009/07/01 - Add s31TrapPowerOffTimeReached and s31TrapPowerOnTimeReached
-- note:	2009/07/01 - Add power consumption limiting traps
-- note:	2009/07/14 - Add asset tag information
-- note:	2009/07/15 - Update trap strings
-- note:	2009/07/17 - Extend value range of s31IBSwitchBladeId
-- note:	2009/08/18 - Add additional value to PowerSupplyUnitStatus; fix trap severities to match SEL severity
-- note:	2009/09/15 - Mark s31SvrViomTable as obsolete
-- note:	2009/09/24 - Extend s31MemModuleType
-- note:	2009/09/29 - Extend s31SvrNicId to 20
-- note:	2009/10/22 - Add BX400 extensions (e.g. SAS switch)
-- note:	2009/12/14 - Mark some OIDs as obsolete
-- note:	2010/03/16 - Add s31SwitchBladeUserAssignedName; clarify s31BootWatchdogTime
-- note:	2010/05/14 - Add s31SysFsiomConnectionStatus, s31SysFsiomConnectionTarget, s31SysChassisAssetTag and s31SysPowerSupplyUnitSourceType
-- note:	2010/10/01 - Add s31SysFsiomModelName and s31SysFsiomManufactureDate
-- note:	2010/10/29 - Adapt sensor range to BX900; add s31SysChassisType
-- note:	2010/12/03 - Add OIDs for controlling SSH service; adapt trap table to IPv6; add s31StorageBladeCtrlStatLed
-- note:	2010/12/21 - Add information about mezzanine cards (s31SvrMezzanineInfo)
-- note:	2011/01/10 - Extend valid s31SvrNicType
-- note:	2011/01/25 - Extend index range s31PhyBladeId
-- note:	2011/02/14 - Add information for action-after-error
-- note:	2011/03/31 - Add VIOM information string
-- note:	2011/05/06 - Add missing IPv6 related OIDs (except for S31SvrExtInfoEntry)

-- Server Management (S31) MIB nodes
-- quanta:				1.3.6.1.4.1.7244
-- server:				1.3.6.1.4.1.7244.1
-- high-density:			1.3.6.1.4.1.7244.1.1
-- s31MgmtAgent:			1.3.6.1.4.1.7244.1.1.1

-- Trap enterprise is "quanta".
-- quanta S31 Trap IDs MIB:		1600-1673  (this MIB)

quanta					OBJECT IDENTIFIER ::= { enterprises 7244 }
server					OBJECT IDENTIFIER ::= { quanta 1 }
high-density				OBJECT IDENTIFIER ::= { server 1 }
s31MgmtAgent				OBJECT IDENTIFIER ::= { high-density 1 }
	s31AgentInfo			OBJECT IDENTIFIER ::= { s31MgmtAgent 1 }
		s31AgentHttp		OBJECT IDENTIFIER ::= { s31AgentInfo 11 }
		s31AgentSnmp		OBJECT IDENTIFIER ::= { s31AgentInfo 12 }
		s31AgentTelnet		OBJECT IDENTIFIER ::= { s31AgentInfo 13 }
		s31AgentDns		OBJECT IDENTIFIER ::= { s31AgentInfo 14 }
		s31AgentSmtp		OBJECT IDENTIFIER ::= { s31AgentInfo 15 }
		s31AgentNtp		OBJECT IDENTIFIER ::= { s31AgentInfo 16 }
		s31AgentDaylightSavingTime	OBJECT IDENTIFIER ::= { s31AgentInfo 17 }

	s31ManagementBlade		OBJECT IDENTIFIER ::= { s31MgmtAgent 2 }
	s31SystemInfo			OBJECT IDENTIFIER ::= { s31MgmtAgent 3 }
		s31SysCtrlInfo		OBJECT IDENTIFIER ::= { s31SystemInfo 1 }
		s31SysPowerSupply	OBJECT IDENTIFIER ::= { s31SystemInfo 2 }
		s31SysFan		OBJECT IDENTIFIER ::= { s31SystemInfo 3 }
		s31SysTemperature	OBJECT IDENTIFIER ::= { s31SystemInfo 4 }
		s31SysChassis		OBJECT IDENTIFIER ::= { s31SystemInfo 5 }
		s31SysUps		OBJECT IDENTIFIER ::= { s31SystemInfo 6 }
		s31SysFsiom		OBJECT IDENTIFIER ::= { s31SystemInfo 8 }
	s31ServerBlade			OBJECT IDENTIFIER ::= { s31MgmtAgent 4 }
		s31SvrCtrlInfo		OBJECT IDENTIFIER ::= { s31ServerBlade 1 }
		s31SvrBlade		OBJECT IDENTIFIER ::= { s31ServerBlade 2 }
		s31SvrCpu		OBJECT IDENTIFIER ::= { s31ServerBlade 3 }
		s31SvrMemory		OBJECT IDENTIFIER ::= { s31ServerBlade 4 }
		s31SvrVoltage		OBJECT IDENTIFIER ::= { s31ServerBlade 5 }
		s31SvrTemperature	OBJECT IDENTIFIER ::= { s31ServerBlade 6 }
		s31SvrNicInfo		OBJECT IDENTIFIER ::= { s31ServerBlade 7 }
		s31SvrCmosConfig	OBJECT IDENTIFIER ::= { s31ServerBlade 8 }
		s31SvrRaidConfig	OBJECT IDENTIFIER ::= { s31ServerBlade 9 }
		s31SvrDeployment	OBJECT IDENTIFIER ::= { s31ServerBlade 10 }
		s31SvrWatchDog		OBJECT IDENTIFIER ::= { s31ServerBlade 11 }
		s31SvrScheduleOnOff	OBJECT IDENTIFIER ::= { s31ServerBlade 12 }
		s31SvrIrmc		OBJECT IDENTIFIER ::= { s31ServerBlade 13 }
		s31SvrViom		OBJECT IDENTIFIER ::= { s31ServerBlade 14 }
		s31SvrMezzanineInfo	OBJECT IDENTIFIER ::= { s31ServerBlade 15 }
	s31SwitchBlade			OBJECT IDENTIFIER ::= { s31MgmtAgent 5 }
	--s31ErrorHandling		OBJECT IDENTIFIER ::= { s31MgmtAgent 6 }
		--s31EventLog		OBJECT IDENTIFIER ::= { s31ErrorHandling 1 }
		--s31ErrorLog		OBJECT IDENTIFIER ::= { s31ErrorHandling 2 }
	s31TrapInfo			OBJECT IDENTIFIER ::= { s31MgmtAgent 7 }
	s31FiberChannel			OBJECT IDENTIFIER ::= { s31MgmtAgent 8 }
		s31FcPassThroughBlade	OBJECT IDENTIFIER ::= { s31FiberChannel 1 }
	s31TftpUpdate			OBJECT IDENTIFIER ::= { s31MgmtAgent 9 }
	s31PhyBlade			OBJECT IDENTIFIER ::= { s31MgmtAgent 10 }
	s31KvmBlade			OBJECT IDENTIFIER ::= { s31MgmtAgent 11 }
	s31FCSwitchBlade		OBJECT IDENTIFIER ::= { s31MgmtAgent 12 }
	s31StorageBlade		  	OBJECT IDENTIFIER ::= { s31MgmtAgent 13 }
	s31fscErrorlog		OBJECT IDENTIFIER ::= { s31MgmtAgent 14 }
		s31el2			OBJECT IDENTIFIER ::= { s31fscErrorlog 1 }
	s31PowerConsumptionHistory 	OBJECT IDENTIFIER ::= { s31MgmtAgent 15 }
	s31IBSwitchBlade		OBJECT IDENTIFIER ::= { s31MgmtAgent 16 }
	s31SASSwitchBlade		OBJECT IDENTIFIER ::= { s31MgmtAgent 17 }

-- **********************************************************************************************
--
-- GROUP: s31AgentInfo
--
--      s31MgmtAgent MIB:        1.3.6.1.4.1.7244.1.1.1
--      s31AgentInfo group:              1.3.6.1.4.1.7244.1.1.1.1
--
-- **********************************************************************************************

s31AgentIpAddress OBJECT-TYPE
	SYNTAX	IpAddress
	ACCESS	read-write
	STATUS	mandatory
	DESCRIPTION
		"The IP address of the agent"
	::= { s31AgentInfo 1 }

s31AgentNetMask OBJECT-TYPE
	SYNTAX	IpAddress
	ACCESS	read-write
	STATUS	mandatory
	DESCRIPTION
		"The subnet mask of the agent"
	::= { s31AgentInfo 2 }

s31AgentGateway OBJECT-TYPE
	SYNTAX	IpAddress
	ACCESS	read-write
	STATUS	mandatory
	DESCRIPTION
		"The gateway of the agent"
	::= { s31AgentInfo 3 }

s31AgentDhcpConfigured OBJECT-TYPE
	SYNTAX	INTEGER{
		unknown(1),
		disable(2),
		enable(3)
	}
	ACCESS	read-write
	STATUS	mandatory
	DESCRIPTION
		"Defines if the IP address should be requested by a DHCP service"
	::= { s31AgentInfo 4 }

s31AgentAdministrativeUrl OBJECT-TYPE
	SYNTAX	DisplayString
	ACCESS	read-only
	STATUS	mandatory
	DESCRIPTION
		"The administrative URL of the agent"
	::= { s31AgentInfo 5 }

s31AgentConsoleTimeout OBJECT-TYPE
	SYNTAX	INTEGER
	ACCESS	read-write
	STATUS	mandatory
	DESCRIPTION
		"Timeout of connecting to management blade through serial port"
	::= { s31AgentInfo 6 }

s31AgentDateTime OBJECT-TYPE
	SYNTAX	DisplayString
	ACCESS	read-write
	STATUS	mandatory
	DESCRIPTION
		"Current time of the agent"
	::= { s31AgentInfo 7 }

s31AgentTimeZone OBJECT-TYPE
	SYNTAX	INTEGER{
		unknown(1),
		gmt-12(2),
		gmt-11(3),
		gmt-10(4),
		gmt-9(5),
		gmt-8A(6),
		gmt-8B(7),
		gmt-7A(8),
		gmt-7B(9),
		gmt-7C(10),
		gmt-6A(11),
		gmt-6B(12),
		gmt-6C(13),
		gmt-6D(14),
		gmt-5A(15),
		gmt-5B(16),
		gmt-5C(17),
		gmt-4A(18),
		gmt-4B(19),
		gmt-4C(20),
		gmt-4D(21),
		gmt-3-30min(22),
		gmt-3A(23),
		gmt-3B(24),
		gmt-3C(25),
		gmt-3D(26),
		gmt-2(27),
		gmt-1A(28),
		gmt-1B(29),
		gmt0A(30),
		gmt0B(31),
		gmt1A(32),
		gmt1B(33),
		gmt1C(34),
		gmt1D(35),
		gmt1E(36),
		gmt2A(37),
		gmt2B(38),
		gmt2C(39),
		gmt2D(40),
		gmt2E(41),
		gmt2F(42),
		gmt2G(43),
		gmt2H(44),
		gmt2I(45),
		gmt3A(46),
		gmt3B(47),
		gmt3C(48),
		gmt3D(49),
		gmt3E(50),
		gmt3-30min(51),
		gmt4A(52),
		gmt4B(53),
		gmt4C(54),
		gmt4-30min(55),
		gmt5A(56),
		gmt5B(57),
		gmt5-30minA(58),
		gmt5-30minB(59),
		gmt5-45min(60),
		gmt6A(61),
		gmt6B(62),
		gmt6-30min(63),
		gmt7A(64),
		gmt7B(65),
		gmt8A(66),
		gmt8B(67),
		gmt8C(68),
		gmt8D(69),
		gmt8E(70),
		gmt9A(71),
		gmt9B(72),
		gmt9C(73),
		gmt9-30minA(74),
		gmt9-30minB(75),
		gmt10A(76),
		gmt10B(77),
		gmt10C(78),
		gmt10D(79),
		gmt10E(80),
		gmt11(81),
		gmt12A(82),
		gmt12B(83),
		gmt13(84)
	}
	ACCESS	read-write
	STATUS	mandatory
	DESCRIPTION
		"Agent time zone"
	::= { s31AgentInfo 8 }

s31AgentName OBJECT-TYPE
	SYNTAX	DisplayString
	ACCESS	read-write
	STATUS	mandatory
	DESCRIPTION
		"Agent name"
	::= { s31AgentInfo 9 }


s31AgentDaylightSavingTimeEnable OBJECT-TYPE
	SYNTAX	INTEGER{
		unknown(1),
		disable(2),
		enable(3)

	}
	ACCESS	read-write
	STATUS	mandatory
	DESCRIPTION
		"Defines the automatic daylight saving time enable or disable"
	::= { s31AgentDaylightSavingTime 1 }

s31AgentDaylightSavingTimeStartDate OBJECT-TYPE
	SYNTAX	DisplayString
	ACCESS	read-write
	STATUS	mandatory
	DESCRIPTION
		"Defines the automatic daylight saving time start date"
	::= { s31AgentDaylightSavingTime 2 }

s31AgentDaylightSavingTimeEndDate OBJECT-TYPE
	SYNTAX	DisplayString
	ACCESS	read-write
	STATUS	mandatory
	DESCRIPTION
		"Defines the automatic daylight saving time end date"
	::= { s31AgentDaylightSavingTime 3 }

s31AgentDefaultRoute OBJECT-TYPE
	SYNTAX	INTEGER{
		unknown(1),
		lan(2),
		ppp(3)

	}
	ACCESS	read-write
	STATUS	mandatory
	DESCRIPTION
		"Agent default send out packet route"
	::= { s31AgentInfo 18 }


s31AgentSmashCli OBJECT-TYPE
	SYNTAX	INTEGER{
		unknown(1),
		enable(2)
	}
	ACCESS	read-only
	STATUS	mandatory
	DESCRIPTION
		"identify SMASH CLI is supported"
	::= { s31AgentInfo 19 }

s31AgentAddressType OBJECT-TYPE
	SYNTAX	INTEGER{
        unknown(0),
        ipv4(1),
        ipv6(2),
        ipv4z(3),
        ipv6z(4),
        dns(16)
	}
	ACCESS	read-write
	STATUS	mandatory
	DESCRIPTION
		"Identify IP address type of the agent address"
	::= { s31AgentInfo 20 }

s31AgentAddress OBJECT-TYPE
    SYNTAX  OCTET STRING (SIZE (1..64))
	ACCESS	read-write
	STATUS	mandatory
	DESCRIPTION
		"IPv6 address for the agent"
	::= { s31AgentInfo 21 }

s31AgentHttpEnable OBJECT-TYPE
	SYNTAX	INTEGER{
		unknown(1),
		disable(2),
		enable(3)
	}
	ACCESS	read-write
	STATUS	mandatory
	DESCRIPTION
		"Defines if the agent should provide HTTP service"
	::= { s31AgentHttp 1 }

s31AgentHttpPort OBJECT-TYPE
	SYNTAX	INTEGER
	ACCESS	read-write
	STATUS	mandatory
	DESCRIPTION
		"The TCP port for HTTP service"
	::= { s31AgentHttp 2 }

s31AgentHttpSslEnable OBJECT-TYPE
	SYNTAX	INTEGER{
		unknown(1),
		disable(2),
		enable(3)
	}
	ACCESS	read-write
	STATUS	mandatory
	DESCRIPTION
		"Defines if the agent should provide SSL service for HTTP"
	::= { s31AgentHttp 3 }

s31AgentSnmpEnable OBJECT-TYPE
	SYNTAX	INTEGER{
		unknown(1),
		disable(2),
		enable(3)
	}
	ACCESS	read-write
	STATUS	mandatory
	DESCRIPTION
		"Defines if the agent should provide SNMP service"
	::= { s31AgentSnmp 1 }

s31AgentSnmpTrapTable OBJECT-TYPE
	SYNTAX	SEQUENCE OF S31AgentSnmpTrapEntry
	ACCESS	not-accessible
	STATUS	mandatory
	DESCRIPTION
		"Table with data of SNMP trap"
	::= { s31AgentSnmp 2 }

s31AgentSnmpTrapEntry OBJECT-TYPE
	SYNTAX	S31AgentSnmpTrapEntry
	ACCESS	not-accessible
	STATUS	mandatory
	DESCRIPTION
		""
	INDEX	{ s31AgentSnmpTrapId }
	::= { s31AgentSnmpTrapTable 1 }

S31AgentSnmpTrapEntry ::=
	SEQUENCE {
		s31AgentSnmpTrapId
			INTEGER,
		s31AgentSnmpTrapDestination
			IpAddress,
		s31AgentSnmpTrapCommunityString
			DisplayString,
		s31SvrTrapDestinationAddressType
			INTEGER,
		s31SvrTrapDestinationAddress
			OCTET STRING (SIZE (1..64))
	}

s31AgentSnmpTrapId OBJECT-TYPE
	SYNTAX	INTEGER (1..5)
	ACCESS	read-only
	STATUS	mandatory
	DESCRIPTION
		"Snmp trap number, index into the snmp trap table (1 based)"
	::= { s31AgentSnmpTrapEntry 1 }

s31AgentSnmpTrapDestination OBJECT-TYPE
	SYNTAX	IpAddress
	ACCESS	read-write
	STATUS	mandatory
	DESCRIPTION
		"The destination IP Address which the SNMP trap will send to"
	::= { s31AgentSnmpTrapEntry 2 }

s31AgentSnmpTrapCommunityString OBJECT-TYPE
	SYNTAX	DisplayString
	ACCESS	read-write
	STATUS	mandatory
	DESCRIPTION
		"SNMP trap community string"
	::= { s31AgentSnmpTrapEntry 3 }

s31SvrTrapDestinationAddressType OBJECT-TYPE
	SYNTAX	INTEGER{
        unknown(0),
        ipv4(1),
        ipv6(2),
        ipv4z(3),
        ipv6z(4),
        dns(16)
	}
	ACCESS	read-write
	STATUS	mandatory
	DESCRIPTION
		"Identify IP address type of this trap destination"
	::= { s31AgentSnmpTrapEntry 4 }

s31SvrTrapDestinationAddress OBJECT-TYPE
    SYNTAX  OCTET STRING (SIZE (1..64))
	ACCESS	read-write
	STATUS	mandatory
	DESCRIPTION
		"IPv6 address for this trap destination"
	::= { s31AgentSnmpTrapEntry 5 }

s31AgentTelnetEnable OBJECT-TYPE
	SYNTAX	INTEGER{
		unknown(1),
		disable(2),
		enable(3)
	}
	ACCESS	read-write
	STATUS	mandatory
	DESCRIPTION
		"Defines if the agent should provide TELNET service"
	::= { s31AgentTelnet 1 }

s31AgentTelnetPort OBJECT-TYPE
	SYNTAX	INTEGER
	ACCESS	read-write
	STATUS	mandatory
	DESCRIPTION
		"The TCP port for TELNET service"
	::= { s31AgentTelnet 2 }

s31AgentTelnetSslEnable OBJECT-TYPE
	SYNTAX	INTEGER{
		unknown(1),
		disable(2),
		enable(3)
	}
	ACCESS	read-write
	STATUS	obsolete
	DESCRIPTION
		"Defines if the agent should provide SSL encryption over TELNET"
	::= { s31AgentTelnet 3 }

s31AgentSshEnable OBJECT-TYPE
	SYNTAX	INTEGER{
		unknown(1),
		disable(2),
		enable(3)
	}
	ACCESS	read-write
	STATUS	mandatory
	DESCRIPTION
		"Defines if the agent should provide SSH service"
	::= { s31AgentTelnet 4 }

s31AgentSshPort OBJECT-TYPE
	SYNTAX	INTEGER
	ACCESS	read-write
	STATUS	mandatory
	DESCRIPTION
		"The TCP port for SSH service"
	::= { s31AgentTelnet 5 }

s31AgentDnsEnable OBJECT-TYPE
	SYNTAX	INTEGER{
		unknown(1),
		disable(2),
		enable(3)
	}
	ACCESS	read-write
	STATUS	mandatory
	DESCRIPTION
		"Defines if the agent should provide DNS service"
	::= { s31AgentDns 1 }

s31AgentDnsIpAddress1 OBJECT-TYPE
	SYNTAX	IpAddress
	ACCESS	read-write
	STATUS	mandatory
	DESCRIPTION
		"The DNS IP address1 of the agent"
	::= { s31AgentDns 2 }

s31AgentDnsIpAddress2 OBJECT-TYPE
	SYNTAX	IpAddress
	ACCESS	read-write
	STATUS	mandatory
	DESCRIPTION
		"The DNS IP address2 of the agent"
	::= { s31AgentDns 3 }

s31AgentDnsAddressType1 OBJECT-TYPE
	SYNTAX	INTEGER{
        unknown(0),
        ipv4(1),
        ipv6(2),
        ipv4z(3),
        ipv6z(4),
        dns(16)
	}
	ACCESS	read-write
	STATUS	mandatory
	DESCRIPTION
		"Identify IP address type of agent DNS address 1"
	::= { s31AgentDns 4 }

s31AgentDnsAddressType2 OBJECT-TYPE
	SYNTAX	INTEGER{
        unknown(0),
        ipv4(1),
        ipv6(2),
        ipv4z(3),
        ipv6z(4),
        dns(16)
	}
	ACCESS	read-write
	STATUS	mandatory
	DESCRIPTION
		"Identify IP address type of agent DNS address 2"
	::= { s31AgentDns 5 }

s31AgentDnsAddress1 OBJECT-TYPE
    SYNTAX  OCTET STRING (SIZE (1..64))
	ACCESS	read-write
	STATUS	mandatory
	DESCRIPTION
		"IPv6 address for agent DNS address 1"
	::= { s31AgentDns 6 }

s31AgentDnsAddress2 OBJECT-TYPE
    SYNTAX  OCTET STRING (SIZE (1..64))
	ACCESS	read-write
	STATUS	mandatory
	DESCRIPTION
		"IPv6 address for agent DNS address 2"
	::= { s31AgentDns 7 }

s31AgentSmtpEnable OBJECT-TYPE
	SYNTAX	INTEGER{
		unknown(1),
		disable(2),
		enable(3)
	}
	ACCESS	read-write
	STATUS	mandatory
	DESCRIPTION
		"Defines if the agent should provide SMTP service"
	::= { s31AgentSmtp 1 }

s31AgentSmtpRelayServer OBJECT-TYPE
	SYNTAX	DisplayString
	ACCESS	read-write
	STATUS	mandatory
	DESCRIPTION
		"IP address/domain name of the SMTP relay server"
	::= { s31AgentSmtp 2 }

s31AgentSmtpSender OBJECT-TYPE
	SYNTAX	DisplayString
	ACCESS	read-write
	STATUS	mandatory
	DESCRIPTION
		"SMTP sender e-mail address"
	::= { s31AgentSmtp 3 }

s31AgentSmtpTestMailEnable OBJECT-TYPE
	SYNTAX	INTEGER{
		unknown(1),
		disable(2),
		enable(3)
	}
	ACCESS	read-write
	STATUS	mandatory
	DESCRIPTION
		"SMTP Test mail "
	::= { s31AgentSmtp 6 }

s31AgentSmtpHostName OBJECT-TYPE
	SYNTAX	DisplayString
	ACCESS	read-write
	STATUS	mandatory
	DESCRIPTION
		"Hostname of this SMTP "
	::={ s31AgentSmtp 7 }

s31AgentSmtpUserTable OBJECT-TYPE
	SYNTAX	SEQUENCE OF S31AgentSmtpUserEntry
	ACCESS	not-accessible
	STATUS	mandatory
	DESCRIPTION
		"Table with data of SMTP setting"
	::= { s31AgentSmtp 4 }

s31AgentSmtpUserEntry OBJECT-TYPE
	SYNTAX	S31AgentSmtpUserEntry
	ACCESS	not-accessible
	STATUS	mandatory
	DESCRIPTION
		""
	INDEX	{ s31AgentSmtpUserId }
	::= { s31AgentSmtpUserTable 1 }

S31AgentSmtpUserEntry ::=
	SEQUENCE {
		s31AgentSmtpUserId
			INTEGER,
		s31AgentSmtpUserMailAddress
			DisplayString
	}

s31AgentSmtpUserId OBJECT-TYPE
	SYNTAX	INTEGER (1..5)
	ACCESS	read-only
	STATUS	mandatory
	DESCRIPTION
		"SMTP user number, index into the SMTP user table (1 based)"
	::= { s31AgentSmtpUserEntry 1 }

s31AgentSmtpUserMailAddress OBJECT-TYPE
	SYNTAX	DisplayString
	ACCESS	read-write
	STATUS	mandatory
	DESCRIPTION
		"E-Mail address the SMTP service sends to"
	::= { s31AgentSmtpUserEntry 2 }


s31AgentSmtpServerTable OBJECT-TYPE
	SYNTAX	SEQUENCE OF S31AgentSmtpServerEntry
	ACCESS	not-accessible
	STATUS	mandatory
	DESCRIPTION
		"Table with server of SMTP setting"
	::= { s31AgentSmtp 5 }

s31AgentSmtpServerEntry OBJECT-TYPE
	SYNTAX	S31AgentSmtpServerEntry
	ACCESS	not-accessible
	STATUS	mandatory
	DESCRIPTION
		""
	INDEX	{ s31AgentSmtpServerId }
	::= { s31AgentSmtpServerTable 1 }

S31AgentSmtpServerEntry ::=
	SEQUENCE {
		s31AgentSmtpServerId
			INTEGER,
		s31AgentSmtpServer
			DisplayString,
		s31AgentSmtpServerPort
			INTEGER,
		s31AgentSmtpAuthType
			INTEGER,
		s31AgentSmtpAuthUserName
			DisplayString,
		s31AgentSmtpAuthPassWord
			DisplayString
	}

s31AgentSmtpServerId OBJECT-TYPE
	SYNTAX	INTEGER (1..2)
	ACCESS	read-only
	STATUS	mandatory
	DESCRIPTION
		"SMTP server number, index into the SMTP user table (1 based)"
	::= { s31AgentSmtpServerEntry 1 }

s31AgentSmtpServer OBJECT-TYPE
	SYNTAX	DisplayString
	ACCESS	read-write
	STATUS	mandatory
	DESCRIPTION
		"SMTP server address"
	::= { s31AgentSmtpServerEntry 2 }

s31AgentSmtpServerPort OBJECT-TYPE
	SYNTAX	INTEGER
	ACCESS	read-write
	STATUS	mandatory
	DESCRIPTION
		"SMTP server port"
	::= { s31AgentSmtpServerEntry 3 }

s31AgentSmtpAuthType OBJECT-TYPE
	SYNTAX	INTEGER{
		unknown(1),
		disable(2),
		auth-Login(3),
		auth-Plain(4),
		auth-Cram-md5(5)
	}
	ACCESS	read-write
	STATUS	mandatory
	DESCRIPTION
		"SMTP server AUTH type"
	::= { s31AgentSmtpServerEntry 4 }

s31AgentSmtpAuthUserName OBJECT-TYPE
	SYNTAX	DisplayString
	ACCESS	read-write
	STATUS	mandatory
	DESCRIPTION
		"SMTP server AUTH Username"
	::= { s31AgentSmtpServerEntry 5 }

s31AgentSmtpAuthPassWord OBJECT-TYPE
	SYNTAX	DisplayString
	ACCESS	read-write
	STATUS	mandatory
	DESCRIPTION
		"SMTP server AUTH Password"
	::= { s31AgentSmtpServerEntry 6 }


s31AgentNtpEnable OBJECT-TYPE
	SYNTAX	INTEGER{
		unknown(1),
		disable(2),
		enable(3)
	}
	ACCESS	read-write
	STATUS	mandatory
	DESCRIPTION
		"Defines if the agent should provide NTP service"
	::= { s31AgentNtp 1 }



s31AgentNtpTable OBJECT-TYPE
	SYNTAX	SEQUENCE OF S31AgentNtpEntry
	ACCESS	not-accessible
	STATUS	mandatory
	DESCRIPTION
		"Table with data of all NTP server IP"
	::= { s31AgentNtp 2 }

s31AgentNtpEntry OBJECT-TYPE
	SYNTAX	S31AgentNtpEntry
	ACCESS	not-accessible
	STATUS	mandatory
	DESCRIPTION
		""
	INDEX	{ s31AgentNtpId }
	::= { s31AgentNtpTable 1 }

S31AgentNtpEntry ::=
	SEQUENCE {
		s31AgentNtpId
			INTEGER,
		s31AgentNtpIpAddress
			IpAddress,
		s31AgentNtpAddressType
			INTEGER,
		s31AgentNtpAddress
			OCTET STRING (SIZE (1..64))
		}

s31AgentNtpId OBJECT-TYPE
	SYNTAX	INTEGER (1..2)
	ACCESS	read-only
	STATUS	mandatory
	DESCRIPTION
		"NTP Server IP number, index into the NTP Server IP table"
	::= { s31AgentNtpEntry 1 }

s31AgentNtpIpAddress OBJECT-TYPE
	SYNTAX	IpAddress
	ACCESS	read-write
	STATUS	mandatory
	DESCRIPTION
		"NTP server IP address"
	::= { s31AgentNtpEntry 2 }

s31AgentNtpAddressType OBJECT-TYPE
	SYNTAX	INTEGER{
        unknown(0),
        ipv4(1),
        ipv6(2),
        ipv4z(3),
        ipv6z(4),
        dns(16)
	}
	ACCESS	read-write
	STATUS	mandatory
	DESCRIPTION
		"Identify IP address type of the NTP server address"
	::= { s31AgentNtpEntry 3 }

s31AgentNtpAddress OBJECT-TYPE
    SYNTAX  OCTET STRING (SIZE (1..64))
	ACCESS	read-write
	STATUS	mandatory
	DESCRIPTION
		"IPv6 address the NTP server"
	::= { s31AgentNtpEntry 4 }

s31AgentNtpLastSyncTime OBJECT-TYPE
	SYNTAX	DisplayString
	ACCESS	read-only
	STATUS	mandatory
	DESCRIPTION
		"Display last NTP sync date/time"
	::= { s31AgentNtp 3 }

s31AgentNtpSyncMode OBJECT-TYPE
	SYNTAX	INTEGER{
		unknown(1),
		sync-afterward(2),
		sync-always(3)
	}
	ACCESS	read-write
	STATUS	mandatory
	DESCRIPTION
		"Defines the NTP sync mode"
	::= { s31AgentNtp 4 }



-- **********************************************************************************************
--
-- GROUP: s31ManagementBlade
--
--      s31MgmtAgent MIB:        1.3.6.1.4.1.7244.1.1.1
--      s31ManagementBlade group:              1.3.6.1.4.1.7244.1.1.1.2
--
-- **********************************************************************************************

s31MgmtBladeTable OBJECT-TYPE
	SYNTAX	SEQUENCE OF S31MgmtBladeEntry
	ACCESS	not-accessible
	STATUS	mandatory
	DESCRIPTION
		"Table with data of management blade"
	::= { s31ManagementBlade 1 }

s31MgmtBladeEntry OBJECT-TYPE
	SYNTAX	S31MgmtBladeEntry
	ACCESS	not-accessible
	STATUS	mandatory
	DESCRIPTION
		""
	INDEX	{ s31MgmtBladeId }
	::= { s31MgmtBladeTable 1 }

S31MgmtBladeEntry ::=
	SEQUENCE {
		s31MgmtBladeId
			INTEGER,
		s31MgmtBladeStatus
			INTEGER,
		s31MgmtBladeManufacture
			DisplayString,
		s31MgmtBladeManufactureDate
			DisplayString,
		s31MgmtBladeSerialNumber
			DisplayString,
		s31MgmtBladeProductName
			DisplayString,
		s31MgmtBladeModelName
			DisplayString,
		s31MgmtBladeHardwareVersion
			DisplayString,
		s31MgmtBladeFirmwareVersion
			DisplayString,
		s31MgmtBladePhysicalAddress
			PhysAddress,
		s31MgmtBladeRunMode
			INTEGER,
		s31MgmtBladeAssetTag
			OCTET STRING (SIZE (1..40))
	}

s31MgmtBladeId OBJECT-TYPE
	SYNTAX	INTEGER (1..2)
	ACCESS	read-only
	STATUS	mandatory
	DESCRIPTION
		"Management blade number, index into the management blade table (1 based)"
	::= { s31MgmtBladeEntry 1 }

s31MgmtBladeStatus OBJECT-TYPE
	SYNTAX	INTEGER{
		unknown(1),
		ok(2),
		not-present(3),
		error(4),
		critical(5),
		standby(6)
	}
	ACCESS	read-only
	STATUS	mandatory
	DESCRIPTION
		"Current status of this management blade"
	::= { s31MgmtBladeEntry 2 }

s31MgmtBladeManufacture OBJECT-TYPE
	SYNTAX	DisplayString
	ACCESS	read-only
	STATUS	mandatory
	DESCRIPTION
		"String containing the management blade manufacturer"
	::= { s31MgmtBladeEntry 3 }

s31MgmtBladeManufactureDate OBJECT-TYPE
	SYNTAX	DisplayString
	ACCESS	read-only
	STATUS	mandatory
	DESCRIPTION
		"Manufacture date of the management blade"
	::= { s31MgmtBladeEntry 4 }

s31MgmtBladeSerialNumber OBJECT-TYPE
	SYNTAX	DisplayString
	ACCESS	read-only
	STATUS	mandatory
	DESCRIPTION
		"Serial number of the management blade"
	::= { s31MgmtBladeEntry 5 }

s31MgmtBladeProductName OBJECT-TYPE
	SYNTAX	DisplayString
	ACCESS	read-only
	STATUS	mandatory
	DESCRIPTION
		"Product name of the management blade"
	::= { s31MgmtBladeEntry 6 }

s31MgmtBladeModelName OBJECT-TYPE
	SYNTAX	DisplayString
	ACCESS	read-only
	STATUS	mandatory
	DESCRIPTION
		"Model name of the management blade"
	::= { s31MgmtBladeEntry 7 }

s31MgmtBladeHardwareVersion OBJECT-TYPE
	SYNTAX	DisplayString
	ACCESS	read-only
	STATUS	mandatory
	DESCRIPTION
		"Hardware version of the management blade"
	::= { s31MgmtBladeEntry 8 }

s31MgmtBladeFirmwareVersion OBJECT-TYPE
	SYNTAX	DisplayString
	ACCESS	read-only
	STATUS	mandatory
	DESCRIPTION
		"Firmware version of the management blade"
	::= { s31MgmtBladeEntry 9 }

s31MgmtBladePhysicalAddress OBJECT-TYPE
	SYNTAX	PhysAddress
	ACCESS	read-only
	STATUS	mandatory
	DESCRIPTION
		"Management blade MAC address"
	::= { s31MgmtBladeEntry 10 }

s31MgmtBladeRunMode OBJECT-TYPE
	SYNTAX	INTEGER{
		unknown(1),
		master(2),
		slave(3)
	}
	ACCESS	read-only
	STATUS	mandatory
	DESCRIPTION
		"Current running mode(master/slave) of the management blade"
	::= { s31MgmtBladeEntry 11 }

s31MgmtBladeAssetTag OBJECT-TYPE
    SYNTAX  OCTET STRING (SIZE (1..40))
	ACCESS	read-write
	STATUS	mandatory
	DESCRIPTION
		"Asset tag for this management blade"
	::={ s31MgmtBladeEntry 12 }

-- **********************************************************************************************
--
-- GROUP: s31SystemInfo
--
--      s31MgmtAgent MIB:        1.3.6.1.4.1.7244.1.1.1
--      s31SystemInfo group:              1.3.6.1.4.1.7244.1.1.1.3
--
-- **********************************************************************************************

s31SysCtrlNumberFans OBJECT-TYPE
	SYNTAX	INTEGER
	ACCESS	read-only
	STATUS	mandatory
	DESCRIPTION
		"Fan number of the system"
	::= { s31SysCtrlInfo 1 }

s31SysCtrlNumberTempSensors OBJECT-TYPE
	SYNTAX	INTEGER
	ACCESS	read-only
	STATUS	mandatory
	DESCRIPTION
		"Temperature sensor number of the system"
	::= { s31SysCtrlInfo 2 }

s31SysCtrlNumberPowerSupplyUnit OBJECT-TYPE
	SYNTAX	INTEGER
	ACCESS	read-only
	STATUS	mandatory
	DESCRIPTION
		"Power supply unit number of the system"
	::= { s31SysCtrlInfo 3 }

s31SysCtrlHousingType OBJECT-TYPE
	SYNTAX	DisplayString
	ACCESS	read-only
	STATUS	mandatory
	DESCRIPTION
		"Type string for housing type"
	::= { s31SysCtrlInfo 4 }

s31SysCtrlOverallStatus OBJECT-TYPE
	SYNTAX	INTEGER{
		unknown(1),
		ok(2),
		error(3),
		critical(4)
	}
	ACCESS	read-only
	STATUS	mandatory
	DESCRIPTION
		"Overall status of the system"
	::= { s31SysCtrlInfo 5 }

s31SysCtrlSystemName OBJECT-TYPE
	SYNTAX	DisplayString
	ACCESS	read-only
	STATUS	mandatory
	DESCRIPTION
		"System name string (PRIMERGY BX300)"
	::= { s31SysCtrlInfo 6 }

s31SysCtrlStatLed OBJECT-TYPE
	SYNTAX	INTEGER{
		unknown(1),
		off(2),
		on(3),
		blinking(4)
	}
	ACCESS	read-write
	STATUS	mandatory
	DESCRIPTION
		"Configure IDENTIFY (formerly STAT) LED status (off/on/blinking)"
	::= { s31SysCtrlInfo 7 }

s31SysCtrlId OBJECT-TYPE
	SYNTAX	DisplayString
	ACCESS	read-only
	STATUS	mandatory
	DESCRIPTION
		"System ID"
	::= { s31SysCtrlInfo 8 }

s31SysCtrlNumberUps OBJECT-TYPE
	SYNTAX	INTEGER{
		unknown(1),
		ups-0(2),
		ups-1(3),
		ups-2(4)
	}
	ACCESS	read-write
	STATUS	mandatory
	DESCRIPTION
		"UPS number of the system"
	::= { s31SysCtrlInfo 9 }

s31SysCtrlUpdateCount OBJECT-TYPE
	SYNTAX	INTEGER
	ACCESS	read-only
	STATUS	mandatory
	DESCRIPTION
		"Update count which would chage after s31SvrBlade, s31SvrNicInfoTable or s31SwitchBladeTable was modified."
	::= { s31SysCtrlInfo 10 }

s31SysCtrlNumberOfUps OBJECT-TYPE
	SYNTAX	INTEGER
	ACCESS	read-write
	STATUS	mandatory
	DESCRIPTION
		"UPS number of the system"
	::= { s31SysCtrlInfo 11 }

s31SysCtrlForceOffEnable OBJECT-TYPE
	SYNTAX	INTEGER{
		unknown(1),
		disable(2),
		enable(3)
	}
	ACCESS	read-write
	STATUS	mandatory
	DESCRIPTION
		"Enable/disable force off system power supply when grace shutdown fail"
	::= { s31SysCtrlInfo 12 }

s31SysCtrlForceOffDelay OBJECT-TYPE
	SYNTAX	INTEGER{
		unknown(1),
		minutes-1(2),
		minutes-2(3),
		minutes-3(4),
		minutes-4(5),
		minutes-5(6),
		minutes-6(7),
		minutes-7(8)
	}
	ACCESS	read-write
	STATUS	mandatory
	DESCRIPTION
		"Expired time of force off system power supply when grace shutdown fail"
	::= { s31SysCtrlInfo 13 }

s31SysPowerSupplyStatus OBJECT-TYPE
	SYNTAX	INTEGER{
		unknown(1),
		ok(2),
		degraded(3),
		critical(4)
	}
	ACCESS	read-only
	STATUS	mandatory
	DESCRIPTION
		"Status of the power supply;
			ok:       all units OK, number >= minimum
			degraded: one or more units failed, number OK >= minimum
			critical: number OK < minimum."
	::= { s31SysPowerSupply 1 }

s31SysPowerSupplyRedundancy OBJECT-TYPE
	SYNTAX	INTEGER
	ACCESS	read-only
	STATUS	mandatory
	DESCRIPTION
		"Number of available redundant power supply units"
	::= { s31SysPowerSupply 2 }

s31SysPowerSupplyCtrl OBJECT-TYPE
	SYNTAX	INTEGER{
		unknown(1),
		off(2),
		on(3),
		graceful-shutdown(4)
	}
	ACCESS	read-write
	STATUS	mandatory
	DESCRIPTION
		"Enable/disable system power supply"
	::= { s31SysPowerSupply 3 }

s31SysPowerSupplyUnitTable OBJECT-TYPE
	SYNTAX	SEQUENCE OF S31SysPowerSupplyUnitEntry
	ACCESS	not-accessible
	STATUS	mandatory
	DESCRIPTION
		"Table with data of power supply unit"
	::= { s31SysPowerSupply 4 }

s31SysPowerSupplyUnitEntry OBJECT-TYPE
	SYNTAX	S31SysPowerSupplyUnitEntry
	ACCESS	not-accessible
	STATUS	mandatory
	DESCRIPTION
		""
	INDEX	{ s31SysPowerSupplyUnitId }
	::= { s31SysPowerSupplyUnitTable 1 }

S31SysPowerSupplyUnitEntry ::=
	SEQUENCE {
		s31SysPowerSupplyUnitId
			INTEGER,
		s31SysPowerSupplyUnitStatus
			INTEGER,
		s31SysPowerSupplyUnitManufacture
			DisplayString,
		s31SysPowerSupplyUnitProductName
			DisplayString,
		s31SysPowerSupplyUnitModelName
			DisplayString,
		s31SysPowerSupplyUnitProductVersion
			DisplayString,
		s31SysPowerSupplyUnitSerialNumber
			DisplayString,
		s31SysPowerSupplyUnitOvpFail
			INTEGER,
		s31SysPowerSupplyUnitOcpFail
			INTEGER,
		s31SysPowerSupplyUnitSourceType
			DisplayString
	}

s31SysPowerSupplyUnitId OBJECT-TYPE
	SYNTAX	INTEGER (1..6)
	ACCESS	read-only
	STATUS	mandatory
	DESCRIPTION
		"Power supply unit number, index into the power supply unit table (1 based)"
	::= { s31SysPowerSupplyUnitEntry 1 }

s31SysPowerSupplyUnitStatus OBJECT-TYPE
	SYNTAX	INTEGER{
		unknown(1),
		ok(2),
		not-present(3),
		error(4),
		critical(5),
		off(6),
		dummy(7),
		fanmodule(8)
	}
	ACCESS	read-only
	STATUS	mandatory
	DESCRIPTION
		"Current status of this power supply unit"
	::= { s31SysPowerSupplyUnitEntry 2 }

s31SysPowerSupplyUnitManufacture OBJECT-TYPE
	SYNTAX	DisplayString
	ACCESS	read-only
	STATUS	mandatory
	DESCRIPTION
		"String containing the power supply unit manufacturer"
	::= { s31SysPowerSupplyUnitEntry 3 }

s31SysPowerSupplyUnitProductName OBJECT-TYPE
	SYNTAX	DisplayString
	ACCESS	read-only
	STATUS	mandatory
	DESCRIPTION
		"Product name of the power supply unit"
	::= { s31SysPowerSupplyUnitEntry 4 }

s31SysPowerSupplyUnitModelName OBJECT-TYPE
	SYNTAX	DisplayString
	ACCESS	read-only
	STATUS	mandatory
	DESCRIPTION
		"Model name of the power supply unit"
	::= { s31SysPowerSupplyUnitEntry 5 }

s31SysPowerSupplyUnitProductVersion OBJECT-TYPE
	SYNTAX	DisplayString
	ACCESS	read-only
	STATUS	mandatory
	DESCRIPTION
		"Product version of the power supply unit"
	::= { s31SysPowerSupplyUnitEntry 6 }

s31SysPowerSupplyUnitSerialNumber OBJECT-TYPE
	SYNTAX	DisplayString
	ACCESS	read-only
	STATUS	mandatory
	DESCRIPTION
		"Serial number of the power supply unit"
	::= { s31SysPowerSupplyUnitEntry 7 }

s31SysPowerSupplyUnitOvpFail OBJECT-TYPE
	SYNTAX	INTEGER{
		unknown(1),
		ok(2),
		fail(3),
		not-available(4)
	}
	ACCESS	read-only
	STATUS	mandatory
	DESCRIPTION
		"Current OVP status of this power supply unit"
	::= { s31SysPowerSupplyUnitEntry 8 }

s31SysPowerSupplyUnitOcpFail OBJECT-TYPE
	SYNTAX	INTEGER{
		unknown(1),
		ok(2),
		fail(3),
		not-available(4)
	}
	ACCESS	read-only
	STATUS	mandatory
	DESCRIPTION
		"Current OCP status of this power supply unit"
	::= { s31SysPowerSupplyUnitEntry 9 }

s31SysPowerSupplyUnitSourceType OBJECT-TYPE
    	SYNTAX       DisplayString
    	ACCESS       read-only
    	STATUS       mandatory
    	DESCRIPTION  
		"System input power source type (e.g. 'AC', 'DC')"
	::= { s31SysPowerSupplyUnitEntry 10 }

s31SysPowerSupplyOvpFailReaction OBJECT-TYPE
	SYNTAX	INTEGER{
		unknown(1),
		continue(2),
		shutdown-and-poweroff(3)
	}
	ACCESS	read-write
	STATUS	mandatory
	DESCRIPTION
		"Reaction when OVP of the power supply has failed (continue, shutdown and power-off...)"
	::= { s31SysPowerSupply 5 }

s31SysPowerSupplyOcpFailReaction OBJECT-TYPE
	SYNTAX	INTEGER{
		unknown(1),
		continue(2),
		shutdown-and-poweroff(3)
	}
	ACCESS	read-write
	STATUS	mandatory
	DESCRIPTION
		"Reaction when OCP of the power supply has failed (continue, shutdown and power-off...)"
	::= { s31SysPowerSupply 6 }

s31SysPowerSupplyRedundancyMode OBJECT-TYPE
	SYNTAX	INTEGER{
		unknown(1),
		mode-2-plus-1(2),
		mode-3-plus-1(3),
		mode-4-plus-0(4)
	}
	ACCESS	read-write
	STATUS	obsolete
	DESCRIPTION
		"Set System Power Supply Redundancy Mode"
	::= { s31SysPowerSupply 7 }

s31SysFanTable OBJECT-TYPE
	SYNTAX	SEQUENCE OF S31SysFanEntry
	ACCESS	not-accessible
	STATUS	mandatory
	DESCRIPTION
		"Table with data of all configured cooling devices (fans)"
	::= { s31SysFan 1 }

s31SysFanEntry OBJECT-TYPE
	SYNTAX	S31SysFanEntry
	ACCESS	not-accessible
	STATUS	mandatory
	DESCRIPTION
		""
	INDEX	{ s31SysFanId }
	::= { s31SysFanTable 1 }

S31SysFanEntry ::=
	SEQUENCE {
		s31SysFanId
			INTEGER,
		s31SysFanStatus
			INTEGER,
		s31SysFanDesignation
			DisplayString,
		s31SysFanCurrentSpeed
			INTEGER,
		s31SysFanNominalMaximumSpeed
			INTEGER,
		s31SysFanCurrentMaximumSpeed
			INTEGER,
		s31SysFanFailReaction
			INTEGER,
		s31SysFanIdentification
			DisplayString
	}


s31SysFanId OBJECT-TYPE
	SYNTAX	INTEGER (1..48)
	ACCESS	read-only
	STATUS	mandatory
	DESCRIPTION
		"Fan number, index into the fan table (1 based)"
	::= { s31SysFanEntry 1 }

s31SysFanStatus OBJECT-TYPE
	SYNTAX	INTEGER{
		unknown(1),
		disable(2),
		ok(3),
		fail(4),
		prefailure-predicted(5),
		redundant-fan-failed(6),
		not-manageable(7),
		not-present(8),
		not-available(9)
	}
	ACCESS	read-only
	STATUS	mandatory
	DESCRIPTION
		"Status of this fan.
			Status prefailure-predicted(5) means the fan will fail in near future.
			Status redundant-fan-failed(6) means a redundant fan has failed, the system is not yet critical.
			Status not-manageable(7) is a fan that is available but has no management facilities.
			Status not-present(8) can be a hot-plug fan that is currently removed."
	::= { s31SysFanEntry 2 }

s31SysFanDesignation OBJECT-TYPE
	SYNTAX	DisplayString
	ACCESS	read-only
	STATUS	mandatory
	DESCRIPTION
		"String containing the fan designation"
	::= { s31SysFanEntry 3 }

s31SysFanCurrentSpeed OBJECT-TYPE
	SYNTAX	INTEGER
	ACCESS	read-only
	STATUS	mandatory
	DESCRIPTION
		"Current speed of this fan (in revolutions per minute)"
	::= { s31SysFanEntry 4 }

s31SysFanNominalMaximumSpeed OBJECT-TYPE
	SYNTAX	INTEGER
	ACCESS	read-only
	STATUS	mandatory
	DESCRIPTION
		"Nominal speed of this fan (in revolutions per minute)
			on maximum power; the speed is measured the first time
			the agent is installed and than compared daily to the
			current speed on maximum power to detect a fan
			prefailure"
	::= { s31SysFanEntry 5 }

s31SysFanCurrentMaximumSpeed OBJECT-TYPE
	SYNTAX	INTEGER
	ACCESS	read-only
	STATUS	mandatory
	DESCRIPTION
		"Current speed of the fan (in revolutions per minute) on maximum power"
	::= { s31SysFanEntry 6 }

s31SysFanFailReaction OBJECT-TYPE
	SYNTAX	INTEGER{
		unknown(1),
		continue(2),
		shutdown-and-poweroff(3)
	}
	ACCESS	read-write
	STATUS	mandatory
	DESCRIPTION
		"Reaction when a fan has failed (continue, shutdown and power-off...)"
	::= { s31SysFanEntry 7 }

s31SysFanIdentification OBJECT-TYPE
	SYNTAX	DisplayString
	ACCESS	read-only
	STATUS	mandatory
	DESCRIPTION
		"Identification of this fan"
	::= { s31SysFanEntry 8 }

s31SysFanDailyTestTime OBJECT-TYPE
	SYNTAX	DisplayString
	ACCESS	read-write
	STATUS	mandatory
	DESCRIPTION
		"Daily time when to automatically test fan speeds (hh:mm, in minutes since midnight)"
	::= { s31SysFan 2 }

s31SysFanStartTest OBJECT-TYPE
	SYNTAX	INTEGER{
		unknown(1),
		disable(2),
		enable(3)
	}
	ACCESS	read-write
	STATUS	mandatory
	DESCRIPTION
		"Fan test of all fans to get the speed at maximum power at every start-up"
	::= { s31SysFan 3 }

s31SysFanOverallStatus OBJECT-TYPE
	SYNTAX	INTEGER{
		unknown(1),
		ok(2),
		degraded(3),
		critical(4)
	}
	ACCESS	read-only
	STATUS	mandatory
	DESCRIPTION
		"Overall status of the system fan"
	::= { s31SysFan 4 }


s31SysTemperatureSensorTable OBJECT-TYPE
	SYNTAX	SEQUENCE OF S31SysTemperatureSensorEntry
	ACCESS	not-accessible
	STATUS	mandatory
	DESCRIPTION
		"Table with data of all configured temperature sensors"
	::= { s31SysTemperature 1 }

s31SysTemperatureSensorEntry OBJECT-TYPE
	SYNTAX	S31SysTemperatureSensorEntry
	ACCESS	not-accessible
	STATUS	mandatory
	DESCRIPTION
		""
	INDEX	{ s31SysTempSensorId }
	::= { s31SysTemperatureSensorTable 1 }

S31SysTemperatureSensorEntry ::=
	SEQUENCE {
		s31SysTempSensorId
			INTEGER,
		s31SysTempSensorStatus
			INTEGER,
		s31SysTempSensorDesignation
			DisplayString,
		s31SysTempUpperWarningLevel
			INTEGER,
		s31SysTempUpperCriticalLevel
			INTEGER,
		s31SysTempCurrentValue
			INTEGER,
		s31SysTempCriticalReaction
			INTEGER
	}

s31SysTempSensorId OBJECT-TYPE
	SYNTAX	INTEGER (1..48)
	ACCESS	read-only
	STATUS	mandatory
	DESCRIPTION
		"Temperature sensor number, index into the temperature sensor table (1 based)"
	::= { s31SysTemperatureSensorEntry 1 }

s31SysTempSensorStatus OBJECT-TYPE
	SYNTAX	INTEGER{
		unknown(1),
		sensor-disable(2),
		ok(3),
		sensor-fail(4),
		warning-temp-warm(5),
		critical-temp-warm(6),
		not-available(7)
	}
	ACCESS	read-only
	STATUS	mandatory
	DESCRIPTION
		"Current status of this temperature sensor"
	::= { s31SysTemperatureSensorEntry 2 }

s31SysTempSensorDesignation OBJECT-TYPE
	SYNTAX	DisplayString
	ACCESS	read-only
	STATUS	mandatory
	DESCRIPTION
		"String containing the temperature sensor designation"
	::= { s31SysTemperatureSensorEntry 3 }

s31SysTempUpperWarningLevel OBJECT-TYPE
	SYNTAX	INTEGER(0..127)
	ACCESS	read-only
	STATUS	mandatory
	DESCRIPTION
		"System sends a temperature warning when temperature rises ABOVE
			this level (degrees Celsius)"
	::= { s31SysTemperatureSensorEntry 4 }

s31SysTempUpperCriticalLevel OBJECT-TYPE
	SYNTAX	INTEGER(0..127)
	ACCESS	read-only
	STATUS	mandatory
	DESCRIPTION
		"System becomes critical when temperature rises ABOVE this level (degrees Celsius).
			A system shutdown is performed if object s31SysTempCriticalReaction
			is set to shutdown-and-poweroff."
	::= { s31SysTemperatureSensorEntry 5 }

s31SysTempCurrentValue OBJECT-TYPE
	SYNTAX	INTEGER
	ACCESS	read-only
	STATUS	mandatory
	DESCRIPTION
		"Current temperature value"
        ::= { s31SysTemperatureSensorEntry 6}

s31SysTempCriticalReaction OBJECT-TYPE
	SYNTAX	INTEGER{
		unknown(1),
		continue(2),
		shutdown-and-poweroff(3)
	}
	ACCESS	read-write
	STATUS	mandatory
	DESCRIPTION
		"Reaction when a temperature gets critical (continue, shutdown and power-off...)"
	::= { s31SysTemperatureSensorEntry 7 }

s31SysTemperatureStatus OBJECT-TYPE
	SYNTAX	INTEGER{
		unknown(1),
		ok(2),
		degraded(3),
		critical(4)
	}
	ACCESS	read-only
	STATUS	mandatory
	DESCRIPTION
		"Overall status of the system temperature"
	::= { s31SysTemperature 2 }

s31SysChassisSerialNumber OBJECT-TYPE
	SYNTAX	DisplayString
	ACCESS	read-only
	STATUS	mandatory
	DESCRIPTION
		"Serial number of system chassis"
	::= { s31SysChassis 1 }

s31SysChassisIntrusionTable OBJECT-TYPE
	SYNTAX	SEQUENCE OF S31SysChassisIntrusionEntry
	ACCESS	not-accessible
	STATUS	mandatory
	DESCRIPTION
		"Table with data of system chassis intrusion"
	::= { s31SysChassis 2 }

s31SysChassisIntrusionEntry OBJECT-TYPE
	SYNTAX	S31SysChassisIntrusionEntry
	ACCESS	not-accessible
	STATUS	mandatory
	DESCRIPTION ""
	INDEX	{ s31SysChassisIntrusionSensorId }
	::= { s31SysChassisIntrusionTable 1 }

S31SysChassisIntrusionEntry ::=
	SEQUENCE {
		s31SysChassisIntrusionSensorId
			INTEGER,
		s31SysChassisIntrusionSensorStatus
			INTEGER,
		s31SysChassisDesignation
			DisplayString
	}

s31SysChassisIntrusionSensorId OBJECT-TYPE
	SYNTAX	INTEGER (1..2)
	ACCESS	read-only
	STATUS	mandatory
	DESCRIPTION
		"Chassis intrusion sensor number, index into the chassis intrusion sensor table (1 based)"
	::= { s31SysChassisIntrusionEntry 1 }

s31SysChassisIntrusionSensorStatus OBJECT-TYPE
	SYNTAX	INTEGER{
		unknow(1),
		open(2),
		closed(3)
	}
	ACCESS	read-only
	STATUS	mandatory
	DESCRIPTION
		"Current status of this chassis (open/close)"
	::= { s31SysChassisIntrusionEntry 2 }

s31SysChassisDesignation OBJECT-TYPE
	SYNTAX	DisplayString
	ACCESS	read-only
	STATUS	mandatory
	DESCRIPTION
		"String containing the chassis designation"
	::= { s31SysChassisIntrusionEntry 3 }

s31SysChassisManagedByViom OBJECT-TYPE
	SYNTAX	INTEGER{
		unknown(1),
		unmanaged(2),
		managed(3)
	}
	ACCESS	read-only
	STATUS	mandatory
	DESCRIPTION
		"Specifies whether the chassis is controlled by 
		ServerView Virtual IO Manager software"
	::= { s31SysChassis 3 }

s31SysChassisRackName OBJECT-TYPE
	SYNTAX	DisplayString
	ACCESS	read-write
	STATUS	mandatory
	DESCRIPTION
		"Specifies a name for the rack into which this chassis
		  has been integrated"
	::= { s31SysChassis 4 }

s31SysChassisRackUniqueId OBJECT-TYPE
	SYNTAX	DisplayString
	ACCESS	read-write
	STATUS	mandatory
	DESCRIPTION
		"Specifies an ID for the rack into which this chassis
		  has been integrated - the uniqueness has to be ensured
		  by the user"
	::= { s31SysChassis 5 }

s31SysChassisConsumptionMode OBJECT-TYPE
	SYNTAX	INTEGER{
		unknown(1),
		unmanaged(2),
		enforced(3),
		low-noise(4),
		minimum(5),
		adaptive(6)
	}
	ACCESS	read-only
	STATUS	mandatory
	DESCRIPTION
		"Specifies the power consumption management mode currently
		configured for the complete chassis."
	::= { s31SysChassis 6 }

s31SysChassisAssetTag OBJECT-TYPE
    SYNTAX  OCTET STRING (SIZE (1..40))
	ACCESS	read-write
	STATUS	mandatory
	DESCRIPTION
		"Asset tag for this chassis"
	::= { s31SysChassis 7 }

s31SysChassisType OBJECT-TYPE
	SYNTAX	INTEGER{
		unknown(1),
		rack(2),
		floor-stand(3)
	}
	ACCESS	read-only
	STATUS	mandatory
	DESCRIPTION
		"Specifies whether the chassis is configured as floor-stand or rack variant"
	::= { s31SysChassis 8 }

s31SysChassisViomManaged OBJECT-TYPE
    	SYNTAX  OCTET STRING 
	ACCESS	read-only
	STATUS	mandatory
	DESCRIPTION
		"The same string as reported by CLP in SystemInfo-ViomManaged"
	::= { s31SysChassis 9 }

s31SysUpsTable OBJECT-TYPE
	SYNTAX	SEQUENCE OF S31SysUpsEntry
	ACCESS	not-accessible
	STATUS	mandatory
	DESCRIPTION
		"Table with data of system chassis intrusion"
	::= { s31SysUps 1 }

s31SysUpsEntry OBJECT-TYPE
	SYNTAX	S31SysUpsEntry
	ACCESS	not-accessible
	STATUS	mandatory
	DESCRIPTION ""
	INDEX	{ s31SysUpsId }
	::= { s31SysUpsTable 1 }

S31SysUpsEntry ::=
	SEQUENCE {
		s31SysUpsId
			INTEGER,
		s31SysUpsVendor
			DisplayString,
		s31SysUpsType
			DisplayString,
		s31SysUpsOemAgentIpAddress
			IpAddress,
		s31SysUpsPort
			INTEGER,
		s31SysUpsSnmpCommunity
			DisplayString,
		s31SysUpsOemAgentAddressType
			INTEGER,
		s31SysUpsOemAgentAddress
			OCTET STRING (SIZE (1..64))
	}

s31SysUpsId OBJECT-TYPE
	SYNTAX	INTEGER (1..2)
	ACCESS	read-only
	STATUS	mandatory
	DESCRIPTION
		"UPS number, index into the system UPS table (1 based)"
	::= { s31SysUpsEntry 1 }

s31SysUpsVendor OBJECT-TYPE
	SYNTAX	DisplayString
	ACCESS	read-write
	STATUS	mandatory
	DESCRIPTION
		"String containing the vendor name of the UPS"
	::= { s31SysUpsEntry 2 }

s31SysUpsType OBJECT-TYPE
	SYNTAX	DisplayString
	ACCESS	read-write
	STATUS	mandatory
	DESCRIPTION
		"String containing the type of the UPS"
	::= { s31SysUpsEntry 3 }

s31SysUpsOemAgentIpAddress OBJECT-TYPE
	SYNTAX	IpAddress
	ACCESS	read-write
	STATUS	mandatory
	DESCRIPTION
		"IP address of an OEM UPS SNMP agent"
	::= { s31SysUpsEntry 4 }

s31SysUpsPort OBJECT-TYPE
	SYNTAX	INTEGER
	ACCESS	read-write
	STATUS	mandatory
	DESCRIPTION
		"Port number for web administration"
	::= { s31SysUpsEntry 5 }

s31SysUpsSnmpCommunity OBJECT-TYPE
	SYNTAX	DisplayString
	ACCESS	read-write
	STATUS	mandatory
	DESCRIPTION
		"Community string for SNMP access"
	::= { s31SysUpsEntry 6 }

s31SysUpsOemAgentAddressType OBJECT-TYPE
	SYNTAX	INTEGER{
        unknown(0),
        ipv4(1),
        ipv6(2),
        ipv4z(3),
        ipv6z(4),
        dns(16)
	}
	ACCESS	read-write
	STATUS	mandatory
	DESCRIPTION
		"Identify IP address type of the OEM UPS SNMP agent"
	::= { s31SysUpsEntry 7 }

s31SysUpsOemAgentAddress OBJECT-TYPE
    SYNTAX  OCTET STRING (SIZE (1..64))
	ACCESS	read-write
	STATUS	mandatory
	DESCRIPTION
		"IPv6 address for the OEM UPS SNMP agent"
	::= { s31SysUpsEntry 8 }

s31MgmtBladeReboot OBJECT-TYPE
	SYNTAX	INTEGER{
		unknown(1),
		disable(2),
		enable(3)
	}
	ACCESS	read-write
	STATUS	mandatory
	DESCRIPTION
		"Reboot the management blade"
	::= { s31SystemInfo 7 }

s31SysFsiomStatus OBJECT-TYPE
	SYNTAX	INTEGER{
		unknown(1),
		ok(2),
		not-present(3),
		error(4),
		critical(5)
	}
	ACCESS	read-only
	STATUS	mandatory
	DESCRIPTION
		"Current status of this front side I/O module"
	::= { s31SysFsiom 1 }

s31SysFsiomManufacturer OBJECT-TYPE
	SYNTAX	DisplayString
	ACCESS	read-only
	STATUS	mandatory
	DESCRIPTION
		"String containing the front side I/O module manufacturer"
	::= { s31SysFsiom 2 }

s31SysFsiomProductName OBJECT-TYPE
	SYNTAX	DisplayString
	ACCESS	read-only
	STATUS	mandatory
	DESCRIPTION
		"Product name of the front side I/O module"
	::= { s31SysFsiom 3 }

s31SysFsiomProductVersion OBJECT-TYPE
	SYNTAX	DisplayString
	ACCESS	read-only
	STATUS	mandatory
	DESCRIPTION
		"Product version of the front side I/O module"
	::= { s31SysFsiom 4 }

s31SysFsiomSerialNumber OBJECT-TYPE
	SYNTAX	DisplayString
	ACCESS	read-only
	STATUS	mandatory
	DESCRIPTION
		"Serial number of the front side I/O module"
	::= { s31SysFsiom 5 }

s31SysFsiomFirmwareVersion OBJECT-TYPE
	SYNTAX	DisplayString
	ACCESS	read-only
	STATUS	mandatory
	DESCRIPTION
		"The firmware version of the front side I/O module"
	::= { s31SysFsiom 6 }

s31SysFsiomConnectionStatus OBJECT-TYPE
	SYNTAX	INTEGER{
		unknown(1),
		free(2),
		connecting(3),
		connected(4),
		mounting(5),
		mounted(6),
		unmounting(7),
		disconnecting(8)
	}
	ACCESS	read-only
	STATUS	mandatory
	DESCRIPTION
		"Current connection status of this front side I/O module,
		 i.e. what is currently happening to the USB hub.
		 For 'connected' and 'mounted' s31SysFsiomConnectionTarget specifies 
		 the target blade, for all other values s31SysFsiomConnectionTarget
		 is not defined."
	::= { s31SysFsiom 7 }

s31SysFsiomConnectionTarget OBJECT-TYPE
	SYNTAX	INTEGER (1..20)
	ACCESS	read-only
	STATUS	mandatory
	DESCRIPTION
		"Server blade number the USB hub is connected/mounted to.
		 Index into the Server blade control table (1 based)
		 Only valid if s31SysFsiomConnectionStatus is 'connected' or 'mounted'."
	::= { s31SysFsiom 8 }

s31SysFsiomModelName OBJECT-TYPE
	SYNTAX	DisplayString
	ACCESS	read-only
	STATUS	mandatory
	DESCRIPTION
		"Model name of the front side I/O module"
	::= { s31SysFsiom 9 }

s31SysFsiomManufactureDate OBJECT-TYPE
	SYNTAX	DisplayString
	ACCESS	read-only
	STATUS	mandatory
	DESCRIPTION
		"Manufacture date of front side I/O module"
	::= { s31SysFsiom 10 }

-- **********************************************************************************************
--
-- GROUP: s31ServerBlade
--
--      s31MgmtAgent MIB:        1.3.6.1.4.1.7244.1.1.1
--      s31ServerBlade group:              1.3.6.1.4.1.7244.1.1.1.4
--
-- **********************************************************************************************

s31SvrCtrlTable OBJECT-TYPE
	SYNTAX	SEQUENCE OF S31SvrCtrlEntry
	ACCESS	not-accessible
	STATUS	mandatory
	DESCRIPTION
		"Table with data of server blade control setting"
	::= { s31SvrCtrlInfo 1 }

s31SvrCtrlEntry OBJECT-TYPE
	SYNTAX	S31SvrCtrlEntry
	ACCESS	not-accessible
	STATUS	mandatory
	DESCRIPTION
		""
	INDEX	{ s31SvrCtrlBladeId }
	::= { s31SvrCtrlTable 1 }

S31SvrCtrlEntry ::=
	SEQUENCE {
		s31SvrCtrlBladeId
			INTEGER,
		s31SvrCtrlCpuMode
			INTEGER,
		s31SvrCtrlBootMode
			INTEGER,
		s31SvrCtrlAdministrativeUrl
			DisplayString,
		s31SvrCtrlPower
			INTEGER,
		s31SvrCtrlMaxRestartRetries
			INTEGER,
		s31SvrCtrlStatLed
			INTEGER,
		s31SvrCtrlDumpFlag
			INTEGER
	}

s31SvrCtrlBladeId OBJECT-TYPE
	SYNTAX	INTEGER (1..20)
	ACCESS	read-only
	STATUS	mandatory
	DESCRIPTION
		"Server blade number, index into the Server blade control table (1 based)"
	::={ s31SvrCtrlEntry 1 }

s31SvrCtrlCpuMode OBJECT-TYPE
	SYNTAX	INTEGER{
			unknown(1),
			battery(2),
			performance(3)
		}
	ACCESS	read-only
	STATUS	mandatory
	DESCRIPTION
		"Current CPU mode of the server blade"
	::={ s31SvrCtrlEntry 2 }

s31SvrCtrlBootMode OBJECT-TYPE
	SYNTAX	INTEGER{
		unknown(1),
		normal(2),
		pxe-lan-1(3),
		pxe-lan-2(4),
		add-in-pci-1(5),
		add-in-pci-2(6),
		pxe-lan-3(7),
		pxe-lan-4(8),
		pxe-lan-5(9),
		pxe-lan-6(10),
		pxe-lan-7(11),
		pxe-lan-8(12),
		inventory(13),
		init-boot(14),
		pxe-lan-9(15),
		pxe-lan-10(16),
		pxe-lan-11(17),
		pxe-lan-12(18)

	}
	ACCESS	read-write
	STATUS	mandatory
	DESCRIPTION
		"Booting mode of the server blade"
	::={ s31SvrCtrlEntry 3 }

s31SvrCtrlAdministrativeUrl OBJECT-TYPE
	SYNTAX	DisplayString
	ACCESS	read-only
	STATUS	mandatory
	DESCRIPTION
		"Administrative URL of the server blade"
	::={ s31SvrCtrlEntry 4 }

s31SvrCtrlPower OBJECT-TYPE
	SYNTAX	INTEGER{
		unknown(1),
		on(2),
		off(3),
		power-cycle(4),
		reset(5),
		nmi(6),
		force-off(7)
	}
	ACCESS	read-write
	STATUS	mandatory
	DESCRIPTION
		"Power control of the server blade"
	::={ s31SvrCtrlEntry 5 }

s31SvrCtrlMaxRestartRetries OBJECT-TYPE
	SYNTAX	INTEGER{
		unknown(1),
		retry-0(2),
		retry-1(3),
		retry-2(4),
		retry-3(5),
		retry-4(6),
		retry-5(7),
		retry-6(8),
		retry-7(9)
	}
	ACCESS	read-write
	STATUS	mandatory
	DESCRIPTION
		"Maximum number of retries to reboot/restart the server when a
			shutdown (and power-off) had occured"
	::={ s31SvrCtrlEntry 6 }

s31SvrCtrlStatLed OBJECT-TYPE
	SYNTAX	INTEGER{
		unknown(1),
		off(2),
		blinking(3),
		on(4)
	}
	ACCESS	read-write
	STATUS	mandatory
	DESCRIPTION
		"Configure server blade IDENTIFY (formerly STAT) LED status (off/blinking)"
	::= { s31SvrCtrlEntry 7 }

s31SvrCtrlDumpFlag OBJECT-TYPE
	SYNTAX	INTEGER{
		unknown(1),
		normal(2),
		memorydump(3)
	}
	ACCESS	read-only
	STATUS	mandatory
	DESCRIPTION
		"Get the memory dump flag status from BMC"
	::= { s31SvrCtrlEntry 8 }

s31SvrBladeTable OBJECT-TYPE
	SYNTAX	SEQUENCE OF S31SvrBladeEntry
	ACCESS	not-accessible
	STATUS	mandatory
	DESCRIPTION
		"Table with data of server blade basic information"
	::={ s31SvrBlade 1 }

s31SvrBladeEntry OBJECT-TYPE
	SYNTAX	S31SvrBladeEntry
	ACCESS	not-accessible
	STATUS	mandatory
	DESCRIPTION
		""
	INDEX	{ s31SvrBladeId }
	::={ s31SvrBladeTable 1 }

S31SvrBladeEntry ::=
	SEQUENCE {
		s31SvrBladeId
			INTEGER,
		s31SvrBladeStatus
			INTEGER,
		s31SvrBladeManufacture
			DisplayString,
		s31SvrBladeManufactureDate
			DisplayString,
		s31SvrBladeSerialNumber
			DisplayString,
		s31SvrBladeProductName
			DisplayString,
		s31SvrBladeModelName
			DisplayString,
		s31SvrBladeHardwareVersion
			DisplayString,
		s31SvrBladeFirmwareVersion
			DisplayString,
		s31SvrBladeBiosVersion
			DisplayString,
		s31SvrBladeNumberCpuSockets
			INTEGER,
		s31SvrBladeNumberMemorySockets
			INTEGER,
		s31SvrBladeOsType
			DisplayString,
		s31SvrBladeOsVersion
			DisplayString,
		s31SvrBladePciAddInPresence
			INTEGER,
		s31SvrBladeKmeVersion
			DisplayString,
		s31SvrBladeIdentSerialNumber
			DisplayString,
		s31SvrBladeGuid
			DisplayString,
		s31SvrBladeDaughterCardType
			DisplayString,
		s31SvrBladeBiosViomSettingStatus
			INTEGER,
		s31SvrHostname
			DisplayString,
		s31SvrBladeCustomerProductName
			DisplayString,
		s31SvrBladeAssetTag
			OCTET STRING (SIZE (1..40)),
		s31SvrBladeConsumptionMode
			INTEGER,
		s31SvrBladeDVDAllowAssignment
			INTEGER,
		s31SvrBladeDVDAssignment
			INTEGER
		}

s31SvrBladeId OBJECT-TYPE
	SYNTAX	INTEGER (1..20)
	ACCESS	read-only
	STATUS	mandatory
	DESCRIPTION
		"Server blade number, index into the server blade table (1 based)"
	::={ s31SvrBladeEntry 1 }

s31SvrBladeStatus OBJECT-TYPE
	SYNTAX	INTEGER{
		unknown(1),
		ok(2),
		not-present(3),
		error(4),
		critical(5),
		standby(6)
	}
	ACCESS	read-only
	STATUS	mandatory
	DESCRIPTION
		"Current status of this server blade"
	::={ s31SvrBladeEntry 2 }

s31SvrBladeManufacture OBJECT-TYPE
	SYNTAX	DisplayString
	ACCESS	read-only
	STATUS	mandatory
	DESCRIPTION
		"String containing the server blade manufacturer"
	::={ s31SvrBladeEntry 3 }

s31SvrBladeManufactureDate OBJECT-TYPE
	SYNTAX	DisplayString
	ACCESS	read-only
	STATUS	mandatory
	DESCRIPTION
		"Manufacture date of the server blade"
	::={ s31SvrBladeEntry 4 }

s31SvrBladeSerialNumber OBJECT-TYPE
	SYNTAX	DisplayString
	ACCESS	read-only
	STATUS	mandatory
	DESCRIPTION
		"The serial number of the server blade"
	::={ s31SvrBladeEntry 5 }

s31SvrBladeProductName OBJECT-TYPE
	SYNTAX	DisplayString
	ACCESS	read-only
	STATUS	mandatory
	DESCRIPTION
		"The internal product name of the server blade.
		 Caveat: this OID is used by deployment software 
		 and is expected to be in the format Dxxxx."
	::={ s31SvrBladeEntry 6 }

s31SvrBladeModelName OBJECT-TYPE
	SYNTAX	DisplayString
	ACCESS	read-only
	STATUS	mandatory
	DESCRIPTION
		"The product model name of the server blade"
	::={ s31SvrBladeEntry 7 }

s31SvrBladeHardwareVersion OBJECT-TYPE
	SYNTAX	DisplayString
	ACCESS	read-only
	STATUS	mandatory
	DESCRIPTION
		"The hardware version of the server blade"
	::={ s31SvrBladeEntry 8 }

s31SvrBladeFirmwareVersion OBJECT-TYPE
	SYNTAX	DisplayString
	ACCESS	read-only
	STATUS	mandatory
	DESCRIPTION
		"The firmware version of the server blade"
	::={ s31SvrBladeEntry 9 }

s31SvrBladeBiosVersion OBJECT-TYPE
	SYNTAX	DisplayString
	ACCESS	read-only
	STATUS	mandatory
	DESCRIPTION
		"The bios version of the server blade"
	::={ s31SvrBladeEntry 10 }

s31SvrBladeNumberCpuSockets OBJECT-TYPE
	SYNTAX	INTEGER
	ACCESS	read-only
	STATUS	mandatory
	DESCRIPTION
		"Number of CPU sockets available on the server blade"
	::={ s31SvrBladeEntry 11 }

s31SvrBladeNumberMemorySockets OBJECT-TYPE
	SYNTAX	INTEGER
	ACCESS	read-only
	STATUS	mandatory
	DESCRIPTION
		"Number of memory module sockets available on the server blade"
	::={ s31SvrBladeEntry 12 }

s31SvrBladeOsType OBJECT-TYPE
	SYNTAX	DisplayString
	ACCESS	read-only
	STATUS	mandatory
	DESCRIPTION
		"The OS type of the server blade"
	::={ s31SvrBladeEntry 13 }

s31SvrBladeOsVersion OBJECT-TYPE
	SYNTAX	DisplayString
	ACCESS	read-only
	STATUS	mandatory
	DESCRIPTION
		"The OS version of the server blade"
	::={ s31SvrBladeEntry 14 }

s31SvrBladePciAddInPresence OBJECT-TYPE
	SYNTAX	INTEGER{
		unknown(1),
		not-present(2),
		present(3)
	}
	ACCESS	read-only
	STATUS	mandatory
	DESCRIPTION
		"Current presence of this server blade PCI Add-In card"
	::={ s31SvrBladeEntry 15 }

s31SvrBladeKmeVersion OBJECT-TYPE
	SYNTAX	DisplayString
	ACCESS	read-only
	STATUS	mandatory
	DESCRIPTION
		"The KME version of the server blade"
	::={ s31SvrBladeEntry 16 }

s31SvrBladeIdentSerialNumber OBJECT-TYPE
	SYNTAX	DisplayString
	ACCESS	read-only
	STATUS	mandatory
	DESCRIPTION
		"The ident Serial Number of the server blade"
	::={ s31SvrBladeEntry 17 }

s31SvrBladeGuid OBJECT-TYPE
	SYNTAX	DisplayString
	ACCESS	read-only
	STATUS	mandatory
	DESCRIPTION
		"The GUID of the server blade"
	::={ s31SvrBladeEntry 18 }

s31SvrBladeDaughterCardType OBJECT-TYPE
	SYNTAX	DisplayString
	ACCESS	read-only
	STATUS	mandatory
	DESCRIPTION
		"The DUAGHTER Card Type of the server blade"
	::={ s31SvrBladeEntry 19 }

s31SvrBladeBiosViomSettingStatus OBJECT-TYPE
	SYNTAX	INTEGER{
		unknown(1),
		power-on-pending(2),
		processing(3),
		mmb-error(4),
		viom-setting-ok(5),
		viom-setting-failed(6),
		boot-without-viom(7),
		inventory-boot-ok(8),
		inventory-boot-failed(9),
		n-a(10)
	}
	ACCESS	read-only
	STATUS	mandatory
	DESCRIPTION
		"The DUAGHTER Card Type of the server blade"
	::={ s31SvrBladeEntry 20 }

s31SvrHostname OBJECT-TYPE
	SYNTAX	DisplayString
	ACCESS	read-write
	STATUS	mandatory
	DESCRIPTION
		"Hostname of this server blade"
	::={ s31SvrBladeEntry 21 }

s31SvrBladeCustomerProductName OBJECT-TYPE
	SYNTAX	DisplayString
	ACCESS	read-only
	STATUS	mandatory
	DESCRIPTION
		"The product name of the server blade as known to the 
		 end customer"
	::={ s31SvrBladeEntry 22 }

s31SvrBladeAssetTag OBJECT-TYPE
    SYNTAX  OCTET STRING (SIZE (1..40))
	ACCESS	read-write
	STATUS	mandatory
	DESCRIPTION
		"Asset tag for this server blade"
	::={ s31SvrBladeEntry 23 }

s31SvrBladeConsumptionMode OBJECT-TYPE
	SYNTAX	INTEGER{
		unknown(1),
		unmanaged(2),
		enforced(3),
		low-noise(4),
		minimum(5),
		adaptive(6)
	}
	ACCESS	read-only
	STATUS	mandatory
	DESCRIPTION
		"Specifies the power consumption management mode currently
		configured for this server blade"
	::={ s31SvrBladeEntry 24 }

s31SvrBladeDVDAllowAssignment OBJECT-TYPE
	SYNTAX	INTEGER{
		unknown(1),
		allowed(2),
		not-allowed(3)
	}
	ACCESS	read-only
	STATUS	mandatory
	DESCRIPTION
		"Specifies whether the chassis DVD drive may be assigned to this
		server blade or not"
	::={ s31SvrBladeEntry 25 }

s31SvrBladeDVDAssignment OBJECT-TYPE
	SYNTAX	INTEGER{
		unknown(1),
		unassigned(2),
		assigned(3)
	}
	ACCESS	read-write
	STATUS	mandatory
	DESCRIPTION
		"Specifies whether the chassis DVD drive is assigned to this
		server blade"
	::={ s31SvrBladeEntry 26 }

s31CpuTable OBJECT-TYPE
	SYNTAX	SEQUENCE OF S31CpuEntry
	ACCESS	not-accessible
	STATUS	mandatory
	DESCRIPTION
		"Table with data of server blade CPU information"
	::={ s31SvrCpu 1 }

s31CpuEntry OBJECT-TYPE
	SYNTAX	S31CpuEntry
	ACCESS	not-accessible
	STATUS	mandatory
	DESCRIPTION
		""
	INDEX	{ s31CpuBladeId, s31CpuId }
	::={ s31CpuTable 1 }

S31CpuEntry ::=
	SEQUENCE {
		s31CpuBladeId
			INTEGER,
		s31CpuId
			INTEGER,
		s31CpuType
			INTEGER,
		s31CpuFrequency
			INTEGER,
		s31CpuStep
			DisplayString,
		s31CpuStatus
			INTEGER,
		s31CpuName
			INTEGER,
		s31CpuSocketDesignation
			DisplayString,
		s31CpuManufacturer
			DisplayString
	}

s31CpuBladeId OBJECT-TYPE
	SYNTAX	INTEGER (1..20)
	ACCESS	read-only
	STATUS	mandatory
	DESCRIPTION
		"Server blade number, index into the CPU table (1 based)"
	::={ s31CpuEntry 1 }

s31CpuId OBJECT-TYPE
	SYNTAX	INTEGER (1..4)
	ACCESS	read-only
	STATUS	mandatory
	DESCRIPTION
		"CPU number, index into the CPU table (1 based)"
	::={ s31CpuEntry 2 }

s31CpuType OBJECT-TYPE
	SYNTAX	INTEGER{
		unknown(1),
		pentium-processor-family(2),
		pentium-pro-processor(3),
		pentium-ii-processor(4),
		pentium-processor-with-mmx-technology(5),
		celeron-processor(6),
		pentium-ii-Xeon-processor(7),
		pentium-iii-processor(8),
		m1-family(9),
		pentium-iv-processor(10),
		pentium-m-processor(11),
		xeon-processor(12),
                amd-opteron(13)
	}
	ACCESS	read-only
	STATUS	mandatory
	DESCRIPTION
		"Type of the CPU"
	::={ s31CpuEntry 3 }

s31CpuFrequency OBJECT-TYPE
	SYNTAX	INTEGER
	ACCESS	read-only
	STATUS	mandatory
	DESCRIPTION
		"Frequency of the CPU (in MHz)"
	::={ s31CpuEntry 4 }

s31CpuStep OBJECT-TYPE
	SYNTAX	DisplayString
	ACCESS	read-only
	STATUS	mandatory
	DESCRIPTION
		"Step (version) of the CPU"
	::={ s31CpuEntry 5 }

s31CpuStatus OBJECT-TYPE
	SYNTAX	INTEGER{
		unknown(1),
		ok(2),
		not-present(3),
		error(4),
		critical(5),
		missing-termination(6),
		disable(7)
	}
	ACCESS	read-only
	STATUS	mandatory
	DESCRIPTION
		"Current status of this CPU"
	::={ s31CpuEntry 6 }

s31CpuName OBJECT-TYPE
	SYNTAX	INTEGER{
		unknown(1),
		unknown-cpu(2),
		celeron(3),
		pentium-ii-processor(4),
		pentium-iii(5),
		pentium-iv(6),
		pentium-m(7),
		intel-xeon(8)
	}
	ACCESS	read-only
	STATUS	mandatory
	DESCRIPTION
		"Name of the CPU"
	::={ s31CpuEntry 7 }

s31CpuSocketDesignation OBJECT-TYPE
	SYNTAX	DisplayString
	ACCESS	read-only
	STATUS	mandatory
	DESCRIPTION
		"String containing the socket designation of a CPU"
	::={ s31CpuEntry 8 }

s31CpuManufacturer OBJECT-TYPE
	SYNTAX	DisplayString
	ACCESS	read-only
	STATUS	mandatory
	DESCRIPTION
		"String containing the CPU manufacturer"
	::={ s31CpuEntry 9 }

s31MemoryCtrlTable OBJECT-TYPE
	SYNTAX	SEQUENCE OF S31MemoryCtrlEntry
	ACCESS	not-accessible
	STATUS	mandatory
	DESCRIPTION
		"Table with data of server blade memory control information"
	::={ s31SvrMemory 1 }

s31MemoryCtrlEntry OBJECT-TYPE
	SYNTAX	S31MemoryCtrlEntry
	ACCESS	not-accessible
	STATUS	mandatory
	DESCRIPTION
		""
	INDEX	{ s31MemCtrlBladeId }
	::={ s31MemoryCtrlTable 1 }

S31MemoryCtrlEntry ::=
	SEQUENCE {
		s31MemCtrlBladeId
			INTEGER,
		s31MemCtrlPhysicalMemorySize
			INTEGER
	}

s31MemCtrlBladeId OBJECT-TYPE
	SYNTAX	INTEGER (1..20)
	ACCESS	read-only
	STATUS	mandatory
	DESCRIPTION
		"Server blade number, index into the memory control table (1 based)"
	::={ s31MemoryCtrlEntry 1 }

s31MemCtrlPhysicalMemorySize OBJECT-TYPE
	SYNTAX	INTEGER
	ACCESS	read-only
	STATUS	mandatory
	DESCRIPTION
		"Size of the whole physical memory on the server blade"
	::={ s31MemoryCtrlEntry 2 }

s31MemoryModulesTable OBJECT-TYPE
	SYNTAX	SEQUENCE OF S31MemoryModulesEntry
	ACCESS	not-accessible
	STATUS	mandatory
	DESCRIPTION
		"Table with data of server blade memory modules information"
	::={ s31SvrMemory 2 }

s31MemoryModulesEntry OBJECT-TYPE
	SYNTAX	S31MemoryModulesEntry
	ACCESS	not-accessible
	STATUS	mandatory
	DESCRIPTION
		""
	INDEX	{ s31MemModuleBladeId, s31MemModuleId }
	::={ s31MemoryModulesTable 1 }

S31MemoryModulesEntry ::=
	SEQUENCE {
		s31MemModuleBladeId
			INTEGER,
		s31MemModuleId
			INTEGER,
		s31MemModuleStatus
			INTEGER,
		s31MemModuleSize
			INTEGER,
		s31MemModuleType
			INTEGER,
		s31MemModuleSocketDesignation
			DisplayString,
		s31MemModuleSpeed
			INTEGER,
		s31MemModuleForm
			DisplayString,
		s31MemModuleXType
			DisplayString
	}

s31MemModuleBladeId OBJECT-TYPE
	SYNTAX	INTEGER (1..20)
	ACCESS	read-only
	STATUS	mandatory
	DESCRIPTION
		"Server blade number, index into the memory modules table (1 based)"
	::={ s31MemoryModulesEntry 1 }

s31MemModuleId OBJECT-TYPE
	SYNTAX	INTEGER (1..8)
	ACCESS	read-only
	STATUS	mandatory
	DESCRIPTION
		"Memory modules number, index into the memory modules table (1 based)"
	::={ s31MemoryModulesEntry 2 }

s31MemModuleStatus OBJECT-TYPE
	SYNTAX	INTEGER{
		unknown(1),
		disable(2),
		ok(3),
		not-present(4),
		critical(5),
		prefailure-warning(6)
	}
	ACCESS	read-only
	STATUS	mandatory
	DESCRIPTION
		"Status of the memory module socket.
			Status disabled(2) when module is disabled by BIOS setup.
			Status not-present(4) for empty sockets.
			Status critical(5) when module has not correctable error.
			Status prefailure-warning(6) when module has too many correctable errors within
			a certain time period."
	::={ s31MemoryModulesEntry 3 }

s31MemModuleSize OBJECT-TYPE
	SYNTAX	INTEGER
	ACCESS	read-only
	STATUS	mandatory
	DESCRIPTION
		"Size of this memory module (in bytes)"
	::={ s31MemoryModulesEntry 4 }

s31MemModuleType OBJECT-TYPE
	SYNTAX	INTEGER
	ACCESS	read-only
	STATUS	mandatory
	DESCRIPTION
		"Information about the type of a memory module (Parity, ECC, EDO, SIMM, DIMM...).
                 The type is a combination of one or more bits.
			Bit field:	Bit 0 - Other
					Bit 1 - Unknown
					Bit 2 - Standard
					Bit 3 - Fast page mode
					Bit 4 - EDO
					Bit 5 - Parity
					Bit 6 - ECC
					Bit 7 - SIMM
					Bit 8 - DIMM
					Bit 9 - Burst EDO
					Bit 10 - SDRAM
					Bit 11 - DDR
					Bit 12 - DDR II
					Bit 13 - DDR III Unbuffered
					Bit 14 - DDR III Registered
					Bit 15 - DDR III Buffered
		 Unused bits are set to zero.
		 In the future, new memory types have will described
		 via s31MemModuleXType. "
	::={ s31MemoryModulesEntry 5 }

s31MemModuleSocketDesignation OBJECT-TYPE
	SYNTAX	DisplayString
	ACCESS	read-only
	STATUS	mandatory
	DESCRIPTION
		"String containing the socket designation of a memory module"
	::={ s31MemoryModulesEntry 6 }

s31MemModuleSpeed OBJECT-TYPE
	SYNTAX	INTEGER
	ACCESS	read-only
	STATUS	mandatory
	DESCRIPTION
		"Current speed of this memory module"
	::={ s31MemoryModulesEntry 7 }

s31MemModuleForm OBJECT-TYPE
    SYNTAX       DisplayString
    ACCESS       read-only
    STATUS       mandatory
    DESCRIPTION  "Memory module form (SIMM, DIMM, ...)"
	::={ s31MemoryModulesEntry 8 }

s31MemModuleXType OBJECT-TYPE
    SYNTAX       DisplayString
    ACCESS       read-only
    STATUS       mandatory
    DESCRIPTION  "Memory module type (SDRAM, DDRAM, DDR2, DDR3, ...)"
	::={ s31MemoryModulesEntry 9 }

s31SvrVoltageTable OBJECT-TYPE
	SYNTAX	SEQUENCE OF S31SvrVoltageEntry
	ACCESS	not-accessible
	STATUS	mandatory
	DESCRIPTION
		"Table with data of all server blade voltages"
	::={ s31SvrVoltage 1 }

s31SvrVoltageEntry OBJECT-TYPE
	SYNTAX	S31SvrVoltageEntry
	ACCESS	not-accessible
	STATUS	mandatory
	DESCRIPTION
		""
	INDEX	{ s31SvrVoltageBladeId, s31SvrVoltageId }
	::={ s31SvrVoltageTable 1 }

S31SvrVoltageEntry ::=
	SEQUENCE {
		s31SvrVoltageBladeId
			INTEGER,
		s31SvrVoltageId
			INTEGER,
		s31SvrVoltageStatus
			INTEGER,
		s31SvrVoltageDesignation
			DisplayString,
		s31SvrVoltageMinimumValue
			INTEGER,
		s31SvrVoltageMaximumValue
			INTEGER,
		s31SvrVoltageCurrentValue
			INTEGER,
		s31SvrVoltageNominalValue
			INTEGER
	}

s31SvrVoltageBladeId OBJECT-TYPE
	SYNTAX	INTEGER (1..20)
	ACCESS	read-only
	STATUS	mandatory
	DESCRIPTION
		"Server blade number, index into the voltage table (1 based)"
	::={ s31SvrVoltageEntry 1 }

s31SvrVoltageId OBJECT-TYPE
	SYNTAX	INTEGER (1..20)
	ACCESS	read-only
	STATUS	mandatory
	DESCRIPTION
		"Voltage number, index into the voltage table (1 based)"
	::={ s31SvrVoltageEntry 2 }

s31SvrVoltageStatus OBJECT-TYPE
	SYNTAX	INTEGER{
		unknown(1),
		not-available(2),
		ok(3),
		too-low(4),
		too-high(5)
	}
	ACCESS	read-only
	STATUS	mandatory
	DESCRIPTION
		"Current status of this voltage"
	::={ s31SvrVoltageEntry 3 }

s31SvrVoltageDesignation OBJECT-TYPE
	SYNTAX	DisplayString
	ACCESS	read-only
	STATUS	mandatory
	DESCRIPTION
		"String containing the voltage designation"
	::={ s31SvrVoltageEntry 4 }

s31SvrVoltageMinimumValue OBJECT-TYPE
	SYNTAX	INTEGER
	ACCESS	read-only
	STATUS	mandatory
	DESCRIPTION
		"Voltage minimum level (1/100th Volts)"
	::={ s31SvrVoltageEntry 5 }

s31SvrVoltageMaximumValue OBJECT-TYPE
	SYNTAX	INTEGER
	ACCESS	read-only
	STATUS	mandatory
	DESCRIPTION
		"Voltage maximum level (1/100th Volts)"
	::={ s31SvrVoltageEntry 6 }

s31SvrVoltageCurrentValue OBJECT-TYPE
	SYNTAX	INTEGER
	ACCESS	read-only
	STATUS	mandatory
	DESCRIPTION
		"Voltage current level (1/100th Volts)"
	::={ s31SvrVoltageEntry 7 }

s31SvrVoltageNominalValue OBJECT-TYPE
	SYNTAX	INTEGER
	ACCESS	read-only
	STATUS	mandatory
	DESCRIPTION
		"Voltage nominal level (1/100th Volts)"
	::={ s31SvrVoltageEntry 8 }

s31SvrTemperatureTable OBJECT-TYPE
	SYNTAX	SEQUENCE OF S31SvrTemperatureEntry
	ACCESS	not-accessible
	STATUS	mandatory
	DESCRIPTION
		"Table with data of server blade temperature information"
	::={ s31SvrTemperature 1 }

s31SvrTemperatureEntry OBJECT-TYPE
	SYNTAX	S31SvrTemperatureEntry
	ACCESS	not-accessible
	STATUS	mandatory
	DESCRIPTION
		""
	INDEX	{ s31SvrTempBladeId, s31SvrTempSensorId }
	::={ s31SvrTemperatureTable 1 }

S31SvrTemperatureEntry ::=
	SEQUENCE {
		s31SvrTempBladeId
			INTEGER,
		s31SvrTempSensorId
			INTEGER,
		s31SvrTempSensorStatus
			INTEGER,
		s31SvrTempSensorDesignation
			DisplayString,
		s31SvrTempUpperWarningLevel
			INTEGER,
		s31SvrTempUpperCriticalLevel
			INTEGER,
		s31SvrTempCurrentValue
			INTEGER,
		s31SvrTempLowerWarningLevel
			INTEGER,
		s31SvrTempLowerCriticalLevel
			INTEGER
	}

s31SvrTempBladeId OBJECT-TYPE
	SYNTAX	INTEGER (1..20)
	ACCESS	read-only
	STATUS	mandatory
	DESCRIPTION
		"Server blade number, index into the temperature table (1 based)"
	::={ s31SvrTemperatureEntry 1 }

s31SvrTempSensorId OBJECT-TYPE
	SYNTAX	INTEGER (1..20)
	ACCESS	read-only
	STATUS	mandatory
	DESCRIPTION
		"Temperature sensor number, index into the temperature table (1 based)"
	::={ s31SvrTemperatureEntry 2 }

s31SvrTempSensorStatus OBJECT-TYPE
	SYNTAX	INTEGER{
		unknown(1),
		sensor-disable(2),
		ok(3),
		sensor-fail(4),
		warning-temp-warm(5),
		critical-temp-warm(6),
		not-available(7),
                warning-temp-cold(8),
                critical-temp-cold(9)
	}
	ACCESS	read-only
	STATUS	mandatory
	DESCRIPTION
		"Current status of this temperature sensor"
	::={ s31SvrTemperatureEntry 3 }

s31SvrTempSensorDesignation OBJECT-TYPE
	SYNTAX	DisplayString
	ACCESS	read-only
	STATUS	mandatory
	DESCRIPTION
		"String containing the temperature sensor designation"
	::={ s31SvrTemperatureEntry 4 }

s31SvrTempUpperWarningLevel OBJECT-TYPE
	SYNTAX	INTEGER
	ACCESS	read-only
	STATUS	mandatory
	DESCRIPTION
		"System sends a temperature upper warning when temperature rises ABOVE
			this level (degrees Celsius)"
	::={ s31SvrTemperatureEntry 5 }

s31SvrTempUpperCriticalLevel OBJECT-TYPE
	SYNTAX	INTEGER
	ACCESS	read-only
	STATUS	mandatory
	DESCRIPTION
		"System becomes critical when temperature rises ABOVE this level
			(degrees Celsius)"
	::={ s31SvrTemperatureEntry 6 }

s31SvrTempCurrentValue OBJECT-TYPE
	SYNTAX	INTEGER
	ACCESS	read-only
	STATUS	mandatory
	DESCRIPTION
		"Current temperature value (degrees Celsius)"
	::={ s31SvrTemperatureEntry 7 }

s31SvrTempLowerWarningLevel OBJECT-TYPE
	SYNTAX	INTEGER
	ACCESS	read-only
	STATUS	mandatory
	DESCRIPTION
		"System sends a temperature lower warning when temperature down BELOW
			this level (degrees Celsius)"
	::={ s31SvrTemperatureEntry 8 }

s31SvrTempLowerCriticalLevel OBJECT-TYPE
	SYNTAX	INTEGER
	ACCESS	read-only
	STATUS	mandatory
	DESCRIPTION
		"System becomes critical when temperature down BELOW this level
			(degrees Celsius)"
	::={ s31SvrTemperatureEntry 9 }

s31SvrNicInfoTable OBJECT-TYPE
	SYNTAX	SEQUENCE OF S31SvrNicInfoEntry
	ACCESS	not-accessible
	STATUS	mandatory
	DESCRIPTION
		"Table with data of server blade NIC information"
	::={ s31SvrNicInfo 1 }

s31SvrNicInfoEntry OBJECT-TYPE
	SYNTAX	S31SvrNicInfoEntry
	ACCESS	not-accessible
	STATUS	mandatory
	DESCRIPTION
		""
	INDEX	{ s31SvrNicBladeId, s31SvrNicId }
	::={ s31SvrNicInfoTable 1 }

S31SvrNicInfoEntry ::=
	SEQUENCE {
		s31SvrNicBladeId
			INTEGER,
		s31SvrNicId
			INTEGER,
		s31SvrNicPhysicalAddress
			PhysAddress,
		s31SvrNicIpAddress
			IpAddress,
		s31SvrManufactureMac
			DisplayString,
		s31SvrNicType
			INTEGER,
		s31SvrNicAddressType
			INTEGER,
		s31SvrNicAddress
			OCTET STRING (SIZE (1..64))
	}

s31SvrNicBladeId OBJECT-TYPE
	SYNTAX	INTEGER (1..20)
	ACCESS	read-only
	STATUS	mandatory
	DESCRIPTION
		"Server blade number, index into the NIC table (1 based)"
	::={ s31SvrNicInfoEntry 1 }

s31SvrNicId OBJECT-TYPE
	SYNTAX	INTEGER (1..20)
	ACCESS	read-only
	STATUS	mandatory
	DESCRIPTION
		"Nic number, index into the NIC table (1 based)"
	::={ s31SvrNicInfoEntry 2 }

s31SvrNicPhysicalAddress OBJECT-TYPE
	SYNTAX	PhysAddress
	ACCESS	read-only
	STATUS	mandatory
	DESCRIPTION
		"The MAC address of this server blade"
	::={ s31SvrNicInfoEntry 3 }

s31SvrNicIpAddress OBJECT-TYPE
	SYNTAX	IpAddress
	ACCESS	read-only
	STATUS	mandatory
	DESCRIPTION
		"The IP address of this server blade"
	::={ s31SvrNicInfoEntry 4 }

s31SvrManufactureMac OBJECT-TYPE
	SYNTAX	DisplayString
	ACCESS	read-only
	STATUS	mandatory
	DESCRIPTION
		"The Manufacture Mac of this server blade"
	::={ s31SvrNicInfoEntry 5 }

s31SvrNicType OBJECT-TYPE
	SYNTAX	INTEGER{
		unknown(1),
		on-board-lan-controller(2),
		daughter-card(3),
		baseboard-management-controller(4)
		}
	ACCESS	read-only
	STATUS	mandatory
	DESCRIPTION
		"The Manufacture Mac of this server blade"
	::={ s31SvrNicInfoEntry 6 }

s31SvrNicAddressType OBJECT-TYPE
	SYNTAX	INTEGER{
        unknown(0),
        ipv4(1),
        ipv6(2),
        ipv4z(3),
        ipv6z(4),
        dns(16)
	}
	ACCESS	read-only
	STATUS	mandatory
	DESCRIPTION
		"Identify IP address type of this server blade"
	::={ s31SvrNicInfoEntry 7 }

s31SvrNicAddress OBJECT-TYPE
    SYNTAX  OCTET STRING (SIZE (1..64))
	ACCESS	read-only
	STATUS	mandatory
	DESCRIPTION
		"IP address for IPv6 for this server blade"
	::={ s31SvrNicInfoEntry 8 }

s31SvrCmosTable OBJECT-TYPE
	SYNTAX	SEQUENCE OF S31SvrCmosEntry
	ACCESS	not-accessible
	STATUS	mandatory
	DESCRIPTION
		"Table with data of server blade CMOS information"
	::={ s31SvrCmosConfig 1 }

s31SvrCmosEntry OBJECT-TYPE
	SYNTAX	S31SvrCmosEntry
	ACCESS	not-accessible
	STATUS	mandatory
	DESCRIPTION
		""
	INDEX	{ s31SvrCmosBladeId }
	::={ s31SvrCmosTable 1 }

S31SvrCmosEntry ::=
	SEQUENCE {
		s31SvrCmosBladeId
			INTEGER,
		s31SvrCmosBiosVersion
			DisplayString,
		s31SvrCmosMacAddr
			PhysAddress,
		s31SvrCmosDateTime
			DisplayString,
		s31SvrCmosRestoreTarget
			INTEGER,
		s31SvrCmosCtrl
			INTEGER
	}

s31SvrCmosBladeId OBJECT-TYPE
	SYNTAX	INTEGER (1..20)
	ACCESS	read-only
	STATUS	mandatory
	DESCRIPTION
		"Server blade number, index into the CMOS table (1 based)"
	::={ s31SvrCmosEntry 1 }

s31SvrCmosBiosVersion OBJECT-TYPE
	SYNTAX	DisplayString
	ACCESS	read-only
	STATUS	mandatory
	DESCRIPTION
		"The lastest BIOS version of this server blade backup to the management blade"
	::={ s31SvrCmosEntry 2 }

s31SvrCmosMacAddr OBJECT-TYPE
	SYNTAX	PhysAddress
	ACCESS	read-only
	STATUS	mandatory
	DESCRIPTION
		"The lastest MAC address of this server blade backup to the management blade"
	::={ s31SvrCmosEntry 3 }

s31SvrCmosDateTime OBJECT-TYPE
	SYNTAX	DisplayString
	ACCESS	read-only
	STATUS	mandatory
	DESCRIPTION
		"The lastest time of this server blade backup to the management blade"
	::={ s31SvrCmosEntry 4 }

s31SvrCmosRestoreTarget OBJECT-TYPE
	SYNTAX	INTEGER
	ACCESS	read-write
	STATUS	mandatory
	DESCRIPTION
		"CMOS data restore to which server blade"
	::={ s31SvrCmosEntry 5 }

s31SvrCmosCtrl OBJECT-TYPE
	SYNTAX	INTEGER{
		unknown(1),
		backup(2),
		smart-restore(3),
		force-restore(4)
	}
	ACCESS	read-write
	STATUS	mandatory
	DESCRIPTION
		"Backup/restore CMOS data.
			Control backup(2) for server blade backup CMOS data to management blade.
			Control smart-restore(3) when management and server blade have the same
			s31SvrCmosBiosVersion/s31SvrCmosMacAddr, CMOS data doesn't restore
			from management blade to server blade.
			Control force-restore(4) for management blade forced restore CMOS data
			to server blade."
	::={ s31SvrCmosEntry 6 }

s31SvrRaidConfigTable OBJECT-TYPE
	SYNTAX	SEQUENCE OF S31SvrRaidConfigEntry
	ACCESS	not-accessible
	STATUS	mandatory
	DESCRIPTION
		"Table with data of server blade Raid Controller type information"
	::={ s31SvrRaidConfig 1 }

s31SvrRaidConfigEntry OBJECT-TYPE
	SYNTAX	S31SvrRaidConfigEntry
	ACCESS	not-accessible
	STATUS	mandatory
	DESCRIPTION
		""
	INDEX	{ s31SvrRaidConfigBladeId, s31SvrRaidConfigId }
	::={ s31SvrRaidConfigTable 1 }

S31SvrRaidConfigEntry ::=
	SEQUENCE {
		s31SvrRaidConfigBladeId
			INTEGER,
		s31SvrRaidConfigId
			INTEGER,
		s31SvrRaidConfigType
			INTEGER
	}

s31SvrRaidConfigBladeId OBJECT-TYPE
	SYNTAX	INTEGER (1..20)
	ACCESS	read-only
	STATUS	mandatory
	DESCRIPTION
		"Server blade number, index into the Raid Controller table (1 based)"
	::={ s31SvrRaidConfigEntry 1 }

s31SvrRaidConfigId OBJECT-TYPE
	SYNTAX	INTEGER (1..12)
	ACCESS	read-only
	STATUS	mandatory
	DESCRIPTION
		"Raid Controller number, index into the Raid Controller table (1 based)"
	::={ s31SvrRaidConfigEntry 2 }


s31SvrRaidConfigType OBJECT-TYPE
	SYNTAX	INTEGER{
		unknown(1),
		sata(2),
		sas(3),
		sas-raid(4)
	}
	ACCESS	read-only
	STATUS	mandatory
	DESCRIPTION
		"Display Raid Controller Type"
	::={ s31SvrRaidConfigEntry 3 }

s31SvrInfoTable OBJECT-TYPE
	SYNTAX	SEQUENCE OF S31SvrInfoEntry
	ACCESS	not-accessible
	STATUS	mandatory
	DESCRIPTION
		"Table with data of server blade information"
	::={ s31SvrDeployment 1 }

s31SvrInfoEntry OBJECT-TYPE
	SYNTAX	S31SvrInfoEntry
	ACCESS	not-accessible
	STATUS	mandatory
	DESCRIPTION
		""
	INDEX	{ s31SvrInfoBladeId }
	::={ s31SvrInfoTable 1 }

S31SvrInfoEntry ::=
	SEQUENCE {
		s31SvrInfoBladeId
			INTEGER,
		s31SvrInfoChassisId
			DisplayString,
		s31SvrInfoMacAddr1
			PhysAddress,
		s31SvrInfoMacAddr2
			PhysAddress,
		s31SvrInfoIpAddr1
			IpAddress,
		s31SvrInfoIpAddr2
			IpAddress,
		s31SvrInfoNetMask1
			IpAddress,
		s31SvrInfoNetMask2
			IpAddress,
		s31SvrInfoGateway1
			IpAddress,
		s31SvrInfoGateway2
			IpAddress,
		s31SvrInfoHostname
			DisplayString,
		s31SvrInfoMasterImageReference
			DisplayString,
		s31SvrInfoStatusOfBlade
			INTEGER,
		s31SvrInfoLanStatusOfSlot
			INTEGER,
		s31SvrInfoAutomaticRecovery
			INTEGER,
		s31SvrInfoStatusOfCloning
			INTEGER,
		s31SvrInfoMacAddr3
			PhysAddress,
		s31SvrInfoMacAddr4
			PhysAddress,
		s31SvrInfoIpAddr3
			IpAddress,
		s31SvrInfoIpAddr4
			IpAddress,
		s31SvrInfoNetMask3
			IpAddress,
		s31SvrInfoNetMask4
			IpAddress,
		s31SvrInfoGateway3
			IpAddress,
		s31SvrInfoGateway4
			IpAddress,
		s31AgentVirtualIoLan
			INTEGER,
		s31AgentVirtualIoFiberchannel
			INTEGER

	}

s31SvrInfoBladeId OBJECT-TYPE
	SYNTAX	INTEGER (1..20)
	ACCESS	read-only
	STATUS	mandatory
	DESCRIPTION
		"Server blade number, index into the server info table (1 based)"
	::={ s31SvrInfoEntry 1 }

s31SvrInfoChassisId OBJECT-TYPE
	SYNTAX	DisplayString
	ACCESS	read-only
	STATUS	mandatory
	DESCRIPTION
		"Chassis serial number"
	::={ s31SvrInfoEntry 2 }

s31SvrInfoMacAddr1 OBJECT-TYPE
	SYNTAX	PhysAddress
	ACCESS	read-only
	STATUS	mandatory
	DESCRIPTION
		"MAC address1 of this server blade"
	::={ s31SvrInfoEntry 3 }

s31SvrInfoMacAddr2 OBJECT-TYPE
	SYNTAX	PhysAddress
	ACCESS	read-only
	STATUS	mandatory
	DESCRIPTION
		"MAC address2 of this server blade"
	::={ s31SvrInfoEntry 4 }

s31SvrInfoIpAddr1 OBJECT-TYPE
	SYNTAX	IpAddress
	ACCESS	read-write
	STATUS	mandatory
	DESCRIPTION
		"IP address1 of this server blade"
	::={ s31SvrInfoEntry 5 }

s31SvrInfoIpAddr2 OBJECT-TYPE
	SYNTAX	IpAddress
	ACCESS	read-write
	STATUS	mandatory
	DESCRIPTION
		"IP address2 of this server blade"
	::={ s31SvrInfoEntry 6 }

s31SvrInfoNetMask1 OBJECT-TYPE
	SYNTAX	IpAddress
	ACCESS	read-write
	STATUS	mandatory
	DESCRIPTION
		"Subnet mask1 of this server blade"
	::={ s31SvrInfoEntry 7 }

s31SvrInfoNetMask2 OBJECT-TYPE
	SYNTAX	IpAddress
	ACCESS	read-write
	STATUS	mandatory
	DESCRIPTION
		"Subnet mask2 of this server blade"
	::={ s31SvrInfoEntry 8 }

s31SvrInfoGateway1 OBJECT-TYPE
	SYNTAX	IpAddress
	ACCESS	read-write
	STATUS	mandatory
	DESCRIPTION
		"Gateway1 of this server blade"
	::={ s31SvrInfoEntry 9 }

s31SvrInfoGateway2 OBJECT-TYPE
	SYNTAX	IpAddress
	ACCESS	read-write
	STATUS	mandatory
	DESCRIPTION
		"Gateway2 of this server blade"
	::={ s31SvrInfoEntry 10 }


s31SvrInfoHostname OBJECT-TYPE
	SYNTAX	DisplayString
	ACCESS	read-write
	STATUS	mandatory
	DESCRIPTION
		"Hostname of this server blade"
	::={ s31SvrInfoEntry 11 }

s31SvrInfoMasterImageReference OBJECT-TYPE
	SYNTAX	DisplayString
	ACCESS	read-write
	STATUS	mandatory
	DESCRIPTION
		"URL in UNC notification (but in ASCII) to remote image file
			(with the extensions of *.img, *.cfg, *.txt)"
	::={ s31SvrInfoEntry 12 }

s31SvrInfoStatusOfBlade OBJECT-TYPE
	SYNTAX	INTEGER{
		unknown(1),
		power-down(2),
		standby(3),
		system-boot-failure(4),
		bios-setup(5),
		booting(6)
	}
	ACCESS	read-only
	STATUS	mandatory
	DESCRIPTION
		"Status of this blade.
			power-down(2):	waiting for boot
			standby(3):	PowerMgmt mode
			system-boot-failure(4):System boot failure
			bios-setup(5):	BIOS setup or boot phase
			booting(6):	ACPI OS booted"
	::={ s31SvrInfoEntry 13 }

s31SvrInfoLanStatusOfSlot OBJECT-TYPE
	SYNTAX	INTEGER{
		unknown(1),
		empty(2),
		preset(3)
	}
	ACCESS	read-write
	STATUS	mandatory
	DESCRIPTION
		"Defines the IP-LAN definations is valid or not.
			empty(2):	The IP-LAN definations in this info field are invalid.
					Once this is done the LAN status of this slot should be set to 1.
			preset(3):	The management blade LAN configuration for this slot is the reference.
					If a new or already installed blade is plugged in, the values from
					the management blade should be used for the installation/adaptation."
	::={ s31SvrInfoEntry 14 }

s31SvrInfoAutomaticRecovery OBJECT-TYPE
	SYNTAX	INTEGER{
		unknown(1),
		false(2),
		true(3)
	}
	ACCESS	read-write
	STATUS	mandatory
	DESCRIPTION
		"Defines if this server blade should be provided automatic recovery.
			false(2):	After Hot-Replacement of a defect CPU blade, no automatic deployment activities
					should be started.
			true(3):	After Hot-Replacement of a defect CPU blade, automatic deployment activities
					should be started."
	::={ s31SvrInfoEntry 15 }

s31SvrInfoStatusOfCloning OBJECT-TYPE
	SYNTAX	INTEGER{
		unknown(1),
		not-cloned(2),
		cloning(3),
		cloned(4)
	}
	ACCESS	read-write
	STATUS	mandatory
	DESCRIPTION
		"Status of cloning.
			not-cloned(2):	The client doesn't contain a valid configuration of an OS.
			cloning(3):	The cloning process is runnung and status will switch to cloned
					until the acknowledge from the cloning module was received by
					the central administration.
			cloned(4):	The assigned image was successfully cloned."
	::={ s31SvrInfoEntry 16 }

s31SvrInfoMacAddr3 OBJECT-TYPE
	SYNTAX	PhysAddress
	ACCESS	read-only
	STATUS	mandatory
	DESCRIPTION
		"MAC address3 of this server blade"
	::={ s31SvrInfoEntry 17 }

s31SvrInfoMacAddr4 OBJECT-TYPE
	SYNTAX	PhysAddress
	ACCESS	read-only
	STATUS	mandatory
	DESCRIPTION
		"MAC address4 of this server blade"
	::={ s31SvrInfoEntry 18 }

s31SvrInfoIpAddr3 OBJECT-TYPE
	SYNTAX	IpAddress
	ACCESS	read-write
	STATUS	mandatory
	DESCRIPTION
		"IP address3 of this server blade"
	::={ s31SvrInfoEntry 19 }

s31SvrInfoIpAddr4 OBJECT-TYPE
	SYNTAX	IpAddress
	ACCESS	read-write
	STATUS	mandatory
	DESCRIPTION
		"IP address4 of this server blade"
	::={ s31SvrInfoEntry 20 }

s31SvrInfoNetMask3 OBJECT-TYPE
	SYNTAX	IpAddress
	ACCESS	read-write
	STATUS	mandatory
	DESCRIPTION
		"Subnet mask3 of this server blade"
	::={ s31SvrInfoEntry 21 }

s31SvrInfoNetMask4 OBJECT-TYPE
	SYNTAX	IpAddress
	ACCESS	read-write
	STATUS	mandatory
	DESCRIPTION
		"Subnet mask4 of this server blade"
	::={ s31SvrInfoEntry 22 }

s31SvrInfoGateway3 OBJECT-TYPE
	SYNTAX	IpAddress
	ACCESS	read-write
	STATUS	mandatory
	DESCRIPTION
		"Gateway3 of this server blade"
	::={ s31SvrInfoEntry 23 }

s31SvrInfoGateway4 OBJECT-TYPE
	SYNTAX	IpAddress
	ACCESS	read-write
	STATUS	mandatory
	DESCRIPTION
		"Gateway4 of this server blade"
	::={ s31SvrInfoEntry 24 }

s31AgentVirtualIoLan OBJECT-TYPE
	SYNTAX	INTEGER
	ACCESS	read-write
	STATUS	mandatory
	DESCRIPTION
		"support virtual IO for Lan "
	::= { s31SvrInfoEntry 25 }

s31AgentVirtualIoFiberchannel OBJECT-TYPE
	SYNTAX	INTEGER
	ACCESS	read-write
	STATUS	mandatory
	DESCRIPTION
		"support virtual IO for Fiberchannel"
	::= { s31SvrInfoEntry 26 }



s31SvrInfoOemTable OBJECT-TYPE
	SYNTAX	SEQUENCE OF S31SvrInfoOemEntry
	ACCESS	not-accessible
	STATUS	mandatory
	DESCRIPTION
		"Table with data of server blade OEM information"
	::={ s31SvrDeployment 2 }

s31SvrInfoOemEntry OBJECT-TYPE
	SYNTAX	S31SvrInfoOemEntry
	ACCESS	not-accessible
	STATUS	mandatory
	DESCRIPTION
		""
	INDEX	{ s31SvrInfoOemBladeId, s31SvrInfoOemParamId}
	::={ s31SvrInfoOemTable 1 }

S31SvrInfoOemEntry ::=
	SEQUENCE {
		s31SvrInfoOemBladeId
			INTEGER,
		s31SvrInfoOemParamId
			INTEGER,
		s31SvrInfoOemParamData
			DisplayString
	}

s31SvrInfoOemBladeId OBJECT-TYPE
	SYNTAX	INTEGER (1..20)
	ACCESS	read-only
	STATUS	mandatory
	DESCRIPTION
		"Server blade number, index into the server info OEM table (1 based)"
	::={ s31SvrInfoOemEntry 1 }

s31SvrInfoOemParamId OBJECT-TYPE
	SYNTAX	INTEGER (1..10)
	ACCESS	read-only
	STATUS	mandatory
	DESCRIPTION
		"Oem Parameter number, index into the OEM table (1 based)"
	::={ s31SvrInfoOemEntry 2 }

s31SvrInfoOemParamData OBJECT-TYPE
	SYNTAX	DisplayString
	ACCESS	read-write
	STATUS	mandatory
	DESCRIPTION
		"OEM parameters"
	::={ s31SvrInfoOemEntry 3 }

s31SvrExtInfoTable OBJECT-TYPE
	SYNTAX	SEQUENCE OF S31SvrExtInfoEntry
	ACCESS	not-accessible
	STATUS	mandatory
	DESCRIPTION
		"Table with data of server blade extion information"
	::={ s31SvrDeployment 3 }

s31SvrExtInfoEntry OBJECT-TYPE
	SYNTAX	S31SvrExtInfoEntry
	ACCESS	not-accessible
	STATUS	mandatory
	DESCRIPTION
		""
	INDEX	{ s31SvrExtInfoMacAddr1 }
	::={ s31SvrExtInfoTable 1 }

S31SvrExtInfoEntry ::=
	SEQUENCE {
		s31SvrExtInfoBladeId
			INTEGER,
		s31SvrExtInfoChassisId
			DisplayString,
		s31SvrExtInfoMacAddr1
			PhysAddress,
		s31SvrExtInfoMacAddr2
			PhysAddress,
		s31SvrExtInfoIpAddr1
			IpAddress,
		s31SvrExtInfoIpAddr2
			IpAddress,
		s31SvrExtInfoNetMask1
			IpAddress,
		s31SvrExtInfoNetMask2
			IpAddress,
		s31SvrExtInfoGateway1
			IpAddress,
		s31SvrExtInfoGateway2
			IpAddress,
		s31SvrExtInfoHostname
			DisplayString,
		s31SvrExtInfoMasterImageReference
			DisplayString,
		s31SvrExtInfoStatusOfBlade
			INTEGER,
		s31SvrExtInfoLanStatusOfSlot
			INTEGER,
		s31SvrExtInfoAutomaticRecovery
			INTEGER,
		s31SvrExtInfoStatusOfCloning
			INTEGER,
		s31SvrExtInfoMacAddr3
			PhysAddress,
		s31SvrExtInfoMacAddr4
			PhysAddress,
		s31SvrExtInfoIpAddr3
			IpAddress,
		s31SvrExtInfoIpAddr4
			IpAddress,
		s31SvrExtInfoNetMask3
			IpAddress,
		s31SvrExtInfoNetMask4
			IpAddress,
		s31SvrExtInfoGateway3
			IpAddress,
		s31SvrExtInfoGateway4
			IpAddress,
		s31AgentExtVirtualIoLan
			INTEGER,
		s31AgentExtVirtualIoFiberchannel
			INTEGER

	}

s31SvrExtInfoBladeId OBJECT-TYPE
	SYNTAX	INTEGER (1..20)
	ACCESS	read-only
	STATUS	mandatory
	DESCRIPTION
		"Server blade number"
	::={ s31SvrExtInfoEntry 1 }

s31SvrExtInfoChassisId OBJECT-TYPE
	SYNTAX	DisplayString
	ACCESS	read-only
	STATUS	mandatory
	DESCRIPTION
		"Chassis serial number"
	::={ s31SvrExtInfoEntry 2 }

s31SvrExtInfoMacAddr1 OBJECT-TYPE
	SYNTAX	PhysAddress
	ACCESS	read-only
	STATUS	mandatory
	DESCRIPTION
		"MAC address1 of this server blade, index into the server extion info table (1 based)"
	::={ s31SvrExtInfoEntry 3 }

s31SvrExtInfoMacAddr2 OBJECT-TYPE
	SYNTAX	PhysAddress
	ACCESS	read-only
	STATUS	mandatory
	DESCRIPTION
		"MAC address2 of this server blade"
	::={ s31SvrExtInfoEntry 4 }

s31SvrExtInfoIpAddr1 OBJECT-TYPE
	SYNTAX	IpAddress
	ACCESS	read-write
	STATUS	mandatory
	DESCRIPTION
		"IP address1 of this server blade"
	::={ s31SvrExtInfoEntry 5 }

s31SvrExtInfoIpAddr2 OBJECT-TYPE
	SYNTAX	IpAddress
	ACCESS	read-write
	STATUS	mandatory
	DESCRIPTION
		"IP address2 of this server blade"
	::={ s31SvrExtInfoEntry 6 }

s31SvrExtInfoNetMask1 OBJECT-TYPE
	SYNTAX	IpAddress
	ACCESS	read-write
	STATUS	mandatory
	DESCRIPTION
		"Subnet mask1 of this server blade"
	::={ s31SvrExtInfoEntry 7 }

s31SvrExtInfoNetMask2 OBJECT-TYPE
	SYNTAX	IpAddress
	ACCESS	read-write
	STATUS	mandatory
	DESCRIPTION
		"Subnet mask2 of this server blade"
	::={ s31SvrExtInfoEntry 8 }

s31SvrExtInfoGateway1 OBJECT-TYPE
	SYNTAX	IpAddress
	ACCESS	read-write
	STATUS	mandatory
	DESCRIPTION
		"Gateway1 of this server blade"
	::={ s31SvrExtInfoEntry 9 }

s31SvrExtInfoGateway2 OBJECT-TYPE
	SYNTAX	IpAddress
	ACCESS	read-write
	STATUS	mandatory
	DESCRIPTION
		"Gateway2 of this server blade"
	::={ s31SvrExtInfoEntry 10 }

s31SvrExtInfoHostname OBJECT-TYPE
	SYNTAX	DisplayString
	ACCESS	read-write
	STATUS	mandatory
	DESCRIPTION
		"Hostname of this server blade"
	::={ s31SvrExtInfoEntry 11 }

s31SvrExtInfoMasterImageReference OBJECT-TYPE
	SYNTAX	DisplayString
	ACCESS	read-write
	STATUS	mandatory
	DESCRIPTION
		"URL in UNC notification (but in ASCII) to remote image file
			(with the extensions of *.img, *.cfg, *.txt)"
	::={ s31SvrExtInfoEntry 12 }

s31SvrExtInfoStatusOfBlade OBJECT-TYPE
	SYNTAX	INTEGER{
		unknown(1),
		power-down(2),
		standby(3),
		system-boot-failure(4),
		bios-setup(5),
		booting(6)
	}
	ACCESS	read-only
	STATUS	mandatory
	DESCRIPTION
		"Status of this blade.
			power-down(2):	waiting for boot.
			standby(3):	PowerMgmt mode.
			system-boot-failure(4):System boot failure.
			bios-setup(5):	BIOS setup or boot phase.
			booting(6):	ACPI OS booted"
	::={ s31SvrExtInfoEntry 13 }

s31SvrExtInfoLanStatusOfSlot OBJECT-TYPE
	SYNTAX	INTEGER{
		unknown(1),
		empty(2),
		preset(3)
	}
	ACCESS	read-write
	STATUS	mandatory
	DESCRIPTION
		"Defines the IP-LAN definations is valid or not.
			empty(2):	The IP-LAN definations in this info field are invalid.
					Once this is done the LAN status of this slot should be set to 1.
			preset(3):	The management blade LAN configuration for this slot is the reference.
					If a new or already installed blade is plugged in, the values from
					the management blade should be used for the installation/adaptation."
	::={ s31SvrExtInfoEntry 14 }

s31SvrExtInfoAutomaticRecovery OBJECT-TYPE
	SYNTAX	INTEGER{
		unknown(1),
		false(2),
		true(3)
	}
	ACCESS	read-write
	STATUS	mandatory
	DESCRIPTION
		"Defines if this server blade should be provided automatic recovery.
			false(2):	After Hot-Replacement of a defect CPU blade, no automatic deployment activities
					should be started.
			true(3):	After Hot-Replacement of a defect CPU blade, automatic deployment activities
					should be started."
	::={ s31SvrExtInfoEntry 15 }

s31SvrExtInfoStatusOfCloning OBJECT-TYPE
	SYNTAX	INTEGER{
		unknown(1),
		not-cloned(2),
		cloning(3),
		cloned(4)
	}
	ACCESS	read-write
	STATUS	mandatory
	DESCRIPTION
		"Status of cloning.
			not-cloned(2):	The client doesn't contain a valid configuration of an OS.
			cloning(3):	The cloning process is runnung and status will switch to cloned
					until the acknowledge from the cloning module was received by
					the central administration.
			cloned(4):	The assigned image was successfully cloned."
	::={ s31SvrExtInfoEntry 16 }

s31SvrExtInfoMacAddr3 OBJECT-TYPE
	SYNTAX	PhysAddress
	ACCESS	read-only
	STATUS	mandatory
	DESCRIPTION
		"MAC address3 of this server blade, index into the server extion info table (1 based)"
	::={ s31SvrExtInfoEntry 17 }

s31SvrExtInfoMacAddr4 OBJECT-TYPE
	SYNTAX	PhysAddress
	ACCESS	read-only
	STATUS	mandatory
	DESCRIPTION
		"MAC address4 of this server blade"
	::={ s31SvrExtInfoEntry 18 }

s31SvrExtInfoIpAddr3 OBJECT-TYPE
	SYNTAX	IpAddress
	ACCESS	read-write
	STATUS	mandatory
	DESCRIPTION
		"IP address3 of this server blade"
	::={ s31SvrExtInfoEntry 19 }

s31SvrExtInfoIpAddr4 OBJECT-TYPE
	SYNTAX	IpAddress
	ACCESS	read-write
	STATUS	mandatory
	DESCRIPTION
		"IP address4 of this server blade"
	::={ s31SvrExtInfoEntry 20 }

s31SvrExtInfoNetMask3 OBJECT-TYPE
	SYNTAX	IpAddress
	ACCESS	read-write
	STATUS	mandatory
	DESCRIPTION
		"Subnet mask3 of this server blade"
	::={ s31SvrExtInfoEntry 21 }

s31SvrExtInfoNetMask4 OBJECT-TYPE
	SYNTAX	IpAddress
	ACCESS	read-write
	STATUS	mandatory
	DESCRIPTION
		"Subnet mask4 of this server blade"
	::={ s31SvrExtInfoEntry 22 }

s31SvrExtInfoGateway3 OBJECT-TYPE
	SYNTAX	IpAddress
	ACCESS	read-write
	STATUS	mandatory
	DESCRIPTION
		"Gateway3 of this server blade"
	::={ s31SvrExtInfoEntry 23 }

s31SvrExtInfoGateway4 OBJECT-TYPE
	SYNTAX	IpAddress
	ACCESS	read-write
	STATUS	mandatory
	DESCRIPTION
		"Gateway4 of this server blade"
	::={ s31SvrExtInfoEntry 24 }

s31AgentExtVirtualIoLan OBJECT-TYPE
	SYNTAX	INTEGER
	ACCESS	read-write
	STATUS	mandatory
	DESCRIPTION
		"support virtual IO for Lan "
	::= { s31SvrExtInfoEntry 25 }

s31AgentExtVirtualIoFiberchannel OBJECT-TYPE
	SYNTAX	INTEGER
	ACCESS	read-write
	STATUS	mandatory
	DESCRIPTION
		"support virtual IO for Fiberchannel"
	::= { s31SvrExtInfoEntry 26 }

s31SvrExtInfoOemTable OBJECT-TYPE
	SYNTAX	SEQUENCE OF S31SvrExtInfoOemEntry
	ACCESS	not-accessible
	STATUS	mandatory
	DESCRIPTION
		"Table with data of server blade extion OEM information"
	::={ s31SvrDeployment 4 }

s31SvrExtInfoOemEntry OBJECT-TYPE
	SYNTAX	S31SvrExtInfoOemEntry
	ACCESS	not-accessible
	STATUS	mandatory
	DESCRIPTION
		""
	INDEX	{ s31SvrExtInfoOemMacAddr1, s31SvrExtInfoOemParamId}
	::={ s31SvrExtInfoOemTable 1 }

S31SvrExtInfoOemEntry ::=
	SEQUENCE {
		s31SvrExtInfoOemBladeId
			INTEGER,
		s31SvrExtInfoOemParamId
			INTEGER,
		s31SvrExtInfoOemMacAddr1
			PhysAddress,
		s31SvrExtInfoOemParamData
			DisplayString
	}

s31SvrExtInfoOemBladeId OBJECT-TYPE
	SYNTAX	INTEGER (1..20)
	ACCESS	read-only
	STATUS	mandatory
	DESCRIPTION
		"Server blade number"
	::={ s31SvrExtInfoOemEntry 1 }

s31SvrExtInfoOemParamId OBJECT-TYPE
	SYNTAX	INTEGER (1..10)
	ACCESS	read-only
	STATUS	mandatory
	DESCRIPTION
		"Oem Parameter number, index into the server extion info OEM table (1 based)"
	::={ s31SvrExtInfoOemEntry 2 }

s31SvrExtInfoOemMacAddr1 OBJECT-TYPE
	SYNTAX	PhysAddress
	ACCESS	read-only
	STATUS	mandatory
	DESCRIPTION
		"MAC address1 of this server blade"
	::={ s31SvrExtInfoOemEntry 3 }

s31SvrExtInfoOemParamData OBJECT-TYPE
	SYNTAX	DisplayString
	ACCESS	read-write
	STATUS	mandatory
	DESCRIPTION
		"OEM parameters"
	::={ s31SvrExtInfoOemEntry 4 }

s31SysDefaultDeployment	OBJECT-TYPE
	SYNTAX	INTEGER{
		unknown(1),
		disable(2),
		enable(3)
	}
	ACCESS	read-write
	STATUS	mandatory
	DESCRIPTION
		"support set system default"
	::= { s31SvrDeployment 5 }




s31SoftwareWatchdogTable OBJECT-TYPE
	SYNTAX	SEQUENCE OF S31SoftwareWatchdogEntry
	ACCESS	not-accessible
	STATUS	mandatory
	DESCRIPTION
		"Table with data of software watchdog"
	::={ s31SvrWatchDog 1 }

s31SoftwareWatchdogEntry OBJECT-TYPE
	SYNTAX	S31SoftwareWatchdogEntry
	ACCESS	not-accessible
	STATUS	mandatory
	DESCRIPTION
		""
	INDEX	{ s31SoftwareWatchdogBladeId }
	::={ s31SoftwareWatchdogTable 1 }

S31SoftwareWatchdogEntry ::=
	SEQUENCE {
		s31SoftwareWatchdogBladeId
			INTEGER,
		s31SoftwareWatchdogStatus
			INTEGER,
		s31SoftwareWatchdogTime
			INTEGER,
		s31SoftwareWatchdogAction
			INTEGER
	}

s31SoftwareWatchdogBladeId OBJECT-TYPE
	SYNTAX	INTEGER (1..20)
	ACCESS	read-only
	STATUS	mandatory
	DESCRIPTION
		"Server blade number, index into the watchdog table (1 based)"
	::={ s31SoftwareWatchdogEntry 1 }

s31SoftwareWatchdogStatus OBJECT-TYPE
	SYNTAX	INTEGER{
		unknown(1),
		control-by-os(2),
		enable(3),
		not-available(4)
	}
	ACCESS	read-only
	STATUS	mandatory
	DESCRIPTION
		"Status of software watchdog"
	::={ s31SoftwareWatchdogEntry 2 }

s31SoftwareWatchdogTime OBJECT-TYPE
	SYNTAX	INTEGER
	ACCESS	read-only
	STATUS	mandatory
	DESCRIPTION
		"Expired time of server blade watchdog"
	::={ s31SoftwareWatchdogEntry 3 }

s31SoftwareWatchdogAction OBJECT-TYPE
	SYNTAX	INTEGER{
		unknown(1),
		no-action(2),
		reset(3),
		power-off(4),
		power-cycle(5)
	}
	ACCESS	read-only
	STATUS	mandatory
	DESCRIPTION
		"Action should be done when watchdog timer expired"
	::={ s31SoftwareWatchdogEntry 4 }


s31BootWatchdogTable OBJECT-TYPE
	SYNTAX	SEQUENCE OF S31BootWatchdogEntry
	ACCESS	not-accessible
	STATUS	mandatory
	DESCRIPTION
		"Table with data of boot watchdog"
	::={ s31SvrWatchDog 2 }

s31BootWatchdogEntry OBJECT-TYPE
	SYNTAX	S31BootWatchdogEntry
	ACCESS	not-accessible
	STATUS	mandatory
	DESCRIPTION
		""
	INDEX	{ s31BootWatchdogBladeId }
	::={ s31BootWatchdogTable 1 }

S31BootWatchdogEntry ::=
	SEQUENCE {
		s31BootWatchdogBladeId
			INTEGER,
		s31BootWatchdogTime
			INTEGER,
		s31BootWatchdogEnable
			INTEGER,
		s31BootWatchdogAction
			INTEGER
	}

s31BootWatchdogBladeId OBJECT-TYPE
	SYNTAX	INTEGER (1..20)
	ACCESS	read-only
	STATUS	mandatory
	DESCRIPTION
		"Server blade number, index into the watchdog table (1 based)"
	::={ s31BootWatchdogEntry 1 }

s31BootWatchdogTime OBJECT-TYPE
	SYNTAX	INTEGER{
		unknown(1),
		minutes-2(2),
		minutes-5(3),
		minutes-10(4),
		minutes-15(5),
		minutes-20(6),
		minutes-30(7),
		minutes-60(8),
		minutes-100(9)
	}
	ACCESS	read-write
	STATUS	mandatory
	DESCRIPTION
		"Expiry time of server blade boot watchdog; since some systems 
		 may allow a more fine grained watchdog setting, the following 
		 mapping should be applied for reading:
		 minutes-2	 1 -  4 minutes
		 minutes-5	 5 -  9 minutes
		 minutes-10	10 - 14 minutes
		 minutes-15	15 - 19 minutes
		 minutes-20	20 - 29 minutes
		 minutes-30	30 - 59 minutes
		 minutes-60	60 - 99 minutes
		 minutes-100	100+    minutes "
	::={ s31BootWatchdogEntry 2 }

s31BootWatchdogEnable OBJECT-TYPE
	SYNTAX	INTEGER{
		unknown(1),
		disable(2),
		enable(3)
	}
	ACCESS	read-write
	STATUS	mandatory
	DESCRIPTION
		"Enable/Disable server blade watchdog"
	::={ s31BootWatchdogEntry 3 }

s31BootWatchdogAction OBJECT-TYPE
	SYNTAX	INTEGER{
		unknown(1),
		no-action(2),
		reboot(3),
		power-off(4),
		power-cycle(5)
	}
	ACCESS	read-write
	STATUS	mandatory
	DESCRIPTION
		"Action should be done when watchdog timer expired"
	::={ s31BootWatchdogEntry 4 }


s31SchedulePowerTable OBJECT-TYPE
	SYNTAX	SEQUENCE OF S31SchedulePowerEntry
	ACCESS	not-accessible
	STATUS	mandatory
	DESCRIPTION
		"Table with data of server blade schedule on/off time"
	::={ s31SvrScheduleOnOff 1 }

s31SchedulePowerEntry OBJECT-TYPE
	SYNTAX	S31SchedulePowerEntry
	ACCESS	not-accessible
	STATUS	mandatory
	DESCRIPTION
		""
	INDEX	{ s31SchedulePowerBladeId, s31SchedulePowerWeekDay }
	::={ s31SchedulePowerTable 1 }

S31SchedulePowerEntry ::=
	SEQUENCE {
		s31SchedulePowerBladeId
			INTEGER,
		s31SchedulePowerWeekDay
			INTEGER,
		s31SchedulePowerOnTime
			DisplayString,
		s31SchedulePowerOffTime
			DisplayString
	}

s31SchedulePowerBladeId OBJECT-TYPE
	SYNTAX	INTEGER (1..20)
	ACCESS	read-only
	STATUS	mandatory
	DESCRIPTION
		"Server blade number, index into the schedule on/off table (1 based)"
	::={ s31SchedulePowerEntry 1 }

s31SchedulePowerWeekDay OBJECT-TYPE
	SYNTAX	INTEGER{
		sunday(1),
		monday(2),
		tuesday(3),
		wednesday(4),
		thursday(5),
		friday(6),
		saturday(7)
	}
	ACCESS	read-only
	STATUS	mandatory
	DESCRIPTION
		"Weekday number, index into the schedule on/off table (1 based)"
	::={ s31SchedulePowerEntry 2 }



s31SchedulePowerOnTime OBJECT-TYPE
	SYNTAX	DisplayString
	ACCESS	read-write
	STATUS	mandatory
	DESCRIPTION
		"Server Blade schedule power on time"
	::={ s31SchedulePowerEntry 3 }



s31SchedulePowerOffTime OBJECT-TYPE
	SYNTAX	DisplayString
	ACCESS	read-write
	STATUS	mandatory
	DESCRIPTION
		"Server Blade schedule power off time"
	::={ s31SchedulePowerEntry 4 }





s31ScheduleForceOffTable OBJECT-TYPE
	SYNTAX	SEQUENCE OF S31ScheduleForceOffEntry
	ACCESS	not-accessible
	STATUS	mandatory
	DESCRIPTION
		"Table with setting of server blade force off when scheduale off fail"
	::={ s31SvrScheduleOnOff 2 }

s31ScheduleForceOffEntry OBJECT-TYPE
	SYNTAX	S31ScheduleForceOffEntry
	ACCESS	not-accessible
	STATUS	mandatory
	DESCRIPTION
		""
	INDEX	{ s31ScheduleForceOffBladeId }
	::={ s31ScheduleForceOffTable 1 }

S31ScheduleForceOffEntry ::=
	SEQUENCE {
		s31ScheduleForceOffBladeId
			INTEGER,
		s31ScheduleForceOffEnable
			INTEGER,
		s31ScheduleForceOffDelay
			INTEGER
	}

s31ScheduleForceOffBladeId OBJECT-TYPE
	SYNTAX	INTEGER (1..20)
	ACCESS	read-only
	STATUS	mandatory
	DESCRIPTION
		"Server blade number, index into the force off table (1 based)"
	::={ s31ScheduleForceOffEntry 1 }

s31ScheduleForceOffEnable OBJECT-TYPE
	SYNTAX	INTEGER{
		unknown(1),
		disable(2),
		enable(3)
	}
	ACCESS	read-write
	STATUS	mandatory
	DESCRIPTION
		"Enable/Disable server blade force off"
	::={ s31ScheduleForceOffEntry 2 }

s31ScheduleForceOffDelay OBJECT-TYPE
	SYNTAX	INTEGER{
		unknown(1),
		minutes-1(2),
		minutes-2(3),
		minutes-3(4),
		minutes-4(5),
		minutes-5(6),
		minutes-6(7),
		minutes-7(8)
	}
	ACCESS	read-write
	STATUS	mandatory
	DESCRIPTION
		"Expired time of server blade to force off"
	::={ s31ScheduleForceOffEntry 3 }


s31SvrIrmcTable OBJECT-TYPE
	SYNTAX	SEQUENCE OF S31SvrIrmcEntry
	ACCESS	not-accessible
	STATUS	mandatory
	DESCRIPTION
		"Table with data of server blade Irmc type information"
	::={ s31SvrIrmc 1 }

s31SvrIrmcEntry OBJECT-TYPE
	SYNTAX	S31SvrIrmcEntry
	ACCESS	not-accessible
	STATUS	mandatory
	DESCRIPTION
		""
	INDEX	{ s31SvrIrmcBladeId }
	::={ s31SvrIrmcTable 1 }

S31SvrIrmcEntry ::=
	SEQUENCE {
		s31SvrIrmcBladeId
			INTEGER,
		s31SvrIrmcMacAddress
			PhysAddress,
		s31SvrIrmcVirtualMacAddress
			PhysAddress,
		s31SvrIrmcIpMode
			INTEGER,
		s31SvrIrmcDhcpName
			DisplayString,
		s31SvrIrmcIpAddress
			IpAddress,
		s31SvrIrmcGatewayAddress
			IpAddress,
		s31SvrIrmcNetmask
			IpAddress,
		s31SvrIrmcAddressType
			INTEGER,
		s31SvrIrmcAddress
			OCTET STRING (SIZE (1..64)),
		s31SvrIrmcVlanId
			INTEGER,
		s31SvrIrmcSettingIpMode
			INTEGER,
		s31SvrIrmcSettingDhcpName
			DisplayString,
		s31SvrIrmcSettingIpAddress
			IpAddress,
		s31SvrIrmcSettingGatewayAddress
			IpAddress,
		s31SvrIrmcSettingNetmask
			IpAddress,
		s31SvrIrmcSettingAddressType
			INTEGER,
		s31SvrIrmcSettingAddress
			OCTET STRING (SIZE (1..64)),
		s31SvrIrmcSettingVlanId
			INTEGER,
		s31SvrIrmcNetSet
			INTEGER
	}

s31SvrIrmcBladeId OBJECT-TYPE
	SYNTAX	INTEGER (1..20)
	ACCESS	read-only
	STATUS	mandatory
	DESCRIPTION
		"Server blade IRMC number"
	::={ s31SvrIrmcEntry 1 }

s31SvrIrmcMacAddress OBJECT-TYPE
	SYNTAX	PhysAddress
	ACCESS	read-only
	STATUS	mandatory
	DESCRIPTION
		"Server blade Irmc Mac Address"
	::={ s31SvrIrmcEntry 2 }

s31SvrIrmcVirtualMacAddress OBJECT-TYPE
	SYNTAX	PhysAddress
	ACCESS	read-only
	STATUS	mandatory
	DESCRIPTION
		"Server blade Irmc Virtual Mac Address"
	::={ s31SvrIrmcEntry 3 }

s31SvrIrmcIpMode OBJECT-TYPE
	SYNTAX	INTEGER{
		unknown(1),
		no-dhcp(2),
		dhcp(3)
		}
	ACCESS	read-only
	STATUS	mandatory
	DESCRIPTION
		"Server blade Irmc Virtual Ip Mode"
	::={ s31SvrIrmcEntry 4 }

s31SvrIrmcDhcpName OBJECT-TYPE
	SYNTAX	DisplayString
	ACCESS	read-only
	STATUS	mandatory
	DESCRIPTION
		"Server blade Irmc Dhcp Name"
	::={ s31SvrIrmcEntry 5 }

s31SvrIrmcIpAddress OBJECT-TYPE
	SYNTAX	IpAddress
	ACCESS	read-only
	STATUS	mandatory
	DESCRIPTION
		"Server blade Irmc Ip Address"
	::={ s31SvrIrmcEntry 6 }

s31SvrIrmcGatewayAddress OBJECT-TYPE
	SYNTAX	IpAddress
	ACCESS	read-only
	STATUS	mandatory
	DESCRIPTION
		"Server blade Irmc Gateway Address"
	::={ s31SvrIrmcEntry 7 }

s31SvrIrmcNetmask OBJECT-TYPE
	SYNTAX	IpAddress
	ACCESS	read-only
	STATUS	mandatory
	DESCRIPTION
		"Server blade Irmc Net mask"
	::={ s31SvrIrmcEntry 8 }

s31SvrIrmcVlanId OBJECT-TYPE
	SYNTAX	INTEGER
	ACCESS	read-only
	STATUS	mandatory
	DESCRIPTION
		"Server blade Irmc Vlan Id"
	::={ s31SvrIrmcEntry 9 }

s31SvrIrmcSettingIpMode OBJECT-TYPE
	SYNTAX	INTEGER{
		unknown(1),
		dhcp(2),
		no-dhcp(3)
		}
	ACCESS	read-write
	STATUS	mandatory
	DESCRIPTION
		"Server blade Irmc Setting Ip Mode"
	::={ s31SvrIrmcEntry 10 }

s31SvrIrmcSettingDhcpName OBJECT-TYPE
	SYNTAX	DisplayString
	ACCESS	read-write
	STATUS	mandatory
	DESCRIPTION
		"Server blade Irmc Setting  Dhcp Name"
	::={ s31SvrIrmcEntry 11 }

s31SvrIrmcSettingIpAddress OBJECT-TYPE
	SYNTAX	IpAddress
	ACCESS	read-write
	STATUS	mandatory
	DESCRIPTION
		"Server blade Irmc Setting  Ip Address"
	::={ s31SvrIrmcEntry 12 }

s31SvrIrmcSettingGatewayAddress OBJECT-TYPE
	SYNTAX	IpAddress
	ACCESS	read-write
	STATUS	mandatory
	DESCRIPTION
		"Server blade Irmc Setting  Gateway Address"
	::={ s31SvrIrmcEntry 13 }

s31SvrIrmcSettingNetmask OBJECT-TYPE
	SYNTAX	IpAddress
	ACCESS	read-write
	STATUS	mandatory
	DESCRIPTION
		"Server blade Irmc Setting  Net mask"
	::={ s31SvrIrmcEntry 14 }

s31SvrIrmcSettingVlanId OBJECT-TYPE
	SYNTAX	INTEGER
	ACCESS	read-write
	STATUS	mandatory
	DESCRIPTION
		"Server blade Irmc Setting  Vlan Id "
	::={ s31SvrIrmcEntry 15 }

s31SvrIrmcNetSet OBJECT-TYPE
	SYNTAX	INTEGER{
		unknown(1),
		apply(2)
		}
	ACCESS	read-write
	STATUS	mandatory
	DESCRIPTION
		"Server blade Irmc Net Set"
	::={ s31SvrIrmcEntry 16 }

s31SvrIrmcAddressType OBJECT-TYPE
	SYNTAX	INTEGER{
        unknown(0),
        ipv4(1),
        ipv6(2),
        ipv4z(3),
        ipv6z(4),
        dns(16)
	}
	ACCESS	read-only
	STATUS	mandatory
	DESCRIPTION
		"Server blade Irmc address type"
	::={ s31SvrIrmcEntry 17 }

s31SvrIrmcAddress OBJECT-TYPE
    SYNTAX  OCTET STRING (SIZE (1..64))
	ACCESS	read-only
	STATUS	mandatory
	DESCRIPTION
		"Server blade Irmc IPv6 address"
	::={ s31SvrIrmcEntry 18 }

s31SvrIrmcSettingAddressType OBJECT-TYPE
	SYNTAX	INTEGER{
        unknown(0),
        ipv4(1),
        ipv6(2),
        ipv4z(3),
        ipv6z(4),
        dns(16)
	}
	ACCESS	read-write
	STATUS	mandatory
	DESCRIPTION
		"Server blade Irmc Setting address type"
	::={ s31SvrIrmcEntry 19 }

s31SvrIrmcSettingAddress OBJECT-TYPE
    SYNTAX  OCTET STRING (SIZE (1..64))
	ACCESS	read-write
	STATUS	mandatory
	DESCRIPTION
		"Server blade Irmc IPv6 Setting address"
	::={ s31SvrIrmcEntry 20 }

s31SvrViomTable OBJECT-TYPE
	SYNTAX	SEQUENCE OF S31SvrViomEntry
	ACCESS	not-accessible
	STATUS	obsolete
	DESCRIPTION
		"Table with data of server blade Viom type information"
	::={ s31SvrViom 1 }

s31SvrViomEntry OBJECT-TYPE
	SYNTAX	S31SvrViomEntry
	ACCESS	not-accessible
	STATUS	obsolete
	DESCRIPTION
		""
	INDEX	{ s31SvrViomBladeId }
	::={ s31SvrViomTable 1 }

S31SvrViomEntry ::=
	SEQUENCE {
		s31SvrViomBladeId
			INTEGER,
		s31SvrViomDataLength
			INTEGER,
		s31SvrViomDataTableLock
			INTEGER,
		s31SvrViomDataTableLockTimeout
			INTEGER,
		s31SvrViomDataTableClear
			INTEGER,
		s31SvrInventoryTable
			DisplayString,
		s31SvrInventoryTableLock
			INTEGER,
		s31SvrInventoryTableLockTimeout
			INTEGER

	}

s31SvrViomBladeId OBJECT-TYPE
	SYNTAX	INTEGER (1..20)
	ACCESS	read-only
	STATUS	obsolete
	DESCRIPTION
		"Server blade Viom number"
	::={ s31SvrViomEntry 1 }

s31SvrViomDataLength OBJECT-TYPE
	SYNTAX	INTEGER
	ACCESS	read-only
	STATUS	obsolete
	DESCRIPTION
		"Server blade Viom Data Length"
	::={ s31SvrViomEntry 2 }

s31SvrViomDataTableLock OBJECT-TYPE
	SYNTAX	INTEGER
	ACCESS	read-write
	STATUS	obsolete
	DESCRIPTION
		"Server blade Viom Data Length Lock"
	::={ s31SvrViomEntry 3 }

s31SvrViomDataTableLockTimeout OBJECT-TYPE
	SYNTAX	INTEGER
	ACCESS	read-write
	STATUS	obsolete
	DESCRIPTION
		"Server blade Viom Data Table Lock Timeout"
	::={ s31SvrViomEntry 4 }

s31SvrViomDataTableClear OBJECT-TYPE
	SYNTAX	INTEGER
	ACCESS	read-write
	STATUS	obsolete
	DESCRIPTION
		"Server blade Viom Data Table Clear"
	::={ s31SvrViomEntry 5 }

s31SvrInventoryTable OBJECT-TYPE
	SYNTAX	DisplayString
	ACCESS	read-only
	STATUS	obsolete
	DESCRIPTION
		"Server blade Inventory Table"
	::={ s31SvrViomEntry 6 }

s31SvrInventoryTableLock OBJECT-TYPE
	SYNTAX	INTEGER
	ACCESS	read-write
	STATUS	obsolete
	DESCRIPTION
		"Server blade Inventory Table Lock"
	::={ s31SvrViomEntry 7 }

s31SvrInventoryTableLockTimeout OBJECT-TYPE
	SYNTAX	INTEGER
	ACCESS	read-write
	STATUS	obsolete
	DESCRIPTION
		"Server blade Inventory Table Lock Timeout"
	::={ s31SvrViomEntry 8 }

s31SvrMezzanineInfoTable OBJECT-TYPE
	SYNTAX	SEQUENCE OF S31SvrMezzanineInfoEntry
	ACCESS	not-accessible
	STATUS	mandatory
	DESCRIPTION
		"Table with data of server blade mezzanine card information"
	::={ s31SvrMezzanineInfo 1 }

s31SvrMezzanineInfoEntry OBJECT-TYPE
	SYNTAX	S31SvrMezzanineInfoEntry
	ACCESS	not-accessible
	STATUS	mandatory
	DESCRIPTION
		""
	INDEX	{ s31SvrMezzanineBladeId, s31SvrMezzanineId }
	::={ s31SvrMezzanineInfoTable 1 }

S31SvrMezzanineInfoEntry ::=
	SEQUENCE {
		s31SvrMezzanineBladeId
			INTEGER,
		s31SvrMezzanineId
			INTEGER,
		s31SvrMezzanineType
			INTEGER,
		s31SvrMezzanineManufacture
			DisplayString,
		s31SvrMezzanineManufactureDate
			DisplayString,
		s31SvrMezzanineSerialNumber
			DisplayString,
		s31SvrMezzanineProductName
			DisplayString,
		s31SvrMezzanineModelName
			DisplayString,
		s31SvrMezzanineHardwareVersion
			DisplayString,
		s31SvrMezzanineFirmwareVersion
			DisplayString,
		s31SvrMezzanineStatus
			INTEGER,
		s31SvrMezzanineNumPorts
			INTEGER
	}

s31SvrMezzanineBladeId OBJECT-TYPE
	SYNTAX	INTEGER (1..20)
	ACCESS	read-only
	STATUS	mandatory
	DESCRIPTION
		"Server blade number, index into the Mezzanine table (1 based)"
	::={ s31SvrMezzanineInfoEntry 1 }

s31SvrMezzanineId OBJECT-TYPE
	SYNTAX	INTEGER (1..4)
	ACCESS	read-only
	STATUS	mandatory
	DESCRIPTION
		"Mezzanine number, index into the Mezzanine table (1 based)"
	::={ s31SvrMezzanineInfoEntry 2 }

s31SvrMezzanineType OBJECT-TYPE
	SYNTAX	INTEGER{
		unknown(1),
		lan-mezzanine-card(2),
		fc-mezzanine-card(3),
		infiniband-mezzanine-card(4),
		cna-mezzanine-card(5),
		fcoe-mezzanine-card(6),
		sas-raid-mezzanine-card(7),
		sas-hba(8)
	}
	ACCESS	read-only
	STATUS	mandatory
	DESCRIPTION
		"Type of the attached mezzanine card (LAN, FC, ...)"
	::={ s31SvrMezzanineInfoEntry 3 }

s31SvrMezzanineManufacture OBJECT-TYPE
	SYNTAX	DisplayString
	ACCESS	read-only
	STATUS	mandatory
	DESCRIPTION
		"String containing the mezzanine card manufacturer"
	::={ s31SvrMezzanineInfoEntry 4 }

s31SvrMezzanineManufactureDate OBJECT-TYPE
	SYNTAX	DisplayString
	ACCESS	read-only
	STATUS	mandatory
	DESCRIPTION
		"String containing the mezzanine card manufacture date"
	::={ s31SvrMezzanineInfoEntry 5 }

s31SvrMezzanineSerialNumber OBJECT-TYPE
	SYNTAX	DisplayString
	ACCESS	read-only
	STATUS	mandatory
	DESCRIPTION
		"String containing the mezzanine card serial number"
	::={ s31SvrMezzanineInfoEntry 6 }

s31SvrMezzanineProductName OBJECT-TYPE
	SYNTAX	DisplayString
	ACCESS	read-only
	STATUS	mandatory
	DESCRIPTION
		"String containing the mezzanine card product name as known to the end customer"
	::={ s31SvrMezzanineInfoEntry 7 }

s31SvrMezzanineModelName OBJECT-TYPE
	SYNTAX	DisplayString
	ACCESS	read-only
	STATUS	mandatory
	DESCRIPTION
		"String containing the mezzanine card model name"
	::={ s31SvrMezzanineInfoEntry 8 }

s31SvrMezzanineHardwareVersion OBJECT-TYPE
	SYNTAX	DisplayString
	ACCESS	read-only
	STATUS	mandatory
	DESCRIPTION
		"String containing the mezzanine card hardware revision"
	::={ s31SvrMezzanineInfoEntry 9 }

s31SvrMezzanineFirmwareVersion OBJECT-TYPE
	SYNTAX	DisplayString
	ACCESS	read-only
	STATUS	mandatory
	DESCRIPTION
		"String containing the mezzanine card firmware revision"
	::={ s31SvrMezzanineInfoEntry 10 }

s31SvrMezzanineStatus OBJECT-TYPE
	SYNTAX	INTEGER{
		unknown(1),
		ok(2),
		not-present(3),
		error(4),
		critical(5)
	}
	ACCESS	read-only
	STATUS	mandatory
	DESCRIPTION
		"Current status of this mezzanine card"
	::={ s31SvrMezzanineInfoEntry 11 }

s31SvrMezzanineNumPorts OBJECT-TYPE
	SYNTAX	INTEGER
	ACCESS	read-only
	STATUS	mandatory
	DESCRIPTION
		"Number of ports available for the mezzanine card"
	::={ s31SvrMezzanineInfoEntry 12 }

-- **********************************************************************************************
--
-- GROUP: s31SwitchBlade
--
--      s31MgmtAgent MIB:        1.3.6.1.4.1.7244.1.1.1
--      s31SwitchBlade group:              1.3.6.1.4.1.7244.1.1.1.5
--
-- **********************************************************************************************

s31SwitchBladeTable OBJECT-TYPE
	SYNTAX	SEQUENCE OF S31SwitchBladeEntry
	ACCESS	not-accessible
	STATUS	mandatory
	DESCRIPTION
		"Table with data of switch blade"
	::={ s31SwitchBlade 1 }

s31SwitchBladeEntry OBJECT-TYPE
	SYNTAX	S31SwitchBladeEntry
	ACCESS	not-accessible
	STATUS	mandatory
	DESCRIPTION
		""
	INDEX	{ s31SwitchBladeId }
	::={ s31SwitchBladeTable 1 }

S31SwitchBladeEntry ::=
	SEQUENCE {
		s31SwitchBladeId
			INTEGER,
		s31SwitchBladeStatus
			INTEGER,
		s31SwitchBladeManufacture
			DisplayString,
		s31SwitchBladeManufactureDate
			DisplayString,
		s31SwitchBladeSerialNumber
			DisplayString,
		s31SwitchBladeProductName
			DisplayString,
		s31SwitchBladeModelName
			DisplayString,
		s31SwitchBladeVersion
			DisplayString,
		s31SwitchBladePhysicalAddress
			PhysAddress,
		s31SwitchBladeIpAddress
			IpAddress,
		s31SwitchBladeAdministrativeUrl
			DisplayString,
		s31SwitchBladeCtrlStatLed
			INTEGER,
		s31SwitchBladeCtrlReboot
			INTEGER,
		s31SwitchBladeGatewayAddress
			IpAddress,
		s31SwitchBladeNetMask
			IpAddress,
		s31SwitchBladeSettingIpAddress
			IpAddress,
		s31SwitchBladeSettingGatewayAddress
			IpAddress,
		s31SwitchBladeSettingNetMask
			IpAddress,
		s31SwitchBladeNetSet
			INTEGER,
		s31SwitchBladeIpMode
			INTEGER,
		s31SwitchBladeDhcpClientName
			DisplayString,
		s31SwitchBladeVlanId
			INTEGER,
		s31SwitchBladeFirmwareVersion
			DisplayString,
		s31SwitchBladeAddressType
			INTEGER,
		s31SwitchBladeAddress
			OCTET STRING (SIZE (1..64)),
		s31SwitchBladeStackingMode
			INTEGER,
		s31SwitchBladeAssetTag
			OCTET STRING (SIZE (1..40)),
		s31SwitchBladeUserAssignedName
			DisplayString
	}

s31SwitchBladeId OBJECT-TYPE
	SYNTAX	INTEGER (1..8)
	ACCESS	read-only
	STATUS	mandatory
	DESCRIPTION
		"Switch blade number, index into the switch blade table (1 based)"
	::={ s31SwitchBladeEntry 1 }

s31SwitchBladeStatus OBJECT-TYPE
	SYNTAX	INTEGER{
		unknown(1),
		ok(2),
		not-present(3),
		error(4),
		critical(5),
		standby(6),
		present(7)
	}
	ACCESS	read-only
	STATUS	mandatory
	DESCRIPTION
		"Current status of this switch blade"
	::={ s31SwitchBladeEntry 2 }

s31SwitchBladeManufacture OBJECT-TYPE
	SYNTAX	DisplayString
	ACCESS	read-only
	STATUS	mandatory
	DESCRIPTION
		"String containing the switch blade manufacturer"
	::={ s31SwitchBladeEntry 3 }

s31SwitchBladeManufactureDate OBJECT-TYPE
	SYNTAX	DisplayString
	ACCESS	read-only
	STATUS	mandatory
	DESCRIPTION
		"Manufacture date of the switch blade"
	::={ s31SwitchBladeEntry 4 }

s31SwitchBladeSerialNumber OBJECT-TYPE
	SYNTAX	DisplayString
	ACCESS	read-only
	STATUS	mandatory
	DESCRIPTION
		"Serial number of the switch blade"
	::={ s31SwitchBladeEntry 5 }

s31SwitchBladeProductName OBJECT-TYPE
	SYNTAX	DisplayString
	ACCESS	read-only
	STATUS	mandatory
	DESCRIPTION
		"Product name of the switch blade"
	::={ s31SwitchBladeEntry 6 }

s31SwitchBladeModelName OBJECT-TYPE
	SYNTAX	DisplayString
	ACCESS	read-only
	STATUS	mandatory
	DESCRIPTION
		"Model name of the switch blade"
	::={ s31SwitchBladeEntry 7 }

s31SwitchBladeVersion OBJECT-TYPE
	SYNTAX	DisplayString
	ACCESS	read-only
	STATUS	mandatory
	DESCRIPTION
		"Switch blade hardware version"
	::={ s31SwitchBladeEntry 8 }

s31SwitchBladePhysicalAddress OBJECT-TYPE
	SYNTAX	PhysAddress
	ACCESS	read-only
	STATUS	mandatory
	DESCRIPTION
		"Switch blade MAC address"
	::={ s31SwitchBladeEntry 9 }

s31SwitchBladeIpAddress OBJECT-TYPE
	SYNTAX	IpAddress
	ACCESS	read-only
	STATUS	mandatory
	DESCRIPTION
		"Switch blade IP address"
	::={ s31SwitchBladeEntry 10 }

s31SwitchBladeAdministrativeUrl OBJECT-TYPE
	SYNTAX	DisplayString
	ACCESS	read-only
	STATUS	mandatory
	DESCRIPTION
		"Administrative URL of the switch blade"
	::={ s31SwitchBladeEntry 11 }

s31SwitchBladeCtrlStatLed OBJECT-TYPE
	SYNTAX	INTEGER{
		unknown(1),
		off(2),
		blinking(3),
		on(4)
	}
	ACCESS	read-write
	STATUS	mandatory
	DESCRIPTION
		"Configure switch blade IDENTIFY (formerly STAT) LED status (off/blinking)"
	::={ s31SwitchBladeEntry 12 }

s31SwitchBladeCtrlReboot OBJECT-TYPE
	SYNTAX	INTEGER{
		unknown(1),
		false(2),
		true(3)
	}
	ACCESS	read-write
	STATUS	mandatory
	DESCRIPTION
		"Reboot switch blade"
	::={ s31SwitchBladeEntry 13 }

s31SwitchBladeGatewayAddress OBJECT-TYPE
	SYNTAX	IpAddress
	ACCESS	read-only
	STATUS	mandatory
	DESCRIPTION
		"Switch blade Gateway IP address"
	::={ s31SwitchBladeEntry 14 }

s31SwitchBladeNetMask OBJECT-TYPE
	SYNTAX	IpAddress
	ACCESS	read-only
	STATUS	mandatory
	DESCRIPTION
		"Switch blade Net Mask"
	::={ s31SwitchBladeEntry 15 }

s31SwitchBladeSettingIpAddress OBJECT-TYPE
	SYNTAX	IpAddress
	ACCESS	read-write
	STATUS	mandatory
	DESCRIPTION
		"Switch blade Setting IP address"
	::={ s31SwitchBladeEntry 16 }

s31SwitchBladeSettingGatewayAddress OBJECT-TYPE
	SYNTAX	IpAddress
	ACCESS	read-write
	STATUS	mandatory
	DESCRIPTION
		"Switch blade Gateway Setting IP address"
	::={ s31SwitchBladeEntry 17 }

s31SwitchBladeSettingNetMask OBJECT-TYPE
	SYNTAX	IpAddress
	ACCESS	read-write
	STATUS	mandatory
	DESCRIPTION
		"Switch blade Setting Net Mask"
	::={ s31SwitchBladeEntry 18 }

s31SwitchBladeNetSet OBJECT-TYPE
	SYNTAX	INTEGER{
		unknown(1),
		false(2),
		true(3)
	}
	ACCESS	read-write
	STATUS	mandatory
	DESCRIPTION
		"Submit switch blade IP address, Gateway and Net Mask"
	::={ s31SwitchBladeEntry 19 }

s31SwitchBladeIpMode OBJECT-TYPE
	SYNTAX	INTEGER{
		unknown(1),
		dhcp(2),
		no-dhcp(3)
	}
	ACCESS	read-only
	STATUS	mandatory
	DESCRIPTION
		"Switch blade read IP mode"
	::={ s31SwitchBladeEntry 20 }

s31SwitchBladeDhcpClientName OBJECT-TYPE
	SYNTAX	DisplayString
	ACCESS	read-only
	STATUS	mandatory
	DESCRIPTION
		"Switch blade read DHCP client name"
	::={ s31SwitchBladeEntry 21 }

s31SwitchBladeVlanId OBJECT-TYPE
	SYNTAX	INTEGER
	ACCESS	read-only
	STATUS	mandatory
	DESCRIPTION
		"Switch blade read Vlan ID"
	::={ s31SwitchBladeEntry 22 }

s31SwitchBladeFirmwareVersion OBJECT-TYPE
	SYNTAX	DisplayString
	ACCESS	read-only
	STATUS	mandatory
	DESCRIPTION
		"Switch blade Firmware version"
	::={ s31SwitchBladeEntry 23 }

s31SwitchBladeAddressType OBJECT-TYPE
	SYNTAX	INTEGER{
        unknown(0),
        ipv4(1),
        ipv6(2),
        ipv4z(3),
        ipv6z(4),
        dns(16)
	}
	ACCESS	read-only
	STATUS	mandatory
	DESCRIPTION
		"Identify IP address type of this switch blade"
	::={ s31SwitchBladeEntry 24 }

s31SwitchBladeAddress OBJECT-TYPE
    SYNTAX  OCTET STRING (SIZE (1..64))
	ACCESS	read-only
	STATUS	mandatory
	DESCRIPTION
		"IP address for IPv6 of this switch blade"
	::={ s31SwitchBladeEntry 25 }

s31SwitchBladeStackingMode OBJECT-TYPE
	SYNTAX	INTEGER{
		unknown(1),
		master(2),
		slave(3)
	}
	ACCESS	read-only
	STATUS	mandatory
	DESCRIPTION
		"Specifies whether the switch is configured as master
		 or slave in switch stacking mode"
	::={ s31SwitchBladeEntry 26 }

s31SwitchBladeAssetTag OBJECT-TYPE
    SYNTAX  OCTET STRING (SIZE (1..40))
	ACCESS	read-write
	STATUS	mandatory
	DESCRIPTION
		"Asset tag for this switch blade"
	::={ s31SwitchBladeEntry 27 }

s31SwitchBladeUserAssignedName OBJECT-TYPE
	SYNTAX	DisplayString
	ACCESS	read-only
	STATUS	mandatory
	DESCRIPTION
		"Name assigned to this switch blade by the user"
	::={ s31SwitchBladeEntry 28 }

-- **********************************************************************************************
--
-- GROUP: s31TrapInfo
--
--      s31MgmtAgent MIB:        1.3.6.1.4.1.7244.1.1.1
--      s31TrapInfo group:              1.3.6.1.4.1.7244.1.1.1.7
--
-- **********************************************************************************************

s31TrapServerName OBJECT-TYPE
	SYNTAX	DisplayString
	ACCESS	read-only
	STATUS	mandatory
	DESCRIPTION
		"Name of the server the trap occured"
	::={ s31TrapInfo 1 }

s31TrapTime OBJECT-TYPE
	SYNTAX	DisplayString
	ACCESS	read-only
	STATUS	mandatory
	DESCRIPTION
		"Time the trap occured"
	::={ s31TrapInfo 2 }

s31TrapObjectNumber OBJECT-TYPE
	SYNTAX	OBJECT IDENTIFIER
	ACCESS	read-write
	STATUS	mandatory
	DESCRIPTION
		"Identifier of the object that trigger this trap"
	::={ s31TrapInfo 3 }

s31TrapString OBJECT-TYPE
	SYNTAX	DisplayString
	ACCESS	read-write
	STATUS	mandatory
	DESCRIPTION
		"Additional string to be displayed in the trap text"
	::={ s31TrapInfo 4 }

s31TrapTestOid OBJECT-TYPE
	SYNTAX	INTEGER
	ACCESS	read-only
	STATUS	mandatory
	DESCRIPTION
		"Object identifier of this test trap"
	::={ s31TrapInfo 5 }

s31TrapSendTest OBJECT-TYPE
	SYNTAX	INTEGER{
		send-trap(1)
	}
	ACCESS	read-write
	STATUS	mandatory
	DESCRIPTION
		"Send a trap to the manager application(s) to test connection
			and trap configuration"
	::={ s31TrapInfo 6 }

s31TrapInteger OBJECT-TYPE
	SYNTAX	INTEGER
	ACCESS	read-write
	STATUS	mandatory
	DESCRIPTION
		"Additional integer value to be displayed in the trap text"
	::={ s31TrapInfo 7 }

-- **********************************************************************************************
--
-- GROUP: s31FiberChannel
--
--      s31MgmtAgent MIB:        1.3.6.1.4.1.7244.1.1.1
--      s31FiberChannel group:              1.3.6.1.4.1.7244.1.1.1.8
--
-- **********************************************************************************************
s31FcPassThroughBladeVoltageTable OBJECT-TYPE
	SYNTAX	SEQUENCE OF S31FcPassThroughBladeVoltageEntry
	ACCESS	not-accessible
	STATUS	obsolete
	DESCRIPTION
		"Table with data of all pass through blade voltages"
	::={ s31FcPassThroughBlade 1 }

s31FcPassThroughBladeVoltageEntry OBJECT-TYPE
	SYNTAX	S31FcPassThroughBladeVoltageEntry
	ACCESS	not-accessible
	STATUS	obsolete
	DESCRIPTION
		""
	INDEX	{ s31FcPassThroughBladeVoltageBladeId, s31FcPassThroughBladeVoltageId }
	::={ s31FcPassThroughBladeVoltageTable 1 }

S31FcPassThroughBladeVoltageEntry ::=
	SEQUENCE {
		s31FcPassThroughBladeVoltageBladeId
			INTEGER,
		s31FcPassThroughBladeVoltageId
			INTEGER,
		s31FcPassThroughBladeVoltageStatus
			INTEGER,
		s31FcPassThroughBladeVoltageMinimumValue
			INTEGER,
		s31FcPassThroughBladeVoltageMaximumValue
			INTEGER,
		s31FcPassThroughBladeVoltageCurrentValue
			INTEGER,
		s31FcPassThroughBladeVoltageNominalValue
			INTEGER
	}

s31FcPassThroughBladeVoltageBladeId OBJECT-TYPE
	SYNTAX	INTEGER (1..2)
	ACCESS	read-only
	STATUS	obsolete
	DESCRIPTION
		"Pass through blade number, index into the voltage table (1 based)"
	::={ s31FcPassThroughBladeVoltageEntry 1 }

s31FcPassThroughBladeVoltageId OBJECT-TYPE
	SYNTAX	INTEGER (1..1)
	ACCESS	read-only
	STATUS	obsolete
	DESCRIPTION
		"Voltage number, index into the voltage table (1 based)"
	::={ s31FcPassThroughBladeVoltageEntry 2 }

s31FcPassThroughBladeVoltageStatus OBJECT-TYPE
	SYNTAX	INTEGER{
		unknown(1),
		not-available(2),
		ok(3),
		too-low(4),
		too-high(5)
	}
	ACCESS	read-only
	STATUS	obsolete
	DESCRIPTION
		"Current status of this voltage"
	::={ s31FcPassThroughBladeVoltageEntry 3 }

s31FcPassThroughBladeVoltageMinimumValue OBJECT-TYPE
	SYNTAX	INTEGER
	ACCESS	read-only
	STATUS	obsolete
	DESCRIPTION
		"Voltage minimum level (1/100th Volts)"
	::={ s31FcPassThroughBladeVoltageEntry 4 }

s31FcPassThroughBladeVoltageMaximumValue OBJECT-TYPE
	SYNTAX	INTEGER
	ACCESS	read-only
	STATUS	obsolete
	DESCRIPTION
		"Voltage maximum level (1/100th Volts)"
	::={ s31FcPassThroughBladeVoltageEntry 5 }

s31FcPassThroughBladeVoltageCurrentValue OBJECT-TYPE
	SYNTAX	INTEGER
	ACCESS	read-only
	STATUS	obsolete
	DESCRIPTION
		"Voltage current level (1/100th Volts)"
	::={ s31FcPassThroughBladeVoltageEntry 6 }

s31FcPassThroughBladeVoltageNominalValue OBJECT-TYPE
	SYNTAX	INTEGER
	ACCESS	read-only
	STATUS	obsolete
	DESCRIPTION
		"Voltage nominal level (1/100th Volts)"
	::={ s31FcPassThroughBladeVoltageEntry 7 }

s31FcPassThroughBladeInfoTable OBJECT-TYPE
	SYNTAX	SEQUENCE OF S31FcPassThroughBladeInfoEntry
	ACCESS	not-accessible
	STATUS	mandatory
	DESCRIPTION
		"Table with info data of pass through blade"
	::={ s31FcPassThroughBlade 2 }

s31FcPassThroughBladeInfoEntry OBJECT-TYPE
	SYNTAX	S31FcPassThroughBladeInfoEntry
	ACCESS	not-accessible
	STATUS	mandatory
	DESCRIPTION
		""
	INDEX	{ s31FcPassThroughBladeInfoBladeId }
	::={ s31FcPassThroughBladeInfoTable 1 }

S31FcPassThroughBladeInfoEntry ::=
	SEQUENCE {
		s31FcPassThroughBladeInfoBladeId
			INTEGER,
		s31FcPassThroughBladeInfoStatus
			INTEGER,
		s31FcPassThroughBladeInfoManufacture
			DisplayString,
		s31FcPassThroughBladeInfoManufactureDate
			DisplayString,
		s31FcPassThroughBladeInfoSerialNumber
			DisplayString,
		s31FcPassThroughBladeInfoProductName
			DisplayString,
		s31FcPassThroughBladeInfoModelName
			DisplayString,
		s31FcPassThroughBladeInfoVersion
			DisplayString,
		s31FcPassThroughBladeActiveWwnn
			DisplayString,
		s31FcPassThroughBladeActiveWwpn
			DisplayString,
		s31FcPassThroughBladeManufactureWwnn
			DisplayString,
		s31FcPassThroughBladeManufactureWwpn
			DisplayString,
		s31FcPassThroughBladeFirmwareVersion 
			DisplayString,
		s31FcPassThroughBladeSlotId
			INTEGER,
		s31FcPassThroughAssetTag
			OCTET STRING (SIZE (1..40))
	}

s31FcPassThroughBladeInfoBladeId OBJECT-TYPE
	SYNTAX	INTEGER (1..8)
	ACCESS	read-only
	STATUS	mandatory
	DESCRIPTION
		"pass through blade number, index into the pass through blade info table (1 based)"
	::={ s31FcPassThroughBladeInfoEntry 1 }

s31FcPassThroughBladeInfoStatus OBJECT-TYPE
	SYNTAX	INTEGER{
		unknown(1),
		ok(2),
		not-present(3),
		error(4),
		critical(5),
		standby(6)
	}
	ACCESS	read-only
	STATUS	mandatory
	DESCRIPTION
		"Current status of this pass through blade"
	::={ s31FcPassThroughBladeInfoEntry 2 }

s31FcPassThroughBladeInfoManufacture OBJECT-TYPE
	SYNTAX	DisplayString
	ACCESS	read-only
	STATUS	mandatory
	DESCRIPTION
		"String containing the pass through blade manufacturer"
	::={ s31FcPassThroughBladeInfoEntry 3 }

s31FcPassThroughBladeInfoManufactureDate OBJECT-TYPE
	SYNTAX	DisplayString
	ACCESS	read-only
	STATUS	mandatory
	DESCRIPTION
		"Manufacture date of the pass through blade"
	::={ s31FcPassThroughBladeInfoEntry 4 }

s31FcPassThroughBladeInfoSerialNumber OBJECT-TYPE
	SYNTAX	DisplayString
	ACCESS	read-only
	STATUS	mandatory
	DESCRIPTION
		"Serial number of the pass through blade"
	::={ s31FcPassThroughBladeInfoEntry 5 }

s31FcPassThroughBladeInfoProductName OBJECT-TYPE
	SYNTAX	DisplayString
	ACCESS	read-only
	STATUS	mandatory
	DESCRIPTION
		"Product name of the pass through blade"
	::={ s31FcPassThroughBladeInfoEntry 6 }

s31FcPassThroughBladeInfoModelName OBJECT-TYPE
	SYNTAX	DisplayString
	ACCESS	read-only
	STATUS	mandatory
	DESCRIPTION
		"Model name of the pass through blade"
	::={ s31FcPassThroughBladeInfoEntry 7 }

s31FcPassThroughBladeInfoVersion OBJECT-TYPE
	SYNTAX	DisplayString
	ACCESS	read-only
	STATUS	mandatory
	DESCRIPTION
		"Pass through blade hardware version"
	::={ s31FcPassThroughBladeInfoEntry 8 }

s31FcPassThroughBladeActiveWwnn OBJECT-TYPE
	SYNTAX	DisplayString
	ACCESS	read-only
	STATUS	obsolete
	DESCRIPTION
		"Pass through blade Active WWNN"
	::={ s31FcPassThroughBladeInfoEntry 9 }

s31FcPassThroughBladeActiveWwpn OBJECT-TYPE
	SYNTAX	DisplayString
	ACCESS	read-only
	STATUS	obsolete
	DESCRIPTION
		"Pass through blade Active WWPN"
	::={ s31FcPassThroughBladeInfoEntry 10 }

s31FcPassThroughBladeManufactureWwnn OBJECT-TYPE
	SYNTAX	DisplayString
	ACCESS	read-only
	STATUS	obsolete
	DESCRIPTION
		"Pass through blade Manufacture WWNN"
	::={ s31FcPassThroughBladeInfoEntry 11 }

s31FcPassThroughBladeManufactureWwpn OBJECT-TYPE
	SYNTAX	DisplayString
	ACCESS	read-only
	STATUS	obsolete
	DESCRIPTION
		"Pass through blade Manufacture WWPN"
	::={ s31FcPassThroughBladeInfoEntry 12 }

s31FcPassThroughBladeFirmwareVersion OBJECT-TYPE
	SYNTAX	DisplayString
	ACCESS	read-only
	STATUS	mandatory
	DESCRIPTION
		"Pass through blade Firmware version"
	::={ s31FcPassThroughBladeInfoEntry 13 }

s31FcPassThroughBladeSlotId OBJECT-TYPE
	SYNTAX	INTEGER
	ACCESS	read-only
	STATUS	mandatory
	DESCRIPTION
		"Pass through blade slot ID"
	::={ s31FcPassThroughBladeInfoEntry 14 }

s31FcPassThroughAssetTag OBJECT-TYPE
    SYNTAX  OCTET STRING (SIZE (1..40))
	ACCESS	read-write
	STATUS	mandatory
	DESCRIPTION
		"Asset tag for this pass through blade"
	::={ s31FcPassThroughBladeInfoEntry 15 }

s31FcPassThroughBladePortsTable OBJECT-TYPE
	SYNTAX	SEQUENCE OF S31FcPassThroughBladePortsEntry
	ACCESS	not-accessible
	STATUS	obsolete
	DESCRIPTION
		"Table with data of all pass through blade Ports Present Status"
	::={ s31FcPassThroughBlade 3 }

s31FcPassThroughBladePortsEntry OBJECT-TYPE
	SYNTAX	S31FcPassThroughBladePortsEntry
	ACCESS	not-accessible
	STATUS	obsolete
	DESCRIPTION
		""
	INDEX	{ s31FcPassThroughBladePortsBladeId, s31FcPassThroughBladePortsId }
	::={ s31FcPassThroughBladePortsTable 1 }

S31FcPassThroughBladePortsEntry ::=
	SEQUENCE {
		s31FcPassThroughBladePortsBladeId
			INTEGER,
		s31FcPassThroughBladePortsId
			INTEGER,
		s31FcPassThroughBladePortsStatus
			INTEGER
	}

s31FcPassThroughBladePortsBladeId OBJECT-TYPE
	SYNTAX	INTEGER (1..2)
	ACCESS	read-only
	STATUS	obsolete
	DESCRIPTION
		"Pass through blade number, index into the ports present table (1 based)"
	::={ s31FcPassThroughBladePortsEntry 1 }

s31FcPassThroughBladePortsId OBJECT-TYPE
	SYNTAX	INTEGER (1..10)
	ACCESS	read-only
	STATUS	obsolete
	DESCRIPTION
		"ports number, index into the ports present table (1 based)"
	::={ s31FcPassThroughBladePortsEntry 2 }

s31FcPassThroughBladePortsStatus OBJECT-TYPE
	SYNTAX	INTEGER{
		unknown(1),
		on(2),
		off(3)
	}
	ACCESS	read-only
	STATUS	obsolete
	DESCRIPTION
		"Current status of ports"
	::={ s31FcPassThroughBladePortsEntry 3 }

-- **********************************************************************************************
--
-- GROUP: s31TftpUpdate
--
--      s31MgmtAgent MIB:        1.3.6.1.4.1.7244.1.1.1
--      s31TftpUpdate group:              1.3.6.1.4.1.7244.1.1.1.9
--
-- **********************************************************************************************

s31TftpUpdateAgentIp OBJECT-TYPE
	SYNTAX	IpAddress
	ACCESS	read-write
	STATUS	mandatory
	DESCRIPTION
		"Tftp agent IP address"
	::={ s31TftpUpdate 1 }

s31TftpUpdateServerIp OBJECT-TYPE
	SYNTAX	IpAddress
	ACCESS	read-write
	STATUS	mandatory
	DESCRIPTION
		"Tftp server IP address"
	::={ s31TftpUpdate 2 }

s31TftpUpdateImage OBJECT-TYPE
	SYNTAX	DisplayString
	ACCESS	read-write
	STATUS	mandatory
	DESCRIPTION
		"Updated image file name"
	::={ s31TftpUpdate 3 }

s31TftpUpdateEnable OBJECT-TYPE
	SYNTAX	INTEGER{
		unknown(1),
		disable(2),
		single-mode(3),
		dual-mode(4)
	}
	ACCESS	read-write
	STATUS	mandatory
	DESCRIPTION
		"Enable to update image file from TFTP"
	::={ s31TftpUpdate 4 }

s31TftpUpdateAction OBJECT-TYPE
	SYNTAX	INTEGER{
		start-tftp(1)
	}
	ACCESS	read-write
	STATUS	mandatory
	DESCRIPTION
		"Start TFTP to update image file"
	::={ s31TftpUpdate 5 }

s31TftpUpdateAgentAddressType OBJECT-TYPE
	SYNTAX	INTEGER{
        unknown(0),
        ipv4(1),
        ipv6(2),
        ipv4z(3),
        ipv6z(4),
        dns(16)
	}
	ACCESS	read-write
	STATUS	mandatory
	DESCRIPTION
		"Identify IP address type of the Tftp agent"
	::={ s31TftpUpdate 6 }

s31TftpUpdateAgentAddress OBJECT-TYPE
    SYNTAX  OCTET STRING (SIZE (1..64))
	ACCESS	read-write
	STATUS	mandatory
	DESCRIPTION
		"IPv6 address for Tftp agent"
	::={ s31TftpUpdate 7 }

s31TftpUpdateServerAddressType OBJECT-TYPE
	SYNTAX	INTEGER{
        unknown(0),
        ipv4(1),
        ipv6(2),
        ipv4z(3),
        ipv6z(4),
        dns(16)
	}
	ACCESS	read-write
	STATUS	mandatory
	DESCRIPTION
		"Identify IP address type of the Tftp server"
	::={ s31TftpUpdate 8 }

s31TftpUpdateServerAddress OBJECT-TYPE
    SYNTAX  OCTET STRING (SIZE (1..64))
	ACCESS	read-write
	STATUS	mandatory
	DESCRIPTION
		"IPv6 address for Tftp server"
	::={ s31TftpUpdate 9 }

-- **********************************************************************************************
--
-- GROUP: s31PhyBlade
--
--      s31MgmtAgent MIB:        1.3.6.1.4.1.7244.1.1.1
--      s31PhyBlade group:              1.3.6.1.4.1.7244.1.1.1.10
--
-- **********************************************************************************************

s31PhyBladeTable OBJECT-TYPE
	SYNTAX	SEQUENCE OF S31PhyBladeEntry
	ACCESS	not-accessible
	STATUS	mandatory
	DESCRIPTION
		"Table with data of phy blade"
	::={ s31PhyBlade 1 }

s31PhyBladeEntry OBJECT-TYPE
	SYNTAX	S31PhyBladeEntry
	ACCESS	not-accessible
	STATUS	mandatory
	DESCRIPTION
		""
	INDEX	{ s31PhyBladeId }
	::={ s31PhyBladeTable 1 }

S31PhyBladeEntry ::=
	SEQUENCE {
		s31PhyBladeId
			INTEGER,
		s31PhyBladeManufacture
			DisplayString,
		s31PhyBladeManufactureDate
			DisplayString,
		s31PhyBladeSerialNumber
			DisplayString,
		s31PhyBladeProductName
			DisplayString,
		s31PhyBladeModelName
			DisplayString,
		s31PhyBladeHardwareVersion
			DisplayString,
		s31PhyBladeFirmwareVersion
			DisplayString,
		s31PhyBladeStatus
			INTEGER,
		s31PhyBladeAssetTag
			OCTET STRING (SIZE (1..40))
	}

s31PhyBladeId OBJECT-TYPE
	SYNTAX	INTEGER (1..8)
	ACCESS	read-only
	STATUS	mandatory
	DESCRIPTION
		"Phy blade number, index into the phy blade table (1 based)"
	::={ s31PhyBladeEntry 1 }

s31PhyBladeManufacture OBJECT-TYPE
	SYNTAX	DisplayString
	ACCESS	read-only
	STATUS	mandatory
	DESCRIPTION
		"String containing the phy blade manufacturer"
	::={ s31PhyBladeEntry 2 }

s31PhyBladeManufactureDate OBJECT-TYPE
	SYNTAX	DisplayString
	ACCESS	read-only
	STATUS	mandatory
	DESCRIPTION
		"Manufacture date of the phy blade"
	::={ s31PhyBladeEntry 3 }

s31PhyBladeSerialNumber OBJECT-TYPE
	SYNTAX	DisplayString
	ACCESS	read-only
	STATUS	mandatory
	DESCRIPTION
		"Serial number of the phy blade"
	::={ s31PhyBladeEntry 4 }

s31PhyBladeProductName OBJECT-TYPE
	SYNTAX	DisplayString
	ACCESS	read-only
	STATUS	mandatory
	DESCRIPTION
		"Product name of the phy blade"
	::={ s31PhyBladeEntry 5 }

s31PhyBladeModelName OBJECT-TYPE
	SYNTAX	DisplayString
	ACCESS	read-only
	STATUS	mandatory
	DESCRIPTION
		"Model name of the phy blade"
	::={ s31PhyBladeEntry 6 }

s31PhyBladeHardwareVersion OBJECT-TYPE
	SYNTAX	DisplayString
	ACCESS	read-only
	STATUS	mandatory
	DESCRIPTION
		"Phy blade hardware version"
	::={ s31PhyBladeEntry 7 }

s31PhyBladeFirmwareVersion OBJECT-TYPE
	SYNTAX	DisplayString
	ACCESS	read-only
	STATUS	mandatory
	DESCRIPTION
		"Phy blade firmware version"
	::={ s31PhyBladeEntry 8 }

s31PhyBladeStatus OBJECT-TYPE
	SYNTAX	INTEGER{
		unknown(1),
		ok(2),
		not-present(3),
		error(4),
		critical(5),
		standby(6)
	}
	ACCESS	read-only
	STATUS	mandatory
	DESCRIPTION
		"Current status of this phy blade"
	::={ s31PhyBladeEntry 9 }

s31PhyBladeAssetTag OBJECT-TYPE
    SYNTAX  OCTET STRING (SIZE (1..40))
	ACCESS	read-write
	STATUS	mandatory
	DESCRIPTION
		"Asset tag for this phy blade"
	::={ s31PhyBladeEntry 10 }

-- **********************************************************************************************
--
-- GROUP: s31KvmBlade
--
--      s31MgmtAgent MIB:        1.3.6.1.4.1.7244.1.1.1
--      s31KvmBlade group:              1.3.6.1.4.1.7244.1.1.1.11
--
-- **********************************************************************************************

s31KvmBladeTable OBJECT-TYPE
	SYNTAX	SEQUENCE OF S31KvmBladeEntry
	ACCESS	not-accessible
	STATUS	mandatory
	DESCRIPTION
		"Table with data of kvm blade"
	::={ s31KvmBlade 1 }

s31KvmBladeEntry OBJECT-TYPE
	SYNTAX	S31KvmBladeEntry
	ACCESS	not-accessible
	STATUS	mandatory
	DESCRIPTION
		""
	INDEX	{ s31KvmBladeId }
	::={ s31KvmBladeTable 1 }


S31KvmBladeEntry ::=
	SEQUENCE {
		s31KvmBladeId
			INTEGER,
		s31KvmBladeManufacture
			DisplayString,
		s31KvmBladeManufactureDate
			DisplayString,
		s31KvmBladeSerialNumber
			DisplayString,
		s31KvmBladeProductName
			DisplayString,
		s31KvmBladeModelName
			DisplayString,
		s31KvmBladeVersion
			DisplayString,
		s31KvmBladeDhcpConfigured
			INTEGER,
		s31KvmBladeIpAddress
			IpAddress,
		s31KvmBladeGatewayAddress
			IpAddress,
		s31KvmBladeNetMask
			IpAddress,
		s31KvmBladeHttpPort
			INTEGER,
		s31KvmBladeFWVersion
			DisplayString,
		s31KvmBladeTFTPServerIpAddress
			IpAddress,
		s31KvmBladeImageName
			DisplayString,
		s31KvmBladeUpdatestatus
			INTEGER,
		s31KvmBladeUpdateStart
			INTEGER,
		s31KvmBladeStatus
			INTEGER,
		s31KvmBladeAdministrativeURL
			DisplayString,
		s31KvmBladeAssetTag
			OCTET STRING (SIZE (1..40)),
		s31KvmBladeAddressType
			INTEGER,
		s31KvmBladeAddress
			OCTET STRING (SIZE (1..64))
	}

s31KvmBladeId OBJECT-TYPE
	SYNTAX	INTEGER (1..4)
	ACCESS	read-only
	STATUS	mandatory
	DESCRIPTION
		"Kvm blade number, index into the kvm blade table (1 based)"
	::={ s31KvmBladeEntry 1 }

s31KvmBladeManufacture OBJECT-TYPE
	SYNTAX	DisplayString
	ACCESS	read-only
	STATUS	mandatory
	DESCRIPTION
		"String containing the kvm blade manufacturer"
	::={ s31KvmBladeEntry 2 }

s31KvmBladeManufactureDate OBJECT-TYPE
	SYNTAX	DisplayString
	ACCESS	read-only
	STATUS	mandatory
	DESCRIPTION
		"Manufacture date of the kvm blade"
	::={ s31KvmBladeEntry 3 }

s31KvmBladeSerialNumber OBJECT-TYPE
	SYNTAX	DisplayString
	ACCESS	read-only
	STATUS	mandatory
	DESCRIPTION
		"Serial number of the kvm blade"
	::={ s31KvmBladeEntry 4 }

s31KvmBladeProductName OBJECT-TYPE
	SYNTAX	DisplayString
	ACCESS	read-only
	STATUS	mandatory
	DESCRIPTION
		"Product name of the kvm blade"
	::={ s31KvmBladeEntry 5 }

s31KvmBladeModelName OBJECT-TYPE
	SYNTAX	DisplayString
	ACCESS	read-only
	STATUS	mandatory
	DESCRIPTION
		"Model name of the kvm blade"
	::={ s31KvmBladeEntry 6 }

s31KvmBladeVersion OBJECT-TYPE
	SYNTAX	DisplayString
	ACCESS	read-only
	STATUS	mandatory
	DESCRIPTION
		"Kvm blade hardware version"
	::={ s31KvmBladeEntry 7 }

s31KvmBladeDhcpConfigured OBJECT-TYPE
	SYNTAX	INTEGER{
		unknown(1),
		disable(2),
		enable(3)
	}
	ACCESS	read-write
	STATUS	mandatory
	DESCRIPTION
		"Defines if the IP address should be requested by a DHCP service"
	::={ s31KvmBladeEntry 8 }

s31KvmBladeIpAddress OBJECT-TYPE
	SYNTAX	IpAddress
	ACCESS	read-only
	STATUS	mandatory
	DESCRIPTION
		"Kvm blade IP address"
	::={ s31KvmBladeEntry 9 }

s31KvmBladeGatewayAddress OBJECT-TYPE
	SYNTAX	IpAddress
	ACCESS	read-only
	STATUS	mandatory
	DESCRIPTION
		"Kvm blade Gateway IP address"
	::={ s31KvmBladeEntry 10 }

s31KvmBladeNetMask OBJECT-TYPE
	SYNTAX	IpAddress
	ACCESS	read-only
	STATUS	mandatory
	DESCRIPTION
		"Kvm blade Net Mask"
	::={ s31KvmBladeEntry 11 }

s31KvmBladeHttpPort OBJECT-TYPE
	SYNTAX	INTEGER
	ACCESS	read-write
	STATUS	mandatory
	DESCRIPTION
		"The TCP port for kvm blade HTTP service"
	::={ s31KvmBladeEntry 12 }

s31KvmBladeFWVersion OBJECT-TYPE
	SYNTAX	DisplayString
	ACCESS	read-only
	STATUS	mandatory
	DESCRIPTION
		"Kvm blade firmware version"
	::={ s31KvmBladeEntry 13 }

s31KvmBladeTFTPServerIpAddress OBJECT-TYPE
	SYNTAX	IpAddress
	ACCESS	read-write
	STATUS	mandatory
	DESCRIPTION
		"The IP address of tftp server for kvm FW update"
	::= { s31KvmBladeEntry 14 }

s31KvmBladeImageName OBJECT-TYPE
	SYNTAX	DisplayString
	ACCESS	read-write
	STATUS	mandatory
	DESCRIPTION
		"Image path under KVM upadte tftp sever"
	::= { s31KvmBladeEntry 15 }


s31KvmBladeUpdatestatus OBJECT-TYPE
	SYNTAX	INTEGER{
		disable(1),
		tftp-start(2),
		tftp-complete(3),
		tftp-fail(4)
	}
	ACCESS	read-only
	STATUS	mandatory
	DESCRIPTION
		"status for the FW upadte of KVM"
	::= { s31KvmBladeEntry 16 }


s31KvmBladeUpdateStart OBJECT-TYPE
	SYNTAX	INTEGER{
		unknown(1),
		disable(2),
		enable(3)
	}
	ACCESS	read-write
	STATUS	mandatory
	DESCRIPTION
		"Start to update KVM FW"
	::={ s31KvmBladeEntry 17 }

s31KvmBladeStatus OBJECT-TYPE
	SYNTAX	INTEGER{
		unknown(1),
		ok(2),
		not-present(3),
		error(4),
		critical(5),
		standby(6)
	}
	ACCESS	read-only
	STATUS	mandatory
	DESCRIPTION
		"Current status of this KVM blade"
	::={ s31KvmBladeEntry 18 }

s31KvmBladeAdministrativeURL OBJECT-TYPE
	SYNTAX	DisplayString
	ACCESS	read-only
	STATUS	mandatory
	DESCRIPTION
		"Administrative URL of the KVM blade"
	::={ s31KvmBladeEntry 19 }

s31KvmBladeAssetTag OBJECT-TYPE
    SYNTAX  OCTET STRING (SIZE (1..40))
	ACCESS	read-write
	STATUS	mandatory
	DESCRIPTION
		"Asset tag for this KVM blade"
	::={ s31KvmBladeEntry 20 }


s31KvmBladeAddressType OBJECT-TYPE
	SYNTAX	INTEGER{
        unknown(0),
        ipv4(1),
        ipv6(2),
        ipv4z(3),
        ipv6z(4),
        dns(16)
	}
	ACCESS	read-write
	STATUS	mandatory
	DESCRIPTION
		"Identify IP address type of the KVM blade"
	::={ s31KvmBladeEntry 21 }

s31KvmBladeAddress OBJECT-TYPE
    SYNTAX  OCTET STRING (SIZE (1..64))
	ACCESS	read-write
	STATUS	mandatory
	DESCRIPTION
		"IPv6 address for KVM blade"
	::={ s31KvmBladeEntry 22 }

-- **********************************************************************************************
--
-- GROUP: s31FCSwitchBlade
--
--      s31MgmtAgent MIB:        1.3.6.1.4.1.7244.1.1.1
--      s31FCSwitchBlade group:              1.3.6.1.4.1.7244.1.1.1.12
--
-- **********************************************************************************************

s31FCSwitchBladeTable OBJECT-TYPE
	SYNTAX	SEQUENCE OF S31FCSwitchBladeEntry
	ACCESS	not-accessible
	STATUS	mandatory
	DESCRIPTION
		"Table with data of FC Switch blade"
	::={ s31FCSwitchBlade 1 }

s31FCSwitchBladeEntry OBJECT-TYPE
	SYNTAX	S31FCSwitchBladeEntry
	ACCESS	not-accessible
	STATUS	mandatory
	DESCRIPTION
		""
	INDEX	{ s31FCSwitchBladeId }
	::={ s31FCSwitchBladeTable 1 }

S31FCSwitchBladeEntry ::=
	SEQUENCE {
		s31FCSwitchBladeId
			INTEGER,
		s31FCSwitchBladeManufacture
			DisplayString,
		s31FCSwitchBladeManufactureDate
			DisplayString,
		s31FCSwitchBladeSerialNumber
			DisplayString,
		s31FCSwitchBladeProductName
			DisplayString,
		s31FCSwitchBladeModelName
			DisplayString,
		s31FCSwitchBladeHardwareVersion
			DisplayString,
		s31FCSwitchBladeIpAddress
			IpAddress,
		s31FCSwitchBladeSubnetMask
			IpAddress,
		s31FCSwitchBladeGatewayAddress
			IpAddress,
		s31FCSwitchBladeFcIpAddress
			IpAddress,
		s31FCSwitchBladeFcSubnetMask
			IpAddress,
		s31FCSwitchBladeFcSwitchName
			DisplayString,
		s31FCSwitchBladeFcDomainId
			DisplayString,
		s31FCSwitchBladeSlotId
			INTEGER,
		s31FCSwitchBladeFirmwareVersion
			DisplayString,
		s31FCSwitchBladeStatus
			INTEGER,
		s31FCSwitchBladeAdministrativeURL
			DisplayString,
		s31FCSwitchBladeAddressType
			INTEGER,
		s31FCSwitchBladeAddress
			OCTET STRING (SIZE (1..64)),
		s31FCSwitchBladePhysicalAddress
			PhysAddress,
		s31FCSwitchBladeAssetTag
			OCTET STRING (SIZE (1..40))
	}

s31FCSwitchBladeId OBJECT-TYPE
	SYNTAX	INTEGER (1..2)
	ACCESS	read-only
	STATUS	mandatory
	DESCRIPTION
		"FC Switch blade number, index into the FC Switch blade table (1 based)"
	::={ s31FCSwitchBladeEntry 1 }

s31FCSwitchBladeManufacture OBJECT-TYPE
	SYNTAX	DisplayString
	ACCESS	read-only
	STATUS	mandatory
	DESCRIPTION
		"String containing the FC Switch blade manufacturer"
	::={ s31FCSwitchBladeEntry 2 }

s31FCSwitchBladeManufactureDate OBJECT-TYPE
	SYNTAX	DisplayString
	ACCESS	read-only
	STATUS	mandatory
	DESCRIPTION
		"Manufacture date of the FC Switch blade"
	::={ s31FCSwitchBladeEntry 3 }

s31FCSwitchBladeSerialNumber OBJECT-TYPE
	SYNTAX	DisplayString
	ACCESS	read-only
	STATUS	mandatory
	DESCRIPTION
		"Serial number of the FC Switch blade"
	::={ s31FCSwitchBladeEntry 4 }

s31FCSwitchBladeProductName OBJECT-TYPE
	SYNTAX	DisplayString
	ACCESS	read-only
	STATUS	mandatory
	DESCRIPTION
		"Product name of the FC Switch blade"
	::={ s31FCSwitchBladeEntry 5 }

s31FCSwitchBladeModelName OBJECT-TYPE
	SYNTAX	DisplayString
	ACCESS	read-only
	STATUS	mandatory
	DESCRIPTION
		"Model name of the FC Switch blade"
	::={ s31FCSwitchBladeEntry 6 }

s31FCSwitchBladeHardwareVersion OBJECT-TYPE
	SYNTAX	DisplayString
	ACCESS	read-only
	STATUS	mandatory
	DESCRIPTION
		"FC Switch blade hardware version"
	::={ s31FCSwitchBladeEntry 7 }



s31FCSwitchBladeIpAddress OBJECT-TYPE
	SYNTAX	IpAddress
	ACCESS	read-only
	STATUS	mandatory
	DESCRIPTION
		"FC Switch blade IP address"
	::={ s31FCSwitchBladeEntry 8 }

s31FCSwitchBladeSubnetMask OBJECT-TYPE
	SYNTAX	IpAddress
	ACCESS	read-only
	STATUS	mandatory
	DESCRIPTION
		"FC Switch blade Subnet Mask "
	::={ s31FCSwitchBladeEntry 9 }

s31FCSwitchBladeGatewayAddress OBJECT-TYPE
	SYNTAX	IpAddress
	ACCESS	read-only
	STATUS	mandatory
	DESCRIPTION
		"FC Switch blade GatewayAddress "
	::={ s31FCSwitchBladeEntry 10 }


s31FCSwitchBladeFcIpAddress OBJECT-TYPE
	SYNTAX	IpAddress
	ACCESS	read-only
	STATUS	mandatory
	DESCRIPTION
		"FC Switch blade FC IP Address"
	::={ s31FCSwitchBladeEntry 11 }

s31FCSwitchBladeFcSubnetMask OBJECT-TYPE
	SYNTAX	IpAddress
	ACCESS	read-only
	STATUS	mandatory
	DESCRIPTION
		"FC Switch blade FC Subnet Mask "
	::={ s31FCSwitchBladeEntry 12 }

s31FCSwitchBladeFcSwitchName OBJECT-TYPE
	SYNTAX	DisplayString
	ACCESS	read-only
	STATUS	mandatory
	DESCRIPTION
		"FC Switch blade FC Switch Name "
	::={ s31FCSwitchBladeEntry 13 }

s31FCSwitchBladeFcDomainId OBJECT-TYPE
	SYNTAX	DisplayString
	ACCESS	read-only
	STATUS	mandatory
	DESCRIPTION
		"FC Switch blade FC Domain Id "
	::={ s31FCSwitchBladeEntry 14 }

s31FCSwitchBladeSlotId OBJECT-TYPE
	SYNTAX	INTEGER
	ACCESS	read-only
	STATUS	mandatory
	DESCRIPTION
		"FC Switch blade slot ID"
	::={ s31FCSwitchBladeEntry 15 }

s31FCSwitchBladeFirmwareVersion OBJECT-TYPE
	SYNTAX	DisplayString
	ACCESS	read-only
	STATUS	mandatory
	DESCRIPTION
		"FC Switch blade Firmware version"
	::={ s31FCSwitchBladeEntry 16 }

s31FCSwitchBladeStatus OBJECT-TYPE
	SYNTAX	INTEGER{
		unknown(1),
		ok(2),
		not-present(3),
		error(4),
		critical(5),
		standby(6)
	}
	ACCESS	read-only
	STATUS	mandatory
	DESCRIPTION
		"Current status of this FC switch blade"
	::={ s31FCSwitchBladeEntry 17 }

s31FCSwitchBladeAdministrativeURL OBJECT-TYPE
	SYNTAX	DisplayString
	ACCESS	read-only
	STATUS	mandatory
	DESCRIPTION
		"Administrative URL of the FC switch blade"
	::={ s31FCSwitchBladeEntry 18 }

s31FCSwitchBladeAddressType OBJECT-TYPE
	SYNTAX	INTEGER{
        unknown(0),
        ipv4(1),
        ipv6(2),
        ipv4z(3),
        ipv6z(4),
        dns(16)
	}
	ACCESS	read-only
	STATUS	mandatory
	DESCRIPTION
		"Identify IP address type of the FC switch blade"
	::={ s31FCSwitchBladeEntry 19 }

s31FCSwitchBladeAddress OBJECT-TYPE
    SYNTAX  OCTET STRING (SIZE (1..64))
	ACCESS	read-only
	STATUS	mandatory
	DESCRIPTION
		"IP address for IPv6 of the FC switch blade"
	::={ s31FCSwitchBladeEntry 20 }

s31FCSwitchBladePhysicalAddress OBJECT-TYPE
	SYNTAX	PhysAddress
	ACCESS	read-only
	STATUS	mandatory
	DESCRIPTION
		"FC switch blade MAC address"
	::={ s31FCSwitchBladeEntry 21 }

s31FCSwitchBladeAssetTag OBJECT-TYPE
    SYNTAX  OCTET STRING (SIZE (1..40))
	ACCESS	read-write
	STATUS	mandatory
	DESCRIPTION
		"Asset tag for this FC switch blade"
	::={ s31FCSwitchBladeEntry 22 }

-- **********************************************************************************************
--
-- GROUP: s31StorageBlade
--
--      s31MgmtAgent MIB:        1.3.6.1.4.1.7244.1.1.1
--      s31StorageBlade group:              1.3.6.1.4.1.7244.1.1.1.13
--
-- **********************************************************************************************

s31StorageBladeTable OBJECT-TYPE
	SYNTAX	SEQUENCE OF S31StorageBladeEntry
	ACCESS	not-accessible
	STATUS	mandatory
	DESCRIPTION
		"Table with data of Storage Blade blade"
	::={ s31StorageBlade 1 }

s31StorageBladeEntry OBJECT-TYPE
	SYNTAX	S31StorageBladeEntry
	ACCESS	not-accessible
	STATUS	mandatory
	DESCRIPTION
		""
	INDEX	{ s31StorageBladeId }
	::={ s31StorageBladeTable 1 }

S31StorageBladeEntry ::=
	SEQUENCE {
		s31StorageBladeId
			INTEGER,
		s31StorageBladeManufacture
			DisplayString,
		s31StorageBladeManufactureDate
			DisplayString,
		s31StorageBladeSerialNumber
			DisplayString,
		s31StorageBladeProductName
			DisplayString,
		s31StorageBladeModelName
			DisplayString,
		s31StorageBladeHardwareVersion
			DisplayString,
		s31StorageBladeStatus
			INTEGER,
		s31StorageBladeFWVersion
			DisplayString,
		s31StorageBladeIdentSerialNumber
			DisplayString,
		s31StorageBladeAdministrativeURL
			DisplayString,
		s31StorageBladeCustomerProductName
			DisplayString,
		s31StorageBladeAssetTag
			OCTET STRING (SIZE (1..40)),
		s31StorageBladeCtrlStatLed
			INTEGER
	}

s31StorageBladeId OBJECT-TYPE
	SYNTAX	INTEGER (1..20)
	ACCESS	read-only
	STATUS	mandatory
	DESCRIPTION
		"Storage Blade blade number, index into the Storage Blade blade table (1 based)"
	::={ s31StorageBladeEntry 1 }

s31StorageBladeManufacture OBJECT-TYPE
	SYNTAX	DisplayString
	ACCESS	read-only
	STATUS	mandatory
	DESCRIPTION
		"String containing the Storage Blade blade manufacturer"
	::={ s31StorageBladeEntry 2 }

s31StorageBladeManufactureDate OBJECT-TYPE
	SYNTAX	DisplayString
	ACCESS	read-only
	STATUS	mandatory
	DESCRIPTION
		"Manufacture date of the Storage Blade blade"
	::={ s31StorageBladeEntry 3 }

s31StorageBladeSerialNumber OBJECT-TYPE
	SYNTAX	DisplayString
	ACCESS	read-only
	STATUS	mandatory
	DESCRIPTION
		"Serial number of the Storage Blade blade"
	::={ s31StorageBladeEntry 4 }

s31StorageBladeProductName OBJECT-TYPE
	SYNTAX	DisplayString
	ACCESS	read-only
	STATUS	mandatory
	DESCRIPTION
		"Product name of the Storage Blade blade"
	::={ s31StorageBladeEntry 5 }

s31StorageBladeModelName OBJECT-TYPE
	SYNTAX	DisplayString
	ACCESS	read-only
	STATUS	mandatory
	DESCRIPTION
		"Model name of the Storage Blade blade"
	::={ s31StorageBladeEntry 6 }

s31StorageBladeHardwareVersion OBJECT-TYPE
	SYNTAX	DisplayString
	ACCESS	read-only
	STATUS	mandatory
	DESCRIPTION
		"Storage Blade hardware version"
	::={ s31StorageBladeEntry 7 }

s31StorageBladeStatus OBJECT-TYPE
	SYNTAX	INTEGER{
		unknown(1),
		ok(2),
		not-present(3),
		error(4),
		critical(5),
		standby(6)
	}
	ACCESS	read-only
	STATUS	mandatory
	DESCRIPTION
		"Current status of this storage blade"
	::={ s31StorageBladeEntry 8 }

s31StorageBladeFWVersion OBJECT-TYPE
	SYNTAX	DisplayString
	ACCESS	read-only
	STATUS	mandatory
	DESCRIPTION
		"Firmware revision of the storage blade"
	::={ s31StorageBladeEntry 9 }

s31StorageBladeIdentSerialNumber OBJECT-TYPE
	SYNTAX	DisplayString
	ACCESS	read-only
	STATUS	mandatory
	DESCRIPTION
		"Ident serial number of the Storage Blade blade"
	::={ s31StorageBladeEntry 10 }

s31StorageBladeAdministrativeURL OBJECT-TYPE
	SYNTAX	DisplayString
	ACCESS	read-only
	STATUS	mandatory
	DESCRIPTION
		"Administrative URL of the storage blade"
	::={ s31StorageBladeEntry 11 }

s31StorageBladeCustomerProductName OBJECT-TYPE
	SYNTAX	DisplayString
	ACCESS	read-only
	STATUS	mandatory
	DESCRIPTION
		"The product name of the storage blade as known to the
		 end customer"
	::={ s31StorageBladeEntry 12 }

s31StorageBladeAssetTag OBJECT-TYPE
    SYNTAX  OCTET STRING (SIZE (1..40))
	ACCESS	read-write
	STATUS	mandatory
	DESCRIPTION
		"Asset tag for this storage blade"
	::={ s31StorageBladeEntry 13 }

s31StorageBladeCtrlStatLed OBJECT-TYPE
	SYNTAX	INTEGER{
		unknown(1),
		off(2),
		blinking(3),
		on(4)
	}
	ACCESS	read-write
	STATUS	mandatory
	DESCRIPTION
		"Configure storage blade IDENTIFY (formerly STAT) LED status (off/blinking)"
	::={ s31StorageBladeEntry 14 }

-- **********************************************************************************************

s31StorageAssignTable OBJECT-TYPE
	SYNTAX	SEQUENCE OF S31StorageAssignEntry
	ACCESS	not-accessible
	STATUS	mandatory
	DESCRIPTION
		"Table describing the assignment between storage and CPU blade
		 This table only has entries for pairs of storage and CPU blades
		 that are connected to each other."
	::={ s31StorageBlade 2 }

s31StorageAssignEntry OBJECT-TYPE
	SYNTAX	S31StorageAssignEntry
	ACCESS	not-accessible
	STATUS	mandatory
	DESCRIPTION
		""
	INDEX	{ s31StorageAssignId, s31SvrAssignId }
	::={ s31StorageAssignTable 1 }

S31StorageAssignEntry ::=
	SEQUENCE {
		s31StorageAssignId
			INTEGER,
		s31SvrAssignId
			INTEGER
	}

s31StorageAssignId OBJECT-TYPE
	SYNTAX	INTEGER (1..20)
	ACCESS	read-only
	STATUS	mandatory
	DESCRIPTION
		"Storage Blade number, index into the Storage Blade table (1 based)"
	::={ s31StorageAssignEntry 1 }

s31SvrAssignId OBJECT-TYPE
	SYNTAX	INTEGER (1..20)
	ACCESS	read-only
	STATUS	mandatory
	DESCRIPTION
		"Server Blade number, index into the Server Blade table (1 based)"
	::={ s31StorageAssignEntry 2 }

-- **********************************************************************************************
--
-- GROUP: s31fscErrorlog
--
--      s31MgmtAgent MIB:			1.3.6.1.4.1.7244.1.1.1
--      s31fscErrorlogMIB group:		1.3.6.1.4.1.7244.1.1.1.14
--
-- **********************************************************************************************

s31elOverviewTable OBJECT-TYPE
    SYNTAX      SEQUENCE OF S31elOverviewEntry
    ACCESS  	not-accessible
    STATUS      mandatory
    DESCRIPTION
		"A table definining Event Log Configuration records."
    ::= { s31el2 1 }

s31elOverviewEntry OBJECT-TYPE
    SYNTAX      S31elOverviewEntry
    ACCESS  	not-accessible
    STATUS      mandatory
    DESCRIPTION
        "Each source has a Event Configuration record, which contains
        per source pertinent logging information."
    INDEX    	{ s31elLogSource }
    ::= { s31elOverviewTable 1 }

S31elOverviewEntry ::= SEQUENCE {
    s31elOverviewSrc              	INTEGER,
    s31elUpdateFlag		           	INTEGER,
    s31elLogNums	              	INTEGER
}

s31elOverviewSrc OBJECT-TYPE
	  SYNTAX	INTEGER{
		   mmb(1),
		   serverblade-1(2),
		   serverblade-2(3),
		   serverblade-3(4),
		   serverblade-4(5),
		   serverblade-5(6),
		   serverblade-6(7),
		   serverblade-7(8),
		   serverblade-8(9),
		   serverblade-9(10),
		   serverblade-10(11),
		   serverblade-11(12),
		   serverblade-12(13),
		   serverblade-13(14),
		   serverblade-14(15),
		   serverblade-15(16),
		   serverblade-16(17),
		   serverblade-17(18),
		   serverblade-18(19)
	  }
    ACCESS  	read-only
    STATUS      mandatory
    DESCRIPTION
		"This object identifies the source of the event:
		Management Blade (1), Blade_1  2, ... "
    ::= { s31elOverviewEntry 1 }

s31elUpdateFlag      OBJECT-TYPE
    SYNTAX      INTEGER
    ACCESS  	read-only
    STATUS      mandatory
    DESCRIPTION
		"This object must be incremented, whenever the Log Table changes"
    ::= { s31elOverviewEntry 2 }

s31elLogNums    OBJECT-TYPE
    SYNTAX      INTEGER (1..512)
    ACCESS  	read-only
    STATUS      mandatory
    DESCRIPTION
		"The number of entries in the following table"
    ::= { s31elOverviewEntry 3 }

--
s31elConfigTable OBJECT-TYPE
    SYNTAX      SEQUENCE OF S31elConfigEntry
    ACCESS  	not-accessible
    STATUS      mandatory
    DESCRIPTION
		"A table definining Event Log Configuration records."
    ::= { s31el2 2 }

s31elConfigEntry OBJECT-TYPE
    SYNTAX      S31elConfigEntry
    ACCESS  	not-accessible
    STATUS      mandatory
    DESCRIPTION
        "Each source has a Event Configuration record, which contains
        per source pertinent logging information."
    INDEX    	{ s31elLogSource }
    ::= { s31elConfigTable 1 }

S31elConfigEntry ::= SEQUENCE {
    s31elConfigSource           	INTEGER,
    s31elConfigLoglevel           	INTEGER,
    s31elConfigLimit              	INTEGER,
    s31elConfigCount	            INTEGER,
    s31elConfigClearLog				INTEGER
}

s31elConfigSource OBJECT-TYPE
    SYNTAX      INTEGER (0..18)
    ACCESS  	read-only
    STATUS      mandatory
    DESCRIPTION
		"This object identifies the source of the event:
		Management Blade (1), Blade_1  2, ... "
    ::= { s31elConfigEntry 1 }

s31elConfigLoglevel      OBJECT-TYPE
	SYNTAX      INTEGER 
    ACCESS  	read-write
    STATUS      mandatory
    DESCRIPTION "0:info,1:minor,2:major,3:critical,100:display all"
    ::= { s31elConfigEntry 2 }

s31elConfigLimit OBJECT-TYPE
    SYNTAX      INTEGER
    ACCESS  	read-write
    STATUS      mandatory
    DESCRIPTION
		"The maximum number of entries the table is able to hold for this source."
    ::= { s31elConfigEntry 3 }

s31elConfigCount OBJECT-TYPE
    SYNTAX      INTEGER
    ACCESS  	read-only
    STATUS      mandatory
    DESCRIPTION
        "The current number of entries the table has for this source."
    ::= { s31elConfigEntry 4 }

s31elConfigClearLog OBJECT-TYPE
    SYNTAX    INTEGER 
    ACCESS  	read-write
    STATUS      mandatory
    DESCRIPTION
        "The value of this object is set to 1 to erase the contents of the
		Event Log of the specified source."
    ::= { s31elConfigEntry 5 }
    
--

s31elLogTable OBJECT-TYPE
	SYNTAX	SEQUENCE OF S31elLogEntry
	ACCESS	not-accessible
	STATUS	obsolete
	DESCRIPTION
		"A table containing Event Log records."
	::={ s31el2 3 }


s31elLogEntry OBJECT-TYPE
    SYNTAX      S31elLogEntry
    ACCESS  not-accessible
    STATUS      obsolete
    DESCRIPTION
        "This table presents the list of all events which are present in the
         MMB event log."
    INDEX	{ s31elLogSource,s31elLogId}
    ::= { s31elLogTable 1 }

S31elLogEntry ::= SEQUENCE {
    s31elLogSource			INTEGER,
    s31elLogTime			DisplayString,
    s31elLogSeverity		DisplayString,
    s31elLogId				INTEGER,
    s31elLogText			DisplayString
}


s31elLogSource OBJECT-TYPE
    SYNTAX	INTEGER{
		   mmb(1),
		   serverblade-1(2),
		   serverblade-2(3),
		   serverblade-3(4),
		   serverblade-4(5),
		   serverblade-5(6),
		   serverblade-6(7),
		   serverblade-7(8),
		   serverblade-8(9),
		   serverblade-9(10),
		   serverblade-10(11),
		   serverblade-11(12),
		   serverblade-12(13),
		   serverblade-13(14),
		   serverblade-14(15),
		   serverblade-15(16),
		   serverblade-16(17),
		   serverblade-17(18),
		   serverblade-18(19)
	  }
    ACCESS  	read-only
    STATUS      obsolete
    DESCRIPTION
		"This object identifies the source of the event:
		Management Blade (1), Blade_1  2, ... "
    ::= { s31elLogEntry 1 }


s31elLogTime OBJECT-TYPE
	SYNTAX	DisplayString
	ACCESS	read-only
	STATUS	obsolete
	DESCRIPTION
		"The time the event was received"
	::={ s31elLogEntry 2 }


s31elLogSeverity OBJECT-TYPE
	SYNTAX	DisplayString
	ACCESS	read-only
	STATUS	obsolete
	DESCRIPTION
		"The severity of the event."
	::={ s31elLogEntry 3 }


s31elLogId      OBJECT-TYPE
    SYNTAX      INTEGER (1..512)
    ACCESS  read-only
    STATUS      obsolete
    DESCRIPTION
		"A unique id as an index"
    ::= { s31elLogEntry 4 }

s31elLogText      OBJECT-TYPE
    SYNTAX      DisplayString 
    ACCESS  read-only
    STATUS      obsolete
    DESCRIPTION
		"The event text"
    ::= { s31elLogEntry 5 }

--

s31elAuditTable OBJECT-TYPE
	SYNTAX	SEQUENCE OF S31elAuditEntry
	ACCESS	not-accessible
	STATUS	mandatory
	DESCRIPTION
		"A table containing audit log records."
	::={ s31el2 4 }

s31elAuditEntry OBJECT-TYPE
    SYNTAX      S31elAuditEntry
    ACCESS  not-accessible
    STATUS      mandatory
    DESCRIPTION
        "This table presents the list of all audit log entries which are
		 available within the MMB."
    INDEX	{ s31elAuditId }
    ::= { s31elAuditTable 1 }

S31elAuditEntry ::= SEQUENCE {
    s31elAuditId		INTEGER,
    s31elAuditTime		DisplayString,
    s31elAuditSeverity	DisplayString,
    s31elAuditText		DisplayString
}

s31elAuditId      OBJECT-TYPE
    SYNTAX      INTEGER (1..512)
    ACCESS  	read-only
    STATUS      mandatory
    DESCRIPTION
		"A unique id as an index"
    ::= { s31elAuditEntry 4 }

s31elAuditTime OBJECT-TYPE
	SYNTAX	DisplayString
	ACCESS	read-only
	STATUS	mandatory
	DESCRIPTION
		"The time the audit log entry was created"
	::={ s31elAuditEntry 2 }

s31elAuditSeverity OBJECT-TYPE
	SYNTAX	DisplayString
	ACCESS	read-only
	STATUS	mandatory
	DESCRIPTION
		"The severity of the audit log entry."
	::={ s31elAuditEntry 3 }

s31elAuditText      OBJECT-TYPE
    SYNTAX      DisplayString 
    ACCESS  	read-only
    STATUS      mandatory
    DESCRIPTION
		"The text of the audit log entry"
    ::= { s31elAuditEntry 5 }

--

s31elLogLanguages OBJECT-TYPE
    SYNTAX       DisplayString
    ACCESS       read-only
    STATUS       mandatory
    DESCRIPTION  "Supported languages of text message log (comma-seperated list of
                    decimal language codes, see s31elTextLogTable).
                  e.g. '1031,1033' means German and English are supported.
                  English (1033) is the default language and is always available."
	::={ s31el2 5 }

s31elTextLogTable OBJECT-TYPE
	SYNTAX	SEQUENCE OF S31elTextLogEntry
	ACCESS	not-accessible
	STATUS	mandatory
	DESCRIPTION
		"A table containing Event Log records, reported as text strings"
::={ s31el2 6 }

-- The message log entries in this table are reported as clear text strings.
-- The log ID is a unique entry number (unique in a unit) and can
--   be used to avoid duplicate entries. It may start with any number (not
--   necessarily 0).
-- The oldest entries have the lowest log id
-- The log can be queried in different languages, the language code defines what
--   language to be reported. See object "s31elLogLanguages"
--   for the available languages.
-- Each MIB table entry can contain only one message entry!
--

s31elTextLogEntry OBJECT-TYPE
    SYNTAX      S31elTextLogEntry
    ACCESS  not-accessible
    STATUS      mandatory
    DESCRIPTION
        "This table presents the list of all events which are present in the
         MMB event log."
    INDEX	{ s31elTextLogLanguage, s31elTextLogSource, s31elTextLogId}
    ::= { s31elTextLogTable 1 }

S31elTextLogEntry ::= SEQUENCE {
    s31elTextLogLanguage		INTEGER,
    s31elTextLogSource			INTEGER,
    s31elTextLogId				INTEGER,
    s31elTextLogTime			DisplayString,
    s31elTextLogSeverity		DisplayString,
    s31elTextLogMessage			DisplayString,
	s31elTextLogErrorCode 		INTEGER,
    s31elTextLogCSSComponent	INTEGER
}


s31elTextLogLanguage OBJECT-TYPE
    SYNTAX       INTEGER
    ACCESS       read-only
    STATUS       mandatory
    DESCRIPTION  "Message log entry language (index, Windows language code)
                  e.g. 1031, 1033 for German, English (default; always available)"
    ::= { s31elTextLogEntry 1 }


s31elTextLogSource OBJECT-TYPE
    SYNTAX	INTEGER{
		   mmb(1),
		   serverblade-1(2),
		   serverblade-2(3),
		   serverblade-3(4),
		   serverblade-4(5),
		   serverblade-5(6),
		   serverblade-6(7),
		   serverblade-7(8),
		   serverblade-8(9),
		   serverblade-9(10),
		   serverblade-10(11),
		   serverblade-11(12),
		   serverblade-12(13),
		   serverblade-13(14),
		   serverblade-14(15),
		   serverblade-15(16),
		   serverblade-16(17),
		   serverblade-17(18),
		   serverblade-18(19)
	  }
    ACCESS  	read-only
    STATUS      mandatory
    DESCRIPTION
		"This object identifies the source of the event:
		Management Blade (1), Blade_1  2, ... "
    ::= { s31elTextLogEntry 2 }


s31elTextLogId      OBJECT-TYPE
    SYNTAX      INTEGER (1..512)
    ACCESS  read-only
    STATUS      mandatory
    DESCRIPTION
		"A unique id as an index"
    ::= { s31elTextLogEntry 3 }


s31elTextLogTime OBJECT-TYPE
	SYNTAX	DisplayString
	ACCESS	read-only
	STATUS	mandatory
	DESCRIPTION
		"The time the event was received"
	::={ s31elTextLogEntry 4 }


s31elTextLogSeverity OBJECT-TYPE
	SYNTAX	DisplayString
	ACCESS	read-only
	STATUS	mandatory
	DESCRIPTION
		"The severity of the event."
	::={ s31elTextLogEntry 5 }


s31elTextLogMessage      OBJECT-TYPE
    SYNTAX      DisplayString 
    ACCESS  read-only
    STATUS      mandatory
    DESCRIPTION
		"The event text in the required language (multibyte encoding)"
    ::= { s31elTextLogEntry 6 }

s31elTextLogErrorCode OBJECT-TYPE
    SYNTAX       INTEGER
    ACCESS       read-only
    STATUS       mandatory
    DESCRIPTION  "Message log entry error code"
    ::= { s31elTextLogEntry 7 }

s31elTextLogCSSComponent OBJECT-TYPE
    SYNTAX       INTEGER
    {
      false(1),
      true(2)
    }
    ACCESS       read-only
    STATUS       mandatory
    DESCRIPTION  "Component which caused the log message may be replaced by the customer (CSS=Customer Self Service)"
    ::= { s31elTextLogEntry 8 }

--

s31MessageLogActionHintTable OBJECT-TYPE
    SYNTAX       SEQUENCE OF S31MessageLogActionHints
    ACCESS       not-accessible
    STATUS       mandatory
    DESCRIPTION  "Action text strings for error and event messages"
	::={ s31el2 7 }

s31MessageLogActionHints OBJECT-TYPE
    SYNTAX       S31MessageLogActionHints
    ACCESS       not-accessible
    STATUS       mandatory
    DESCRIPTION  ""
    INDEX   { s31mlaLanguage, s31mlaErrorCode, s31mlaType, s31mlaIndex }
    ::= { s31MessageLogActionHintTable 1 }

S31MessageLogActionHints ::= SEQUENCE
{
    s31mlaLanguage
        INTEGER,
    s31mlaErrorCode
        INTEGER,
    s31mlaType
        INTEGER,
    s31mlaIndex
        INTEGER,
    s31mlaMessage
        DisplayString
}

s31mlaLanguage OBJECT-TYPE
    SYNTAX       INTEGER
    ACCESS       read-only
    STATUS       mandatory
    DESCRIPTION  "Action text language (index, Windows language code)
                  e.g. 1031, 1033 for German, English"
    ::= { s31MessageLogActionHints 1 }

s31mlaErrorCode OBJECT-TYPE
    SYNTAX       INTEGER
    ACCESS       read-only
    STATUS       mandatory
    DESCRIPTION  "Action text error code (index)"
    ::= { s31MessageLogActionHints 2 }

s31mlaType OBJECT-TYPE
    SYNTAX       INTEGER
    {
        summary(1),
        cause(2),
        resolution(3)
    }
    ACCESS       read-only
    STATUS       mandatory
    DESCRIPTION  "Message log entry severity"
    ::= { s31MessageLogActionHints 3 }

s31mlaIndex OBJECT-TYPE
    SYNTAX       INTEGER
    ACCESS       read-only
    STATUS       mandatory
    DESCRIPTION  "Action text entry string index (index, 1..n)"
    ::= { s31MessageLogActionHints 4 }

s31mlaMessage OBJECT-TYPE
    SYNTAX       DisplayString
    ACCESS       read-only
    STATUS       mandatory
    DESCRIPTION  "Action message string"
    ::= { s31MessageLogActionHints 5 }


-- **********************************************************************************************
--
-- GROUP: s31PowerConsumptionHistory
--
--      s31MgmtAgent MIB:       		 1.3.6.1.4.1.7244.1.1.1
--      s31PowerConsumptionHistory group:        1.3.6.1.4.1.7244.1.1.1.15
--
-- **********************************************************************************************

s31UtilizationHistoryTable OBJECT-TYPE
    SYNTAX       SEQUENCE OF S31UtilizationHistory
    ACCESS       not-accessible
    STATUS       mandatory
    DESCRIPTION  "Utilization history table (for power consumption); table only contains existing
                  values (no values for non-existing values)"
    ::= { s31PowerConsumptionHistory 1 }

s31UtilizationHistoryEntry OBJECT-TYPE
    SYNTAX       S31UtilizationHistory
    ACCESS       not-accessible
    STATUS       mandatory
    DESCRIPTION  ""
    INDEX   { s31uthUnitId, s31uthEntity, s31uthTimeStamp }
    ::= { s31UtilizationHistoryTable 1 }

S31UtilizationHistory ::= SEQUENCE
{
    s31uthUnitId
        INTEGER,
    s31uthEntity
        INTEGER,
    s31uthTimeStamp
        INTEGER,
    s31uthHardwareUUID
        DisplayString,
    s31uthAverageValue
        Gauge,
    s31uthMinValue
        Gauge,
    s31uthMaxValue
        Gauge
}

s31uthUnitId OBJECT-TYPE
    SYNTAX       INTEGER
    ACCESS       read-only
    STATUS       mandatory
    DESCRIPTION  "Unit identifier (index, 1..n)"
    ::= { s31UtilizationHistoryEntry 1 }

s31uthEntity OBJECT-TYPE
    SYNTAX       INTEGER
    {
        powerConsumptionDay(1),
        powerConsumptionMonth(2),
        powerConsumptionYear(3)
    }
    ACCESS       read-only
    STATUS       mandatory
    DESCRIPTION  "Utilization value entity; describes what kind of value to be requested:
                    powerConsumptionDay:   power consumption values of the last 24 hours; one value (Watts) per minute
                    powerConsumptionMonth: power consumption values of the last month; one value (Watts) per hour
                    powerConsumptionYear:  power consumption values of the last year; one value (Watts) per day"
    ::= { s31UtilizationHistoryEntry 2 }

s31uthTimeStamp OBJECT-TYPE
    SYNTAX       INTEGER
    ACCESS       read-only
    STATUS       mandatory
    DESCRIPTION  "Time stamp of the currenty history entry (time_t = seconds since 1/1/1970, 0:00 AM)"
    ::= { s31UtilizationHistoryEntry 3 }

s31uthHardwareUUID OBJECT-TYPE
    SYNTAX       DisplayString
    ACCESS       read-only
    STATUS       mandatory
    DESCRIPTION  "UUID of the hardware instance that delivered the value (from object s31srvUUID);
                  may change if an installation is migrated to another hardware (e.g. in blade environments)"
    ::= { s31UtilizationHistoryEntry 4 }

s31uthAverageValue OBJECT-TYPE
    SYNTAX       Gauge
    ACCESS       read-only
    STATUS       mandatory
    DESCRIPTION  "Average value (in Watts) within the monitored time period (minute, hour, day)"
    ::= { s31UtilizationHistoryEntry 5 }

s31uthMinValue OBJECT-TYPE
    SYNTAX       Gauge
    ACCESS       read-only
    STATUS       mandatory
    DESCRIPTION  "Minimum (lowest) value within the monitored time period"
    ::= { s31UtilizationHistoryEntry 6 }

s31uthMaxValue OBJECT-TYPE
    SYNTAX       Gauge
    ACCESS       read-only
    STATUS       mandatory
    DESCRIPTION  "Maximum (highest) value within the monitored time period"
    ::= { s31UtilizationHistoryEntry 7 }

-- **********************************************************************************************
--
-- GROUP: s31IBSwitchBlade
--
--      s31MgmtAgent MIB:        1.3.6.1.4.1.7244.1.1.1
--      s31IBSwitchBlade group:              1.3.6.1.4.1.7244.1.1.1.16
--
-- **********************************************************************************************

s31IBSwitchBladeTable OBJECT-TYPE
	SYNTAX	SEQUENCE OF S31IBSwitchBladeEntry
	ACCESS	not-accessible
	STATUS	mandatory
	DESCRIPTION
		"Table with data of Infiniband Switch blade"
	::={ s31IBSwitchBlade 1 }

s31IBSwitchBladeEntry OBJECT-TYPE
	SYNTAX	S31IBSwitchBladeEntry
	ACCESS	not-accessible
	STATUS	mandatory
	DESCRIPTION
		""
	INDEX	{ s31IBSwitchBladeId }
	::={ s31IBSwitchBladeTable 1 }

S31IBSwitchBladeEntry ::=
	SEQUENCE {
		s31IBSwitchBladeId
			INTEGER,
		s31IBSwitchBladeManufacture
			DisplayString,
		s31IBSwitchBladeManufactureDate
			DisplayString,
		s31IBSwitchBladeSerialNumber
			DisplayString,
		s31IBSwitchBladeProductName
			DisplayString,
		s31IBSwitchBladeModelName
			DisplayString,
		s31IBSwitchBladeHardwareVersion
			DisplayString,
		s31IBSwitchBladeIpAddress
			IpAddress,
		s31IBSwitchBladeSubnetMask
			IpAddress,
		s31IBSwitchBladeGatewayAddress
			IpAddress,
		s31IBSwitchBladeSlotId
			INTEGER,
		s31IBSwitchBladeFirmwareVersion
			DisplayString,
		s31IBSwitchBladeStatus
			INTEGER,
		s31IBSwitchBladeAdministrativeURL
			DisplayString,
		s31IBSwitchBladeAddressType
			INTEGER,
		s31IBSwitchBladeAddress
			OCTET STRING (SIZE (1..64)),
		s31IBSwitchBladePhysicalAddress
			PhysAddress,
		s31IBSwitchBladeAssetTag
			OCTET STRING (SIZE (1..40))
	}

s31IBSwitchBladeId OBJECT-TYPE
	SYNTAX	INTEGER (1..8)
	ACCESS	read-only
	STATUS	mandatory
	DESCRIPTION
		"Infiniband Switch blade number, index into the Infiniband Switch blade table (1 based)"
	::={ s31IBSwitchBladeEntry 1 }

s31IBSwitchBladeManufacture OBJECT-TYPE
	SYNTAX	DisplayString
	ACCESS	read-only
	STATUS	mandatory
	DESCRIPTION
		"String containing the Infiniband Switch blade manufacturer"
	::={ s31IBSwitchBladeEntry 2 }

s31IBSwitchBladeManufactureDate OBJECT-TYPE
	SYNTAX	DisplayString
	ACCESS	read-only
	STATUS	mandatory
	DESCRIPTION
		"Manufacture date of the Infiniband Switch blade"
	::={ s31IBSwitchBladeEntry 3 }

s31IBSwitchBladeSerialNumber OBJECT-TYPE
	SYNTAX	DisplayString
	ACCESS	read-only
	STATUS	mandatory
	DESCRIPTION
		"Serial number of the Infiniband Switch blade"
	::={ s31IBSwitchBladeEntry 4 }

s31IBSwitchBladeProductName OBJECT-TYPE
	SYNTAX	DisplayString
	ACCESS	read-only
	STATUS	mandatory
	DESCRIPTION
		"Product name of the Infiniband Switch blade"
	::={ s31IBSwitchBladeEntry 5 }

s31IBSwitchBladeModelName OBJECT-TYPE
	SYNTAX	DisplayString
	ACCESS	read-only
	STATUS	mandatory
	DESCRIPTION
		"Model name of the Infiniband Switch blade"
	::={ s31IBSwitchBladeEntry 6 }

s31IBSwitchBladeHardwareVersion OBJECT-TYPE
	SYNTAX	DisplayString
	ACCESS	read-only
	STATUS	mandatory
	DESCRIPTION
		"Infiniband Switch blade hardware version"
	::={ s31IBSwitchBladeEntry 7 }

s31IBSwitchBladeIpAddress OBJECT-TYPE
	SYNTAX	IpAddress
	ACCESS	read-only
	STATUS	mandatory
	DESCRIPTION
		"Infiniband Switch blade IP address"
	::={ s31IBSwitchBladeEntry 8 }

s31IBSwitchBladeSubnetMask OBJECT-TYPE
	SYNTAX	IpAddress
	ACCESS	read-only
	STATUS	mandatory
	DESCRIPTION
		"Infiniband Switch blade Subnet Mask "
	::={ s31IBSwitchBladeEntry 9 }

s31IBSwitchBladeGatewayAddress OBJECT-TYPE
	SYNTAX	IpAddress
	ACCESS	read-only
	STATUS	mandatory
	DESCRIPTION
		"Infiniband Switch blade GatewayAddress "
	::={ s31IBSwitchBladeEntry 10 }

s31IBSwitchBladeSlotId OBJECT-TYPE
	SYNTAX	INTEGER
	ACCESS	read-only
	STATUS	mandatory
	DESCRIPTION
		"Infiniband Switch blade slot ID"
	::={ s31IBSwitchBladeEntry 11 }

s31IBSwitchBladeFirmwareVersion OBJECT-TYPE
	SYNTAX	DisplayString
	ACCESS	read-only
	STATUS	mandatory
	DESCRIPTION
		"Infiniband Switch blade Firmware version"
	::={ s31IBSwitchBladeEntry 12 }

s31IBSwitchBladeStatus OBJECT-TYPE
	SYNTAX	INTEGER{
		unknown(1),
		ok(2),
		not-present(3),
		error(4),
		critical(5),
		standby(6)
	}
	ACCESS	read-only
	STATUS	mandatory
	DESCRIPTION
		"Current status of this Infiniband switch blade"
	::={ s31IBSwitchBladeEntry 13 }

s31IBSwitchBladeAdministrativeURL OBJECT-TYPE
	SYNTAX	DisplayString
	ACCESS	read-only
	STATUS	mandatory
	DESCRIPTION
		"Administrative URL of the Infiniband switch blade"
	::={ s31IBSwitchBladeEntry 14 }

s31IBSwitchBladeAddressType OBJECT-TYPE
	SYNTAX	INTEGER{
        unknown(0),
        ipv4(1),
        ipv6(2),
        ipv4z(3),
        ipv6z(4),
        dns(16)
	}
	ACCESS	read-only
	STATUS	mandatory
	DESCRIPTION
		"Identify IP address type of the Infiniband switch blade"
	::={ s31IBSwitchBladeEntry 15 }

s31IBSwitchBladeAddress OBJECT-TYPE
    SYNTAX  OCTET STRING (SIZE (1..64))
	ACCESS	read-only
	STATUS	mandatory
	DESCRIPTION
		"IP address for IPv6 of the Infiniband switch blade"
	::={ s31IBSwitchBladeEntry 16 }

s31IBSwitchBladePhysicalAddress OBJECT-TYPE
	SYNTAX	PhysAddress
	ACCESS	read-only
	STATUS	mandatory
	DESCRIPTION
		"Infiniband switch blade MAC address"
	::={ s31IBSwitchBladeEntry 17 }

s31IBSwitchBladeAssetTag OBJECT-TYPE
    SYNTAX  OCTET STRING (SIZE (1..40))
	ACCESS	read-write
	STATUS	mandatory
	DESCRIPTION
		"Asset tag for this Infiniband switch blade"
	::={ s31IBSwitchBladeEntry 18 }

-- **********************************************************************************************
--
-- GROUP: s31SASSwitchBlade
--
--      s31MgmtAgent MIB:        1.3.6.1.4.1.7244.1.1.1
--      s31SASSwitchBlade group:              1.3.6.1.4.1.7244.1.1.1.17
--
-- **********************************************************************************************

s31SASSwitchBladeTable OBJECT-TYPE
	SYNTAX	SEQUENCE OF S31SASSwitchBladeEntry
	ACCESS	not-accessible
	STATUS	mandatory
	DESCRIPTION
		"Table with data of SAS Switch blade"
	::={ s31SASSwitchBlade 1 }

s31SASSwitchBladeEntry OBJECT-TYPE
	SYNTAX	S31SASSwitchBladeEntry
	ACCESS	not-accessible
	STATUS	mandatory
	DESCRIPTION
		""
	INDEX	{ s31SASSwitchBladeId }
	::={ s31SASSwitchBladeTable 1 }

S31SASSwitchBladeEntry ::=
	SEQUENCE {
		s31SASSwitchBladeId
			INTEGER,
		s31SASSwitchBladeManufacture
			DisplayString,
		s31SASSwitchBladeManufactureDate
			DisplayString,
		s31SASSwitchBladeSerialNumber
			DisplayString,
		s31SASSwitchBladeProductName
			DisplayString,
		s31SASSwitchBladeModelName
			DisplayString,
		s31SASSwitchBladeHardwareVersion
			DisplayString,
		s31SASSwitchBladeIpAddress
			IpAddress,
		s31SASSwitchBladeSubnetMask
			IpAddress,
		s31SASSwitchBladeGatewayAddress
			IpAddress,
		s31SASSwitchBladeSlotId
			INTEGER,
		s31SASSwitchBladeFirmwareVersion
			DisplayString,
		s31SASSwitchBladeStatus
			INTEGER,
		s31SASSwitchBladeAdministrativeURL
			DisplayString,
		s31SASSwitchBladeAddressType
			INTEGER,
		s31SASSwitchBladeAddress
			OCTET STRING (SIZE (1..64)),
		s31SASSwitchBladePhysicalAddress
			PhysAddress,
		s31SASSwitchBladeAssetTag
			OCTET STRING (SIZE (1..40))
	}

s31SASSwitchBladeId OBJECT-TYPE
	SYNTAX	INTEGER (1..8)
	ACCESS	read-only
	STATUS	mandatory
	DESCRIPTION
		"SAS Switch blade number, index into the SAS Switch blade table (1 based)"
	::={ s31SASSwitchBladeEntry 1 }

s31SASSwitchBladeManufacture OBJECT-TYPE
	SYNTAX	DisplayString
	ACCESS	read-only
	STATUS	mandatory
	DESCRIPTION
		"String containing the SAS Switch blade manufacturer"
	::={ s31SASSwitchBladeEntry 2 }

s31SASSwitchBladeManufactureDate OBJECT-TYPE
	SYNTAX	DisplayString
	ACCESS	read-only
	STATUS	mandatory
	DESCRIPTION
		"Manufacture date of the SAS Switch blade"
	::={ s31SASSwitchBladeEntry 3 }

s31SASSwitchBladeSerialNumber OBJECT-TYPE
	SYNTAX	DisplayString
	ACCESS	read-only
	STATUS	mandatory
	DESCRIPTION
		"Serial number of the SAS Switch blade"
	::={ s31SASSwitchBladeEntry 4 }

s31SASSwitchBladeProductName OBJECT-TYPE
	SYNTAX	DisplayString
	ACCESS	read-only
	STATUS	mandatory
	DESCRIPTION
		"Product name of the SAS Switch blade"
	::={ s31SASSwitchBladeEntry 5 }

s31SASSwitchBladeModelName OBJECT-TYPE
	SYNTAX	DisplayString
	ACCESS	read-only
	STATUS	mandatory
	DESCRIPTION
		"Model name of the SAS Switch blade"
	::={ s31SASSwitchBladeEntry 6 }

s31SASSwitchBladeHardwareVersion OBJECT-TYPE
	SYNTAX	DisplayString
	ACCESS	read-only
	STATUS	mandatory
	DESCRIPTION
		"SAS Switch blade hardware version"
	::={ s31SASSwitchBladeEntry 7 }

s31SASSwitchBladeIpAddress OBJECT-TYPE
	SYNTAX	IpAddress
	ACCESS	read-only
	STATUS	mandatory
	DESCRIPTION
		"SAS Switch blade IP address"
	::={ s31SASSwitchBladeEntry 8 }

s31SASSwitchBladeSubnetMask OBJECT-TYPE
	SYNTAX	IpAddress
	ACCESS	read-only
	STATUS	mandatory
	DESCRIPTION
		"SAS Switch blade Subnet Mask "
	::={ s31SASSwitchBladeEntry 9 }

s31SASSwitchBladeGatewayAddress OBJECT-TYPE
	SYNTAX	IpAddress
	ACCESS	read-only
	STATUS	mandatory
	DESCRIPTION
		"SAS Switch blade GatewayAddress "
	::={ s31SASSwitchBladeEntry 10 }

s31SASSwitchBladeSlotId OBJECT-TYPE
	SYNTAX	INTEGER
	ACCESS	read-only
	STATUS	mandatory
	DESCRIPTION
		"SAS Switch blade slot ID"
	::={ s31SASSwitchBladeEntry 11 }

s31SASSwitchBladeFirmwareVersion OBJECT-TYPE
	SYNTAX	DisplayString
	ACCESS	read-only
	STATUS	mandatory
	DESCRIPTION
		"SAS Switch blade Firmware version"
	::={ s31SASSwitchBladeEntry 12 }

s31SASSwitchBladeStatus OBJECT-TYPE
	SYNTAX	INTEGER{
		unknown(1),
		ok(2),
		not-present(3),
		error(4),
		critical(5),
		standby(6)
	}
	ACCESS	read-only
	STATUS	mandatory
	DESCRIPTION
		"Current status of this SAS switch blade"
	::={ s31SASSwitchBladeEntry 13 }

s31SASSwitchBladeAdministrativeURL OBJECT-TYPE
	SYNTAX	DisplayString
	ACCESS	read-only
	STATUS	mandatory
	DESCRIPTION
		"Administrative URL of the SAS switch blade"
	::={ s31SASSwitchBladeEntry 14 }

s31SASSwitchBladeAddressType OBJECT-TYPE
	SYNTAX	INTEGER{
        unknown(0),
        ipv4(1),
        ipv6(2),
        ipv4z(3),
        ipv6z(4),
        dns(16)
	}
	ACCESS	read-only
	STATUS	mandatory
	DESCRIPTION
		"Identify IP address type of the SAS switch blade"
	::={ s31SASSwitchBladeEntry 15 }

s31SASSwitchBladeAddress OBJECT-TYPE
    SYNTAX  OCTET STRING (SIZE (1..64))
	ACCESS	read-only
	STATUS	mandatory
	DESCRIPTION
		"IP address for IPv6 of the SAS switch blade"
	::={ s31SASSwitchBladeEntry 16 }

s31SASSwitchBladePhysicalAddress OBJECT-TYPE
	SYNTAX	PhysAddress
	ACCESS	read-only
	STATUS	mandatory
	DESCRIPTION
		"SAS switch blade MAC address"
	::={ s31SASSwitchBladeEntry 17 }

s31SASSwitchBladeAssetTag OBJECT-TYPE
    SYNTAX  OCTET STRING (SIZE (1..40))
	ACCESS	read-write
	STATUS	mandatory
	DESCRIPTION
		"Asset tag for this SAS switch blade"
	::={ s31SASSwitchBladeEntry 18 }

-- **********************************************************************************************
--
-- TRAP definitions
--
--      Trap ID range:       1600..1638
--      Trap enterprise:     s31MgmtAgent (1.3.6.1.4.1.7244.1.1.1)
--
-- **********************************************************************************************

s31TestTrap  TRAP-TYPE
	ENTERPRISE s31MgmtAgent
	VARIABLES {
		s31TrapServerName,
		s31TrapTime
	}
	DESCRIPTION
	    "Test trap to verify trap connection."
	--#TYPE         "Test trap"
	--#SUMMARY      "Test trap from blade chassis %s (no error)."
	--#ARGUMENTS    { 0 }
	--#SEVERITY     INFORMATIONAL
	--#TIMEINDEX    1
	--#STATE        OPERATIONAL
	::= 1600

s31MgmtBladeAdded  TRAP-TYPE
	ENTERPRISE s31MgmtAgent
	VARIABLES {
		s31TrapServerName,
		s31TrapTime,
		s31TrapObjectNumber,
		s31MgmtBladeId
	}
	DESCRIPTION
	    "Management blade was added"
	--#TYPE         "Management blade added"
	--#SUMMARY      "Management blade %d at blade chassis %s was added."
	--#ARGUMENTS    { 3,  0 }
	--#SEVERITY     INFORMATIONAL
	--#TIMEINDEX    1
	--#STATE        OPERATIONAL
	::= 1601

s31MgmtBladeRemoved TRAP-TYPE
	ENTERPRISE s31MgmtAgent
	VARIABLES {
		s31TrapServerName,
		s31TrapTime,
		s31TrapObjectNumber,
		s31MgmtBladeId
	}
	DESCRIPTION
	    "Management blade was removed"
	--#TYPE         "Management blade removed"
	--#SUMMARY      "Management blade %d at blade chassis %s was removed."
	--#ARGUMENTS    { 3,  0 }
	--#SEVERITY     INFORMATIONAL
	--#TIMEINDEX    1
	--#STATE        OPERATIONAL
	::= 1602

s31MgmtBladeOk  TRAP-TYPE
	ENTERPRISE s31MgmtAgent
	VARIABLES {
		s31TrapServerName,
		s31TrapTime,
		s31TrapObjectNumber,
		s31MgmtBladeId
	}
	DESCRIPTION
	    "Management blade status is OK"
	--#TYPE         "Status of management blade is OK"
	--#SUMMARY      "Management blade %d at blade chassis %s status is ok."
	--#ARGUMENTS    { 3,  0 }
	--#SEVERITY     INFORMATIONAL
	--#TIMEINDEX    1
	--#STATE        OPERATIONAL
	::= 1603

s31MgmtBladeError TRAP-TYPE
	ENTERPRISE s31MgmtAgent
	VARIABLES {
		s31TrapServerName,
		s31TrapTime,
		s31TrapObjectNumber,
		s31MgmtBladeId
	}
	DESCRIPTION
	    "Management blade status is error"
	--#TYPE         "Status of management blade is error"
	--#SUMMARY      "Management blade %d at blade chassis %s status is error."
	--#ARGUMENTS    { 3,  0 }
	--#SEVERITY     MAJOR
	--#TIMEINDEX    1
	--#HELP         "Not Implement"
	--#HELPTAG	0
	--#STATE        OPERATIONAL
	::= 1604

s31MgmtBladeCriticalError TRAP-TYPE
	ENTERPRISE s31MgmtAgent
	VARIABLES {
		s31TrapServerName,
		s31TrapTime,
		s31TrapObjectNumber,
		s31MgmtBladeId
	}
	DESCRIPTION
	    "Management blade status is critical"
	--#TYPE         "Status of management blade is critical"
	--#SUMMARY      "Management blade %d at blade chassis %s status is critical."
	--#ARGUMENTS    { 3,  0 }
	--#SEVERITY     CRITICAL
	--#TIMEINDEX    1
	--#HELP         "mgmt blade status changes to critical because mgmt nic status change to critical or slave mgmt blade fail to receive heart beat. Action: Check the cable connection for NIC of mgmt blade or Slave mgmt blade."
	--#HELPTAG	0
	--#STATE        OPERATIONAL
	::= 1605

s31ServerBladeAdded TRAP-TYPE
	ENTERPRISE s31MgmtAgent
	VARIABLES {
		s31TrapServerName,
		s31TrapTime,
		s31TrapObjectNumber,
		s31SvrBladeId
	}
	DESCRIPTION
	    "server blade was added"
	--#TYPE         "Server blade added"
	--#SUMMARY      "Server blade %d at blade chassis %s was added."
	--#ARGUMENTS    { 3,  0 }
	--#SEVERITY     INFORMATIONAL
	--#TIMEINDEX    1
	--#STATE        OPERATIONAL
	::= 1606

s31ServerBladeRemoved TRAP-TYPE
	ENTERPRISE s31MgmtAgent
	VARIABLES {
		s31TrapServerName,
		s31TrapTime,
		s31TrapObjectNumber,
		s31SvrBladeId
	}
	DESCRIPTION
	    "Server blade was removed"
	--#TYPE         "Server blade removed"
	--#SUMMARY      "Server blade %d at blade chassis %s was removed."
	--#ARGUMENTS    { 3,  0 }
	--#SEVERITY     INFORMATIONAL
	--#TIMEINDEX    1
	--#STATE        OPERATIONAL
	::= 1607

s31ServerBladeOk TRAP-TYPE
	ENTERPRISE s31MgmtAgent
	VARIABLES {
		s31TrapServerName,
		s31TrapTime,
		s31TrapObjectNumber,
		s31SvrBladeId
	}
	DESCRIPTION
	    "Server blade status is OK"
	--#TYPE         "Status of server blade is OK"
	--#SUMMARY      "Server blade %d at blade chassis %s status is OK."
	--#ARGUMENTS    { 3,  0 }
	--#SEVERITY     INFORMATIONAL
	--#TIMEINDEX    1
	--#STATE        OPERATIONAL
	::= 1608

s31ServerBladeError  TRAP-TYPE
	ENTERPRISE s31MgmtAgent
	VARIABLES {
		s31TrapServerName,
		s31TrapTime,
		s31TrapObjectNumber,
		s31SvrBladeId
	}
	DESCRIPTION
	    "Server blade status is error"
	--#TYPE         "Status of server blade is error"
	--#SUMMARY      "Server blade %d at blade chassis %s status is error."
	--#ARGUMENTS    { 3,  0 }
	--#SEVERITY     MAJOR
	--#TIMEINDEX    1
	--#HELP         "Server Blade status change to error because one of the following factor:1. Voltage of CPU Blade is error. 2.MEMORY-ERROR (SINGLE BIT)  3.BIOS-POST-ERROR  4.WATCHDOG-TIMER Error 5.BMC (I2C bus 0) Error. Action: Check eventlog of server blade."
	--#HELPTAG	0
	--#STATE        OPERATIONAL
	::= 1609

s31ServerBladeCriticalError TRAP-TYPE
	ENTERPRISE s31MgmtAgent
	VARIABLES {
		s31TrapServerName,
		s31TrapTime,
		s31TrapObjectNumber,
		s31SvrBladeId
	}
	DESCRIPTION
	    "Server blade status is critical"
	--#TYPE         "Status of server blade is critical"
	--#SUMMARY      "Server blade %d at blade chassis %s status is critical."
	--#ARGUMENTS    { 3,  0 }
	--#SEVERITY     CRITICAL
	--#TIMEINDEX    1
	--#HELP         "Server Blade status change to Critical because one of the following factor:1. Voltage of CPU Blade is critical. 2. Temperature of CPU Blade is  critical. 3. PCI of CPU blade is error. 4. Memory of CPU Blade (MULTI-BITS). Action: Check eventlog of server blade."
	--#HELPTAG	0
	--#STATE        OPERATIONAL
	::= 1610

s31SwitchBladeAdded  TRAP-TYPE
	ENTERPRISE s31MgmtAgent
	VARIABLES {
		s31TrapServerName,
		s31TrapTime,
		s31TrapObjectNumber,
		s31SwitchBladeId
	}
	DESCRIPTION
	    "Connection blade was added"
	--#TYPE         "Connection blade added"
	--#SUMMARY      "Connection blade %d at blade chassis %s was added."
	--#ARGUMENTS    { 3,  0 }
	--#SEVERITY     INFORMATIONAL
	--#TIMEINDEX    1
	--#STATE        OPERATIONAL
	::= 1611

s31SwitchBladeRemoved TRAP-TYPE
	ENTERPRISE s31MgmtAgent
	VARIABLES {
		s31TrapServerName,
		s31TrapTime,
		s31TrapObjectNumber,
		s31SwitchBladeId
	}
	DESCRIPTION
	    "Connection blade was removed"
	--#TYPE         "Connection blade removed"
	--#SUMMARY      "Connection blade %d at blade chassis %s was removed."
	--#ARGUMENTS    { 3,  0 }
	--#SEVERITY     INFORMATIONAL
	--#TIMEINDEX    1
	--#STATE        OPERATIONAL
	::= 1612

s31SwitchBladeOk TRAP-TYPE
	ENTERPRISE s31MgmtAgent
	VARIABLES {
		s31TrapServerName,
		s31TrapTime,
		s31TrapObjectNumber,
		s31SwitchBladeId
	}
	DESCRIPTION
	    "Connection blade status is OK"
	--#TYPE         "Status of connection blade is OK"
	--#SUMMARY      "Connection blade %d at blade chassis %s status is OK."
	--#ARGUMENTS    { 3,  0 }
	--#SEVERITY     INFORMATIONAL
	--#TIMEINDEX    1
	--#STATE        OPERATIONAL
	::= 1613

s31SwitchBladeError  TRAP-TYPE
	ENTERPRISE s31MgmtAgent
	VARIABLES {
		s31TrapServerName,
		s31TrapTime,
		s31TrapObjectNumber,
		s31SwitchBladeId
	}
	DESCRIPTION
	    "Connection blade status is error"
	--#TYPE         "Status of connection blade is error"
	--#SUMMARY      "Connection blade %d at blade chassis %s status is error."
	--#ARGUMENTS    { 3,  0 }
	--#SEVERITY     MAJOR
	--#TIMEINDEX    1
	--#HELP         "Not Implement"
	--#HELPTAG	0
	--#STATE        OPERATIONAL
	::= 1614

s31SwitchBladeCriticalError TRAP-TYPE
	ENTERPRISE s31MgmtAgent
	VARIABLES {
		s31TrapServerName,
		s31TrapTime,
		s31TrapObjectNumber,
		s31SwitchBladeId
	}
	DESCRIPTION
	    "Connection blade status is critical"
	--#TYPE         "Status of connection blade is critical"
	--#SUMMARY      "Connection blade %d at blade chassis %s status is critical."
	--#ARGUMENTS    { 3,  0 }
	--#SEVERITY     CRITICAL
	--#TIMEINDEX    1
	--#HELP         "Not implement"
	--#HELPTAG	0
	--#STATE        OPERATIONAL
	::= 1615

s31SysFanAdded  TRAP-TYPE
	ENTERPRISE s31MgmtAgent
	VARIABLES {
		s31TrapServerName,
		s31TrapTime,
		s31TrapObjectNumber,
		s31SysFanId
	}
	DESCRIPTION
	    "System fan was added"
	--#TYPE         "System fan added"
	--#SUMMARY      "System fan %d at blade chassis %s was added."
	--#ARGUMENTS    { 3,  0 }
	--#SEVERITY     INFORMATIONAL
	--#TIMEINDEX    1
	--#STATE        OPERATIONAL
	::= 1616

s31SysFanRemoved TRAP-TYPE
	ENTERPRISE s31MgmtAgent
	VARIABLES {
		s31TrapServerName,
		s31TrapTime,
		s31TrapObjectNumber,
		s31SysFanId
	}
	DESCRIPTION
	    "System fan was removed"
	--#TYPE         "System fan removed"
	--#SUMMARY      "System fan %d at blade chassis %s was removed."
	--#ARGUMENTS    { 3,  0 }
	--#SEVERITY     INFORMATIONAL
	--#TIMEINDEX    1
	--#STATE        OPERATIONAL
	::= 1617

s31SysFanOk TRAP-TYPE
	ENTERPRISE s31MgmtAgent
	VARIABLES {
		s31TrapServerName,
		s31TrapTime,
		s31TrapObjectNumber,
		s31SysFanId
	}
	DESCRIPTION
	    "System fan status is OK"
	--#TYPE         "Status of system fan is OK"
	--#SUMMARY      "System fan %d at blade chassis %s status is OK."
	--#ARGUMENTS    { 3,  0 }
	--#SEVERITY     INFORMATIONAL
	--#TIMEINDEX    1
	--#STATE        OPERATIONAL
	::= 1618

s31SysFanError  TRAP-TYPE
	ENTERPRISE s31MgmtAgent
	VARIABLES {
		s31TrapServerName,
		s31TrapTime,
		s31TrapObjectNumber,
		s31SysFanId
	}
	DESCRIPTION
	    "System fan status is error"
	--#TYPE         "Status of system fan is error"
	--#SUMMARY      "System fan %d at blade chassis %s status is error."
	--#ARGUMENTS    { 3,  0 }
	--#SEVERITY     MAJOR
	--#TIMEINDEX    1
	--#HELP         "The current maximal speed of fan can't reach 80% of original maximal speed.fan pre-fail is indicated. Action: The pre-fail fan should be replace."
	--#HELPTAG	0
	--#STATE        OPERATIONAL
	::= 1619

s31SysFanCriticalError TRAP-TYPE
	ENTERPRISE s31MgmtAgent
	VARIABLES {
		s31TrapServerName,
		s31TrapTime,
		s31TrapObjectNumber,
		s31SysFanId
	}
	DESCRIPTION
	    "System fan status is critical"
	--#TYPE         "Status of system fan is critical"
	--#SUMMARY      "System fan %d at blade chassis %s status is critical."
	--#ARGUMENTS    { 3,  0 }
	--#SEVERITY     CRITICAL
	--#TIMEINDEX    1
	--#HELP         "The normal speed of fan reach critical level. the critical level fans speed is under 50% of original normal fan speed. fan fail is indicated. Action: The fail fan should be replace immediately."
	--#HELPTAG	0
	--#STATE        OPERATIONAL
	::= 1620

s31SysTempOk TRAP-TYPE
	ENTERPRISE s31MgmtAgent
	VARIABLES {
		s31TrapServerName,
		s31TrapTime,
		s31TrapObjectNumber,
		s31SysTempSensorId
	}
	DESCRIPTION
	    "The temperature of the indicated system temperature sensor has
	     decreased to the normal level"
	--#TYPE         "Temperature normal"
	--#SUMMARY      "Temperature at system temperature sensor %d of blade chassis %s is within normal range."
	--#ARGUMENTS    { 3, 0 }
	--#SEVERITY     INFORMATIONAL
	--#TIMEINDEX    1
	--#STATE        OPERATIONAL
	::= 1621

s31SysTempError TRAP-TYPE
	ENTERPRISE s31MgmtAgent
	VARIABLES {
		s31TrapServerName,
		s31TrapTime,
		s31TrapObjectNumber,
		s31SysTempSensorId
	}
	DESCRIPTION
	    "The temperature of the indicated system temperature sensor is out of normal range"
	--#TYPE         "Temperature abnormal"
	--#SUMMARY      "Temperature at system temperature sensor %d of blade chassis %s is out of normal range."
	--#ARGUMENTS    { 3, 0 }
	--#SEVERITY     MAJOR
	--#TIMEINDEX    1
        --#HELP         "The temperature of the indicated system temperature is out of tolerance range and in warning level. The system will shut down and power off if shutdown is enabled. Action: Check fan openings Check fans Reduce ambient temperature and let the system cool down before restart. Do not operate system with cover removed. Proper airflow will not be guaranteed."
	--#HELPTAG	0
	--#STATE        OPERATIONAL
	::= 1622

s31SysTempCriticalError TRAP-TYPE
	ENTERPRISE s31MgmtAgent
	VARIABLES {
		s31TrapServerName,
		s31TrapTime,
		s31TrapObjectNumber,
		s31SysTempSensorId
	}
	DESCRIPTION
	    "The temperature of the indicated system temperature sensor is out of tolerance range.
	     The system will shut down and power off if shutdown is enabled"
	--#TYPE         "Temperature critical"
	--#SUMMARY      "Temperature at system temperature sensor %d of blade chassis %s has reached the critical level."
	--#ARGUMENTS    { 3, 0 }
	--#SEVERITY     CRITICAL
	--#TIMEINDEX    1
        --#HELP         "The temperature of the indicated system temperature sensor is out of tolerance range. The system will shut down and power off if shutdown is enabled. Action: Check fan openings Check fans Reduce ambient temperature.Let the system cool down before restart. Do not operate system with cover removed. Proper airflow will not be guaranteed."
	--#HELPTAG	0
	--#STATE        OPERATIONAL
	::= 1623

s31SysTempSensorOk TRAP-TYPE
	ENTERPRISE s31MgmtAgent
	VARIABLES {
		s31TrapServerName,
		s31TrapTime,
		s31TrapObjectNumber,
		s31SysTempSensorId
	}
	DESCRIPTION
	    "The indicated broken system temperature sensor is OK again"
	--#TYPE         "System temperature sensor OK"
	--#SUMMARY      "System temperature sensor %d of blade chassis %s is working again."
	--#ARGUMENTS    { 3, 0 }
	--#SEVERITY     INFORMATIONAL
	--#TIMEINDEX    1
	--#STATE        OPERATIONAL
	::= 1624

s31SysTempSensorBroken TRAP-TYPE
	ENTERPRISE s31MgmtAgent
	VARIABLES {
		s31TrapServerName,
		s31TrapTime,
		s31TrapObjectNumber,
		s31SysTempSensorId
	}
	DESCRIPTION
	    "The indicated system temperature sensor is broken"
	--#TYPE         "System temperature sensor broken"
	--#SUMMARY      "System temperature sensor %d of blade chassis %s is broken or not connected."
	--#ARGUMENTS    { 3, 0 }
	--#SEVERITY     MAJOR
	--#TIMEINDEX    1
	--#HELP		"The indicated system temperature sensor is broken, Action: Check connection or replace temperature sensor."
	--#HELPTAG	0
	--#STATE        OPERATIONAL
	::= 1625

s31SysPowerSupplyAdded TRAP-TYPE
	ENTERPRISE s31MgmtAgent
	VARIABLES {
		s31TrapServerName,
		s31TrapTime,
		s31TrapObjectNumber,
		s31SysPowerSupplyUnitId
	}
	DESCRIPTION
	    "Hot-replace power supply was added"
	--#TYPE         "Power supply added"
	--#SUMMARY      "Power supply unit %d at blade chassis %s was added."
	--#ARGUMENTS    { 3, 0 }
	--#SEVERITY     INFORMATIONAL
	--#TIMEINDEX    1
	--#STATE        OPERATIONAL
	::= 1626

s31SysPowerSupplyRemoved TRAP-TYPE
	ENTERPRISE s31MgmtAgent
	VARIABLES {
		s31TrapServerName,
		s31TrapTime,
		s31TrapObjectNumber,
		s31SysPowerSupplyUnitId
	}
	DESCRIPTION
	    "Hot-replace power supply was removed"
	--#TYPE         "Power supply removed"
	--#SUMMARY      "Power supply unit %d at blade chassis %s was removed."
	--#ARGUMENTS    { 3, 0 }
	--#SEVERITY     INFORMATIONAL
	--#TIMEINDEX    1
	--#STATE        OPERATIONAL
	::= 1627

s31SysPowerSupplyOk TRAP-TYPE
	ENTERPRISE s31MgmtAgent
	VARIABLES {
		s31TrapServerName,
		s31TrapTime,
		s31TrapObjectNumber,
		s31SysPowerSupplyUnitId
	}
	DESCRIPTION
	    "Power supply is working again"
	--#TYPE         "Power supply OK"
	--#SUMMARY      "Power supply unit %d at blade chassis %s is working again."
	--#ARGUMENTS    { 3, 0 }
	--#SEVERITY     INFORMATIONAL
	--#TIMEINDEX    1
	--#STATE        OPERATIONAL
	::= 1628

s31SysPowerSupplyError TRAP-TYPE
	ENTERPRISE s31MgmtAgent
	VARIABLES {
		s31TrapServerName,
		s31TrapTime,
		s31TrapObjectNumber,
		s31SysPowerSupplyUnitId
	}
	DESCRIPTION
	    "Hot-replace power supply failed"
	--#TYPE         "Power supply failed"
	--#SUMMARY      "Power supply unit %d at blade chassis %s failed."
	--#ARGUMENTS    { 3, 0 }
	--#SEVERITY     MAJOR
	--#TIMEINDEX    1
	--#HELP		"One hot-replace power supply failed,Action: Replace defect power supply. Attention: Power supply redundancy is lost. To restore redundancy replace defect power supply as soon as possible"
	--#HELPTAG	0
	--#STATE        OPERATIONAL
	::= 1629

s31SysPowerSupplyCriticalError TRAP-TYPE
	ENTERPRISE s31MgmtAgent
	VARIABLES {
		s31TrapServerName,
		s31TrapTime,
		s31TrapObjectNumber,
		s31SysPowerSupplyUnitId
	}
	DESCRIPTION
	    "Power supply status has become critical"
	--#TYPE         "Power supply critical"
	--#SUMMARY      "Insufficiant operating power supplies unit available in power supply unit %d at blade chassis %s."
	--#ARGUMENTS    { 3, 0 }
	--#SEVERITY     CRITICAL
	--#TIMEINDEX    1
	--#HELP         "power supply critical event will be sent when one of the following conditions occurs 1: fan1 rotational speed fault 2: fan2 rotational speed fault 3: fan3 rotational speed fault 4: temperature is over normal range 5: Over voltage protection in 12V output ,Action: Replace defective power supply. Install additional power supply."
	--#HELPTAG	0
	--#STATE        OPERATIONAL
	::= 1630

s31ServerPowerOn TRAP-TYPE
	ENTERPRISE s31MgmtAgent
	VARIABLES {
		s31TrapServerName,
		s31TrapTime,
		s31TrapObjectNumber,
		s31SvrBladeId
	}
	DESCRIPTION
	    "Server blade is powered on"
	--#TYPE         "Power on"
	--#SUMMARY      "Server blade %d at blade chassis %s is powered on."
	--#ARGUMENTS    { 3, 0 }
	--#SEVERITY     INFORMATIONAL
	--#TIMEINDEX    1
	--#STATE        OPERATIONAL
	::= 1631

s31ServerPostError TRAP-TYPE
	ENTERPRISE s31MgmtAgent
	VARIABLES {
		s31TrapServerName,
		s31TrapTime,
		s31TrapObjectNumber,
		s31SvrBladeId
	}
	DESCRIPTION
	    "System boot fails, because the power on selftest (POST) has reported an error"
	--#TYPE         "Post error"
	--#SUMMARY      "Server blade %d at blade chassis %s reports power on selftest error."
	--#ARGUMENTS    { 3, 0 }
	--#SEVERITY     INFORMATIONAL
	--#TIMEINDEX    1
	--#HELP         "System boot fails, because the power on selftest (POST) has reported an error.Action:Please refer to BIOS specifiction for detail POST error description"
	--#HELPTAG	0
	--#STATE        NONOPERATIONAL
	::= 1632

s31ServerBootError TRAP-TYPE
	ENTERPRISE s31MgmtAgent
	VARIABLES {
		s31TrapServerName,
		s31TrapTime,
		s31TrapObjectNumber,
		s31SvrBladeId
	}
	DESCRIPTION
	    "No bootable operating system can be found"
	--#TYPE         "Boot error"
	--#SUMMARY      "No bootable operation system found at server blade %d of blade chassis %s."
	--#ARGUMENTS    { 3, 0 }
	--#SEVERITY     INFORMATIONAL
	--#TIMEINDEX    1
	--#STATE        NONOPERATIONAL
	::= 1633

s31ServerShutdown TRAP-TYPE
	ENTERPRISE s31MgmtAgent
	VARIABLES {
		s31TrapServerName,
		s31TrapTime,
		s31TrapObjectNumber,
		s31SvrBladeId
	}
	DESCRIPTION
	    "Server blade will be shut down"
	--#TYPE         "Server shutdown"
	--#SUMMARY      "Server blade %d at blade chassis %s is shut down."
	--#ARGUMENTS    { 3, 0 }
	--#SEVERITY     INFORMATIONAL
	--#TIMEINDEX    1
	--#STATE        NONOPERATIONAL
	::= 1634

s31ServerSoftwareWatchdogExpired TRAP-TYPE
	ENTERPRISE s31MgmtAgent
	VARIABLES {
		s31TrapServerName,
		s31TrapTime,
		s31TrapObjectNumber,
		s31SvrBladeId
	}
	DESCRIPTION
	    "Software watchdog expires"
	--#TYPE         "Software watchdog expired"
	--#SUMMARY      "Software watchdog at server blade %d of blade chassis %s expired."
	--#ARGUMENTS    { 3, 0 }
	--#SEVERITY     INFORMATIONAL
	--#TIMEINDEX    1
	--#STATE        NONOPERATIONAL
	::= 1635

s31ServerBootWatchdogExpired TRAP-TYPE
	ENTERPRISE s31MgmtAgent
	VARIABLES {
		s31TrapServerName,
		s31TrapTime,
		s31TrapObjectNumber,
		s31SvrBladeId
	}
	DESCRIPTION
	    "Boot watchdog expires"
	--#TYPE         "Boot watchdog expired"
	--#SUMMARY      "Boot watchdog at server blade %d of blade chassis %s expired."
	--#ARGUMENTS    { 3, 0 }
	--#SEVERITY     INFORMATIONAL
	--#TIMEINDEX    1
	--#STATE        NONOPERATIONAL
	::= 1636

s31UserAuthenticationFailure TRAP-TYPE
	ENTERPRISE s31MgmtAgent
	VARIABLES {
		s31TrapServerName,
		s31TrapTime,
		s31TrapObjectNumber,
		s31TrapString
	}
	DESCRIPTION
	    "User authentication failure is detected via SNMP, HTTP or telnet"
	--#TYPE         "User authentication failure"
	--#SUMMARY      "User authentication failure detected at blade chassis %s, performing protocol %s."
	--#ARGUMENTS    { 0, 3 }
	--#SEVERITY     MAJOR
	--#TIMEINDEX    1
	--#HELP         "User has no authority, please contact with administration"
	--#HELPTAG	0
	--#STATE        OPERATIONAL
	::= 1637

s31TrapEventLog TRAP-TYPE
	ENTERPRISE s31MgmtAgent
	VARIABLES {
		s31TrapServerName,
		s31TrapTime,
		s31TrapObjectNumber
	}
	DESCRIPTION
	    "An error message was written into the system blade's event/error log.
		 This could have happened when an error occured before the agent was running
		 or any error without a specific trap."
	--#TYPE         "Error in event log"
	--#SUMMARY      "An error was recorded on blade chassis %s. See server management"
	--#SUMMARY      "event error log (Recovery) for detailed information."
	--#ARGUMENTS    { 0 }
	--#SEVERITY     MAJOR
	--#TIMEINDEX    1
	--#STATE        OPERATIONAL
	::= 1638

s31ServerBladeNewAdd TRAP-TYPE
	ENTERPRISE s31MgmtAgent
	VARIABLES {
		s31TrapServerName,
		s31TrapTime,
		s31TrapObjectNumber,
		s31SvrBladeId
	}
	DESCRIPTION
	    "Server blade was added to an empty slot"
	--#TYPE         "Server blade was added to an empty slot"
	--#SUMMARY      "Server blade %d at blade chassis %s is added to an empty slot."
	--#ARGUMENTS    { 3,  0 }
	--#SEVERITY     INFORMATIONAL
	--#TIMEINDEX    1
	--#STATE        OPERATIONAL
	::= 1639

s31ServerBladeHotReplace TRAP-TYPE
	ENTERPRISE s31MgmtAgent
	VARIABLES {
		s31TrapServerName,
		s31TrapTime,
		s31TrapObjectNumber,
		s31SvrBladeId
	}
	DESCRIPTION
	    "server blade was added to a slot marked for hot replacement"
	--#TYPE         "Server blade was added to a slot marked for hot replacement"
	--#SUMMARY      "Server blade %d at blade chassis %s is added to a slot marked for hot replacement."
	--#ARGUMENTS    { 3,  0 }
	--#SEVERITY     INFORMATIONAL
	--#TIMEINDEX    1
	--#STATE        OPERATIONAL
	::= 1640

s31ServerPowerOff TRAP-TYPE
	ENTERPRISE s31MgmtAgent
	VARIABLES {
		s31TrapServerName,
		s31TrapTime,
		s31TrapObjectNumber,
		s31SvrBladeId
	}
	DESCRIPTION
	    "Server blade is powered off"
	--#TYPE         "Power off"
	--#SUMMARY      "Server blade %d at blade chassis %s is powered off."
	--#ARGUMENTS    { 3, 0 }
	--#SEVERITY     INFORMATIONAL
	--#TIMEINDEX    1
	--#STATE        OPERATIONAL
	::= 1641

s31SysTempSensorAdded TRAP-TYPE
	ENTERPRISE s31MgmtAgent
	VARIABLES {
		s31TrapServerName,
		s31TrapTime,
		s31TrapObjectNumber,
		s31SysTempSensorId
	}
	DESCRIPTION
	    "The indicated system temperature sensor is added"
	--#TYPE         "System temperature sensor added"
	--#SUMMARY      "System temperature sensor %d of blade chassis %s is added."
	--#ARGUMENTS    { 3, 0 }
	--#SEVERITY     INFORMATIONAL
	--#TIMEINDEX    1
	--#STATE        OPERATIONAL
	::= 1642

s31SysTempSensorRemoved TRAP-TYPE
	ENTERPRISE s31MgmtAgent
	VARIABLES {
		s31TrapServerName,
		s31TrapTime,
		s31TrapObjectNumber,
		s31SysTempSensorId
	}
	DESCRIPTION
	    "The indicated system temperature sensor is removed"
	--#TYPE         "System temperature sensor removed"
	--#SUMMARY      "System temperature sensor %d of blade chassis %s is removed."
	--#ARGUMENTS    { 3, 0 }
	--#SEVERITY     INFORMATIONAL
	--#TIMEINDEX    1
	--#STATE        OPERATIONAL
	::= 1643

s31LivetimeError TRAP-TYPE
	ENTERPRISE s31MgmtAgent
	VARIABLES {
		s31TrapServerName,
		s31TrapTime,
		s31TrapObjectNumber,
		s31TrapString
	}
	DESCRIPTION
	    "Front/rear fan or PSU live time has exceeded the limited count."
	--#TYPE         "System live time has exceeded the limited count"
	--#SUMMARY      "Server %s live time has exceeded the limited count."
	--#ARGUMENTS    { 0 }
	--#SEVERITY     MINOR
	--#TIMEINDEX    1
	--#HELP         "Action: The unit that exceeded livetime is ready to be replaced by a new one."
	--#HELPTAG	0
	--#STATE        OPERATIONAL
	::= 1644

s31PowerOverBudget TRAP-TYPE
	ENTERPRISE s31MgmtAgent
	VARIABLES {
		s31TrapServerName,
		s31TrapTime,
		s31TrapObjectNumber,
		s31SvrBladeId
	}
	DESCRIPTION
	    "Server blade power on failed because of over power budget"
	--#TYPE         "Server blade power on failed"
	--#SUMMARY      "Server blade %d at blade chassis %s power on failed because of over power budget."
	--#ARGUMENTS    { 3, 0 }
	--#SEVERITY     MINOR
	--#TIMEINDEX    1
	--#HELP         "The output of system power supply is insufficient to add one more Server Blade to Power on. Action: Check whether Power units is not full loaded or fail. S71 is 3+1 (S32/31 is 1+1)power budget module."
	--#HELPTAG	0
	--#STATE        OPERATIONAL
	::= 1645

s31NicDetectionFail TRAP-TYPE
	ENTERPRISE s31MgmtAgent
	VARIABLES {
		s31TrapServerName,
		s31TrapTime,
		s31TrapObjectNumber,
		s31SvrBladeId
	}
	DESCRIPTION
	    "Management blade NIC detection failed"
	--#TYPE         "NIC detection failed"
	--#SUMMARY      "Management blade %d at blade chassis %s NIC detection failed."
	--#ARGUMENTS    { 3, 0 }
	--#SEVERITY     INFORMATIONAL
	--#TIMEINDEX    1
	--#HELP         "NIC HW fail or no line connected with. Action: Check the connection of line, or replace management Blade"
	--#HELPTAG	0
	--#STATE        OPERATIONAL
	::= 1646

s31SysPowerSupplyOvpFail TRAP-TYPE
	ENTERPRISE s31MgmtAgent
	VARIABLES {
		s31TrapServerName,
		s31TrapTime,
		s31TrapObjectNumber,
		s31SysPowerSupplyUnitId
	}
	DESCRIPTION
	    "Power supply unit OVP fail"
	--#TYPE         "Power supply OVP fail"
	--#SUMMARY      "Power supply unit %d OVP fail."
	--#ARGUMENTS    { 3 }
	--#SEVERITY     CRITICAL
	--#TIMEINDEX    1
	--#HELP         "Over Voltage(OV) Protection in 12V Output occurred,Over Current 12V is an active LOW output signal that goes low whenever the power supply status shuts down because of an over voltage condition on +12V as in Over Voltage Protection, Action: Check Power or replace another PowerSupply"
	--#HELPTAG	0
	--#STATE        OPERATIONAL
	::= 1647

s31SysPowerSupplyOcpFail TRAP-TYPE
	ENTERPRISE s31MgmtAgent
	VARIABLES {
		s31TrapServerName,
		s31TrapTime,
		s31TrapObjectNumber,
		s31SysPowerSupplyUnitId
	}
	DESCRIPTION
	    "Power supply unit OCP fail"
	--#TYPE         "Power supply OCP fail"
	--#SUMMARY      "Power supply unit %d OCP fail."
	--#ARGUMENTS    { 3 }
	--#SEVERITY     CRITICAL
	--#TIMEINDEX    1
	--#HELP         "Over Current Protection in 12V Output occurred,Over Current 12V is an active LOW output signal that goes low whenever the power supply status shuts down because of an over current condition on +12V as in Over Current Protection. Action: Check Power or replace another PowerSupply"
	--#HELPTAG	0
	--#STATE        OPERATIONAL
	::= 1648

s31FiberChannelAdded TRAP-TYPE
	ENTERPRISE s31MgmtAgent
	VARIABLES {
		s31TrapServerName,
		s31TrapTime,
		s31TrapObjectNumber,
		s31FcPassThroughBladeInfoBladeId
	}
	DESCRIPTION
	    "Fiber channel pass through card was added"
	--#TYPE         "Fiber channel pass through card added"
	--#SUMMARY      "Fiber channel pass through card %d at blade chassis %s was added."
	--#ARGUMENTS    { 3,  0 }
	--#SEVERITY     INFORMATIONAL
	--#TIMEINDEX    1
	--#STATE        OPERATIONAL
	::= 1649

s31FiberChannelRemoved TRAP-TYPE
	ENTERPRISE s31MgmtAgent
	VARIABLES {
		s31TrapServerName,
		s31TrapTime,
		s31TrapObjectNumber,
		s31FcPassThroughBladeInfoBladeId
	}
	DESCRIPTION
	    "Fiber channel pass through card was removed"
	--#TYPE         "Fiber channel pass through card removed"
	--#SUMMARY      "Fiber channel pass through card %d at blade chassis %s was removed."
	--#ARGUMENTS    { 3,  0 }
	--#SEVERITY     INFORMATIONAL
	--#TIMEINDEX    1
	--#STATE        OPERATIONAL
	::= 1650

s31SysPowerSupplyOverallStatusOk TRAP-TYPE
	ENTERPRISE s31MgmtAgent
	VARIABLES {
		s31TrapServerName,
		s31TrapTime,
		s31TrapObjectNumber,
		s31TrapString
	}
	DESCRIPTION
	    "System power supply overall status"
	--#TYPE         "System power supply overall status"
	--#SUMMARY      "System power supply overall status = OK"
	--#ARGUMENTS    {  }
	--#SEVERITY     INFORMATIONAL
	--#TIMEINDEX    1
	--#STATE        OPERATIONAL
	::= 1651

s31SysPowerSupplyOverallStatusDegraded TRAP-TYPE
	ENTERPRISE s31MgmtAgent
	VARIABLES {
		s31TrapServerName,
		s31TrapTime,
		s31TrapObjectNumber,
		s31TrapString
	}
	DESCRIPTION
	    "System power supply overall status"
	--#TYPE         "System power supply overall status"
	--#SUMMARY      "System power supply overall status = degraded"
	--#ARGUMENTS    {  }
	--#SEVERITY     MAJOR
	--#TIMEINDEX    1
	--#STATE        OPERATIONAL
	::= 1652

s31SysPowerSupplyOverallStatusCritical TRAP-TYPE
	ENTERPRISE s31MgmtAgent
	VARIABLES {
		s31TrapServerName,
		s31TrapTime,
		s31TrapObjectNumber,
		s31TrapString
	}
	DESCRIPTION
	    "System power supply overall status"
	--#TYPE         "System power supply overall status"
	--#SUMMARY      "System power supply overall status = critical"
	--#ARGUMENTS    {  }
	--#SEVERITY     CRITICAL
	--#TIMEINDEX    1
	--#STATE        OPERATIONAL
	::= 1653

s31SysFanOverallStatusOk TRAP-TYPE
	ENTERPRISE s31MgmtAgent
	VARIABLES {
		s31TrapServerName,
		s31TrapTime,
		s31TrapObjectNumber,
		s31TrapString
	}
	DESCRIPTION
	    "System fan overall status"
	--#TYPE         "System fan overall status"
	--#SUMMARY      "System fan overall status = OK"
	--#ARGUMENTS    {  }
	--#SEVERITY     INFORMATIONAL
	--#TIMEINDEX    1
	--#STATE        OPERATIONAL
	::= 1654

s31SysFanOverallStatusDegraded TRAP-TYPE
	ENTERPRISE s31MgmtAgent
	VARIABLES {
		s31TrapServerName,
		s31TrapTime,
		s31TrapObjectNumber,
		s31TrapString
	}
	DESCRIPTION
	    "System fan overall status"
	--#TYPE         "System fan overall status"
	--#SUMMARY      "System fan overall status = degraded"
	--#ARGUMENTS    {  }
	--#SEVERITY     MAJOR
	--#TIMEINDEX    1
	--#STATE        OPERATIONAL
	::= 1655

s31SysFanOverallStatusCritical TRAP-TYPE
	ENTERPRISE s31MgmtAgent
	VARIABLES {
		s31TrapServerName,
		s31TrapTime,
		s31TrapObjectNumber,
		s31TrapString
	}
	DESCRIPTION
	    "System fan overall status"
	--#TYPE         "System fan overall status"
	--#SUMMARY      "system fan overall status = critical"
	--#ARGUMENTS    {  }
	--#SEVERITY     CRITICAL
	--#TIMEINDEX    1
	--#STATE        OPERATIONAL
	::= 1656

s31SysTemperatureOverallStatusOk TRAP-TYPE
	ENTERPRISE s31MgmtAgent
	VARIABLES {
		s31TrapServerName,
		s31TrapTime,
		s31TrapObjectNumber,
		s31TrapString
	}
	DESCRIPTION
	    "System temperature overall status"
	--#TYPE         "System temperature overall status"
	--#SUMMARY      "System temperature overall status = OK"
	--#ARGUMENTS    {  }
	--#SEVERITY     INFORMATIONAL
	--#TIMEINDEX    1
	--#STATE        OPERATIONAL
	::= 1657

s31SysTemperatureOverallStatusDegraded TRAP-TYPE
	ENTERPRISE s31MgmtAgent
	VARIABLES {
		s31TrapServerName,
		s31TrapTime,
		s31TrapObjectNumber,
		s31TrapString
	}
	DESCRIPTION
	    "System temperature overall status"
	--#TYPE         "System temperature overall status"
	--#SUMMARY      "System temperature overall status = degraded"
	--#ARGUMENTS    {  }
	--#SEVERITY     MAJOR
	--#TIMEINDEX    1
	--#STATE        OPERATIONAL
	::= 1658

s31SysTemperatureOverallStatusCritical TRAP-TYPE
	ENTERPRISE s31MgmtAgent
	VARIABLES {
		s31TrapServerName,
		s31TrapTime,
		s31TrapObjectNumber,
		s31TrapString
	}
	DESCRIPTION
	    "System temperature overall status"
	--#TYPE         "System temperature overall status"
	--#SUMMARY      "System temperature overall status = critical"
	--#ARGUMENTS    {  }
	--#SEVERITY     CRITICAL
	--#TIMEINDEX    1
	--#STATE        OPERATIONAL
	::= 1659

s31LivetimeWarnning TRAP-TYPE
	ENTERPRISE s31MgmtAgent
	VARIABLES {
		s31TrapServerName,
		s31TrapTime,
		s31TrapObjectNumber,
		s31TrapString
	}
	DESCRIPTION
	    "Front/rear fan or PSU live time has pre-expired the limited count."
	--#TYPE         "System live time has pre-expired the limited count"
	--#SUMMARY      "Power/fan %s live time has pre-expired the limited count."
	--#ARGUMENTS    { 0 }
	--#SEVERITY     INFORMATIONAL
	--#TIMEINDEX    1
	--#HELP         "Action: The unit that has pre-expired livetime please Contact Support soon"
	--#HELPTAG	0
	--#STATE        OPERATIONAL
	::= 1660

s31ServerVirtualizationError TRAP-TYPE
	ENTERPRISE s31MgmtAgent
	VARIABLES {
		s31TrapServerName,
		s31TrapTime,
		s31TrapObjectNumber,
		s31SvrBladeId
	}
	DESCRIPTION
		"System initialization fails, because the power on self test (POST) has reported a virtualization error"
	--#TYPE         "Virtualization error"
	--#SUMMARY      "Server blade %d at blade chassis %s: I/O virtualization error."
	--#ARGUMENTS    { 3, 0 }
	--#SEVERITY     CRITICAL
	--#TIMEINDEX    1
	--#HELP         "System boot fails, because the power on self test (POST) has reported an error. Action:Please refer to BIOS specification for detail POST error description"
	--#HELPTAG  0
	--#STATE        NONOPERATIONAL
	::= 1661

s31ServerPortMismatchError TRAP-TYPE
	ENTERPRISE s31MgmtAgent
	VARIABLES {
		s31TrapServerName,
		s31TrapTime,
		s31SvrBladeId,
		s31TrapString
	}
	DESCRIPTION
		"Server blade mezzanine card has been plugged into a slot of incompatible type"
	--#TYPE         "Server blade mismatch"
	--#SUMMARY      "Server blade %d at blade chassis %s: %s mismatch - port disabled"
	--#ARGUMENTS    { 2, 0, 3 }
	--#SEVERITY     MAJOR
	--#TIMEINDEX    1
	--#HELP         "Server blade configuration does not match connection blade configuration. Action:Please refer to hardware manual for compatible configurations"
	--#HELPTAG  0
	--#STATE        OPERATIONAL
	::= 1662

s31ServerPortMismatchOK TRAP-TYPE
	ENTERPRISE s31MgmtAgent
	VARIABLES {
		s31TrapServerName,
		s31TrapTime,
		s31SvrBladeId
	}
	DESCRIPTION
		"Mismatch between server blade mezzanine card and slot type has been resolved"
	--#TYPE         "Server blade mismatch"
	--#SUMMARY      "Server blade %d at blade chassis %s: mismatch OK"
	--#ARGUMENTS    { 2, 0 }
	--#SEVERITY     INFORMATIONAL
	--#TIMEINDEX    1
	--#STATE        OPERATIONAL
	::= 1663

s31ConnectionMismatchError TRAP-TYPE
	ENTERPRISE s31MgmtAgent
	VARIABLES {
		s31TrapServerName,
		s31TrapTime,
		s31SwitchBladeId,
		s31TrapString
	}
	DESCRIPTION
		"Connection blade has been plugged into a slot of incompatible type"
	--#TYPE         "Connection blade mismatch"
	--#SUMMARY      "Connection blade %d at blade chassis %s: %s mismatch - port disabled"
	--#ARGUMENTS    { 2, 0, 3 }
	--#SEVERITY     MAJOR
	--#TIMEINDEX    1
	--#HELP         "Connection blade configuration does not match server blade configuration. Action:Please refer to hardware manual for compatible configurations"
	--#HELPTAG  0
	--#STATE        OPERATIONAL
	::= 1664

s31ConnectionMismatchOK TRAP-TYPE
	ENTERPRISE s31MgmtAgent
	VARIABLES {
		s31TrapServerName,
		s31TrapTime,
		s31SwitchBladeId
	}
	DESCRIPTION
		"Mismatch between connection blade and slot type has been resolved"
	--#TYPE         "Connection blade mismatch"
	--#SUMMARY      "Connection blade %d at blade chassis %s: mismatch OK"
	--#ARGUMENTS    { 2, 0 }
	--#SEVERITY     INFORMATIONAL
	--#TIMEINDEX    1
	--#STATE        OPERATIONAL
	::= 1665

s31StorageMismatchError TRAP-TYPE
	ENTERPRISE s31MgmtAgent
	VARIABLES {
		s31TrapServerName,
		s31TrapTime,
		s31StorageBladeId,
		s31TrapString
	}
	DESCRIPTION
		"Storage blade has been plugged into a slot of incompatible type"
	--#TYPE         "Storage blade mismatch"
	--#SUMMARY      "Storage blade %d at blade chassis %s: %s mismatch - port disabled"
	--#ARGUMENTS    { 2, 0, 3 }
	--#SEVERITY     MAJOR
	--#TIMEINDEX    1
	--#HELP         "Storage blade configuration does not match slot type. Action:Please refer to hardware manual for compatible configurations"
	--#HELPTAG  0
	--#STATE        OPERATIONAL
	::= 1666

s31StorageMismatchOK TRAP-TYPE
	ENTERPRISE s31MgmtAgent
	VARIABLES {
		s31TrapServerName,
		s31TrapTime,
		s31StorageBladeId
	}
	DESCRIPTION
		"Mismatch between storage blade and slot type has been resolved"
	--#TYPE         "Storage blade mismatch"
	--#SUMMARY      "Storage blade %d at blade chassis %s: mismatch OK"
	--#ARGUMENTS    { 2, 0 }
	--#SEVERITY     INFORMATIONAL
	--#TIMEINDEX    1
	--#STATE        OPERATIONAL
	::= 1667

			
s31TrapPowerOffTimeReached TRAP-TYPE
	ENTERPRISE s31MgmtAgent
	VARIABLES {
		s31TrapServerName,
		s31TrapTime,
		s31SvrBladeId,
		s31TrapInteger
	}
	DESCRIPTION     "This trap is sent when a CPU blade is going to be switched off by schedule in some minutes."
	--#TYPE         "Scheduled power off time reached"
	--#SUMMARY      "The scheduled power-off time is reached in blade %d on blade chassis %s! System shutdown in %d minutes."
	--#ARGUMENTS    { 2, 0, 3 }
	--#SEVERITY     INFORMATIONAL
	--#TIMEINDEX    1
	--#HELP         ""
	--#STATE        OPERATIONAL
	::= 1668

s31TrapPowerOnTimeReached TRAP-TYPE
	ENTERPRISE s31MgmtAgent
	VARIABLES {
		s31TrapServerName,
		s31TrapTime,
		s31SvrBladeId,
		s31TrapInteger
	}
	DESCRIPTION     "This trap is sent when a CPU blade is going to be switched on by schedule in some minutes."
	--#TYPE         "Scheduled power on time reached"
	--#SUMMARY      "The scheduled power-on time is reached in blade %d on blade chassis %s! System will be powered on in %d minutes."
	--#ARGUMENTS    { 2, 0, 3 }
	--#SEVERITY     INFORMATIONAL
	--#TIMEINDEX    1
	--#HELP         ""
	--#STATE        OPERATIONAL
	::= 1669
			
s31PowerLimitOK TRAP-TYPE
	ENTERPRISE s31MgmtAgent
	VARIABLES {
		s31TrapServerName,
		s31TrapTime
	}
	DESCRIPTION     "This trap is sent when power consumption limiting returns to normal state."
	--#TYPE         "Chassis power consumption limiting"
	--#SUMMARY      "Power consumption limiting of blade chassis %s returned to normal state."
	--#ARGUMENTS    { 0 }
	--#SEVERITY     INFORMATIONAL
	--#TIMEINDEX    1
	--#HELP         ""
	--#STATE        OPERATIONAL
	::= 1670
			
s31PowerLimitOverWarning TRAP-TYPE
	ENTERPRISE s31MgmtAgent
	VARIABLES {
		s31TrapServerName,
		s31TrapTime,
		s31TrapString
	}
	DESCRIPTION     "This trap is sent when power consumption limiting exceeds the warning level."
	--#TYPE         "Chassis power consumption limiting"
	--#SUMMARY      "Power consumption limiting of blade chassis %s exceeds warning level: %s"
	--#ARGUMENTS    { 0, 2 }
	--#SEVERITY     MINOR
	--#TIMEINDEX    1
	--#HELP         "Verify Power Consumption Limiting Configuration"
	--#STATE        OPERATIONAL
	::= 1671
			
s31PowerLimitOverThreshold TRAP-TYPE
	ENTERPRISE s31MgmtAgent
	VARIABLES {
		s31TrapServerName,
		s31TrapTime,
		s31TrapString
	}
	DESCRIPTION     "This trap is sent when power consumption limiting exceeds the limit threshold."
	--#TYPE         "Chassis power consumption limiting"
	--#SUMMARY      "Power consumption limiting of blade chassis %s exceeds the limit threshold: %s"
	--#ARGUMENTS    { 0, 2 }
	--#SEVERITY     MAJOR
	--#TIMEINDEX    1
	--#HELP         "Verify Power Consumption Limiting Configuration"
	--#STATE        OPERATIONAL
	::= 1672
			
s31ShutdownOverLimit TRAP-TYPE
	ENTERPRISE s31MgmtAgent
	VARIABLES {
		s31TrapServerName,
		s31TrapTime,
		s31SvrBladeId,
		s31TrapString
	}
	DESCRIPTION     "This trap is sent when power consumption limiting causes a blade shutdown."
	--#TYPE         "Chassis power consumption limiting"
	--#SUMMARY      "Power consumption limiting of blade chassis %s causes blade %d to shut down: %s"
	--#ARGUMENTS    { 0, 2, 3 }
	--#SEVERITY     MAJOR
	--#TIMEINDEX    1
	--#HELP         "Verify Power Consumption Limiting Configuration"
	--#STATE        OPERATIONAL
	::= 1673
			
END
