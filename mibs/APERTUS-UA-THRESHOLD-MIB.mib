APERTUS-UA-THRESHOLD-MIB DEFINITIONS ::= BEGIN

	IMPORTS
		mib-2
			FROM RFC1213-MIB
		MODULE-IDENTITY, OBJECT-TYPE, OBJECT-IDENTITY,
		TimeTicks, IpAddress, Counter32, Gauge32
			FROM SNMPv2-SMI
		TEXTUAL-CONVENTION, RowStatus, DisplayString, TruthValue
			FROM SNMPv2-TC
		MODULE-COMPLIANCE, OBJECT-GROUP
			FROM SNMPv2-CONF;

internet      OBJECT IDENTIFIER ::= { iso org(3) dod(6) 1 }

directory     OBJECT IDENTIFIER ::= { internet 1 }

mgmt          OBJECT IDENTIFIER ::= { internet 2 }

experimental  OBJECT IDENTIFIER ::= { internet 3 }

private       OBJECT IDENTIFIER ::= { internet 4 }
enterprises   OBJECT IDENTIFIER ::= { private 1 }


	apertus OBJECT IDENTIFIER ::= { enterprises 543 }

	isg OBJECT IDENTIFIER ::= { apertus 3 }

	aperua OBJECT IDENTIFIER ::= { isg 3 }

	aperthresh OBJECT IDENTIFIER ::= { aperua 2 }

	aperThreshMIB OBJECT IDENTIFIER ::= { aperthresh 1 }


	aperThreshMIBObjects       OBJECT IDENTIFIER ::= { aperThreshMIB 1 }

	-- (Old-style) groups in the apertus Threshold extension

	aperThreshConfig  OBJECT IDENTIFIER ::= { aperThreshMIBObjects 1 }
	aperThreshDomain  OBJECT IDENTIFIER ::= { aperThreshMIBObjects 2 }
	aperThreshNode  OBJECT IDENTIFIER ::= { aperThreshMIBObjects 3 }

	-- Threshold config information group
	aperThreshConfigStatus OBJECT-TYPE
		SYNTAX      INTEGER {	ready(1),
								loading(2),
								down(3) }
		ACCESS  read-only
		STATUS      mandatory
		DESCRIPTION
               "Status of Universal Access server"
		::= { aperThreshConfig 1 }

	aperThreshConfigUpTime OBJECT-TYPE
		SYNTAX      TimeTicks
		ACCESS  read-only
		STATUS      mandatory
		DESCRIPTION
               "This value represents the time elapsed since the server
                was started in 1/100nths of a second."
		::= { aperThreshConfig 2 }


	-- Threshold zone information group

	aperThreshDomainTable OBJECT-TYPE
		SYNTAX      SEQUENCE OF AperThreshDomainEntry
		ACCESS  not-accessible
		STATUS      mandatory
		DESCRIPTION
	               "Domain information broken down domain name."
		::= { aperThreshDomain 1 }

	aperThreshDomainEntry OBJECT-TYPE
		SYNTAX      AperThreshDomainEntry
		ACCESS  not-accessible
		STATUS      mandatory
		DESCRIPTION
               "This table contains information on each of the load balance
				domains under its control."
		INDEX     { aperThreshDomainName }
		::= { aperThreshDomainTable 1 }

	AperThreshDomainEntry ::=
		SEQUENCE {
			aperThreshDomainName
				DisplayString,
			aperThreshDomainLbparms
				DisplayString,
			aperThreshDomainFreeSessions
				INTEGER,
			aperThreshDomainMaxSessions
				INTEGER,
			aperThreshDomainUpServers
				INTEGER,
			aperThreshDomainDownServers
				INTEGER,
			aperThreshDomainCmpMethod
				INTEGER
		    }

	aperThreshDomainName OBJECT-TYPE
		SYNTAX		DisplayString
		ACCESS  read-only	
		STATUS		mandatory
		DESCRIPTION
			"The zone name for this load-balance domain."
		::= { aperThreshDomainEntry 1 }

	aperThreshDomainLbparms OBJECT-TYPE
		SYNTAX		DisplayString
		ACCESS	read-only
		STATUS		mandatory
		DESCRIPTION
			"The load-balance parameters for this load-balance domain."
		::= { aperThreshDomainEntry 2 }

	aperThreshDomainFreeSessions OBJECT-TYPE
		SYNTAX		INTEGER ( -2147483648..2147483647 )
		ACCESS	read-only
		STATUS		mandatory
		DESCRIPTION
			"The number of total sessions report free for this zone."
		::= { aperThreshDomainEntry 3 }

	aperThreshDomainMaxSessions OBJECT-TYPE
		SYNTAX		INTEGER ( -2147483648..2147483647 )
		ACCESS	read-only
		STATUS		mandatory
		DESCRIPTION
			"The number of sessions, not including downed servers,
			 possible for this zone."
		::= { aperThreshDomainEntry 4 }

	aperThreshDomainUpServers OBJECT-TYPE
		SYNTAX		INTEGER ( -2147483648..2147483647 )
		ACCESS	read-only
		STATUS		mandatory
		DESCRIPTION
			"The number of servers that are up at this time."
		::= { aperThreshDomainEntry 5 }

	aperThreshDomainDownServers OBJECT-TYPE
		SYNTAX		INTEGER ( -2147483648..2147483647 )
		ACCESS	read-only
		STATUS		mandatory
		DESCRIPTION
			"The number of servers in list that are marked as down at this
			 time."
		::= { aperThreshDomainEntry 6 }

	aperThreshDomainCmpMethod OBJECT-TYPE
		SYNTAX		INTEGER	{ percent(1), absolute(2) }
		ACCESS	read-only
		STATUS		mandatory
		DESCRIPTION
			"The method used when comparing values within the zone.  The
			 percent(1) method indicates that balancing is done as a 
			 percentage of available resources.  Absolute(2) indicates that
			 the session values themselves are used during compares."
		::= { aperThreshDomainEntry 7 }

	-- Threshold zone information group

	aperThreshNodeTable OBJECT-TYPE
		SYNTAX      SEQUENCE OF AperThreshNodeEntry
		ACCESS  not-accessible
		STATUS      mandatory
		DESCRIPTION
               "Node information broken down domain name and IP address"
		::= { aperThreshNode 1 }

	aperThreshNodeEntry OBJECT-TYPE
		SYNTAX      AperThreshNodeEntry
		ACCESS  not-accessible
		STATUS      mandatory
		DESCRIPTION
               "This table contains information on each of the machines
				in the different laod balance zones."
		INDEX     { aperThreshNodeName,
					aperThreshNodeIP }
		::= { aperThreshNodeTable 1 }

	AperThreshNodeEntry ::=
		SEQUENCE {
			aperThreshNodeName
				DisplayString,
			aperThreshNodeIP
				IpAddress,
			aperThreshNodeThresholdPercent
				INTEGER,
			aperThreshNodeStatus
				INTEGER,
			aperThreshNodeSessionsAvailable
				INTEGER,
			aperThreshNodeSessionsPossible
				INTEGER,
			aperThreshNodeHandFasted
				INTEGER
		    }

	aperThreshNodeName OBJECT-TYPE
		SYNTAX		DisplayString
		ACCESS  read-only	
		STATUS		mandatory
		DESCRIPTION
			"The zone name for this Node."
		::= { aperThreshNodeEntry 1 }

	aperThreshNodeIP OBJECT-TYPE
		SYNTAX		IpAddress
		ACCESS  read-only	
		STATUS		mandatory
		DESCRIPTION
			"The IP address of the NODE."
		::= { aperThreshNodeEntry 2 }

	aperThreshNodeThresholdPercent OBJECT-TYPE
		SYNTAX		INTEGER (0..100)
		ACCESS	read-only
		STATUS		mandatory
		DESCRIPTION
			"This value is the threshold percentage at which this node becomes
			 available for consideration.  All nodes with less threshold
			 percentage than this must be either down or at this percentage
			 of usage before the NODE processess for this IP will be
			 queried for status.  At least one 0% node must exist for the
			 domain to function."
		::= { aperThreshNodeEntry 3 }


	aperThreshNodeStatus OBJECT-TYPE
		SYNTAX		INTEGER {	up(1),
								down(2),
								notqueried(3) }
		ACCESS	read-only
		STATUS		mandatory
		DESCRIPTION
			"Indicates the status of the node.  Up(1) shows that the node is
			 up and is being considered for use.  Down(2) indicates that
			 the last query to the NODE image resulted in a down marker for
			 the node.  Admindown(3) indicates that an administrator took
			 the node offline manually (from the UA server end).
			 Notqueried(4) is used to indicate that a node has never been
			 queried.  This is normally the case when threshold percentages
			 are being used."
		::= { aperThreshNodeEntry 4 }

	aperThreshNodeSessionsAvailable OBJECT-TYPE
		SYNTAX		INTEGER ( -2147483648..2147483647 )
		ACCESS	read-only
		STATUS		mandatory
		DESCRIPTION
			"Number of session available at last query.  If Status is not
			 up(1), this value may be inaccurate."
		::= { aperThreshNodeEntry 5 }

	aperThreshNodeSessionsPossible OBJECT-TYPE
		SYNTAX		INTEGER ( -2147483648..2147483647 )
		ACCESS	read-only
		STATUS		mandatory
		DESCRIPTION
			"Number of sessions possible for this node.  If Status is not
			up(1), this value may be inaccurate."
		::= { aperThreshNodeEntry 6 }

	aperThreshNodeHandFasted OBJECT-TYPE
		SYNTAX		INTEGER ( -2147483648..2147483647 )
		ACCESS	read-only
		STATUS		mandatory
		DESCRIPTION
			"Number of sessions assigned to this node for which a NODE query
			 has not resolved."
		::= { aperThreshNodeEntry 7 }
END
