--
-- OPCD-USSDGW-MIB-V2
-- Last Modified: Monday, August 08, 2005
--


OPCD-USSDGW-MIB-V2 DEFINITIONS ::= BEGIN


--  OPCD-USSDGW-MIB:
--    A private enterprise mib for Opencode USSD Gateway application.


IMPORTS
	MODULE-IDENTITY, OBJECT-TYPE, NOTIFICATION-TYPE, enterprises	FROM SNMPv2-SMI
	DisplayString							FROM SNMPv2-TC
	opencode-systems 					      	FROM OPCD-SUPPORT-MIB-V2;





--  opencode ussdgw  branch: 30374.2
--  opencode ussdgw traps branch: 30374.2.1


  ocussdgw		OBJECT IDENTIFIER ::= { opencode-systems 2 }
  ocussdgw-traps	OBJECT IDENTIFIER ::= { ocussdgw 1 }

  definitions 		OBJECT IDENTIFIER ::= { ocussdgw-traps 0 }
  vars		 	OBJECT IDENTIFIER ::= { ocussdgw-traps 1 }
--
--


mcr-Host OBJECT-TYPE
	SYNTAX DisplayString (SIZE (0..255))
	MAX-ACCESS accessible-for-notify
	STATUS current
	DESCRIPTION
		"String containing hostname of fault node."
	::= { vars 1 }


mcr-Severity OBJECT-TYPE
	SYNTAX INTEGER{
		critical(1),
		major(2),
		minor(3),
		normal(4),
		warning(5)
	}
	MAX-ACCESS accessible-for-notify
	STATUS mandatory
	DESCRIPTION
		"Alarm severity."
	::= { vars 2 }


mcr-Text OBJECT-TYPE
	SYNTAX DisplayString (SIZE (0..255))
	MAX-ACCESS accessible-for-notify
	STATUS current
	DESCRIPTION
		"String containing text of the alarm."
	::= { vars 3 }


--
-- Traps
--
-----------------------------------------------------------------------------------------------


------------------------------------------------------------------------------------------



-- 1.3.6......0.2
ocussdgw-Crash NOTIFICATION-TYPE
	OBJECTS	{ mcr-Host, mcr-Severity, mcr-Text}	
	STATUS	current
	DESCRIPTION  "USSD Gateway Service crashed and was restarted by WDOG!!"
	--#SUMMARY   "Alarm on host: $1 (ussdgw application) :  $3"
	--#CATEGORY  "Error Alarms"
        --#ARGUMENTS {}
        --#SEVERITY  CRITICAL
	::= { definitions 2 }

-- 1.3.6......0.3
ocussdgw-Crash-Canceled NOTIFICATION-TYPE
	OBJECTS	{ mcr-Host, mcr-Severity, mcr-Text}	
	STATUS	current
	DESCRIPTION  "USSD Gateway Service crashed-Canceled"
	--#SUMMARY   "Alarm on host: $1 (ussdgw application) :  $3"
	--#CATEGORY  "Error Alarms"
        --#ARGUMENTS {}
        --#SEVERITY  NORMAL
	::= { definitions 3 }


-- 1.3.6......0.4
ocussdgw-Stp1-Inaccessible NOTIFICATION-TYPE
	OBJECTS	{ mcr-Host, mcr-Severity, mcr-Text}	
	STATUS	current
	DESCRIPTION  "STP 1 is not accessible from ussdgw servers."
	--#SUMMARY   "Alarm on host: $1 (ussdgw application) :  $3"
	--#CATEGORY  "Error Alarms"
        --#ARGUMENTS {}
        --#SEVERITY  MAJOR
	::= { definitions 4 }

-- 1.3.6......0.5
ocussdgw-Stp1-Inaccessible-Canceled NOTIFICATION-TYPE
	OBJECTS	{ mcr-Host, mcr-Severity, mcr-Text}	
	STATUS	current
	DESCRIPTION  "STP 1 is not accessible from ussdgw servers-Canceled"
	--#SUMMARY   "Alarm on host: $1 (ussdgw application) :  $3"
	--#CATEGORY  "Error Alarms"
        --#ARGUMENTS {}
        --#SEVERITY  NORMAL
	::= { definitions 5 }


-- 1.3.6......0.6
ocussdgw-Stp2-Inaccessible NOTIFICATION-TYPE
	OBJECTS	{ mcr-Host, mcr-Severity, mcr-Text}	
	STATUS	current
	DESCRIPTION  "STP 2 is not accessible from ussdgw servers."
	--#SUMMARY   "Alarm on host: $1 (ussdgw application) :  $3"
	--#CATEGORY  "Error Alarms"
        --#ARGUMENTS {}
        --#SEVERITY  MAJOR
	::= { definitions 6 }

-- 1.3.6......0.7
ocussdgw-Stp2-Inaccessible-Canceled NOTIFICATION-TYPE
	OBJECTS	{ mcr-Host, mcr-Severity, mcr-Text}	
	STATUS	current
	DESCRIPTION  "STP 2 is not accessible from ussdgw servers-Canceled"
	--#SUMMARY   "Alarm on host: $1 (ussdgw application) :  $3"
	--#CATEGORY  "Error Alarms"
        --#ARGUMENTS {}
        --#SEVERITY  NORMAL
	::= { definitions 7 }

-- 1.3.6......0.8
ocussdgw-Stp1-Congestion NOTIFICATION-TYPE
	OBJECTS	{ mcr-Host, mcr-Severity, mcr-Text}	
	STATUS	current
	DESCRIPTION  "Congestion to STP1."
	--#SUMMARY   "Alarm on host: $1 (ussdgw application) :  $3"
	--#CATEGORY  "Error Alarms"
        --#ARGUMENTS {}
        --#SEVERITY  MAJOR
	::= { definitions 8 }

-- 1.3.6......0.9
ocussdgw-Stp1-Congestion-Canceled NOTIFICATION-TYPE
	OBJECTS	{ mcr-Host, mcr-Severity, mcr-Text}	
	STATUS	current
	DESCRIPTION  "Congestion to STP1-Canceled"
	--#SUMMARY   "Alarm on host: $1 (ussdgw application) :  $3"
	--#CATEGORY  "Error Alarms"
        --#ARGUMENTS {}
        --#SEVERITY  NORMAL
	::= { definitions 9 }


-- 1.3.6......0.10
ocussdgw-Stp2-Congestion NOTIFICATION-TYPE
	OBJECTS	{ mcr-Host, mcr-Severity, mcr-Text}	
	STATUS	current
	DESCRIPTION	"Congestion to STP2."
	--#SUMMARY   "Alarm on host: $1 (ussdgw application) :  $3"
	--#CATEGORY  "Error Alarms"
        --#ARGUMENTS {}
        --#SEVERITY  MAJOR
	::= { definitions 10 }

-- 1.3.6......0.11
ocussdgw-Stp2-Congestion-Canceled NOTIFICATION-TYPE
	OBJECTS	{ mcr-Host, mcr-Severity, mcr-Text}	
	STATUS	current
	DESCRIPTION	"Congestion to STP2-Canceled"
	--#SUMMARY   "Alarm on host: $1 (ussdgw application) :  $3"
	--#CATEGORY  "Error Alarms"
        --#ARGUMENTS {}
        --#SEVERITY  NORMAL
	::= { definitions 11 }


-- 1.3.6......0.12
ocussdgw-CongestionUssd NOTIFICATION-TYPE
	OBJECTS	{ mcr-Host, mcr-Severity, mcr-Text}	
	STATUS	current
	DESCRIPTION  "Congestion on USSDGW servers."
	--#SUMMARY   "Alarm on host: $1 (ussdgw application) :  $3"
	--#CATEGORY  "Error Alarms"
        --#ARGUMENTS {}
        --#SEVERITY  CRITICAL
	::= { definitions 12 }

-- 1.3.6......0.13
ocussdgw-CongestionUssd-Canceled NOTIFICATION-TYPE
	OBJECTS	{ mcr-Host, mcr-Severity, mcr-Text}	
	STATUS	current
	DESCRIPTION  "Congestion on USSDGW servers-Canceled"
	--#SUMMARY   "Alarm on host: $1 (ussdgw application) :  $3"
	--#CATEGORY  "Error Alarms"
        --#ARGUMENTS {}
        --#SEVERITY  NORMAL
	::= { definitions 13 }


-- 1.3.6......0.14
ocussdgw-SmppConnDown NOTIFICATION-TYPE
	OBJECTS	{ mcr-Host, mcr-Severity, mcr-Text}	
	STATUS	current
	DESCRIPTION  "Smpp connection down on USSDGW servers."
	--#SUMMARY   "Alarm on host: $1 (ussdgw application) :  $3"
	--#CATEGORY  "Error Alarms"
        --#ARGUMENTS {}
        --#SEVERITY  CRITICAL
	::= { definitions 14 }

-- 1.3.6......0.15
ocussdgw-SmppConnDown-Canceled NOTIFICATION-TYPE
	OBJECTS	{ mcr-Host, mcr-Severity, mcr-Text}	
	STATUS	current
	DESCRIPTION  "Smpp connection down on USSDGW servers-Canceled"
	--#SUMMARY   "Alarm on host: $1 (ussdgw application) :  $3"
	--#CATEGORY  "Error Alarms"
        --#ARGUMENTS {}
        --#SEVERITY  NORMAL
	::= { definitions 15 }


-- 1.3.6......0.16
ocussdgw-NoSS7trafic NOTIFICATION-TYPE
	OBJECTS	{ mcr-Host, mcr-Severity, mcr-Text}	
	STATUS	current
	DESCRIPTION  "No ss7 traffic.Possible ss7 board problem."
	--#SUMMARY   "Alarm on host: $1 (ussdgw application) :  $3"
	--#CATEGORY  "Error Alarms"
        --#ARGUMENTS {}
        --#SEVERITY  MAJOR
	::= { definitions 16 }


-- 1.3.6......0.17
ocussdgw-NoSS7trafic-Canceled NOTIFICATION-TYPE
	OBJECTS	{ mcr-Host, mcr-Severity, mcr-Text}	
	STATUS	current
	DESCRIPTION  "No ss7 traffic.Possible ss7 board problem-Canceled"
	--#SUMMARY   "Alarm on host: $1 (ussdgw application) :  $3"
	--#CATEGORY  "Error Alarms"
        --#ARGUMENTS {}
        --#SEVERITY  NORMAL
	::= { definitions 17 }

----------------------------------------------------------------------------------------------


END


--
-- OPCD-USSDGW-MIB-V2
--
