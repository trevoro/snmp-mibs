Nortel-Magellan-Passport-UsefulDefinitionsMIB
DEFINITIONS ::= BEGIN

IMPORTS

      enterprises
   FROM RFC1155-SMI;

--   LAST-UPDATED    "9607010000Z"
--   ORGANIZATION    "Nortel"
--   CONTACT-INFO    "
--         Nortel Magellan Network Management
--
--         Postal: P.O. Box 5080, Station F
--                 Ottawa, Ontario
--                 Canada  K2C 3T1
--
--         Email:  nm_plm@nt.com"
--   DESCRIPTION	
--    "The MIB module describing the top-level Nortel Magellan Passport
--    OBJECT IDENTIFIER tree structure. It also provides definitions for
--    values of the variable sysOID for different Passport products."
-- 
--  usefulDefinitionsMIB	  OBJECT IDENTIFIER ::= { passportMIBs 1 }


-- FYI:
-- enterprises OBJECT IDENTIFIER ::= { iso(1) org(3) dod(6)
--                                       internet(1) private(4) 1 }

-- arcs up to the enterprises:
nortel      OBJECT IDENTIFIER ::= { enterprises 562 }
magellan    OBJECT IDENTIFIER ::= { nortel 2 }
products    OBJECT IDENTIFIER ::= { magellan 1 }
passport    OBJECT IDENTIFIER ::= { magellan 4 }

--
-- values for sysOID:
--

--   STATUS      current
--   DESCRIPTION
--      " Passport (Model 30/50/160) is a cell-based switch providing high
--      bandwidth, high performance networking for LAN interconnect
--      applications and network consolidation of data, voice, image and
--      video traffic. "

passport50  OBJECT IDENTIFIER ::= { products 1 }

--   STATUS      current
--   DESCRIPTION
--      " Passport (Model 30/50/160) is a cell-based switch providing high
--      bandwidth, high performance networking for LAN interconnect
--      applications and network consolidation of data, voice, image and 
--      video traffic. "

passport160 OBJECT IDENTIFIER ::= { products 2 }

--   STATUS      current
--   DESCRIPTION
--      " Meridian Passport is a cell-based switch providing high
--      bandwidth and network consolidation of data, voice, image and 
--      video traffic. "

meridianPassport OBJECT IDENTIFIER ::= { products 8 }

--   STATUS      current
--   DESCRIPTION
--      " Passport (Model 30/50/160) is a cell-based switch providing high
--      bandwidth, high performance networking for LAN interconnect
--      applications and network consolidation of data, voice, image and 
--      video traffic. "

passport30  OBJECT IDENTIFIER ::= { products 11 }

--   STATUS      current
--   DESCRIPTION
--      " Passport Virtual Router is a subsystem within Passport which
--      provides internetworking capabilities. The Virtual Router
--      provides routing and packet forwarding functionality which
--      is similar to a real router."
 
passportVirtualRouter  OBJECT IDENTIFIER ::= { products 12 }

-- arcs immediately subordinate to Passport:
components                OBJECT IDENTIFIER ::= { passport 1 }
                              -- all MIB variables are defined
                              -- in the subtree rooted at 'components'.
passportMIBs              OBJECT IDENTIFIER ::= { passport 2 }
                              -- all MIBs, OBJECT_GROUP and
                              -- AGENT-CAPABILITIES are defined
                              -- in the subtree rooted at 'passportMIBs'.

-- see DESCRIPTION at the beginning of this module
usefulDefinitionsMIB	  OBJECT IDENTIFIER ::= { passportMIBs 1 }

-- the following component is assigned here for convenience:
passportTraps             OBJECT IDENTIFIER ::= { components 3 }
                              -- traps may be defined in a number
                              -- of different modules. Defining this
                              -- component here makes the IMPORT clauses
                              -- easier to understand.


--
-- Version and Compliance statements
--
 
 
-- Object-Group Statement:

--    OBJECTS   { }
--    STATUS    current
--    DESCRIPTION
--       "A list of all current accessible leaf objects."

usefulDefinitionsGroup OBJECT IDENTIFIER ::= { usefulDefinitionsMIB 1 }
usefulDefinitionsGroupBC OBJECT IDENTIFIER ::= { usefulDefinitionsGroup 3 }
usefulDefinitionsGroupBC03 OBJECT IDENTIFIER ::= { usefulDefinitionsGroupBC 3 }
usefulDefinitionsGroupBC03A OBJECT IDENTIFIER ::= { usefulDefinitionsGroupBC03 2 }


-- Agent-Capabilities Statement:

--    PRODUCT-RELEASE "Passport Release 3.3 Useful Definitions."
--    STATUS          current
--    DESCRIPTION
--       "Useful Definitions MIB: MIB Version BC03A."
--    SUPPORTS        Nortel-Magellan-Passport-UsefuleDefinitionsMIB
--    INCLUDES        { usefulDefinitionsGroupBC03A }

usefulDefinitionsCapabilities OBJECT IDENTIFIER ::= { usefulDefinitionsMIB 3 }
usefulDefinitionsCapabilitiesBC OBJECT IDENTIFIER ::= { usefulDefinitionsCapabilities 3 }
usefulDefinitionsCapabilitiesBC03 OBJECT IDENTIFIER ::= { usefulDefinitionsCapabilitiesBC 3 }
usefulDefinitionsCapabilitiesBC03A OBJECT IDENTIFIER ::= { usefulDefinitionsCapabilitiesBC03 2 }


END
