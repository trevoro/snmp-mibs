--			Ascend mibredundancy MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBREDUNDANCY-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibredundancyProfile  OBJECT IDENTIFIER ::= { configuration 16}

	-- The mibredundancyProfile table
	--
	-- This table contains parameters for the mibredundancyProfile profile
	--

    mibredundancyProfileTable	OBJECT-TYPE
	SYNTAX		SEQUENCE OF MibredundancyProfileEntry
	ACCESS		not-accessible
	STATUS		mandatory
	DESCRIPTION	"A list of mibredundancyProfile profile entries."
	::= { mibredundancyProfile 1 }

    mibredundancyProfileEntry	OBJECT-TYPE
	SYNTAX		MibredundancyProfileEntry
	ACCESS		not-accessible
	STATUS		mandatory
	DESCRIPTION	"A mibredundancyProfile entry containing objects that
			 maps to the parameters of mibredundancyProfile profile."
	INDEX		{ redundancyProfile-Index-o }
	::= { mibredundancyProfileTable 1 }

    MibredundancyProfileEntry ::=
	SEQUENCE {
	    redundancyProfile-Index-o
		INTEGER,
	    redundancyProfile-PrimaryPreference
		INTEGER,
	    redundancyProfile-SyncEnabled
		INTEGER,
	    redundancyProfile-Action-o
		INTEGER
	}

    redundancyProfile-Index-o	OBJECT-TYPE
	SYNTAX	INTEGER
	ACCESS	read-only
	STATUS	mandatory
	DESCRIPTION	""
	::= { mibredundancyProfileEntry 1 }

    redundancyProfile-PrimaryPreference	OBJECT-TYPE
	SYNTAX	INTEGER {
		    noPreference (1),
		    leftControllerPreferred (2),
		    rightControllerPreferred (3),
		    firstControllerPreferred (4),
		    secondControllerPreferred (5)
		}
	ACCESS	read-write
	STATUS	mandatory
	DESCRIPTION	"Indicates which controller is to be given preference to become primary."
	::= { mibredundancyProfileEntry 2 }

    redundancyProfile-SyncEnabled	OBJECT-TYPE
	SYNTAX	INTEGER {
		    no (1),
		    yes (2)
		}
	ACCESS	read-write
	STATUS	mandatory
	DESCRIPTION	"Indicates whether run time sync of data from primary to secondary is enabled. CAUTION: The SECONDARY will be reset for changes to take effect!!!"
	::= { mibredundancyProfileEntry 4 }

    redundancyProfile-Action-o	OBJECT-TYPE
	SYNTAX	INTEGER {
		    noAction (1),
		    createProfile (2),
		    deleteProfile (3)
		}
	ACCESS	read-write
	STATUS	mandatory
	DESCRIPTION	""
	::= { mibredundancyProfileEntry 3 }


	-- The mibredundancyProfile__context table
	--
	-- This table contains parameters for the mibredundancyProfile__context profile
	--

    mibredundancyProfile-ContextTable	OBJECT-TYPE
	SYNTAX		SEQUENCE OF MibredundancyProfile-ContextEntry
	ACCESS		not-accessible
	STATUS		mandatory
	DESCRIPTION	"A list of mibredundancyProfile__context profile entries."
	::= { mibredundancyProfile 2 }

    mibredundancyProfile-ContextEntry	OBJECT-TYPE
	SYNTAX		MibredundancyProfile-ContextEntry
	ACCESS		not-accessible
	STATUS		mandatory
	DESCRIPTION	"A mibredundancyProfile__context entry containing objects that
			 maps to the parameters of mibredundancyProfile__context profile."
	INDEX		{ redundancyProfile-Context-Index-o, redundancyProfile-Context-Index1-o }
	::= { mibredundancyProfile-ContextTable 1 }

    MibredundancyProfile-ContextEntry ::=
	SEQUENCE {
	    redundancyProfile-Context-Index-o
		INTEGER,
	    redundancyProfile-Context-Index1-o
		INTEGER,
	    redundancyProfile-Context-MustAgree
		INTEGER
	}

    redundancyProfile-Context-Index-o	OBJECT-TYPE
	SYNTAX	INTEGER
	ACCESS	read-only
	STATUS	mandatory
	DESCRIPTION	""
	::= { mibredundancyProfile-ContextEntry 1 }

    redundancyProfile-Context-Index1-o	OBJECT-TYPE
	SYNTAX	INTEGER
	ACCESS	read-only
	STATUS	mandatory
	DESCRIPTION	""
	::= { mibredundancyProfile-ContextEntry 2 }

    redundancyProfile-Context-MustAgree	OBJECT-TYPE
	SYNTAX	INTEGER {
		    no (1),
		    yes (2)
		}
	ACCESS	read-write
	STATUS	mandatory
	DESCRIPTION	"Indicates whether the controllers must agree on the choice of a primary controller"
	::= { mibredundancyProfile-ContextEntry 3 }

END
