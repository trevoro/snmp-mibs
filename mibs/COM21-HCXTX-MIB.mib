-- 
--  Copyright 1996, Com21 Inc.  All Rights Reserved.
--
 
COM21-HCXTX-MIB DEFINITIONS ::= BEGIN
  IMPORTS
        MODULE-IDENTITY, OBJECT-TYPE, NOTIFICATION-TYPE, Integer32,
        IpAddress, Gauge32, TimeTicks
            FROM SNMPv2-SMI
        DisplayString, MacAddress
            FROM SNMPv2-TC
        com21, com21Hcx
            FROM COM21-HCX-MIB
        com21Traps FROM COM21-HCX-MIB
		  hcxAlmSeverity, hcxEventLogTime
            FROM COM21-HCXALM-MIB;



        com21HcxTx MODULE-IDENTITY
                LAST-UPDATED "9701080000Z"
                ORGANIZATION "Com21, Inc."
                CONTACT-INFO
                "       Network Management
                                Postal: Paul Gordon
                                Com21, Inc.
                                750 Tasman Drive
                                Milpitas, California 95035
                                USA
                                Tel: +1 408 953 9100
                                Fax: +1 408 953 9299
                                E-mail: pgordon@com21.com"

                DESCRIPTION
                        "This is the Com21 ComController TX Unit Control 
			   MIB module. COM21 Part# 005-0025-00"
                ::= { com21Hcx 20 }


        com21HcxDnstrmPortGroup         OBJECT IDENTIFIER ::= {com21Hcx 21 }
        com21HcxDnstrmStatsGroup        OBJECT IDENTIFIER ::= {com21Hcx 22 }
        com21HcxDnstrmUnitGroup         OBJECT IDENTIFIER ::= {com21Hcx 23 }

        Gain             ::= INTEGER (0..255)
        PrimServiceState ::= INTEGER { is(1), oos(2) }


        -- -- -- -- -- -- -- -- -- -- -- -- -- -- -- -- -- -- -- -- -- -- -- --
        -- -- -- -- -- -- -- -- -- -- -- -- -- -- -- -- -- -- -- -- -- -- -- --
        --
        -- COM21 ComController Enterprise MIB
        --
        -- This MIB contains SNMP Groups and Attributes definitions for COM21
        -- specific management.
        -- Also supported by the ComController shall be the MIB II for the 
	-- SNMP interface and the MIB II Interfaces Group for both the 
	-- ComController and ComPort Ethernet interfaces.
        -- This Enterprise MIB contains many elements of the ATM UNI 2.1 ILMI
        -- MIB. This full MIB is not presently supported by the COM21 equipment
        -- as there are no external UNI interfaces. When this changes then the
        -- full MIB should be supported and the related Enterprise MIB entries
        -- removed.
        --
        --   com21HcxDnstrmUnitGroup    - this group provides for monitor and
        --                                control of a single RF TX card. As
        --                                noted above, all control of the port
        --                                state shall be performed through this
        --                                card level group.
        --
        --   com21HcxDnstrmPortGroup    - this group represents a single
        --                                downstream RF port on the RF TX card.
        --                                Note that the TX card contains only
        --                                one port. Therefore the control of
        --                                port state is presently at the card
        --                                level. If a multiport card is
        --                                produced in the future, this group
        --                                shall be expanded.
        --
        --   com21HcxDnstrmStatsGroup   - this provides statistical data
        --                                related to a single downstream RF
        --                                port.
        --
        -- -- -- -- -- -- -- -- -- -- -- -- -- -- -- -- -- -- -- -- -- -- -- --
        -- -- -- -- -- -- -- -- -- -- -- -- -- -- -- -- -- -- -- -- -- -- -- --



	-- -- -- -- -- -- -- -- -- -- -- -- -- -- -- -- -- -- -- -- -- -- -- --
	-- -- -- -- -- -- -- -- -- -- -- -- -- -- -- -- -- -- -- -- -- -- -- --
	--
	-- com21HcxDnstrmUnitGroup
	--
	-- defines the attributes related to the management of the 
	-- ComController RF Transmitter Unit.
	--
	-- -- -- -- -- -- -- -- -- -- -- -- -- -- -- -- -- -- -- -- -- -- -- --
	-- -- -- -- -- -- -- -- -- -- -- -- -- -- -- -- -- -- -- -- -- -- -- --

        hcxDownstreamShelfId OBJECT-TYPE
                SYNTAX INTEGER (1..2)
                MAX-ACCESS read-only
                STATUS current
                DESCRIPTION "
                        contains the associated shelf id."
                ::= { com21HcxDnstrmUnitGroup 1 }

        hcxDownstreamSlotId OBJECT-TYPE
                SYNTAX Integer32
                MAX-ACCESS read-only
                STATUS current
                DESCRIPTION "
                        contains downstream slot id."
                ::= { com21HcxDnstrmUnitGroup 2 }

        hcxDownstreamHardwareVersion OBJECT-TYPE
                SYNTAX DisplayString (SIZE(16))
                MAX-ACCESS read-only   
                STATUS current
                DESCRIPTION "  
                        contains the hardware version of the TX card.
			An empty string if card not present."
                ::= { com21HcxDnstrmUnitGroup 3 }
 
        hcxDownstreamBootVersion OBJECT-TYPE
                SYNTAX DisplayString (SIZE(16))
                MAX-ACCESS read-only
                STATUS current
                DESCRIPTION "
                        contains the version of the TX card boot ROM.
			An empty string if card not present."
                ::= { com21HcxDnstrmUnitGroup 4 }

        hcxDnstreamUnitPrimServState OBJECT-TYPE
                SYNTAX PrimServiceState
                MAX-ACCESS read-only
                STATUS current
                DESCRIPTION "
                        contains primary service state of the Downstream 
			Unit."
                ::= { com21HcxDnstrmUnitGroup 5 }

        hcxDnstrmUnitPrimStateChange NOTIFICATION-TYPE
                OBJECTS { hcxAlmSeverity, hcxEventLogTime,
		            hcxDownstreamShelfId, hcxDownstreamSlotId, 
			    hcxDnstreamUnitPrimServState }
                STATUS current
                DESCRIPTION "
                        Generated whenever a the hcxDnstreamUnitPrimServState
                        changes in value. This an event with no clear 
			condition. Only severity is WARNING."
                ::= { com21Traps 60 }

        hcxDnstreamUnitSecServState OBJECT-TYPE
                SYNTAX DisplayString (SIZE(16))
                MAX-ACCESS read-only
                STATUS current
                DESCRIPTION "
                        contains a string defining the secondary service states 
			of the Downstream Unit. The substrings supported by
			the Downstream Unit shall be: TEST - in test, as 
			set by hcxDnUnitConfigState, STBY - standby, again set
			by hcxDnUnitConfigState, MT - maintenance, set by
			hcxDnUnitConfigState, FAULT - hardware failure, UNEQ -
			unequipped."
                ::= { com21HcxDnstrmUnitGroup 6 }
 
        hcxDnstrmUnitSecStateChange NOTIFICATION-TYPE
                OBJECTS { hcxAlmSeverity, hcxEventLogTime,
		            hcxDownstreamShelfId, hcxDownstreamSlotId, 
                            hcxDnstreamUnitSecServState }
                STATUS current
                DESCRIPTION "
                        Generated whenever a the hcxDnstreamUnitSecServState
                        changes in value. This an event with no clear 
			condition. Only severity is WARNING."
                ::= { com21Traps 61 }

        hcxDnUnitConfigState OBJECT-TYPE
		SYNTAX INTEGER {
                                offline(2000),  -- prim = OOS, sec = MT
                                online(2001),   -- prim = IS
                                test(2002),     -- prim = OOS, sec = TEST
                                standby(2003) } -- prim = OOS, sec = STBY
                MAX-ACCESS read-write
                STATUS current
                DESCRIPTION "
                        The Downstream Unit State is an active-value.
			Note that because we have only one port per card
			then this state change is exactly the same as
			hcxDnstrmPortState. Note that initially standby
			will be the same state as offline. Later this will
			change when TX redundancy is supported. offline
			is default."
                ::= { com21HcxDnstrmUnitGroup 7 }

	hcxDnUnitRestartAction OBJECT-TYPE
		SYNTAX INTEGER {
                                nil(1),
                                restart(2) }
                MAX-ACCESS read-write
                STATUS current
                DESCRIPTION "
			The TX Unit Action is an active-value. The setting
			of this attibute to restart(2) causes the TX card
			to reset and download a new image."
                ::= { com21HcxDnstrmUnitGroup 8 }

        hcxDnDiagTestAction OBJECT-TYPE
                SYNTAX INTEGER { nil(1), execute(2) }
                MAX-ACCESS read-write
                STATUS current
                DESCRIPTION "
                        This attribute is used to invoke the internal
                        TX diagnostic test. In order to activate this
                        test, the card must be placed in the test state."
                ::= { com21HcxDnstrmUnitGroup 9 }
 
        hcxDnDiagTestComplete NOTIFICATION-TYPE
                OBJECTS { hcxAlmSeverity, hcxEventLogTime,
		            hcxDownstreamShelfId, hcxDownstreamSlotId, 
                            hcxDnDiagTestResult }
                STATUS current
                DESCRIPTION "
                        This notification is generated whenever the TX
                        internal diagnostic tests are completed. This an event 
                        with no clear condition. Only severity is WARNING."
                ::= { com21Traps 62 }
 
        hcxDnDiagTestResult OBJECT-TYPE
                SYNTAX INTEGER { 
				inprogress(1),
				success(2), 
				failure(3),
				invalidState(4) }
                MAX-ACCESS read-only
                STATUS current
                DESCRIPTION "
                        This attribute contains the result of the last TX
                        diagnostic test. Details TBD."
                ::= { com21HcxDnstrmUnitGroup 10 }

        hcxDnTestStatusLed OBJECT-TYPE
                SYNTAX INTEGER { on (1), off (2) }
                MAX-ACCESS read-only
                STATUS current
                DESCRIPTION "
                        The TX Test Status LED is a read-only attribute
                        which describes the condition of the TX
                        Test Status light emitting diode located on
                        the RX board. A value of on(1) indicates that a
                        service effecting test is in progress and that
                        the LED is illuminated. off if card not present."
                ::= { com21HcxDnstrmUnitGroup 11 }

        hcxDnTestStatusLedChange NOTIFICATION-TYPE
                OBJECTS { hcxAlmSeverity, hcxEventLogTime,
		            hcxDownstreamShelfId, hcxDownstreamSlotId, 
                            hcxDnTestStatusLed }
                STATUS current
                DESCRIPTION "
                        generated whenever there is a change in test LED
                        status. This an event with no clear condition.
                        Only severity is WARNING."
                ::= { com21Traps 63  }

        hcxDnFaultStatusLed OBJECT-TYPE
                SYNTAX INTEGER { on (1), off (2) }
                MAX-ACCESS read-only
                STATUS current
                DESCRIPTION "
                        The RX Fault Status LED is a read-only attribute
                        which describes the condition of the TX
                        Fault Status light emitting diode located on
                        the TX board. A value of on(1) indicates that an
                        fault condition has been detected (for which a
                        trap will have been issued) and the LED is
                        illuminated. off if card not present."
                ::= { com21HcxDnstrmUnitGroup 12 }
 
        hcxDnFaultStatusLedChange NOTIFICATION-TYPE
                OBJECTS { hcxAlmSeverity, hcxEventLogTime,
		            hcxDownstreamShelfId, hcxDownstreamSlotId, 
                            hcxDnFaultStatusLed }
                STATUS current
                DESCRIPTION "
                        generated whenever there is a change in the Fault
                        LED status. This an event with no clear condition.
                        Only severity is WARNING."
                ::= { com21Traps 64 }
 
        hcxDnOperationFailure NOTIFICATION-TYPE
                OBJECTS { hcxAlmSeverity, hcxEventLogTime,
		            hcxDownstreamShelfId, hcxDownstreamSlotId }
                STATUS current
                DESCRIPTION "
                        This notification is generated by the CC whenever
                        a TX card fails to respond correctly to a
                        request. This failure could indicate either a
                        resource problem or software failure. Note that
                        if a TX card failures to respond completely to
                        a CC request, then a hcxInsertChange trap shall
                        be generated. This is an event with no clear 
			condition. Only severity is WARNING."
                ::= { com21Traps 65 }

        hcxDownstreamSerialNumber OBJECT-TYPE
                SYNTAX DisplayString (SIZE(16))
                MAX-ACCESS read-only   
                STATUS current
                DESCRIPTION "  
                        contains the serial number of the TX card.
			An empty string if card not present."
                ::= { com21HcxDnstrmUnitGroup 13 }

 

	-- -- -- -- -- -- -- -- -- -- -- -- -- -- -- -- -- -- -- -- -- -- -- --
	-- -- -- -- -- -- -- -- -- -- -- -- -- -- -- -- -- -- -- -- -- -- -- --
	--
	-- com21HcxDnstrmPortGroup
	--
	-- defines the attributes related to the management of the 
	-- Downstream RF and MAC layers. For the moment there is the assumption
	-- that there is only one downstream port active at any given time.
	--
	-- -- -- -- -- -- -- -- -- -- -- -- -- -- -- -- -- -- -- -- -- -- -- --
	-- -- -- -- -- -- -- -- -- -- -- -- -- -- -- -- -- -- -- -- -- -- -- --

	hcxDownstreamPortId OBJECT-TYPE
                SYNTAX Integer32
                MAX-ACCESS read-only
                STATUS current
                DESCRIPTION "
                        contains downstream port id. Initially at least, only 1
			supported."
                ::= { com21HcxDnstrmPortGroup 1 }

	hcxXmitFrequency OBJECT-TYPE
		SYNTAX INTEGER (88000..800000)
		MAX-ACCESS read-write
		STATUS current
		DESCRIPTION "
			Contains the transmit frequency of the RF port in 
			KHz. If this value is changed AFTER the acquisition of
			ComPorts then a corresponding change to the
			stuXmitFrequency attribute shall be broadcast to all
			the acquired ComPorts. Minimum step size is 200. i.e.
			200000hz. Default is 0."
		::= { com21HcxDnstrmPortGroup 2 }

	hcxXmitGain OBJECT-TYPE
		SYNTAX INTEGER (45..60)	-- in dB
		MAX-ACCESS read-write
		STATUS current
		DESCRIPTION "
			Transmit gain is used to specify the power level in 
			the ComController transmitter. Default is 0."
		::= { com21HcxDnstrmPortGroup 3 }

        hcxSynthLockLossDetected NOTIFICATION-TYPE
                OBJECTS { hcxAlmSeverity, hcxEventLogTime, 
                            hcxDownstreamShelfId, hcxDownstreamSlotId,
		            hcxDownstreamPortId }
                STATUS current
                DESCRIPTION "Default severity is MINOR."
                ::= { com21Traps 68 }
 
        hcxSynthLockLossClear NOTIFICATION-TYPE
                OBJECTS { hcxAlmSeverity, hcxEventLogTime,
                            hcxDownstreamShelfId, hcxDownstreamSlotId,
		            hcxDownstreamPortId }
                STATUS current
                DESCRIPTION "Severity is CLEARED."
                ::= { com21Traps 69 }
 
        hcxLossOfFrameClkDetected NOTIFICATION-TYPE
                OBJECTS { hcxAlmSeverity, hcxEventLogTime,
                            hcxDownstreamShelfId, hcxDownstreamSlotId,
		            hcxDownstreamPortId }
                STATUS current
                DESCRIPTION "Default severity is MINOR."
                ::= { com21Traps 70 }
 
        hcxLossOfFrameClkClear NOTIFICATION-TYPE
                OBJECTS { hcxAlmSeverity, hcxEventLogTime,
                            hcxDownstreamShelfId, hcxDownstreamSlotId,
		            hcxDownstreamPortId }
                STATUS current
                DESCRIPTION "Severity is CLEARED."
                ::= { com21Traps 71 }
 


	-- -- -- -- -- -- -- -- -- -- -- -- -- -- -- -- -- -- -- -- -- -- -- --
	-- -- -- -- -- -- -- -- -- -- -- -- -- -- -- -- -- -- -- -- -- -- -- --
	--
	-- com21HcxDnstrmStatsGroup
	--
	-- defines the attributes related to the statistical analysis of the 
	-- Downstream port. This statistical infomation covers physical and ATM
	-- layer stastics. For the moment there is the assumption that there is
	-- only one downstream port active at any given time.
	-- This data is collected by the RF Transmitter card.
	--
	-- -- -- -- -- -- -- -- -- -- -- -- -- -- -- -- -- -- -- -- -- -- -- --
	-- -- -- -- -- -- -- -- -- -- -- -- -- -- -- -- -- -- -- -- -- -- -- --

	hcxStatsCurrMinTxCells OBJECT-TYPE
		SYNTAX Gauge32
		MAX-ACCESS read-only
                STATUS current
                DESCRIPTION " 
                        Represents the number of cells transmitted in the 
			current 15 minute period."
                ::= { com21HcxDnstrmStatsGroup 1 }

	hcxStatsCurrMinTxNullCells OBJECT-TYPE
		SYNTAX Gauge32
		MAX-ACCESS read-only
                STATUS current
                DESCRIPTION " 
                        Represents the number of null cells transmitted in the 
			current 15 minute period."
                ::= { com21HcxDnstrmStatsGroup 2 }

	hcxStatsPrevMinTxCells OBJECT-TYPE
		SYNTAX Gauge32
		MAX-ACCESS read-only
                STATUS current
                DESCRIPTION " 
                        Represents the number of cells transmitted in the 
			previous 15 minute period."
                ::= { com21HcxDnstrmStatsGroup 3 }

	hcxStatsPrevMinTxNullCells OBJECT-TYPE
		SYNTAX Gauge32
		MAX-ACCESS read-only
                STATUS current
                DESCRIPTION " 
                        Represents the number of null cells transmitted in the 
			previous 15 minute period."
                ::= { com21HcxDnstrmStatsGroup 4 }

	hcxDownstreamUtil OBJECT-TYPE
                SYNTAX Gauge32     -- 0% -to- 100%
                MAX-ACCESS read-only
                STATUS current
                DESCRIPTION "
                        Represents the percentage of utilization on the 
			downstream channel - the RF TX will stuff with null
			cells to match line rate. 
			i.e. traffic cells/(traffic cells + null cells) * 100.
                        This figure is updated every second."
                ::= { com21HcxDnstrmStatsGroup 5 }

        hcxStatsClearTxCurrStats OBJECT-TYPE
                SYNTAX INTEGER  { nil(1), clear(2) }
                MAX-ACCESS read-write
                STATUS current
                DESCRIPTION "
                        This attribute is used to clear current TX
                        statistics counters in this group. This operation
                        is only possible if the hcxStatsControl attribute
                        is set to wrapCurr."
                ::= { com21HcxDnstrmStatsGroup 6 }

END
