ADSLF-MIB DEFINITIONS ::= BEGIN
 
        IMPORTS
		Counter
                  FROM RFC1155-SMI

          OBJECT-TYPE
                  FROM RFC-1212
          DisplayString
						FROM SNMPv2-TC
			usrAdslf,  UsrConfigStatus
                  FROM USR-DEFINITIONS-MIB;
 

		adslLineCoding OBJECT-TYPE
		    SYNTAX	INTEGER {
			dmt (1), -- Discrete MultiTone
			cap (2), -- Carrierless Amplitude & Phase modulation
			qam (3) -- Quadrature Amplitude Modulation
		    }
		    ACCESS	read-only
		    STATUS	mandatory
		    DESCRIPTION
			"Specifies the ADSL coding type used on this line.
			Other types may be added in the future with higher values ala ifIANAtype.
			This is used to create a LCS sub-MIB in the same way ifIANAtype adsl(94)
			is used to create this MIB."
		::= { usrAdslf 1 }


		adslLineType OBJECT-TYPE
		    SYNTAX	INTEGER {
			physical (1), -- physical layer only
			fast (2), -- fast channel only
			interleave (3), -- interleaved channel only
			physFast (4), -- combined physical and fast in one entry
			physInterleave (5) -- combined physical and interleaved in one entry
		    }
		    ACCESS	read-only
		    STATUS	mandatory
		    DESCRIPTION
			"this describes which other tables go with this ifEntry.
			use EITHER three separate ifEntries (and adslLinEntries):
			(1) and tables 1,2,3, 6,7,8,9 
			(2) with 1,4,5, and (3) and 1,4,5,
				OR 
			use values (4) or (5) with tables 1-9 as a single ifEntry/adslLineEntry"
		::= { usrAdslf 2 }

		adslLineSpecific OBJECT-TYPE
		    SYNTAX	OBJECT IDENTIFIER
		    ACCESS	read-only
		    STATUS	mandatory
		    DESCRIPTION
			"OID instance in vendor-specific MIB.  The Instance may be
			used to determine shelf/slot/port of the ATU-C interface
			in a DSLAM (among other possibilities)"
		::= { usrAdslf 3 }

		adslLineStatus OBJECT-TYPE
		    SYNTAX	INTEGER {
			operational (1), -- Everything is OK
			lossOfFraming (2), -- ATU-C not receiving valid frame format from ATU-R
			lossOfSignal (3), -- ATU-C not receiving any signal from ATU-R
			lossOfPower (4), -- ATU-R has lost power
			initFailure (5) -- ATU-C had local initialization failure
		    }
		    ACCESS	read-only
		    STATUS	mandatory
		    DESCRIPTION
			"Status indicates mandatory state of the line.
			This is a bit-map of possible conditions.
			These are from the perspective of the ATU-C, since any loss of
			communication with the ATU-R prevents determination of its state.
			This is intended to supplement ifOperStatus and ifAdminStatus."
		::= { usrAdslf 4 }

		-- inventory group
		-- These items should describe the lowest level identifiable component,
		-- be it a stand-alone modem, a card in a rack, 
		-- a child-board, or whatever.
		adslAturInvSerialNumber OBJECT-TYPE
		    SYNTAX	DisplayString (SIZE(1..32))
		    ACCESS	read-only
		    STATUS	mandatory
		    DESCRIPTION
			"Vendor specific Serial number of the ATU-C modem"
		::= { usrAdslf 5 }

		adslAturInvVendorID OBJECT-TYPE
		    SYNTAX	INTEGER
		    ACCESS	read-only
		    STATUS	mandatory
		    DESCRIPTION
			"The vendor ID assigned by T1E1.4 according to its Appendix D."
		::= { usrAdslf 6 }


		-- mandatory status group
		adslAturCurrOutputPower OBJECT-TYPE
		    SYNTAX	DisplayString
		    ACCESS	read-only
		    STATUS	mandatory
		    DESCRIPTION
			"Current output power"
		::= { usrAdslf 7 }

		adslAturCurrTransmitRate OBJECT-TYPE
		    SYNTAX	DisplayString
		    ACCESS	read-only
		    STATUS	mandatory
		    DESCRIPTION
			"Current transmit rate in kbps, limited to multiples of 32kbps"
		::= { usrAdslf 8 }

		adslAturCurrCodeWordLength OBJECT-TYPE
		    SYNTAX	INTEGER
		    ACCESS	read-only
		    STATUS	mandatory
		    DESCRIPTION
			"Current Code Word Length,
			calculated from Transmit rate and noise margin"
		::= { usrAdslf 9 }


		-- these 3 seem redundant.  Do we need all of them?
		adslAturCurrSnrMgn OBJECT-TYPE
		    SYNTAX	DisplayString
		    ACCESS	read-only
		    STATUS	mandatory
		    DESCRIPTION
			"to be supplied."
		::= { usrAdslf 10 }

		adslAturCurrAtn OBJECT-TYPE
		    SYNTAX	DisplayString
		    ACCESS	read-only
		    STATUS	mandatory
		    DESCRIPTION
			"to be supplied."
		::= { usrAdslf 11 }

		adslAturCurrReceiveGain OBJECT-TYPE
		    SYNTAX	INTEGER
		    ACCESS	read-only
		    STATUS	mandatory
		    DESCRIPTION
			"to be supplied."
		::= { usrAdslf 12 }


		-- performance group
		adslAturPerfValidIntervals OBJECT-TYPE
		    SYNTAX	INTEGER(0..95)
		    ACCESS	read-only
		    STATUS	mandatory
		    DESCRIPTION
			"number of valid intervals in the adslAturPerfDataTable"
		::= { usrAdslf 13 }


		-- Event Counters
		-- Also see adslAturPerfDataTable for 15 minute interval elapsed counters.
		adslAturPerfLof OBJECT-TYPE
		    SYNTAX	INTEGER
		    ACCESS	read-only
		    STATUS	mandatory
		    DESCRIPTION
			"count of the number of Loss of Framing events since system reset."
		::= { usrAdslf 14 }

		adslAturPerfLos  OBJECT-TYPE
		    SYNTAX	INTEGER
		    ACCESS	read-only
		    STATUS	mandatory
		    DESCRIPTION
			"count of the number of Loss of Signal events since system reset."
		::= { usrAdslf 15 }

		adslAturPerfLpr  OBJECT-TYPE
		    SYNTAX	INTEGER
		    ACCESS	read-only
		    STATUS	mandatory
		    DESCRIPTION
			"count of the number of Loss of Power events since system reset."
		::= { usrAdslf 16 }

		adslAturPerfCV  OBJECT-TYPE
		    SYNTAX	INTEGER
		    ACCESS	read-only
		    STATUS	mandatory
		    DESCRIPTION
			"count of the number of Loss of Coding Violation events since system reset."
		::= { usrAdslf 17 }

		adslAturPerfES  OBJECT-TYPE
		    SYNTAX	INTEGER
		    ACCESS	read-only
		    STATUS	mandatory
		    DESCRIPTION
			"count of the number of Errored Seconds since system reset."
		::= { usrAdslf 18 }


		-- one Day Current and Previous Interval (second) counters
		-- Also see adslAturPerfDataTable for 15 minute interval counters
		adslAturPerfCurr1DayElapSecs OBJECT-TYPE
		    SYNTAX	INTEGER
		    ACCESS	read-only
		    STATUS	mandatory
		    DESCRIPTION
			"The total time interval over which all Curr1Day interval counters are measured.
			If 0, this interval is invalid."
		::= { usrAdslf 19 }

		adslAturPerfCurr1DayMoniSecs OBJECT-TYPE
		    SYNTAX	INTEGER
		    ACCESS	read-only
		    STATUS	mandatory
		    DESCRIPTION
			"The total number of valid seconds in the Curr1Day interval counters.
			This may be less than adslAturPerfCurr1DayElapSecs only when
			there were some seconds in the interval when no valid data
			could be collected."
		::= { usrAdslf 20 }

		adslAturPerfPrev1DayElapSecs OBJECT-TYPE
		    SYNTAX	INTEGER
		    ACCESS	read-only
		    STATUS	mandatory
		    DESCRIPTION
			"The total time interval over which all Prev1Day interval counters are measured.
			If 0, this interval is invalid."
		::= { usrAdslf 21 }

		adslAturPerfPrev1DayMoniSecs OBJECT-TYPE
		    SYNTAX	INTEGER
		    ACCESS	read-only
		    STATUS	mandatory
		    DESCRIPTION
			"The total number of valid seconds in the Prev1Day interval counters.
			This may be less than adslAturPerfPrev1DayElapSecs only when
			there were some seconds in the interval when no valid data
			could be collected."
		::= { usrAdslf 22 }

		adslAturPerfCurr1DayLofs  OBJECT-TYPE
		    SYNTAX	INTEGER
		    ACCESS	read-only
		    STATUS	mandatory
		    DESCRIPTION
			"Count of the number of seconds when there was Loss of Framing
			during the mandatory day, as measured by adslAturPerfCurr1DayElapSecs."
		::= { usrAdslf 23 }

		adslAturPerfPrev1DayLofs  OBJECT-TYPE
		    SYNTAX	INTEGER
		    ACCESS	read-only
		    STATUS	mandatory
		    DESCRIPTION
			"to be supplied."
		::= { usrAdslf 24 }

		adslAturPerfCurr1DayLoss  OBJECT-TYPE
		    SYNTAX	INTEGER
		    ACCESS	read-only
		    STATUS	mandatory
		    DESCRIPTION
			"to be supplied."
		::= { usrAdslf 25 }

		adslAturPerfPrev1DayLoss  OBJECT-TYPE
		    SYNTAX	INTEGER
		    ACCESS	read-only
		    STATUS	mandatory
		    DESCRIPTION
			"to be supplied."
		::= { usrAdslf 26 }

		adslAturPerfCurr1DayLprs  OBJECT-TYPE
		    SYNTAX	INTEGER
		    ACCESS	read-only
		    STATUS	mandatory
		    DESCRIPTION
			"to be supplied."
		::= { usrAdslf 27 }

		adslAturPerfPrev1DayLprs  OBJECT-TYPE
		    SYNTAX	INTEGER
		    ACCESS	read-only
		    STATUS	mandatory
		    DESCRIPTION
			"to be supplied."
		::= { usrAdslf 28 }

		adslAturPerfCurr1DayCVs  OBJECT-TYPE
		    SYNTAX	INTEGER
		    ACCESS	read-only
		    STATUS	mandatory
		    DESCRIPTION
			"to be supplied."
		::= { usrAdslf 29 }

		adslAturPerfPrev1DayCVs  OBJECT-TYPE
		    SYNTAX	INTEGER
		    ACCESS	read-only
		    STATUS	mandatory
		    DESCRIPTION
			"to be supplied."
		::= { usrAdslf 30 }

		adslAturPerfCurr1DayES  OBJECT-TYPE
		    SYNTAX	INTEGER
		    ACCESS	read-only
		    STATUS	mandatory
		    DESCRIPTION
			"to be supplied."
		::= { usrAdslf 31 }

		adslAturPerfPrev1DayES  OBJECT-TYPE
		    SYNTAX	INTEGER
		    ACCESS	read-only
		    STATUS	mandatory
		    DESCRIPTION
			"to be supplied."
		::= { usrAdslf 32 }



		adslAturPerfCurr15minLofs OBJECT-TYPE
                    SYNTAX      INTEGER
                    ACCESS  read-only
                    STATUS      mandatory
                    DESCRIPTION
                        "to be supplied."
                ::= { usrAdslf 33 }

 
                adslAturPerfPrev15minLofs OBJECT-TYPE
                    SYNTAX      INTEGER
                    ACCESS  read-only
                    STATUS      mandatory
                    DESCRIPTION
                        "to be supplied."
                ::= { usrAdslf 34 }

                adslAturPerfCurr15minLoss OBJECT-TYPE
                    SYNTAX      INTEGER
                    ACCESS  read-only
                    STATUS      mandatory
                    DESCRIPTION
                        "to be supplied."
                ::= { usrAdslf 35 }
 
                adslAturPerfPrev15minLoss OBJECT-TYPE
                    SYNTAX      INTEGER
                    ACCESS  read-only
                    STATUS      mandatory
                    DESCRIPTION
                        "to be supplied."
                ::= { usrAdslf 36 }
 
                adslAturPerfCurr15minLprs OBJECT-TYPE
                    SYNTAX      INTEGER
                    ACCESS  read-only
                    STATUS      mandatory
                    DESCRIPTION
                        "to be supplied."
                ::= { usrAdslf 37 }
 
                adslAturPerfPrev15minLprs OBJECT-TYPE
                    SYNTAX      INTEGER
                    ACCESS  read-only
                    STATUS      mandatory
                    DESCRIPTION
                        "to be supplied."
                ::= { usrAdslf 38 }
 
                adslAturPerfCurr15minES OBJECT-TYPE
                    SYNTAX      INTEGER
                    ACCESS  read-only
                    STATUS      mandatory
                    DESCRIPTION
                        "to be supplied."
                ::= { usrAdslf 39 }
 
                adslAturPerfPrev15minES OBJECT-TYPE
                    SYNTAX      INTEGER
                    ACCESS  read-only
                    STATUS      mandatory
                    DESCRIPTION
                        "to be supplied."
                ::= { usrAdslf 40 }
 



		-- threshold group
		-- For TrapEnable objects, 0 disables the corresponding threshold trap,
		-- >0 sets the threshold for the trap to that number
		-- of seconds in a single 15 minute interval.
		-- The counter is reset at the beginning of each interval,
		-- thus limiting traps to at most one every 15 minutes (per type). 
		adslAturThresh15MinLofs OBJECT-TYPE
		    SYNTAX	INTEGER(0..900)
		    ACCESS	read-write
		    STATUS	mandatory
		    DESCRIPTION
			"to be supplied."
		::= { usrAdslf 41 }

		adslAturThresh15MinLoss  OBJECT-TYPE
		    SYNTAX	INTEGER(0..900)
		    ACCESS	read-write
		    STATUS	mandatory
		    DESCRIPTION
			"to be supplied."
		::= { usrAdslf 42 }

		adslAturThresh15MinLprs  OBJECT-TYPE
		    SYNTAX	INTEGER(0..900)
		    ACCESS	read-write
		    STATUS	mandatory
		    DESCRIPTION
			"to be supplied."
		::= { usrAdslf 43 }

		adslAturThresh15MinCVs  OBJECT-TYPE
		    SYNTAX	INTEGER(0..900)
		    ACCESS	read-write
		    STATUS	mandatory
		    DESCRIPTION
			"to be supplied."
		::= { usrAdslf 44 }

		adslAturThresh15MinES  OBJECT-TYPE
		    SYNTAX	INTEGER(0..900)
		    ACCESS	read-write
		    STATUS	mandatory
		    DESCRIPTION
			"to be supplied."
		::= { usrAdslf 45 }


		-- other trap enables
		adslAturInitFailureTrapEnable OBJECT-TYPE
		    SYNTAX	INTEGER {
			enable (1),
			disable (2)
		    }
		    ACCESS	read-write
		    STATUS	mandatory
		    DESCRIPTION	"values as above"
		::= { usrAdslf 46 }



		adslAturChanCurrTxRate  OBJECT-TYPE
		    SYNTAX	INTEGER
		    ACCESS	read-only
		    STATUS	mandatory
		    DESCRIPTION
			"derived from adslAturConfMinTxRate + <available excess bandwidth> * (adslAturConfRateChanRatio / 100)
			as long as it is < adslAturChanConfMaxTxRate"
		::= { usrAdslf 47 }

		adslAturChanPrevTxRate OBJECT-TYPE
		    SYNTAX	INTEGER
		    ACCESS	read-only
		    STATUS	mandatory
		    DESCRIPTION
			"The rate that was set at the previous adslAturRateChangeTrap event.
			It is also set at initialization to prevent a trap being sent.
			Small rate changes are accumulated until either the rate changes by
			adslAturChanConfDownDeltaRate or adslAturChanConfUpDeltaRate."
		::= { usrAdslf 48 }


		-- performance group
		-- Note: block is intended to mean Reed Solomon Frame
		-- or other low-level encoding block,
		-- NOT an HDLC frame or other high-level block
		-- basic  statistics
		adslAturChanReceivedBlocks OBJECT-TYPE
		    SYNTAX	Counter
		    ACCESS	read-only
		    STATUS	mandatory
		    DESCRIPTION
			"count of all encoded blocks received on this channel."
		::= { usrAdslf 49 }

		adslAturChanTransmittedBlocks  OBJECT-TYPE
		    SYNTAX	Counter
		    ACCESS	read-only
		    STATUS	mandatory
		    DESCRIPTION
			"count of all encoded blocks transmitted on this channel."
		::= { usrAdslf 50 }

		adslAturChanCorrectedBlocks  OBJECT-TYPE
		    SYNTAX	Counter
		    ACCESS	read-only
		    STATUS	mandatory
		    DESCRIPTION
			"count of all blocks received with errors that were corrected.
			These blocks are passed on as good data."
		::= { usrAdslf 51 }

		adslAturChanUncorrectableBlocks  OBJECT-TYPE
		    SYNTAX	Counter
		    ACCESS	read-only
		    STATUS	mandatory
		    DESCRIPTION
			"count of all blocks received with uncorrectable errors.
			These blocks are dropped from the received data stream."
		::= { usrAdslf 52 }


 
        usrAdslCFMStatusFlag OBJECT-TYPE
         SYNTAX  UsrConfigStatus
         ACCESS  read-write
         STATUS  mandatory
         DESCRIPTION
                "This variable controls saving and loading of configuration
                information for the ADSL WAN Driver. The value can be set
                to either save or load by a management station. The other
                values indicate if any configuration operation and what type
                is in progress."
         ::= { usrAdslf 53 }
 
 
       usrAdslCfgFileName OBJECT-TYPE
         SYNTAX  DisplayString
         ACCESS  read-only
         STATUS  mandatory
         DESCRIPTION
                "The name of a ConfigFile to read/write the ADSL parameters.
                 If the value of this object is an empty string, then the
                 ADSL Driver uses the default name `@file://adsl.cfg'."
         ::= { usrAdslf 54 }
 
       usrAdslResetStatus OBJECT-TYPE
         SYNTAX   INTEGER
         ACCESS   read-write
         STATUS   mandatory
         DESCRIPTION
            "The Reset Status of the ADSL Starlet chipset"
         ::= { usrAdslf 55 }
 

       usrAdslActualBaudDataRateDwn OBJECT-TYPE
         SYNTAX   DisplayString
         ACCESS   read-only
         STATUS   mandatory
         DESCRIPTION
            "Actual Downstream Baud Rate"
         ::= { usrAdslf 56 }
 
        usrAdslFwRel OBJECT-TYPE
         SYNTAX   DisplayString
         ACCESS   read-only
         STATUS   mandatory
         DESCRIPTION
            "Firmware release number of the GTI supplied transceiver
             software module."
         ::= { usrAdslf 57 }


        usrAdslAdiVerson OBJECT-TYPE
         SYNTAX   INTEGER
         ACCESS   read-only
         STATUS   mandatory
         DESCRIPTION
            "Value is a number that corresponds to the version number of
             the ADI chipset."
         ::= { usrAdslf 58 }


-- Followings are only temporary. They are used by HTML. It be here untill HTML get changed

       usrAdslLocalReqDwnConstStatus OBJECT-TYPE
         SYNTAX   INTEGER {
                                                   const-8(1),
                                                   const-16(2),
                                                   const-32(3),
                                                   const-64(4),
                                                   const-128(5),
                                                   const-256(6),
                                                   const-256U(7)
                          }
         ACCESS   read-write
         STATUS   mandatory
         DESCRIPTION
                "Value corresponds to the local downstream constellation
                 requested."
           DEFVAL { 1 }
         --CONFIGURABLE
         ::= { usrAdslf 59 }

        usrAdslActualUpConstStatus OBJECT-TYPE
         SYNTAX   INTEGER {
                                                   const-auto(1),
                                                   const-8(2),
                                                   const-8ER(3),
                                                   const-16(4),
                                                   const-32(5),
                                                   const-64(6),
                                                   const-128(7),
                                                   const-256(8),
                                                   const-256U(9),
                                                   unavailable-LinkDown(10)
                          }
         ACCESS   read-only
         STATUS   mandatory
         DESCRIPTION
                "Value corresponds to the actual upstream constellation
                 that was used, which may differ from the value requested."
         ::= { usrAdslf 60 }
 

        usrAdslRemoteReqBaudDataRateDwn OBJECT-TYPE
         SYNTAX   INTEGER {
                           baud-340K(1),
                           baud-680K(2),
                           baud-952K(3),
                                                   unavailable-LinkDown(4)
                          }
         ACCESS   read-only
         STATUS   mandatory
         DESCRIPTION
            "Remote Downstream Baud Rate requested by the User."
         ::= { usrAdslf 90 }
 

        usrAdslRemoteReqUpConstStatus OBJECT-TYPE
         SYNTAX   INTEGER {
                                                   const-auto(1),
                                                   const-8(2),
                                                   const-8ER(3),
                                                   const-16(4),
                                                   const-32(5),
                                                   const-64(6),
                                                   const-128(7),
                                                   const-256(8),
                                                   const-256U(9),
                                                   unavailable-LinkDown(10)
                          }
         ACCESS   read-only
         STATUS   mandatory
         DESCRIPTION
                "Value corresponds to the remote requested downstream constellation
                 requested."
         ::= { usrAdslf 62 }

 
        usrAdslStartletVerson OBJECT-TYPE
         SYNTAX   INTEGER (0..4)
         ACCESS   read-only
         STATUS   mandatory
         DESCRIPTION
            "Value is a number that corresponds to the version number of
             the STARLET VLSI in the transceiver."
         ::= { usrAdslf 63 }
 

 
        usrAdslActualDwnConstStatus OBJECT-TYPE
         SYNTAX   INTEGER {
                                                   const-auto(1),
                                                   const-8(2),
                                                   const-8ER(3),
                                                   const-16(4),
                                                   const-32(5),
                                                   const-64(6),
                                                   const-128(7),
                                                   const-256(8),
                                                   const-256U(9),
                                                   unavailable-LinkDown(10)
                          }
         ACCESS   read-only
         STATUS   mandatory
         DESCRIPTION
                "Value corresponds to the actual downstream constellation
                 that was used, which may differ from the value requested."
         ::= { usrAdslf 64 }


        usrAdslLocalReqUpConstStatus OBJECT-TYPE
         SYNTAX   INTEGER {
                                                   const-8(1),
                                                   const-16(2),
                                                   const-32(3),
                                                   const-64(4),
                                                   const-128(5),
                                                   const-256(6),
                                                   const-256U(7)
                          }
         ACCESS   read-write
         STATUS   mandatory
         DESCRIPTION
                "Value corresponds to the local upstream constellation
                 requested."
           DEFVAL { 1 }
         --CONFIGURABLE
         ::= { usrAdslf 65 }
 

        usrAdslRemoteReqDwnConstStatus OBJECT-TYPE
         SYNTAX   INTEGER {
                                                   const-auto(1),
                                                   const-8(2),
                                                   const-8ER(3),
                                                   const-16(4),
                                                   const-32(5),
                                                   const-64(6),
                                                   const-128(7),
                                                   const-256(8),
                                                   const-256U(9),
                                                   unavailable-LinkDown(10)
                          }
         ACCESS   read-only
         STATUS   mandatory
         DESCRIPTION
                "Value corresponds to the remote downstream constellation
                 requested."
         ::= { usrAdslf 66 }
 

        usrAdslLocalReqBaudDataRateDwn OBJECT-TYPE
         SYNTAX   INTEGER {
                           baud-340K(1),
                           baud-680K(2),
                           baud-952K(3)
                          }
         ACCESS   read-write
         STATUS   mandatory
         DESCRIPTION
            "Local Downstream Baud Rate requested by the User."
          DEFVAL { 1 }
         --CONFIGURABLE
         ::= { usrAdslf 67 }


        usrAdslFixBitStatus OBJECT-TYPE
         SYNTAX   INTEGER {
                           enabled(1),
                           disabled(2)
                          }
         ACCESS   read-write
         STATUS   mandatory
         DESCRIPTION
            "Fixed Bit Rate feature status."
           DEFVAL { 2 }
         --CONFIGURABLE
         ::= { usrAdslf 68 }

        usrAdslLocalReqXmitPower OBJECT-TYPE
         SYNTAX   INTEGER {
                           zero-dB(1),
                           minus3-dB(2),
                           minus6-dB(3),
                           minus9-dB(4),
                           minus12-dB(5),
                           minus15-dB(6)
                          }
         ACCESS   read-write
         STATUS   mandatory
         DESCRIPTION
            "Transmit power requested at the local ADSL transceiver represented i n dB."
           DEFVAL { 1 }
         --CONFIGURABLE
         ::= { usrAdslf 69 }


        usrAdslRemoteProtocolType OBJECT-TYPE
         SYNTAX   INTEGER {
                           v109(1),
                           v208orHigher(2),
                                                   unavailable-LinkDown(3)
                          }
         ACCESS   read-only
         STATUS   mandatory
         DESCRIPTION
            "Protocol type in use by the remote RTU."
         ::= { usrAdslf 70 }

        usrAdslMeanSqError OBJECT-TYPE
         SYNTAX   DisplayString
         ACCESS   read-only
         STATUS   mandatory
         DESCRIPTION
            "Received signal to noise ratio."
         ::= { usrAdslf 71 }

        usrAdslLocalActualXmitPower OBJECT-TYPE
         SYNTAX   DisplayString
         ACCESS   read-only
         STATUS   mandatory
         DESCRIPTION
            "Transmit power of the local ADSL transceiver represented in dB."
         ::= { usrAdslf 72 }

  usrAdslOverFlowCounter OBJECT-TYPE
         SYNTAX   Counter
         ACCESS   read-only
         STATUS   mandatory
         DESCRIPTION
            "Running counter for when usrAdslBytesErrorCorrected or
             usrAdslBytesNotErrorCorrected overflows. This Number is reset
             to zero each time the Transceiver transitions from Idle Mode to Data Mode."
         ::= { usrAdslf 73 }


        usrAdslLastFailedStatus OBJECT-TYPE
         SYNTAX   INTEGER {
                           no-failure(1),
                           handshake-failure(2),
                           training-failure(3),
                           download-failure(4),
                           invalid-parm(5)
                          }
         ACCESS   read-only
         STATUS   mandatory
         DESCRIPTION
            "Defines the last detailed state reached in
             usrAdslStartupProgress before startup failed."
         ::= { usrAdslf 74 }

        usrAdslBytesNotErrCorrected OBJECT-TYPE
         SYNTAX   Counter
         ACCESS   read-only
         STATUS   mandatory
         DESCRIPTION
            "Number of bytes not corrected by Reed-Solomon error correction
             algorithm in the STARLET.This Number is reset to zero each
             time the Transceiver transitions from Idle Mode to Data
Mode."
         ::= { usrAdslf 75 }

 


        usrAdslOpState OBJECT-TYPE
         SYNTAX   INTEGER {
                                                   idleMode(1),
                                                   dataMode(2)
                          }
         ACCESS   read-only
         STATUS   mandatory
         DESCRIPTION
            "Defines the high level operating state of the transceiver.
             Used by the customer to determine whether the transceiver
             is in idle mode or data mode."
           DEFVAL { 1 }
         --CONFIGURABLE
         ::= { usrAdslf 76 }


        usrAdslBytesErrCorrected OBJECT-TYPE
         SYNTAX   Counter
         ACCESS   read-only
         STATUS   mandatory
         DESCRIPTION
            "Number of bytes corrected by Reed-Solomon error correction
             algorithm in the STARLET.This Number is reset to zero each
                         time the Transceiver transitions from Idle Mode to Data Mode."
         ::= { usrAdslf 77 }

        usrAdslLocalProtocolType OBJECT-TYPE
         SYNTAX   INTEGER {
                           v109(1),
                           v208orHigher(2),
                                                   unavailable-LinkDown(3)
                          }
         ACCESS   read-only
         STATUS   mandatory
         DESCRIPTION
            "Protocol type in use by the local RTU."
         ::= { usrAdslf 78 }


 

 
        usrAdslLastFailedErrorValue OBJECT-TYPE
         SYNTAX   INTEGER (0..255)
         ACCESS   read-only
         STATUS   mandatory
         DESCRIPTION
            "Defines the last detailed value reached in
             usrAdslStartupProgress before startup failed."
         ::= { usrAdslf 79 }
 

 
        usrAdslLocalReceiverGain OBJECT-TYPE
         SYNTAX   DisplayString
         ACCESS   read-only
         STATUS   mandatory
         DESCRIPTION
            "Total local receiver gain measured in dB."
         ::= { usrAdslf 81 }


        usrAdslSwitchType OBJECT-TYPE
         SYNTAX   INTEGER {
                     v3alcatel(1),
                     v4alcatel(2),
		     adi(3)
                          }
         ACCESS   read-write
         STATUS   mandatory
         DESCRIPTION
            "DSLAM switch type."
           DEFVAL { 1 }
         --CONFIGURABLE
         ::= { usrAdslf 82 }
 



END
